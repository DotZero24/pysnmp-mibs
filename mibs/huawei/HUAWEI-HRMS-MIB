-- ===================================================================
-- Copyright (C) 2018 by HUAWEI TECHNOLOGIES. All rights reserved.
-- Description:
-- Reference:
-- Version: V1.01
-- ===================================================================


    HUAWEI-HRMS-MIB DEFINITIONS ::= BEGIN

        IMPORTS
            OBJECT-GROUP, MODULE-COMPLIANCE, NOTIFICATION-GROUP
                FROM SNMPv2-CONF
            TimeTicks, Integer32, Unsigned32, IpAddress, Counter32, OBJECT-TYPE,
            MODULE-IDENTITY, NOTIFICATION-TYPE
                FROM SNMPv2-SMI
            hwDatacomm
                FROM HUAWEI-MIB;


        hwHRMS MODULE-IDENTITY
            LAST-UPDATED "201801151600Z"
            ORGANIZATION
                  "Huawei Technologies Co.,Ltd."
            CONTACT-INFO
                  "Huawei Industrial Base
                   Bantian, Longgang
                  Shenzhen 518129
                  People's Republic of China
                  Website: http://www.huawei.com
                  Email: support@huawei.com "

            DESCRIPTION
               "The MIB module describes Huawei NE device availability Statistics"
            REVISION    "201801151600Z"
            DESCRIPTION "V1.01, initial version."

            REVISION    "201304151600Z"
            DESCRIPTION "V1.00, initial version."

            ::= { hwDatacomm 354 }

    hwHRMSObjects  OBJECT IDENTIFIER ::= { hwHRMS  1 }

    hwsysHaltCount OBJECT-TYPE
        SYNTAX  Integer32
        MAX-ACCESS  read-only
        STATUS  current
        DESCRIPTION
            "This object indicates the number of times the system is stopped after the startup of network management."
        ::= { hwHRMSObjects  1 }

    hwsysHaltTime OBJECT-TYPE
        SYNTAX  Integer32
        MAX-ACCESS  read-only
        STATUS  current
        DESCRIPTION
                "This object indicates the total duration in which the system is stopped after the startup of network management."
        ::= { hwHRMSObjects  2 }

    hwHRMSConformance OBJECT IDENTIFIER ::= { hwHRMS  2 }

    hwHRMSCompliances MODULE-COMPLIANCE
            STATUS current
            DESCRIPTION
                "The compliance statement for systems supporting
                the HUAWEI HRMS MIB."
            MODULE
                MANDATORY-GROUPS {hwsysHaltCount, hwsysHaltTime  }
            ::= { hwHRMSConformance 1 }

    hwHRMSGroup OBJECT-GROUP
            OBJECTS
           {hwsysHaltCount, hwsysHaltTime  }
            STATUS current
            DESCRIPTION
                "Group for HRMS objects."
            ::= { hwHRMSConformance 2 }

    END

--
-- HUAWEI-HRMS-MIB.mib
--
