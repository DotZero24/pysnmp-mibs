-- ============================================================================
-- Copyright (C) 2018 by  HUAWEI TECHNOLOGIES. All rights reserved.
-- Description:  This mib is used for defining huawei's XDSL line management MIB objects.
-- Reference:
-- Version: V2.00
-- ============================================================================
    HUAWEI-XDSL-LINE-MIB DEFINITIONS ::= BEGIN

        IMPORTS
            MODULE-IDENTITY, OBJECT-TYPE, Unsigned32, NOTIFICATION-TYPE,
            Integer32, Counter32, Gauge32, Counter64
               FROM SNMPv2-SMI
            huaweiUtility
              FROM HUAWEI-MIB
            ifIndex
               FROM IF-MIB
            TruthValue, DateAndTime,  RowStatus, TEXTUAL-CONVENTION
               FROM SNMPv2-TC
            hwFrameIndex, hwSlotIndex, hwPortIndex, hwPortOperStatus, hwPortPrimaryStatus, hwPortSecondaryStatus,
            hwConfigChangeIP
               FROM HUAWEI-DEVICE-MIB
            HCPerfIntervalThreshold, HCPerfTimeElapsed
               FROM  HC-PerfHist-TC-MIB   -- [RFC3705]
            hwXdslProfName
               FROM HUAWEI-XDSL-COMMON-MIB
            HwXdslUnit,
            HwXdslDirection,
            HwXdslTransmissionModeType,
            HwXdslRaMode,
            HwXdslInitResult,
            HwXdslOperationModes,
            HwXdslPowerMngState,
            HwXdslConfPmsForce,
            HwXdslLConfProfPmMode,
            HwXdslLineLdsf,
            HwXdslLdsfResult,
            HwXdslSymbolProtectionDs,
            HwXdslSymbolProtectionUs,
            HwXdslMaxBer,
            HwXdslScMaskDs,
            HwXdslScMaskUs,
            HwXdslRfi,
            HwXdslvdsltoneblackout,
            HwXdslPsdMaskDs,
            HwXdslPsdMaskUs,
            HwXdslTssi,
            HwXdslBandPlan,
            HwXdslLastTransmittedState,
            HwXdslLineStatus,
            HwXdslChAtmStatus,
            HwXdslChPtmStatus,
            HwXdslBandOptUsage,
            HwXdslPSDClassMask,
            HwXdslProfiles,
            HwXdslDataPathMode,
            HwXdslDpboEpsd,
            HwXdslDpboEscm,
            HwXdslUpboPsdBand,
            HwXdslUpboKl0RefBand,
            HwXdslUpboKlf,
            HwXdslBitSwap,
            HwXdslUpboBoostMode,
            HwXdslProfSwitchType,
            HwXdslForceINP,
            HwXdslPhyRControl,
            HwXdslChEnabling,
            HwXdslDataPathModeType,
            HwXdslSubProfiles,
            HwXdslSubProfilesWeight,
            HwXdslUs0PsdMask,
            HwXdslUpsPsdMaskSelection,
            HwXdslTIPsdClassMask,
            HwXdslPsdLimitMask,
            HwXdslUs0Disable,
            HwVdslCfgMode,
            HwXdslBand,
            HwXdslVirtualNoise,
            HwXdslVirtualNoiseDs,
            HwXdslVirtualNoiseUs,
            HwXdslAutoProfile,
            HwXdslStatusRtxUsed,
            HwXdslActmode
               FROM   HUAWEI-XDSL-LINE-TC-MIB       -- [This document]
            MODULE-COMPLIANCE, OBJECT-GROUP, NOTIFICATION-GROUP
               FROM SNMPv2-CONF
            HWVOPGfastProfiles,
            Xdsl2CarMask,
            Xdsl2UpboKLF,
            Xdsl2RfiBands,
            HWVOPGfastIarBands,
            Xdsl2LineSnrMode,
            HWVOPGfastRaMode,
            HWVOPGfastPsdMask
               FROM HUAWEI-VOP-MIB;


        hwXdslMIB MODULE-IDENTITY
            LAST-UPDATED "201809120000Z"
            ORGANIZATION "Huawei Technologies Co.,Ltd."
            CONTACT-INFO
                         "Huawei Industrial Base
                          Bantian, Longgang
                          Shenzhen 518129
                          People's Republic of China
                          Website: http://www.huawei.com
                          Email: support@huawei.com
                         "
            DESCRIPTION
               "This mib is used for defining huawei's XDSL line management MIB objects."

            --  Revision history
            REVISION     "201809120000Z"
            DESCRIPTION  "V2.00, Modified the description of hwXdslNlvSCFextVictimPeerId and hwXdslNlvSCFextDisturberPeerId.
                         Modified the description of hwXdslUnSuppVectorPortActFailAlarmTrap,hwXdslVdsl2Profile35bFallbackFaultAlarmTrap
						 and hwXdslVdsl2Profile35bFallbackRecoveryAlarmTrap.
                         "
            REVISION     "201805260000Z"
            DESCRIPTION  "V1.99, changes in this revision:
                          1.Add leaf node
                           hwXdslPMChCurr15MLANDEFTRS,
                           hwXdslPMChCurr1DayLANDEFTRS,
                           hwXdslPMChEverBeforeLANDEFTRS,
                           hwXdslPMChCurr15MANDEFTRDS,
                           hwXdslPMChCurr1DayANDEFTRDS,
                           hwXdslPMChEverBeforeANDEFTRDS,
                           hwXdslPMChCurr15MMINANDEFTR,
                           hwXdslPMChCurr1DayMINANDEFTR,
                           hwXdslPMChEverBeforeMINANDEFTR,
                           hwXdslPMChCurr15MMAXANDEFTR,
                           hwXdslPMChCurr1DayMAXANDEFTR,
                           hwXdslPMChEverBeforeMAXANDEFTR,
                           hwXdslPMChCurr15MSUMANDEFTR,
                           hwXdslPMChCurr1DaySUMANDEFTR,
                           hwXdslPMChEverBeforeSUMANDEFTR
                           in hwXdslPMChCurrTable.
                          2.Add leaf node
                           hwXdslPMChHist15MLANDEFTRS,
                           hwXdslPMChHist15MANDEFTRDS,
                           hwXdslPMChHist15MMINANDEFTR,
                           hwXdslPMChHist15MMAXANDEFTR,
                           hwXdslPMChHist15MSUMANDEFTR
                           in hwXdslPMChHist15MinTable.
                          3.Add leaf node
                           hwXdslPMChHist1DLANDEFTRS,
                           hwXdslPMChHist1DANDEFTRDS,
                           hwXdslPMChHist1DMINANDEFTR,
                           hwXdslPMChHist1DMAXANDEFTR,
                           hwXdslPMChHist1DSUMANDEFTR
                           in hwXdslPMChHist1DTable.
                          4.Add leaf node
                           hwXdslTR129ChConfProfGfastLowANDEFTRThresholdDs,
                           hwXdslTR129ChConfProfGfastLowANDEFTRThresholdUs
                           in hwXdslTR129ChConfProfileTable.
                          5.Modify the DESCRIPTION and SYNTAX INTEGER of hwVdslLConfProfPSDClassMask.
                          6.Add leaf node
                          hwVdslConfProfPSDMaskOffset,
                          hwVdslConfProfPSDBuriedAtten
                          in hwVdslLineConfProfModeSpecTable.
			  7. Add table hwXdslNlvSCFextTable.
                          "

            REVISION     "201805090000Z"
            DESCRIPTION  "V1.98, changes in this revision:
                         1.Modify the description of hwXdslVdsl2LrModeGlobalConfigSwitch and hwXdslLInvVdslLrSupport.
                         "

            REVISION     "201804270000Z"
            DESCRIPTION  "V1.97, changes in this revision:
                         1.Add leaf node
                          hwXdslLineStatusActVdsl2LrMode,
                          hwXdslLInvVdslLrSupport,
                          hwVdslLConfProfLrMode,
                          hwXdslVdsl2LrModeGlobalConfigSwitch,
                          hwXdslVdsl2LrMode.
                         "

            REVISION     "201801220000Z"
            DESCRIPTION  "V1.96, changes in this revision:
                        1.Add leaf node
                          hwXdslToneBlackoutGlobalConfigSwitch,
                          hwXdslVdslToneBlackoutGlobalConfig,
                          hwXdslGfastCarMaskGlobalConfigDs,
                          hwXdslGfastCarMaskGlobalConfigUs,
                          hwXdslGfastLowFreqEdgeGlobalConfigSwitch,
                          hwXdslGfastLowFreqEdgeGlobalConfigDs,
                          hwXdslGfastLowFreqEdgeGlobalConfigUs.
			 "

            REVISION     "201704110000Z"
            DESCRIPTION  "V1.95, Modify the description of hwXdslTR129ChConfProfGfastMaxDelayRtxDs and hwXdslTR129ChConfProfGfastMaxDelayRtxUs.
                         "

            REVISION     "201701090000Z"
            DESCRIPTION  "V1.94, Modify the description of  hwXdslTR129LineConfProfGfastPsdMaskDs and hwXdslTR129LineConfProfGfastPsdMaskUs.
                         "
            REVISION     "201609210000Z"
            DESCRIPTION  "V1.93, changes in this revision:
                        1.Add leaf node hwXdslLineCnfgTR129RfiProf, hwXdslGlobalConfigRfiNotchBands, hwXdslTR129LineConfProfGfastFallbackFreq,
                        2.Modify the name of these leaves: hwXdslGlobalConfigRfiNotchDescription,hwXdslGlobalConfigRfiNotchSwitch.
                        3.Modify the description of these leaves: hwXdslGlobalConfigRfiNotchDescription,hwXdslGlobalConfigRfiNotchSwitch,hwGfastModeCfg.
			 "

            REVISION     "201609090000Z"
            DESCRIPTION  "V1.92, changes in this revision:
                        1.Modify the description of these entry: hwOntXdslSCStatusSegmentEntry.
			 "

            REVISION     "201608100000Z"
            DESCRIPTION  "V1.91, changes in this revision:
                        1.Add leaf node hwXdslLineVdsl2ProfileFallbackstatus.
			 "

            REVISION     "201606200000Z"
            DESCRIPTION  "V1.90, changes in this revision:
                        1.Add leaf node hwXdslBypassAutoRecoverTime.
                         "
            REVISION     "201606150000Z"
            DESCRIPTION  "V1.89, changes in this revision:
                        1.Modify the value range and description of these leaves:
                          hwOntXdslSCStatusSegmentLogScGroupSize,
                          hwOntXdslSCStatusSegmentQlnScGroupSize,
                          hwOntXdslSCStatusSegmentLinScGroupSize,
                          hwOntXdslSCStatusSegmentSnrScGroupSize.
                        2.Modify the description of this leaf: hwOntXdslSCStatusSegmentTxPSD.
                         "
            REVISION     "201606070000Z"
            DESCRIPTION  "V1.88, changes in this revision:
                        1.Modify the name of these leaves: hwXdslTR129LineConfProfGfastLineLowFreqEdgeValue,
                        2.Add leaf node
                          hwXdslTR129LineConfProfGfastLineLowFreqEdgeValueUs.
                         "

            REVISION     "201605270000Z"
            DESCRIPTION  "V1.87, changes in this revision:
                        1.Add table of hwOntXdslSCStatusSegmentTable,
                        2.Add leaf node
                          hwOntXdslSCStatusDirection,
                          hwOntXdslSCStatusSegment,
                          hwOntXdslSCStatusSegmentLinReal,
                          hwOntXdslSCStatusSegmentLinImg,
                          hwOntXdslSCStatusSegmentLog,
                          hwOntXdslSCStatusSegmentQln,
                          hwOntXdslSCStatusSegmentSnr,
                          hwOntXdslSCStatusSegmentBitsAlloc,
                          hwOntXdslSCStatusSegmentGainAlloc,
                          hwOntXdslSCStatusSegmentTxPSD,
                          hwOntXdslSCStatusSegmentSnrMargin,
                          hwOntXdslSCStatusSegmentLogScGroupSize,
                          hwOntXdslSCStatusSegmentQlnScGroupSize,
                          hwOntXdslSCStatusSegmentLinScGroupSize,
                          hwOntXdslSCStatusSegmentSnrScGroupSize
                          in hwOntXdslSCStatusSegmentTable.
                         "

            REVISION     "201604230000Z"
            DESCRIPTION  "V1.86, changes in this revision:
                          Add leaf node hwXdslVdsl2Profile35bFallbackFaultAlarmTrap,
                          hwXdslVdsl2Profile35bFallbackRecoveryAlarmTrap,
                          hwXdslLineVdsl2ProfileConfig,
                          hwXdslLineVdsl2ProfileFallback.
                         "

            REVISION     "201603220000Z"
            DESCRIPTION  "V1.85, changes in this revision:
                          Modify the description of these leaf: hwXdslTR129LineConfProfGfastCarMaskUs,hwXdslTR129LineConfProfGfastMinSnrmRmcUs.
                         "

            REVISION     "201603100000Z"
            DESCRIPTION  "V1.84, changes in this revision:
                       1. Add leaf node
                          hwXdslTR129LineConfProfGfastCarMaskUs,
                          hwXdslTR129LineConfProfGfastTargetSnrmRmcDs,
                          hwXdslTR129LineConfProfGfastTargetSnrmRmcUs,
                          hwXdslTR129LineConfProfGfastMinSnrmRmcDs,
                          hwXdslTR129LineConfProfGfastMinSnrmRmcUs,
                          hwXdslTR129LineConfProfGfastMaxBLRmcDs,
                          hwXdslTR129LineConfProfGfastMaxBLRmcUs,
                          hwXdslTR129LineConfProfGfastSosFraVenDiscDs,
                          hwXdslTR129LineConfProfGfastSosFraVenDiscUs.
                        2.Modify the value range of these leaves: hwXdslTR129LineConfProfGfastLineLowFreqEdgeValue.
                        3.Modify the name of these leaves: hwXdslTR129LineConfProfGfastCarMask.
                         "

            REVISION     "201603080000Z"
            DESCRIPTION  "V1.83, changes in this revision:
                          Modify the value range of these leaf: hwXdslGlobalConfigGfastRfiNotchDescription.
                         "

            REVISION     "201602250000Z"
            DESCRIPTION  "V1.82, changes in this revision:
                          Modify the description of these leaf: hwXdslVdsl2Profile35bFallbackConfigValue.
                         "

            REVISION     "201601200000Z"
            DESCRIPTION  "V1.81, changes in this revision:
                          Add leaf node hwXdslVdsl2Profile35bFallbackConfigValue in hwXdslGlobalConfig.
                         "

            REVISION     "201511070000Z"
            DESCRIPTION  "V1.80, changes in this revision:
                        1.Modify the value range of these leaves:
                          hwVdslChConfProfMinDataRateDs,
                          hwVdslChConfProfMinDataRateUs,
                          hwVdslChConfProfMinResDataRateDs,
                          hwVdslChConfProfMinResDataRateUs,
                          hwVdslChConfProfMaxDataRateDs,
                          hwVdslChConfProfMaxDataRateUs,
                          hwVdslChConfProfMinDataRateLowPwrDs,
                          hwVdslChConfProfMaxDataRateLowPwrDs,
                          hwVdslChConfProfUsDataRateDs,
                          hwVdslChConfProfDsDataRateDs,
                          hwVdslChConfProfUsDataRateUs,
                          hwVdslChConfProfDsDataRateUs,
                          hwVdslChConfProfMinEtrRtxDs,
                          hwVdslChConfProfMinEtrRtxUs,
                          hwVdslChConfProfMaxEtrRtxDs,
                          hwVdslChConfProfMaxEtrRtxUs,
                          hwVdslChConfProfMaxNdrRtxDs,
                          hwVdslChConfProfMaxNdrRtxUs,
                          hwVdslLConfProfDpboFmax.
                        2.Modify the description of these leaf: hwVdslLConfProfPSDClassMask.
                        3.Add leaf node
                          hwXdslChStatusInpReportingMode in hwXdslChannelStatusTable.
                        4.Add leaf node
                          hwXdslPMLCurr15MBitswapSuccess,
                          hwXdslPMLCurr15MTigaSuccess,
                          hwXdslPMLCurr1DayBitswapSuccess,
                          hwXdslPMLCurr1DayTigaSuccess,
                          hwXdslPMLEverBeforeBitswapSuccess,
                          hwXdslPMLEverBeforeTigaSuccess in hwXdslPMLineCurrTable,
                        5.Add leaf node
                          hwXdslPMLineHist15MBitswapSuccess,
                          hwXdslPMLineHist15MTigaSuccess in hwXdslPMLineHist15MinTable.
                        6.Add leaf node
                          hwXdslPMLineHist1DayBitswapSuccess,
                          hwXdslPMLineHist1DayTigaSuccess in hwXdslPMLineHist1DayTable.
                         "

            REVISION     "201511040000Z"
            DESCRIPTION  "V1.79, changes in this revision:
                          Add leaf node hwXdslGlobalConfigGfastRfiNotchSwitch,hwXdslGlobalConfigGfastRfiNotchBands,
                          hwXdslGlobalConfigGfastIarNotchBands,hwXdslGlobalConfigGfastRfiNotchDescription in hwXdslGlobalConfig.
                         "

            REVISION     "201510140000Z"
            DESCRIPTION  "V1.78, changes in this revision:
                          1. Add leaf node hwXdslPMLineCurrInit15MAbnormalReInit,hwXdslPMLineCurrInit1DayAbnormalReInit,hwXdslPMLineCurrInitEverBeforeAbnormalReInit
                             in hwXdslPMLineCurrInitTable.
                          2. Add leaf node hwXdslPMLHistInit15MAbnormalReInit in hwXdslPMLineInitHist15MinTable.
                          3. Add leaf node hwXdslPMLHistinit1DAbnormalReInit in hwXdslPMLineInitHist1DayTable.
                         "

            REVISION     "201510130000Z"
            DESCRIPTION  "V1.77, Modify node description of leaf hwXdslTR129LineConfProfGfastPsdMaskDs and hwXdslTR129LineConfProfGfastPsdMaskUs."

            REVISION     "201509240000Z"
            DESCRIPTION  "V1.76, changes in this revision:
              1.Add leaf node hwXdslLineCurrentGfastSnrMarginRmcDs,hwXdslLineCurrentGfastSnrMarginRmcUs in hwXdslLineCfgTable.
              Add leaf node hwXdslSCStatusSegmentBitsAllocRmc in hwXdslSCStatusSegmentTable.
              Add leaf node hwXdslPMLCurr15MLors,hwXdslPMLCurr15MLor,hwXdslPMLCurr15MRpaSuccess,hwXdslPMLCurr1DayLors,
              hwXdslPMLCurr1DayLor,hwXdslPMLCurr1DayRpaSuccess,hwXdslPMLEverBeforeLors,hwXdslPMLEverBeforeLor,
              hwXdslPMLEverBeforeRpaSuccess in hwXdslPMLineCurrTable.
              Add leaf node hwXdslPMLineHist15MLors,hwXdslPMLineHist15MLor,hwXdslPMLineHist15MRpaSuccess in hwXdslPMLineHist15MinTable.
              Add leaf node hwXdslPMLineHist1DayLors,hwXdslPMLineHist1DayLor,hwXdslPMLineHist1DayRpaSuccess in hwXdslPMLineHist1DayTable.
              2.Modify the description of these leaves:
              hwXdslLineStatusXtur,hwXdslLineStatusXtuc,hwXdslSCStatusSegmentQln,hwXdslSCStatusSegmentQlnWithVectoring,
              hwXdslPMLCurr15MSosSuccess,hwXdslPMLCurr1DaySosSuccess,hwXdslPMLEverBeforeSosSuccess,hwXdslPMLHist15MSosSuccess,
              hwXdslPMLHist1DSosSuccess."


            REVISION     "201509210000Z"
            DESCRIPTION  "V1.75, Modify node description and SYNTAX of leaf hwXdslTR129LineConfProfMode."

            REVISION     "201509100000Z"
            DESCRIPTION  "V1.74, changes in this revision:
                          1.Modify the name of table hwXdslLineConfTemplateTable,hwXdslLineConfProfTable,hwXdslLineConfProfTable
                          and all names of leaf nodes which belong to these tables.
                          Modify the name of node hwXdslLConfTempTemplateChangeTrap,hwXdslLConfProfProfileChangeTrap,hwXdslChConfProfProfileChangeTrap.
                          hwXdslModeSwitchTrap,hwXdslCurrentModeTrap and hwVdslmodecfg.
                          The modify rule is:change 'hwXdsl' to 'hwVdsl' .For example :change the name of hwXdslLineConfTemplateTable to hwVdslLineConfTemplateTable.
                          2.Add table hwXdslTR129LineConfTemplateTable,hwXdslTR129LineConfProfTable,
                          hwXdslTR129LineConfProfModeSpecTable and hwXdslTR129ChConfProfileTable.
                          3.Add node hwXdslTR129LineTemplateChangeTrap,hwXdslTR129LineProfileChangeTrap,hwXdslTR129ChannelProfileChangeTrap
                            hwXdslTR129ChannelProfileChangeTrap,hwGfastModeSwitchTrap and hwGfastCurrentModeTrap.
                          4.Expend the value rang of hwXdslTemplateType,add parameter 'xdsltr129lineConfTemplate(10)'.
                          5.Modify the description of leaf hwXdslModeSwitchResult.
                          6.Add leaf hwGfastModeCfg.
                          7.Modify the description of following nodes hwXdslSCStatusSegmentSnr,hwXdslSCStatusSegmentSnr."

            REVISION     "201509080000Z"
            DESCRIPTION  "V1.73, changes in this revision:
                          Modify the value range of these leaves: hwXdslSCStatusLinScGroupSize,hwXdslSCStatusLogScGroupSize,hwXdslSCStatusQlnScGroupSize,
                          hwXdslSCStatusSnrScGroupSize,hwXdslSCStatusSegmentLogScGroupSize,hwXdslSCStatusSegmentQlnScGroupSize,hwXdslSCStatusSegmentLinScGroupSize,
                          hwXdslSCStatusSegmentSnrScGroupSize.
                          Modify the description of these leaves: hwXdslSCStatusLinScGroupSize,hwXdslSCStatusLogScGroupSize,hwXdslSCStatusQlnScGroupSize,
                          hwXdslSCStatusSnrScGroupSize,hwXdslSCStatusSegmentLogScGroupSize,hwXdslSCStatusSegmentQlnScGroupSize,hwXdslSCStatusSegmentLinScGroupSize,
                          hwXdslSCStatusSegmentSnrScGroupSize.
                          "

            REVISION     "201508130000Z"
            DESCRIPTION  "V1.72, changes in this revision:
                          Modify the value range of these leaves: hwXdslLineStatusActPsdLimitMask.
                          Modify the description of these leaf: hwXdslSCStatusClassmask.
                          "

            REVISION     "201507250000Z"
            DESCRIPTION  "V1.71, changes in this revision:
                          Modify the description of these leaf: hwOntXdslChStatusINP.
                          "

            REVISION     "201507100000Z"
            DESCRIPTION  "V1.70, changes in this revision:
                          Modify the value range of these leaves: hwXdslChStatusActDataRate,hwXdslChStatusPrevDataRate,hwXdslChStatusActEftr.
                          Modify the description of these leaves: hwXdslSCStatusClassmask,hwXdslSCStatusSegmentGainAlloc,hwXdslSCStatusSegmentTxPSD,
                          hwXdslSCStatusSegmentSnrMargin.
                          "

            REVISION     "201506270000Z"
            DESCRIPTION  "V1.69, changes in this revision:
                          Modify the description of these leaf: hwXdslSCStatusSegmentBitsAlloc.
                          "

            REVISION     "201506210000Z"
            DESCRIPTION  "V1.68, changes in this revision:
                          Modify the description of these leaves: hwXdslLineCurrentVdsl2Profile,hwXdslLineStatusActPsdLimitMask,
                          hwXdslSCStatusSegment.
                          Modify the value range of these leaves: hwXdslLineStatusActPsdLimitMask,hwXdslSCStatusSegment,
                          hwXdslChAlarmConfProfileMonitoringRateDs,hwXdslChAlarmConfProfileMonitoringRateUs.
                          "

            REVISION     "201505190000Z"
            DESCRIPTION  "V1.67, changes in this revision:
                          Modify the description of these leaf nodes: hwXdslLineCurrentVdsl2Profile,hwXdslLineStatusPwrMngState.
                          "

            REVISION     "201505050000Z"
            DESCRIPTION  "V1.66, changes in this revision:
                          Modify the value range of these leaf nodes: hwXdslSCFextXlinRealDs,
                          hwXdslSCFextXlinImgDs,hwXdslSCFextXlinRealUs,hwXdslSCFextXlinImgUs.
                          Modify the name of table hwXdslGfastConfProfTable and all names of leaf nodes which belong to this table.
                          Modify the names of mib nodes: hwXdslGfastCnfgProfile ,hwXdslGfastProfileChangeTrap,hwXdslGfastFrameProfileConfChangeTrap
                          The modify rule is:change 'Profile' to 'TddProfile' , 'Prof' to 'TddProf'.
                          For example :hwXdslGfastConfProfTable to hwXdslGfastConfTddProfTable.
                          "

            REVISION     "201504080000Z"
            DESCRIPTION  "V1.65, changes in this revision:
                          Modify the value range of these leaf nodes: hwOntXdslChStatusActNetDataRate,
                          hwOntXdslChStatusPrevNetDataRate,hwOntXdslChStatusActDelay,hwOntXdslChStatusINP.
                          "

            REVISION     "201504020000Z"
            DESCRIPTION  "V1.64, changes in this revision:
                          Modify the value range of the MIB nodes hwXdslGfastChAlarmConfProfileMonitoringRateDs
                          and hwXdslGfastChAlarmConfProfileMonitoringRateUs.
                          "

            REVISION     "201503180000Z"
            DESCRIPTION  "V1.63, changes in this revision:
                          Modify the DESCRIPTION of following MIB nodes:
                          hwXdslGfastLineAlarmConfTemplateTable,hwXdslGfastLineAlarmConfTemplateEntry,hwXdslGfastLAlarmConfTempLineProfile,
                          hwXdslGfastLAlarmConfTempChanConfProfile,hwXdslGfastLAlarmConfProfTable,hwXdslGfastLAlarmConfProfEntry,
                          hwXdslGfastLAlarmConfProfDyingGaspAlarmSwitch,hwXdslGfastChAlarmConfProfileTable,hwXdslGfastChAlarmConfProfileEntry,
                          ."

            REVISION     "201503030000Z"
            DESCRIPTION  "V1.62, changes in this revision:
                          Add leaf node hwXdslLineDetectionResult."

            REVISION     "201501290000Z"
            DESCRIPTION  "V1.61, changes in this revision:
                          Modify all of the mib node name.
                          Add the table of hwXdslSCFextTable, hwXdslGfastConfProfTable,
                          hwXdslGfastLAlarmConfProfTable, hwXdslGfastChAlarmConfProfileTable and hwXdslGfastConfTable.
                          Add leaf node hwXdslLineCurrentGfastProfile."

            REVISION     "201410200000Z"
            DESCRIPTION  "V1.60,changes in this revision:
                          Modify the description of these leaf nodes:hwXdslSCStatusSegmentSnrMargin, hwXdslSCStatusSegmentTxPSD.
                         "
            REVISION     "201409170000Z"
            DESCRIPTION  "V1.59,changes in this revision:
                          Modify the MAX-ACCESS of hwXdslSCStatusRowStatus.
                         "

            REVISION     "201407300000Z"
            DESCRIPTION  "V1.58,changes in this revision:
                         Add the definition of the leaf node hwXdslLineStatusLastRetrainInfo for getting the last retrained information.
                         Add leaf node  hwXdslPortAutoDeactiveLineRetrainInfo.
                         Modify leaf node  the enumerated values  of hwXdslPortAutoDeactiveLineFaultAlarmTrap .
                         "

            REVISION     "201406300000Z"
            DESCRIPTION  "V1.57,changes in this revision:
                          Modify the description of these leaf nodes: hwXdslSCStatusBandLnAtten, hwXdslSCStatusBandSigAtten, hwXdslSCStatusBandSnrMargin.
                         "

            REVISION     "201406200000Z"
            DESCRIPTION  "V1.56,changes in this revision:
                          Modify the description of these leaf nodes: hwXdslPMLCurr15MInmainpeq, hwXdslPMLCurr15MInmaiat,
                          hwXdslPMLCurr1DayInmainpeq, hwXdslPMLCurr1DayInmaiat, hwXdslPMLEverBeforeInmainpeq, hwXdslPMLEverBeforeInmaiat,
                          hwXdslPMLHist15MInmainpeq, hwXdslPMLHist15MInmaiat, hwXdslPMLHist1DInmainpeq,hwXdslPMLHist1DInmaiat.
                          Modify the definition of the trap node ,include : hwXdslPortAutoDeactiveLineFaultAlarmTrap.
                          Add the leaves hwXdslChConfProfMaxDataRateLowPwrDs and hwXdslChConfProfL2MinDataRateToL0ActDataRateDs in hwXdslChConfProfileTable.
                          Add leaf node hwXdslLineStatusActInpRocDs, hwXdslLineStatusActInpRocUs, hwXdslLineStatusActSnrmRocDs,
                          hwXdslLineStatusActSnrmRocUs in hwXdslLineCfgTable.
                         "

            REVISION     "201405050000Z"
            DESCRIPTION  "V1.55,changes in this revision:
                          Add the leaves hwXdslChConfProfMaxDelayVar in hwXdslChConfProfileTable.
                          Modified the units of the leaf nodes: hwXdslChConfProfMinSosBrDs, hwXdslChConfProfMinSosBrUs.
                          Modify leaf node hwXdslChStatusINP value range from (0..254) to (0..254 | 4294967295)."

            REVISION     "201403300000Z"
            DESCRIPTION  "V1.55,changes in this revision:
                          Add leaf node hwXdslChConfProfMaxDelayOctetSplit in hwXdslChConfProfileTable."

            REVISION     "201403180000Z"
            DESCRIPTION  "V1.55,changes in this revision:
                          Modify leaf node hwXdslLineSplitterMode default value in hwXdslLineCfgTable.
                          Add value annexB998ADE17-SPE-M2x-A(33) for hwXdslLineStatusActPsdLimitMask.
                          Modify the description of these leaf nodes: hwXdslLineStatusActPsdLimitMask, hwXdslSCStatusClassmask, hwXdslLConfProfPSDClassMask.
                         "

            REVISION     "201312050000Z"
            DESCRIPTION  "V1.55,changes in this revision:
                          Add leaf node hwXdslChStatusActEftr in hwXdslChannelStatusTable.
                          Modify the range of hwXdslLineSplitterMode.
                                           "

            REVISION     "201308200000Z"
            DESCRIPTION  "V1.54,changes in this revision:
                          Add leaf nodes hwXdslLineStatusActRaModeDs and hwXdslLineStatusActRaModeUs in hwXdslLineCfgTable.
                         "
            REVISION     "201308120000Z"
            DESCRIPTION  "V1.54,changes in this revision:
                          Add leaf node hwXdslLConfTempTemplateChangeTrap, hwXdslLConfProfProfileChangeTrap, hwXdslChConfProfProfileChangeTrap in hwXdslCfgCommonTrapsPrefix.
                          Add leaf node hwXdslProfOperType in hwXdslCfgTrapsVbOids.
                         "
            REVISION     "201308010000Z"
            DESCRIPTION  "V1.53,changes in this revision:
                          Add hwOntXdslLineTable,
                          hwOntXdslChannelStatusTable,
                          hwOntXdslPMLineCurrTable,
                          hwOntXdslPMLineCurrInitTable,
                          hwOntXdslPMLineHist15MinTable,
                          hwOntXdslPMLineHist1DayTable,
                          hwOntXdslPMLineInitHist15MinTable,
                          hwOntXdslPMLineInitHist1DayTable,
                          hwOntXdslPMChCurrTable,
                          hwOntXdslPMChHist15MinTable,
                          hwOntXdslPMChHist1DTable,
                          hwOntXdslSCStatusBandTable,
                          hwOntXdslLineInventoryTable .
                         "


            REVISION     "201307240000Z"
            DESCRIPTION  "V1.53,changes in this revision:
                          Add leaf node hwXdslLConfTempTemplateChangeTrap, hwXdslLConfProfProfileChangeTrap, hwXdslChConfProfProfileChangeTrap in hwXdslCfgCommonTrapsPrefix.
                          Add leaf node hwXdslProfOperType in hwXdslCfgTrapsVbOids.
                         "

            REVISION     "201306260000Z"
            DESCRIPTION  "V1.52,changes in this revision:
                          Add leaf node hwXdslPMLEverBeforeDisorderLeavingEvent, hwXdslPMLEverBeforeLof, hwXdslPMLEverBeforeLos, hwXdslPMLEverBeforeLop, hwXdslPMLEverBeforeLom,
                          hwXdslPMLCurr15MDisorderLeavingEvent, hwXdslPMLCurr1DayDisorderLeavingEvent, hwXdslPMLCurr15MLof, hwXdslPMLCurr15MLos, hwXdslPMLCurr15MLop,
                          hwXdslPMLCurr15MLom, hwXdslPMLCurr1DayLof, hwXdslPMLCurr1DayLos, hwXdslPMLCurr1DayLop, hwXdslPMLCurr1DayLom in xdsl2PMLineCurrTable.
                          Add leaf node hwXdslPMLHist15MDisorderLeavingEvent, hwXdslPMLHist15MLof, hwXdslPMLHist15MLos, hwXdslPMLHist15MLop, hwXdslPMLHist15MLom in xdsl2PMLineHist15MinTable.
                          Add leaf node hwXdslPMLHist1DDisorderLeavingEvent, hwXdslPMLHist1DLof, hwXdslPMLHist1DLos, hwXdslPMLHist1DLop, hwXdslPMLHist1DLom in xdsl2PMLineHist1DayTable.
                          Modify leaf node hwXdslChConfProfMaxDelayDs, hwXdslChConfProfMaxDelayUs value range from (0..200) to (0..200 | 255).
                          Add leaf node hwXdslLineStatusActPsdLimitMask in table xdsl2LineTable for getting actual limit PSD mask."

            REVISION     "201302210000Z"
            DESCRIPTION  "V1.51,changes in this revision:
                          Add leaf node hwXdslPMLCurr15MSraDownShiftEvent, hwXdslPMLCurr15MSraUpShiftEvent, hwXdslPMLCurr1DaySraDownShiftEvent,
                          hwXdslPMLCurr1DaySraUpShiftEvent in xdsl2PMLineCurrTable.
                          Add leaf node hwXdslPMLHist15MSraDownShiftEvent, hwXdslPMLHist15MSraUpShiftEvent in xdsl2PMLineHist15MinTable.
                          Add leaf node hwXdslPMLHist1DSraDownShiftEvent, hwXdslPMLHist1DSraUpShiftEvent in xdsl2PMLineHist1DayTable.
                          Modify leaf node hwXdslLConfProfMaxNomAtpDs, hwXdslLConfProfMaxNomAtpUs, hwXdslSpectrumProfMaxNomAtpDs, hwXdslSpectrumProfMaxNomAtpUs
                          value range from (0..205) to (0..510)
                         "

            REVISION     "201301200000Z"
            DESCRIPTION  "V1.50,changes in this revision:
                          Add leaf node hwXdslChStatusUnlimitedVersionEtru in xdsl2ChannelStatusTable.
                          Delete the node of hwXdslPrivSCStatusLinReal, hwXdslPrivSCStatusLinImg, hwXdslPrivSCStatusLog, hwXdslPrivSCStatusQln,
                          hwXdslPrivSCStatusLnAtten, hwXdslPrivSCStatusSigAtten, hwXdslPrivSCStatusSnrMargin, modify the node name of hwXdslPrivSCStatusLinScale,
                          hwXdslPrivSCStatusLogMt, hwXdslPrivSCStatusQlnMt, hwXdslPrivSCStatusAttainableRate, hwXdslPrivSCStatusActAtp, hwXdslPrivSCStatusRowStatus.
                          Add leaf node hwXdslPMLEverBeforeSraDownShiftEvent, hwXdslPMLEverBeforeSraUpShiftEvent in hwXdslPMLineCurrTable.
                          Add leaf node hwXdslLineAlarmConfProfilePSConfigAbnormalAlarmSwitch in hwXdslLineAlarmConfProfileTable.
                         "
            REVISION     "201211260000Z"
            DESCRIPTION  "V1.49, changes in this revision:
                          Add leaf node hwXdslLinePhyRcontrol in hwXdslLineCfgTable.
                         "
            REVISION     "201211080000Z"
            DESCRIPTION  "V1.48, changes in this revision:
                          Add leaf node hwXdslLineSplitterMode, hwXdslLineBackup, hwXdslLineBackupPort in hwXdslLineCfgTable.
                         "

            REVISION     "201208260000Z"
            DESCRIPTION  "V1.47, changes in this revision:
                          Add leaf node hwXdslLineAlarmConfProfileVictAbnormalVariationAlarmSwitch, hwXdslLineAlarmConfProfileDistAbnormalVariationAlarmSwitch,
                          hwXdslLineAlarmConfProfileReceivedESAbnormalAlarmSwitch, hwXdslLineAlarmConfProfileNonVectoringCPEActivatedAlarmSwitch,
                          hwXdslLineAlarmConfProfileFreqRetrainReachThresholdAlarmSwitch.
                          Add leaf node hwXdslSCStatusSegmentQlnWithVectoring.
                         "

            REVISION     "201207200000Z"
            DESCRIPTION  "V1.46, delete unnecessary en dashes.
                         "
            REVISION     "201204260000Z"
            DESCRIPTION  "V1.45, add leaf node hwXdslLconfProfUpboKlAuto.
                           Modify these leaf nodes:hwXdslServProfRaMode,hwXdslServProfCh1MinDataRateDs,hwXdslServProfCh1MinDataRateUs,
                           hwXdslServProfCh1MaxDataRateDs,hwXdslServProfCh1MaxDataRateUs,hwXdslDelayInpProfCh1MaxDelayDs,
                           hwXdslDelayInpProfCh1MaxDelayUs,hwXdslDelayInpProfCh1MinProtectionDs,hwXdslDelayInpProfCh1MinProtectionUs.
                           Add leaf nodes:hwXdslServProfMinEtrRtxDs,hwXdslServProfMinEtrRtxUs,hwXdslServProfMaxEtrRtxDs,hwXdslServProfMaxEtrRtxUs,hwXdslServProfMaxNdrRtxDs,
                           hwXdslServProfMaxNdrRtxUs,hwXdslSpectrumProfRtxModeDs,hwXdslSpectrumProfRtxModeUs,hwXdslSpectrumProfProfLeftrThreshDs,
                           hwXdslSpectrumProfProfLeftrThreshUs,hwXdslDelayInpProfCh1MaxDelayRtxDs,hwXdslDelayInpProfCh1MaxDelayRtxUs,hwXdslDelayInpProfCh1MinDelayRtxDs,
                           hwXdslDelayInpProfCh1MinDelayRtxUs,hwXdslDelayInpProfCh1MinInpShineRtxDs,hwXdslDelayInpProfCh1MinInpShineRtxUs,hwXdslDelayInpProfCh1MinInp8ShineRtxDs,
                           hwXdslDelayInpProfCh1MinInp8ShineRtxUs,hwXdslDelayInpProfCh1ShineRatioRtxDs,hwXdslDelayInpProfCh1ShineRatioRtxUs,hwXdslDelayInpProfCh1MinInpReinRtxDs,
                           hwXdslDelayInpProfCh1MinInpReinRtxUs,hwXdslDelayInpProfCh1MinInp8ReinRtxDs,hwXdslDelayInpProfCh1MinInp8ReinRtxUs,hwXdslDelayInpProfCh1IatReinRtxDs,
                           hwXdslDelayInpProfCh1IatReinRtxUs.
                         "
            REVISION     "201203200000Z"
            DESCRIPTION  "V1.44, add leaf node hwXdslSCFextXLinScaleUs, hwXdslSCFextXlinScGroupSizeUs, hwXdslSCFextXLinBandUs
                          hwXdslSCFextXlinRealUs, hwXdslSCFextXlinImgUs.
                          Modify the description of these leaf nodes hwXdslLineActmode,
                          hwXdslLineStatusXtuTransSys, hwXdslLineStatusLnAttenDs, hwXdslLineStatusLnAttenUs, hwXdslLineStatusSigAttenDs,
                          hwXdslLineStatusSigAttenUs, hwXdslLineStatusSnrMarginDs, hwXdslLineStatusSnrMarginUs,hwXdslLineStatusAttainableRateDs,
                          hwXdslLineStatusAttainableRateUs, hwXdslLineStatusActPsdDs, hwXdslLineStatusActPsdUs, hwXdslLineStatusActAtpDs,
                          hwXdslLineStatusActAtpUs, hwXdslUpboProfKl0CpeVal, hwXdslLineStatusCodingGainDs, hwXdslLineStatusCodingGainUs,
                          hwXdslLineStatusPcbDs, hwXdslUpboProfKl0CoVal, hwXdslUpboRxThreshDs, hwXdslUpboRxThreshUs, hwXdslLineStatusLineRateDs,
                          hwXdslLineStatusLineRateUs, hwXdslChStatusActDataRate, hwXdslChStatusPrevDataRate, hwXdslChStatusActDelay,
                          hwXdslChStatusINP, hwXdslChStatusRSRedundancy, hwXdslChStatusRSSymbols, hwXdslChStatusInterDepth,
                          hwXdslChStatusSymbolLength, hwXdslChStatusRSSize, hwXdslChStatusInterBlockLength, hwXdslChStatusLPATH,
                          hwXdslChStatusPhyRrrcBits, hwXdslChStatusPhyRtxQueue, hwXdslChStatusActNetDataRate, hwXdslChStatusActINPAgainstREIN,
                          hwXdslUpboRxThreshDs, hwXdslUpboRxThreshUs.
                          Add the definition of the leaf node hwXdslMaximumInterleavedDepth.
                         "
            REVISION     "201112050000Z"
            DESCRIPTION  "V1.43, add leaf node hwXdslSCStatusBandUpbokle,hwXdslUpboRxThreshDs,hwXdslUpboRxThreshUs,hwXdslLineStatusLineRateDs,
                          hwXdslLineStatusLineRateUs,hwXdslLConfProfAeleMode,hwXdslLConfProfUpboElmt.
                          Add the definition of the table: hwXdslSCFextTable.
                          Add leaf node hwXdslLineAlarmConfProfileLegacyCpeAlarmSwitch, hwXdslUnSuppVectorPortActFailAlarmTrap.
                          "
            REVISION     "201110150000Z"
            DESCRIPTION  "V1.42, add leaf node hwXdslLineAlarmConfProfileDyingGaspAlarmSwitch, hwXdslLineAlarmConfProfileActiveFailAlarmSwitch, hwXdslLineAlarmConfProfileRateChangeAlarmSwitch.
                         "

            REVISION     "201109280000Z"
            DESCRIPTION  "V1.41, add leaf node hwXdslProfileAutoNegotiationSwitch for the XDSL G993.2 profile auto-negotiation function.
                          modify the name of the nodes from hwXdslDpboEselGlobalConfig to hwXdslGlobalConfig."

            REVISION     "201108270000Z"
            DESCRIPTION  "V1.40, modify the value range of the leaf node hwXdslNoiseMarginProfDsThresholdDs, hwXdslNoiseMarginProfUsThresholdDs, hwXdslNoiseMarginProfDsThresholdUs,
                          hwXdslNoiseMarginProfUsThresholdUs."

            REVISION     "201106080000Z"
            DESCRIPTION  "V1.39, add the definition of the leaf node hwXdslLConfProfForceInpDs, hwXdslLConfProfForceInpUs
                          for force framer setting for impulse noise protection.
                          Add the definition of the leaf node hwXdslChConfProfInitPolicy for setting channel initialization policy."

            REVISION     "201105100000Z"
            DESCRIPTION  "V1.38, add the definition of the leaf node hwXdslLineStatusLastRetrainInfo for getting the last retrained information."

            REVISION     "201104140000Z"
            DESCRIPTION  "V1.37, modify the description of these leaf nodes:hwXdslLConfProfPsdMaskSelectUs,hwXdslPMLHist15MInmainpeq,
                          hwXdslPMLHist15MInmame,hwXdslPMLHist15MInmaiat,hwXdslPMLHist1DInmainpeq,hwXdslPMLHist1DInmame,hwXdslPMLHist1DInmaiat.
                          Delete the default value of hwXdslLConfProfPsdMaskSelectUs.
                          Modify the default value of hwXdslLConfProfPSDClassMask and hwXdslLConfProfProfiles.
                          Modify the hwXdslLConfProfPsdMaskSelectUs ranges from 0 to 9."

            REVISION     "201102210000Z"
            DESCRIPTION  "V1.36, Modify the description of these leaf nodes about default value:hwXdslLConfProfRaUsNrmDs,hwXdslLConfProfRaUsNrmUs,hwXdslLConfProfRaUsTimeDs,
                          hwXdslLConfProfRaUsTimeUs,hwXdslLConfProfRaDsNrmsDs,hwXdslLConfProfRaDsNrmsUs,hwXdslLConfProfRaDsTimeDs,hwXdslLConfProfRaDsTimeUs,
                          hwXdslLConfProfMaxSnrmDs,hwXdslLConfProfMaxSnrmUs,hwXdslLConfProfMinSnrmDs,hwXdslLConfProfMinSnrmUs,hwXdslLConfProfL2Time,hwXdslLConfProfL2Atpr,
                          hwXdslLConfProfL2Atprt,hwXdslDelayInpProfForceINP.
                          Modify the Description of these leaf nodes:hwXdslLineStatusSnrMarginDs,hwXdslLineStatusSnrMarginUs,hwXdslLineStatusActAtpDs,
                          hwXdslLineStatusActAtpUs,hwXdslLineStatusActPsdDs,hwXdslLineStatusActPsdUs.
                         "

            REVISION     "201012120900Z"
            DESCRIPTION  "V1.35, Modify these leaf nodes:hwXdslLConfProfRaModeDs,hwXdslChConfProfMinDataRateDs,hwXdslChConfProfMinDataRateUs,hwXdslChConfProfMaxDataRateDs,
                          hwXdslChConfProfMaxDataRateUs,hwXdslChConfProfMaxDelayDs,hwXdslChConfProfMaxDelayUs,hwXdslChConfProfMinProtectionDs,hwXdslChConfProfMinProtectionUs,
                          hwXdslChConfProfUsDataRateDs,hwXdslChConfProfUsDataRateUs,hwXdslChConfProfDsDataRateDs and hwXdslChConfProfDsDataRateUs.
                          add leaf nodes:hwXdslLineAlarmConfProfileXtucThresh15MinLeftrs,hwXdslLineAlarmConfProfileXturThresh15MinLeftrs,hwXdslLConfProfRtxModeDs,
                          hwXdslLConfProfRtxModeUs,hwXdslLConfProfLeftrThreshDs,hwXdslLConfProfLeftrThreshUs,hwXdslChConfProfMinEtrRtxDs,hwXdslChConfProfMinEtrRtxUs,
                          hwXdslChConfProfMaxEtrRtxDs,hwXdslChConfProfMaxEtrRtxUs,hwXdslChConfProfMaxNdrRtxDs,hwXdslChConfProfMaxNdrRtxUs,hwXdslChConfProfMaxDelayRtxDs,
                          hwXdslChConfProfMaxDelayRtxUs,hwXdslChConfProfMinDelayRtxDs,hwXdslChConfProfMinDelayRtxUs,hwXdslChConfProfMinInpShineRtxDs,hwXdslChConfProfMinInpShineRtxUs,
                          hwXdslChConfProfMinInp8ShineRtxDs,hwXdslChConfProfMinInp8ShineRtxUs,hwXdslChConfProfShineRatioRtxDs,hwXdslChConfProfShineRatioRtxUs,hwXdslChConfProfMinInpReinRtxDs,
                          hwXdslChConfProfMinInpReinRtxUs,hwXdslChConfProfMinInp8ReinRtxDs,hwXdslChConfProfMinInp8ReinRtxUs,hwXdslChConfProfIatReinRtxDs,hwXdslChConfProfIatReinRtxUs.
                         "

            REVISION     "201009270900Z"
            DESCRIPTION  "V1.34, Modify the Description of the whole MIB file.
                          modify the range of node about XDSL channel rate in table hwXdslServProfTable."

            REVISION     "201009070900Z"
            DESCRIPTION  "V1.33,Modify the Description of hwXdslPortStatusChangeTrap."

            REVISION     "201008030900Z"
            DESCRIPTION  "V1.32, add the definition of the trap node ,include: hwXdslTemplateIDChangeTrap.
                          add leaf node hwXdslTemplateType in table hwXdslCfgTrapsVbOids.
                          modify the definition of the trap node hwXdslDownstreamRateLowerThresholdAlarmTrap.
                          modify the range of hwXdslLineAlarmCnfgTemplate from 1...32 to 0...32 in hwXdslLineCfgTable.
                          Modify the description of the trap node ,include:hwXdslDownstreamRateLowerThresholdAlarmTrap,
                          hwXdslChannelUpstreamLowerThresholdAlarmTrap,hwXdslChannelUpstreamExcThreAlarmTrap,hwXdslChannelUpstreamRestoreThreAlarmTrap,
                          hwXdslChannelDownstreamExcThreAlarmTrap,hwXdslChannelDownstreamRestoreThreAlarmTrap."

            REVISION     "201006220900Z"
            DESCRIPTION  "V1.31,Modify chinese character."

            REVISION     "201005200900Z"
            DESCRIPTION  "V1.30, modify the definition of the trap node hwXdslPortStatusChangeTrap."

            REVISION     "201005130900Z"
            DESCRIPTION  "V1.29, modify the hwXdslLConfProfL3Time ranges from 0 to 65535 seconds."

            REVISION     "201005050900Z"
            DESCRIPTION  "V1.28, modify the errors of the MIB file."

            REVISION     "201004020000Z"
            DESCRIPTION  "V1.27, add the definition of the trap node ,include:hwXdslDeltOperResultTrap.
                          modify the definition of the trap node ,include:hwXdslPortAutoDeactiveLineFaultAlarmTrap,
                          hwXdslPortReactiveAfterRecoverAlarmTrap,hwXdslPerformanceStatiReachThresholdAlarmTrap, hwXdslDownstreamRateLowerThresholdAlarmTrap,
                          hwXdslXTURPowerOffAlarmTrap, hwXdslPortActiveRateChangeAlarmTrap, hwXdslChannelUpstreamExcThreAlarmTrap, hwXdslChannelUpstreamRestoreThreAlarmTrap,
                          hwXdslChannelDownstreamExcThreAlarmTrap, hwXdslChannelDownstreamRestoreThreAlarmTrap."

            REVISION     "201001200000Z"
            DESCRIPTION  "V1.26, add leaf node hwXdslPMLineCurr15MStartTime, hwXdslPMLineCurr1DayStartTime, hwXdslPMLineCurrInit15MStartTime,
                          hwXdslPMLineCurrInit1DayStartTime, hwXdslPMLHist15MStartTime, hwXdslPMLHist1DStartTime, hwXdslPMLHistInit15MStartTime,
                          hwXdslPMLHistinit1DStartTime, hwXdslPMChCurr15MStartTime, hwXdslPMChCurr1DayStartTime,
                          hwXdslPMChHist15MStartTime, hwXdslPMChHist1DStartTime  for performance monitoring.
                          create table hwXdslCfgAutoDeleteProfUnused,add leaf node hwXdslAutoDeleteVdslProfUnusedProfType,
                          hwXdslAutoDeleteVdslProfUnusedOperType for deleting unused profile.
                          Add leaf node hwXdslUpboProfKl0CoVal in hwXdslLineCfgTable to achieve the KL0 feature,
                          The node hwXdslUpboProfKl0Val is renamed hwXdslUpboProfKl0CpeVal."

            REVISION     "201001120000Z"
            DESCRIPTION  "V1.25, add the definition of the trap node,include:
                          hwXdslModeSwitchTrap
                          hwXdslCurrentModeTrap
                          hwXdslPortStatusChangeTrap
                          hwXdslAutoDeactivateLackLicensesCfgAlarmTrap
                          hwXdslPortAutoDeactiveLineFaultAlarmTrap
                          hwXdslPortReactiveAfterRecoverAlarmTrap
                          hwXdslPerformanceStatiReachThresholdAlarmTrap
                          hwXdslDownstreamRateLowerThresholdAlarmTrap
                          hwXdslActivePortFailConfigParaAlarmTrap
                          hwXdslPerformanceStatisReachThresholdAlarmTrap
                          hwXdslChannelUpstreamLowerThresholdAlarmTrap
                          hwXdslXTURPowerOffAlarmTrap
                          hwXdslPortActiveRateChangeAlarmTrap
                          hwXdslChipsetUnavailableAlarmTrap
                          hwXdslChipsetRecoverAlarmTrap
                          "
            REVISION     "201001050000Z"
            DESCRIPTION  "V1.24, Add leaf node hwXdslUpboProfKl0CoVal in hwXdslLineCfgTable to achieve the KL0 feature,
                          The node hwXdslUpboProfKl0Val is renamed hwXdslUpboProfKl0CpeVal."

            REVISION     "200906050000Z"
            DESCRIPTION  "V1.19, Add leaf node in table hwXdslLineConfProfTable, hwXdslChConfProfileTable, hwXdslPMLineCurrTable, hwXdslPMLineHist15MinTable,
                          and hwXdslPMLineHist1DayTable to achieve the save our showtime and the impulse noise monitor features.
                          Delete enumerated values AnnexA998-D-48, AnnexA998-D-128, AnnexB998E17-M2x-A, and AnnexB998ADE17-M2x-M from leaf node hwXdslLConfProfPSDClassMask."

            REVISION     "200806030000Z"
            DESCRIPTION  "V1.10, add leaf node hwadslLConfProfAdslMode for the actual value of coding gain parameter,
                          add leaf node hwXdslSCStatusSegmentTable for the sub-carriers."

            REVISION     "200604270000Z"
            DESCRIPTION  "V1.00, Initial version."

            ::= { huaweiUtility 115 }

        hwXdsl              OBJECT IDENTIFIER ::= { hwXdslMIB 1 }
        hwXdslLine          OBJECT IDENTIFIER ::= { hwXdsl 1 }
        hwXdslStatus        OBJECT IDENTIFIER ::= { hwXdsl 2 }
        hwXdslInventory     OBJECT IDENTIFIER ::= { hwXdsl 3 }
        hwXdslPM            OBJECT IDENTIFIER ::= { hwXdsl 4 }
        hwXdslProfile       OBJECT IDENTIFIER ::= { hwXdsl 5 }
        hwXdslScalar        OBJECT IDENTIFIER ::= { hwXdsl 6 }
        hwXdslNotifications OBJECT IDENTIFIER ::= { hwXdsl 0 }
        hwXdslConformance   OBJECT IDENTIFIER ::= { hwXdsl 8 }
        hwXdslMode          OBJECT IDENTIFIER ::= { hwXdsl 9 }
        hwXdslGlobalConfig            OBJECT IDENTIFIER ::= { hwXdsl 10 }
        hwXdslCfgAutoDeleteProfUnused  OBJECT IDENTIFIER ::= { hwXdsl 11 }
        hwXdslGfastConf              OBJECT IDENTIFIER ::= { hwXdsl 12 }
        hwXdslCfgTraps                OBJECT IDENTIFIER ::= { hwXdsl 15 }
        hwXdslCfgTrapsVbOids           OBJECT IDENTIFIER ::= { hwXdsl 16 }

        hwXdslPMLine      OBJECT IDENTIFIER ::= { hwXdslPM 1 }
        hwXdslPMChannel   OBJECT IDENTIFIER ::= { hwXdslPM 2 }
        hwXdslProfileLine      OBJECT IDENTIFIER ::= { hwXdslProfile 1 }
        hwXdslProfileChannel   OBJECT IDENTIFIER ::= { hwXdslProfile 2 }
        hwXdslProfileAlarmConf OBJECT IDENTIFIER ::= { hwXdslProfile 3 }
        hwXdslProfileTIMode    OBJECT IDENTIFIER ::= { hwXdslProfile 4 }
        hwXdslGfastTddProfile    OBJECT IDENTIFIER ::= { hwXdslProfile 5 }
        hwXdslGfastProfileAlarmConf OBJECT IDENTIFIER ::= { hwXdslProfile 6 }
        hwXdslScalarSC         OBJECT IDENTIFIER ::= { hwXdslScalar 1 }
        hwXdslCfgCommonTraps           OBJECT IDENTIFIER ::= { hwXdslCfgTraps 1 }
        hwXdslCfgCommonTrapsPrefix     OBJECT IDENTIFIER ::= { hwXdslCfgCommonTraps 0 }
        hwXdslCfgAlarmTraps            OBJECT IDENTIFIER ::= { hwXdslCfgTraps 2 }
        hwXdslCfgAlarmTrapsPrefix      OBJECT IDENTIFIER ::= { hwXdslCfgAlarmTraps 0 }

        --         hwXdslLineCfgTable
        hwXdslLineCfgTable  OBJECT-TYPE
            SYNTAX      SEQUENCE  OF  HwXdslLineCfgEntry
            MAX-ACCESS  not-accessible
            STATUS      current
            DESCRIPTION
                "The table hwXdslLineCfgTable contains configuration,
                 command and status parameters of the XDSL line.
                 The index of this table is ifIndex.
                "
            ::= { hwXdslLine 1 }

        hwXdslLineCfgEntry  OBJECT-TYPE
            SYNTAX      HwXdslLineCfgEntry
            MAX-ACCESS  not-accessible
            STATUS      current
            DESCRIPTION
                "The table hwXdslLineCfgTable contains configuration,
                 command and status parameters of the XDSL line.
                 The index of this entry is ifIndex.
                "
            INDEX  { ifIndex }
            ::= { hwXdslLineCfgTable 1 }

        HwXdslLineCfgEntry  ::=
            SEQUENCE {
              hwXdslLineCnfgTemplate            OCTET STRING,
              hwXdslLineAlarmCnfgTemplate       OCTET STRING,
              hwXdslLineCmndConfPmsf            HwXdslConfPmsForce,
              hwXdslLineCmndConfLdsf            HwXdslLineLdsf,
              hwXdslLineCmndConfLdsfFailReason  HwXdslLdsfResult,
              hwXdslLineCmndAutomodeColdStart   TruthValue,
              hwXdslLineStatusXtuTransSys       Unsigned32,
              hwXdslLineStatusPwrMngState       HwXdslPowerMngState,
              hwXdslLineStatusInitResult        HwXdslInitResult,
              hwXdslLineStatusLastStateDs       HwXdslLastTransmittedState,
              hwXdslLineStatusLastStateUs       HwXdslLastTransmittedState,
              hwXdslLineStatusXtur              HwXdslLineStatus,
              hwXdslLineStatusXtuc              HwXdslLineStatus,
              hwXdslLineStatusLnAttenDs         Unsigned32,
              hwXdslLineStatusLnAttenUs         Unsigned32,
              hwXdslLineStatusSigAttenDs        Unsigned32,
              hwXdslLineStatusSigAttenUs        Unsigned32,
              hwXdslLineStatusSnrMarginDs       Integer32,
              hwXdslLineStatusSnrMarginUs       Integer32,
              hwXdslLineStatusAttainableRateDs  Unsigned32,
              hwXdslLineStatusAttainableRateUs  Unsigned32,
              hwXdslLineStatusActPsdDs          Integer32,
              hwXdslLineStatusActPsdUs          Integer32,
              hwXdslLineStatusActAtpDs          Integer32,
              hwXdslLineStatusActAtpUs          Integer32,
              hwXdslLineBandPlan                HwXdslBandPlan,
              hwXdslLinePsdMaskClassSelection   HwXdslTIPsdClassMask,
              hwXdslLineCurrentVdsl2Profile     HwXdslSubProfiles,
              hwXdslLineCnfgServiceProf         OCTET STRING,
              hwXdslLineCnfgSpectrumProf        OCTET STRING,
              hwXdslLineCnfgDpboProf            OCTET STRING,
              hwXdslLineCnfgUpboProf            OCTET STRING,
              hwXdslLineCnfgNoiseMarginProf     OCTET STRING,
              hwXdslLineCnfgDelayINPProf        OCTET STRING,
              hwXdslUpboProfKl0CpeVal        Unsigned32,
              hwXdslLineStatusCodingGainDs      Unsigned32,
              hwXdslLineStatusCodingGainUs      Unsigned32,
              hwXdslLineStatusPcbDs             Unsigned32,
              hwxdslDlmDsmprofile              OCTET STRING,
              hwXdslLineActmode               HwXdslActmode,
              hwXdslUpboProfKl0CoVal         Unsigned32,
              hwXdslLineStatusRtxUsedDs         HwXdslStatusRtxUsed,
              hwXdslLineStatusRtxUsedUs         HwXdslStatusRtxUsed,
              hwXdslLineStatusLastRetrainInfo   INTEGER,
              hwXdslUpboRxThreshDs              Integer32,
              hwXdslUpboRxThreshUs              Integer32,
              hwXdslLineStatusLineRateDs      Unsigned32,
              hwXdslLineStatusLineRateUs      Unsigned32,
              hwXdslLineSplitterMode          INTEGER,
              hwXdslLineBackup                INTEGER,
              hwXdslLineBackupPort            Unsigned32,
              hwXdslLinePhyRcontrol           INTEGER,
              hwXdslLineStatusActPsdLimitMask INTEGER,
              hwXdslLineStatusActRaModeDs     INTEGER,
              hwXdslLineStatusActRaModeUs     INTEGER,
              hwXdslLineStatusActInpRocDs     Unsigned32,
              hwXdslLineStatusActInpRocUs     Unsigned32,
              hwXdslLineStatusActSnrmRocDs    Integer32,
              hwXdslLineStatusActSnrmRocUs    Integer32,
              hwXdslLineCurrentGfastProfile   INTEGER,
              hwXdslLineDetectionResult       BITS,
              hwXdslLineCurrentGfastSnrMarginRmcDs   Integer32,
              hwXdslLineCurrentGfastSnrMarginRmcUs   Integer32,
              hwXdslBypassAutoRecoverTime          Unsigned32,
              hwXdslLineVdsl2ProfileFallbackstatus INTEGER,
              hwXdslLineCnfgTR129RfiProf         OCTET STRING,
              hwXdslLineStatusActVdsl2LrMode     INTEGER
            }

        hwXdslLineCnfgTemplate  OBJECT-TYPE
            SYNTAX      OCTET STRING (SIZE(0..32))
            MAX-ACCESS  read-write
            STATUS      current
            DESCRIPTION
                "The value of this object identifies the row in the XDSL Line
                 Configuration Templates Table, (hwXdslConfTemplatesTable),
                 which applies for this XDSL line.
                "
            REFERENCE    "DSL Forum TR-90, paragraph 5.1.1"
            DEFVAL       { "DEFVAL" }
            ::= { hwXdslLineCfgEntry 1 }

        hwXdslLineAlarmCnfgTemplate  OBJECT-TYPE
            SYNTAX      OCTET STRING (SIZE(0..32))
            MAX-ACCESS  read-write
            STATUS      current
            DESCRIPTION
                "The value of this object identifies the row in the XDSL Line
                 Alarm Configuration Template Table,
                 (hwXdslLineAlarmConfTemplateTable or hwXdslGfastLineAlarmConfTemplateTable),
                  which applies to this XDSL line."
            REFERENCE    "DSL Forum TR-90, paragraph 5.1.1"
            DEFVAL       { "DEFVAL" }
            ::= { hwXdslLineCfgEntry 2 }

        hwXdslLineCmndConfPmsf  OBJECT-TYPE
            SYNTAX      HwXdslConfPmsForce
            MAX-ACCESS  read-write
            STATUS      current
            DESCRIPTION
                "Power management state forced. Defines the line states to be
                 forced by the near-end xTU on this line.
                 Options:
                 1. l3toL0(0)     - Force the line to transition from the L3
                                    idle state to the L0 full-on state
                 2. l0toL2(2)     - Force the line to transition from L0
                                    full on to L2 low power state
                 3. l0orL2toL3(3) - Force the line to transition from the L0
                                    full-on or L2 low power state to the L3 idle state
                 4. invalidValue(-1) -Invalid value
                "
            REFERENCE    "ITU-T G.997.1, paragraph 7.3.1.1.3"
            DEFVAL       { l3toL0 }
            ::= { hwXdslLineCfgEntry 3 }

        hwXdslLineCmndConfLdsf  OBJECT-TYPE
            SYNTAX      HwXdslLineLdsf
            MAX-ACCESS  read-write
            STATUS      current
            DESCRIPTION
                "Loop diagnostics mode forced (LDSF). Defines whether the line
                 should be forced into the loop diagnostics mode by the
                 near-end xTU on this line or only be responsive to loop
                 diagnostics initiated by the far-end xTU.
                "
            REFERENCE    "ITU-T G.997.1, paragraph 7.3.1.1.8"
            DEFVAL       { inhibit }
            ::= { hwXdslLineCfgEntry 4 }

        hwXdslLineCmndConfLdsfFailReason  OBJECT-TYPE
            SYNTAX      HwXdslLdsfResult
            MAX-ACCESS  read-only
            STATUS      current
            DESCRIPTION
                "The status of the recent occasion the Loop diagnostics mode
                 forced (LDSF) was issued for the associated line.
                 Options:
                 1. none(1)         - The default value in case LDSF was never
                                      requested for the associated line
                 2. success(2)      - The recent command completed
                                      successfully
                 3. inProgress(3)   - The Loop Diagnostics process is in
                                      progress
                 4. unsupported(4)  - The NE or the line card doesn't support
                                      LDSF
                 5. cannotRun(5)    - The NE cannot initiate the command, due
                                      to a non specific reason
                 6. aborted(6)      - The Loop Diagnostics process aborted
                 7. failed(7)       - The Loop Diagnostics process failed
                 8. illegalMode(8)  - The NE cannot initiate the command, due
                                      to the specific mode of the relevant
                                      line
                 9. adminUp(9)      - The NE cannot initiate the command, as
                                      the relevant line is administratively
                                      'Up'
                 10.tableFull(10)   - The NE cannot initiate the command, due
                                      to reaching the maximum number of rows
                                      in the results table
                 11.noResources(11) - The NE cannot initiate the command, due
                                      to lack of internal memory resources
                 Default: none(1)
                "
            ::= { hwXdslLineCfgEntry 5 }

        hwXdslLineCmndAutomodeColdStart   OBJECT-TYPE
            SYNTAX      TruthValue
            MAX-ACCESS  read-write
            STATUS      current
            DESCRIPTION
                "Automode cold start forced. This parameter is defined
                 in order to improve testing of the performance of ATUs
                 supporting automode when it is enabled in the MIB.
                 Change the value of this parameter to 'true' indicates
                 a change in loop conditions applied to the devices under
                 test. The ATUs shall reset any historical information
                 used for automode and for shortening G.994.1 handshake
                 and initialization.
                 Automode is the case where multiple operation-modes are
                 enabled through the hwXdslLConfProfXtuTransSysEna object
                 in the line configuration profile being used for the
                 XDSL line, and where the selection of the actual
                 operation-mode depends not only on the common
                 capabilities of both ATUs (as exchanged in G.994.1), but
                 also on achievable data rates under given loop
                 conditions.
                "
            REFERENCE    "ITU-T G.997.1, paragraph 7.3.1.1.10"
            DEFVAL       { false }
            ::= { hwXdslLineCfgEntry 6 }

        hwXdslLineStatusXtuTransSys  OBJECT-TYPE
            SYNTAX      Unsigned32
            MAX-ACCESS  read-only
            STATUS      current
            DESCRIPTION
                "The xTU Transmission System (XTS) in use.
                 This parameter may be derived from the handshaking procedures
                 defined in Recommendation G.994.1. The invalid value is 4294967295.
                 If data on the port is invalid or no data is generated on the
                 port because the port has not been activated, the invalid value
                 will be returned. One of XDSL line
                 transmission modes:
                        ANSI_T1413(1)
                        ETSI_DTS_TM06006(2)
                        G9921_POTS_NONOVERLAP(3)
                        G9921_POTS_OVERLAP(4)
                        G9921_ISDN_NONOVERLAP(5)
                        G9921_ISDN_OVERLAP(6)
                        G9921_TCMISDN_NONOVERLAP(7)
                        G9921_TCMISDN_OVERLAP(8)
                        G9922_POTS_NONOVERLAP(9)
                        G9922_POTS_OVERLAP(10)
                        G9922_TCMISDN_NONOVERLAP(11)
                        G9922_TCMISDN_OVERLAP(12)
                        G9921_TCMISDN_SYMMETRIC(13)
                        G9923_POTS_NONOVERLAP(19)
                        G9923_POTS_OVERLAP(20)
                        G9923_ISDN_NONOVERLAP(21)
                        G9923_ISDN_OVERLAP(22)
                        G9924_POTS_NONOVERLAP(25)
                        G9924_POTS_OVERLAP(26)
                        G9923_ANNEXI_ALLDIGI_NONOVERLAP(29)
                        G9923_ANNEXI_ALLDIGI_OVERLAP(30)
                        G9923_ANNEXJ_ALLDIGI_NONOVERLAP(31)
                        G9923_ANNEXJ_ALLDIGI_OVERLAP(32)
                        G9924_ANNEXI_ALLDIGI_NONOVERLAP(33)
                        G9924_ANNEXI_ALLDIGI_OVERLAP(34)
                        G9923_ANNEXL_POTS_NONOVERLAP_MODE1_WIDEUS(35)
                        G9923_ANNEXL_POTS_NONOVERLAP_MODE2_NARROWUS(36)
                        G9923_ANNEXL_POTS_OVERLAP_MODE3_WIDEUS(37)
                        G9923_ANNEXL_POTS_NONOVERLAP_MODE4_NARROWUS(38)
                        G9923_ANNEXM_POTS_NONOVERLAP(39)
                        G9923_ANNEXM_POTS_OVERLAP(40)
                        G9925_POTS_NONOVERLAP(41)
                        G9925_POTS_OVERLAP(42)
                        G9925_ISDN_NONOVERLAP(43)
                        G9925_ISDN_OVERLAP(44)
                        G9925_ANNEXI_ALLDIGI_NONOVERLAP(47)
                        G9925_ANNEXI_ALLDIGI_OVERLAP(48)
                        G9925_ANNEXJ_ALLDIGI_NONOVERLAP(49)
                        G9925_ANNEXJ_ALLDIGI_OVERLAP(50)
                        G9925_ANNEXM_POTS_NONOVERLAP(51)
                        G9925_ANNEXM_POTS_OVERLAP(52)
                        G9931(65)
                        G9932_ANNEXA_POTS(73)
                        G9932_ANNEXA_ISDN(74)
                        G9932_ANNEXB_POTS(75)
                        G9932_ANNEXB_ISDN(76)
                        G9932_ANNEXC_POTS(77)
                        G9932_ANNEXC_ISDN(78)
                        G9935(79)
                        G9935_FRIENDLY_DS(80)
                        G9935_FULL_FRIENDLY(81)
                        G9701(82)
               "
            ::= { hwXdslLineCfgEntry 7 }

        hwXdslLineStatusPwrMngState  OBJECT-TYPE
            SYNTAX      HwXdslPowerMngState
            MAX-ACCESS  read-only
            STATUS      current
            DESCRIPTION
                "The current power management state.
                 Options:
                 1. L0 - Synchronized and full transmission
                 2. L1 - Low Power with reduced net data rate
                 3. L2 - Low Power with reduced net data rate
                 4. L3 - No power
                 5. invalidValue(-1)  - Invalid value
                 The various possible values are:l0(0), l1(1), l2(2), l3(3), invalidValue(-1).
                "
            REFERENCE    "ITU-T G.997.1, paragraph 7.5.1.2"
               ::= { hwXdslLineCfgEntry 8 }

        hwXdslLineStatusInitResult  OBJECT-TYPE
            SYNTAX      HwXdslInitResult
            MAX-ACCESS  read-only
            STATUS      current
            DESCRIPTION
                "Indicates the result of the last full initialization performed
                 on the line.
                 Options:
                 1. noFail (0)            - Successful initialization
                 2. configError (1)       - Configuration failure
                 3. configNotFeasible (2) - Configuration details not supported
                 4. commFail (3)          - Communication failure
                 5. noPeerXtu (4)         - Peer xTU not detected
                 6. otherCause (5)        - Other initialization failure reason
                 7. ginpNotSelected(6)    - G.998.4 Retransmission mode was not selected
                                            while RTX_MODE = FORCED or with RTX_MODE = RTX_TESTMODE
                 8. invalidValue(-1)      - Invalid value
                "
            REFERENCE    "ITU-T G.997.1, paragraph 7.5.1.3"
            ::= { hwXdslLineCfgEntry 9 }

        hwXdslLineStatusLastStateDs  OBJECT-TYPE
            SYNTAX      HwXdslLastTransmittedState
            MAX-ACCESS  read-only
            STATUS      current
            DESCRIPTION
                "The last successful transmitted initialization state in
                 the downstream direction in the last full initialization
                 performed on the line. States are per the specific XDSL type
                 and are counted from 0 (if G.994.1 is used) or 1 (if G.994.1
                 is not used) up to Showtime.
                "
            REFERENCE    "ITU-T G.997.1, paragraph 7.5.1.4"
            ::= { hwXdslLineCfgEntry 10 }

        hwXdslLineStatusLastStateUs  OBJECT-TYPE
            SYNTAX      HwXdslLastTransmittedState
            MAX-ACCESS  read-only
            STATUS      current
            DESCRIPTION
                "The last successful transmitted initialization state in the
                 upstream direction in the last full initialization performed
                 on the line.  States are per the specific XDSL type and are
                 counted from 0 (if G.994.1 is used) or 1 (if G.994.1 is not
                 used) up to Showtime.
                "
            REFERENCE    "ITU-T G.997.1, paragraph 7.5.1.5"
            ::= { hwXdslLineCfgEntry 11 }

        hwXdslLineStatusXtur  OBJECT-TYPE
            SYNTAX      HwXdslLineStatus
            MAX-ACCESS  read-only
            STATUS      current
            DESCRIPTION
                "Indicates current state (existing failures) of the xTU-R.
                 This is a bit-map of possible conditions.  The various bit
                 positions are: noFailure(0), lossOfFraming(1),
                 lossOfSignal(2), lossOfPower(3),
                 initFailure(4) - never active on xTU-R,
                 lossOfMargin(5), lossOfRMC(6)
                "
            REFERENCE    "ITU-T G.997.1, paragraph 7.1.1.2"
            ::= { hwXdslLineCfgEntry 12 }

        hwXdslLineStatusXtuc  OBJECT-TYPE
            SYNTAX      HwXdslLineStatus
            MAX-ACCESS  read-only
            STATUS      current
            DESCRIPTION
                "Indicates current state (existing failures) of the xTU-C.
                 This is a bit-map of possible conditions. This BITS structure can
                 report the following failures:
                 1. noDefect (0)      - This bit position positively reports
                                        that no defect or failure exist
                 2. lossOfFraming (1) - Loss of frame synchronization
                 3. lossOfSignal (2)  - Loss of signal
                 4. lossOfPower (3)   - Loss of power.  Usually this failure may
                                        be reported for CPE units only
                 5. initFailure (4)   - Recent initialization process failed
                 6. lossOfMargin(5)   - Loss of margin
                 7. lossOfRMC(6)      - Loss of RMC
                "
            REFERENCE    "ITU-T G.997.1, paragraph 7.1.1.1"
            ::= { hwXdslLineCfgEntry 13 }

        hwXdslLineStatusLnAttenDs  OBJECT-TYPE
            SYNTAX      Unsigned32
            UNITS       "0.1 dB"
            MAX-ACCESS  read-only
            STATUS      current
            DESCRIPTION
                "The measured difference in the total power transmitted by the
                 xTU-C and the total power received by the xTU-R over all
                 sub-carriers during diagnostics mode and initialization. It
                 ranges from 0 to 1270 units of 0.1 dB (Physical values
                 are 0 to 127 dB). A value of 0xffffffff indicates the line
                 attenuation is out of range to be represented. The invalid value
                 is 4294967295. If data on the port is invalid or no data is
                 generated on the port because the port has not been activated,
                 the invalid value will be returned.
                 Unit: 0.1 dB
                "
            REFERENCE    "ITU-T G.997.1, paragraph 7.5.1.6"
            ::= { hwXdslLineCfgEntry 14 }

        hwXdslLineStatusLnAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during diagnostics mode and initialization.
                 It ranges from 0 to 1270 units of 0.1 dB (Physical values are
                 0 to 127 dB).  A value of 0xffffffff indicates the line
                 attenuation is out of range to be represented. The invalid value
                 is 4294967295. If data on the port is invalid or no data is
                 generated on the port because the port has not been activated,
                 the invalid value will be returned.
                 Unit: 0.1 dB
                "
            REFERENCE    "ITU-T G.997.1, paragraph 7.5.1.7"
            ::= { hwXdslLineCfgEntry 15 }

        hwXdslLineStatusSigAttenDs  OBJECT-TYPE
            SYNTAX      Unsigned32
            UNITS       "0.1 dB"
            MAX-ACCESS  read-only
            STATUS      current
            DESCRIPTION
                "The measured difference in the total power transmitted by the
                 xTU-C and the total power received by the xTU-R over all sub-
                 carriers during Showtime.  It ranges from 0 to 1270 units of
                 0.1 dB (Physical values are 0 to 127 dB).  A value of all
                 1's indicates the line attenuation is out of range to be
                 represented. The invalid value is 4294967295. If data on the
                 port is invalid or no data is generated on the port because
                 the port has not been activated, the invalid value will be returned.
                 Unit: 0.1 dB
                "
            REFERENCE    "ITU-T G.997.1, paragraph 7.5.1.8"
            ::= { hwXdslLineCfgEntry 16 }

        hwXdslLineStatusSigAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during Showtime.  It ranges from 0 to 1270 units of
                 0.1 dB (Physical values are 0 to 127 dB).  A value of all
                 1's indicates the line attenuation is out of range to be
                 represented. The invalid value is 4294967295. If data on the
                 port is invalid or no data is generated on the port because
                 the port has not been activated, the invalid value will be returned.
                 Unit: 0.1 dB
                "
            REFERENCE    "ITU-T G.997.1, paragraph 7.5.1.9"
            ::= { hwXdslLineCfgEntry 17 }

        hwXdslLineStatusSnrMarginDs  OBJECT-TYPE
            SYNTAX      Integer32
            UNITS       "0.1 dB"
            MAX-ACCESS  read-only
            STATUS      current
            DESCRIPTION
                "Downstream SNR Margin is the maximum increase in dB of the
                 noise power received at the xTU-R, such that the BER
                 requirements are met for all downstream bearer channels.  It
                 ranges from -640 to 630 units of 0.1 dB (Physical values are
                 -64 to 63 dB).  A value of 0x7FFFFFFF(2147483647) indicates the line
                 attenuation is out of range to be represented. The invalid
                 value is 2147483647. If data on the port is invalid or no data
                 is generated on the port because the port has not been activated,
                 the invalid value will be returned.
                 Unit: 0.1 dB
                "
            REFERENCE    "ITU-T G.997.1, paragraph 7.5.1.10"
            ::= { hwXdslLineCfgEntry 18 }

        hwXdslLineStatusSnrMarginUs  OBJECT-TYPE
            SYNTAX      Integer32
            UNITS       "0.1 dB"
            MAX-ACCESS  read-only
            STATUS      current
            DESCRIPTION
                "Upstream SNR Margin is the maximum increase in dB of the noise
                 power received at the xTU-C, such that the BER requirements
                 are met for all downstream bearer channels.  It ranges from
                 -640 to 630 units of 0.1 dB (Physical values are -64 to
                 63 dB).  A value of 0x7FFFFFFF(2147483647) indicates the line attenuation
                 is out of range to be represented. The invalid value is 2147483647.
                 If data on the port is invalid or no data is generated on
                 the port because the port has not been activated, the
                 invalid value will be returned.
                 Unit: 0.1 dB
                "
            REFERENCE    "ITU-T G.997.1, paragraph 7.5.1.11"
            ::= { hwXdslLineCfgEntry 19 }

        hwXdslLineStatusAttainableRateDs  OBJECT-TYPE
            SYNTAX      Unsigned32
            UNITS       "bits/second"
            MAX-ACCESS  read-only
            STATUS      current
            DESCRIPTION
                "Maximum Attainable Data Rate Downstream.
                 The maximum downstream net data rate currently attainable by
                 the xTU-C transmitter and the xTU-R receiver, coded in bit/s.
                 The invalid value is 4294967295. If data on the port is invalid
                 or no data is generated on the port because the port has not
                 been activated, the invalid value will be returned.
                 Unit: bits/second
                "
            REFERENCE    "ITU-T G.997.1, paragraph 7.5.1.12"
            ::= { hwXdslLineCfgEntry 20 }

        hwXdslLineStatusAttainableRateUs  OBJECT-TYPE
            SYNTAX      Unsigned32
            UNITS       "bits/second"
            MAX-ACCESS  read-only
            STATUS      current
            DESCRIPTION
                "Maximum Attainable Data Rate Upstream.
                 The maximum upstream net data rate currently attainable by the
                 xTU-R transmitter and the xTU-C receiver, coded in bit/s.
                 The invalid value is 4294967295. If data on the port is invalid
                 or no data is generated on the port because the port has not
                 been activated, the invalid value will be returned.
                 Unit: bits/second
                "
            REFERENCE    "ITU-T G.997.1, paragraph 7.5.1.13"
            ::= { hwXdslLineCfgEntry 21 }

        hwXdslLineStatusActPsdDs OBJECT-TYPE
            SYNTAX      Integer32
            UNITS       "0.1 dB"
            MAX-ACCESS  read-only
            STATUS      current
            DESCRIPTION
                "Actual Power Spectrum Density (PSD) Downstream.  The average
                 downstream transmit PSD over the sub-carriers used for
                 downstream.  It ranges from -900 to 0 units of 0.1 dB
                 (Physical values are -90 to 0 dBm/Hz).  A value of 0x7FFFFFFF(2147483647)
                 indicates the measurement is out of range to be represented.
                 The invalid value is 2147483647. If data on the port is invalid
                 or no data is generated on the port because the port has not
                 been activated, the invalid value will be returned.
                 Unit: 0.1 dB
                "
            REFERENCE    "ITU-T G.997.1, paragraph 7.5.1.14"
            ::= { hwXdslLineCfgEntry 22 }

        hwXdslLineStatusActPsdUs OBJECT-TYPE
            SYNTAX      Integer32
            UNITS       "0.1 dB"
            MAX-ACCESS  read-only
            STATUS      current
            DESCRIPTION
                "Actual Power Spectrum Density (PSD) Upstream.  The average
                 upstream transmit PSD over the sub-carriers used for upstream.
                 It ranges from -900 to 0 units of 0.1 dB (Physical values
                 are -90 to 0 dBm/Hz).  A value of 0x7FFFFFFF(2147483647) indicates the
                 measurement is out of range to be represented. The invalid value
                 is 2147483647. If data on the port is invalid or no data is
                 generated on the port because the port has not been activated,
                 the invalid value will be returned.
                 Unit: 0.1 dB
                "
            REFERENCE    "ITU-T G.997.1, paragraph 7.5.1.15"
            ::= { hwXdslLineCfgEntry 23 }

        hwXdslLineStatusActAtpDs  OBJECT-TYPE
            SYNTAX      Integer32
            UNITS       "0.1 dB"
            MAX-ACCESS  read-only
            STATUS      current
            DESCRIPTION
                "Actual Aggregate Transmit Power Downstream.  The total amount
                 of transmit power delivered by the xTU-C at the U-C reference
                 point, at the instant of measurement.  It ranges from -310 to
                 310 units of 0.1 dB (Physical values are -31 to 31 dBm).  A
                 value of 0x7FFFFFFF(2147483647) indicates the measurement is out of range to
                 be represented. The invalid value is 2147483647. If data on the
                 port is invalid or no data is generated on the port because
                 the port has not been activated, the invalid value will be returned.
                 Unit: 0.1 dB
                "
            REFERENCE    "ITU-T G.997.1, paragraph 7.5.1.16"
            ::= { hwXdslLineCfgEntry 24 }

        hwXdslLineStatusActAtpUs  OBJECT-TYPE
            SYNTAX      Integer32
            UNITS       "0.1 dB"
            MAX-ACCESS  read-only
            STATUS      current
            DESCRIPTION
                "Actual Aggregate Transmit Power Upstream.  The total amount of
                 transmit power delivered by the xTU-R at the U-R
                 reference point, at the instant of measurement.  It ranges
                 from -310 to 310 units of 0.1 dB (Physical values are -31
                 to 31 dBm).  A value of 0x7FFFFFFF(2147483647) indicates the measurement
                 is out of range to be represented.
                 Unit: 0.1 dB
                "
            REFERENCE    "ITU-T G.997.1, paragraph 7.5.1.17"
            ::= { hwXdslLineCfgEntry 25 }

        hwXdslLineBandPlan  OBJECT-TYPE
            SYNTAX      HwXdslBandPlan
            MAX-ACCESS  read-only
            STATUS      current
            DESCRIPTION
                "Band contains a series of subcarriers.
                 The first octet is the number of bands. Other octets describe the info of
                 each band.
                 Each band info is a pair of values occupying 4 octets with the
               following structure:
               First octets        - serial number of band
               Second octets       - Direction of band
               Third fourth octets - Start index of band
               Fifth sixth octets  - End index of band
                 Huawei defined.
                "
            ::= { hwXdslLineCfgEntry 26 }

        hwXdslLinePsdMaskClassSelection  OBJECT-TYPE
            SYNTAX      HwXdslTIPsdClassMask
            MAX-ACCESS  read-only
            STATUS      current
            DESCRIPTION
                "The sub class of XDSL2 PSD Mask."
            REFERENCE    "ITU-T G.997.1, paragraph 7.3.1.1.12"
            ::= { hwXdslLineCfgEntry 27 }

        hwXdslLineCurrentVdsl2Profile  OBJECT-TYPE
            SYNTAX HwXdslSubProfiles
            MAX-ACCESS  read-only
            STATUS      current
            DESCRIPTION
                "This configuration parameter contains the G.993.2 profiles
                 to be allowed by the near-end xTU on this line.
                 Options:
                 1. profile8a(1)     - Profile 8a
                 2. profile8b(2)     - Profile 8b
                 3. profile8c(3)     - Profile 8c
                 4. profile8d(4)     - Profile 8d
                 5. profile12a(5)    - Profile 12a
                 6. profile12b(6)    - Profile 12b
                 7. profile17a(7)    - Profile 17a
                 8. profile30a(8)    - Profile 30a
                 9. profile35b(9)    - Profile 35b
                 10. invalidValue(-1) - Invalid value
                "
            REFERENCE    "ITU-T G.997.1, paragraph 7.3.1.1.11"
            ::= { hwXdslLineCfgEntry 28 }

        hwXdslLineCnfgServiceProf  OBJECT-TYPE
            SYNTAX      OCTET STRING (SIZE(0..32))
            MAX-ACCESS  read-write
            STATUS      current
            DESCRIPTION
                "The value of this object identifies the row in the XDSL Line
                 Configuration Service Profile Table, (hwXdslServProfTable),
                 which applies for this XDSL line.
                "
            DEFVAL       { "DEFVAL" }
            ::= { hwXdslLineCfgEntry 29 }

        hwXdslLineCnfgSpectrumProf  OBJECT-TYPE
            SYNTAX      OCTET STRING (SIZE(0..32))
            MAX-ACCESS  read-write
            STATUS      current
            DESCRIPTION
                "The value of this object identifies the row in the XDSL Line
                 Configuration Spectrum Profile Table, (hwXdslSpectrumProfTable),
                 which applies for this XDSL line.
                "
            DEFVAL       { "DEFVAL" }
            ::= { hwXdslLineCfgEntry 30 }

        hwXdslLineCnfgDpboProf  OBJECT-TYPE
            SYNTAX      OCTET STRING (SIZE(0..32))
            MAX-ACCESS  read-write
            STATUS      current
            DESCRIPTION
                "The value of this object identifies the row in the XDSL Line
                 Configuration Dpbo Profile Table, (hwXdslDpboProfTable),
                 which applies for this XDSL line.
                "
            DEFVAL       { "DEFVAL" }
            ::= { hwXdslLineCfgEntry 31 }

        hwXdslLineCnfgUpboProf  OBJECT-TYPE
            SYNTAX      OCTET STRING (SIZE(0..32))
            MAX-ACCESS  read-write
            STATUS      current
            DESCRIPTION
                "The value of this object identifies the row in the XDSL Line
                 Configuration Upbo Profile Table, (hwXdslUpboProfTable),
                 which applies for this XDSL line.
                "
            DEFVAL       { "DEFVAL" }
            ::= { hwXdslLineCfgEntry 32 }

        hwXdslLineCnfgNoiseMarginProf  OBJECT-TYPE
            SYNTAX      OCTET STRING (SIZE(0..32))
            MAX-ACCESS  read-write
            STATUS      current
            DESCRIPTION
                "The value of this object identifies the row in the XDSL Line
                 Configuration Noise Margin Profile Table, (hwXdslNoiseMarginProfTable),
                 which applies for this XDSL line.
                "
            DEFVAL       { "DEFVAL" }
            ::= { hwXdslLineCfgEntry 33 }

        hwXdslLineCnfgDelayINPProf  OBJECT-TYPE
            SYNTAX      OCTET STRING (SIZE(0..32))
            MAX-ACCESS  read-write
            STATUS      current
            DESCRIPTION
                "The value of this object identifies the row in the XDSL Line
                 Configuration Delay-INP Profile Table, (hwXdslDelayInpProfTable),
                 which applies for this XDSL line.
                "
            DEFVAL       { "DEFVAL" }
            ::= { hwXdslLineCfgEntry 34 }

        hwXdslUpboProfKl0CpeVal  OBJECT-TYPE
            SYNTAX      Unsigned32
            UNITS       "0.1dB"
            MAX-ACCESS  read-only
            STATUS      current
            DESCRIPTION
                "The actual value of KL0_CPE parameter,it ranges
                 from 0 to 1280 units of 0.1 dB. The invalid value is 4294967295.
                 If data on the port cannot be queried, data on the port is invalid,
                 or no data is generated on the port because the port has not been
                 activated, the invalid value will be returned.
                 Unit: 0.1dB
                "
            ::= { hwXdslLineCfgEntry 35 }

        hwXdslLineStatusCodingGainDs  OBJECT-TYPE
            SYNTAX      Unsigned32
            UNITS       "0.5dB"
            MAX-ACCESS  read-only
            STATUS      current
            DESCRIPTION
                "The actual value of Coding gain downstream parameter,it ranges
                 from 0 to 16 units of 0.5 dB. The invalid value is 4294967295.
                 If data on the port cannot be queried, data on the port is invalid,
                 or no data is generated on the port because the port has not
                 been activated, the invalid value will be returned.
                 Unit: 0.5dB
                "
            ::= { hwXdslLineCfgEntry 36 }

        hwXdslLineStatusCodingGainUs  OBJECT-TYPE
            SYNTAX      Unsigned32
            UNITS       "0.5dB"
            MAX-ACCESS  read-only
            STATUS      current
            DESCRIPTION
                "The actual value of Coding gain upstream parameter,it ranges
                 from 0 to 16 units of 0.5 dB. The invalid value is 4294967295.
                 If data on the port cannot be queried, data on the port is invalid,
                 or no data is generated on the port because the port has not
                 been activated, the invalid value will be returned.
                 Unit: 0.5dB
                "
            ::= { hwXdslLineCfgEntry 37 }

        hwXdslLineStatusPcbDs  OBJECT-TYPE
            SYNTAX      Unsigned32
            UNITS       "1dB"
            MAX-ACCESS  read-only
            STATUS      current
            DESCRIPTION
                "The actual value of power cut back downstream parameter,
                 it ranges from 0 to 40 units of 1 dB. The invalid value
                 is 4294967295. If data on the port cannot be queried,
                 data on the port is invalid, or no data is generated on the
                 port because the port has not been activated, the invalid
                 value will be returned.
                 Unit: 1dB
                "
            ::= { hwXdslLineCfgEntry 38 }

        hwxdslDlmDsmprofile  OBJECT-TYPE
            SYNTAX      OCTET STRING (SIZE(0..32))
            MAX-ACCESS  read-write
            STATUS      current
            DESCRIPTION
                "The value of this object identifies the row
                 in the DLM/DSM Profile Table,
                 which applies for this XDSL line.
                "
            ::= { hwXdslLineCfgEntry 39 }

        hwXdslLineActmode  OBJECT-TYPE
            SYNTAX      HwXdslActmode
            MAX-ACCESS  read-only
            STATUS      current
            DESCRIPTION
                "Actived mode after training between co and cpe.
                 Options:
                 1. ADSL(1)          - ETSI,T1.413 G992.1,G992.2
                 2. ADSL2(2)         - G992.3,G992.4
                 3. ADSL2PLUS(3)     - G992.5
                 4. VDSL(4)          - G993.1
                 5. VDSL2(5)         - G993.2,G993.5
                 6. FAST(6)          - G.9701
                 7. invalidValue(-1) - Invalid value
                "
            ::= { hwXdslLineCfgEntry 40 }

        hwXdslUpboProfKl0CoVal  OBJECT-TYPE
            SYNTAX      Unsigned32
            UNITS       "0.1dB"
            MAX-ACCESS  read-only
            STATUS      current
            DESCRIPTION
                "The actual value of KL0_CO parameter, it ranges
                 from 0 to 1280 units of 0.1 dB. The invalid value
                 is 4294967295. If data on the port cannot be queried,
                 data on the port is invalid, or no data is generated
                 on the port because the port has not been activated,
                 the invalid value will be returned.
                 Unit: 0.1dB
                "
            ::= { hwXdslLineCfgEntry 41 }

        hwXdslLineStatusRtxUsedDs  OBJECT-TYPE
            SYNTAX      HwXdslStatusRtxUsed
            MAX-ACCESS  read-only
            STATUS      current
            DESCRIPTION
                "This parameter specifies whether G.998.4 retransmission
                 is used in downstream.
                 Options:
                 1. rtxInuse(1)                             - RTX in use
                 2. rtxUnusedModeForbidden(2)               - RTX not in use, due to RTX_MODE = FORBIDDEN
                 3. rtxUnusedNotSupportedXtuc(3)            - RTX not in use, due to not supported by the XTU-C
                 4. rtxUnusedNotSupportedXtur(4)            - RTX not in use, due to not supported by the XTU-R
                 5. rtxUnusedNotSupportedXtucAndXtur(5)     - RTX not in use, due to not supported by the XTU-C and XTU-R
                 6. invalidValue(-1)                        - Invalid value
                "
            REFERENCE    "ITU-T G.997.1, paragraph 7.5.1.38"
            ::= { hwXdslLineCfgEntry 42 }


        hwXdslLineStatusRtxUsedUs  OBJECT-TYPE
            SYNTAX      HwXdslStatusRtxUsed
            MAX-ACCESS  read-only
            STATUS      current
            DESCRIPTION
                "This parameter specifies whether G.998.4 retransmission
                 is used in upstream.
                 Options:
                 1. rtxInuse(1)                             - RTX in use
                 2. rtxUnusedModeForbidden(2)               - RTX not in use, due to RTX_MODE = FORBIDDEN
                 3. rtxUnusedNotSupportedXtuc(3)            - RTX not in use, due to not supported by the XTU-C
                 4. rtxUnusedNotSupportedXtur(4)            - RTX not in use, due to not supported by the XTU-R
                 5. rtxUnusedNotSupportedXtucAndXtur(5)     - RTX not in use, due to not supported by the XTU-C and XTU-R
                 6. invalidValue(-1)                        - Invalid value
                "
            REFERENCE    "ITU-T G.997.1, paragraph 7.5.1.38"
            ::= { hwXdslLineCfgEntry 43 }

      hwXdslLineStatusLastRetrainInfo  OBJECT-TYPE
          SYNTAX INTEGER
                {
                 none(1),
                 cpeL3Trigger(2),
                 lomUsTriggerDra(3),
                 lomDsTriggerDra(4),
                 cpeNeverAnswerOam(5),
                 cpeNoMoreAnswerOam(6),
                 persistentNcdUs(7),
                 persistentNcdDs(8),
                 persistentLcdUs(9),
                 persistentLcdDs(10),
                 l2ProblemCoDrop(11),
                 l2ProblemCpeDrop(12),
                 bitswapRefusedUsCoDrop(13),
                 bitswapRefusedUsCpeDrop(14),
                 channelChangeUsCoDrop(15),
                 channelChangeUsCpeDrop(16),
                 noiseIncreaseUsCoDrop(17),
                 noiseIncreaseUsCpeDrop(18),
                 bitswapRefusedDsCoDrop(19),
                 bitswapRefusedDsCpeDrop(20),
                 channelChangeDsCoDrop(21),
                 channelChangeDsCpeDrop(22),
                 noiseIncreaseDsCoDrop(23),
                 noiseIncreaseDsCpeDrop(24),
                 lomUsCoDrop(25),
                 lomUsCpeDrop(26),
                 lomDsCoDrop(27),
                 lomDsCpeDrop(28),
                 sraProblemUsCoDrop(29),
                 sraProblemUsCpeDrop(30),
                 sraFailedUsCoDrop(31),
                 sraFailedUsCpeDrop(32),
                 sraProblemDsCoDrop(33),
                 sraProblemDsCpeDrop(34),
                 sraRejectedDsCoDrop(35),
                 sraRejectedDsCpeDrop(36),
                 bitswapProblemUsCoDrop(37),
                 bitswapProblemUsCpeDrop(38),
                 bitswapFailedUsCoDrop(39),
                 bitswapFailedUsCpeDrop(40),
                 bitswapProblemDsCoDrop(41),
                 bitswapProblemDsCpeDrop(42),
                 bitswapRejectedDsCoDrop(43),
                 bitswapRejectedDsCpeDrop(44),
                 cpeSwitchedOff(45),
                 cpeLost(46),
                 coReset(47),
                 coStop(48),
                 unknown(49),
                 vceTriggered(50)
                }
      MAX-ACCESS  read-only
      STATUS      current
      DESCRIPTION
         "Indicates the last retrained information performed on the line.
          Options:
          1. none(1)                       - No record is available
          2. cpeL3Trigger(2)               - The terminal initiates a low power consumption L3 request
          3. lomUsTriggerDra(3)            - The upstream noise margin is smaller than the minimum noise margin in rate dynamic adjustment
          4. lomDsTriggerDra(4)            - The downstream noise margin is smaller than the minimum noise margin in rate dynamic adjustment
          5. cpeNeverAnswerOam(5)          - No OAM response is received from the CPE all the time
          6. cpeNoMoreAnswerOam(6)         - No OAM response is received from the CPE
          7. persistentNcdUs(7)            - Upstream continuous no cell delineation
          8. persistentNcdDs(8)            - Downstream continuous no cell delineation
          9. persistentLcdUs(9)            - Upstream continuous loss of cell delineation
          10.persistentLcdDs(10)           - Downstream continuous loss of cell delineation
          11.l2ProblemCoDrop(11)           - The CO is faulty during the switching from L0 to L2
          12.l2ProblemCpeDrop(12)          - The CPE is faulty during the switching from L0 to L2
          13.bitswapRefusedUsCoDrop(13)    - The CO goes offline when the upstream bit swap fault occurs 10 times consecutively
          14.bitswapRefusedUsCpeDrop(14)   - The CPE goes offline when the downstream bit swap fault occurs 10 times consecutively
          15.channelChangeUsCoDrop(15)     - The CO goes offline when the upstream net rate changes
          16.channelChangeUsCpeDrop(16)    - The CPE goes offline when the upstream net rate changes
          17.noiseIncreaseUsCoDrop(17)     - The CO goes offline when the upstream noise increases
          18.noiseIncreaseUsCpeDrop(18)    - The CPE goes offline when the upstream noise increases
          19.bitswapRefusedDsCoDrop(19)    - The CO goes offline when the downstream bit swap fault occurs 10 times consecutively
          20.bitswapRefusedDsCpeDrop(20)   - The CPE goes offline when the downstream bit swap fault occurs 10 times consecutively
          21.channelChangeDsCoDrop(21)     - The CO goes offline when the downstream net rate changes
          22.channelChangeDsCpeDrop(22)    - The CPE goes offline when the downstream net rate changes
          23.noiseIncreaseDsCoDrop(23)     - The CO goes offline when the downstream noise increases
          24.noiseIncreaseDsCpeDrop(24)    - The CPE goes offline when the downstream noise increases
          25.lomUsCoDrop(25)               - The CO goes offline when the upstream noise margin is smaller than the minimum noise margin
          26.lomUsCpeDrop(26)              - The CPE goes offline when the upstream noise margin is smaller than the minimum noise margin
          27.lomDsCoDrop(27)               - The CO goes offline when the downstream noise margin is smaller than the minimum noise margin
          28.lomDsCpeDrop(28)              - The CPE goes offline when the downstream noise margin is smaller than the minimum noise margin
          29.sraProblemUsCoDrop(29)        - The CO goes offline when the upstream SRA is faulty
          30.sraProblemUsCpeDrop(30)       - The CPE goes offline when the upstream SRA is faulty
          31.sraFailedUsCoDrop(31)         - The CO goes offline when the upstream SRA fails
          32.sraFailedUsCpeDrop(32)        - The CPE goes offline when the upstream SRA fails
          33.sraProblemDsCoDrop(33)        - The CO goes offline when the downstream SRA is fault
          34.sraProblemDsCpeDrop(34)       - The CPE goes offline when the downstream SRA is faulty
          35.sraRejectedDsCoDrop(35)       - The CO goes offline when the downstream SRA is rejected
          36.sraRejectedDsCpeDrop(36)      - The CPE goes offline when the downstream SRA is rejected
          37.bitswapProblemUsCoDrop(37)    - The CO goes offline when the upstream bit swap is faulty
          38.bitswapProblemUsCpeDrop(38)   - The CPE goes offline when the upstream bit swap is faulty
          39.bitswapFailedUsCoDrop(39)     - The CO goes offline when the upstream bit swap fails
          40.bitswapFailedUsCpeDrop(40)    - The CPE goes offline when the upstream bit swap fails
          41.bitswapProblemDsCoDrop(41)    - The CO goes offline when the downstream bit swap is faulty
          42.bitswapProblemDsCpeDrop(42)   - The CPE goes offline when the downstream bit swap is faulty
          43.bitswapRejectedDsCoDrop(43)   - The CO goes offline when the downstream bit swap is rejected
          44.bitswapRejectedDsCpeDrop(44)  - The CPE goes offline when the downstream bit swap is rejected
          45.cpeSwitchedOff(45)            - The CPE power supply is shut down
          46.cpeLost(46)                   - The CPE is disconnected
          47.coReset(47)                   - The CO resets the chipset or line
          48.coStop(48)                    - The CO actively deactivate the port
          49.unknown(49)                   - Unknown reason
          50.vceTriggered(50)        - The VCE initial DSP to drop from showtime
          "
      ::= { hwXdslLineCfgEntry 44 }

        hwXdslUpboRxThreshDs OBJECT-TYPE
            SYNTAX      Integer32
            UNITS       "dB"
            MAX-ACCESS  read-only
            STATUS      current
            DESCRIPTION
                "This parameter reports the downstream received signal level threshold value
                 used in the Alternative Electrical Length Estimation method (ELE-M1).
                 This parameter represents an offset from -100 dB,
                 and ranges from -64 dB to 0 dB in steps of 1 dB. The invalid value is
                 2147483647. If data on the port cannot be queried, data on the port
                 is invalid, or no data is generated on the port because the port has
                 not been activated, the invalid value will be returned.
                 Unit: dB
                "
            REFERENCE    "ITU-T G.997.1, paragraph 7.5.1.23.5"
            ::= { hwXdslLineCfgEntry 45 }

        hwXdslUpboRxThreshUs OBJECT-TYPE
            SYNTAX      Integer32
            UNITS       "dB"
            MAX-ACCESS  read-only
            STATUS      current
            DESCRIPTION
                "This parameter reports the upstream received signal level threshold value
                 used in the Alternative Electrical Length Estimation method (ELE-M1).
                 This parameter represents an offset from -100 dB,
                 and ranges from -64 dB to 0 dB in steps of 1 dB. The invalid value is
                 2147483647. If data on the port cannot be queried, data on the port
                 is invalid, or no data is generated on the port because the port has
                 not been activated, the invalid value will be returned.
                 Unit: dB
                "
            REFERENCE    "ITU-T G.997.1, paragraph 7.5.1.23.6"
            ::= { hwXdslLineCfgEntry 46 }

        hwXdslLineStatusLineRateDs  OBJECT-TYPE
            SYNTAX      Unsigned32
            UNITS       "bits/second"
            MAX-ACCESS  read-only
            STATUS      current
            DESCRIPTION
                "The actual line rate downstream. The invalid value is 4294967295.
                If data on the port cannot be queried, data on the port is invalid,
                or no data is generated on the port because the port has not been
                activated, the invalid value will be returned.
                 Unit: bits/second
                "
            ::= { hwXdslLineCfgEntry 47 }

        hwXdslLineStatusLineRateUs  OBJECT-TYPE
            SYNTAX      Unsigned32
            UNITS       "bits/second"
            MAX-ACCESS  read-only
            STATUS      current
            DESCRIPTION
                "The actual line rate upstream. The invalid value is 4294967295.
                If data on the port cannot be queried, data on the port is invalid,
                or no data is generated on the port because the port has not been
                activated, the invalid value will be returned.
                 Unit: bits/second
                "
            ::= { hwXdslLineCfgEntry 48 }

        hwXdslLineSplitterMode  OBJECT-TYPE
            SYNTAX INTEGER
                {connect(1),
                 bypass(2),
                 pstnonly(3),
                 lineonly(4)

                }
            MAX-ACCESS  read-write
            STATUS      current
            DESCRIPTION
                "This parameter indicates which mode will be applied to the port splitter .
                 Options:
                 1. connect (1)          - Splitter mode is connect or no splitter(always connected)
                 2. bypass (2)           - Splitter mode is bypass
                 3. pstnonly (3)         - Only the pstn port is plugged to the linecard
                 4. lineonly (4)         - Only the line port is plugged to the linecard
                "
            ::= { hwXdslLineCfgEntry 49 }

        hwXdslLineBackup OBJECT-TYPE
            SYNTAX INTEGER
                {enable(1),
                 disable(2)
                }
            MAX-ACCESS  read-write
            STATUS      current
            DESCRIPTION
                 "This parameter indicates whether the port backup is enabled.
                Options:
                1. enable(1)      - Enable the port backup.
                2. disable(2)     - Disable the port backup.
               "
            DEFVAL       { disable }
            ::= { hwXdslLineCfgEntry 50 }

        hwXdslLineBackupPort OBJECT-TYPE
            SYNTAX Unsigned32
            MAX-ACCESS  read-only
            STATUS      current
            DESCRIPTION
                 "This parameter indicates the backup port ifindex. If data on the port is invalid or no data is
                  generated on the port, the port is not backed up.
                  The invalid value is 4294967295.
               "
            ::= { hwXdslLineCfgEntry 51 }

        hwXdslLinePhyRcontrol   OBJECT-TYPE
            SYNTAX INTEGER {
                               enable (1),
                               disable (2)
                           }
            MAX-ACCESS  read-write
            STATUS      current
            DESCRIPTION
                "This parameter indicates whether the PHY-R retransmission is enabling.
                 In TR165 mode, the H80BVDPM board should be enabled when it works as ADSL mode.
               Options:
                1. enable(1)        - Enable the PHY-R retransmission of VDSL2 line.
                2. disable(2)       - Disable the PHY-R retransmission of VDSL2 line.
              "
            DEFVAL       { disable }
            ::= { hwXdslLineCfgEntry 52 }

        hwXdslLineStatusActPsdLimitMask    OBJECT-TYPE
            SYNTAX      INTEGER {
                          annexA998D32              (1),
                          annexA998D64              (2),
                          annexB997M1cA7            (3),
                          annexB997M1xM8            (4),
                          annexB997M1xM             (5),
                          annexB997M2xM8            (6),
                          annexB997M2xA             (7),
                          annexB997M2xM             (8),
                          annexB998M1xA             (9),
                          annexB998M1xB             (10),
                          annexB998M1xNUS0          (11),
                          annexB998M2xA             (12),
                          annexB998M2xM             (13),
                          annexB998M2xB             (14),
                          annexB998M2xNUS0          (15),
                          annexBHPE17M1NUS0         (16),
                          annexBHPE30M1NUS0         (17),
                          annexB997E17M2xA          (18),
                          annexB997E30M2xNUS0       (19),
                          annexB998E17M2xNUS0       (20),
                          annexB998E17M2xNUS0M      (21),
                          annexB998ADE17M2xNUS0M    (22),
                          annexB998ADE17M2xB        (23),
                          annexB998E30M2xNUS0       (24),
                          annexB998E30M2xNUS0M      (25),
                          annexB998ADE30M2xNUS0M    (26),
                          annexB998ADE17M2xA        (27),
                          annexB998ADE30M2xNUS0A    (28),
                          annexA998D48              (29),
                          annexA998D128             (30),
                          annexB998ADE17M2xM        (31),
                          annexB998E17M2xA          (32),
                          annexB998ADE17SPEM2xA     (33),
                          annexB998E35M2xA          (34),
                          annexB998ADE35M2xA        (35),
                          annexB998ADE35M2xB        (36),
                          annexB998ADE35M2xM        (37),
                          invalidValue              (-1)
            }
            MAX-ACCESS  read-only
            STATUS      current
            DESCRIPTION
               "(LIMITMASK).
                This parameter contains the actual G.993.2 limit PSD masks selected during showtime.
                Options:
              1. annexA998D32(1)                 - D-32
              2. annexA998D64(2)                 - D-64
              3. annexB997M1cA7(3)               - B7-1
              4. annexB997M1xM8(4)               - B7-2
              5. annexB997M1xM(5)                - B7-3
              6. annexB997M2xM8(6)               - B7-4
              7. annexB997M2xA(7)                - B7-5
              8. annexB997M2xM(8)                - B7-6
              9. annexB998M1xA(9)                - B8-1
              10.annexB998M1xB(10)               - B8-2
              11.annexB998M1xNUS0(11)            - B8-3
              12.annexB998M2xA(12)               - B8-4
              13.annexB998M2xM(13)               - B8-5
              14.annexB998M2xB(14)               - B8-6
              15.annexB998M2xNUS0(15)            - B8-7
              16.annexBHPE17M1NUS0(16)           - B7-7
              17.annexBHPE30M1NUS0(17)           - B7-8
              18.annexB997E17M2xA(18)            - B7-9
              19.annexB997E30M2xNUS0(19)         - B7-10
              20.annexB998E17M2xNUS0(20)         - B8-8
              21.annexB998E17M2xNUS0M(21)        - B8-9
              22.annexB998ADE17M2xNUS0M(22)      - B8-10
              23.annexB998ADE17M2xB(23)          - B8-12
              24.annexB998E30M2xNUS0(24)         - B8-13
              25.annexB998E30M2xNUS0M(25)        - B8-14
              26.annexB998ADE30M2xNUS0M(26)      - B8-15
              27.annexB998ADE17M2xA(27)          - B8-11
              28.annexB998ADE30M2xNUS0A(28)      - B8-16
              29.annexA998D48(29)                - D-48
              30.annexA998D128(30)               - D-128
              31.annexB998ADE17M2xM(31)          - B8-17
              32.annexB998E17M2xA(32)            - B8-18
              33.annexB998ADE17SPEM2xA(33)       - new limit PSD masks for vdsl2 rate elevation
              34.annexB998E35M2xA(34)            - B8-19
              35.annexB998ADE35M2xA(35)          - B8-20
              36.annexB998ADE35M2xB(36)          - B8-21
              37.annexB998ADE35M2xM(37)          - B8-22
              38.invalidValue(-1)                - Invalid value
                "
            REFERENCE    "ITU-T G.997.1, paragraph #7.3.1.2.16"
            ::= { hwXdslLineCfgEntry 53 }

        hwXdslLineStatusActRaModeDs OBJECT-TYPE
            SYNTAX INTEGER
                { manual(1),
                  rainit(2),
                  dynamic(3),
                  dynamicwithsos(4),
                  invalidValue(-1)
                }
            MAX-ACCESS  read-only
            STATUS      current
            DESCRIPTION
               "Actual transmit rate adaptation mode downstream.
                Options:
                1. manual(1)         - No Rate-Adaptation. The initialization process
                                       attempts to synchronize to a specified rate.
                2. rainit(2)         - Rate-Adaptation during initialization process
                                       only, which attempts to synchronize to a rate
                                       between minimum and maximum specified values.
                3. dynamic(3)        - Rate-Adaptation during show time.
                4. dynamicwithsos(4) - Rate-Adaptation during show time by SOS and SRA.
                                       In this mode, enabling of SOS and SRA is mandatory.
                5. invalidValue(-1)  - Invalid value
                "
            ::= { hwXdslLineCfgEntry 54 }

        hwXdslLineStatusActRaModeUs OBJECT-TYPE
            SYNTAX INTEGER
                { manual(1),
                  rainit(2),
                  dynamic(3),
                  dynamicwithsos(4),
                  invalidValue(-1)
                }
            MAX-ACCESS  read-only
            STATUS      current
            DESCRIPTION
               "Actual transmit rate adaptation mode upstream.
                Options:
                1. manual(1)         - No Rate-Adaptation. The initialization process
                                       attempts to synchronize to a specified rate.
                2. rainit(2)         - Rate-Adaptation during initialization process
                                       only, which attempts to synchronize to a rate
                                       between minimum and maximum specified values.
                3. dynamic(3)        - Rate-Adaptation during show time.
                4. dynamicwithsos(4) - Rate-Adaptation during show time by SOS and SRA.
                                       In this mode, enabling of SOS and SRA is mandatory.
                5. invalidValue(-1)  - Invalid value
                "
            ::= { hwXdslLineCfgEntry 55 }

        hwXdslLineStatusActInpRocDs  OBJECT-TYPE
            SYNTAX      Unsigned32(0..254 | 4294967295)
            UNITS       "0.1 DMT symbol"
            MAX-ACCESS  read-only
            STATUS      current
            DESCRIPTION
                "This parameter reports the actual impulse noise protection (INP) of the ROC
                 in the downstream direction.
                 The value is coded in fractions of DMT symbols with a granularity of 0.1 symbols.
                 The invalid value is 4294967295. If data on the port is invalid or no
                 data is generated on the port because the port has not been activated,
                 the invalid value will be returned.
                 Unit: 0.1 DMT symbol
                "
            REFERENCE    "ITU-T G.997.1, paragraph 7.5.1.34"
            ::= { hwXdslLineCfgEntry 56 }

        hwXdslLineStatusActInpRocUs  OBJECT-TYPE
            SYNTAX      Unsigned32(0..254 | 4294967295)
            UNITS       "0.1 DMT symbol"
            MAX-ACCESS  read-only
            STATUS      current
            DESCRIPTION
                "This parameter reports the actual impulse noise protection (INP) of the ROC
                 in the upstream direction.
                 The value is coded in fractions of DMT symbols with a granularity of 0.1 symbols.
                 The invalid value is 4294967295. If data on the port is invalid or no
                 data is generated on the port because the port has not been activated,
                 the invalid value will be returned.
                 Unit: 0.1 DMT symbol
                "
            REFERENCE    "ITU-T G.997.1, paragraph 7.5.1.34"
            ::= { hwXdslLineCfgEntry 57 }

        hwXdslLineStatusActSnrmRocDs  OBJECT-TYPE
            SYNTAX      Integer32
            UNITS       "0.1 dB"
            MAX-ACCESS  read-only
            STATUS      current
            DESCRIPTION
                "This parameter reports the actual SNR Margin of the ROC
                 in the downstream direction.
                 Downstream SNR Margin is the maximum increase in dB of the
                 noise power received at the xTU-R, such that the BER
                 requirements are met for all downstream bearer channels. It
                 ranges from -640 to 630 units of 0.1 dB (Physical values are
                 -64 to 63 dB). A value of 0x7FFFFFFF(2147483647) indicates the line
                 attenuation is out of range to be represented. The invalid
                 value is 2147483647. If data on the port is invalid or no data
                 is generated on the port because the port has not been activated,
                 the invalid value will be returned.
                 Unit: 0.1 dB
                "
            REFERENCE    "ITU-T G.997.1, paragraph 7.5.1.35"
            ::= { hwXdslLineCfgEntry 58 }

        hwXdslLineStatusActSnrmRocUs  OBJECT-TYPE
            SYNTAX      Integer32
            UNITS       "0.1 dB"
            MAX-ACCESS  read-only
            STATUS      current
            DESCRIPTION
                "This parameter reports the actual SNR Margin of the ROC
                 in the upstream direction.
                 Upstream SNR Margin is the maximum increase in dB of the noise
                 power received at the xTU-C, such that the BER requirements
                 are met for all upstream bearer channels. It ranges from
                 -640 to 630 units of 0.1 dB (Physical values are -64 to
                 63 dB). A value of 0x7FFFFFFF(2147483647) indicates the line attenuation
                 is out of range to be represented. The invalid value is 2147483647.
                 If data on the port is invalid or no data is generated on
                 the port because the port has not been activated, the
                 invalid value will be returned.
                 Unit: 0.1 dB
                "
            REFERENCE    "ITU-T G.997.1, paragraph 7.5.1.35"
            ::= { hwXdslLineCfgEntry 59 }

        hwXdslLineCurrentGfastProfile  OBJECT-TYPE
            SYNTAX      INTEGER{
                fastprofile106(1),
                fastprofile212(2),
                invalidValue(-1)
            }
            MAX-ACCESS  read-only
            STATUS      current
            DESCRIPTION
                "This parameter reports the current G.fast profile.
                 Options:
                 1. fastprofile106(1)     - The current G.fast profile is G.fast profile 106.
                 2. fastprofile212(2)     - The current G.fast profile is G.fast profile 212.
                 3. invalidValue(-1)      - Invalid value
                "
            ::= { hwXdslLineCfgEntry 60 }

        hwXdslLineDetectionResult  OBJECT-TYPE
            SYNTAX BITS {
                noFailure(0),
                abLineConnect(1),
                singleLineInterruption(2),
                lostSplitter(3),
                bridgedTapExist(4)
            }
            MAX-ACCESS  read-only
            STATUS      current
            DESCRIPTION
                "Indicates current line detection result (possible failures) of the line.
             This is a bit-map of possible conditions. The various bit positions are:
             noFailure(0), abLineConnect(1), singleLineInterruption(2), lostSplitter(3),
             bridgedTapExist(4).
                "
            ::= { hwXdslLineCfgEntry 61 }

        hwXdslLineCurrentGfastSnrMarginRmcDs     OBJECT-TYPE
            SYNTAX      Integer32
            UNITS       "0.1 dB"
            MAX-ACCESS  read-only
            STATUS      current
            DESCRIPTION
                "This parameter reports the signal-to-noise ratio margin for the RMC
                 in the downstream direction. It ranges from -511 to 511 units of 0.1 dB
                 (Physical values are -51.1 to 51.1 dB).A special value of 0x7FFFFFFF(2147483647)
                 indicates that the signal-to-noise ratio margin for the RMC is out of the
                 range to be represented.The invalid value is 2147483647.If data on the port
                 is invalid or no data is generated on the port because the port has not
                 been activated, the invalid value will be returned.
                 Unit: 0.1 dB
                "
            REFERENCE    "ITU-T G.997.2, paragraph 7.10.12.1"
            ::= { hwXdslLineCfgEntry 62 }

        hwXdslLineCurrentGfastSnrMarginRmcUs     OBJECT-TYPE
            SYNTAX      Integer32
            UNITS       "0.1 dB"
            MAX-ACCESS  read-only
            STATUS      current
            DESCRIPTION
                "This parameter reports the signal-to-noise ratio margin for the RMC
                 in the upstream direction. It ranges from -511 to 511 units of 0.1 dB
                 (Physical values are -51.1 to 51.1 dB).A special value of 0x7FFFFFFF(2147483647)
                 indicates that the signal-to-noise ratio margin for the RMC is out of the
                 range to be represented.The invalid value is 2147483647.If data on the port
                 is invalid or no data is generated on the port because the port has not
                 been activated, the invalid value will be returned.
                 Unit: 0.1 dB
                "
            REFERENCE    "ITU-T G.997.2, paragraph 7.10.12.2"
            ::= { hwXdslLineCfgEntry 63 }

        hwXdslBypassAutoRecoverTime  OBJECT-TYPE
            SYNTAX      Unsigned32(0 | 60..86400)
            UNITS       "second"
            MAX-ACCESS  read-write
            STATUS      current
            DESCRIPTION
                "This parameter indicates the automatic recovery time-out duration configuration, which can be configured as 0, or 60-86400 seconds.
                 0 is the special value indicating that automatic recovery is disabled. 0 is also the default configuration.
                 If the auto-recover-time is configured in a non-zero value, and the bypass relay is configured to
                 bypass/line-only/pstn-only mode, the port level timer will be started, after it's timed out,
                 the bypass relay will be recovered to connect mode automatically.
                 Unit: second
                "
            ::= { hwXdslLineCfgEntry 64 }

        hwXdslLineVdsl2ProfileFallbackstatus  OBJECT-TYPE
            SYNTAX      INTEGER{
                noFallback(1),
                fallback(2)
            }
            MAX-ACCESS  read-only
            STATUS      current
            DESCRIPTION
                "This parameter reports the G.993.2 profile fallback state.
                 Options:
                 1. noFallback(1)   - The G.993.2 profile fallback is not in use or not configured.
                 2. fallback(2)     - The G.993.2 profile fallback is in use.
                "
            ::= { hwXdslLineCfgEntry 65 }

        hwXdslLineCnfgTR129RfiProf  OBJECT-TYPE
            SYNTAX      OCTET STRING (SIZE(0..128))
            MAX-ACCESS  read-write
            STATUS      current
            DESCRIPTION
                "The value of this object identifies the row in the XDSL Line
                 Configuration RFI Profile Table, (hwVOPRFIConfProfTable),
                 which applies for this XDSL line.
                "
            DEFVAL       { "DEFVAL" }
            ::= { hwXdslLineCfgEntry 66 }

        hwXdslLineStatusActVdsl2LrMode  OBJECT-TYPE
            SYNTAX INTEGER
                {
                 notoperate(0),
                 shortloop(1),
                 mediumloop(2),
                 longloop(3)
                }
            MAX-ACCESS  read-only
            STATUS      current
            DESCRIPTION
                "This parameter reports the actual operation type of VDSL2-LR.
                 Options:
                 1. notoperate(0)              -the line does not operate in VDSL2-LR mode
                 2. shortloop(1)               -the line operates according to the short loop operation type of VDSL2-LR
                 3. mediumloop(2)              -the line operates according to the medium loop operation type of VDSL2-LR
                 4. longloop(3)                -the line operates according to the long loop operation type of VDSL2-LR
                "
            ::= { hwXdslLineCfgEntry 67 }

        --         hwOntXdslLineTable
        hwOntXdslLineTable  OBJECT-TYPE
            SYNTAX      SEQUENCE  OF  HwOntXdslLineEntry
            MAX-ACCESS  not-accessible
            STATUS      current
            DESCRIPTION
                "The table hwOntXdslLineTable contains configuration,
                 command and status parameters of the ONT XDSL port line.
                 The indexes of this table are ifIndex, hwOntObjectIndex, hwOntUniPhyType and hwOntXdslPortid.
                "
            ::= { hwXdslLine 2 }
        hwOntXdslLineEntry  OBJECT-TYPE
            SYNTAX      HwOntXdslLineEntry
            MAX-ACCESS  not-accessible
            STATUS      current
            DESCRIPTION
                "The table hwOntXdslLineTable contains configuration,
                 command and status parameters of the ONT XDSL port line.
                 The indexes of this entry are ifIndex,hwOntObjectIndex, hwOntUniPhyType and hwOntXdslPortid.
                "
            INDEX  { ifIndex,
                     hwOntObjectIndex,
                     hwOntUniPhyType,
                     hwOntXdslPortid }
            ::= { hwOntXdslLineTable 1 }
        HwOntXdslLineEntry  ::=
            SEQUENCE {
              hwOntObjectIndex                      Integer32,
              hwOntUniPhyType                       INTEGER,
              hwOntXdslPortid                      Integer32,
              hwOntXdslLineCnfgTemplate            OCTET STRING,
              hwOntXdslLineAlarmCnfgTemplate       OCTET STRING,
              hwOntXdslLineAdminStatus             INTEGER,
              hwOntXdslLineOperationStatus         INTEGER,
              hwOntXdslLineBandPlan                HwXdslBandPlan,
              hwOntXdslLineStatusAttainableRateDs  Unsigned32,
              hwOntXdslLineStatusAttainableRateUs  Unsigned32,
              hwOntXdslLineStatusXtuTransSys       Unsigned32,
              hwOntXdslLineStatusPwrMngState       HwXdslPowerMngState,
              hwOntXdslLineStatusInitResult        HwXdslInitResult,
              hwOntXdslLineStatusActAtpDs          Integer32,
              hwOntXdslLineStatusActAtpUs          Integer32,
              hwOntXdslLineCurrentVdsl2Profile     HwXdslSubProfiles,
              hwOntXdslLineStatusLnAttenDs         Unsigned32,
              hwOntXdslLineStatusLnAttenUs         Unsigned32,
              hwOntXdslLineStatusSigAttenDs        Unsigned32,
              hwOntXdslLineStatusSigAttenUs        Unsigned32,
              hwOntXdslLineStatusSnrMarginDs       Integer32,
              hwOntXdslLineStatusSnrMarginUs       Integer32
            }

        hwOntObjectIndex  OBJECT-TYPE
            SYNTAX      Integer32
            MAX-ACCESS  not-accessible
            STATUS      current
            DESCRIPTION
                "ONT ID.
                "
            ::= { hwOntXdslLineEntry 1 }
        hwOntUniPhyType  OBJECT-TYPE
            SYNTAX      INTEGER{
                vdsl(37)
            }
            MAX-ACCESS  not-accessible
            STATUS      current
            DESCRIPTION
                "This object indicates the physical type of ONT UNI.
           Options:
           1. vdsl(37)           - VDSL
                "
            ::= { hwOntXdslLineEntry 2 }
        hwOntXdslPortid  OBJECT-TYPE
            SYNTAX      Integer32
            MAX-ACCESS  not-accessible
            STATUS      current
            DESCRIPTION
                "The ONT XDSL port ID.
                "
            ::= { hwOntXdslLineEntry 3 }
        hwOntXdslLineCnfgTemplate  OBJECT-TYPE
            SYNTAX      OCTET STRING (SIZE(0..32))
            MAX-ACCESS  read-write
            STATUS      current
            DESCRIPTION
                "The value of this object identifies the row in the XDSL Line
                 Configuration Templates Table, (hwXdslLineConfTemplateTable),
                 which applies for this XDSL line.
                "
            REFERENCE    "DSL Forum TR-90, paragraph 5.1.1"
            DEFVAL       { "DEFVAL" }
            ::= { hwOntXdslLineEntry 4 }
        hwOntXdslLineAlarmCnfgTemplate  OBJECT-TYPE
            SYNTAX      OCTET STRING (SIZE(0..32))
            MAX-ACCESS  read-write
            STATUS      current
            DESCRIPTION
                "The value of this object identifies the row in the XDSL Line
                 Alarm Configuration Template Table,
                 (hwXdslLineAlarmConfTemplateTable), which applies to this XDSL
                 line.
                 Currently, this leaf is reserved, and it is not supported.
                "
            REFERENCE    "DSL Forum TR-90, paragraph 5.1.1"
            DEFVAL       { "DEFVAL" }
            ::= { hwOntXdslLineEntry 5 }
        hwOntXdslLineAdminStatus  OBJECT-TYPE
            SYNTAX INTEGER
                {up(1),
                 down(2)
                }
            MAX-ACCESS  read-write
            STATUS      current
             DESCRIPTION
                "The current operational state of the ONT XDSL port.
                Options:
                1. up(1)      - indicates up operation.
                2. down(2)    - indicates down operation.
               "
            DEFVAL       { up }
            ::= { hwOntXdslLineEntry 6 }
         hwOntXdslLineOperationStatus  OBJECT-TYPE
              SYNTAX INTEGER
                {activated(1),
                 activating(2),
                 deactivated(3),
                 failed(4)
                }
             MAX-ACCESS  read-only
             STATUS      current
             DESCRIPTION
                "ONT XDSL port status.
                 Options:
     1. activated(1)      - indicates up status
     2. activating(2)     - indicates that the port is being activated
                 3. deactivated(3)    - indicates down status
                 4. failed(4)         - indicates that port failure
                "
             ::= { hwOntXdslLineEntry 7 }
        hwOntXdslLineBandPlan  OBJECT-TYPE
            SYNTAX      HwXdslBandPlan
            MAX-ACCESS  read-only
            STATUS      current
            DESCRIPTION
                "Band contains a series of subcarriers.
                 The first octet is the number of bands. Other octets describe the info of
                 each band.
                 Each band info is a pair of values occupying 4 octets with the
               following structure:
               First octets        - serial number of band
               Second octets       - Direction of band
               Third fourth octets - Start index of band
               Fifth sixth octets  - End index of band
                 Huawei defined.
                "
            ::= { hwOntXdslLineEntry 8 }
        hwOntXdslLineStatusAttainableRateDs  OBJECT-TYPE
            SYNTAX      Unsigned32
            UNITS       "bits/second"
            MAX-ACCESS  read-only
            STATUS      current
            DESCRIPTION
                "Maximum Attainable Data Rate Downstream.
                 The maximum downstream net data rate currently attainable by
                 the xTU-C transmitter and the xTU-R receiver, coded in bit/s.
                 The invalid value is 4294967295. If data on the port is invalid
                 or no data is generated on the port because the port has not
                 been activated, the invalid value will be returned.
                 Unit: bits/second
                "
            REFERENCE    "ITU-T G.997.1, paragraph 7.5.1.12"
            ::= { hwOntXdslLineEntry 9 }
        hwOntXdslLineStatusAttainableRateUs  OBJECT-TYPE
            SYNTAX      Unsigned32
            UNITS       "bits/second"
            MAX-ACCESS  read-only
            STATUS      current
            DESCRIPTION
                "Maximum Attainable Data Rate Upstream.
                 The maximum upstream net data rate currently attainable by the
                 xTU-R transmitter and the xTU-C receiver, coded in bit/s.
                 The invalid value is 4294967295. If data on the port is invalid
                 or no data is generated on the port because the port has not
                 been activated, the invalid value will be returned.
                 Unit: bits/second
                "
            REFERENCE    "ITU-T G.997.1, paragraph 7.5.1.13"
            ::= { hwOntXdslLineEntry 10 }
        hwOntXdslLineStatusXtuTransSys  OBJECT-TYPE
            SYNTAX      Unsigned32
            MAX-ACCESS  read-only
            STATUS      current
            DESCRIPTION
                "The xTU Transmission System (XTS) in use.
                 This parameter may be derived from the handshaking procedures
                 defined in Recommendation G.994.1. The invalid value is 4294967295.
                 If data on the port is invalid or no data is generated on the
                 port because the port has not been activated, the invalid value
                 will be returned. One of XDSL line
                 transmission modes:
                        ANSI_T1413(1)
                        ETSI_DTS_TM06006(2)
                        G9921_POTS_NONOVERLAP(3)
                        G9921_POTS_OVERLAP(4)
                        G9921_ISDN_NONOVERLAP(5)
                        G9921_ISDN_OVERLAP(6)
                        G9921_TCMISDN_NONOVERLAP(7)
                        G9921_TCMISDN_OVERLAP(8)
                        G9922_POTS_NONOVERLAP(9)
                        G9922_POTS_OVERLAP(10)
                        G9922_TCMISDN_NONOVERLAP(11)
                        G9922_TCMISDN_OVERLAP(12)
                        G9921_TCMISDN_SYMMETRIC(13)
                        G9923_POTS_NONOVERLAP(19)
                        G9923_POTS_OVERLAP(20)
                        G9923_ISDN_NONOVERLAP(21)
                        G9923_ISDN_OVERLAP(22)
                        G9924_POTS_NONOVERLAP(25)
                        G9924_POTS_OVERLAP(26)
                        G9923_ANNEXI_ALLDIGI_NONOVERLAP(29)
                        G9923_ANNEXI_ALLDIGI_OVERLAP(30)
                        G9923_ANNEXJ_ALLDIGI_NONOVERLAP(31)
                        G9923_ANNEXJ_ALLDIGI_OVERLAP(32)
                        G9924_ANNEXI_ALLDIGI_NONOVERLAP(33)
                        G9924_ANNEXI_ALLDIGI_OVERLAP(34)
                        G9923_ANNEXL_POTS_NONOVERLAP_MODE1_WIDEUS(35)
                        G9923_ANNEXL_POTS_NONOVERLAP_MODE2_NARROWUS(36)
                        G9923_ANNEXL_POTS_OVERLAP_MODE3_WIDEUS(37)
                        G9923_ANNEXL_POTS_NONOVERLAP_MODE4_NARROWUS(38)
                        G9923_ANNEXM_POTS_NONOVERLAP(39)
                        G9923_ANNEXM_POTS_OVERLAP(40)
                        G9925_POTS_NONOVERLAP(41)
                        G9925_POTS_OVERLAP(42)
                        G9925_ISDN_NONOVERLAP(43)
                        G9925_ISDN_OVERLAP(44)
                        G9925_ANNEXI_ALLDIGI_NONOVERLAP(47)
                        G9925_ANNEXI_ALLDIGI_OVERLAP(48)
                        G9925_ANNEXJ_ALLDIGI_NONOVERLAP(49)
                        G9925_ANNEXJ_ALLDIGI_OVERLAP(50)
                        G9925_ANNEXM_POTS_NONOVERLAP(51)
                        G9925_ANNEXM_POTS_OVERLAP(52)
                        G9931(65)
                        G9932_ANNEXA_POTS(73)
                        G9932_ANNEXA_ISDN(74)
                        G9932_ANNEXB_POTS(75)
                        G9932_ANNEXB_ISDN(76)
                        G9932_ANNEXC_POTS(77)
                        G9932_ANNEXC_ISDN(78)
                        G9935(79)
                        G9935_FRIENDLY_DS(80)
                        G9935_FULL_FRIENDLY(81)
               "
            ::= { hwOntXdslLineEntry 11 }
        hwOntXdslLineStatusPwrMngState  OBJECT-TYPE
            SYNTAX      HwXdslPowerMngState
            MAX-ACCESS  read-only
            STATUS      current
            DESCRIPTION
                "The current power management state.
                 Options:
                 1. L0 - Synchronized and full transmission
                 2. L1 - Low Power with reduced net data rate
                 3. L2 - Low Power with reduced net data rate
                 4. L3 - No power
                 The various possible values are:l0(0), l1(1), l2(2), l3(3).
                "
            REFERENCE    "ITU-T G.997.1, paragraph 7.5.1.2"
               ::= { hwOntXdslLineEntry 12 }
         hwOntXdslLineStatusInitResult  OBJECT-TYPE
            SYNTAX      HwXdslInitResult
            MAX-ACCESS  read-only
            STATUS      current
            DESCRIPTION
                "Indicates the result of the last full initialization performed
                 on the line.
                 Options:
                 1. noFail (0)            - Successful initialization
                 2. configError (1)       - Configuration failure
                 3. configNotFeasible (2) - Configuration details not supported
                 4. commFail (3)          - Communication failure
                 5. noPeerXtu (4)         - Peer xTU not detected
                 6. otherCause (5)        - Other initialization failure reason
                 7. ginpNotSelected(6)    - G.998.4 Retransmission mode was not selected
                                            while RTX_MODE = FORCED or with RTX_MODE = RTX_TESTMODE
                 8. invalidValue(-1)      - Invalid value
                "
            REFERENCE    "ITU-T G.997.1, paragraph 7.5.1.3"
            ::= { hwOntXdslLineEntry 13 }
        hwOntXdslLineStatusActAtpDs  OBJECT-TYPE
            SYNTAX      Integer32
            UNITS       "0.1 dB"
            MAX-ACCESS  read-only
            STATUS      current
            DESCRIPTION
                "Actual Aggregate Transmit Power Downstream.  The total amount
                 of transmit power delivered by the xTU-C at the U-C reference
                 point, at the instant of measurement.  It ranges from -310 to
                 310 units of 0.1 dB (Physical values are -31 to 31 dBm).  A
                 value of 0x7FFFFFFF(2147483647) indicates the measurement is out of range to
                 be represented. The invalid value is 2147483647. If data on the
                 port is invalid or no data is generated on the port because
                 the port has not been activated, the invalid value will be returned.
                 Unit: 0.1 dB
                "
            REFERENCE    "ITU-T G.997.1, paragraph 7.5.1.16"
            ::= { hwOntXdslLineEntry 14 }
        hwOntXdslLineStatusActAtpUs  OBJECT-TYPE
            SYNTAX      Integer32
            UNITS       "0.1 dB"
            MAX-ACCESS  read-only
            STATUS      current
            DESCRIPTION
                "Actual Aggregate Transmit Power Upstream.  The total amount of
                 transmit power delivered by the xTU-R at the U-R
                 reference point, at the instant of measurement.  It ranges
                 from -310 to 310 units of 0.1 dB (Physical values are -31
                 to 31 dBm).  A value of 0x7FFFFFFF(2147483647) indicates the measurement
                 is out of range to be represented.
                 Unit: 0.1 dB
                "
            REFERENCE    "ITU-T G.997.1, paragraph 7.5.1.17"
            ::= { hwOntXdslLineEntry 15 }
        hwOntXdslLineCurrentVdsl2Profile  OBJECT-TYPE
            SYNTAX      HwXdslSubProfiles
            MAX-ACCESS  read-only
            STATUS      current
            DESCRIPTION
                "This configuration parameter contains the G.993.2 profiles
                 to be allowed by the near-end xTU on this line.
                "
            REFERENCE    "ITU-T G.997.1, paragraph 7.3.1.1.11"
            ::= { hwOntXdslLineEntry 16 }
        hwOntXdslLineStatusLnAttenDs  OBJECT-TYPE
            SYNTAX      Unsigned32
            UNITS       "0.1 dB"
            MAX-ACCESS  read-only
            STATUS      current
            DESCRIPTION
                "The measured difference in the total power transmitted by the
                 xTU-C and the total power received by the xTU-R over all
                 sub-carriers during diagnostics mode and initialization. It
                 ranges from 0 to 1270 units of 0.1 dB (Physical values
                 are 0 to 127 dB). A value of all 1's indicates the line
                 attenuation is out of range to be represented. The invalid value
                 is 4294967295. If data on the port is invalid or no data is
                 generated on the port because the port has not been activated,
                 the invalid value will be returned.
                 Unit: 0.1 dB
                "
            REFERENCE    "ITU-T G.997.1, paragraph 7.5.1.6"
            ::= { hwOntXdslLineEntry 17 }
        hwOntXdslLineStatusLnAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during diagnostics mode and initialization.
                 It ranges from 0 to 1270 units of 0.1 dB (Physical values are
                 0 to 127 dB).  A value of all 1's indicates the line
                 attenuation is out of range to be represented. The invalid value
                 is 4294967295. If data on the port is invalid or no data is
                 generated on the port because the port has not been activated,
                 the invalid value will be returned.
                 Unit: 0.1 dB
                "
            REFERENCE    "ITU-T G.997.1, paragraph 7.5.1.7"
            ::= { hwOntXdslLineEntry 18 }
        hwOntXdslLineStatusSigAttenDs  OBJECT-TYPE
            SYNTAX      Unsigned32
            UNITS       "0.1 dB"
            MAX-ACCESS  read-only
            STATUS      current
            DESCRIPTION
                "The measured difference in the total power transmitted by the
                 xTU-C and the total power received by the xTU-R over all sub-
                 carriers during Showtime.  It ranges from 0 to 1270 units of
                 0.1 dB (Physical values are 0 to 127 dB).  A value of all
                 1's indicates the line attenuation is out of range to be
                 represented. The invalid value is 4294967295. If data on the
                 port is invalid or no data is generated on the port because
                 the port has not been activated, the invalid value will be returned.
                 Unit: 0.1 dB
                "
            REFERENCE    "ITU-T G.997.1, paragraph 7.5.1.8"
            ::= { hwOntXdslLineEntry 19 }
        hwOntXdslLineStatusSigAttenUs  OBJECT-TYPE
            SYNTAX      Unsigned32
            UNITS       "0.1 dB"
            MAX-ACCESS  read-only
            STATUS      current
            DESCRIPTION
                "The measured difference in the total power transmitted by the
                 xTU-R and the total power received by the xTU-C over all sub-
                 carriers during Showtime.  It ranges from 0 to 1270 units of
                 0.1 dB (Physical values are 0 to 127 dB).  A value of all
                 1's indicates the line attenuation is out of range to be
                 represented. The invalid value is 4294967295. If data on the
                 port is invalid or no data is generated on the port because
                 the port has not been activated, the invalid value will be returned.
                 Unit: 0.1 dB
                "
            REFERENCE    "ITU-T G.997.1, paragraph 7.5.1.9"
            ::= { hwOntXdslLineEntry 20 }
        hwOntXdslLineStatusSnrMarginDs  OBJECT-TYPE
            SYNTAX      Integer32
            UNITS       "0.1 dB"
            MAX-ACCESS  read-only
            STATUS      current
            DESCRIPTION
                "Downstream SNR Margin is the maximum increase in dB of the
                 noise power received at the xTU-R, such that the BER
                 requirements are met for all downstream bearer channels.  It
                 ranges from -640 to 630 units of 0.1 dB (Physical values are
                 -64 to 63 dB).  A value of 0x7FFFFFFF(2147483647) indicates the line
                 attenuation is out of range to be represented. The invalid
                 value is 2147483647. If data on the port is invalid or no data
                 is generated on the port because the port has not been activated,
                 the invalid value will be returned.
                 Unit: 0.1 dB
                "
            REFERENCE    "ITU-T G.997.1, paragraph 7.5.1.10"
            ::= { hwOntXdslLineEntry 21 }
        hwOntXdslLineStatusSnrMarginUs  OBJECT-TYPE
            SYNTAX      Integer32
            UNITS       "0.1 dB"
            MAX-ACCESS  read-only
            STATUS      current
            DESCRIPTION
                "Upstream SNR Margin is the maximum increase in dB of the noise
                 power received at the xTU-C, such that the BER requirements
                 are met for all downstream bearer channels.  It ranges from
                 -640 to 630 units of 0.1 dB (Physical values are -64 to
                 63 dB).  A value of 0x7FFFFFFF(2147483647) indicates the line attenuation
                 is out of range to be represented. The invalid value is 2147483647.
                 If data on the port is invalid or no data is generated on
                 the port because the port has not been activated, the
                 invalid value will be returned.
                 Unit: 0.1 dB
                "
            REFERENCE    "ITU-T G.997.1, paragraph 7.5.1.11"
            ::= { hwOntXdslLineEntry 22 }
        --       hwXdslChannelStatusTable
        hwXdslChannelStatusTable  OBJECT-TYPE
            SYNTAX      SEQUENCE  OF  HwXdslChannelStatusEntry
            MAX-ACCESS  not-accessible
            STATUS      current
            DESCRIPTION
                "The table hwXdslChannelStatusTable contains status
                 parameters of XDSL channel.
                 The indexes of this table are ifIndex and hwXdslChStatusUnit.
                "
            ::= { hwXdslStatus 1 }

        hwXdslChannelStatusEntry  OBJECT-TYPE
            SYNTAX      HwXdslChannelStatusEntry
            MAX-ACCESS  not-accessible
            STATUS      current
            DESCRIPTION
                "The table hwXdslChannelStatusTable contains status
                 parameters of XDSL channel.
                 The indexes of this entry are ifIndex and hwXdslChStatusUnit.
                "
            INDEX  { ifIndex, hwXdslChStatusUnit }
            ::= { hwXdslChannelStatusTable 1 }

        HwXdslChannelStatusEntry  ::=
           SEQUENCE {
              hwXdslChStatusUnit                HwXdslUnit,
              hwXdslChStatusChannelNum          Unsigned32,
              hwXdslChStatusActDataRate         Unsigned32,
              hwXdslChStatusPrevDataRate        Unsigned32,
              hwXdslChStatusActDelay            Unsigned32,
              hwXdslChStatusAtmStatus           HwXdslChAtmStatus,
              hwXdslChStatusPtmStatus           HwXdslChPtmStatus,
              hwXdslChStatusINP                 Unsigned32,
              hwXdslChStatusRSRedundancy        Unsigned32,
              hwXdslChStatusRSSymbols           Unsigned32,
              hwXdslChStatusInterDepth          Unsigned32,
              hwXdslChStatusSymbolLength        Unsigned32,
              hwXdslChStatusRSSize              Unsigned32,
              hwXdslChStatusInterBlockLength    Unsigned32,
              hwXdslChStatusLPATH        Unsigned32,
              hwXdslChStatusPhyRrrcBits        Unsigned32,
              hwXdslChStatusPhyRtxQueue        Unsigned32,
              hwXdslChStatusActNetDataRate      Unsigned32,
              hwXdslChStatusActINPAgainstREIN   Unsigned32,
              hwXdslChStatusUnlimitedVersionEtru Unsigned32,
              hwXdslChStatusActEftr           Unsigned32,
              hwXdslChStatusInpReportingMode  Unsigned32
           }

        hwXdslChStatusUnit  OBJECT-TYPE
            SYNTAX      HwXdslUnit
            MAX-ACCESS  not-accessible
            STATUS      current
            DESCRIPTION
                "The termination unit xTU-C(1) or xTU-R(2)."
            ::= { hwXdslChannelStatusEntry 1 }

        hwXdslChStatusChannelNum  OBJECT-TYPE
            SYNTAX      Unsigned32
            MAX-ACCESS  read-only
            STATUS      current
            DESCRIPTION
                "Provides the bearer channel number associated with this
                 row (i.e., the channel ifIndex).
                 This enables determining the channel configuration profile
                 and the channel thresholds profile applicable for this
                 bearer channel.
                "
            ::= { hwXdslChannelStatusEntry 2 }

        hwXdslChStatusActDataRate  OBJECT-TYPE
            SYNTAX      Unsigned32
            UNITS       "bits/second"
            MAX-ACCESS  read-only
            STATUS      current
            DESCRIPTION
                "If retransmission is not used in a given transmit direction,
                 this parameter reports the actual net data rate at which the
                 bearer channel is operating in L0 power management state, and
                 in L1 or L2 states, the parameter contains the net data rate
                 in the previous L0 state.
                 If retransmission is used in a given transmit direction,
                 this parameter reports the Expected Throughput(ETR) at which the
                 bearer channel is operating in L0 power management state, and in
                 L1 or L2 states, the parameter contains the Expected Throughput(ETR)
                 in the previous L0 state.
                 The data rate is coded in steps of 1000 bit/s.
                 The invalid value is 4294967295. If data on the port is invalid
                 or no data is generated on the port because the port has not been
                 activated, the invalid value will be returned.
                 Unit: bits/second
                "
            REFERENCE    "ITU-T G.997.1, paragraph 7.5.2.1"
            ::= { hwXdslChannelStatusEntry 3 }

        hwXdslChStatusPrevDataRate  OBJECT-TYPE
            SYNTAX      Unsigned32
            UNITS       "bits/second"
            MAX-ACCESS  read-only
            STATUS      current
            DESCRIPTION
                "If retransmission is not used in a given transmit direction, this
                 parameter reports the previous net data rate the bearer channel
                 was operating at just before the latest net data rate change event
                 occurred, excluding all transitions between L0 state and L1 or L2
                 states.
                 If retransmission is used in a given transmit direction, this
                 parameter reports the previous Expected Throughput(ETR)
                 (as defined in G.998.4) the bearer channel was operating at just
                 before the latest ETR change event occurred, excluding all
                 transitions between L0 state and L1 or L2 states.
                 The data rate is coded in steps of 1000 bit/s.
                 The invalid value is 4294967295. If data on the port is invalid
                 or no data is generated on the port because the port has not
                 been activated, the invalid value will be returned.
                 Unit: bits/second
                "
            REFERENCE    "ITU-T G.997.1, paragraph 7.5.2.2"
            ::= { hwXdslChannelStatusEntry 4 }

        hwXdslChStatusActDelay  OBJECT-TYPE
            SYNTAX      Unsigned32(0..8176)
            UNITS       "milliseconds"
            MAX-ACCESS  read-only
            STATUS      current
            DESCRIPTION
                "If retransmission is not used in a given transmit direction, this
                 parameter is the actual one-way interleaving delay introduced by
                 the PMS-TC excluding delay in L1 and L2 state. In L1 and L2 state,
                 the parameter contains the interleaving delay in the previous L0
                 state.
                 If retransmission is used in a given transmit direction, this
                 parameter specifies the actual value of the time-independent
                 component of the delay due to retransmission only.
                 It is coded in ms (rounded to the nearest ms).
                 The invalid value is 4294967295. If data on the port is invalid
                 or no data is generated on the port because the port has not
                 been activated, the invalid value will be returned.
                 Unit: milliseconds
                "
            REFERENCE    "ITU-T G.997.1, paragraph 7.5.2.3"
            ::= { hwXdslChannelStatusEntry 5 }

        hwXdslChStatusAtmStatus  OBJECT-TYPE
            SYNTAX      HwXdslChAtmStatus
            MAX-ACCESS  read-only
            STATUS      current
            DESCRIPTION
                "Indicates current state (existing failures) of the XDSL
                 channel in case its Data Path is ATM.  This is a bit-map of
                 possible conditions.
                 Options:
                 1. noDefect(0)              - This bit position positively
                                               reports that no defect or failure
                                               exist
                 2. noCellDelineation(1)     - The link was successfully
                                               initialized but cell delineation
                                               was never acquired on the
                                               associated ATM data path
                 3. lossOfCellDelineation(2) - Loss of cell delineation on the
                                               associated ATM data path
                 In case the channel is not of ATM Data Path, the object is set
                 to '0'.
                "
            REFERENCE    "ITU-T G.997.1, paragraph 7.1.4"
            ::= { hwXdslChannelStatusEntry 6 }

        hwXdslChStatusPtmStatus  OBJECT-TYPE
            SYNTAX      HwXdslChPtmStatus
            MAX-ACCESS  read-only
            STATUS      current
            DESCRIPTION
                "Indicates current state (existing failures) of the XDSL
                 channel in case its Data Path is PTM.  This is a bit-map of
                 possible conditions.
                 Options:
                 1. noFailure(0)   - No failure
                 2. outOfSync (1)  - Out of synchronization
                 In case the channel is not of PTM Data Path the object is set
                 to '0'.
                "
            REFERENCE    "ITU-T G.997.1, paragraph 7.1.5"
            ::= { hwXdslChannelStatusEntry 7 }

        hwXdslChStatusINP  OBJECT-TYPE
            SYNTAX      Unsigned32(0..254 | 4294967295)
            UNITS       "0.1 DMT symbol"
            MAX-ACCESS  read-only
            STATUS      current
            DESCRIPTION
                "If retransmission is not used in a given transmit direction, this
                 parameter reports the actual impulse noise protection (INP) on the
                 bearer channel in the L0 state. In the L1 or L2 state, the parameter
                 contains the INP in the previous L0 state.
                 If retransmission is used in a given transmit direction, this parameter
                 reports the actual impulse noise protection (INP) against SHINE on
                 the bearer channel in the L0 state. In the L2 state, the parameter
                 contains the INP in the previous L0 state.
                 The value is coded in fractions of DMT symbols with a granularity of 0.1 symbols.
                 The invalid value is 4294967295. If data on the port is invalid or no
                 data is generated on the port because the port has not been activated,
                 the invalid value will be returned.
                 Unit: 0.1 DMT symbol
                "
            REFERENCE    "ITU-T G.997.1(200604), paragraph 7.5.2.4"
            ::= { hwXdslChannelStatusEntry 8 }

        hwXdslChStatusRSRedundancy  OBJECT-TYPE
            SYNTAX      Unsigned32(0..16)
            UNITS       "byte"
            MAX-ACCESS  read-only
            STATUS      current
            DESCRIPTION
                "The actual number of Reed-Solomon redundancy
                 bytes per codeword used in the latency path
                 in which the bearer channel is transported.
                 The value is coded in bytes.
                 The value 0 indicates no Reed-Solomon coding.
                 The invalid value is 4294967295. If data on the port is invalid
                 or no data is generated on the port because the port has not
                 been activated, the invalid value will be returned.
                 Unit: byte
                "
            REFERENCE    "ITU-T G.997.1(200604), paragraph 7.5.2.6.2"
            ::= { hwXdslChannelStatusEntry 9 }

        hwXdslChStatusRSSymbols  OBJECT-TYPE
            SYNTAX      Unsigned32
            UNITS       "0.01 DMT symbol"
            MAX-ACCESS  read-only
            STATUS      current
            DESCRIPTION
                "The DMT Symbol number per codeword used in
                 the latency path in which the bearer channel
                 is transported. The invalid value is 4294967295.
                 If data on the port is invalid or no data is generated
                 on the port because the port has not been activated,
                 the invalid value will be returned.
                 Unit: 0.01 DMT symbol
                "
            REFERENCE    "ITU-T G.997.1, paragraph 7.5.2.3"
            ::= { hwXdslChannelStatusEntry 10 }

        hwXdslChStatusInterDepth  OBJECT-TYPE
            SYNTAX      Unsigned32(1..4096)
            MAX-ACCESS  read-only
            STATUS      current
            DESCRIPTION
                "The actual Reed-Solomon codeword size used
                 in the latency path in which the bearer channel
                 is transported.
                 The value ranges from 1 to 4096 by step of 1.
                 The value 1 indicates no interleaving. The invalid
                 value is 4294967295. If data on the port is invalid
                 or no data is generated on the port because the port
                 has not been activated, the invalid value will be returned.
                "
            REFERENCE    "ITU-T G.997.1(200604), paragraph 7.5.2.6.4"
            ::= { hwXdslChannelStatusEntry 11 }

        hwXdslChStatusSymbolLength  OBJECT-TYPE
            SYNTAX      Unsigned32(0..65535)
            UNITS       "bit"
            MAX-ACCESS  read-only
            STATUS      current
            DESCRIPTION
                "The actual number of bits per symbol assigned
                 to the latency path in which the bearer channel
                 is transported.
                 This value does not include trellis overhead. The invalid
                 value is 4294967295. If data on the port is invalid or no
                 data is generated on the port because the port has not been
                 activated, the invalid value will be returned.
                 Unit: bit
                "
            REFERENCE    "ITU-T G.997.1(200604), paragraph 7.5.2.6.3"
            ::= { hwXdslChannelStatusEntry 12 }

        hwXdslChStatusRSSize  OBJECT-TYPE
            SYNTAX      Unsigned32(0..255)
            UNITS       "byte"
            MAX-ACCESS  read-only
            STATUS      current
            DESCRIPTION
                "The actual Reed-Solomon codeword size used
                 in the latency path in which the bearer channel
                 is transported. The invalid value is 4294967295.
                 If data on the port is invalid or no data is
                 generated on the port because the port has not
                 been activated, the invalid value will be returned.
                 Unit: byte
                "
            REFERENCE    "ITU-T G.997.1(200604), paragraph 7.5.2.6.1"
            ::= { hwXdslChannelStatusEntry 13 }

        hwXdslChStatusInterBlockLength  OBJECT-TYPE
            SYNTAX      Unsigned32(4..255)
            UNITS       "byte"
            MAX-ACCESS  read-only
            STATUS      current
            DESCRIPTION
                "The actual block length of the interleaver
                 used in the latency path in which the bearer
                 channel is transported. The invalid value is 4294967295.
                 If data on the port is invalid or no data is generated
                 on the port because the port has not been activated,
                 the invalid value will be returned.
                 Unit: byte
                "
            REFERENCE    "ITU-T G.997.1(200604), paragraph 7.5.2.6.5"
            ::= { hwXdslChannelStatusEntry 14 }

        hwXdslChStatusLPATH  OBJECT-TYPE
            SYNTAX      Unsigned32(0..3)
            MAX-ACCESS  read-only
            STATUS      current
            DESCRIPTION
                "The index of the actual
                 latency path in which the bearer is transported.
                 The invalid value is 4294967295. If data on the port
                 is invalid or no data is generated on the port because
                 the port has not been activated, the invalid value
                 will be returned.
                "
            REFERENCE    "ITU-T G.997.1, paragraph 7.5.2.7"
            ::= { hwXdslChannelStatusEntry 15 }

        hwXdslChStatusPhyRrrcBits OBJECT-TYPE
            SYNTAX      Unsigned32
            MAX-ACCESS  read-only
            STATUS      current
            DESCRIPTION
                "The bits in the channel that used to retransmission.
                 The invalid value is 4294967295. If data on the port cannot
                 be queried, data on the port is invalid, or no data is
                 generated on the port because the port has not been
                 activated, the invalid value will be returned.
                "
            ::= { hwXdslChannelStatusEntry 16 }

        hwXdslChStatusPhyRtxQueue OBJECT-TYPE
            SYNTAX      Unsigned32
            MAX-ACCESS  read-only
            STATUS      current
            DESCRIPTION
                "Queues in send buffer used for retransmission.
                 The invalid value is 4294967295. If data on the port
                 cannot be queried, data on the port is invalid, or no
                 data is generated on the port because the port has
                 not been activated, the invalid value will be returned.
                "
            ::= { hwXdslChannelStatusEntry 17 }

        hwXdslChStatusActNetDataRate OBJECT-TYPE
            SYNTAX      Unsigned32
            UNITS       "bits/second"
            MAX-ACCESS  read-only
            STATUS      current
            DESCRIPTION
                "In L0 state, this parameter reports the Net Data Rate at which the bearer channel is operating.
                 In L2 state, this parameter contains the Net Data Rate in the previous L0 state.
                 This parameter is optional if G.998.4 retransmission function is not supported.
                 The data rate is coded in steps of 1000 bit/s. The invalid value is 4294967295.
                 If data on the port cannot be queried, data on the port is invalid,
                 or no data is generated on the port because the port has not been activated,
                 the invalid value will be returned.
                "
            REFERENCE    "ITU-T G.997.1, paragraph 7.5.2.8"
            ::= { hwXdslChannelStatusEntry 18 }

        hwXdslChStatusActINPAgainstREIN OBJECT-TYPE
            SYNTAX      Unsigned32
            MAX-ACCESS  read-only
            STATUS      current
            DESCRIPTION
                "If retransmission is used in a given transmit direction,
                 this parameter reports the actual impulse noise protection (INP)
                 against REIN (under specific conditions detailed in G.998.4)
                 on the bearer channel in the L0 state. In the L2 state, the
                 parameter contains the INP in the previous L0 state. The value
                 is coded in fractions of DMT symbols with a granularity of 0.1 symbols.
                 The invalid value is 4294967295. If data on the port cannot be
                 queried, data on the port is invalid, or no data is generated
                 on the port because the port has not been activated, the invalid
                 value will be returned.
                "
            REFERENCE    "ITU-T G.997.1, paragraph 7.5.2.9"
            ::= { hwXdslChannelStatusEntry 19 }

        hwXdslChStatusUnlimitedVersionEtru OBJECT-TYPE
            SYNTAX      Unsigned32
            UNITS       "bits/second"
            MAX-ACCESS  read-only
            STATUS      current
            DESCRIPTION
                "The unlimited version of expected throughput in kbit/s:(1 - RTxOH) * NDR.
                 This value is specified in G.998.4 (G.INP)."
            ::= { hwXdslChannelStatusEntry 20 }

        hwXdslChStatusActEftr  OBJECT-TYPE
            SYNTAX      Unsigned32
            UNITS       "bits/second"
            MAX-ACCESS  read-only
            STATUS      current
            DESCRIPTION
                "The actual error-free throughput (EFTR).
                 The EFTR shall be measured in Showtime by the receiver.
                 The EFTR shall be calculated every second.
                 The EFTR is not a test parameter directly reported to the ME, but is
                 indirectly used in the definition of related parameter EFTRmin and
                 leftr defects.
                 The invalid value is 4294967295. If data on the port is invalid
                 or no data is generated on the port because the port has not been
                 activated, the invalid value will be returned.
                 Unit: bits/second
                "
            REFERENCE    "ITU-T G.998.4, paragraph 11.2.2"
            ::= { hwXdslChannelStatusEntry 21 }

        hwXdslChStatusInpReportingMode OBJECT-TYPE
            SYNTAX      Unsigned32
            MAX-ACCESS  read-only
            STATUS      current
            DESCRIPTION
                "This parameter reports the method used to compute the ACTINP.
                 If set to 0, the ACTINP is computed according to the INP_no_erasure formula (see clause 9.6 of [ITU-T G.993.2]).
                 If set to 1, the ACTINP is the value estimated by the xTU receiver.
                "
            ::= { hwXdslChannelStatusEntry 22 }

        --       hwXdslPrivSCStatusTable

        hwXdslPrivSCStatusTable  OBJECT-TYPE
            SYNTAX      SEQUENCE  OF  HwXdslPrivSCStatusEntry
            MAX-ACCESS  not-accessible
            STATUS      current
            DESCRIPTION
                "The table hwXdslPrivSCStatusTable contains status parameters
                 of XDSL sub-carriers.
                 The indexes of this table are ifIndex and hwXdslPrivSCStatusDirection.
                "
            ::= { hwXdslStatus 2 }

        hwXdslPrivSCStatusEntry  OBJECT-TYPE
            SYNTAX      HwXdslPrivSCStatusEntry
            MAX-ACCESS  not-accessible
            STATUS      current
            DESCRIPTION
                "The table hwXdslPrivSCStatusTable contains status parameters
                 of XDSL sub-carriers.
                 The indexes of this entry are ifIndex and hwXdslPrivSCStatusDirection.
                "
            INDEX  { ifIndex, hwXdslPrivSCStatusDirection }
            ::= { hwXdslPrivSCStatusTable 1 }

        HwXdslPrivSCStatusEntry  ::=
            SEQUENCE {
              hwXdslPrivSCStatusDirection         HwXdslDirection,
              hwXdslPrivSCStatusMtime             Unsigned32,
              hwXdslPrivSCStatusSnr               OCTET STRING,
              hwXdslPrivSCStatusBitsAlloc         OCTET STRING,
              hwXdslPrivSCStatusGainAlloc         OCTET STRING
            }

        hwXdslPrivSCStatusDirection  OBJECT-TYPE
            SYNTAX      HwXdslDirection
            MAX-ACCESS  not-accessible
            STATUS      current
            DESCRIPTION
                "The direction of the sub-carrier either
                 upstream or downstream.
                "
            ::= { hwXdslPrivSCStatusEntry 1 }

        hwXdslPrivSCStatusMtime  OBJECT-TYPE
            SYNTAX      Unsigned32
            UNITS       "symbols"
            MAX-ACCESS  read-only
            STATUS      current
            DESCRIPTION
                "SNR Measurement Time.  The number of symbols used to
                 measure the SNR values on the respective transmission
                 direction.  It should correspond to the value specified in the
                 recommendation (e.g., the number of symbols in 1 second
                 time interval for G.992.3).  This parameter corresponds to
                 1 second in loop diagnostic procedure and should be updated
                 otherwise.
                 Unit: symbols
                "
            REFERENCE  "ITU-T G.997.1, paragraph 7.5.1.20.1 (SNRMTds)
                        and paragraph 7.5.1.20.3 (SNRMTus)"
            ::= { hwXdslPrivSCStatusEntry 2 }

        hwXdslPrivSCStatusSnr  OBJECT-TYPE
            SYNTAX      OCTET STRING  (SIZE(0..4096))
            MAX-ACCESS  read-only
            STATUS      current
            DESCRIPTION
                "The SNR Margin per sub-carrier, expressing the ratio between
                 the received signal power and received noise power per
                 subscriber.  It is an array of 4096 bytes, designed for
                 supporting up to 4096 sub-carriers.
                 The number of utilized octets on downstream direction depends
                 on NSCds, and on upstream direction it depends on NSCus.  This
                 value is referred here as NSC.
                 Byte i (0 &lt;= i &lt; NSC) is set to a value in the range 0 to
                 254 to indicate that the respective downstream or upstream sub-
                 carrier i has SNR of: (-32 + hwXdslSubcarrierSnr(i)/2) in dB
                 (i.e., -32 to 95dB).
                 The special value 255 means that no measurement could be done
                 for the subcarrier because it is out of the PSD mask passband
                 or that the noise PSD is out of range to be represented.
                 Each value in this array is 8 bits wide.
                "
            REFERENCE    "ITU-T G.997.1, paragraph 7.5.1.20.2 (SNRpsds)
                          and paragraph 7.5.1.20.4 (SNRpsus)"
            ::= { hwXdslPrivSCStatusEntry 3 }

        hwXdslPrivSCStatusBitsAlloc  OBJECT-TYPE
            SYNTAX      OCTET STRING  (SIZE(0..2048))
            UNITS       "bits"
            MAX-ACCESS  read-only
            STATUS      current
            DESCRIPTION
                "The bits allocation per sub-carrier.  An array of 2048 bytes,
                 designed for supporting up to 4096 sub-carriers.
                 The number of utilized nibbles on downstream direction depends
                 on NSCds, and on upstream direction it depends on NSCus.  This
                 value is referred here as NSC.
                 Nibble i (0 &lt;= i &lt; NSC) is set to a value in the range 0
                 to 15 to indicate that the respective downstream or upstream
                 sub-carrier i has the same amount of bits allocation.
                 Unit: bits
                "
            REFERENCE    "ITU-T G.997.1, paragraph 7.5.1.21.1 (BITSpsds)
                         and paragraph 7.5.1.21.2 (BITSpsus)"
             ::= { hwXdslPrivSCStatusEntry 4 }

        hwXdslPrivSCStatusGainAlloc  OBJECT-TYPE
            SYNTAX      OCTET STRING  (SIZE(0..8192))
            MAX-ACCESS  read-only
            STATUS      current
            DESCRIPTION
                "The gain allocation per sub-carrier.  An array of 8192 bytes,
                 designed for supporting up to 4096 sub-carriers.
                 The number of utilized octets on downstream direction depends
                 on NSCds, and on upstream direction it depends on NSCus.  This
                 value is referred here as NSC.
                 Value i (0 &lt;= i &lt; NSC) is in the range 0 to 4093 to indicate
                 that the respective downstream or upstream sub-carrier i has the
                 same amount of gain value.
                 The gain value is represented as a multiple of 1/512 on
                 linear scale.  Each value in this array is 16 bits wide and is
                 stored in big endian format.
                "
            REFERENCE    "ITU-T G.997.1, paragraph 7.5.1.21.3 (GAINSpsds)
                          and paragraph 7.5.1.21.4 (GAINSpsus)"
            ::= { hwXdslPrivSCStatusEntry 5 }

--               Scalars that relate to the hwXdslScalar.
        hwXdslScalarSCMaxInterfaces  OBJECT-TYPE
            SYNTAX      Unsigned32
            MAX-ACCESS  read-only
            STATUS      current
            DESCRIPTION
                "This value determines the maximum number of
                 interfaces supported by hwXdslSCStatusTable,
                 hwXdslSCStatusBandTable, and hwXdslSCStatusSegmentTable.
                "
            ::= { hwXdslScalarSC 1 }

        hwXdslScalarSCAvailInterfaces  OBJECT-TYPE
            SYNTAX      Unsigned32
            MAX-ACCESS  read-only
            STATUS      current
            DESCRIPTION
                "This value determines the currently available number of
                 interfaces listed in hwXdslSCStatusTable,
                 hwXdslSCStatusBandTable, and hwXdslSCStatusSegmentTable.
                "
            ::= { hwXdslScalarSC 2 }

        --       hwXdslSCStatusTable

        hwXdslSCStatusTable  OBJECT-TYPE
            SYNTAX      SEQUENCE  OF  HwXdslSCStatusEntry
            MAX-ACCESS  not-accessible
            STATUS      current
            DESCRIPTION
                "The table hwXdslSCStatusTable contains
                 sub-carrier status parameters for VDSL2/ADSL/ADSL2/ADSL2+
     and FAST that DO NOT refer to specific sub-carriers.
                 In addition, the table contains parameters
                 that provide information about the size of parameters
                 in hwXdslSCStatusSegmentTable.  This table contains live data
                 from equipment. The indexes of this table are ifIndex and
                 hwXdslSCStatusDirection.
                "
            ::= { hwXdslStatus 3 }

        hwXdslSCStatusEntry  OBJECT-TYPE
            SYNTAX      HwXdslSCStatusEntry
            MAX-ACCESS  not-accessible
            STATUS      current
            DESCRIPTION
                "The table hwXdslSCStatusTable contains
                 sub-carrier status parameters for VDSL2/ADSL/ADSL2/ADSL2+
     and FAST that DO NOT refer to specific sub-carriers.
                 In addition, the table contains parameters
                 that provide information about the size of parameters
                 in hwXdslSCStatusSegmentTable.  This table contains live data
                 from equipment. The indexes of this entry are ifIndex and
                 hwXdslSCStatusDirection.
                "
            INDEX  { ifIndex, hwXdslSCStatusDirection }
            ::= { hwXdslSCStatusTable 1 }

        HwXdslSCStatusEntry  ::=
           SEQUENCE {
              hwXdslSCStatusDirection         HwXdslDirection,
              hwXdslSCStatusLinScale          Unsigned32,
              hwXdslSCStatusLinScGroupSize    Unsigned32,
              hwXdslSCStatusLogMt             Unsigned32,
              hwXdslSCStatusLogScGroupSize    Unsigned32,
              hwXdslSCStatusQlnMt             Unsigned32,
              hwXdslSCStatusQlnScGroupSize    Unsigned32,
              hwXdslSCStatusMtime             Unsigned32,
              hwXdslSCStatusSnrScGroupSize    Unsigned32,
              hwXdslSCStatusAttainableRate    Unsigned32,
              hwXdslSCStatusActAtp            Integer32,
              hwXdslSCStatusRowStatus         RowStatus,
              hwXdslSCStatusProfile        HwXdslProfiles,
              hwXdslSCStatusClassmask    HwXdslPSDClassMask
           }

        hwXdslSCStatusDirection  OBJECT-TYPE
            SYNTAX      HwXdslDirection
            MAX-ACCESS  not-accessible
            STATUS      current
            DESCRIPTION
                "The direction of the sub-carrier either
                 upstream or downstream"
            ::= { hwXdslSCStatusEntry 1 }

        hwXdslSCStatusLinScale  OBJECT-TYPE
            SYNTAX      Unsigned32
            MAX-ACCESS  read-only
            STATUS      current
            DESCRIPTION
                "The scale factor to be applied to the H(f) linear
                 representation values for the respective transmission direction.
                 This parameter is only available after a loop diagnostic
                 procedure.
                "
            REFERENCE  "ITU-T G.997.1, paragraph #7.5.1.26.1 (HLINSCds)
                        and paragraph #7.5.1.26.7 (HLINSCus)"
            ::= { hwXdslSCStatusEntry 2 }

        hwXdslSCStatusLinScGroupSize OBJECT-TYPE
            SYNTAX      Unsigned32(1 | 2 | 4 | 8 | 16)
            MAX-ACCESS  read-only
            STATUS      current
            DESCRIPTION
                "Number of sub-carriers per group used to report the H(f)
                 linear representation values for the respective transmission
                 direction. The valid values are 1, 2, 4, 8 and 16. For ADSL, this
                 parameter is equal to one and, for XDSL, it is equal to the
                 size of a sub-carrier group used to compute these parameters.
                 This parameter is only available after a loop diagnostic
                 procedure.
                "
            REFERENCE  "ITU-T G.997.1, paragraph #7.5.1.26.2 (HLINGds)
                        and paragraph #7.5.1.26.8 (HLINGus)"
            ::= { hwXdslSCStatusEntry 3 }
        hwXdslSCStatusLogMt  OBJECT-TYPE
            SYNTAX      Unsigned32
            MAX-ACCESS  read-only
            STATUS      current
            DESCRIPTION
                "The number of symbols used to measure the H(f) logarithmic
                 measurement values for the respective transmission direction.
                 This parameter should correspond to the value specified in the
                 recommendation (e.g., the number of symbols in 1 second
                 time interval for G.992.3).  This parameter corresponds to 1
                 second in loop diagnostic procedure and should be updated in
                 initialization.
                "
            REFERENCE  "ITU-T G.997.1, paragraph #7.5.1.26.4 (HLOGMTds)
                        and paragraph #7.5.1.26.10 (HLOGMTus)"
            ::= { hwXdslSCStatusEntry 4 }

        hwXdslSCStatusLogScGroupSize OBJECT-TYPE
            SYNTAX      Unsigned32(1 | 2 | 4 | 8 | 16)
            MAX-ACCESS  read-only
            STATUS      current
            DESCRIPTION
                "Number of sub-carriers per group used to report the H(f)
                 logarithmic representation values for the respective
                 transmission direction. The valid values are 1, 2, 4, 8 and 16.
                 For ADSL, this parameter is equal to one and, for XDSL, it is
                 equal to the size of a sub-carrier group used to compute these
                 parameters.
                 This parameter is only available after a loop diagnostic
                 procedure.
                "
            REFERENCE  "ITU-T G.997.1, paragraph #7.5.1.26.5 (HLOGGds)
                        and paragraph #7.5.1.26.11 (HLOGGus)"
            ::= { hwXdslSCStatusEntry 5 }

        hwXdslSCStatusQlnMt  OBJECT-TYPE
            SYNTAX      Unsigned32
            MAX-ACCESS  read-only
            STATUS      current
            DESCRIPTION
                "The number of symbols used to measure the Quiet Line Noise
                 values on the respective transmission direction.   This
                 parameter should correspond to the value specified in the
                 recommendation (e.g., the number of symbols in 1 second time
                 interval for G.992.3).  This parameter corresponds to 1 second
                 in loop diagnostic procedure and should be updated in
                 initialization.
                "
            REFERENCE  "ITU-T G.997.1, paragraph #7.5.1.27.1 (QLNMTds)
                        and paragraph #7.5.1.27.4 (QLNMTus)"
            ::= { hwXdslSCStatusEntry 6 }
        hwXdslSCStatusQlnScGroupSize OBJECT-TYPE
            SYNTAX      Unsigned32(1 | 2 | 4 | 8 | 16)
            MAX-ACCESS  read-only
            STATUS      current
            DESCRIPTION
                "Number of sub-carriers per group used to report the Quiet
                 Line Noise values for the respective transmission direction.
                 The valid values are 1, 2, 4, 8 and 16.
                 For ADSL, this parameter is equal to one and, for XDSL, it is
                 equal to the size of a sub-carrier group used to compute these
                 parameters.
                 This parameter is only available after a loop diagnostic
                 procedure.
                "
            REFERENCE  "ITU-T G.997.1, paragraph #7.5.1.27.2 (QLNGds)
                        and paragraph #7.5.1.27.5 (QLNGus)"
            ::= { hwXdslSCStatusEntry 7 }

        hwXdslSCStatusMtime  OBJECT-TYPE
            SYNTAX      Unsigned32
            UNITS       "symbols"
            MAX-ACCESS  read-only
            STATUS      current
            DESCRIPTION
                "SNR Measurement Time.  The number of symbols used to
                 measure the SNR values on the respective transmission
                 direction.  It should correspond to the value specified in the
                 recommendation (e.g., the number of symbols in 1 second
                 time interval for G.992.3).  This parameter corresponds to
                 1 second in loop diagnostic procedure and should be updated
                 otherwise.
                 Unit: symbols
                "
            REFERENCE    "ITU-T G.997.1, paragraph #7.5.1.28.1 (SNRMTds)
                          and paragraph #7.5.1.28.4 (SNRMTus)"
            ::= { hwXdslSCStatusEntry 8 }

        hwXdslSCStatusSnrScGroupSize OBJECT-TYPE
            SYNTAX      Unsigned32(1 | 2 | 4 | 8 | 16)
            MAX-ACCESS  read-only
            STATUS      current
            DESCRIPTION
                "Number of sub-carriers per group used to report the SNR
                 values on the respective transmission direction.
                 The valid values are 1, 2, 4, 8 and 16.
                 For ADSL, this parameter is equal to one and, for XDSL, it is
                 equal to the size of a sub-carrier group used to compute these
                 parameters.
                 This parameter is only available after a loop diagnostic
                 procedure.
                "
            REFERENCE  "ITU-T G.997.1, paragraph #7.5.1.28.2 (QLNGds)
                        and paragraph #7.5.1.28.5 (QLNGus)"
            ::= { hwXdslSCStatusEntry 9 }

        hwXdslSCStatusAttainableRate  OBJECT-TYPE
            SYNTAX      Unsigned32
            UNITS       "bits/second"
            MAX-ACCESS  read-only
            STATUS      current
            DESCRIPTION
                "Maximum Attainable Data Rate.  The maximum net data rate
                 currently attainable by the XTU-C transmitter and XTU-R
                 receiver (when referring to downstream direction) or by the
                 XTU-R transmitter and XTU-C receiver (when referring to
                 upstream direction).  Value is coded in bits/s.
                 This object reflects the value of the parameter following the
                 most recent DELT performed on the associated line.  Once
                 the DELT process is over, the parameter no longer changes
                 until the row is deleted or a new DELT process is initiated.
                 Unit: bits/second
                "
            REFERENCE  "ITU-T G.997.1, paragraph #7.5.1.12 (ATTNDRds)
                        and paragraph #7.5.1.13 (ATTNDRus)"
            ::= { hwXdslSCStatusEntry 10 }

        hwXdslSCStatusActAtp  OBJECT-TYPE
            SYNTAX      Integer32
            UNITS       "0.1 dB"
            MAX-ACCESS  read-only
            STATUS      current
            DESCRIPTION
                "Actual Aggregate Transmit Power from the XTU (XTU-R on
                 downstream direction and XTU-C on upstream direction), at the
                 instant of measurement.  It ranges from -310 to 310 units of
                 0.1 dB (Physical values are -31 to 31 dBm).  A value of all
                 1's indicates the measurement is out of range to be
                 represented.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.16 (ACTATPds)
                        and paragraph #7.5.1.17 (ACTATPus)"
            ::= { hwXdslSCStatusEntry 11 }

        hwXdslSCStatusRowStatus  OBJECT-TYPE
            SYNTAX      RowStatus
            MAX-ACCESS  read-create
            STATUS      current
            DESCRIPTION
                "Row Status.  The SNMP agent should create rows in this
                 table and in the hwXdslSCStatusTable for storing the results
                 of a DELT performed on the associated line, if such rows
                 do not already exist.
                 The SNMP agent may have limited resources; therefore, if
                 multiple rows co-exist in the table, it may fail to add
                 new rows to the two tables or allocate memory resources for
                 a new DELT process.  If that occurs, the SNMP agent responds with
                 either the value 'tableFull' or the value
                 'noResources' (for xdsl2LineCmndConfLdsfFailReason
                 object in xdsl2LineTable)
                 The management system (the operator) may delete rows according
                 to any scheme.  E.g., after retrieving the results.
                "
            ::= { hwXdslSCStatusEntry 12 }

        hwXdslSCStatusProfile  OBJECT-TYPE
            SYNTAX      HwXdslProfiles
            MAX-ACCESS  read-only
            STATUS      current
            DESCRIPTION
                "This configuration parameter contains the G.993.2
                 profiles to be allowed by the near-end xTU on this line.
                "
            REFERENCE    "ITU-T G.997.1(200604), paragraph 7.3.1.1.11"
             ::= { hwXdslSCStatusEntry 13 }

        hwXdslSCStatusClassmask  OBJECT-TYPE
            SYNTAX      HwXdslPSDClassMask
            MAX-ACCESS  read-only
            STATUS      current
            DESCRIPTION
                "In order to reduce the number of configuration possibilities,
                 the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1-NUS0.
                 -  Class HPE30 Annex B: HPE30-M1-NUS0.
                 -  Class 997E17-M2x Annex B: 997E17-M2x-NUS0.
                 -  Class 997E30-M2x Annex B: 997E30-M2x-NUS0.
                 -  Class 998E17-M2x Annex B: 998E17-M2x-NUS0, 998E17-M2x-NUS0-M, 998E17-M2x-A.
                 -  Class 998ADE17-M2x Annex B: 998ADE17-M2x-NUS0-M, 998ADE17-M2x-A, 998ADE17-M2x-B, 998ADE17-SPE-M2x-A.
                 -  Class 998E30-M2x Annex B: 998E30-M2x-NUS0, 998E30-M2x-NUS0-M.
                 -  Class 998ADE30-M2x Annex B: 998ADE30-M2x-NUS0-M, 998ADE30-M2x-NUS0-A.
                 -  Class 998E35-M2x Annex B: 998E35-M2x-A.
                 -  Class 998ADE35-M2x Annex B: 998ADE35-M2x-A, 998ADE35-M2x-B, 998ADE35-M2x-M.
                "
            REFERENCE    "ITU-T G.997.1(200604), paragraph 7.3.1.1.12"
            ::= { hwXdslSCStatusEntry 14 }

        --       hwXdslSCStatusBandTable

        hwXdslSCStatusBandTable  OBJECT-TYPE
            SYNTAX      SEQUENCE  OF  HwXdslSCStatusBandEntry
            MAX-ACCESS  not-accessible
            STATUS      current
            DESCRIPTION
                "The table hwXdslSCStatusBandTable contains
                 sub-carrier status parameters for VDSL2/ADSL/ADSL2/ADSL2+
                 and FAST that are grouped per-band.
                 For ADSL/ADSL2/ADSL2+, there is a single
                 upstream band and a single downstream band.
                 for XDSL, there are several downstream bands and
                 several upstream bands.
                 The indexes of this table are ifIndex and hwXdslSCStatusBand.
                "
            ::= { hwXdslStatus 4 }

        hwXdslSCStatusBandEntry  OBJECT-TYPE
            SYNTAX      HwXdslSCStatusBandEntry
            MAX-ACCESS  not-accessible
            STATUS      current
            DESCRIPTION
                "The table hwXdslSCStatusBandTable contains
                 sub-carrier status parameters for VDSL2/ADSL/ADSL2/ADSL2+
                 and FAST that are grouped per-band.
                 For ADSL/ADSL2/ADSL2+, there is a single
                 upstream band and a single downstream band.
                 for XDSL, there are several downstream bands and
                 several upstream bands.
                 The indexes of this entry are ifIndex and hwXdslSCStatusBand.
                "
            INDEX  { ifIndex, hwXdslSCStatusBand }
            ::= { hwXdslSCStatusBandTable 1 }

        HwXdslSCStatusBandEntry  ::=
            SEQUENCE {
              hwXdslSCStatusBand                  HwXdslBand,
              hwXdslSCStatusBandLnAtten           Unsigned32,
              hwXdslSCStatusBandSigAtten          Unsigned32,
              hwXdslSCStatusBandSnrMargin         Integer32,
              hwXdslSCStatusBandUpbokle           Unsigned32
            }

        hwXdslSCStatusBand OBJECT-TYPE
            SYNTAX      HwXdslBand
            MAX-ACCESS  not-accessible
            STATUS      current
            DESCRIPTION
                "The transmission band.
                 Identifies a band in a VDSL2/ADSL/ADSL2/ADSL2+ and FAST link.
                 For a band in the upstream direction, transmission is from
                 the remote end (xTU-R) towards the central office end (xTU-C).
                 A band in the upstream direction is indicated by upstream(1)
                 for ADSL/ADSL2/ADSL2+ single band, or any of us0(3), us1(5),
                 us2(7), us3(9), or us4(11) for XDSL multiple bands.
                 For a band in the downstream direction, transmission is from
                 the xTU-C towards the xTU-R. A band in the downstream
                 direction is indicated by downstream(2) for ADSL/ADSL2/ADSL2+
                 single band, or any of ds1(4), ds2(6), ds3(8), or ds4(10) for
                 XDSL multiple bands.
                "
            ::= { hwXdslSCStatusBandEntry 1 }

        hwXdslSCStatusBandLnAtten  OBJECT-TYPE
            SYNTAX      Unsigned32 (0..1270 | 2147483646 | 2147483647)
            UNITS       "0.1 dB"
            MAX-ACCESS  read-only
            STATUS      current
            DESCRIPTION
                "When referring to a band in the downstream direction, it is
                 the measured difference in the total power transmitted by the
                 xTU-C and the total power received by the xTU-R over all
                 sub-carriers during diagnostics mode.
                 When referring to a band in the upstream direction, it is the
                 measured difference in the total power transmitted by the xTU-R
                 and the total power received by the xTU-C over all sub-carriers
                 during diagnostics mode.
                 It ranges from 0 to 1270 units of 0.1 dB (Physical values are
                 0 to 127 dB).
                 A special value of 0x7FFFFFFF (2147483647) indicates the line
                 attenuation is out of range to be represented.
                 A special value of 0x7FFFFFFE (2147483646) indicates the line
                 attenuation measurement is unavailable.
                 When the port is in the activated state, this object reflects
                 actual activation parameters. When the port is in the deactivated
                 state, this object reflects DELT data if DELT data is available
                 and activation parameters for the port activated last time if
                 the DELT data is unavailable.
                 Unit: 0.1 dB
                "
            REFERENCE  "ITU-T G.997.1, paragraph #7.5.1.6 (LATNds)
                        and paragraph #7.5.1.7 (LATNus)"
            ::= { hwXdslSCStatusBandEntry 2 }

        hwXdslSCStatusBandSigAtten  OBJECT-TYPE
            SYNTAX      Unsigned32 (0..1270 | 2147483646 | 2147483647)
            UNITS       "0.1 dB"
            MAX-ACCESS  read-only
            STATUS      current
            DESCRIPTION
                "When referring to a band the downstream direction, it is the
                 measured difference in the total power transmitted by the
                 xTU-C and the total power received by the xTU-R over all sub
                 carriers during Showtime after the diagnostics mode.
                 When referring to the upstream direction, it is the measured
                 difference in the total power transmitted by the
                 xTU-R and the total power received by the xTU-C over all sub
                 carriers during Showtime after the diagnostics mode.
                 It ranges from 0 to 1270 units of 0.1 dB (Physical values
                 are 0 to 127 dB).
                 A special value of 0x7FFFFFFF (2147483647) indicates the line
                 attenuation is out of range to be represented.
                 A special value of 0x7FFFFFFE (2147483646) indicates the line
                 attenuation measurement is unavailable.
                 When the port is in the activated state, this object reflects
                 actual activation parameters. When the port is in the deactivated
                 state, this object reflects DELT data if DELT data is available
                 and activation parameters for the port activated last time if
                 the DELT data is unavailable.
                 Unit: 0.1 dB
                "
            REFERENCE  "ITU-T G.997.1, paragraph #7.5.1.8 (SATNds)
                        and paragraph #7.5.1.9 (SATNus)"
            ::= { hwXdslSCStatusBandEntry 3 }

        hwXdslSCStatusBandSnrMargin  OBJECT-TYPE
            SYNTAX      Integer32 (-640..630 | 2147483646 | 2147483647)
            UNITS       "0.1 dB"
            MAX-ACCESS  read-only
            STATUS      current
            DESCRIPTION
                "SNR Margin is the maximum increase in dB of the noise power
                 received at the XTU (xTU-R on downstream direction and xTU-C
                 on upstream direction), such that the BER requirements are met
                 for all bearer channels received at the XTU.  It ranges from
                 -640 to 630 units of 0.1 dB (Physical values are -64 to
                 63 dB).
                 A special value of 0x7FFFFFFF (2147483647) indicates the
                 SNR Margin is out of range to be represented.
                 A special value of 0x7FFFFFFE (2147483646) indicates the
                 SNR Margin measurement is currently unavailable.
                 When the port is in the activated state, this object reflects
                 actual activation parameters. When the port is in the deactivated
                 state, this object reflects DELT data if DELT data is available
                 and activation parameters for the port activated last time if
                 the DELT data is unavailable.
                 Unit: 0.1 dB
                "
            REFERENCE  "ITU-T G.997.1, paragraph #7.5.1.10 (SNRMds)
                        and paragraph #7.5.1.11 (SNRMus)"
            ::= { hwXdslSCStatusBandEntry 4 }

        hwXdslSCStatusBandUpbokle  OBJECT-TYPE
            SYNTAX      Unsigned32 (0..1280 | 2047 | 2147483647)
            UNITS       "0.1 dB"
            MAX-ACCESS  read-only
            STATUS      current
            DESCRIPTION
                "This parameter is a vector of UPBO electrical length per-band
                 estimates for each supported upstream/downstream band,
                 expressed in dB at 1 MHz (kl0) calculated by the VTU-O/VTU-R,
                 based on separate measurements in the supported upstream bands excluding US0/downstream bands.
                 The value ranges from 0 to 128 dB in steps of 0.1 dB, with special value 204.7
                 which indicates that the estimate is greater than 128 dB.
                 This parameter is required for the Alternative Electrical Length Estimation method (ELE-M1).
                 Unit: 0.1 dB
                "
            REFERENCE  "ITU-T G.997.1, paragraph #7.5.1.23"
            ::= { hwXdslSCStatusBandEntry 5 }

        --       hwXdslSCStatusSegmentTable

        hwXdslSCStatusSegmentTable  OBJECT-TYPE
            SYNTAX      SEQUENCE  OF  HwXdslSCStatusSegmentEntry
            MAX-ACCESS  not-accessible
            STATUS      current
            DESCRIPTION
                "The table hwXdslSCStatusSegmentTable contains status parameters
                 of VDSL2/ADSL/ADSL2/ADSL2+ and FAST sub-carriers.
                 Several objects in the table refer to NSus and NSds. For
                 G.993.2, the value of NSus and NSds are respectively the indices
                 of the highest supported upstream and downstream subcarriers
                 according to the selected implementation profile. For ADSL,
                 NSus is equal to NSCus-1 and NSds is equal to NSCds-1.
                 The indexes of this table are ifIndex, hwXdslSCStatusDirection,
                 and hwXdslSCStatusSegment.
                 One index of this entry is an interface index where the
                 interface has an ifType of VDSL2/FAST. The second index of this
                 entry is the transmission direction. The third index identifies
                 the specific segment of the sub-carriers status addressed.
                "
            ::= { hwXdslStatus 5 }

        hwXdslSCStatusSegmentEntry  OBJECT-TYPE
            SYNTAX      HwXdslSCStatusSegmentEntry
            MAX-ACCESS  not-accessible
            STATUS      current
            DESCRIPTION
                "The table hwXdslSCStatusSegmentTable contains status parameters
                 of VDSL2/ADSL/ADSL2/ADSL2+ and FAST sub-carriers.
                 Several objects in the table refer to NSus and NSds. For
                 G.993.2, the value of NSus and NSds are respectively the indices
                 of the highest supported upstream and downstream subcarriers
                 according to the selected implementation profile. For ADSL,
                 NSus is equal to NSCus-1 and NSds is equal to NSCds-1.
                 The indexes of this entry are ifIndex, hwXdslSCStatusDirection,
                 and hwXdslSCStatusSegment.
                 One index of this entry is an interface index where the
                 interface has an ifType of VDSL2/FAST. The second index of this
                 entry is the transmission direction. The third index identifies
                 the specific segment of the sub-carriers status addressed.
                "
            INDEX  { ifIndex,
                     hwXdslSCStatusDirection,
                     hwXdslSCStatusSegment   }
            ::= { hwXdslSCStatusSegmentTable 1 }

        HwXdslSCStatusSegmentEntry  ::=
            SEQUENCE {
              hwXdslSCStatusSegment                  Unsigned32,
              hwXdslSCStatusSegmentLinReal           OCTET STRING,
              hwXdslSCStatusSegmentLinImg            OCTET STRING,
              hwXdslSCStatusSegmentLog               OCTET STRING,
              hwXdslSCStatusSegmentQln               OCTET STRING,
              hwXdslSCStatusSegmentSnr               OCTET STRING,
              hwXdslSCStatusSegmentBitsAlloc         OCTET STRING,
              hwXdslSCStatusSegmentGainAlloc         OCTET STRING,
              hwXdslSCStatusSegmentTssi              HwXdslTssi,
              hwXdslSCStatusSegmentTxPSD             OCTET STRING,
              hwXdslSCStatusSegmentSnrMargin         OCTET STRING,
              hwXdslSCStatusSegmentLogScGroupSize    Unsigned32,
              hwXdslSCStatusSegmentQlnScGroupSize    Unsigned32,
              hwXdslSCStatusSegmentLinScGroupSize    Unsigned32,
              hwXdslSCStatusSegmentSnrScGroupSize    Unsigned32,
              hwXdslSCStatusSegmentQlnWithVectoring OCTET STRING,
              hwXdslSCStatusSegmentBitsAllocRmc     OCTET STRING
            }

        hwXdslSCStatusSegment  OBJECT-TYPE
            SYNTAX      Unsigned32(1..16)
            MAX-ACCESS  not-accessible
            STATUS      current
            DESCRIPTION
                "The segment of the sub-carriers
                 status information provided by this
                 row.
                 Several status parameters in this table
                 are retrieved in segments. The first segment
                 of the status information is retrieved with
                 hwXdslSCStatusSegment=1, the second segment
                 is retrieved with hwXdslSCStatusSegment=2, and
                 so on. When any status parameter is retrieved
                 in n segments where n<16) then, for that
                 parameter, GET operations for the rest segment
                 numbers (n+1 to 16) are responded with a value
                 that indicates: No measurement could be done.
                "
           ::= { hwXdslSCStatusSegmentEntry 1 }

        hwXdslSCStatusSegmentLinReal  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the real component [referred here as
                 a(i)] of Hlin(f = i*Df) value for a particular sub-carrier group
                 index i (0 <= i < NS).
                 Hlin(f) is represented as ((scale/2^15)*((a(i)+j*b(i))/2^15)),
                 where scale is hwXdslSCStatusLinScale and a(i) and b(i)
                 [provided by the hwXdslSCStatusSegmentLinImg object] are in the
                 range (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { hwXdslSCStatusSegmentEntry 2 }

        hwXdslSCStatusSegmentLinImg  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the imaginary component [referred
                 here as b(i)] of Hlin(f = i*Df) value for a particular sub-
                 carrier group index i (0 <= i < NS).
                 Hlin(f) is represented as ((scale/2^15)*((a(i)+j*b(i))/2^15)),
                 where scale is hwXdslSCStatusLinScale and a(i) [provided by
                 the hwXdslSCStatusSegmentLinReal object] and b(i) are in the range
                 (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { hwXdslSCStatusSegmentEntry 3 }

        hwXdslSCStatusSegmentLog  OBJECT-TYPE
            SYNTAX      OCTET STRING  (SIZE(0..1024))
            UNITS       "dB"
            MAX-ACCESS  read-only
            STATUS      current
            DESCRIPTION
                "An array of up to 512 real H(f) logarithmic representation
                 values in dB for the respective transmission direction.  It is
                 designed to support up to 512 (downstream) sub-carriers groups
                 and can be retrieved in a single segment.
                 The number of utilized values on downstream direction depends
                 on NSds, and on upstream direction it depends on NSus.  This
                 value is referred here as NS.
                 Each array entry represents the real Hlog(f = i*Df) value for a
                 particular sub-carrier group index i, (0 <= i < NS).
                 The real Hlog(f) value is represented as (6-m(i)/10), with m(i)
                 in the range 0 to 1022.  A special value m=1023 indicates that
                 no measurement could be done for the sub-carrier group because
                 it is out of the passband or that the attenuation is out of
                 range to be represented.  This parameter is applicable in loop
                 diagnostic procedure and initialization.
                 Each value in this array is 16 bits wide and is stored
                 in big endian format.
                 Unit: dB
                "
            REFERENCE  "ITU-T G.997.1, paragraph #7.5.1.26.6 (HLOGpsds)
                        and paragraph #7.5.1.26.12 (HLOGpsus)"
            ::= { hwXdslSCStatusSegmentEntry 4 }

        hwXdslSCStatusSegmentQln  OBJECT-TYPE
            SYNTAX      OCTET STRING  (SIZE(0..512))
            UNITS       "dBm/Hz"
            MAX-ACCESS  read-only
            STATUS      current
            DESCRIPTION
                "An array of up to 512 real Quiet Line Noise values in dBm/Hz
                 for the respective transmission direction.  It is designed for
                 up to 512 (downstream) sub-carriers groups and can be retrieved
                 in a single segment.
                 The number of utilized values on downstream direction depends
                 on NSds, and on upstream direction it depends on NSus.  This
                 value is referred here as NS.
                 Each array entry represents the QLN(f = i*Df) value for a
                 particular sub-carrier index i, (0 <= i < NS).
                 The QLN(f) is represented as ( -23-n(i)/2)(if the line is activated
                 as G9701 of hwXdslLineStatusXtuTransSys
                 it is represented as ( -33-n(i)/2)), with n(i) in the
                 range 0 to 254.  A special value n(i)=255 indicates that no
                 measurement could be done for the sub-carrier group because it
                 is out of the passband or that the noise PSD is out of range
                 to be represented.
                 This parameter is applicable in loop diagnostic procedure and
                 initialization.  Each value in this array is 8 bits wide.
                 Unit: dBm/Hz
                "
            REFERENCE  "ITU-T G.997.1, paragraph #7.5.1.27.3 (QLNpsds)
                        and paragraph #7.5.1.27.6 (QLNpsus)"
            ::= { hwXdslSCStatusSegmentEntry 5 }

        hwXdslSCStatusSegmentSnr  OBJECT-TYPE
            SYNTAX      OCTET STRING  (SIZE(0..512))
            UNITS       "dB"
            MAX-ACCESS  read-only
            STATUS      current
            DESCRIPTION
                "The SNR Margin per sub-carrier group, expressing the
                 ratio between the received signal power and received noise
                 power per sub-scriber group.  It is an array of 512 octets,
                 designed for supporting up to 512 (downstream) sub-carriers
                 groups and can be retrieved in a single segment.
                 The number of utilized octets on downstream direction depends
                 on NSds, and on upstream direction it depends on NSus.  This
                 value is referred here as NS.
                 Octet i (0 <= i < NS) is set to a value in the range 0 to
                 254 to indicate that the respective downstream or upstream sub-
                 carrier group i has SNR of: (-32 + hwXdslSCStatusSegmentSnr(i)/2)
                 in dB (i.e., -32 to 95dB).
                 The special value 255 means that no measurement could be done
                 for the sub-carrier group because it is out of the PSD mask
                 passband or that the noise PSD is out of range to be
                 represented.  Each value in this array is 8 bits wide.
                 Unit: dB
                "
            REFERENCE    "ITU-T G.997.1, paragraph #7.5.1.28.3 (SNRpsds)
                          and paragraph #7.5.1.28.6 (SNRpsus)"
            ::= { hwXdslSCStatusSegmentEntry 6 }

        hwXdslSCStatusSegmentBitsAlloc  OBJECT-TYPE
            SYNTAX      OCTET STRING  (SIZE(0..256))
            UNITS       "bits"
            MAX-ACCESS  read-only
            STATUS      current
            DESCRIPTION
                "The bits allocation per sub-carrier.  An array of 256 octets
                 (512 nibbles), designed for supporting up to 512 (downstream)
                 sub-carriers. When more then 512 sub-carriers are supported,
                 the status information is reported through multiple (up to 16)
                 segments. The first segment is then used for the first 512
                 sub-carriers. The second segment is used for the sub-carriers
                 512 to 1023 and so on.
                 The aggregate number of utilized nibbles on downstream direction
                 (in all segments) depends on NSds, and on upstream direction it
                 depends on NSus.
                 This value is referred here as NS. The segment number is in
                 xdsl2SCStatusSegment.
                 Nibble i (0 <= i < MIN(NS-(segment-1)*512,512)) in each
                 segment is set to a value in the range 0 to 15 to indicate that
                 the respective downstream or upstream sub-carrier j
                 (j=(segement-1)*512+i) has the same amount of bits
                 allocation.
                 Unit: bits
                "
            REFERENCE    "ITU-T G.997.1, paragraph #7.5.1.29.1 (BITSpsds)
                          and paragraph #7.5.1.29.2 (BITSpsus)"
            ::= { hwXdslSCStatusSegmentEntry 7 }

        hwXdslSCStatusSegmentGainAlloc  OBJECT-TYPE
            SYNTAX      OCTET STRING  (SIZE(0..1024))
            MAX-ACCESS  read-only
            STATUS      current
            DESCRIPTION
                "The gain allocation per sub-carrier.  An array of 512 16-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The aggregate number of utilized octets on downstream direction
                 depends on NSds, and on upstream direction it depends on NSus.
                 This value is referred here as NS. The segment number is in
                 xdsl2SCStatusSegment.
                 Value i (0 <= i < MIN(NS-(segment-1)*512,512)) in each
                 segment is set to a value in the range 0 to 4093 to indicate
                 that the respective downstream or upstream sub-carrier j
                 (j=(segement-1)*512+i) has the same amount of gain value.
                 The gain value is represented as a multiple of 1/512 on
                 linear scale.  Each value in this array is 16 bits wide and is
                 stored in big endian format.
                "
            REFERENCE    "ITU-T G.997.1, paragraph #7.5.1.29.3 (GAINSpsds)
                          and paragraph #7.5.1.29.4 (GAINSpsus)"
            ::= { hwXdslSCStatusSegmentEntry 8 }

        hwXdslSCStatusSegmentTssi  OBJECT-TYPE
            SYNTAX      HwXdslTssi
            MAX-ACCESS  read-only
            STATUS      current
            DESCRIPTION
                "The transmit spectrum shaping (TSSi) breakpoints expressed
                 as the set of breakpoints exchanged during G.994.1.
                 Each breakpoint is a pair of values occupying 3 octets with the
                 following structure:
                 First 2 octets - Index of the subcarrier used in the context of
                                  the breakpoint.
                 Third octet    - The shaping parameter at the breakpoint.
                 Subcarrier index is an unsigned number in the range 1 to either
                 NSCds (downstream direction) or NSCus (upstream direction).
                 The shaping parameter value is in the range 0 to 127 (units of
                 -0.5dB). The special value 127 indicates that the subcarrier
                 is not transmitted.
                "
            REFERENCE  "ITU-T G.997.1, paragraph #7.5.1.29.5 (TSSpsds)
                        and paragraph #7.5.1.29.6 (TSSpsus)"
            ::= { hwXdslSCStatusSegmentEntry 9 }

        hwXdslSCStatusSegmentTxPSD  OBJECT-TYPE
            SYNTAX      OCTET STRING  (SIZE(0..1024))
            MAX-ACCESS  read-only
            STATUS      current
            DESCRIPTION
                "The TxPSD per sub-carrier. An array of 512 8-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The special value 0xff means that no measurement could be done
                 for the sub-carrier group because it is out of the PSD mask
                 passband or that the noise PSD is out of range to be
                 represented. Each value in this array is 8 bits wide.
                 Unit: -0.5 dBm/Hz
                "
            ::= { hwXdslSCStatusSegmentEntry 65535 }

        hwXdslSCStatusSegmentSnrMargin  OBJECT-TYPE
            SYNTAX      OCTET STRING  (SIZE(0..1024))
            MAX-ACCESS  read-only
            STATUS      current
            DESCRIPTION
                "The SnrMargin per sub-carrier.  An array of 512 16-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The real value is represented as (hwXdslSCStatusSegmentSnrMargin/10).
                 The special value 0x7fff indicates that no measurement could be
                 done for the sub-carrier group because it is out of the passband
                 or that the noise PSD is out of range to be represented.
                 Each value in this array is 16 bits wide.
                 Unit: dB
                "
            ::= { hwXdslSCStatusSegmentEntry 65536 }

        hwXdslSCStatusSegmentLogScGroupSize  OBJECT-TYPE
            SYNTAX      Unsigned32(1 | 2 | 4 | 8 | 16)
            MAX-ACCESS  read-only
            STATUS      current
            DESCRIPTION
                "Number of sub-carriers per group used to report the H(f)
                 logarithmic representation values for the respective
                 transmission direction. The valid values are 1, 2, 4, 8 and 16.
                 For ADSL, this parameter is equal to one and, for XDSL, it is
                 equal to the size of a sub-carrier group used to compute these
                 parameters.
                 This parameter is only available after a loop diagnostic
                 procedure.
                 It's available for the first segment, other segments return '-1'.
                "
            REFERENCE  "ITU-T G.997.1, paragraph #7.5.1.26.2 (HLINGds)
                        and paragraph #7.5.1.26.8 (HLINGus)"
            ::= { hwXdslSCStatusSegmentEntry 65537 }

        hwXdslSCStatusSegmentQlnScGroupSize  OBJECT-TYPE
            SYNTAX      Unsigned32(1 | 2 | 4 | 8 | 16)
            MAX-ACCESS  read-only
            STATUS      current
            DESCRIPTION
                "Number of sub-carriers per group used to report the Quiet
                 Line Noise values for the respective transmission direction.
                 The valid values are 1, 2, 4, 8 and 16.
                 For ADSL, this parameter is equal to one and, for XDSL, it is
                 equal to the size of a sub-carrier group used to compute these
                 parameters.
                 This parameter is only available after a loop diagnostic
                 procedure.
                 It's available for the first segment, other segments return '-1'.
                "
            REFERENCE  "ITU-T G.997.1, paragraph #7.5.1.26.2 (HLINGds)
                         and paragraph #7.5.1.26.8 (HLINGus)"
            ::= { hwXdslSCStatusSegmentEntry 65538 }

        hwXdslSCStatusSegmentLinScGroupSize OBJECT-TYPE
            SYNTAX      Unsigned32(1 | 2 | 4 | 8 | 16)
            MAX-ACCESS  read-only
            STATUS      current
            DESCRIPTION
                "Number of sub-carriers per group used to report the H(f)
                 linear representation values for the respective transmission
                 direction. The valid values are 1, 2, 4, 8 and 16. For ADSL, this
                 parameter is equal to one and, for XDSL, it is equal to the
                 size of a sub-carrier group used to compute these parameters.
                 This parameter is only available after a loop diagnostic
                 procedure.
                 It's available for the first segment, other segments return '-1'.
                "
            REFERENCE  "ITU-T G.997.1, paragraph #7.5.1.26.2 (HLINGds)
                          and paragraph #7.5.1.26.8 (HLINGus)"
            ::= { hwXdslSCStatusSegmentEntry 65539 }

        hwXdslSCStatusSegmentSnrScGroupSize  OBJECT-TYPE
            SYNTAX      Unsigned32(1 | 2 | 4 | 8 | 16)
            MAX-ACCESS  read-only
            STATUS      current
            DESCRIPTION
                "Number of sub-carriers per group used to report the SNR
                 values on the respective transmission direction.
                 The valid values are 1, 2, 4, 8 and 16.
                 For ADSL, this parameter is equal to one and, for XDSL, it is
                 equal to the size of a sub-carrier group used to compute these
                 parameters.
                 This parameter is only available after a loop diagnostic
                 procedure.
                 It's available for the first segment, other segments return '-1'.
                "
            REFERENCE  "ITU-T G.997.1, paragraph #7.5.1.26.2 (HLINGds)
                         and paragraph #7.5.1.26.8 (HLINGus)"
            ::= { hwXdslSCStatusSegmentEntry 65540 }

        hwXdslSCStatusSegmentQlnWithVectoring  OBJECT-TYPE
            SYNTAX      OCTET STRING  (SIZE(0..512))
            UNITS       "dBm/Hz"
            MAX-ACCESS  read-only
            STATUS      current
            DESCRIPTION
                "An array of up to 512 real Quiet Line Noise values in dBm/Hz
                 for the respective transmission direction.  It is designed for
                 up to 512 (downstream) sub-carriers groups and can be retrieved
                 in a single segment.
                 The number of utilized values on downstream direction depends
                 on NSds, and on upstream direction it depends on NSus.  This
                 value is referred here as NS.
                 Each array entry represents the QLN(f = i*Df) value for a
                 particular sub-carrier index i, (0 <= i < NS).
                 The QLN(f) is represented as ( -23-n(i)/2)(if the line is activated
                 as G9701 of hwXdslLineStatusXtuTransSys
                 it is represented as ( -33-n(i)/2)), with n(i) in the
                 range 0 to 254.  A special value n(i)=255 indicates that no
                 measurement could be done for the sub-carrier group because it
                 is out of the passband or that the noise PSD is out of range
                 to be represented.
                 This parameter is applicable in loop diagnostic procedure and
                 initialization.  Each value in this array is 8 bits wide.
                 Unit: dBm/Hz
                 This value is calculated with vectoring effect.
                "
            REFERENCE  "ITU-T G.997.1, paragraph #7.5.1.27.3 (QLNpsds)
                        and paragraph #7.5.1.27.6 (QLNpsus)"
            ::= { hwXdslSCStatusSegmentEntry 65541 }

        hwXdslSCStatusSegmentBitsAllocRmc  OBJECT-TYPE
            SYNTAX      OCTET STRING  (SIZE(0..256))
            UNITS       "bits"
            MAX-ACCESS  read-only
            STATUS      current
            DESCRIPTION
                "The bit allocation values on RMC sub-carriers in RMC symbols.
                 An array of 256 octets (512 nibbles), designed for supporting
                 up to 512 (downstream) sub-carriers. When more then 512
                 sub-carriers are supported, the status information is reported
                 through multiple (up to 16) segments. The first segment is then
                 used for the first 512 sub-carriers. The second segment is used
                 for the sub-carriers 512 to 1023 and so on.
                 The aggregate number of utilized nibbles on downstream direction
                 (in all segments) depends on NSds, and on upstream direction it
                 depends on NSus.
                 This value is referred here as NS. The segment number is in
                 xdsl2SCStatusSegment.
                 Nibble i (0 <= i < MIN(NS-(segment-1)*512,512)) in each
                 segment is set to a value in the range 0 to 15 to indicate that
                 the respective downstream or upstream sub-carrier j
                 (j=(segement-1)*512+i) has the same amount of bits
                 allocation.
                 Unit: bits
                "
            REFERENCE    "ITU-T G.997.2, paragraph #7.10.12.3 (BITSRMCpsds)
                          and paragraph #7.10.12.4 (BITSRMCpsus)"
            ::= { hwXdslSCStatusSegmentEntry 65542 }

        hwXdslVDSLSCFextTable  OBJECT-TYPE
            SYNTAX      SEQUENCE  OF  HWXdslVDSLSCFextEntry
            MAX-ACCESS  not-accessible
            STATUS      current
            DESCRIPTION
                "The table hwXdslVDSLSCFextTable contains FEXT coupling function parameters.
                 The indexes of this table are ifIndex, hwXdslVDSLSCFextFromIfindex,
                 and hwXdslVDSLSCFextRequestXLinScGroupSize.
                "
            ::= { hwXdslStatus 6 }

        hwXdslVDSLSCFextEntry  OBJECT-TYPE
            SYNTAX      HWXdslVDSLSCFextEntry
            MAX-ACCESS  not-accessible
            STATUS      current
            DESCRIPTION
                "The table hwXdslVDSLSCFextTable contains FEXT coupling function parameters.
                 The indexes of this entry are ifIndex, hwXdslVDSLSCFextFromIfindex,
                 and hwXdslVDSLSCFextRequestXLinScGroupSize.
                "
            INDEX  { ifIndex,
                     hwXdslVDSLSCFextFromIfindex,
                     hwXdslVDSLSCFextRequestXLinScGroupSize   }
            ::= { hwXdslVDSLSCFextTable 1 }

        HWXdslVDSLSCFextEntry  ::=
            SEQUENCE {
              hwXdslVDSLSCFextFromIfindex                   Integer32,
              hwXdslVDSLSCFextRequestXLinScGroupSize        Unsigned32,
              hwXdslVDSLSCFextXLinScaleDs                   Unsigned32,
              hwXdslVDSLSCFextXlinScGroupSizeDs             Unsigned32,
              hwXdslVDSLSCFextXLinBandDs                    OCTET STRING,
              hwXdslVDSLSCFextXlinRealDs                    OCTET STRING,
              hwXdslVDSLSCFextXlinImgDs                     OCTET STRING,
              hwXdslVDSLSCFextXLinScaleUs                   Unsigned32,
              hwXdslVDSLSCFextXlinScGroupSizeUs             Unsigned32,
              hwXdslVDSLSCFextXLinBandUs                    OCTET STRING,
              hwXdslVDSLSCFextXlinRealUs                    OCTET STRING,
              hwXdslVDSLSCFextXlinImgUs                     OCTET STRING
            }

        hwXdslVDSLSCFextFromIfindex  OBJECT-TYPE
            SYNTAX      Integer32
            MAX-ACCESS  not-accessible
            STATUS      current
            DESCRIPTION
                "The hwXdslVDSLSCFextFromIfindex is an interface index where the
                 interface has an ifType of vdsl2(251).
                "
           ::= { hwXdslVDSLSCFextEntry 1 }

        hwXdslVDSLSCFextRequestXLinScGroupSize  OBJECT-TYPE
            SYNTAX      Unsigned32(1 | 2 | 4 | 8 | 16 | 32 | 64)
            MAX-ACCESS  not-accessible
            STATUS      current
            DESCRIPTION
                "This parameter is the requested value of XLING.
                 The valid values are 1, 2, 4, 8, 16, 32, and 64.
                "
            REFERENCE  "ITU-T G.997.1, paragraph #7.5.1.38.3 and #7.5.1.38.8"
            ::= { hwXdslVDSLSCFextEntry 2 }

        hwXdslVDSLSCFextXLinScaleDs  OBJECT-TYPE
            SYNTAX      Unsigned32
            MAX-ACCESS  read-only
            STATUS      current
            DESCRIPTION
                "This parameter is the scale factor to be applied to the downstream
                 Xlinpsds values. It is represented as an unsigned integer
                 in the range from 1 to 2^16 - 1.
                "
            REFERENCE  "ITU-T G.997.1, paragraph #7.5.1.38.1 "
            ::= { hwXdslVDSLSCFextEntry 3 }

        hwXdslVDSLSCFextXlinScGroupSizeDs  OBJECT-TYPE
            SYNTAX      Unsigned32(1 | 2 | 4 | 8 | 16 | 32 | 64)
            MAX-ACCESS  read-only
            STATUS      current
            DESCRIPTION
                "This parameter is the number of subcarriers per group used
                 to report Xlinpsds. The valid values are 1, 2, 4, 8, 16, 32,
                 and 64. XLINGds should equal the sub-sampling factor used to
                 estimate the crosstalk channel for cancellation.
                "
            REFERENCE  "ITU-T G.997.1, paragraph #7.5.1.38.2"
            ::= { hwXdslVDSLSCFextEntry 4 }

        hwXdslVDSLSCFextXLinBandDs  OBJECT-TYPE
            SYNTAX      OCTET STRING  (SIZE(0..96))
            MAX-ACCESS  read-only
            STATUS      current
            DESCRIPTION
                "XLINBANDSds contains pairs of (start_subcarrier_index, stop_subcarrier_index)
                 for every band in which XLINpsds is reported.
                "
            REFERENCE  "ITU-T G.997.1, paragraph #7.5.1.38.4"
            ::= { hwXdslVDSLSCFextEntry 5 }

        hwXdslVDSLSCFextXlinRealDs  OBJECT-TYPE
            SYNTAX      OCTET STRING  (SIZE(0..1024))
            MAX-ACCESS  read-only
            STATUS      current
            DESCRIPTION
                "For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5 "
            ::= { hwXdslVDSLSCFextEntry 6 }

        hwXdslVDSLSCFextXlinImgDs  OBJECT-TYPE
            SYNTAX      OCTET STRING  (SIZE(0..1024))
            MAX-ACCESS  read-only
            STATUS      current
            DESCRIPTION
                "For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5"
            ::= { hwXdslVDSLSCFextEntry 7 }

        hwXdslVDSLSCFextXLinScaleUs  OBJECT-TYPE
            SYNTAX      Unsigned32
            MAX-ACCESS  read-only
            STATUS      current
            DESCRIPTION
                "This parameter is the scale factor to be applied to the upstream
                 Xlinpsus values. It is represented as an unsigned integer
                 in the range from 1 to 2^16 - 1.
                "
            REFERENCE  "ITU-T G.997.1, paragraph #7.5.1.38.6"
            ::= { hwXdslVDSLSCFextEntry 8 }

        hwXdslVDSLSCFextXlinScGroupSizeUs  OBJECT-TYPE
            SYNTAX      Unsigned32(1 | 2 | 4 | 8 | 16 | 32 | 64)
            MAX-ACCESS  read-only
            STATUS      current
            DESCRIPTION
                "This parameter is the number of subcarriers per group used
                 to report Xlinpsus. The valid values are 1, 2, 4, 8, 16, 32,
                 and 64. XLINGus should equal the sub-sampling factor used to
                 estimate the crosstalk channel for cancellation.
                "
            REFERENCE  "ITU-T G.997.1, paragraph #7.5.1.38.7"
            ::= { hwXdslVDSLSCFextEntry 9 }

        hwXdslVDSLSCFextXLinBandUs  OBJECT-TYPE
            SYNTAX      OCTET STRING  (SIZE(0..96))
            MAX-ACCESS  read-only
            STATUS      current
            DESCRIPTION
                "XLINBANDSus contains pairs of (start_subcarrier_index, stop_subcarrier_index)
                 for every band in which XLINpsus is reported.
                "
            REFERENCE  "ITU-T G.997.1, paragraph #7.5.1.38.9"
            ::= { hwXdslVDSLSCFextEntry 10 }

        hwXdslVDSLSCFextXlinRealUs  OBJECT-TYPE
            SYNTAX      OCTET STRING  (SIZE(0..1024))
            MAX-ACCESS  read-only
            STATUS      current
            DESCRIPTION
                "For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"
            ::= { hwXdslVDSLSCFextEntry 11 }

        hwXdslVDSLSCFextXlinImgUs  OBJECT-TYPE
            SYNTAX      OCTET STRING  (SIZE(0..1024))
            MAX-ACCESS  read-only
            STATUS      current
            DESCRIPTION
                "For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"

            ::= { hwXdslVDSLSCFextEntry 12 }

          --      hwOntXdslChannelStatusTable
        hwOntXdslChannelStatusTable  OBJECT-TYPE
            SYNTAX      SEQUENCE  OF  HwOntXdslChannelStatusEntry
            MAX-ACCESS  not-accessible
            STATUS      current
            DESCRIPTION
                "The table hwOntXdslChannelStatusTable contains status
                 parameters of XDSL channel.
                 The indexes of this table are ifIndex, hwOntObjectIndex, hwOntUniPhyType,
                 hwOntXdslPortid, hwOntXdslChannelIDand hwOntXdslChStatusUnit.
                "
            ::= { hwXdslStatus 7 }

       hwOntXdslChannelStatusEntry  OBJECT-TYPE
            SYNTAX      HwOntXdslChannelStatusEntry
            MAX-ACCESS  not-accessible
            STATUS      current
            DESCRIPTION
                "The table hwOntXdslChannelStatusTable contains status
                 parameters of XDSL channel.
                 The indexes of this entry are ifIndex, hwOntObjectIndex, hwOntUniPhyType,
                 hwOntXdslPortid, hwOntXdslChannelIDand hwOntXdslChStatusUnit.
                "
            INDEX  { ifIndex,
                     hwOntObjectIndex,
                     hwOntUniPhyType,
                     hwOntXdslPortid,
                     hwOntXdslChannelID,
                     hwOntXdslChStatusUnit }
            ::= { hwOntXdslChannelStatusTable 1 }

       HwOntXdslChannelStatusEntry  ::=
           SEQUENCE {
               hwOntXdslChannelID                  Integer32,
               hwOntXdslChStatusUnit               HwXdslUnit,
               hwOntXdslChStatusActNetDataRate     Unsigned32,
               hwOntXdslChStatusPrevNetDataRate    Unsigned32,
         hwOntXdslChStatusActDelay           Unsigned32,
               hwOntXdslChStatusINP                Unsigned32
           }

        hwOntXdslChannelID  OBJECT-TYPE
            SYNTAX      Integer32
            MAX-ACCESS  not-accessible
            STATUS      current
            DESCRIPTION
                "Channel ID."
            ::= { hwOntXdslChannelStatusEntry 1 }

        hwOntXdslChStatusUnit  OBJECT-TYPE
            SYNTAX      HwXdslUnit
            MAX-ACCESS  not-accessible
            STATUS      current
            DESCRIPTION
                "The termination unit xTU-C(1) or xTU-R(2)."
            ::= { hwOntXdslChannelStatusEntry 2 }

        hwOntXdslChStatusActNetDataRate  OBJECT-TYPE
            SYNTAX      Unsigned32(0..200000000 | 4294967295)
            UNITS       "bits/second"
            MAX-ACCESS  read-only
            STATUS      current
            DESCRIPTION
                "If retransmission is not used in a given transmit direction,
                 this parameter reports the actual net data rate at which the
                 bearer channel is operating in L0 power management state, and
                 in L1 or L2 states, the parameter contains the net data rate
                 in the previous L0 state.
                 If retransmission is used in a given transmit direction,
                 this parameter reports the Expected Throughput(ETR) at which the
                 bearer channel is operating in L0 power management state, and in
                 L1 or L2 states, the parameter contains the Expected Throughput(ETR)
                 in the previous L0 state.
                 The data rate is coded in steps of 1000 bit/s.
                 The invalid value is 4294967295. If data on the port is invalid
                 or no data is generated on the port because the port has not been
                 activated, the invalid value will be returned.
                 Unit: bits/second
                "
            REFERENCE    "ITU-T G.997.1, paragraph 7.5.2.1"
            ::= { hwOntXdslChannelStatusEntry 3 }

         hwOntXdslChStatusPrevNetDataRate  OBJECT-TYPE
            SYNTAX      Unsigned32(0..200000000 | 4294967295)
            UNITS       "bits/second"
            MAX-ACCESS  read-only
            STATUS      current
            DESCRIPTION
                "If retransmission is not used in a given transmit direction, this
                 parameter reports the previous net data rate the bearer channel
                 was operating at just before the latest net data rate change event
                 occurred, excluding all transitions between L0 state and L1 or L2
                 states.
                 If retransmission is used in a given transmit direction, this
                 parameter reports the previous Expected Throughput(ETR)
                 (as defined in G.998.4) the bearer channel was operating at just
                 before the latest ETR change event occurred, excluding all
                 transitions between L0 state and L1 or L2 states.
                 The data rate is coded in steps of 1000 bit/s.
                 The invalid value is 4294967295. If data on the port is invalid
                 or no data is generated on the port because the port has not
                 been activated, the invalid value will be returned.
                 Unit: bits/second
                "
            REFERENCE    "ITU-T G.997.1, paragraph 7.5.2.2"
            ::= { hwOntXdslChannelStatusEntry 4 }

         hwOntXdslChStatusActDelay  OBJECT-TYPE
            SYNTAX      Unsigned32(0..8176 | 4294967295)
            UNITS       "milliseconds"
            MAX-ACCESS  read-only
            STATUS      current
            DESCRIPTION
                "If retransmission is not used in a given transmit direction, this
                 parameter is the actual one-way interleaving delay introduced by
                 the PMS-TC excluding delay in L1 and L2 state. In L1 and L2 state,
                 the parameter contains the interleaving delay in the previous L0
                 state.
                 If retransmission is used in a given transmit direction, this
                 parameter specifies the actual value of the time-independent
                 component of the delay due to retransmission only.
                 It is coded in ms (rounded to the nearest ms).
                 The invalid value is 4294967295. If data on the port is invalid
                 or no data is generated on the port because the port has not
                 been activated, the invalid value will be returned.
                 Unit: milliseconds
                "
            REFERENCE    "ITU-T G.997.1, paragraph 7.5.2.3"
            ::= { hwOntXdslChannelStatusEntry 5 }

        hwOntXdslChStatusINP OBJECT-TYPE
            SYNTAX      Unsigned32(0..255 | 4294967295)
            UNITS       "0.1 DMT symbol"
            MAX-ACCESS  read-only
            STATUS      current
            DESCRIPTION
                "If retransmission is not used in a given transmit direction, this
                 parameter reports the actual impulse noise protection (INP) on the
                 bearer channel in the L0 state. In the L1 or L2 state, the parameter
                 contains the INP in the previous L0 state.
                 If retransmission is used in a given transmit direction, this parameter
                 reports the actual impulse noise protection (INP) against SHINE on
                 the bearer channel in the L0 state. In the L2 state, the parameter
                 contains the INP in the previous L0 state.
                 The value is coded in fractions of DMT symbols with a granularity of 0.1 symbols.
                 The value 255 indicates the INP is higher than 25.4.
                 The invalid value is 4294967295. If data on the port is invalid or no
                 data is generated on the port because the port has not been activated,
                 the invalid value will be returned.
                 Unit: 0.1 DMT symbol
                "
            REFERENCE    "ITU-T G.997.1, paragraph 7.5.2.9"
            ::= { hwOntXdslChannelStatusEntry 6 }


        --       hwOntXdslSCStatusBandTable
        hwOntXdslSCStatusBandTable  OBJECT-TYPE
            SYNTAX      SEQUENCE  OF  HwOntXdslSCStatusBandEntry
            MAX-ACCESS  not-accessible
            STATUS      current
            DESCRIPTION
                "The table hwOntXdslSCStatusBandTable contains
                 sub-carrier status parameters for VDSL2/ADSL/ADSL2/ADSL2+
     and FAST that are grouped per-band.
                 For ADSL/ADSL2/ADSL2+, there is a single
                 upstream band and a single downstream band.
                 for XDSL, there are several downstream bands and
                 several upstream bands.
                 The indexes of this table are ifIndex, hwOntObjectIndex, hwOntUniPhyType, hwOntXdslPortid and hwOntXdslSCStatusBand.
                "
            ::= { hwXdslStatus 8 }

        hwOntXdslSCStatusBandEntry  OBJECT-TYPE
            SYNTAX      HwOntXdslSCStatusBandEntry
            MAX-ACCESS  not-accessible
            STATUS      current
            DESCRIPTION
                "The table hwOntXdslSCStatusBandTable contains
                 sub-carrier status parameters for VDSL2/ADSL/ADSL2/ADSL2+
     and FAST that are grouped per-band.
                 For ADSL/ADSL2/ADSL2+, there is a single
                 upstream band and a single downstream band.
                 for XDSL, there are several downstream bands and
                 several upstream bands.
                 The indexes of this entry are ifIndex, hwOntObjectIndex, hwOntUniPhyType, hwOntXdslPortid and hwOntXdslSCStatusBand.
                "
            INDEX  { ifIndex, hwOntObjectIndex, hwOntUniPhyType, hwOntXdslPortid, hwOntXdslSCStatusBand }
            ::= { hwOntXdslSCStatusBandTable 1 }

        HwOntXdslSCStatusBandEntry  ::=
            SEQUENCE {
              hwOntXdslSCStatusBand                 HwXdslBand,
              hwOntXdslSCStatusBandLnAtten          Unsigned32,
              hwOntXdslSCStatusBandSigAtten         Unsigned32,
              hwOntXdslSCStatusBandSnrMargin        Integer32
            }

        hwOntXdslSCStatusBand OBJECT-TYPE
            SYNTAX      HwXdslBand
            MAX-ACCESS  not-accessible
            STATUS      current
            DESCRIPTION
                "The transmission band.
                 Identifies a band in a VDSL2/ADSL/ADSL2/ADSL2+ and FAST link.
                 For a band in the upstream direction, transmission is from
                 the remote end (xTU-R) towards the central office end (xTU-C).
                 A band in the upstream direction is indicated by upstream(1)
                 for ADSL/ADSL2/ADSL2+ single band, or any of us0(3), us1(5),
                 us2(7), us3(9), or us4(11) for XDSL multiple bands.
                 For a band in the downstream direction, transmission is from
                 the xTU-C towards the xTU-R. A band in the downstream
                 direction is indicated by downstream(2) for ADSL/ADSL2/ADSL2+
                 single band, or any of ds1(4), ds2(6), ds3(8), or ds4(10) for
                 XDSL multiple bands.
                "
            ::= { hwOntXdslSCStatusBandEntry 1 }

        hwOntXdslSCStatusBandLnAtten  OBJECT-TYPE
            SYNTAX      Unsigned32 (0..1270 | 2147483646 | 2147483647)
            UNITS       "0.1 dB"
            MAX-ACCESS  read-only
            STATUS      current
            DESCRIPTION
                "When referring to a band in the downstream direction, it is
                 the measured difference in the total power transmitted by the
                 xTU-C and the total power received by the xTU-R over all
                 sub-carriers during diagnostics mode.
                 When referring to a band in the upstream direction, it is the
                 measured difference in the total power transmitted by the xTU-R
                 and the total power received by the xTU-C over all sub-carriers
                 during diagnostics mode.
                 It ranges from 0 to 1270 units of 0.1 dB (Physical values are
                 0 to 127 dB).
                 A special value of 0x7FFFFFFF (2147483647) indicates the line
                 attenuation is out of range to be represented.
                 A special value of 0x7FFFFFFE (2147483646) indicates the line
                 attenuation measurement is unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.6 (LATNds)
                        and paragraph #7.5.1.7 (LATNus)"
            ::= { hwOntXdslSCStatusBandEntry 2 }

        hwOntXdslSCStatusBandSigAtten  OBJECT-TYPE
            SYNTAX      Unsigned32 (0..1270 | 2147483646 | 2147483647)
            UNITS       "0.1 dB"
            MAX-ACCESS  read-only
            STATUS      current
            DESCRIPTION
                "When referring to a band the downstream direction, it is the
                 measured difference in the total power transmitted by the
                 xTU-C and the total power received by the xTU-R over all sub
                 carriers during Showtime after the diagnostics mode.
                 When referring to the upstream direction, it is the measured
                 difference in the total power transmitted by the
                 xTU-R and the total power received by the xTU-C over all sub
                 carriers during Showtime after the diagnostics mode.
                 It ranges from 0 to 1270 units of 0.1 dB (Physical values
                 are 0 to 127 dB).
                 A special value of 0x7FFFFFFF (2147483647) indicates the line
                 attenuation is out of range to be represented.
                 A special value of 0x7FFFFFFE (2147483646) indicates the line
                 attenuation measurement is unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.8 (SATNds)
                        and paragraph #7.5.1.9 (SATNus)"
            ::= { hwOntXdslSCStatusBandEntry 3 }

        hwOntXdslSCStatusBandSnrMargin  OBJECT-TYPE
            SYNTAX      Integer32 (-640..630 | 2147483646 | 2147483647)
            UNITS       "0.1 dB"
            MAX-ACCESS  read-only
            STATUS      current
            DESCRIPTION
                "SNR Margin is the maximum increase in dB of the noise power
                 received at the XTU (xTU-R on downstream direction and xTU-C
                 on upstream direction), such that the BER requirements are met
                 for all bearer channels received at the XTU.  It ranges from
                 -640 to 630 units of 0.1 dB (Physical values are -64 to
                 63 dB).
                 A special value of 0x7FFFFFFF (2147483647) indicates the
                 SNR Margin is out of range to be represented.
                 A special value of 0x7FFFFFFE (2147483646) indicates the
                 SNR Margin measurement is currently unavailable.
                 This object reflects the value of the parameter following the
                 most recent DELT performed on the associated line.  Once
                 the DELT process is over, the parameter no longer changes
                 until the row is deleted or a new DELT process is initiated.
                 Unit: 0.1 dB
                "
            REFERENCE  "ITU-T G.997.1, paragraph #7.5.1.10 (SNRMds)
                        and paragraph #7.5.1.11 (SNRMus)"
            ::= { hwOntXdslSCStatusBandEntry 4 }

        hwXdslSCFextTable  OBJECT-TYPE
            SYNTAX      SEQUENCE  OF  HwXdslSCFextEntry
            MAX-ACCESS  not-accessible
            STATUS      current
            DESCRIPTION
                "The table hwXdslSCFextTable contains FEXT coupling function parameters.
                 The indexes of this table are ifIndex, hwXdslSCFextFromIfindex,
                 hwXdslSCFextRequestXLinScGroupSize and hwXdslSCFextSegment,the ifType of
                 ifIndex and hwXdslSCFextFromIfindex must be same.
                "
            ::= { hwXdslStatus 9 }

        hwXdslSCFextEntry  OBJECT-TYPE
            SYNTAX      HwXdslSCFextEntry
            MAX-ACCESS  not-accessible
            STATUS      current
            DESCRIPTION
                "The table hwXdslSCFextTable contains FEXT coupling function parameters.
                 The indexes of this entry are ifIndex, hwXdslSCFextFromIfindex,
                 hwXdslSCFextRequestXLinScGroupSize and hwXdslSCFextSegment,the ifType of
                 ifIndex and hwXdslSCFextFromIfindex must be same.
                "
            INDEX  { ifIndex,
                     hwXdslSCFextFromIfindex,
                     hwXdslSCFextRequestXLinScGroupSize,
                     hwXdslSCFextSegment
                   }
            ::= { hwXdslSCFextTable 1 }

        HwXdslSCFextEntry  ::=
            SEQUENCE {
              hwXdslSCFextFromIfindex                   Integer32,
              hwXdslSCFextRequestXLinScGroupSize        Unsigned32,
              hwXdslSCFextSegment                       Unsigned32,
              hwXdslSCFextXLinScaleDs                   Unsigned32,
              hwXdslSCFextXlinScGroupSizeDs             Unsigned32,
              hwXdslSCFextXLinBandDs                    OCTET STRING,
              hwXdslSCFextXlinRealDs                    OCTET STRING,
              hwXdslSCFextXlinImgDs                     OCTET STRING,
              hwXdslSCFextXLinScaleUs                   Unsigned32,
              hwXdslSCFextXlinScGroupSizeUs             Unsigned32,
              hwXdslSCFextXLinBandUs                    OCTET STRING,
              hwXdslSCFextXlinRealUs                    OCTET STRING,
              hwXdslSCFextXlinImgUs                     OCTET STRING
            }

        hwXdslSCFextFromIfindex  OBJECT-TYPE
            SYNTAX      Integer32
            MAX-ACCESS  not-accessible
            STATUS      current
            DESCRIPTION
                "The hwXdslSCFextFromIfindex is an interface index where the
                 interface has an ifType of G.fast(279) or vdsl2(251).
                "
           ::= { hwXdslSCFextEntry 1 }

        hwXdslSCFextRequestXLinScGroupSize  OBJECT-TYPE
            SYNTAX      Unsigned32(1 | 2 | 4 | 8 | 16 | 32 | 64)
            MAX-ACCESS  not-accessible
            STATUS      current
            DESCRIPTION
                "This parameter is the requested value of XLING.
                 The valid values are 1, 2, 4, 8, 16, 32, and 64.
                "
            REFERENCE  "ITU-T G.997.1, paragraph #7.5.1.38.3 and #7.5.1.38.8"
            ::= { hwXdslSCFextEntry 2 }

        hwXdslSCFextSegment  OBJECT-TYPE
            SYNTAX      Unsigned32(1..8)
            MAX-ACCESS  not-accessible
            STATUS      current
            DESCRIPTION
                "The segment of the XLING information provided by this row.
                 Several XLING parameters in this table
                 are retrieved in segments. The first segment
                 of the XLING parameter is retrieved with
                 hwXdslSCFextSegment=1, the second segment
                 is retrieved with hwXdslSCFextSegment=2, and
                 so on.
                "
           ::= { hwXdslSCFextEntry 3 }

        hwXdslSCFextXLinScaleDs  OBJECT-TYPE
            SYNTAX      Unsigned32
            MAX-ACCESS  read-only
            STATUS      current
            DESCRIPTION
                "This parameter is the scale factor to be applied to the downstream
                 Xlinpsds values. It is represented as an unsigned integer
                 in the range from 1 to 2^16 - 1.
                 It's available for the first segment, other segments return 4294967295.
                "
            REFERENCE  "ITU-T G.997.1, paragraph #7.5.1.38.1 "
            ::= { hwXdslSCFextEntry 4 }

        hwXdslSCFextXlinScGroupSizeDs  OBJECT-TYPE
            SYNTAX      Unsigned32(1 | 2 | 4 | 8 | 16 | 32 | 64)
            MAX-ACCESS  read-only
            STATUS      current
            DESCRIPTION
                "This parameter is the number of subcarriers per group used
                 to report Xlinpsds. The valid values are 1, 2, 4, 8, 16, 32,
                 and 64. XLINGds should equal the sub-sampling factor used to
                 estimate the crosstalk channel for cancellation.
                 It's available for the first segment, other segments return 4294967295.
                "
            REFERENCE  "ITU-T G.997.1, paragraph #7.5.1.38.2"
            ::= { hwXdslSCFextEntry 5 }

        hwXdslSCFextXLinBandDs  OBJECT-TYPE
            SYNTAX      OCTET STRING  (SIZE(0..96))
            MAX-ACCESS  read-only
            STATUS      current
            DESCRIPTION
                "XLINBANDSds contains pairs of (start_subcarrier_index, stop_subcarrier_index)
                 for every band in which XLINpsds is reported.
                 It's available for the first segment, other segments return zero-length string.
                "
            REFERENCE  "ITU-T G.997.1, paragraph #7.5.1.38.4"
            ::= { hwXdslSCFextEntry 6 }

        hwXdslSCFextXlinRealDs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5 "
            ::= { hwXdslSCFextEntry 7 }

        hwXdslSCFextXlinImgDs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5"
            ::= { hwXdslSCFextEntry 8 }

        hwXdslSCFextXLinScaleUs  OBJECT-TYPE
            SYNTAX      Unsigned32
            MAX-ACCESS  read-only
            STATUS      current
            DESCRIPTION
                "This parameter is the scale factor to be applied to the upstream
                 Xlinpsus values. It is represented as an unsigned integer
                 in the range from 1 to 2^16 - 1.
                "
            REFERENCE  "ITU-T G.997.1, paragraph #7.5.1.38.6"
            ::= { hwXdslSCFextEntry 9 }

        hwXdslSCFextXlinScGroupSizeUs  OBJECT-TYPE
            SYNTAX      Unsigned32(1 | 2 | 4 | 8 | 16 | 32 | 64)
            MAX-ACCESS  read-only
            STATUS      current
            DESCRIPTION
                "This parameter is the number of subcarriers per group used
                 to report Xlinpsus. The valid values are 1, 2, 4, 8, 16, 32,
                 and 64. XLINGus should equal the sub-sampling factor used to
                 estimate the crosstalk channel for cancellation.
                "
            REFERENCE  "ITU-T G.997.1, paragraph #7.5.1.38.7"
            ::= { hwXdslSCFextEntry 10 }

        hwXdslSCFextXLinBandUs  OBJECT-TYPE
            SYNTAX      OCTET STRING  (SIZE(0..96))
            MAX-ACCESS  read-only
            STATUS      current
            DESCRIPTION
                "XLINBANDSus contains pairs of (start_subcarrier_index, stop_subcarrier_index)
                 for every band in which XLINpsus is reported.
                "
            REFERENCE  "ITU-T G.997.1, paragraph #7.5.1.38.9"
            ::= { hwXdslSCFextEntry 11 }

        hwXdslSCFextXlinRealUs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"
            ::= { hwXdslSCFextEntry 12 }

        hwXdslSCFextXlinImgUs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"

            ::= { hwXdslSCFextEntry 13 }

        --       hwOntXdslSCStatusSegmentTable
        hwOntXdslSCStatusSegmentTable  OBJECT-TYPE
            SYNTAX      SEQUENCE  OF  HwOntXdslSCStatusSegmentEntry
            MAX-ACCESS  not-accessible
            STATUS      current
            DESCRIPTION
                "The table hwOntXdslSCStatusSegmentTable contains status parameters
                 of ONT VDSL2 sub-carriers. Several objects in the table refer to
                 NSus and NSds. For G.993.2, the value of NSus and NSds are
                 respectively the indices of the highest supported upstream and
                 downstream subcarriers according to the selected implementation
                 profile. For ONT VDSL2, NSus is equal to NSCus-1 and NSds is equal
                 to NSCds-1. The indexes of this table are ifIndex, hwOntObjectIndex,
                 hwOntUniPhyType, hwOntXdslPortid, hwOntXdslSCStatusDirection and
                 hwOntXdslSCStatusSegment.
                 The first index of this entry is an interface index where the
                 interface has an ifType of ONT VDSL2. The second index of this
                 entry is ONT ID. The third index of this entry is the physical
                 type of ONT UNI. The fourth index of this entry is the ONT XDSL
                 port ID. The fifth index of this entry is the transmission direction.
                 The sixth index identifiest the specific segment of the sub-carriers
                 status addressed.
                "
            ::= { hwXdslStatus 10 }

        hwOntXdslSCStatusSegmentEntry  OBJECT-TYPE
            SYNTAX      HwOntXdslSCStatusSegmentEntry
            MAX-ACCESS  not-accessible
            STATUS      current
            DESCRIPTION
                "The table hwOntXdslSCStatusSegmentTable contains status parameters
                 of ONT VDSL2 sub-carriers. Several objects in the table refer to
                 NSus and NSds. For G.993.2, the value of NSus and NSds are
                 respectively the indices of the highest supported upstream and
                 downstream subcarriers according to the selected implementation
                 profile. For ONT VDSL2, NSus is equal to NSCus-1 and NSds is equal
                 to NSCds-1. The indexes of this entry are ifIndex, hwOntObjectIndex,
                 hwOntUniPhyType, hwOntXdslPortid, hwOntXdslSCStatusDirection and
                 hwOntXdslSCStatusSegment.
                 The first index of this entry is an interface index where the
                 interface has an ifType of ONT VDSL2. The second index of this
                 entry is ONT ID. The third index of this entry is the physical
                 type of ONT UNI. The fourth index of this entry is the ONT XDSL
                 port ID. The fifth index of this entry is the transmission direction.
                 The sixth index identifiest the specific segment of the sub-carriers
                 status addressed.
                "


            INDEX  { ifIndex,
                     hwOntObjectIndex,
                     hwOntUniPhyType,
                     hwOntXdslPortid,
                     hwOntXdslSCStatusDirection,
                     hwOntXdslSCStatusSegment   }
            ::= { hwOntXdslSCStatusSegmentTable 1 }

        HwOntXdslSCStatusSegmentEntry  ::=
            SEQUENCE {
              hwOntXdslSCStatusDirection                HwXdslDirection,
              hwOntXdslSCStatusSegment                  Unsigned32,
              hwOntXdslSCStatusSegmentLinReal           OCTET STRING,
              hwOntXdslSCStatusSegmentLinImg            OCTET STRING,
              hwOntXdslSCStatusSegmentLog               OCTET STRING,
              hwOntXdslSCStatusSegmentQln               OCTET STRING,
              hwOntXdslSCStatusSegmentSnr               OCTET STRING,
              hwOntXdslSCStatusSegmentBitsAlloc         OCTET STRING,
              hwOntXdslSCStatusSegmentGainAlloc         OCTET STRING,
              hwOntXdslSCStatusSegmentTxPSD             OCTET STRING,
              hwOntXdslSCStatusSegmentSnrMargin         OCTET STRING,
              hwOntXdslSCStatusSegmentLogScGroupSize    Unsigned32,
              hwOntXdslSCStatusSegmentQlnScGroupSize    Unsigned32,
              hwOntXdslSCStatusSegmentLinScGroupSize    Unsigned32,
              hwOntXdslSCStatusSegmentSnrScGroupSize    Unsigned32
            }

        hwOntXdslSCStatusDirection  OBJECT-TYPE
            SYNTAX      HwXdslDirection
            MAX-ACCESS  not-accessible
            STATUS      current
            DESCRIPTION
                "The direction of the ONT sub-carrier either
                 upstream or downstream.
                "
            ::= { hwOntXdslSCStatusSegmentEntry 1 }

        hwOntXdslSCStatusSegment  OBJECT-TYPE
            SYNTAX      Unsigned32(1..16)
            MAX-ACCESS  not-accessible
            STATUS      current
            DESCRIPTION
                "The segment of the sub-carriers
                 status information provided by this
                 row.
                 Several status parameters in this table
                 are retrieved in segments. The first segment
                 of the status information is retrieved with
                 hwOntXdslSCStatusSegment=1, the second segment
                 is retrieved with hwOntXdslSCStatusSegment=2, and
                 so on. When any status parameter is retrieved
                 in n segments where n<16) then, for that
                 parameter, GET operations for the rest segment
                 numbers (n+1 to 16) are responded with a value
                 that indicates: No measurement could be done.
                "
           ::= { hwOntXdslSCStatusSegmentEntry 2 }

        hwOntXdslSCStatusSegmentLinReal  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the real component [referred here as
                 a(i)] of Hlin(f = i*Df) value for a particular sub-carrier group
                 index i (0 <= i < NS).
                 Hlin(f) is represented as ((scale/2^15)*((a(i)+j*b(i))/2^15)),
                 where scale is hwXdslSCStatusLinScale and a(i) and b(i)
                 [provided by the hwOntXdslSCStatusSegmentLinImg object] are in the
                 range (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { hwOntXdslSCStatusSegmentEntry 3 }

        hwOntXdslSCStatusSegmentLinImg  OBJECT-TYPE
            SYNTAX      OCTET STRING  (SIZE(0..1024))
            MAX-ACCESS  read-only
            STATUS      current
            DESCRIPTION
                "An array of up to 512 complex H(f) linear representation
                 values in linear scale for the respective transmission
                 direction.  It is designed to support up to 512 (downstream)
                 sub-carriers groups and can be retrieved in a single segment.
                 The number of utilized values on downstream direction depends
                 on NSds, and on upstream direction it depends on NSus.  This
                 value is referred here as NS.
                 Each array entry represents the imaginary component [referred
                 here as b(i)] of Hlin(f = i*Df) value for a particular sub-
                 carrier group index i (0 <= i < NS).
                 Hlin(f) is represented as ((scale/2^15)*((a(i)+j*b(i))/2^15)),
                 where scale is hwXdslSCStatusLinScale and a(i) [provided by
                 the hwOntXdslSCStatusSegmentLinReal object] and b(i) are in the range
                 (-2^15+1) to (+2^15-1).
                 A special value a(i)=b(i)= -2^15 indicates that no measurement
                 could be done for the sub-carriers group because it is out of
                 the passband or that the attenuation is out of range to be
                 represented.  This parameter is only available after a loop
                 diagnostic procedure.
                 Each value in this array is 16 bits wide and is stored in big
                 endian format.
                "
            REFERENCE  "ITU-T G.997.1, paragraph #7.5.1.26.3 (HLINpsds)
                        and paragraph #7.5.1.26.9 (HLINpsus)"
            ::= { hwOntXdslSCStatusSegmentEntry 4 }

        hwOntXdslSCStatusSegmentLog  OBJECT-TYPE
            SYNTAX      OCTET STRING  (SIZE(0..1024))
            UNITS       "dB"
            MAX-ACCESS  read-only
            STATUS      current
            DESCRIPTION
                "An array of up to 512 real H(f) logarithmic representation
                 values in dB for the respective transmission direction.  It is
                 designed to support up to 512 (downstream) sub-carriers groups
                 and can be retrieved in a single segment.
                 The number of utilized values on downstream direction depends
                 on NSds, and on upstream direction it depends on NSus.  This
                 value is referred here as NS.
                 Each array entry represents the real Hlog(f = i*Df) value for a
                 particular sub-carrier group index i, (0 <= i < NS).
                 The real Hlog(f) value is represented as (6-m(i)/10), with m(i)
                 in the range 0 to 1022.  A special value m=1023 indicates that
                 no measurement could be done for the sub-carrier group because
                 it is out of the passband or that the attenuation is out of
                 range to be represented.  This parameter is applicable in loop
                 diagnostic procedure and initialization.
                 Each value in this array is 16 bits wide and is stored
                 in big endian format.
                 Unit: dB
                "
            REFERENCE  "ITU-T G.997.1, paragraph #7.5.1.26.6 (HLOGpsds)
                        and paragraph #7.5.1.26.12 (HLOGpsus)"
            ::= { hwOntXdslSCStatusSegmentEntry 5 }

        hwOntXdslSCStatusSegmentQln  OBJECT-TYPE
            SYNTAX      OCTET STRING  (SIZE(0..512))
            UNITS       "dBm/Hz"
            MAX-ACCESS  read-only
            STATUS      current
            DESCRIPTION
                "An array of up to 512 real Quiet Line Noise values in dBm/Hz
                 for the respective transmission direction.  It is designed for
                 up to 512 (downstream) sub-carriers groups and can be retrieved
                 in a single segment.
                 The number of utilized values on downstream direction depends
                 on NSds, and on upstream direction it depends on NSus.  This
                 value is referred here as NS.
                 Each array entry represents the QLN(f = i*Df) value for a
                 particular sub-carrier index i, (0 <= i < NS).
                 The QLN(f) is represented as ( -23-n(i)/2)(if the line is activated
                 as G9701 of hwXdslLineStatusXtuTransSys
                 it is represented as ( -33-n(i)/2)), with n(i) in the
                 range 0 to 254.  A special value n(i)=255 indicates that no
                 measurement could be done for the sub-carrier group because it
                 is out of the passband or that the noise PSD is out of range
                 to be represented.
                 This parameter is applicable in loop diagnostic procedure and
                 initialization.  Each value in this array is 8 bits wide.
                 Unit: dBm/Hz
                "
            REFERENCE  "ITU-T G.997.1, paragraph #7.5.1.27.3 (QLNpsds)
                        and paragraph #7.5.1.27.6 (QLNpsus)"
            ::= { hwOntXdslSCStatusSegmentEntry 6 }

        hwOntXdslSCStatusSegmentSnr  OBJECT-TYPE
            SYNTAX      OCTET STRING  (SIZE(0..512))
            UNITS       "dB"
            MAX-ACCESS  read-only
            STATUS      current
            DESCRIPTION
                "The SNR Margin per sub-carrier group, expressing the
                 ratio between the received signal power and received noise
                 power per sub-scriber group.  It is an array of 512 octets,
                 designed for supporting up to 512 (downstream) sub-carriers
                 groups and can be retrieved in a single segment.
                 The number of utilized octets on downstream direction depends
                 on NSds, and on upstream direction it depends on NSus.  This
                 value is referred here as NS.
                 Octet i (0 <= i < NS) is set to a value in the range 0 to
                 254 to indicate that the respective downstream or upstream sub-
                 carrier group i has SNR of: (-32 + hwOntXdslSCStatusSegmentSnr(i)/2)
                 in dB (i.e., -32 to 95dB).
                 The special value 255 means that no measurement could be done
                 for the sub-carrier group because it is out of the PSD mask
                 passband or that the noise PSD is out of range to be
                 represented.  Each value in this array is 8 bits wide.
                 Unit: dB
                "
            REFERENCE    "ITU-T G.997.1, paragraph #7.5.1.28.3 (SNRpsds)
                          and paragraph #7.5.1.28.6 (SNRpsus)"
            ::= { hwOntXdslSCStatusSegmentEntry 7 }

        hwOntXdslSCStatusSegmentBitsAlloc  OBJECT-TYPE
            SYNTAX      OCTET STRING  (SIZE(0..256))
            UNITS       "bits"
            MAX-ACCESS  read-only
            STATUS      current
            DESCRIPTION
                "The bits allocation per sub-carrier.  An array of 256 octets
                 (512 nibbles), designed for supporting up to 512 (downstream)
                 sub-carriers. When more then 512 sub-carriers are supported,
                 the status information is reported through multiple (up to 16)
                 segments. The first segment is then used for the first 512
                 sub-carriers. The second segment is used for the sub-carriers
                 512 to 1023 and so on.
                 The aggregate number of utilized nibbles on downstream direction
                 (in all segments) depends on NSds, and on upstream direction it
                 depends on NSus.
                 This value is referred here as NS. The segment number is in
                 hwOntXdslSCStatusSegment.
                 Nibble i (0 <= i < MIN(NS-(segment-1)*512,512)) in each
                 segment is set to a value in the range 0 to 15 to indicate that
                 the respective downstream or upstream sub-carrier j
                 (j=(segement-1)*512+i) has the same amount of bits
                 allocation.
                 Unit: bits
                "
            REFERENCE    "ITU-T G.997.1, paragraph #7.5.1.29.1 (BITSpsds)
                          and paragraph #7.5.1.29.2 (BITSpsus)"
            ::= { hwOntXdslSCStatusSegmentEntry 8 }

        hwOntXdslSCStatusSegmentGainAlloc  OBJECT-TYPE
            SYNTAX      OCTET STRING  (SIZE(0..1024))
            MAX-ACCESS  read-only
            STATUS      current
            DESCRIPTION
                "The gain allocation per sub-carrier.  An array of 512 16-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The aggregate number of utilized octets on downstream direction
                 depends on NSds, and on upstream direction it depends on NSus.
                 This value is referred here as NS. The segment number is in
                 hwOntXdslSCStatusSegment.
                 Value i (0 <= i < MIN(NS-(segment-1)*512,512)) in each
                 segment is set to a value in the range 0 to 4093 to indicate
                 that the respective downstream or upstream sub-carrier j
                 (j=(segement-1)*512+i) has the same amount of gain value.
                 The gain value is represented as a multiple of 1/512 on
                 linear scale.  Each value in this array is 16 bits wide and is
                 stored in big endian format.
                "
            REFERENCE    "ITU-T G.997.1, paragraph #7.5.1.29.3 (GAINSpsds)
                          and paragraph #7.5.1.29.4 (GAINSpsus)"
            ::= { hwOntXdslSCStatusSegmentEntry 9 }

        hwOntXdslSCStatusSegmentTxPSD  OBJECT-TYPE
            SYNTAX      OCTET STRING  (SIZE(0..1024))
            MAX-ACCESS  read-only
            STATUS      current
            DESCRIPTION
                "The TxPSD per sub-carrier. An array of 512 8-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The special value 0xffff means that no measurement could be done
                 for the sub-carrier group because it is out of the PSD mask
                 passband or that the noise PSD is out of range to be
                 represented. Each value in this array is 16 bits wide.
                 Unit: -0.5 dBm/Hz
                "
            ::= { hwOntXdslSCStatusSegmentEntry 65535 }

        hwOntXdslSCStatusSegmentSnrMargin  OBJECT-TYPE
            SYNTAX      OCTET STRING  (SIZE(0..1024))
            MAX-ACCESS  read-only
            STATUS      current
            DESCRIPTION
                "The SnrMargin per sub-carrier.  An array of 512 16-bits
                 values, designed for supporting up to 512 (downstream) sub-
                 carriers. When more then 512 sub-carriers are supported,
                 the status information is reported through multiple (up to 16)
                 segments. The first segment is then used for the first 512
                 sub-carriers. The second segment is used for the sub-carriers
                 512 to 1023 and so on.
                 The real value is represented as (hwOntXdslSCStatusSegmentSnrMargin/10).
                 The special value 0x7fff indicates that no measurement could be
                 done for the sub-carrier group because it is out of the passband
                 or that the noise PSD is out of range to be represented.
                 Each value in this array is 16 bits wide.
                 Unit: dB
                "
            ::= { hwOntXdslSCStatusSegmentEntry 65536 }

        hwOntXdslSCStatusSegmentLogScGroupSize  OBJECT-TYPE
            SYNTAX      Unsigned32(1 | 2 | 4 | 8 | 16 | 4294967295)
            MAX-ACCESS  read-only
            STATUS      current
            DESCRIPTION
                "Number of sub-carriers per group used to report the H(f)
                 logarithmic representation values for the respective
                 transmission direction. The valid values are 1, 2, 4, 8 and 16.
                 For ONT XDSL, it is equal to the size of a sub-carrier group
                 used to compute these parameters.
                 This parameter is only available after a loop diagnostic
                 procedure.
                 It's available for the first segment, other segments return
                 invalid value 4294967295.
                "
            REFERENCE  "ITU-T G.997.1, paragraph #7.5.1.26.2 (HLINGds)
                        and paragraph #7.5.1.26.8 (HLINGus)"
            ::= { hwOntXdslSCStatusSegmentEntry 65537 }

        hwOntXdslSCStatusSegmentQlnScGroupSize  OBJECT-TYPE
            SYNTAX      Unsigned32(1 | 2 | 4 | 8 | 16 | 4294967295)
            MAX-ACCESS  read-only
            STATUS      current
            DESCRIPTION
                "Number of sub-carriers per group used to report the Quiet
                 Line Noise values for the respective transmission direction.
                 The valid values are 1, 2, 4, 8 and 16.
                 For ONT XDSL, it is equal to the size of a sub-carrier group
                 used to compute these parameters.
                 This parameter is only available after a loop diagnostic
                 procedure.
                 It's available for the first segment, other segments return
                 invalid value 4294967295.
                "
            REFERENCE  "ITU-T G.997.1, paragraph #7.5.1.26.2 (HLINGds)
                         and paragraph #7.5.1.26.8 (HLINGus)"
            ::= { hwOntXdslSCStatusSegmentEntry 65538 }

        hwOntXdslSCStatusSegmentLinScGroupSize OBJECT-TYPE
            SYNTAX      Unsigned32(1 | 2 | 4 | 8 | 16 | 4294967295)
            MAX-ACCESS  read-only
            STATUS      current
            DESCRIPTION
                "Number of sub-carriers per group used to report the H(f)
                 linear representation values for the respective transmission
                 direction. The valid values are 1, 2, 4, 8 and 16.
                 For ONT XDSL, it is equal to the size of a sub-carrier group
                 used to compute these parameters.
                 This parameter is only available after a loop diagnostic
                 procedure.
                 It's available for the first segment, other segments return
                 invalid value 4294967295.
                "
            REFERENCE  "ITU-T G.997.1, paragraph #7.5.1.26.2 (HLINGds)
                          and paragraph #7.5.1.26.8 (HLINGus)"
            ::= { hwOntXdslSCStatusSegmentEntry 65539 }

        hwOntXdslSCStatusSegmentSnrScGroupSize  OBJECT-TYPE
            SYNTAX      Unsigned32(1 | 2 | 4 | 8 | 16 | 4294967295)
            MAX-ACCESS  read-only
            STATUS      current
            DESCRIPTION
                "Number of sub-carriers per group used to report the SNR
                 values on the respective transmission direction.
                 The valid values are 1, 2, 4, 8 and 16.
                 For ONT XDSL, it is equal to the size of a sub-carrier group
                 used to compute these parameters.
                 This parameter is only available after a loop diagnostic
                 procedure.
                 It's available for the first segment, other segments return
                 invalid value 4294967295.
                "
            REFERENCE  "ITU-T G.997.1, paragraph #7.5.1.26.2 (HLINGds)
                         and paragraph #7.5.1.26.8 (HLINGus)"
            ::= { hwOntXdslSCStatusSegmentEntry 65540 }
        --       hwXdslNlvSCFextTable
        hwXdslNlvSCFextTable  OBJECT-TYPE
            SYNTAX      SEQUENCE  OF  HwXdslNlvSCFextEntry
            MAX-ACCESS  not-accessible
            STATUS      current
            DESCRIPTION
                "The table hwXdslNlvSCFextTable contains FEXT coupling function parameters.
                 The indexes of this table are ifIndex, hwXdslNlvSCFextFromIfindex,
                 hwXdslNlvSCFextRequestXLinScGroupSize, hwXdslNlvSCFextSegment, hwXdslNlvSCFextVictimPeerId and hwXdslNlvSCFextDisturberPeerId,
                 the ifType of ifIndex and hwXdslNlvSCFextFromIfindex must be same.
                "
            ::= { hwXdslStatus 11 }

        hwXdslNlvSCFextEntry  OBJECT-TYPE
            SYNTAX      HwXdslNlvSCFextEntry
            MAX-ACCESS  not-accessible
            STATUS      current
            DESCRIPTION
                "The table hwXdslNlvSCFextTable contains FEXT coupling function parameters.
                 The indexes of this entry are ifIndex, hwXdslNlvSCFextFromIfindex,
                 hwXdslNlvSCFextRequestXLinScGroupSize, hwXdslNlvSCFextSegment, hwXdslNlvSCFextVictimPeerId and hwXdslNlvSCFextDisturberPeerId,
                 the ifType of ifIndex and hwXdslNlvSCFextFromIfindex must be same.
                "
            INDEX  { ifIndex,
                     hwXdslNlvSCFextFromIfindex,
                     hwXdslNlvSCFextRequestXLinScGroupSize,
                     hwXdslNlvSCFextSegment,
                     hwXdslNlvSCFextVictimPeerId,
                     hwXdslNlvSCFextDisturberPeerId
                   }
            ::= { hwXdslNlvSCFextTable 1 }

        HwXdslNlvSCFextEntry  ::=
            SEQUENCE {
              hwXdslNlvSCFextFromIfindex                   Integer32,
              hwXdslNlvSCFextRequestXLinScGroupSize        Unsigned32,
              hwXdslNlvSCFextSegment                       Unsigned32,
              hwXdslNlvSCFextVictimPeerId                  INTEGER,
              hwXdslNlvSCFextDisturberPeerId               INTEGER,
              hwXdslNlvSCFextXLinScaleDs                   Unsigned32,
              hwXdslNlvSCFextXlinScGroupSizeDs             Unsigned32,
              hwXdslNlvSCFextXLinBandDs                    OCTET STRING,
              hwXdslNlvSCFextXlinRealDs                    OCTET STRING,
              hwXdslNlvSCFextXlinImgDs                     OCTET STRING,
              hwXdslNlvSCFextXLinScaleUs                   Unsigned32,
              hwXdslNlvSCFextXlinScGroupSizeUs             Unsigned32,
              hwXdslNlvSCFextXLinBandUs                    OCTET STRING,
              hwXdslNlvSCFextXlinRealUs                    OCTET STRING,
              hwXdslNlvSCFextXlinImgUs                     OCTET STRING
            }

        hwXdslNlvSCFextFromIfindex  OBJECT-TYPE
            SYNTAX      Integer32
            MAX-ACCESS  not-accessible
            STATUS      current
            DESCRIPTION
                "The hwXdslNlvSCFextFromIfindex is an interface index where the
                 interface has an ifType of G.fast(279) or vdsl2(251).
                "
           ::= { hwXdslNlvSCFextEntry 1 }

        hwXdslNlvSCFextRequestXLinScGroupSize  OBJECT-TYPE
            SYNTAX      Unsigned32(1 | 2 | 4 | 8 | 16 | 32 | 64)
            MAX-ACCESS  not-accessible
            STATUS      current
            DESCRIPTION
                "This parameter is the requested value of XLING.
                 The valid values are 1, 2, 4, 8, 16, 32, and 64.
                "
            REFERENCE  "ITU-T G.997.1, paragraph #7.5.1.38.3 and #7.5.1.38.8"
            ::= { hwXdslNlvSCFextEntry 2 }

        hwXdslNlvSCFextSegment  OBJECT-TYPE
            SYNTAX      Unsigned32(1..8)
            MAX-ACCESS  not-accessible
            STATUS      current
            DESCRIPTION
                "The segment of the XLING information provided by this row.
                 Several XLING parameters in this table
                 are retrieved in segments. The first segment
                 of the XLING parameter is retrieved with
                 hwXdslNlvSCFextSegment=1, the second segment
                 is retrieved with hwXdslNlvSCFextSegment=2, and
                 so on.
                "
           ::= { hwXdslNlvSCFextEntry 3 }

        hwXdslNlvSCFextVictimPeerId  OBJECT-TYPE
            SYNTAX INTEGER
          {
              local(0)
          }
            MAX-ACCESS  not-accessible
            STATUS      current
            DESCRIPTION
                "The value of this object identifies the node level vectoring victim peer equipment.
                 the value only one is 0.
				 Options:
                 1. local(0)  - indicates local level
                "
           ::= { hwXdslNlvSCFextEntry 4 }

        hwXdslNlvSCFextDisturberPeerId  OBJECT-TYPE
            SYNTAX INTEGER
          {
              local(0),
              peer1(1),
              peer2(2)
          }
            MAX-ACCESS  not-accessible
            STATUS      current
            DESCRIPTION
                "The value of this object identifies the node level vectoring disturber peer equipment.
				Options:
                 1. local(0)  - indicates local level
                 2. peer1(1)  - indicates peer1 level
                 3. peer2(2)  - indicates peer2 level
                "
           ::= { hwXdslNlvSCFextEntry 5 }

        hwXdslNlvSCFextXLinScaleDs  OBJECT-TYPE
            SYNTAX      Unsigned32
            MAX-ACCESS  read-only
            STATUS      current
            DESCRIPTION
                "This parameter is the scale factor to be applied to the downstream
                 Xlinpsds values. It is represented as an unsigned integer
                 in the range from 1 to 2^16 - 1.
                 It's available for the first segment, other segments return 4294967295.
                "
            REFERENCE  "ITU-T G.997.1, paragraph #7.5.1.38.1 "
            ::= { hwXdslNlvSCFextEntry 6 }

        hwXdslNlvSCFextXlinScGroupSizeDs  OBJECT-TYPE
            SYNTAX      Unsigned32(1 | 2 | 4 | 8 | 16 | 32 | 64)
            MAX-ACCESS  read-only
            STATUS      current
            DESCRIPTION
                "This parameter is the number of subcarriers per group used
                 to report Xlinpsds. The valid values are 1, 2, 4, 8, 16, 32,
                 and 64. XLINGds should equal the sub-sampling factor used to
                 estimate the crosstalk channel for cancellation.
                 It's available for the first segment, other segments return 4294967295.
                "
            REFERENCE  "ITU-T G.997.1, paragraph #7.5.1.38.2"
            ::= { hwXdslNlvSCFextEntry 7 }

        hwXdslNlvSCFextXLinBandDs  OBJECT-TYPE
            SYNTAX      OCTET STRING  (SIZE(0..96))
            MAX-ACCESS  read-only
            STATUS      current
            DESCRIPTION
                "XLINBANDSds contains pairs of (start_subcarrier_index, stop_subcarrier_index)
                 for every band in which XLINpsds is reported.
                 It's available for the first segment, other segments return zero-length string.
                "
            REFERENCE  "ITU-T G.997.1, paragraph #7.5.1.38.4"
            ::= { hwXdslNlvSCFextEntry 8 }

        hwXdslNlvSCFextXlinRealDs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5 "
            ::= { hwXdslNlvSCFextEntry 9 }

        hwXdslNlvSCFextXlinImgDs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for downstream FEXT coupling
                 coefficients Xlinds(f) originating from the loop connected to the VCE
                 port k into the loop for which Xlinds(f) is being reported. Each array
                 entry represents the Xlinds(f = n*Df) value for a particular subcarrier
                 index n. The Xlinds(f = n*Df) value is represented as
                 ((XLINSCds/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinds
                 (f = n*Df) is ((XLINSCds/2^15) * (a(n)/2^15)).
                "
            REFERENCE  "ITU-T G.997.1, paragraph #7.5.1.38.5"
            ::= { hwXdslNlvSCFextEntry 10 }

        hwXdslNlvSCFextXLinScaleUs  OBJECT-TYPE
            SYNTAX      Unsigned32
            MAX-ACCESS  read-only
            STATUS      current
            DESCRIPTION
                "This parameter is the scale factor to be applied to the upstream
                 Xlinpsus values. It is represented as an unsigned integer
                 in the range from 1 to 2^16 - 1.
                "
            REFERENCE  "ITU-T G.997.1, paragraph #7.5.1.38.6"
            ::= { hwXdslNlvSCFextEntry 11 }

        hwXdslNlvSCFextXlinScGroupSizeUs  OBJECT-TYPE
            SYNTAX      Unsigned32(1 | 2 | 4 | 8 | 16 | 32 | 64)
            MAX-ACCESS  read-only
            STATUS      current
            DESCRIPTION
                "This parameter is the number of subcarriers per group used
                 to report Xlinpsus. The valid values are 1, 2, 4, 8, 16, 32,
                 and 64. XLINGus should equal the sub-sampling factor used to
                 estimate the crosstalk channel for cancellation.
                "
            REFERENCE  "ITU-T G.997.1, paragraph #7.5.1.38.7"
            ::= { hwXdslNlvSCFextEntry 12 }

        hwXdslNlvSCFextXLinBandUs  OBJECT-TYPE
            SYNTAX      OCTET STRING  (SIZE(0..96))
            MAX-ACCESS  read-only
            STATUS      current
            DESCRIPTION
                "XLINBANDSus contains pairs of (start_subcarrier_index, stop_subcarrier_index)
                 for every band in which XLINpsus is reported.
                "
            REFERENCE  "ITU-T G.997.1, paragraph #7.5.1.38.9"
            ::= { hwXdslNlvSCFextEntry 13 }

        hwXdslNlvSCFextXlinRealUs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"
            ::= { hwXdslNlvSCFextEntry 14 }

        hwXdslNlvSCFextXlinImgUs  OBJECT-TYPE
            SYNTAX      OCTET STRING  (SIZE(0..2048))
            MAX-ACCESS  read-only
            STATUS      current
            DESCRIPTION
                "An array of 512 32-bits values.
                 For each given VCE port index k, this parameter is a one-dimensional
                 array of complex values in linear scale for upstream FEXT coupling
                 coefficients Xlinus(f) originating from the loop connected to the VCE
                 port k into the loop for which Xlinus(f) is being reported. Each array
                 entry represents the Xlinus(f = n*Df) value for a particular subcarrier
                 index n. The Xlinus(f = n*Df) value is represented as
                 ((XLINSCus/2^15) * ((a(n) + j*b(n))/2^15)), where a(n) and b(n) are
                 signed integers in the (-2^15 + 1) to (+2^15 - 1) range. A special
                 value indicates that no measurement could be done from line k into this
                 line for subcarrier n. Another special value indicates that there is
                 no phase information and the magnitude of Xlinus
                 (f = n*Df) is ((XLINSCus/2^15) * (a(n)/2^15)).
                "
            REFERENCE  "ITU-T G.997.1, paragraph #7.5.1.38.10"

            ::= { hwXdslNlvSCFextEntry 15 }

        --       hwXdslLineInventoryTable
        hwXdslLineInventoryTable  OBJECT-TYPE
            SYNTAX      SEQUENCE  OF  HwXdslLineInventoryEntry
            MAX-ACCESS  not-accessible
            STATUS      current
            DESCRIPTION
                "The table hwXdslLineInventoryTable contains inventory of XDSL2
                 unit. The indexes of this table are ifIndex and hwXdslLInvUnit.
                "
            ::= { hwXdslInventory 1 }

        hwXdslLineInventoryEntry  OBJECT-TYPE
            SYNTAX      HwXdslLineInventoryEntry
            MAX-ACCESS  not-accessible
            STATUS      current
            DESCRIPTION
                "The table hwXdslLineInventoryTable contains inventory of XDSL2
                 unit. The indexes of this entry are ifIndex and hwXdslLInvUnit.
                "
            INDEX  { ifIndex, hwXdslLInvUnit }
            ::= { hwXdslLineInventoryTable 1 }

        HwXdslLineInventoryEntry  ::=
           SEQUENCE {
              hwXdslLInvUnit                      HwXdslUnit,
              hwXdslLInvG994VendorId              OCTET STRING,
              hwXdslLInvSystemVendorId            OCTET STRING,
              hwXdslLInvVersionNumber             OCTET STRING,
              hwXdslLInvSerialNumber              OCTET STRING,
              hwXdslLInvSelfTestResult            OCTET STRING,
              hwXdslLInvTransmissionCapabilities  HwXdslTransmissionModeType,
              hwXdslLInvModelId                   OCTET STRING,
              hwXdslLInvVdslLrSupport             INTEGER
           }

        hwXdslLInvUnit  OBJECT-TYPE
            SYNTAX      HwXdslUnit
            MAX-ACCESS  not-accessible
            STATUS      current
            DESCRIPTION
                "The termination unit XTUC{1} or XTUR{2}."
            ::= { hwXdslLineInventoryEntry 1 }

        hwXdslLInvG994VendorId  OBJECT-TYPE
            SYNTAX      OCTET STRING  (SIZE(0..8))
            MAX-ACCESS  read-only
            STATUS      current
            DESCRIPTION
                "The xTU G.994.1 Vendor ID as inserted in the G.994.1 CL/CLR
                 message.  It consists of 8 binary octets, including a country
                 code followed by a (regionally allocated) provider code, as
                 defined in Recommendation T.35.
                "
            REFERENCE    "ITU-T G.997.1(200604), paragraph 7.4"
            ::= { hwXdslLineInventoryEntry 2 }

        hwXdslLInvSystemVendorId  OBJECT-TYPE
            SYNTAX      OCTET STRING  (SIZE(0..8))
            MAX-ACCESS  read-only
            STATUS      current
            DESCRIPTION
                "The xTU System Vendor ID (identifies the xTU system
                 integrator) as inserted in the Overhead Messages (both xTUs
                 for G.992.3 and G.992.4) or in the Embedded Operations
                 Channel (only xTU-R in G.992.1 and G.992.2).  It consists of
                 8 binary octets, with same format as used for
                 hwXdslInvG994VendorId.
                "
            REFERENCE    "ITU-T G.997.1(200604), paragraph 7.4"
            ::= { hwXdslLineInventoryEntry 3 }

        hwXdslLInvVersionNumber  OBJECT-TYPE
            SYNTAX      OCTET STRING  (SIZE(0..16))
            MAX-ACCESS  read-only
            STATUS      current
            DESCRIPTION
                "The xTU version number (vendor specific information) as
                 inserted in the Overhead Messages (both xTUs for G.992.3 and
                 G.992.4) or in the Embedded Operations Channel (only xTU-R in
                 G.992.1 and G.992.2).  It consists of up to 16 binary octets.
                "
            REFERENCE    "ITU-T G.997.1(200604), paragraph 7.4"
            ::= { hwXdslLineInventoryEntry 4 }

        hwXdslLInvSerialNumber  OBJECT-TYPE
            SYNTAX      OCTET STRING  (SIZE(0..32))
            MAX-ACCESS  read-only
            STATUS      current
            DESCRIPTION
                "The xTU serial number (vendor specific information) as
                 inserted in the Overhead Messages (both xTUs for G.992.3 and
                 G.992.4) or in the Embedded Operations Channel (only xTU-R in
                 G.992.1 and G.992.2).  It is vendor specific information.  It
                 consists of up to 32 ASCII characters.
                "
            REFERENCE    "ITU-T G.997.1(200604), paragraph 7.4"
            ::= { hwXdslLineInventoryEntry 5 }

        hwXdslLInvSelfTestResult  OBJECT-TYPE
            SYNTAX      OCTET STRING  (SIZE(0..4))
            MAX-ACCESS  read-only
            STATUS      current
            DESCRIPTION
                "The xTU self-test result, coded as a 32-bit integer.  The
                 most significant octet of this object is '0' if the self-test
                 passed, and '1' if the self-test failed.  The interpretation
                 of the other octets is vendor discretionary.
                "
            REFERENCE    "ITU-T G.997.1(200604), paragraph 7.4"
            ::= { hwXdslLineInventoryEntry 6 }

        hwXdslLInvTransmissionCapabilities  OBJECT-TYPE
            SYNTAX      HwXdslTransmissionModeType
            MAX-ACCESS  read-only
            STATUS      current
            DESCRIPTION
                "The xTU transmission system capability list of the different
                 coding types.  It is coded in a bit-map representation with 1
                 or more bits set.  A bit set to '1' means that the xTU
                 supports the respective coding.  The value may be derived
                 from the handshaking procedures defined in G.994.1.  A set
                 of XDSL line transmission modes, with one bit per mode.
                "
            REFERENCE    "ITU-T G.997.1(200604), paragraph 7.4"
            ::= { hwXdslLineInventoryEntry 7 }

        hwXdslLInvModelId  OBJECT-TYPE
            SYNTAX      OCTET STRING  (SIZE(0..32))
            MAX-ACCESS  read-only
            STATUS      current
            DESCRIPTION
                "The XTU model ID."
            ::= { hwXdslLineInventoryEntry 8 }

        hwXdslLInvVdslLrSupport  OBJECT-TYPE
            SYNTAX INTEGER
                {
                 notsupported(0),
                 supported(1)
                }
            MAX-ACCESS  read-only
            STATUS      current
            DESCRIPTION
                "This parameter indicates the support of VDSL2-LR by the xTU.
                 The parameter is set to 0 if VDSL2-LR is not supported and set to 1 if VDSL2-LR is supported.
                 Options:
                 1. notsupported(0)  - VDSL2-LR is not supported
                 2. supported(1)     - VDSL2-LR is supported
                "
            ::= { hwXdslLineInventoryEntry 9 }

        --    hwOntXdslLineInventoryTable
        hwOntXdslLineInventoryTable  OBJECT-TYPE
            SYNTAX      SEQUENCE  OF  HwOntXdslLineInventoryEntry
            MAX-ACCESS  not-accessible
            STATUS      current
            DESCRIPTION
                "The table hwOntXdslLineInventoryTable contains inventory of XDSL unit.
                 The indexes of this table are ifIndex, hwOntObjectIndex,
                 hwOntUniPhyType, hwOntXdslPortid and hwOntXdslLInvUnit.
                "
            ::= { hwXdslInventory 2 }
        hwOntXdslLineInventoryEntry  OBJECT-TYPE
            SYNTAX      HwOntXdslLineInventoryEntry
            MAX-ACCESS  not-accessible
            STATUS      current
            DESCRIPTION
                "The table hwOntXdslLineInventoryTable contains inventory of XDSL unit.
                 The indexes of this entry are ifIndex, hwOntObjectIndex,
                 hwOntUniPhyType, hwOntXdslPortid and hwOntXdslLInvUnit.
                "
      INDEX  { ifIndex,
                     hwOntObjectIndex,
                     hwOntUniPhyType,
                     hwOntXdslPortid,
                     hwOntXdslLInvUnit }
            ::= { hwOntXdslLineInventoryTable 1 }

        HwOntXdslLineInventoryEntry  ::=
           SEQUENCE {
              hwOntXdslLInvUnit                      HwXdslUnit,
              hwOntXdslLInvG994VendorId              OCTET STRING,
              hwOntXdslLInvSystemVendorId            OCTET STRING,
              hwOntXdslLInvVersionNumber             OCTET STRING,
              hwOntXdslLInvSerialNumber              OCTET STRING,
              hwOntXdslLInvSelfTestResult            OCTET STRING,
              hwOntXdslLInvTransmissionCapabilities  HwXdslTransmissionModeType,
              hwOntXdslLInvModelId                OCTET STRING
           }
        hwOntXdslLInvUnit  OBJECT-TYPE
            SYNTAX      HwXdslUnit
            MAX-ACCESS  not-accessible
            STATUS      current
            DESCRIPTION
                "The termination unit XTUC{1} or XTUR{2}."
            ::= { hwOntXdslLineInventoryEntry 1 }
        hwOntXdslLInvG994VendorId  OBJECT-TYPE
            SYNTAX      OCTET STRING  (SIZE(0..8))
            MAX-ACCESS  read-only
            STATUS      current
            DESCRIPTION
                "The xTU G.994.1 Vendor ID as inserted in the G.994.1 CL/CLR
                 message.  It consists of 8 binary octets, including a country
                 code followed by a (regionally allocated) provider code, as
                 defined in Recommendation T.35.
                "
            REFERENCE    "ITU-T G.997.1(200604), paragraph 7.4"
            ::= { hwOntXdslLineInventoryEntry 2 }
        hwOntXdslLInvSystemVendorId  OBJECT-TYPE
            SYNTAX      OCTET STRING  (SIZE(0..8))
            MAX-ACCESS  read-only
            STATUS      current
            DESCRIPTION
                "The xTU System Vendor ID (identifies the xTU system
                 integrator) as inserted in the Overhead Messages (both xTUs
                 for G.992.3 and G.992.4) or in the Embedded Operations
                 Channel (only xTU-R in G.992.1 and G.992.2).  It consists of
                 8 binary octets, with same format as used for
                 hwXdslInvG994VendorId.
                "
            REFERENCE    "ITU-T G.997.1(200604), paragraph 7.4"
            ::= { hwOntXdslLineInventoryEntry 3 }
        hwOntXdslLInvVersionNumber  OBJECT-TYPE
            SYNTAX      OCTET STRING  (SIZE(0..16))
            MAX-ACCESS  read-only
            STATUS      current
            DESCRIPTION
                "The xTU version number (vendor specific information) as
                 inserted in the Overhead Messages (both xTUs for G.992.3 and
                 G.992.4) or in the Embedded Operations Channel (only xTU-R in
                 G.992.1 and G.992.2).  It consists of up to 16 binary octets.
                "
            REFERENCE    "ITU-T G.997.1(200604), paragraph 7.4"
            ::= { hwOntXdslLineInventoryEntry 4 }
        hwOntXdslLInvSerialNumber  OBJECT-TYPE
            SYNTAX      OCTET STRING  (SIZE(0..32))
            MAX-ACCESS  read-only
            STATUS      current
            DESCRIPTION
                "The xTU serial number (vendor specific information) as
                 inserted in the Overhead Messages (both xTUs for G.992.3 and
                 G.992.4) or in the Embedded Operations Channel (only xTU-R in
                 G.992.1 and G.992.2).  It is vendor specific information.  It
                 consists of up to 32 ASCII characters.
                "
            REFERENCE    "ITU-T G.997.1(200604), paragraph 7.4"
            ::= { hwOntXdslLineInventoryEntry 5 }
        hwOntXdslLInvSelfTestResult  OBJECT-TYPE
            SYNTAX      OCTET STRING  (SIZE(0..4))
            MAX-ACCESS  read-only
            STATUS      current
            DESCRIPTION
                "The xTU self-test result, coded as a 32-bit integer.  The
                 most significant octet of this object is '0' if the self-test
                 passed, and '1' if the self-test failed.  The interpretation
                 of the other octets is vendor discretionary.
                "
            REFERENCE    "ITU-T G.997.1(200604), paragraph 7.4"
            ::= { hwOntXdslLineInventoryEntry 6 }
        hwOntXdslLInvTransmissionCapabilities  OBJECT-TYPE
            SYNTAX      HwXdslTransmissionModeType
            MAX-ACCESS  read-only
            STATUS      current
            DESCRIPTION
                "The xTU transmission system capability list of the different
                 coding types.  It is coded in a bit-map representation with 1
                 or more bits set.  A bit set to '1' means that the xTU
                 supports the respective coding.  The value may be derived
                 from the handshaking procedures defined in G.994.1.  A set
                 of XDSL line transmission modes, with one bit per mode.
                "
            REFERENCE    "ITU-T G.997.1(200604), paragraph 7.4"
            ::= { hwOntXdslLineInventoryEntry 7 }
        hwOntXdslLInvModelId  OBJECT-TYPE
            SYNTAX      OCTET STRING  (SIZE(0..32))
            MAX-ACCESS  read-only
            STATUS      current
            DESCRIPTION
                "The XTU model ID."
            ::= { hwOntXdslLineInventoryEntry 8 }
        --       hwVdslLineConfTemplateTable
        hwVdslLineConfTemplateTable  OBJECT-TYPE
            SYNTAX      SEQUENCE  OF  HwVdslLineConfTemplateEntry
            MAX-ACCESS  not-accessible
            STATUS      current
            DESCRIPTION
                "The table hwVdslLineConfTemplateTable contains XDSL line
                 configuration template. The index of this table is
                 hwVdslLConfTempTemplateName.
                 A default template with an index of 'DEFVAL' will
                 always exist and its parameters will be set to vendor-specific
                 values, unless otherwise specified in this document.
                "
            ::= { hwXdslProfileLine 1 }

        hwVdslLineConfTemplateEntry  OBJECT-TYPE
            SYNTAX      HwVdslLineConfTemplateEntry
            MAX-ACCESS  not-accessible
            STATUS      current
            DESCRIPTION
                "The table hwVdslLineConfTemplateTable contains XDSL line
                 configuration template.
                 The index of this entry is hwVdslLConfTempTemplateName.
                 A default template with an index of 'DEFVAL' will
                 always exist and its parameters will be set to vendor-specific
                 values, unless otherwise specified in this document.
                "
            INDEX  { IMPLIED hwVdslLConfTempTemplateName }
            ::= { hwVdslLineConfTemplateTable 1 }

        HwVdslLineConfTemplateEntry  ::=
            SEQUENCE {
              hwVdslLConfTempTemplateName      OCTET STRING,
              hwVdslLConfTempLineProfile       OCTET STRING,
              hwVdslLConfTempChan1ConfProfile  OCTET STRING,
              hwVdslLConfTempChan1RaRatioDs    Unsigned32,
              hwVdslLConfTempChan1RaRatioUs    Unsigned32,
              hwVdslLConfTempChan2ConfProfile  OCTET STRING,
              hwVdslLConfTempChan2RaRatioDs    Unsigned32,
              hwVdslLConfTempChan2RaRatioUs    Unsigned32,
              hwVdslLConfTempChan3ConfProfile  OCTET STRING,
              hwVdslLConfTempChan3RaRatioDs    Unsigned32,
              hwVdslLConfTempChan3RaRatioUs    Unsigned32,
              hwVdslLConfTempChan4ConfProfile  OCTET STRING,
              hwVdslLConfTempChan4RaRatioDs    Unsigned32,
              hwVdslLConfTempChan4RaRatioUs    Unsigned32,
              hwVdslLConfTempRowStatus         RowStatus
           }

        hwVdslLConfTempTemplateName  OBJECT-TYPE
            SYNTAX      OCTET STRING (SIZE(1..32))
            MAX-ACCESS  accessible-for-notify
            STATUS      current
            DESCRIPTION
                "This object identifies a row in this table."
            REFERENCE    "DSL Forum TR-90, paragraph 5.1.4"
            ::= { hwVdslLineConfTemplateEntry 1 }

        hwVdslLConfTempLineProfile  OBJECT-TYPE
            SYNTAX      OCTET STRING (SIZE(1..32))
            MAX-ACCESS  read-create
            STATUS      current
            DESCRIPTION
                "The value of this object identifies the row in the XDSL Line
                 Configuration Profile Table, (hwVdslLineConfProfTable),
                 which applies for this XDSL line.
                "
            REFERENCE    "DSL Forum TR-90, paragraph 5.1.4"
            DEFVAL       { "DEFVAL" }
            ::= { hwVdslLineConfTemplateEntry 2 }

        hwVdslLConfTempChan1ConfProfile  OBJECT-TYPE
            SYNTAX      OCTET STRING (SIZE(1..32))
            MAX-ACCESS  read-create
            STATUS      current
            DESCRIPTION
                "The value of this object identifies the row in the XDSL2
                 Channel Configuration Profile Table,
                 (hwVdslChConfProfileTable) that applies to XDSL bearer
                 channel #1.  The channel profile name specified here must
                 match the name of an existing row in the
                 hwVdslChConfProfileTable table.
                "
            DEFVAL       { "DEFVAL" }
            ::= { hwVdslLineConfTemplateEntry 3 }

        hwVdslLConfTempChan1RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Downstream.  The ratio refers to the available
                 data rate in excess of the Minimum Data Rate, summed over all
                 bearer channels.  Also, the 100 -
                 hwVdslConfTemplateChan1RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 100 }
            ::= { hwVdslLineConfTemplateEntry 4 }

        hwVdslLConfTempChan1RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Upstream.  The ratio refers to the available
                 data rate in excess of the Minimum Data Rate, summed over all
                 bearer channels.  Also, the
                 100 - hwVdslLConfTempChan1RaRatioUs is the ratio of excess
                 data rate to be assigned to all other bearer channels on
                 Upstream direction.  The sum of rate adaptation ratios over
                 all bearers on the same direction shall be equal to 100 %.
                 Unit: percents
                "

            REFERENCE    "ITU-T G.997.1, paragraph 7.3.2.1"
            DEFVAL       { 100 }
            ::= { hwVdslLineConfTemplateEntry 5 }

        hwVdslLConfTempChan2ConfProfile  OBJECT-TYPE
            SYNTAX      OCTET STRING (SIZE(0..32))
            MAX-ACCESS  read-create
            STATUS      current
            DESCRIPTION
                "The value of this object identifies the row in the XDSL2
                 Channel Configuration Profile Table,
                 (hwVdslChConfProfileTable) that applies to XDSL bearer
                 channel #2.  If the channel is unused, then the object is set
                 to a zero length string.
                 This object may be set to a zero length string only if
                 hwVdslLConfTempChan3ConfProfile contains a zero length
                 string.
                "
            ::= { hwVdslLineConfTemplateEntry 6 }

        hwVdslLConfTempChan2RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Downstream.  The ratio refers to the available
                 data rate in excess of the Minimum Data Rate, summed over all
                 bearer channels.  Also, the
                 100 - hwVdslLConfTempChan2RaRatioDs is the ratio of excess
                 data rate to be assigned to all other bearer channels on
                 Downstream direction.  The sum of rate adaptation ratios
                 over all bearers on the same direction shall be equal to
                 100%.
                 Unit: percents
                "
            REFERENCE    "ITU-T G.997.1, paragraph 7.3.2.1"
            DEFVAL       { 0 }
            ::= { hwVdslLineConfTemplateEntry 7 }

        hwVdslLConfTempChan2RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Upstream.  The ratio refers to the available
                 data rate in excess of the Minimum Data Rate, summed over all
                 bearer channels.  Also, the
                 100 - hwVdslConfTemplateChan2RaRatioUs is the ratio of excess
                 data rate to be assigned to all other bearer channels on
                 Upstream direction.  The sum of rate adaptation ratios over
                 all bearers on the same direction shall be equal to 100 %.
                 Unit: percents
                "
            REFERENCE    "ITU-T G.997.1, paragraph 7.3.2.1"
            DEFVAL       { 0 }
            ::= { hwVdslLineConfTemplateEntry 8 }

        hwVdslLConfTempChan3ConfProfile  OBJECT-TYPE
            SYNTAX      OCTET STRING (SIZE(0..32))
            MAX-ACCESS  read-create
            STATUS      current
            DESCRIPTION
                "The value of this object identifies the row in the XDSL2
                 Channel Configuration Profile Table,
                 (hwVdslChConfProfileTable) that applies to XDSL bearer
                 channel #3.  If the channel is unused, then the object is set
                 to a zero length string.
                 This object may be set to a zero length string only if
                 hwVdslLConfTempChan4ConfProfile contains a zero length
                 string.
                 This object may be set to a non-zero length string only if
                 hwVdslLConfTempChan2ConfProfile contains a non-zero length
                 string.
                "
            ::= { hwVdslLineConfTemplateEntry 9 }

        hwVdslLConfTempChan3RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #3 when performing rate
                 adaptation on Downstream.  The ratio refers to the available
                 data rate in excess of the Minimum Data Rate, summed over all
                 bearer channels.  Also, the 100 -
                 hwVdslConfTemplateChan3RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 0 }
            ::= { hwVdslLineConfTemplateEntry 10 }

        hwVdslLConfTempChan3RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #3 when performing rate
                 adaptation on Upstream.  The ratio refers to the available
                 data rate in excess of the Minimum Data Rate, summed over all
                 bearer channels.  Also, the
                 100 - hwVdslLConfTempChan3RaRatioUs is the ratio of excess
                 data rate to be assigned to all other bearer channels on
                 Upstream direction.  The sum of rate adaptation ratios over
                 all bearers on the same direction shall be equal to 100%.
                 Unit: percents
                "
            REFERENCE    "ITU-T G.997.1, paragraph 7.3.2.1"
            DEFVAL       { 0 }
            ::= { hwVdslLineConfTemplateEntry 11 }

        hwVdslLConfTempChan4ConfProfile  OBJECT-TYPE
            SYNTAX      OCTET STRING (SIZE(0..32))
            MAX-ACCESS  read-create
            STATUS      current
            DESCRIPTION
                "The value of this object identifies the row in the XDSL2
                 Channel Configuration Profile Table
                 (hwVdslChConfProfileTableDs) that applies to XDSL bearer
                 channel #4.  If the channel is unused, then the object is set
                 to a zero length string.
                 This object may be set to a non-zero length string only if
                 hwVdslLConfTempChan3ConfProfile contains a non-zero length
                 string.
                "
            ::= { hwVdslLineConfTemplateEntry 12 }

        hwVdslLConfTempChan4RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #4 when performing rate
                 adaptation on Downstream.  The ratio refers to the available
                 data rate in excess of the Minimum Data Rate, summed over all
                 bearer channels.  Also, the 100 -
                 hwVdslLConfTempChan4RaRatioDs is the ratio of
                 excess data rate to be assigned to all other bearer channels.
                 The sum of rate adaptation ratios over all bearers on the same
                 direction shall sum to 100%.
                 Unit: percents
                "
            REFERENCE    "ITU-T G.997.1, paragraph 7.3.2.1"
            DEFVAL       { 0 }
            ::= { hwVdslLineConfTemplateEntry 13 }

        hwVdslLConfTempChan4RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #4 when performing rate
                 adaptation on Upstream.  The ratio refers to the available
                 data rate in excess of the Minimum Data Rate, summed over
                 all bearer channels.  Also, the 100 -
                 hwVdslLConfTempChan4RaRatioUs is the
                 ratio of excess data rate to be assigned to all other bearer
                 channels.  The sum of rate adaptation ratios over all bearers
                 on the same direction shall sum to 100%.
                 Unit: percents
                "
            REFERENCE    "ITU-T G.997.1, paragraph 7.3.2.1"
            DEFVAL       { 0 }
            ::= { hwVdslLineConfTemplateEntry 14 }

        hwVdslLConfTempRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwVdslLineConfTemplateEntry 15 }

        --        hwVdslLineConfProfTable
        HwXdslLineClockReferenceType ::= TEXTUAL-CONVENTION
            STATUS    current
            DESCRIPTION
                "The various clock references for the XDSL line.
                 Options:
                 1. freeRun(1)  - network timing reference clock mode is freeRun
                 2. system(2)   - network timing reference clock mode is system
                "
            SYNTAX    INTEGER
                   {
                   freeRun(1),
                   system(2)
                   }

        hwVdslLineConfProfTable  OBJECT-TYPE
            SYNTAX      SEQUENCE  OF  HwVdslLineConfProfEntry
            MAX-ACCESS  not-accessible
            STATUS      current
            DESCRIPTION
                "The table hwVdslLineConfProfTable contains XDSL line profile
                 configuration. The index of this table is hwVdslLConfProfProfileName.
                 A default profile with an index of 'DEFVAL' will
                 always exist and its parameters will be set to vendor-specific
                 values, unless otherwise specified in this document.
                "
            ::= { hwXdslProfileLine 2 }

        hwVdslLineConfProfEntry  OBJECT-TYPE
            SYNTAX      HwVdslLineConfProfEntry
            MAX-ACCESS  not-accessible
            STATUS      current
            DESCRIPTION
                "The table hwVdslLineConfProfTable contains XDSL line profile
                 configuration. The index of this entry is hwVdslLConfProfProfileName.
                 A default profile with an index of 'DEFVAL' will
                 always exist and its parameters will be set to vendor-specific
                 values, unless otherwise specified in this document.
                "
            INDEX  { IMPLIED hwVdslLConfProfProfileName }
            ::= { hwVdslLineConfProfTable 1 }

        HwVdslLineConfProfEntry  ::=
           SEQUENCE {
              hwVdslLConfProfProfileName          OCTET STRING,
              hwVdslLConfProfScMaskDs             HwXdslScMaskDs,
              hwVdslLConfProfScMaskUs             HwXdslScMaskUs,
              hwVdslLConfProfRfiBands             OCTET STRING,
              hwVdslLConfProfVDSLtoneblackout     OCTET STRING,
              hwVdslLConfProfRaModeDs             INTEGER,
              hwVdslLConfProfRaModeUs             INTEGER,
              hwVdslLConfProfRaUsNrmDs            Unsigned32,
              hwVdslLConfProfRaUsNrmUs            Unsigned32,
              hwVdslLConfProfRaUsTimeDs           Unsigned32,
              hwVdslLConfProfRaUsTimeUs           Unsigned32,
              hwVdslLConfProfRaDsNrmsDs           Unsigned32,
              hwVdslLConfProfRaDsNrmsUs           Unsigned32,
              hwVdslLConfProfRaDsTimeDs           Unsigned32,
              hwVdslLConfProfRaDsTimeUs           Unsigned32,
              hwVdslLConfProfTargetSnrmDs         Unsigned32,
              hwVdslLConfProfTargetSnrmUs         Unsigned32,
              hwVdslLConfProfMaxSnrmDs            Unsigned32,
              hwVdslLConfProfMaxSnrmUs            Unsigned32,
              hwVdslLConfProfMinSnrmDs            Unsigned32,
              hwVdslLConfProfMinSnrmUs            Unsigned32,
              hwVdslLConfProfMsgMinUs             Unsigned32,
              hwVdslLConfProfMsgMinDs             Unsigned32,
              hwVdslLConfProfXtuTransSysEna       HwXdslTransmissionModeType,
              hwVdslLConfProfPmMode               HwXdslLConfProfPmMode,
              hwVdslLConfProfL0Time               Unsigned32,
              hwVdslLConfProfL2Time               Unsigned32,
              hwVdslLConfProfL2Atpr               Unsigned32,
              hwVdslLConfProfL2Atprt              Unsigned32,
              hwVdslLConfProfDpboEpsd             HwXdslDpboEpsd,
              hwVdslLConfProfDpboEsel             Unsigned32,
              hwVdslLConfProfDpboEscm             HwXdslDpboEscm,
              hwVdslLConfProfDpboMus              Unsigned32,
              hwVdslLConfProfDpboFmin             Unsigned32,
              hwVdslLConfProfDpboFmax             Unsigned32,
              hwVdslLConfProfUpboPsdBand          HwXdslUpboPsdBand,
              hwVdslLConfProfUpboKl               Unsigned32,
              hwVdslLConfProfUpboKlf              HwXdslUpboKlf,
              hwVdslLConfProfRowStatus            RowStatus,
              hwVdslLConfProfBitSwapDs            HwXdslBitSwap,
              hwVdslLConfProfBitSwapUs            HwXdslBitSwap,
              hwVdslLConfProfUpboBoostMode        HwXdslUpboBoostMode,
              hwVdslLConfProfDpboEselMin          Unsigned32,
              hwVdslLConfProfUpboKl0RefBand       HwXdslUpboKl0RefBand,
              hwVdslLConfProfReferenceClock       HwXdslLineClockReferenceType,
              hwVdslLConfProfSosTimeDs            Unsigned32,
              hwVdslLConfProfSosTimeUs            Unsigned32,
              hwVdslLConfProfSosNtonesDs          Unsigned32,
              hwVdslLConfProfSosNtonesUs          Unsigned32,
              hwVdslLConfProfSosCrcDs             Unsigned32,
              hwVdslLConfProfSosCrcUs             Unsigned32,
              hwVdslLConfProfMaxSosDs             Unsigned32,
              hwVdslLConfProfMaxSosUs             Unsigned32,
              hwVdslLConfProfSnrmoffsetRocDs      Unsigned32,
              hwVdslLConfProfSnrmoffsetRocUs      Unsigned32,
              hwVdslLConfProfInpminRocDs          Unsigned32,
              hwVdslLConfProfInpminRocUs          Unsigned32,
              hwVdslLConfProfInmIatoDs            Unsigned32,
              hwVdslLConfProfInmIatsDs            Unsigned32,
              hwVdslLConfProfInmCcDs              Unsigned32,
              hwVdslLConfProfInmInpeqModeDs       Unsigned32,
              hwVdslLConfProfInmIatoUs            Unsigned32,
              hwVdslLConfProfInmIatsUs            Unsigned32,
              hwVdslLConfProfInmCcUs              Unsigned32,
              hwVdslLConfProfInmInpeqModeUs       Unsigned32,
              hwVdslLConfProfL3Time               Unsigned32,
              hwVdslLConfProfRtxModeDs            INTEGER,
              hwVdslLConfProfRtxModeUs            INTEGER,
              hwVdslLConfProfLeftrThreshDs        Unsigned32,
              hwVdslLConfProfLeftrThreshUs        Unsigned32,
              hwVdslLConfProfForceInpDs           TruthValue,
              hwVdslLConfProfForceInpUs           TruthValue,
              hwVdslLConfProfAeleMode             Unsigned32,
              hwVdslLConfProfUpboElmt             Unsigned32,
              hwVdslLconfProfUpboKlAuto           Unsigned32,
              hwVdslLConfProfLrMode               BITS
           }

        hwVdslLConfProfProfileName  OBJECT-TYPE
            SYNTAX      OCTET STRING (SIZE(1..32))
            MAX-ACCESS  accessible-for-notify
            STATUS      current
            DESCRIPTION
                "This object identifies a row in this table."
            ::= { hwVdslLineConfProfEntry 1 }

        hwVdslLConfProfScMaskDs  OBJECT-TYPE
            SYNTAX      HwXdslScMaskDs
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 all 1's).  Also note that if NSCds &lt; 512, all bits
                 i (NSCds i &lt;= 512) should be set to '1'.
                "
            REFERENCE    "ITU-T G.997.1, paragraph 7.3.1.2.6"
            ::= { hwVdslLineConfProfEntry 2 }

        hwVdslLConfProfScMaskUs  OBJECT-TYPE
            SYNTAX      HwXdslScMaskUs
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be all 1's).  Also note that if NSCus &lt;
                 64, all bits i (NSCus &lt; i &lt;= 64) should be set to '1'.
                "
            REFERENCE    "ITU-T G.997.1, paragraph 7.3.1.2.7"
            ::= { hwVdslLineConfProfEntry 3 }

        hwVdslLConfProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
            ::= { hwVdslLineConfProfEntry 4 }

        hwVdslLConfProfVDSLtoneblackout  OBJECT-TYPE
             SYNTAX      OCTET STRING(SIZE(0..79))
             MAX-ACCESS  read-create
             STATUS      current
             DESCRIPTION
                 "The subset of subcarrier mask that shall be
                  used to mask the subcarriers.
                  It is a string of bands consist of begin tone index
                  and end tone index.
                  for example :0-10,20-50,100-4095
                  It can contain as most as 8 bands.
                 "
             REFERENCE    "ITU-T G.997.1(200604), paragraph 7.3.1.2.8"
             ::= { hwVdslLineConfProfEntry 5 }

        hwVdslLConfProfRaModeDs  OBJECT-TYPE
            SYNTAX      INTEGER
                        {
                         manual(1),
                         rainit(2),
                         dynamic(3),
                         dynamicwithsos(4)
                        }
            MAX-ACCESS  read-create
            STATUS      current
            DESCRIPTION
                "The mode of operation of a rate-adaptive xTU-C in the transmit
                 direction.
                 Options:
                 1. manual(1)            - No Rate-Adaptation.  The initialization
                                           process attempts to synchronize to a
                                           specified rate
                 2. rainit(2)            - Rate-Adaptation during initialization process
                                           only, which attempts to synchronize to a rate
                                           between minimum and maximum specified values
                 3. dynamic(3)           - Rate-Adaptation during show time
                 4. dynamicwithsos(4)    - Rate-Adaptation during show time by SOS and SRA.
                                           In this mode, enabling of SOS and SRA is mandatory.

                "
            REFERENCE    "ITU-T G.997.1, paragraph 7.3.1.4.1"
            DEFVAL       { raInit }
            ::= { hwVdslLineConfProfEntry 6 }

        hwVdslLConfProfRaModeUs  OBJECT-TYPE
            SYNTAX      INTEGER
                        {
                         manual(1),
                         rainit(2),
                         dynamic(3),
                         dynamicwithsos(4)
                        }
            MAX-ACCESS  read-create
            STATUS      current
            DESCRIPTION
                "The mode of operation of a rate-adaptive xTU-R in the transmit
                 direction.
                 Options:
                 1. manual(1)            - No Rate-Adaptation.  The initialization
                                           process attempts to synchronize to a
                                           specified rate
                 2. rainit(2)            - Rate-Adaptation during initialization process
                                           only, which attempts to synchronize to a rate
                                           between minimum and maximum specified values
                 3. dynamic(3)           - Rate-Adaptation during show time
                 4. dynamicwithsos(4)    - Rate-Adaptation during show time by SOS and SRA.
                                           In this mode, enabling of SOS and SRA is mandatory.
                "
            REFERENCE    "ITU-T G.997.1, paragraph 7.3.1.4.2"
            DEFVAL       { raInit }
            ::= { hwVdslLineConfProfEntry 7 }

        hwVdslLConfProfRaUsNrmDs  OBJECT-TYPE
            SYNTAX      Unsigned32(0..310)
            UNITS       "0.1 dB"
            MAX-ACCESS  read-create
            STATUS      current
            DESCRIPTION
                "The Downstream Up-Shift Noise Margin value, to be used when
                 hwVdslLConfProfRaModeDs is set to DynamicRa.  If the downstream
                 noise margin is above this value and stays above it for
                 more than the time specified by the hwVdslLConfProfRaUsTimeDs,
                 the xTU-R shall attempt to increase the downstream net data
                 rate.  The Downstream Up-shift Noise Margin ranges from 0 to
                 310 units of 0.1 dB (Physical values are 0 to 31 dB).
                 Unit: 0.1 dB
                "
            REFERENCE    "ITU-T G.997.1, paragraph 7.3.1.4.3"
            DEFVAL       { 0 }
            ::= { hwVdslLineConfProfEntry 8 }

        hwVdslLConfProfRaUsNrmUs  OBJECT-TYPE
            SYNTAX      Unsigned32(0..310)
            UNITS       "0.1 dB"
            MAX-ACCESS  read-create
            STATUS      current
            DESCRIPTION
                "The Upstream Up-Shift Noise Margin value, to be used when
                 hwVdslLConfProfRaModeUs is set to DynamicRa.  If the upstream
                 noise margin is above this value and stays above it for more
                 than the time specified by the hwVdslLConfProfRaUsTimeUs, the
                 xTU-C shall attempt to increase the upstream net data rate.
                 The Upstream Up-shift Noise Margin ranges from 0 to 310 units
                 of 0.1 dB (Physical values are 0 to 31 dB).
                 Unit: 0.1 dB
                "
            REFERENCE    "ITU-T G.997.1, paragraph 7.3.1.4.4"
            DEFVAL       { 0 }
            ::= { hwVdslLineConfProfEntry 9 }

        hwVdslLConfProfRaUsTimeDs  OBJECT-TYPE
            SYNTAX      Unsigned32(0..16383)
            UNITS       "seconds"
            MAX-ACCESS  read-create
            STATUS      current
            DESCRIPTION
                "The Downstream Up-Shift Time Interval, to be used when
                 hwVdslLConfProfRaModeDs is set to DynamicRa.  The interval of
                 time that the downstream noise margin should stay above the
                 Downstream Up-shift Noise Margin before the xTU-R shall
                 attempt to increase the downstream net data rate.  The time
                 interval ranges from 0 to 16383 seconds.
                 Unit: seconds
                "
            REFERENCE    "ITU-T G.997.1, paragraph 7.3.1.4.5"
            DEFVAL       { 0 }
            ::= { hwVdslLineConfProfEntry 10 }

        hwVdslLConfProfRaUsTimeUs  OBJECT-TYPE
            SYNTAX      Unsigned32(0..16383)
            UNITS       "seconds"
            MAX-ACCESS  read-create
            STATUS      current
            DESCRIPTION
                "The Upstream Up-Shift Time Interval, to be used when
                 hwVdslLConfProfRaModeUs is set to DynamicRa.  The interval of
                 time the upstream noise margin should stay above the
                 Upstream Up-shift Noise Margin before the xTU-C shall
                 attempt to increase the upstream net data rate.
                 Unit: seconds
                "
            REFERENCE    "ITU-T G.997.1, paragraph 7.3.1.4.6"
            DEFVAL       { 0 }
            ::= { hwVdslLineConfProfEntry 11 }

        hwVdslLConfProfRaDsNrmsDs  OBJECT-TYPE
            SYNTAX      Unsigned32(0..310)
            UNITS       "0.1 dB"
            MAX-ACCESS  read-create
            STATUS      current
            DESCRIPTION
                "The Downstream Down-Shift Noise Margin value, to be used when
                 hwVdslLConfProfRaModeDs is set to DynamicRa.  If the downstream
                 noise margin is below this value and stays below that for more
                 than the time specified by the hwVdslLConfProfRaDsTimeDs, the
                 xTU-R shall attempt to decrease the downstream net data rate.
                 The Downstream Down-shift Noise Margin ranges from 0 to 310
                 units of 0.1 dB (Physical values are 0 to 31 dB).
                 Unit: 0.1 dB
                "
            REFERENCE    "ITU-T G.997.1, paragraph 7.3.1.4.7"
            DEFVAL       { 0 }
            ::= { hwVdslLineConfProfEntry 12 }

        hwVdslLConfProfRaDsNrmsUs  OBJECT-TYPE
            SYNTAX      Unsigned32(0..310)
            UNITS       "0.1 dB"
            MAX-ACCESS  read-create
            STATUS      current
            DESCRIPTION
                "The Upstream Down-shift Noise Margin value, to be used when
                 hwVdslLConfProfRaModeUs is set to DynamicRa.  If the upstream
                 noise margin is below this value and stays below that for more
                 than the time specified by the hwVdslLConfProfRaDsTimeUs, the
                 xTU-C shall attempt to decrease the upstream net data rate.
                 The Upstream Down-shift Noise Margin ranges from 0 to 310
                 units of 0.1 dB (Physical values are 0 to 31 dB).
                 Unit: 0.1 dB
                "
            REFERENCE    "ITU-T G.997.1, paragraph 7.3.1.4.8"
            DEFVAL       { 0 }
            ::= { hwVdslLineConfProfEntry 13 }

        hwVdslLConfProfRaDsTimeDs  OBJECT-TYPE
            SYNTAX      Unsigned32(0..16383)
            UNITS       "seconds"
            MAX-ACCESS  read-create
            STATUS      current
            DESCRIPTION
                "The Downstream Down-shift Time Interval, to be used when
                 hwVdslLConfProfRaModeDs is set to DynamicRa.  The interval of
                 time the downstream noise margin should stay below the
                 Downstream Down-shift Noise Margin before the xTU-R shall
                 attempt to decrease the downstream net data rate.
                 Unit: seconds
                "
            REFERENCE    "ITU-T G.997.1, paragraph 7.3.1.4.9"
            DEFVAL       { 0 }
            ::= { hwVdslLineConfProfEntry 14 }

        hwVdslLConfProfRaDsTimeUs  OBJECT-TYPE
            SYNTAX      Unsigned32(0..16383)
            UNITS       "seconds"
            MAX-ACCESS  read-create
            STATUS      current
            DESCRIPTION
                "The Upstream Down-Shift Time Interval, to be used when
                 hwVdslLConfProfRaModeUs is set to DynamicRa.  The interval of
                 time the upstream noise margin should stay below the Upstream
                 Down-shift Noise Margin before the xTU-C shall attempt to
                 decrease the upstream net data rate.
                 Unit: seconds
                "
            REFERENCE    "ITU-T G.997.1, paragraph 7.3.1.4.10"
            DEFVAL       { 0 }
            ::= { hwVdslLineConfProfEntry 15 }

        hwVdslLConfProfTargetSnrmDs  OBJECT-TYPE
            SYNTAX      Unsigned32(0..310)
            UNITS       "0.1 dB"
            MAX-ACCESS  read-create
            STATUS      current
            DESCRIPTION
                "The minimum Noise Margin the xTU-R receiver shall achieve,
                 relative to the BER requirement for each of the downstream
                 bearer channels, to successfully complete initialization.
                 The target noise margin ranges from 0 to 310 units of 0.1 dB
                 (Physical values are 0 to 31 dB).
                 Unit: 0.1 dB
                "
            REFERENCE    "ITU-T G.997.1, paragraph 7.3.1.3.1"
            DEFVAL       { 60 }
            ::= { hwVdslLineConfProfEntry 16 }

        hwVdslLConfProfTargetSnrmUs  OBJECT-TYPE
            SYNTAX      Unsigned32(0..310)
            UNITS       "0.1 dB"
            MAX-ACCESS  read-create
            STATUS      current
            DESCRIPTION
                "The minimum Noise Margin the xTU-C receiver shall achieve,
                 relative to the BER requirement for each of the upstream
                 bearer channels, to successfully complete initialization.
                 The target noise margin ranges from 0 to 310 units of 0.1 dB
                 (Physical values are 0 to 31 dB).
                 Unit: 0.1 dB
                "
            REFERENCE    "ITU-T G.997.1, paragraph 7.3.1.3.2"
            DEFVAL       { 60 }
            ::= { hwVdslLineConfProfEntry 17 }

        hwVdslLConfProfMaxSnrmDs  OBJECT-TYPE
            SYNTAX      Unsigned32
            UNITS       "0.1 dB"
            MAX-ACCESS  read-create
            STATUS      current
            DESCRIPTION
                "The maximum Noise Margin the xTU-R receiver shall try to
                 sustain. If the Noise Margin is above this level, the xTU-R
                 shall request that the xTU-C reduce the xTU-C transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.3"
            DEFVAL       { 300 }
            ::= { hwVdslLineConfProfEntry 18 }

        hwVdslLConfProfMaxSnrmUs  OBJECT-TYPE
            SYNTAX      Unsigned32
            UNITS       "0.1 dB"
            MAX-ACCESS  read-create
            STATUS      current
            DESCRIPTION
                "The maximum Noise Margin the xTU-C receiver shall try to
                 sustain. If the Noise Margin is above this level, the xTU-C
                 shall request that the xTU-R reduce the xTU-R transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.4"
            DEFVAL       { 300 }
            ::= { hwVdslLineConfProfEntry 19 }

        hwVdslLConfProfMinSnrmDs  OBJECT-TYPE
            SYNTAX      Unsigned32(0..310)
            UNITS       "0.1 dB"
            MAX-ACCESS  read-create
            STATUS      current
            DESCRIPTION
                "The minimum Noise Margin the xTU-R receiver shall tolerate.
                 If the noise margin falls below this level, the xTU-R shall
                 request that the xTU-C increase the xTU-C transmit power.
                 If an increase to xTU-C transmit power is not possible, a
                 loss-of-margin (LOM) defect occurs, the xTU-R shall fail and
                 attempt to reinitialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.5"
            DEFVAL       { 0 }
            ::= { hwVdslLineConfProfEntry 20 }

        hwVdslLConfProfMinSnrmUs  OBJECT-TYPE
            SYNTAX      Unsigned32(0..310)
            UNITS       "0.1 dB"
            MAX-ACCESS  read-create
            STATUS      current
            DESCRIPTION
                "The minimum Noise Margin the xTU-C receiver shall tolerate.
                 If the noise margin falls below this level, the xTU-C shall
                 request that the xTU-R increase the xTU-R transmit power.
                 If an increase of xTU-R transmit power is not possible, a
                 loss-of-margin (LOM) defect occurs, the xTU-C shall fail and
                 attempt to re-initialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.6"
            DEFVAL       { 0 }
            ::= { hwVdslLineConfProfEntry 21 }

        hwVdslLConfProfMsgMinUs  OBJECT-TYPE
            SYNTAX      Unsigned32(4000..63000)
            UNITS       "bits/second"
            MAX-ACCESS  read-create
            STATUS      current
            DESCRIPTION
                "Minimum Overhead Rate Upstream.  Defines the minimum rate of
                 the message-based overhead that shall be maintained by the xTU
                 in upstream direction.  Expressed in bits per second and
                 ranges from 4000 to 63000 bps.
                 Unit: bits/second
                "
            REFERENCE    "ITU-T G.997.1, paragraph 7.3.1.5.1"
            DEFVAL       { 4000 }
            ::= { hwVdslLineConfProfEntry 22 }

        hwVdslLConfProfMsgMinDs  OBJECT-TYPE
            SYNTAX      Unsigned32(4000..63000)
            UNITS       "bits/second"
            MAX-ACCESS  read-create
            STATUS      current
            DESCRIPTION
                "Minimum Overhead Rate Downstream.  Defines the minimum rate of
                 the message-based overhead that shall be maintained by the xTU
                 in downstream direction.  Expressed in bits per second and
                 ranges from 4000 to 63000 bps.
                 Unit: bits/second
                "
            REFERENCE    "ITU-T G.997.1, paragraph 7.3.1.5.2"
            DEFVAL       { 4000 }
            ::= { hwVdslLineConfProfEntry 23 }

        hwVdslLConfProfXtuTransSysEna  OBJECT-TYPE
            SYNTAX      HwXdslTransmissionModeType
            MAX-ACCESS  read-create
            STATUS      current
            DESCRIPTION
                "xTU Transmission System Enabling (XTSE).  A list of the
                 different coding types enabled in this profile.  It is coded
                 in a bit-map representation with 1 or more bits set.  A bit
                 set to  '1' means that the XTUs may apply the respective
                 coding for the XDSL line.  A bit set to '0' means that
                 the XTUs cannot apply the respective coding for the XDSL
                 line.  All 'reserved' bits should be set to '0'.
                "
            REFERENCE    "ITU-T G.997.1, paragraph 7.3.1.1.1"
            ::= { hwVdslLineConfProfEntry 24 }

        hwVdslLConfProfPmMode  OBJECT-TYPE
            SYNTAX      HwXdslLConfProfPmMode
            MAX-ACCESS  read-create
            STATUS      current
            DESCRIPTION
                "Power management state enabling.  Defines the power states the
                 xTU-C or xTU-R may autonomously transition to on this line.
                 Options:
                 1. allowTransitionsToIdle (0)
                 2. allowTransitionsToLowPower (1)
                 A bit with a '1' value means
                 that the xTU is allowed to transit into the respective state
                 and a '0' value means that the xTU is not allowed
                 to transit into the respective state.
                "
            REFERENCE    "ITU-T G.997.1, paragraph 7.3.1.1.4"
            DEFVAL  { allowTransitionsToIdle }
            ::= { hwVdslLineConfProfEntry 25 }

        hwVdslLConfProfL0Time  OBJECT-TYPE
            SYNTAX      Unsigned32 (0..255)
            UNITS       "seconds"
            MAX-ACCESS  read-create
            STATUS      current
            DESCRIPTION
                "This minimum time (in seconds) between an Exit from the L2
                 state and the next Entry into the L2 state.
                 Unit: seconds
                "
            REFERENCE    "ITU-T G.997.1, paragraph 7.3.1.1.5"
            DEFVAL       { 255 }
            ::= { hwVdslLineConfProfEntry 26 }

        hwVdslLConfProfL2Time  OBJECT-TYPE
            SYNTAX      Unsigned32 (0..255)
            UNITS       "seconds"
            MAX-ACCESS  read-create
            STATUS      current
            DESCRIPTION
                "This minimum time (in seconds) between an Entry into the
                 L2 state and the first Power Trim in the L2 state and between
                 two consecutive Power Trims in the L2 State.
                 Unit: seconds
                "
            REFERENCE    "ITU-T G.997.1, paragraph 7.3.1.1.6"
            DEFVAL       { 30 }
            ::= { hwVdslLineConfProfEntry 27 }

        hwVdslLConfProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 It ranges from 0 dB to 31 dB.
                 Unit: dB
                "
            REFERENCE    "ITU-T G.997.1 (amendment 1), 7.3.1.1.7"
            DEFVAL       { 3 }
            ::= { hwVdslLineConfProfEntry 28 }

        hwVdslLConfProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims.
                 Unit: dB
                "
            REFERENCE    "ITU-T G.997.1 (amendment 1), 7.3.1.1.9"
            DEFVAL       { 9 }
            ::= { hwVdslLineConfProfEntry 29 }

        hwVdslLConfProfDpboEpsd  OBJECT-TYPE
            SYNTAX      HwXdslDpboEpsd
            MAX-ACCESS  read-create
            STATUS      current
            DESCRIPTION
                "This parameter defines the PSD mask that is assumed to be permitted at the exchange.
                 This parameter shall use the same format as PSDMASKds.The maximum number of breakpoints
                 for DPBOEPSD is 16.
                 This is a string of 16 pairs of values in the following
                 structure:
                 Octets 0+1 - Index of 1st sub-carrier used in the context
                              of a first breakpoint.
                 Octet 2    - The PSD reduction for the sub-carrier indicated in
                             octets 0 and 1.
                 Octets 3-5 - Same, for a 2nd breakpoint.
                 Octets 6-8 - Same, for a 3rd breakpoint.
                 This architecture continues until octets 45-47, which are
                 associated with a 16th breakpoint.
                 Each subcarrier index is an unsigned number in the range 1 and
                 NSCds.  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.
                "
            REFERENCE    "ITU-T G.997.1(200604), paragraph 7.3.1.2.13"
            ::= { hwVdslLineConfProfEntry 30 }

        hwVdslLConfProfDpboEsel  OBJECT-TYPE
            SYNTAX      Unsigned32 (0..511)
            UNITS       "0.5dB"
            MAX-ACCESS  read-create
            STATUS      current
            DESCRIPTION
                "This configuration parameter defines the assumed electrical length of
                 cables (E-side cables) connecting exchange based DSL services to a remote
                 flexibility point (cabinet), that hosts the xTU-C that is subject to
                 spectrally shaped downstream power back-off depending on this length.
                 For this parameter the electrical length is defined as the loss (in dB)
                 of an equivalent length of hypothetical cable at a reference frequency
                 defined by the network operator or in spectrum management regulations.
                 DPBOESEL shall be coded as an unsigned integer representing an electrical
                 length from 0 dB (coded as 0) to 255.5 dB (coded as 511) in steps of 0.5 dB.
                 All values in the range are valid.If DPBOESEL is set to zero, the DPBO in
                 this section shall be disabled.
                 Unit: 0.5dB
                "
            REFERENCE    "ITU-T G.997.1(200604), paragraph 7.3.1.2.13"
            ::= { hwVdslLineConfProfEntry 31 }

        hwVdslLConfProfDpboEscm  OBJECT-TYPE
            SYNTAX      HwXdslDpboEscm
            MAX-ACCESS  read-create
            STATUS      current
            DESCRIPTION
                "This configuration parameter defines a cable model in terms of three scalars
                 DPBOESCMA, DPBOESCMB and DPBOESCMC that shall be used to describe the frequency
                 dependent loss of E-side cables.Parameters DPBOESCMA, DPBOESCMB, DPBOESCMC shall be
                 coded as unsigned integers representing a scalar value from -1 (coded as 0) to 1.5
                 (coded as 640) in step of 1/256. All values in the range are valid.
                 Octets 0+1 DPBOESCMA
                 Octets 2+3 DPBOESCMB
                 Octets 4+5 DPBOESCMC
                "
            REFERENCE    "ITU-T G.997.1(200604), paragraph 7.3.1.2.13"
            ::= { hwVdslLineConfProfEntry 32 }

        hwVdslLConfProfDpboMus  OBJECT-TYPE
            SYNTAX      Unsigned32 (0..255)
            UNITS       "-0.5dBm/Hz"
            MAX-ACCESS  read-create
            STATUS      current
            DESCRIPTION
                "DPBOMUS defines the assumed Minimum Usable receive Signal PSD (in dBm/Hz) for
                 exchange based services, used to modify parameter DPBOFMAX defined below. It
                 shall be coded as an unsigned integer representing a PSD level from 0 dBm/Hz
                 (coded as 0) to -127.5 dBm/Hz (coded as 255) in steps of 0.5 dBm/Hz.
                 All values in the range are valid.
                 Unit: -0.5dBm/Hz
                "
             REFERENCE    "ITU-T G.997.1(200604), paragraph 7.3.1.2.13"
            ::= { hwVdslLineConfProfEntry 33 }

        hwVdslLConfProfDpboFmin  OBJECT-TYPE
            SYNTAX      Unsigned32 (0..2048)
            UNITS       "4.3125 KHz"
            MAX-ACCESS  read-create
            STATUS      current
            DESCRIPTION
                "DPBOFMIN defines the minimum frequency from which the DPBO shall be applied.
                 It shall be coded as a 16 bits unsigned integer representing a frequency in
                 multiple of 4.3125 KHz. The range of valid values is from 0 kHz (coded as 0)
                 to 8832 kHz (coded as 2048).
                 Unit: 4.3125 KHz
                "
            REFERENCE    "ITU-T G.997.1(200604), paragraph 7.3.1.2.13"
            ::= { hwVdslLineConfProfEntry 34 }

        hwVdslLConfProfDpboFmax  OBJECT-TYPE
            SYNTAX      Unsigned32 (32..8191)
            UNITS       "4.3125 KHz"
            MAX-ACCESS  read-create
            STATUS      current
            DESCRIPTION
                "DPBOFMAX defines the maximum frequency at which DPBO may be applied. It shall be
                 coded as a 16 bits unsigned integer representing a frequency in multiple of 4.3125 KHz.
                 The range of valid values is from 138 kHz (coded as 32) to 35323.6875 kHz (coded as 8191).
                 Unit: 4.3125 KHz
                "
            REFERENCE    "ITU-T G.997.1(200604), paragraph 7.3.1.2.13"
            ::= { hwVdslLineConfProfEntry 35 }

        hwVdslLConfProfUpboPsdBand  OBJECT-TYPE
            SYNTAX      HwXdslUpboPsdBand
            MAX-ACCESS  read-create
            STATUS      current
            DESCRIPTION
                "This parameter defines the UPBO reference PSD used to compute the upstream power back-off
                 for each upstream band except US0. A UPBOPSD defined for each band shall consist of two
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps
                 of 0.01 dBm/Hz. The UPBO reference PSD at the frequency f expressed in MHz shall be equal
                 to '-a-b(SQRT(f))'. The set of parameter values a = 40 dBm/Hz, b = 0 dBm/Hz is a special configuration
                 to disable UPBO in the respective upstream band.
                 Octets 0+1 -   a[0]
                 Octets 2+3 -   b[0]
                 Octets 4+5 -   a[1]
                 Octets 6+7 -   b[1]
                 Octets 8+9 -   a[2]
                 Octets 10+11 - b[2]
           Octets 12+13 - a[3]
                 Octets 14+15 - b[3]
                "
            REFERENCE    "ITU-T G.997.1(200604), paragraph 7.3.1.2.14"
            ::= { hwVdslLineConfProfEntry 36 }

        hwVdslLConfProfUpboKl  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0)
                 to 128 dB (coded as 1280) in steps of 0.1 dB.
                 Unit: 0.1 dB
                "
            REFERENCE    "ITU-T G.997.1(200604), paragraph 7.3.1.2.14"
            ::= { hwVdslLineConfProfEntry 37 }

        hwVdslLConfProfUpboKlf  OBJECT-TYPE
            SYNTAX      HwXdslUpboKlf
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                "
            REFERENCE    "ITU-T G.997.1(200604), paragraph 7.3.1.2.14"
            ::= { hwVdslLineConfProfEntry 38 }

        hwVdslLConfProfRowStatus  OBJECT-TYPE
            SYNTAX      RowStatus
            MAX-ACCESS  read-create
            STATUS      current
            DESCRIPTION
                "This object is used to create a new row or to modify or
                 delete an existing row in this table.
                 A profile is activated by setting this object to 'active'.
                 When 'active' is set, the system will validate the profile.
                 Before a profile can be deleted or taken out of service
                 (by setting this object to 'destroy' or 'outOfService'),
                 it must be not referenced from all associated
                 templates.
                "
            ::= { hwVdslLineConfProfEntry 39 }

        hwVdslLConfProfReferenceClock  OBJECT-TYPE
            SYNTAX      HwXdslLineClockReferenceType
            MAX-ACCESS  read-create
            STATUS      current
            DESCRIPTION
                "This object configures the clock reference for the ATU-C
                 in a XDSL Line.
                "
            DEFVAL       { freeRun }
            ::= { hwVdslLineConfProfEntry 65534 }

        hwVdslLConfProfBitSwapDs  OBJECT-TYPE
            SYNTAX      HwXdslBitSwap
            MAX-ACCESS  read-create
            STATUS      current
            DESCRIPTION
                "Enables or disables the bit swap downstream of a line."
            DEFVAL       { enable }
            ::= { hwVdslLineConfProfEntry 65535 }

        hwVdslLConfProfBitSwapUs  OBJECT-TYPE
            SYNTAX      HwXdslBitSwap
            MAX-ACCESS  read-create
            STATUS      current
            DESCRIPTION
               "Enables or disables the bit swap upstream of a line."
            DEFVAL       { enable }
            ::= { hwVdslLineConfProfEntry 65536 }

        hwVdslLConfProfUpboBoostMode  OBJECT-TYPE
            SYNTAX      HwXdslUpboBoostMode
            MAX-ACCESS  read-create
            STATUS      current
            DESCRIPTION
              "Options:
               1. disable(1)  - The Equalized FEXT UPBO method is not supported
               2. enable(2)   - The Equalized FEXT UPBO method is supported
              "
            DEFVAL       { enable }
            ::= { hwVdslLineConfProfEntry 65537 }

        hwVdslLConfProfDpboEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and XDSL provision of additional KVz areas from this KVz
                 using cross-cables to additional KVz), including the KVz at the MSAN site. This value must
                 be adjustable as the minimum requirement via the SNMP interface in the configuration profile
                 for each XDSL2 port, and is set individually for each MSAN site and usage. As an option,
                 As an option, adjustment can be done for each MSAN or line card, thus taking effect for
                 entire port groups. It is used only for determining the MUF.
                 Unit: 0.5 dB
                "
            ::= { hwVdslLineConfProfEntry 65538 }

        hwVdslLConfProfUpboKl0RefBand  OBJECT-TYPE
            SYNTAX      HwXdslUpboKl0RefBand
            MAX-ACCESS  read-create
            STATUS      current
            DESCRIPTION
                "Octets 0+1 - length[1]
                 Octets 2+3 - length[2]
                 Octets 4+5 - length[3]
                 Octets 6+7 - length[4]
                "
            REFERENCE
                "This parameter defines the UPBO reference electrical length used to compute the
                 upstream power back-off for each upstream band except US0, for the optional Equalized FEXT UPBO
                 method. The value ranges from 1.8 to 63.5 dB in steps of 0.1 dB with special value 0.The special
                 value 0 indicates optional Equalized FEXT UPBO method is not supported.
                "
            ::= { hwVdslLineConfProfEntry 65539 }

        hwVdslLConfProfSosTimeDs  OBJECT-TYPE
            SYNTAX      Unsigned32 (0..255)
            UNITS       "64ms"
            MAX-ACCESS  read-create
            STATUS      current
            DESCRIPTION
                "The parameter is used in the specification of the receiver initiated SOS.
                 If the value of this parameter is not zero, the standard SOS triggering criteria are enabled,
                 and the value corresponds with duration of the time window used in the standard SOS triggering
                 criteria in the downstream direction.The special value zero, indicates that the standard SOS
                 triggering criteria are disabled. The valid range of non-zero values is from 64 ms to (255*64) ms
                 in steps of 64ms.
                 Unit: 64ms
                "
            REFERENCE    "ITU-T G.997.1(200811), paragraph 7.3.1.10.1"
            ::= { hwVdslLineConfProfEntry 65540 }

        hwVdslLConfProfSosTimeUs  OBJECT-TYPE
            SYNTAX      Unsigned32 (0..255)
            UNITS       "64ms"
            MAX-ACCESS  read-create
            STATUS      current
            DESCRIPTION
                "The parameter is used in the specification of the receiver initiated SOS.
                 If the value of this parameter is not zero, the standard SOS triggering criteria are enabled,
                 and the value corresponds with duration of the time window used in the standard SOS triggering
                 criteria in the upstream direction.The special value zero, indicates that the standard SOS
                 triggering criteria are disabled. The valid range of non-zero values is from 64 ms to (255*64) ms
                 in steps of 64ms.
                 Unit: 64ms
                "
            REFERENCE    "ITU-T G.997.1(200811), paragraph 7.3.1.10.2"
            ::= { hwVdslLineConfProfEntry 65541 }

        hwVdslLConfProfSosNtonesDs  OBJECT-TYPE
            SYNTAX      Unsigned32 (0..100)
            MAX-ACCESS  read-create
            STATUS      current
            DESCRIPTION
                "This parameter is defined as the minimum percentage of tones in the downstream MEDLEY SET
                 that must be degraded in order to arm the first sub-condition of the standard SOS triggering
                 criteria in the downstream direction. The parameter SOS-NTONES-ds is defined as a percentage of tones.
                 The valid range of values is from 1 to 100 in steps of 1. A special value of 0 indicates that this
                 parameter is not used in the decision criteria.
                "
            REFERENCE    "ITU-T G.997.1(200811), paragraph 7.3.1.10.3"
            ::= { hwVdslLineConfProfEntry 65542 }

        hwVdslLConfProfSosNtonesUs  OBJECT-TYPE
            SYNTAX      Unsigned32 (0..100)
            MAX-ACCESS  read-create
            STATUS      current
            DESCRIPTION
                "This parameter is defined as the minimum percentage of tones in the upstream MEDLEY SET
                 that must be degraded in order to arm the first sub-condition of the standard SOS triggering
                 criteria in the downstream direction. The parameter SOS-NTONES-ds is defined as a percentage of tones.
                 The valid range of values is from 1 to 100 in steps of 1. A special value of 0 indicates that this
                 parameter is not used in the decision criteria.
                "
            REFERENCE    "ITU-T G.997.1(200811), paragraph 7.3.1.10.4"
            ::= { hwVdslLineConfProfEntry 65543 }

        hwVdslLConfProfSosCrcDs  OBJECT-TYPE
            SYNTAX      Unsigned32 (1..65535)
            UNITS       "0.02"
            MAX-ACCESS  read-create
            STATUS      current
            DESCRIPTION
                "This parameter is defined as the minimum number of normalized CRC anomalies received in SOS-TIME-ds
                 seconds in order to arm the second sub-condition of the standard SOS triggering criteria  in the
                 downstream direction. The valid range of SOS-CRC values is 0.02 to 65535*0.02, in steps of 0.02.
                 Unit: 0.02
                "
            REFERENCE    "ITU-T G.997.1(200811), paragraph 7.3.1.10.5"
            ::= { hwVdslLineConfProfEntry 65544 }

        hwVdslLConfProfSosCrcUs  OBJECT-TYPE
            SYNTAX      Unsigned32 (1..65535)
            UNITS       "0.02"
            MAX-ACCESS  read-create
            STATUS      current
            DESCRIPTION
                "This parameter is defined as the minimum number of normalized CRC anomalies received in SOS-TIME-ds
                 seconds in order to arm the second sub-condition of the standard SOS triggering criteria  in the
                 upstream direction. The valid range of SOS-CRC values is 0.02 to 65535*0.02, in steps of 0.02.
                 Unit: 0.02
                "
           REFERENCE    "ITU-T G.997.1(200811), paragraph 7.3.1.10.6"
           ::= { hwVdslLineConfProfEntry 65545 }

        hwVdslLConfProfMaxSosDs  OBJECT-TYPE
            SYNTAX      Unsigned32 (0..15)
            MAX-ACCESS  read-create
            STATUS      current
            DESCRIPTION
                "This parameter is used in G.993.2 de-activation. If the number of successful SOS procedures in the
                 downstream direction performed within a 120-second interval exceeds MAX-SOS-ds, the modem shall transition
                 to the L3 state. The valid range of values is 1 to 15. A special value of 0 indicates that there is no
                 limit on the maximum allowed number of SOS recoveries within this time interval.
                "
            REFERENCE    "ITU-T G.997.1(200811), paragraph 7.3.1.10.7"
            ::= { hwVdslLineConfProfEntry 65546 }

        hwVdslLConfProfMaxSosUs  OBJECT-TYPE
            SYNTAX      Unsigned32 (0..15)
            MAX-ACCESS  read-create
            STATUS      current
            DESCRIPTION
                "This parameter is used in G.993.2 de-activation. If the number of successful SOS procedures in the
                 upstream direction performed within a 120-second interval exceeds MAX-SOS-ds, the modem shall transition
                 to the L3 state. The valid range of values is 1 to 15. A special value of 0 indicates that there is no
                 limit on the maximum allowed number of SOS recoveries within this time interval.
                "
            REFERENCE    "ITU-T G.997.1(200811), paragraph 7.3.1.10.8"
            ::= { hwVdslLineConfProfEntry 65547 }

        hwVdslLConfProfSnrmoffsetRocDs  OBJECT-TYPE
            SYNTAX      Unsigned32 (0..310)
            UNITS       "0.1dB"
            MAX-ACCESS  read-create
            STATUS      current
            DESCRIPTION
                "The parameter is defined as the SNR Margin offset for the ROC channel in the downstream direction.
                 The parameter is used in the specification of the Channel Initialization Policy (see 12.3.7.1/G.993.2).
                 The valid range of SNR margin offset values is from 0 to (310*0.1) dB with 0.1 dB steps.
                 Unit: 0.1dB
                "
            REFERENCE    "ITU-T G.997.1(200811), paragraph 7.3.1.10.9"
        ::= { hwVdslLineConfProfEntry 65548 }

        hwVdslLConfProfSnrmoffsetRocUs  OBJECT-TYPE
            SYNTAX      Unsigned32 (0..310)
            UNITS       "0.1dB"
            MAX-ACCESS  read-create
            STATUS      current
            DESCRIPTION
                "The parameter is defined as the SNR Margin offset for the ROC channel in the upstream direction.
                 The parameter is used in the specification of the Channel Initialization Policy (see 12.3.7.1/G.993.2).
                 The valid range of SNR margin offset values is from 0 to (310*0.1) dB with 0.1 dB steps.
                 Unit: 0.1dB
                "
            REFERENCE    "ITU-T G.997.1(200811), paragraph 7.3.1.10.10"
            ::= { hwVdslLineConfProfEntry 65549 }

        hwVdslLConfProfInpminRocDs  OBJECT-TYPE
            SYNTAX      Unsigned32 (0..16)
            MAX-ACCESS  read-create
            STATUS      current
            DESCRIPTION
                "This parameter contains the minimum impulse noise protection to apply on the ROC in the downstream direction.
                 The minimum impulse noise protection is an integer ranging from 0 to 16.
                "
            REFERENCE    "ITU-T G.997.1(200811), paragraph 7.3.1.10.11"
            ::= { hwVdslLineConfProfEntry 65550 }

        hwVdslLConfProfInpminRocUs  OBJECT-TYPE
            SYNTAX      Unsigned32 (0..16)
            MAX-ACCESS  read-create
            STATUS      current
            DESCRIPTION
                "This parameter contains the minimum impulse noise protection to apply on the robust ROC in the upstream direction.
                 The minimum impulse noise protection is an integer ranging from 0 to 16.
                "
            REFERENCE    "ITU-T G.997.1(200811), paragraph 7.3.1.10.12"
            ::= { hwVdslLineConfProfEntry 65551 }

        hwVdslLConfProfInmIatoDs  OBJECT-TYPE
            SYNTAX      Unsigned32(3..511)
            MAX-ACCESS  read-create
            STATUS      current
            DESCRIPTION
                "The parameter of downstream impulse noise monitoring inter arrival time offset.
                 This is the Inter Arrival Time Offset that the xTU receiver shall use to determine
                 in which bin of the Inter Arrival Time histogram the IAT is reported.
                 The valid values for INMIATO ranges from 3 to 511 DMT symbols in steps of 1 DMT symbol.
                "
            REFERENCE    "ITU-T G.997.1, paragraph 7.3.1.9.1"
            DEFVAL       { 3 }
            ::= { hwVdslLineConfProfEntry 65552 }

        hwVdslLConfProfInmIatsDs  OBJECT-TYPE
            SYNTAX      Unsigned32(0..7)
            MAX-ACCESS  read-create
            STATUS      current
            DESCRIPTION
                "The parameter of downstream impulse noise monitoring inter arrival time step.
                 This is the Inter Arrival Time Step that the xTU receiver shall use to determine
                 in which bin of the Inter Arrival Time histogram the IAT is reported.
                 The valid values for INMIATS ranges from 0 to 7 in steps of 1.
                "
            REFERENCE    "ITU-T G.997.1, paragraph 7.3.1.9.2"
            DEFVAL       { 0 }
            ::= { hwVdslLineConfProfEntry 65553 }

        hwVdslLConfProfInmCcDs  OBJECT-TYPE
            SYNTAX      Unsigned32(0..64)
            MAX-ACCESS  read-create
            STATUS      current
            DESCRIPTION
                "The parameter of Downstream impulse noise monitoring cluster continuation value.
                 This is the Cluster Continuation value that the xTU receiver shall use
                 in the cluster indication process described in the relevant ITU-T Recommendation.
                 The valid values for INMCC range from 0 to 64 DMT symbols in steps of 1 DMT symbol.
                "
            REFERENCE    "ITU-T G.997.1, paragraph 7.3.1.9.3"
            DEFVAL       { 0 }
            ::= { hwVdslLineConfProfEntry 65554 }

        hwVdslLConfProfInmInpeqModeDs  OBJECT-TYPE
            SYNTAX      Unsigned32(0..4)
            MAX-ACCESS  read-create
            STATUS      current
            DESCRIPTION
                "The parameter of Downstream impulse noise monitoring equivalent impulse noise protect mode.
                 This is the INM Equivalent INP Mode that the xTU receiver shall use in the computation of the Equivalent INP,
                 as defined in the relevant ITU-T Recommendation. The valid values for INM_INPEQ_MODE are 0, 1, 2, 3, and 4.
                "
            REFERENCE    "ITU-T G.997.1, paragraph 7.3.1.9.4"
            DEFVAL       { 0 }
            ::= { hwVdslLineConfProfEntry 65555 }

        hwVdslLConfProfInmIatoUs  OBJECT-TYPE
            SYNTAX      Unsigned32(3..511)
            MAX-ACCESS  read-create
            STATUS      current
            DESCRIPTION
                "The parameter of upstream impulse noise monitoring inter arrival time offset.
                 This is the Inter Arrival Time Offset that the xTU receiver shall use to determine
                 in which bin of the Inter Arrival Time histogram the IAT is reported.
                 The valid values for INMIATO ranges from 3 to 511 DMT symbols in steps of 1 DMT symbol.
                "
            REFERENCE    "ITU-T G.997.1, paragraph 7.3.1.9.1"
            DEFVAL       { 3 }
            ::= { hwVdslLineConfProfEntry 65556 }

        hwVdslLConfProfInmIatsUs  OBJECT-TYPE
            SYNTAX      Unsigned32(0..7)
            MAX-ACCESS  read-create
            STATUS      current
            DESCRIPTION
                "The parameter of upstream impulse noise monitoring inter arrival time step.
                 This is the Inter Arrival Time Step that the xTU receiver shall use to determine
                 in which bin of the Inter Arrival Time histogram the IAT is reported.
                 The valid values for INMIATS ranges from 0 to 7 in steps of 1.
                "
            REFERENCE    "ITU-T G.997.1, paragraph 7.3.1.9.2"
            DEFVAL       { 0 }
            ::= { hwVdslLineConfProfEntry 65557 }

        hwVdslLConfProfInmCcUs  OBJECT-TYPE
            SYNTAX      Unsigned32(0..64)
            MAX-ACCESS  read-create
            STATUS      current
            DESCRIPTION
                "The parameter of upstream impulse noise monitoring cluster continuation value.
                 This is the Cluster Continuation value that the xTU receiver shall use
                 in the cluster indication process described in the relevant ITU-T Recommendation.
                 The valid values for INMCC range from 0 to 64 DMT symbols in steps of 1 DMT symbol.
                "
            REFERENCE    "ITU-T G.997.1, paragraph 7.3.1.9.3"
            DEFVAL       { 0 }
            ::= { hwVdslLineConfProfEntry 65558 }

        hwVdslLConfProfInmInpeqModeUs  OBJECT-TYPE
            SYNTAX      Unsigned32(0..4)
            MAX-ACCESS  read-create
            STATUS      current
            DESCRIPTION
                "The parameter of upstream impulse noise monitoring equivalent impulse noise protect mode.
                 This is the INM Equivalent INP Mode that the xTU receiver shall use in the computation of the Equivalent INP,
                 as defined in the relevant ITU-T Recommendation. The valid values for INM_INPEQ_MODE are 0, 1, 2, 3, and 4.
                "
            REFERENCE    "ITU-T G.997.1, paragraph 7.3.1.9.4"
            DEFVAL       { 0 }
            ::= { hwVdslLineConfProfEntry 65559 }

        hwVdslLConfProfL3Time  OBJECT-TYPE
            SYNTAX      Unsigned32 (0..65535)
            UNITS       "seconds"
            MAX-ACCESS  read-create
            STATUS      current
            DESCRIPTION
                "This minimum time (in seconds) between an Entry into the
                 L3 state and the L0 or L2 state.
                 Unit: seconds
                "
            DEFVAL       { 255 }
            ::= { hwVdslLineConfProfEntry 65560 }
        hwVdslLConfProfRtxModeDs  OBJECT-TYPE
            SYNTAX      INTEGER
                        {
                         forbidden(0),
                         preferred(1),
                         forced(2),
                         testmode(3)
                        }
            MAX-ACCESS  read-create
            STATUS      current
            DESCRIPTION
                "The mode of operation of G.998.4 retransmission in downstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwVdslLineConfProfEntry 65561 }

        hwVdslLConfProfRtxModeUs  OBJECT-TYPE
            SYNTAX      INTEGER
                        {
                         forbidden(0),
                         preferred(1),
                         forced(2),
                         testmode(3)
                        }
            MAX-ACCESS  read-create
            STATUS      current
            DESCRIPTION
                "The mode of operation of G.998.4 retransmission in upstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwVdslLineConfProfEntry 65562 }

        hwVdslLConfProfLeftrThreshDs  OBJECT-TYPE
            SYNTAX      Unsigned32(0..99)
            UNITS       "0.01"
            MAX-ACCESS  read-create
            STATUS      current
            DESCRIPTION
                "If retransmission is used in downstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwVdslLineConfProfEntry 65563 }

        hwVdslLConfProfLeftrThreshUs  OBJECT-TYPE
            SYNTAX      Unsigned32(0..99)
            UNITS       "0.01"
            MAX-ACCESS  read-create
            STATUS      current
            DESCRIPTION
                "If retransmission is used in upstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwVdslLineConfProfEntry 65564 }

        hwVdslLConfProfForceInpDs  OBJECT-TYPE
            SYNTAX TruthValue
            MAX-ACCESS  read-create
            STATUS      current
            DESCRIPTION
                "This parameter indicates that the framer settings of the
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"
            DEFVAL       { false }
            ::= { hwVdslLineConfProfEntry 65565 }

        hwVdslLConfProfForceInpUs  OBJECT-TYPE
            SYNTAX TruthValue
            MAX-ACCESS  read-create
            STATUS      current
            DESCRIPTION
                "This parameter indicates that the framer settings of the
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"
            DEFVAL       { false }
            ::= { hwVdslLineConfProfEntry 65566 }

        hwVdslLConfProfAeleMode  OBJECT-TYPE
            SYNTAX      Unsigned32(0..3)
            MAX-ACCESS  read-create
            STATUS      current
            DESCRIPTION
                "This parameter defines the UPBO electrical length estimation mode to be used
                 in the Alternative Electrical Length Estimation method (ELE-M1) in 7.2.1.3.2.2/G.993.2.
                 The value of this parameter is 0, 1, 2 or 3.
                 0-ELE_M0, 1-ELE_DS, 2-ELE_PB, 3-ELE_MIN
                "
            REFERENCE    "ITU-T G.997.1, paragraph 7.3.1.2.14"
            DEFVAL       { 0 }
            ::= { hwVdslLineConfProfEntry 65567 }

        hwVdslLConfProfUpboElmt  OBJECT-TYPE
            SYNTAX      Unsigned32(0..15)
            MAX-ACCESS  read-create
            STATUS      current
            DESCRIPTION
                "This parameter defines the UPBO electrical length minimum threshold percentile
                 in percent used in the Alternative Electrical Length Estimation method (ELE-M1)
                 in clause 7.2.1.3.2.2/G.993.2.  It is set by network management via the CO-MIB.
                 The parameter ranges from 0 to 15 percent in steps of 1 percent.
                 This value is communicated to the VTU-R via G.994.1 at start-up.
                "
            REFERENCE    "ITU-T G.997.1, paragraph 7.3.1.2.14"
            DEFVAL       { 10 }
            ::= { hwVdslLineConfProfEntry 65568 }

        hwVdslLconfProfUpboKlAuto  OBJECT-TYPE
            SYNTAX      Unsigned32(1..4 | 4294967295)
            MAX-ACCESS  read-create
            STATUS      current
            DESCRIPTION
                "This parameter defines the mode in which kl0 is computed when hwVdslLconfProfUpboKlf is auto.
                 Options:
                 1--max(kl0_CO,kl0_CPE)
                 2--min(kl0_CO,kl0_CPE)
                 3--kl0_CO
                 4--kl0_CPE
                 4294967295--Invalid value
                "
            DEFVAL       { 1 }
            ::= { hwVdslLineConfProfEntry 65569 }

        hwVdslLConfProfLrMode  OBJECT-TYPE
            SYNTAX BITS
            {
                shortloop(0),
                mediumloop(1),
                longloop(2)
            }
            MAX-ACCESS  read-create
            STATUS      current
            DESCRIPTION
                "This parameter specifies which VDSL2-LR operation types are allowed.
                 The parameter is encoded as a bitmap representation (0 is not allowed, 1 is allowed).
                 Default value: 0.
                 Options:
                 1. shortloop(bit 0)               -short loop operation type
                 2. mediumloop(bit 1)              -medium loop operation type
                 3. longloop(bit 2)                -long loop operation type
                "
            DEFVAL       { 0 }
            ::= { hwVdslLineConfProfEntry 65570 }

        --    hwVdslLineConfProfModeSpecTable
        hwVdslLineConfProfModeSpecTable  OBJECT-TYPE
            SYNTAX      SEQUENCE  OF  HwVdslLineConfProfModeSpecEntry
            MAX-ACCESS  not-accessible
            STATUS      current
            DESCRIPTION
                "The table hwVdslLineConfProfModeSpecTable extends the
                 XDSL line configuration profile by XDSL Mode Specific
                 parameters.
                 A row in this table that has an index of
                 hwVdslLconfProfVdslMode == defMode(1), is called a
                 'mandatory' row.
                 A row in this table that has an index such that
                 hwVdslLconfProfVdslMode is not equal to defMode(1),
                 is called an 'optional' row.
                 When a row in the hwVdslLineConfProfTable table
                 (the parent row) is created, the SNMP agent will
                 automatically create a 'mandatory' row in this table.
                 When the parent row is deleted, the SNMP agent will
                 automatically delete all associated rows in this table.
                 Any attempt to delete the 'mandatory' row using the
                 hwVdslLConfProfModeSpecRowStatus attribute will be
                 rejected by the SNMP agent.
                 The manager MAY create an 'optional' row in this table
                 using the hwVdslLConfProfModeSpecRowStatus attribute if
                 the parent row exists.
                 The manager MAY delete an 'optional' row in this table
                 using the hwVdslLConfProfModeSpecRowStatus attribute at
                 any time.
                 If the actual transmission mode of a DSL line does not
                 match one of the 'optional' rows in this table, then
                 the line will use the PSD configuration from the
                 'mandatory' row.
                 The indexes of this table are hwVdslLConfProfProfileName
                 and hwVdslLconfProfVdslMode.
                "
            ::= { hwXdslProfileLine 3 }

        hwVdslLineConfProfModeSpecEntry  OBJECT-TYPE
            SYNTAX      HwVdslLineConfProfModeSpecEntry
            MAX-ACCESS  not-accessible
            STATUS      current
            DESCRIPTION
                "The table hwVdslLineConfProfModeSpecTable extends the
                 XDSL line configuration profile by XDSL Mode Specific
                 parameters.
                 A row in this table that has an index of
                 hwVdslLconfProfVdslMode == defMode(1), is called a
                 'mandatory' row.
                 A row in this table that has an index such that
                 hwVdslLconfProfVdslMode is not equal to defMode(1),
                 is called an 'optional' row.
                 When a row in the hwVdslLineConfProfTable table
                 (the parent row) is created, the SNMP agent will
                 automatically create a 'mandatory' row in this table.
                 When the parent row is deleted, the SNMP agent will
                 automatically delete all associated rows in this table.
                 Any attempt to delete the 'mandatory' row using the
                 hwVdslLConfProfModeSpecRowStatus attribute will be
                 rejected by the SNMP agent.
                 The manager MAY create an 'optional' row in this table
                 using the hwVdslLConfProfModeSpecRowStatus attribute if
                 the parent row exists.
                 The manager MAY delete an 'optional' row in this table
                 using the hwVdslLConfProfModeSpecRowStatus attribute at
                 any time.
                 If the actual transmission mode of a DSL line does not
                 match one of the 'optional' rows in this table, then
                 the line will use the PSD configuration from the
                 'mandatory' row.
                 The indexes of this entry are hwVdslLConfProfProfileName
                 and hwVdslLconfProfVdslMode.
                "
            INDEX  { hwVdslLConfProfProfileName, hwVdslLconfProfVdslMode }
            ::= { hwVdslLineConfProfModeSpecTable 1 }

        HwVdslLineConfProfModeSpecEntry  ::=
            SEQUENCE {
              hwVdslLconfProfVdslMode             HwXdslOperationModes,
              hwVdslLConfProfMaxNomPsdDs          Integer32,
              hwVdslLConfProfMaxNomPsdUs          Integer32,
              hwVdslLConfProfMaxNomAtpDs          Unsigned32,
              hwVdslLConfProfMaxNomAtpUs          Unsigned32,
              hwVdslLConfProfMaxAggRxPwrUs        Integer32,
              hwVdslLConfProfPsdMaskDs            HwXdslPsdMaskDs,
              hwVdslLConfProfPsdMaskUs            HwXdslPsdMaskUs,
              hwVdslLConfProfPsdMaskSelectUs      Unsigned32,
              hwVdslLConfProfPSDClassMask      HwXdslPSDClassMask,
              hwVdslLConfProfProfiles        HwXdslProfiles,
              hwVdslLConfProfBandOptUsage      HwXdslBandOptUsage,
              hwVdslLConfProfModeSpecRowStatus    RowStatus,
              hwVdslConfProfVirtualNoiseModeDs  HwXdslVirtualNoise,
              hwVdslConfProfVirtualNoiseModeUs  HwXdslVirtualNoise,
              hwVdslConfProfVirtualNoiseDs      HwXdslVirtualNoiseDs,
              hwVdslConfProfVirtualNoiseUs      HwXdslVirtualNoiseUs,
              hwVdslConfProfAutoProfile         HwXdslAutoProfile,
              hwVdslConfProfPSDMaskOffset       OCTET STRING,
              hwVdslConfProfPSDBuriedAtten      OCTET STRING
           }

        hwVdslLconfProfVdslMode    OBJECT-TYPE
            SYNTAX      HwXdslOperationModes
            MAX-ACCESS  not-accessible
            STATUS      current
            DESCRIPTION
                "The XDSL Mode is a way of categorizing the various XDSL
                 transmission modes into groups, each group (XDSL Mode) shares
                 the same PSD configuration.
                 There should be multiple entries in this table for a given
                 line profile in case multiple bits are set in
                 hwVdslLConfProfXtuTransSysEna for that profile.
                "
            REFERENCE    "DSL Forum TR-90, paragraph 5.1.8"
            ::= { hwVdslLineConfProfModeSpecEntry 1 }

        hwVdslLConfProfMaxNomPsdDs  OBJECT-TYPE
            SYNTAX      Integer32(-600..-300)
            UNITS       "0.1 dBm/Hz"
            MAX-ACCESS  read-create
            STATUS      current
            DESCRIPTION
                "The maximum nominal transmit PSD in the downstream
                 direction during initialization and Showtime.  It ranges from
                 -600 to -300 units of 0.1 dBm/Hz.  (physical values are -60 to
                 -30 dBm/Hz).
                 Unit: 0.1 dBm/Hz
                "
            REFERENCE    "ITU-T G.997.1, paragraph 7.3.1.2"
            DEFVAL       { -300 }
            ::= { hwVdslLineConfProfModeSpecEntry 2 }

        hwVdslLConfProfMaxNomPsdUs  OBJECT-TYPE
            SYNTAX      Integer32(-600..-300)
            UNITS       "0.1 dBm/Hz"
            MAX-ACCESS  read-create
            STATUS      current
            DESCRIPTION
                "The maximum nominal transmit PSD in the upstream direction
                 during initialization and Showtime.  It ranges from -600 to
                 -300 units of 0.1 dBm/Hz.  (physical values are -60 to
                 -30 dBm/Hz).
                 Unit: 0.1 dBm/Hz
                "
            REFERENCE    "ITU-T G.997.1, paragraph 7.3.1.2"
            DEFVAL       { -300 }
            ::= { hwVdslLineConfProfModeSpecEntry 3 }

        hwVdslLConfProfMaxNomAtpDs  OBJECT-TYPE
            SYNTAX      Unsigned32 (0..510)
            UNITS       "0.1 dBm"
            MAX-ACCESS  read-create
            STATUS      current
            DESCRIPTION
                "The maximum nominal aggregate transmit power in the
                 downstream direction during initialization and Showtime.
                 It ranges from 0 to 510 units of 0.1 dBm  (0 to 255 physical
                 values are 0 to 25.5 dBm, 256 to 510 physical values are
                 -25.5 to -0.1 dBm).
                 Unit: 0.1 dBm
                "
            REFERENCE    "ITU-T G.997.1, paragraph 7.3.1.2"
            DEFVAL       { 145 }
            ::= { hwVdslLineConfProfModeSpecEntry 4 }

        hwVdslLConfProfMaxNomAtpUs  OBJECT-TYPE
            SYNTAX      Unsigned32 (0..510)
            UNITS       "0.1 dBm"
            MAX-ACCESS  read-create
            STATUS      current
            DESCRIPTION
                "The maximum nominal aggregate transmit power in the upstream
                 direction during initialization and Showtime.
                 It ranges from 0 to 510 units of 0.1 dBm  (0 to 255 physical
                 values are 0 to 25.5 dBm, 256 to 510 physical values are
                 -25.5 to -0.1 dBm).
                 Unit: 0.1 dBm
                "
            REFERENCE    "ITU-T G.997.1, paragraph 7.3.1.2"
            DEFVAL       { 145 }
            ::= { hwVdslLineConfProfModeSpecEntry 5 }

        hwVdslLConfProfMaxAggRxPwrUs  OBJECT-TYPE
            SYNTAX      Integer32(-255..255)
            UNITS       "0.1 dBm"
            MAX-ACCESS  read-create
            STATUS      current
            DESCRIPTION
                "The maximum upstream aggregate receive power over the relevant
                 set of sub-carriers.  The xTU-C should verify that the
                 upstream power cutback is such that this maximum aggregate
                 receive power value is honored.  It ranges from -255 to 255
                 units of 0.1 dBm (physical values are -25.5 to 25.5 dBm).
                 A value of all means that there is no limit.
                 Unit: 0.1 dBm
                "
            REFERENCE    "ITU-T G.997.1, paragraph 7.3.1.2"
            DEFVAL       { 255 }
            ::= { hwVdslLineConfProfModeSpecEntry 6 }

        hwVdslLConfProfPsdMaskDs   OBJECT-TYPE
            SYNTAX      HwXdslPsdMaskDs
            MAX-ACCESS  read-create
            STATUS      current
            DESCRIPTION
                "This configuration parameter defines the downstream PSD mask
                 applicable at the U C2 reference point.
                 This MIB PSD mask may impose PSD restrictions in addition
                 to the Limit PSD mask defined in the relevant Recommendation
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup.
                "
            REFERENCE    "ITU-T G.997.1(200604), paragraph 7.3.1.2.9"
            ::= { hwVdslLineConfProfModeSpecEntry 7 }

        hwVdslLConfProfPsdMaskUs   OBJECT-TYPE
            SYNTAX      HwXdslPsdMaskUs
            MAX-ACCESS  read-create
            STATUS      current
            DESCRIPTION
                "This configuration parameter defines the upstream PSD
                 mask applicable at the U R2 reference point. This MIB
                 PSD mask may impose PSD restrictions in addition to the
                 Limit PSD mask defined in the relevant Recommendations
                 (e.g., ITU-T Recommendations G.992.3, G.993.2).
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup.
                "
            REFERENCE    "ITU-T G.997.1(200604), paragraph 7.3.1.2.12"
            ::= { hwVdslLineConfProfModeSpecEntry 8 }

        hwVdslLConfProfPsdMaskSelectUs  OBJECT-TYPE
            SYNTAX      Unsigned32(0..9)
            MAX-ACCESS  read-create
            STATUS      current
            DESCRIPTION
                "The selected upstream PSD mask. This parameter is used only
                 for annexes J and M of G.992.3 and G.992.5, and the same
                 selection is used for all relevant enabled bits in
                 hwVdslLConfProfXtuTransSysEna.
                 The value is defined as below:
                 0-Invalid value
                 1-ADLU-32/EU-32
                 2-ADLU-36/EU-36
                 3-ADLU-40/EU-40
                 4-ADLU-44/EU-44
                 5-ADLU-48/EU-48
                 6-ADLU-52/EU-52
                 7-ADLU-56/EU-56
                 8-ADLU-60/EU-60
                 9-ADLU-64/EU-64
                "
            REFERENCE    "ITU-T G.997.1 (amendment 1), 7.3.1.10"
            ::= { hwVdslLineConfProfModeSpecEntry 9 }

        hwVdslLConfProfPSDClassMask  OBJECT-TYPE
            SYNTAX      HwXdslPSDClassMask
            MAX-ACCESS  read-create
            STATUS      current
            DESCRIPTION
                "In order to reduce the number of configuration possibilities,
                 the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1-NUS0.
                 -  Class HPE30 Annex B: HPE30-M1-NUS0.
                 -  Class 997E17-M2x Annex B: 997E17-M2x-NUS0.
                 -  Class 997E30-M2x Annex B: 997E30-M2x-NUS0.
                 -  Class 998E17-M2x Annex B: 998E17-M2x-NUS0, 998E17-M2x-NUS0-M, 998E17-M2x-A.
                 -  Class 998ADE17-M2x Annex B: 998ADE17-M2x-NUS0-M, 998ADE17-M2x-A, 998ADE17-M2x-B, 998ADE17-SPE-M2x-A.
                 -  Class 998E30-M2x Annex B: 998E30-M2x-NUS0, 998E30-M2x-NUS0-M.
                 -  Class 998ADE30-M2x Annex B: 998ADE30-M2x-NUS0-M, 998ADE30-M2x-NUS0-A.
                 -  Class 998E35-M2x Annex B: 998E35-M2x-A.
                 -  Class 998ADE35-M2x Annex B: 998ADE35-M2x-A, 998ADE35-M2x-B, 998ADE35-M2x-M.
                 -  Class CN17-M2x Annex N: CN17-M2x-A, CN17-M2x-B, CN17-M2x-M, CN17-M2x-NUS0-M.
                "
            REFERENCE    "ITU-T G.997.1(200604), paragraph 7.3.1.1.12,
                          ITU-T G.993.2(201501), Annex N Paragraph N.2"
            DEFVAL       { 14 }
            ::= { hwVdslLineConfProfModeSpecEntry 10 }

        hwVdslLConfProfProfiles  OBJECT-TYPE
            SYNTAX      HwXdslProfiles
            MAX-ACCESS  read-create
            STATUS      current
            DESCRIPTION
                "This configuration parameter contains the G.993.2
                 profiles to be allowed by the near-end xTU on this line.
                "
            REFERENCE    "ITU-T G.997.1(200604), paragraph 7.3.1.1.11"
            DEFVAL       { 5 }
             ::= { hwVdslLineConfProfModeSpecEntry 11 }

        hwVdslLConfProfBandOptUsage  OBJECT-TYPE
            SYNTAX      HwXdslBandOptUsage
            MAX-ACCESS  read-create
            STATUS      current
            DESCRIPTION
                "Defines the XDSL link use of the optional frequency
                 range [25kHz - 138kHz] (Opt).
                 Options:
                 1. unused(1)        - indicates Opt is unused
                 2. used(2)          - indicates Opt usage is for upstream
                 3. invalidValue(-1) -Invalid value
                 Huawei defined.
                "
            DEFVAL       { unused }
            ::= { hwVdslLineConfProfModeSpecEntry 12 }

        hwVdslLConfProfModeSpecRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwVdslLineConfProfModeSpecEntry 13 }

        hwVdslConfProfVirtualNoiseModeDs  OBJECT-TYPE
            SYNTAX      HwXdslVirtualNoise
            MAX-ACCESS  read-create
            STATUS      current
            DESCRIPTION
               "This parameter enables the transmitter referred
                virtual noise in the downstream direction.
                If set to 1, the virtual noise is disabled.
                If set to 2, the virtual noise is enabled.
               "
            REFERENCE    "ITU-T G.997.1(200604), paragraph 7.3.1.7.1"
            DEFVAL       { disable }
            ::= { hwVdslLineConfProfModeSpecEntry 65535 }

        hwVdslConfProfVirtualNoiseModeUs  OBJECT-TYPE
            SYNTAX      HwXdslVirtualNoise
            MAX-ACCESS  read-create
            STATUS      current
            DESCRIPTION
               "This parameter enables the transmitter referred
                virtual noise in the upstream direction.
                If set to 1, the virtual noise is disabled.
                If set to 2, the virtual noise is enabled.
               "
            REFERENCE    "ITU-T G.997.1(200604),paragraph 7.3.1.7.2"
            DEFVAL       { disable }
            ::= { hwVdslLineConfProfModeSpecEntry 65536 }

        hwVdslConfProfVirtualNoiseDs  OBJECT-TYPE
            SYNTAX      HwXdslVirtualNoiseDs
            MAX-ACCESS  read-create
            STATUS      current
            DESCRIPTION
                "This configuration parameter defines the downstream
                 transmitter referred virtual noise (TXREFVNds).
                 The TXREFVNds shall be specified through a set of breakpoints.
                 Each breakpoint shall consist of a subcarrier index,
                 with a subcarrier spacing of 4.3125 kHz,
                 and a noise PSD level (expressed in dBm/Hz) at that subcarrier.
                 The set of breakpoints can then be represented as
                 [(t1, PSD1), (t2, PSD2),..., (tN, PSDN)].
                 The subcarrier index shall be coded as an unsigned integer.
                 The noise level shall be coded as an 8-bit unsigned integer
                 representing the noise level -40 dBm/Hz (coded as 0) to -140 dBm/Hz
                 (coded as 200), in steps of 0.5 dBm/Hz.
                 Values from 201 to 255 are special values indicating a noise
                 level of 0 W/Hz. The maximum number of breakpoints is 32.
                "
            REFERENCE    "ITU-T G.997.1(200604), paragraph 7.3.1.7.3"
            ::= { hwVdslLineConfProfModeSpecEntry 65537 }

        hwVdslConfProfVirtualNoiseUs  OBJECT-TYPE
            SYNTAX      HwXdslVirtualNoiseUs
            MAX-ACCESS  read-create
            STATUS      current
            DESCRIPTION
                "This configuration parameter defines the upstream
                 transmitter referred virtual noise (TXREFVNus).
                 The TXREFVNus shall be specified through a set of breakpoints.
                 Each breakpoint shall consist of a subcarrier index t,
                 with a subcarrier spacing of 4.3125 kHz, and a noise PSD level
                 (expressed in dBm/Hz) at that subcarrier.
                 The set of breakpoints can then be represented as
                 [(t1, PSD1), (t2, PSD2), ... , (tN, PSDN)].
                 The subcarrier index shall be coded as an unsigned integer.
                 The noise level shall be coded as an 8-bit unsigned integer
                 representing the noise level -40 dBm/Hz (coded as 0) to -140 dBm/Hz
                 (coded as 200), in steps of 0.5 dBm/Hz.
                 Values from 201 to 255 are special values indicating
                 a noise level of 0 W/Hz. The maximum number of breakpoints is 16.
                "
            REFERENCE    "ITU-T G.997.1(200604), paragraph 7.3.1.7.4"
            ::= { hwVdslLineConfProfModeSpecEntry 65538 }

        hwVdslConfProfAutoProfile  OBJECT-TYPE
            SYNTAX      HwXdslAutoProfile
            MAX-ACCESS  read-create
            STATUS      current
            DESCRIPTION
                 "Enable or disable the G.993.2 profiles adaptive function.
                  If set to 1, the G.993.2 profiles adaptive function is disabled.
                If set to 2, the G.993.2 profiles adaptive function is enabled.
               "
            REFERENCE    "ITU-T G.997.1(200604), paragraph 7.3.1.1.11"
            DEFVAL       { disable }
            ::= { hwVdslLineConfProfModeSpecEntry 65539 }

        hwVdslConfProfPSDMaskOffset  OBJECT-TYPE
            SYNTAX      OCTET STRING (SIZE(0..4))
            MAX-ACCESS  read-create
            STATUS      current
            DESCRIPTION
                "The value of this object identifies the PSD mask offset,
                 each byte represents a Dx, ranging from 0 to 6, the default value is 0.
                "
            ::= { hwVdslLineConfProfModeSpecEntry 65540 }

        hwVdslConfProfPSDBuriedAtten  OBJECT-TYPE
            SYNTAX      OCTET STRING (SIZE(0..4))
            MAX-ACCESS  read-create
            STATUS      current
            DESCRIPTION
                "The value of this object identifies the PSD burried attenuation,
                 each byte represents a Dx, ranging from 0 to 10, the default value is 0.
                "
            ::= { hwVdslLineConfProfModeSpecEntry 65541 }

        --        hwXdslServProfTable
        hwXdslServProfTable  OBJECT-TYPE
            SYNTAX      SEQUENCE  OF  HwXdslServProfEntry
            MAX-ACCESS  not-accessible
            STATUS      current
            DESCRIPTION
                "The table hwXdslServProfTable contains xDSL line
                 service configuration.
                 The index of this table is hwXdslServProfName.
                 A default profile with an index of 'DEFVAL' will
                 always exist and its parameters will be set to vendor-specific
                 values, unless otherwise specified in this document.
                "
            ::= { hwXdslProfileTIMode 1 }

        hwXdslServProfEntry  OBJECT-TYPE
            SYNTAX      HwXdslServProfEntry
            MAX-ACCESS  not-accessible
            STATUS      current
            DESCRIPTION
                "The table hwXdslServProfTable contains xDSL line
                 service configuration.
                 The index of this entry is hwXdslServProfName.
                 A default profile with an index of 'DEFVAL' will
                 always exist and its parameters will be set to vendor-specific
                 values, unless otherwise specified in this document.
                 "
            INDEX  { IMPLIED hwXdslServProfName }
            ::= { hwXdslServProfTable 1 }

        HwXdslServProfEntry  ::=
           SEQUENCE {
              hwXdslServProfName                     OCTET STRING,
              hwXdslServProfDataPathMode             HwXdslDataPathModeType,
              hwXdslServProfBitSwapEnablingDs        HwXdslProfSwitchType,
              hwXdslServProfBitSwapEnablingUs        HwXdslProfSwitchType,
              hwXdslServProfRaMode                   HwXdslRaMode,
              hwXdslServProfCh1Enabling              HwXdslChEnabling,
              hwXdslServProfCh1MinDataRateDs         Unsigned32,
              hwXdslServProfCh1MinDataRateUs         Unsigned32,
              hwXdslServProfCh1MinResDataRateDs      Unsigned32,
              hwXdslServProfCh1MinResDataRateUs      Unsigned32,
              hwXdslServProfCh1MaxDataRateDs         Unsigned32,
              hwXdslServProfCh1MaxDataRateUs         Unsigned32,
              hwXdslServProfCh1MinDataRateLowPwrDs   Unsigned32,
              hwXdslServProfCh1MinDataRateLowPwrUs   Unsigned32,
              hwXdslServProfCh1RaRatioDs             Unsigned32,
              hwXdslServProfCh1RaRatioUs             Unsigned32,
              hwXdslServProfCh2Enabling              HwXdslChEnabling,
              hwXdslServProfCh2MinDataRateDs         Unsigned32,
              hwXdslServProfCh2MinDataRateUs         Unsigned32,
              hwXdslServProfCh2MinResDataRateDs      Unsigned32,
              hwXdslServProfCh2MinResDataRateUs      Unsigned32,
              hwXdslServProfCh2MaxDataRateDs         Unsigned32,
              hwXdslServProfCh2MaxDataRateUs         Unsigned32,
              hwXdslServProfCh2MinDataRateLowPwrDs   Unsigned32,
              hwXdslServProfCh2MinDataRateLowPwrUs   Unsigned32,
              hwXdslServProfCh2RaRatioDs             Unsigned32,
              hwXdslServProfCh2RaRatioUs             Unsigned32,
              hwXdslServProfRowStatus                RowStatus,
              hwXdslServProfMinEtrRtxDs            Unsigned32,
              hwXdslServProfMinEtrRtxUs            Unsigned32,
              hwXdslServProfMaxEtrRtxDs            Unsigned32,
              hwXdslServProfMaxEtrRtxUs            Unsigned32,
              hwXdslServProfMaxNdrRtxDs            Unsigned32,
              hwXdslServProfMaxNdrRtxUs            Unsigned32
            }

        hwXdslServProfName  OBJECT-TYPE
            SYNTAX      OCTET STRING (SIZE(1..32))
            MAX-ACCESS  not-accessible
            STATUS      current
            DESCRIPTION
                "This object identifies a row in this table."
            ::= { hwXdslServProfEntry 1 }

        hwXdslServProfDataPathMode  OBJECT-TYPE
            SYNTAX      HwXdslDataPathModeType
            MAX-ACCESS  read-create
            STATUS      current
            DESCRIPTION
               "This parameter indicates the XDSL line data path modes.
                Options:
                1. atm (1)   - atm mode
                2. ptm (2)   - ptm mode
               "
            DEFVAL       { ptm }
            ::= { hwXdslServProfEntry 2 }

         hwXdslServProfBitSwapEnablingDs  OBJECT-TYPE
             SYNTAX      HwXdslProfSwitchType
             MAX-ACCESS  read-create
             STATUS      current
             DESCRIPTION
                "Enables or disables the bit swap downstream of a line.
                 Options:
                 1. enable(1)       - Enable the bit swap downstream of a line
                 2. disable(2)      - Disable the bit swap downstream of a line
                 huawei defined.
                "
             DEFVAL       { enable }
             ::= { hwXdslServProfEntry 3 }

         hwXdslServProfBitSwapEnablingUs  OBJECT-TYPE
             SYNTAX      HwXdslProfSwitchType
             MAX-ACCESS  read-create
             STATUS      current
             DESCRIPTION
               "Enables or disables the bit swap upstream of a line.
                Options:
                1. enable(1)      - Enable the bit swap upstream of a line.
                2. disable(2)     - Disable the bit swap upstream of a line.
                huawei defined.
               "
             DEFVAL       { enable }
             ::= { hwXdslServProfEntry 4 }

        hwXdslServProfRaMode  OBJECT-TYPE
            SYNTAX      HwXdslRaMode
            MAX-ACCESS  read-create
            STATUS      current
            DESCRIPTION
                "The mode of operation of a rate-adaptive xTU-R in the transmit
                 direction.
                 Options:
                 1. manual (1)           - No Rate-Adaptation.  The initialization
                                           process attempts to synchronize to a
                                           specified rate.
                 2. rainit (2)           - Rate-Adaptation during initialization process
                                           only, which attempts to synchronize to a rate
                                           between minimum and maximum specified values.
                 3. dynamic (3)          - Rate-Adaptation during show time
                "
            REFERENCE    "ITU-T G.997.1, paragraph 7.3.1.4.2"
            DEFVAL       { raInit }
            ::= { hwXdslServProfEntry 5 }

        hwXdslServProfCh1Enabling  OBJECT-TYPE
            SYNTAX      HwXdslChEnabling
            MAX-ACCESS  read-create
            STATUS      current
            DESCRIPTION
                 "This parameter indicates whether the bearer 1 of XDSL line is enabling.
                Options:
                1. enable(1)      - Enable the bearer 1 of XDSL line.
                2. disable(2)     - Disable the bearer 1 of XDSL line.
                huawei defined.
                "
            DEFVAL       { enable }
            ::= { hwXdslServProfEntry 6 }

        hwXdslServProfCh1MinDataRateDs  OBJECT-TYPE
            SYNTAX      Unsigned32(32000..200000000)
            UNITS       "bits/second"
            MAX-ACCESS  read-create
            STATUS      current
            DESCRIPTION
                "If retransmission is not used in downstream direction,this parameter specifics
                 minimum data rate for the bearer channel on downstream direction. coded in bit/s.
                 Unit: bits/second
                "
            REFERENCE    "ITU-T G.997.1, paragraph 7.3.2.1"
            ::= { hwXdslServProfEntry 7 }

        hwXdslServProfCh1MinDataRateUs  OBJECT-TYPE
            SYNTAX      Unsigned32(32000..200000000)
            UNITS       "bits/second"
            MAX-ACCESS  read-create
            STATUS      current
            DESCRIPTION
                "If retransmission is not used in upstream direction,this parameter specifics
                 minimum data rate for the bearer channel on upstream direction. coded in bit/s.
                 Unit: bits/second
                "
            REFERENCE    "ITU-T G.997.1, paragraph 7.3.2.1"
            ::= { hwXdslServProfEntry 8 }

        hwXdslServProfCh1MinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode of the bearer channel (i.e., hwXdslServProfRaMode) is set
                 to Dynamic.
                 Unit: bits/second
                "
            REFERENCE    "ITU-T G.997.1, paragraph 7.3.2.1"
            ::= { hwXdslServProfEntry 9 }

        hwXdslServProfCh1MinResDataRateUs  OBJECT-TYPE
            SYNTAX      Unsigned32(32000..200000000)
            UNITS       "bits/second"
            MAX-ACCESS  read-create
            STATUS      current
            DESCRIPTION
                "Minimum Reserved Data Rate on Upstream direction.  The minimum
                 reserved net data rate for the bearer channel, coded in
                 bit/s.  This parameter is used only if the Rate Adaptation
                 Mode of the bearer channel (i.e., hwXdslServProfRaMode) is set
                 to Dynamic.
                 Unit: bits/second
                "
            REFERENCE    "ITU-T G.997.1, paragraph 7.3.2.1"
            ::= { hwXdslServProfEntry 10 }

        hwXdslServProfCh1MaxDataRateDs  OBJECT-TYPE
            SYNTAX      Unsigned32(32000..200000000)
            UNITS       "bits/second"
            MAX-ACCESS  read-create
            STATUS      current
            DESCRIPTION
                "If retransmission is not used in downstream direction,this parameter specifics
                 maximum data rate for the bearer channel on downstream direction. coded in bit/s.
                 Unit: bits/second
                "
            REFERENCE    "ITU-T G.997.1, paragraph 7.3.2.1"
            ::= { hwXdslServProfEntry 11 }

        hwXdslServProfCh1MaxDataRateUs  OBJECT-TYPE
            SYNTAX      Unsigned32(32000..200000000)
            UNITS       "bits/second"
            MAX-ACCESS  read-create
            STATUS      current
            DESCRIPTION
                "If retransmission is not used in upstream direction,this parameter specifics
                 maximum data rate for the bearer channel on upstream direction. coded in bit/s.
                 Unit: bits/second
                "
            REFERENCE    "ITU-T G.997.1, paragraph 7.3.2.1"
            ::= { hwXdslServProfEntry 12 }

        hwXdslServProfCh1MinDataRateLowPwrDs  OBJECT-TYPE
            SYNTAX      Unsigned32(32000..200000000)
            UNITS       "bits/second"
            MAX-ACCESS  read-create
            STATUS      current
            DESCRIPTION
                "Minimum Data Rate in Low Power state on Downstream direction.
                 The minimum net data rate for the bearer channel, coded in
                 bit/s., during the low power state (L1 in G.992.2, L2 in
                 G.992.3).
                 Unit: bits/second
                "
            REFERENCE    "ITU-T G.997.1, paragraph 7.3.2.1"
            ::= { hwXdslServProfEntry 13 }

        hwXdslServProfCh1MinDataRateLowPwrUs  OBJECT-TYPE
            SYNTAX      Unsigned32(32000..200000000)
            UNITS       "bits/second"
            MAX-ACCESS  read-create
            STATUS      current
            DESCRIPTION
                "Minimum Data Rate in Low Power state on Upstream direction.
                 The minimum net data rate for the bearer channel, coded in
                 bit/s, during the low power state (L1 in G.992.2, L2 in
                 G.992.3).
                 Unit: bits/second
                "
            REFERENCE    "ITU-T G.997.1, paragraph 7.3.2.1"
            ::= { hwXdslServProfEntry 14 }

        hwXdslServProfCh1RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Downstream.  The ratio refers to the available
                 data rate in excess of the Minimum Data Rate, summed over all
                 bearer channels.  Also, the 100 -
                 hwXdslServProfCh1RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 100 }
            ::= { hwXdslServProfEntry 15 }

        hwXdslServProfCh1RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #1 when performing rate
                 adaptation on Upstream.  The ratio refers to the available
                 data rate in excess of the Minimum Data Rate, summed over all
                 bearer channels.  Also, the 100 -
                 hwXdslServProfCh1RaRatioUs is the ratio of excess data
                 rate to be assigned to all other bearer channels on Upstream
                 direction.  The sum of rate adaptation ratios over all bearers
                 on the same direction shall be equal to 100%.
                 Unit: percents
                "
            REFERENCE    "ITU-T G.997.1, paragraph 7.3.2.1"
            DEFVAL       { 100 }
            ::= { hwXdslServProfEntry 16 }

        hwXdslServProfCh2Enabling  OBJECT-TYPE
            SYNTAX      HwXdslChEnabling
            MAX-ACCESS  read-create
            STATUS      current
            DESCRIPTION
                 "This parameter indicates whether the bearer 2 of XDSL line is enabling.
                Options:
                1. enable(1)      - Enable the bearer 2 of XDSL line.
                2. disable(2)     - Disable the bearer 2 of XDSL line.
                huawei defined.
                 "
            DEFVAL       { disable }
            ::= { hwXdslServProfEntry 17 }

        hwXdslServProfCh2MinDataRateDs  OBJECT-TYPE
            SYNTAX      Unsigned32(32000..200000000)
            UNITS       "bits/second"
            MAX-ACCESS  read-create
            STATUS      current
            DESCRIPTION
                "Minimum Data Rate on Downstream direction.  The minimum net
                 data rate for the bearer channel, coded in bit/s.
                 Unit: bits/second
                "
            REFERENCE    "ITU-T G.997.1, paragraph 7.3.2.1"
            ::= { hwXdslServProfEntry 18 }

        hwXdslServProfCh2MinDataRateUs  OBJECT-TYPE
            SYNTAX      Unsigned32(32000..200000000)
            UNITS       "bits/second"
            MAX-ACCESS  read-create
            STATUS      current
            DESCRIPTION
                "Minimum Data Rate on Upstream direction.  The minimum net data
                 rate for the bearer channel, coded in bit/s.
                 Unit: bits/second
                "
            REFERENCE    "ITU-T G.997.1, paragraph 7.3.2.1"
            ::= { hwXdslServProfEntry 19 }

        hwXdslServProfCh2MinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode of the bearer channel (i.e., hwXdslServProfRaMode) is set
                 to Dynamic.
                 Unit: bits/second
                "
            REFERENCE    "ITU-T G.997.1, paragraph 7.3.2.1"
            ::= { hwXdslServProfEntry 20 }

        hwXdslServProfCh2MinResDataRateUs  OBJECT-TYPE
            SYNTAX      Unsigned32(32000..200000000)
            UNITS       "bits/second"
            MAX-ACCESS  read-create
            STATUS      current
            DESCRIPTION
                "Minimum Reserved Data Rate on Upstream direction.  The minimum
                 reserved net data rate for the bearer channel, coded in
                 bit/s.  This parameter is used only if the Rate Adaptation
                 Mode of the bearer channel (i.e., hwXdslServProfRaMode) is set
                 to Dynamic.
                 Unit: bits/second
                "
            REFERENCE    "ITU-T G.997.1, paragraph 7.3.2.1"
            ::= { hwXdslServProfEntry 21 }

        hwXdslServProfCh2MaxDataRateDs  OBJECT-TYPE
            SYNTAX      Unsigned32(32000..200000000)
            UNITS       "bits/second"
            MAX-ACCESS  read-create
            STATUS      current
            DESCRIPTION
                "Maximum Data Rate on Downstream direction.  The maximum net
                 data rate for the bearer channel, coded in bit/s.
                 Unit: bits/second
                "
            REFERENCE    "ITU-T G.997.1, paragraph 7.3.2.1"
            ::= { hwXdslServProfEntry 22 }

        hwXdslServProfCh2MaxDataRateUs  OBJECT-TYPE
            SYNTAX      Unsigned32(32000..200000000)
            UNITS       "bits/second"
            MAX-ACCESS  read-create
            STATUS      current
            DESCRIPTION
                "Maximum Data Rate on Upstream direction.  The maximum net data
                 rate for the bearer channel, coded in bit/s.
                 Unit: bits/second
                "
            REFERENCE    "ITU-T G.997.1, paragraph 7.3.2.1"
            ::= { hwXdslServProfEntry 23 }

        hwXdslServProfCh2MinDataRateLowPwrDs  OBJECT-TYPE
            SYNTAX      Unsigned32(32000..200000000)
            UNITS       "bits/second"
            MAX-ACCESS  read-create
            STATUS      current
            DESCRIPTION
                "Minimum Data Rate in Low Power state on Downstream direction.
                 The minimum net data rate for the bearer channel, coded in
                 bit/s, during the low power state (L1 in G.992.2, L2 in
                 G.992.3).
                 Unit: bits/second
                "
            REFERENCE    "ITU-T G.997.1, paragraph 7.3.2.1"
            ::= { hwXdslServProfEntry 24 }

        hwXdslServProfCh2MinDataRateLowPwrUs  OBJECT-TYPE
            SYNTAX      Unsigned32(32000..200000000)
            UNITS       "bits/second"
            MAX-ACCESS  read-create
            STATUS      current
            DESCRIPTION
                "Minimum Data Rate in Low Power state on Upstream direction.
                 The minimum net data rate for the bearer channel, coded in
                 bit/s, during the low power state (L1 in G.992.2, L2 in
                 G.992.3).
                 Unit: bits/second
                "
            REFERENCE    "ITU-T G.997.1, paragraph 7.3.2.1"
            ::= { hwXdslServProfEntry 25 }

        hwXdslServProfCh2RaRatioDs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Downstream.  The ratio refers to the available
                 data rate in excess of the Minimum Data Rate, summed over all
                 bearer channels.  Also, the 100 -
                 hwXdslServProfCh2RaRatioDs is the ratio of excess data
                 rate to be assigned to all other bearer channels on Downstream
                 direction.  The sum of rate adaptation ratios over all bearers
                 on the same direction shall be equal to 100%.
                 Unit: percents
                "
            REFERENCE    "ITU-T G.997.1, paragraph 7.3.2.1"
            DEFVAL       { 0 }
            ::= { hwXdslServProfEntry 26 }

        hwXdslServProfCh2RaRatioUs  OBJECT-TYPE
            SYNTAX      Unsigned32(0..100)
            UNITS       "percents"
            MAX-ACCESS  read-create
            STATUS      current
            DESCRIPTION
                "Rate Adaptation Ratio.  The ratio (in %) that should be taken
                 into account for the bearer channel #2 when performing rate
                 adaptation on Upstream.  The ratio refers to the available
                 data rate in excess of the Minimum Data Rate, summed over all
                 bearer channels.  Also, the 100 -
                 hwXdslServProfCh2RaRatioUs is the ratio of excess data
                 rate to be assigned to all other bearer channels on Upstream
                 direction.  The sum of rate adaptation ratios over all bearers
                 on the same direction shall be equal to 100%.
                 Unit: percents
                "
            REFERENCE    "ITU-T G.997.1, paragraph 7.3.2.1"
            DEFVAL       { 0 }
            ::= { hwXdslServProfEntry 27 }

        hwXdslServProfRowStatus  OBJECT-TYPE
            SYNTAX      RowStatus
            MAX-ACCESS  read-create
            STATUS      current
            DESCRIPTION
                "This object is used to create a new row or to modify or
                delete an existing row in this table.

                A profile is activated by setting this object to 'active'.
                When 'active' is set, the system will validate the profile.

                Before a profile can be deleted or taken out of service
                (by setting this object to 'destroy' or 'outOfService'),
                it must be not referenced from all associated
                lines.
               "
            ::= { hwXdslServProfEntry 28 }

        hwXdslServProfMinEtrRtxDs  OBJECT-TYPE
            SYNTAX      Unsigned32(32000..200000000)
            UNITS       "bits/second"
            MAX-ACCESS  read-create
            STATUS      current
            DESCRIPTION
               "If retransmission is used in downstream direction, this parameter specifies the
                minimum expected throughput for the bearer channel.The values range in steps of
                1000 bit/s.
               "
            REFERENCE    "ITU-T G.997.1, paragraph 7.3.2.1.8"
            ::= { hwXdslServProfEntry 29 }

        hwXdslServProfMinEtrRtxUs  OBJECT-TYPE
            SYNTAX      Unsigned32(32000..200000000)
            UNITS       "bits/second"
            MAX-ACCESS  read-create
            STATUS      current
            DESCRIPTION
               "If retransmission is used in upstream direction, this parameter specifies the
                minimum expected throughput for the bearer channel.The values range in steps of
                1000 bit/s.
               "
            REFERENCE    "ITU-T G.997.1, paragraph 7.3.2.1.8"
            ::= { hwXdslServProfEntry 30 }

        hwXdslServProfMaxEtrRtxDs  OBJECT-TYPE
            SYNTAX      Unsigned32(32000..200000000)
            UNITS       "bits/second"
            MAX-ACCESS  read-create
            STATUS      current
            DESCRIPTION
               "If retransmission is used in downstream direction, this parameter specifies the
                maximum expected throughput for the bearer channel.The values range in steps of
                1000 bit/s.
               "
            REFERENCE    "ITU-T G.997.1, paragraph 7.3.2.1.9"
            ::= { hwXdslServProfEntry 31 }

        hwXdslServProfMaxEtrRtxUs  OBJECT-TYPE
            SYNTAX      Unsigned32(32000..200000000)
            UNITS       "bits/second"
            MAX-ACCESS  read-create
            STATUS      current
            DESCRIPTION
               "If retransmission is used in upstream direction, this parameter specifies the
                maximum expected throughput for the bearer channel.The values range in steps of
                1000 bit/s.
               "
            REFERENCE    "ITU-T G.997.1, paragraph 7.3.2.1.9"
            ::= { hwXdslServProfEntry 32 }

        hwXdslServProfMaxNdrRtxDs  OBJECT-TYPE
            SYNTAX      Unsigned32(32000..200000000)
            UNITS       "bits/second"
            MAX-ACCESS  read-create
            STATUS      current
            DESCRIPTION
               "If retransmission is used in downstream direction, this parameter specifies the
                maximum net data rate for the bearer channel. The values range in steps of 1000 bit/s.
               "
            REFERENCE    "ITU-T G.997.1, paragraph 7.3.2.1.10"
            ::= { hwXdslServProfEntry 33 }

        hwXdslServProfMaxNdrRtxUs  OBJECT-TYPE
            SYNTAX      Unsigned32(32000..200000000)
            UNITS       "bits/second"
            MAX-ACCESS  read-create
            STATUS      current
            DESCRIPTION
               "If retransmission is used in upstream direction, this parameter specifies the
                maximum net data rate for the bearer channel.The values range in steps of 1000 bit/s.
               "
            REFERENCE    "ITU-T G.997.1, paragraph 7.3.2.1.10"
            ::= { hwXdslServProfEntry 34 }

        --        hwXdslSpectrumProfTable
        hwXdslSpectrumProfTable  OBJECT-TYPE
            SYNTAX      SEQUENCE  OF  HwXdslSpectrumProfEntry
            MAX-ACCESS  not-accessible
            STATUS      current
            DESCRIPTION
                "The table hwXdslSpectrumProfTable contains XDSL line
                 spectrum configuration.
                 The index of this table is hwXdslSpectrumProfName.
                 A default profile with an index of 'DEFVAL' will
                 always exist and its parameters will be set to vendor-specific
                 values, unless otherwise specified in this document.
                "
            ::= { hwXdslProfileTIMode 2 }

        hwXdslSpectrumProfEntry  OBJECT-TYPE
            SYNTAX      HwXdslSpectrumProfEntry
            MAX-ACCESS  not-accessible
            STATUS      current
            DESCRIPTION
                "The table hwXdslSpectrumProfTable contains XDSL line
                 spectrum configuration.
                 The index of this entry is hwXdslSpectrumProfName.
                 A default profile with an index of 'DEFVAL' will
                 always exist and its parameters will be set to vendor-specific
                 values, unless otherwise specified in this document.
                "
            INDEX  { IMPLIED hwXdslSpectrumProfName }
            ::= { hwXdslSpectrumProfTable 1 }

        HwXdslSpectrumProfEntry  ::=
            SEQUENCE {
              hwXdslSpectrumProfName              OCTET STRING,
              hwXdslSpectrumProfXtuTransSysEna    HwXdslTransmissionModeType,
              hwXdslSpectrumProfScMaskDs          HwXdslScMaskDs,
              hwXdslSpectrumProfScMaskUs          HwXdslScMaskUs,
              hwXdslSpectrumProfVDSLtoneblackout  OCTET STRING,
              hwXdslSpectrumProfRfiBands          OCTET STRING,
              hwXdslSpectrumProfRowStatus         RowStatus,
              hwXdslSpectrumProfRtxModeDs       INTEGER,
              hwXdslSpectrumProfRtxModeUs       INTEGER,
              hwXdslSpectrumProfProfLeftrThreshDs  Unsigned32,
              hwXdslSpectrumProfProfLeftrThreshUs  Unsigned32
            }

        hwXdslSpectrumProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { hwXdslSpectrumProfEntry 1 }

        hwXdslSpectrumProfXtuTransSysEna  OBJECT-TYPE
            SYNTAX      HwXdslTransmissionModeType
            MAX-ACCESS  read-create
            STATUS      current
            DESCRIPTION
                "xTU Transmission System Enabling (xTSE).  A list of the
                 different coding types enabled in this profile.  It is coded
                 in a bit-map representation with 1 or more bits set.  A bit
                 set to  '1' means that the XTUs may apply the respective
                 coding for the XDSL line.  A bit set to '0' means that
                 the XTUs cannot apply the respective coding for the XDSL
                 line.  All 'reserved' bits should be set to '0'.
                "
            REFERENCE    "ITU-T G.997.1, paragraph 7.3.1.1.1"
            ::= { hwXdslSpectrumProfEntry 2 }

        hwXdslSpectrumProfScMaskDs  OBJECT-TYPE
            SYNTAX      HwXdslScMaskDs
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 all 1's).  Also note that if NSCds &lt; 512, all bits
                 i (NSCds i &lt;= 512) should be set to '1'.
                "
            REFERENCE    "ITU-T G.997.1, paragraph 7.3.1.2.6"
            ::= { hwXdslSpectrumProfEntry 3 }

        hwXdslSpectrumProfScMaskUs  OBJECT-TYPE
            SYNTAX      HwXdslScMaskUs
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be all 1's).  Also note that if NSCus &lt;
                 64, all bits i (NSCus &lt; i &lt;= 64) should be set to '1'.
                "
            REFERENCE    "ITU-T G.997.1, paragraph 7.3.1.2.7"
            ::= { hwXdslSpectrumProfEntry 4 }

        hwXdslSpectrumProfVDSLtoneblackout  OBJECT-TYPE
            SYNTAX      OCTET STRING(SIZE(0..79))
            MAX-ACCESS  read-create
            STATUS      current
            DESCRIPTION
                "The subset of subcarrier mask that shall be
                 used to mask the subcarriers.
                 It is a string of bands consist of begin tone index
                 and end tone index.
                 for example :0-10,20-50,100-4095
                 It can contain as most as 8 bands.
                "
            REFERENCE    "ITU-T G.997.1(200604), paragraph 7.3.1.2.8"
            ::= { hwXdslSpectrumProfEntry 5 }

        hwXdslSpectrumProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
            ::= { hwXdslSpectrumProfEntry 6 }

        hwXdslSpectrumProfRowStatus  OBJECT-TYPE
            SYNTAX      RowStatus
            MAX-ACCESS  read-create
            STATUS      current
            DESCRIPTION
                "This object is used to create a new row or to modify or
                 delete an existing row in this table.
                 A profile is activated by setting this object to 'active'.
                 When 'active' is set, the system will validate the profile.
                 Before a profile can be deleted or taken out of service
                 (by setting this object to 'destroy' or 'outOfService'),
                 it must be not referenced from all associated
                 lines.
                "
            ::= { hwXdslSpectrumProfEntry 7 }

        hwXdslSpectrumProfRtxModeDs  OBJECT-TYPE
            SYNTAX      INTEGER
                        {
                         forbidden(0),
                         preferred(1),
                         forced(2),
                         testmode(3)
                        }
            MAX-ACCESS  read-create
            STATUS      current
            DESCRIPTION
                "The mode of operation of G.998.4 retransmission in downstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwXdslSpectrumProfEntry 8 }

        hwXdslSpectrumProfRtxModeUs  OBJECT-TYPE
            SYNTAX      INTEGER
                        {
                         forbidden(0),
                         preferred(1),
                         forced(2),
                         testmode(3)
                        }
            MAX-ACCESS  read-create
            STATUS      current
            DESCRIPTION
                "The mode of operation of G.998.4 retransmission in upstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwXdslSpectrumProfEntry 9 }

        hwXdslSpectrumProfProfLeftrThreshDs  OBJECT-TYPE
            SYNTAX      Unsigned32(0..99)
            UNITS       "0.01"
            MAX-ACCESS  read-create
            STATUS      current
            DESCRIPTION
                "If retransmission is used in downstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwXdslSpectrumProfEntry 10 }

        hwXdslSpectrumProfProfLeftrThreshUs  OBJECT-TYPE
            SYNTAX      Unsigned32(0..99)
            UNITS       "0.01"
            MAX-ACCESS  read-create
            STATUS      current
            DESCRIPTION
                "If retransmission is used in upstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwXdslSpectrumProfEntry 11 }

        --    hwXdslSpectrumProfModeSpecTable
        hwXdslSpectrumProfModeSpecTable  OBJECT-TYPE
            SYNTAX      SEQUENCE  OF  HwXdslSpectrumProfModeSpecEntry
            MAX-ACCESS  not-accessible
            STATUS      current
            DESCRIPTION
                "The table hwXdslSpectrumProfModeSpecTable extends the
                 XDSL line configuration profile by XDSL Mode Specific
                 parameters.
                 A row in this table that has an index of
                 hwVdslLconfProfVdslMode == defMode(1), is called a
                 'mandatory' row.
                 A row in this table that has an index such that
                 hwVdslLconfProfVdslMode is not equal to defMode(1),
                 is called an 'optional' row.
                 When a row in the hwVdslLineConfProfTable table
                 (the parent row) is created, the SNMP agent will
                 automatically create a 'mandatory' row in this table.
                 When the parent row is deleted, the SNMP agent will
                 automatically delete all associated rows in this table.
                 Any attempt to delete the 'mandatory' row using the
                 hwVdslLConfProfModeSpecRowStatus attribute will be
                 rejected by the SNMP agent.
                 The manager MAY create an 'optional' row in this table
                 using the hwVdslLConfProfModeSpecRowStatus attribute if
                 the parent row exists.
                 The manager MAY delete an 'optional' row in this table
                 using the hwVdslLConfProfModeSpecRowStatus attribute at
                 any time.
                 If the actual transmission mode of a DSL line does not
                 match one of the 'optional' rows in this table, then
                 the line will use the PSD configuration from the
                 'mandatory' row.
                 The indexes of this table are hwXdslSpectrumProfName and
                 hwXdslSpectrumProfXdslMode.
                "
            ::= { hwXdslProfileTIMode 3 }

        hwXdslSpectrumProfModeSpecEntry  OBJECT-TYPE
            SYNTAX      HwXdslSpectrumProfModeSpecEntry
            MAX-ACCESS  not-accessible
            STATUS      current
            DESCRIPTION
                "The table hwXdslSpectrumProfModeSpecTable extends the
                 XDSL line configuration profile by XDSL Mode Specific
                 parameters.
                 A row in this table that has an index of
                 hwVdslLconfProfVdslMode == defMode(1), is called a
                 'mandatory' row.
                 A row in this table that has an index such that
                 hwVdslLconfProfVdslMode is not equal to defMode(1),
                 is called an 'optional' row.
                 When a row in the hwVdslLineConfProfTable table
                 (the parent row) is created, the SNMP agent will
                 automatically create a 'mandatory' row in this table.
                 When the parent row is deleted, the SNMP agent will
                 automatically delete all associated rows in this table.
                 Any attempt to delete the 'mandatory' row using the
                 hwVdslLConfProfModeSpecRowStatus attribute will be
                 rejected by the SNMP agent.
                 The manager MAY create an 'optional' row in this table
                 using the hwVdslLConfProfModeSpecRowStatus attribute if
                 the parent row exists.
                 The manager MAY delete an 'optional' row in this table
                 using the hwVdslLConfProfModeSpecRowStatus attribute at
                 any time.
                 If the actual transmission mode of a DSL line does not
                 match one of the 'optional' rows in this table, then
                 the line will use the PSD configuration from the
                 'mandatory' row.
                 The indexes of this entry are hwXdslSpectrumProfName
                 and hwXdslSpectrumProfXdslMode.
                "
            INDEX  { hwXdslSpectrumProfName, hwXdslSpectrumProfXdslMode }
            ::= { hwXdslSpectrumProfModeSpecTable 1 }

        HwXdslSpectrumProfModeSpecEntry ::=
            SEQUENCE {
              hwXdslSpectrumProfXdslMode             HwXdslOperationModes,
              hwXdslSpectrumProfMaxNomPsdDs          Integer32,
              hwXdslSpectrumProfMaxNomPsdUs          Integer32,
              hwXdslSpectrumProfMaxNomAtpDs          Unsigned32,
              hwXdslSpectrumProfMaxNomAtpUs          Unsigned32,
              hwXdslSpectrumProfMaxAggRxPwrUs        Integer32,
              hwXdslSpectrumProfPsdMaskDs            HwXdslPsdMaskDs,
              hwXdslSpectrumProfPsdMaskUs            HwXdslPsdMaskUs,
              hwXdslSpectrumProfUpsPsdMaskSelection  HwXdslUpsPsdMaskSelection,
              hwXdslSpectrumProfPmMode               HwXdslLConfProfPmMode,
              hwXdslSpectrumProfL0Time               Unsigned32,
              hwXdslSpectrumProfL2Time               Unsigned32,
              hwXdslSpectrumProfL2Atpr               Unsigned32,
              hwXdslSpectrumProfL2Atprt              Unsigned32,
              hwXdslSpectrumProfModeSpecRowStatus    RowStatus
           }

        hwXdslSpectrumProfXdslMode    OBJECT-TYPE
            SYNTAX      HwXdslOperationModes
            MAX-ACCESS  not-accessible
            STATUS      current
            DESCRIPTION
                "The xDSL Mode is a way of categorizing the various xDSL
                 transmission modes into groups, each group (xDSL Mode) shares
                 the same PSD configuration.
                 There should be multiple entries in this table for a given
                 line profile in case multiple bits are set in
                 hwVdslLConfProfXtuTransSysEna for that profile.
                "
            REFERENCE    "DSL Forum TR-90, paragraph 5.1.8"
            ::= { hwXdslSpectrumProfModeSpecEntry 1 }

        hwXdslSpectrumProfMaxNomPsdDs  OBJECT-TYPE
            SYNTAX      Integer32(-600..-300)
            UNITS       "0.1 dBm/Hz"
            MAX-ACCESS  read-create
            STATUS      current
            DESCRIPTION
                "The maximum nominal transmit PSD in the downstream
                 direction during initialization and Showtime.  It ranges from
                 -600 to -300 units of 0.1 dBm/Hz.  (physical values are -60 to
                 -30 dBm/Hz).
                 Unit: 0.1 dBm/Hz
                "
            REFERENCE    "ITU-T G.997.1, paragraph 7.3.1.2"
            DEFVAL       { -400 }
            ::= { hwXdslSpectrumProfModeSpecEntry 2 }

        hwXdslSpectrumProfMaxNomPsdUs  OBJECT-TYPE
            SYNTAX      Integer32(-600..-300)
            UNITS       "0.1 dBm/Hz"
            MAX-ACCESS  read-create
            STATUS      current
            DESCRIPTION
                "The maximum nominal transmit PSD in the upstream direction
                 during initialization and Showtime.  It ranges from -600 to
                 -300 units of 0.1 dBm/Hz.  (physical values are -60 to
                 -30 dBm/Hz).
                 Unit: 0.1 dBm/Hz
                "
            REFERENCE    "ITU-T G.997.1, paragraph 7.3.1.2"
            DEFVAL       { -380 }
            ::= { hwXdslSpectrumProfModeSpecEntry 3 }

        hwXdslSpectrumProfMaxNomAtpDs  OBJECT-TYPE
            SYNTAX      Unsigned32 (0..510)
            UNITS       "0.1 dBm"
            MAX-ACCESS  read-create
            STATUS      current
            DESCRIPTION
                "The maximum nominal aggregate transmit power in the
                 downstream direction during initialization and Showtime. It
                 ranges from 0 to 510 units of 0.1 dBm (0 to 255 physical
                 values are 0 to 25.5 dBm, 256 to 510 physical values are
                 -25.5 to -0.1 dBm).
                 Unit: 0.1 dBm
                "
            REFERENCE    "ITU-T G.997.1, paragraph 7.3.1.2"
            DEFVAL       { 200 }
            ::= { hwXdslSpectrumProfModeSpecEntry 4 }

        hwXdslSpectrumProfMaxNomAtpUs  OBJECT-TYPE
            SYNTAX      Unsigned32 (0..510)
            UNITS       "0.1 dBm"
            MAX-ACCESS  read-create
            STATUS      current
            DESCRIPTION
               "The maximum nominal aggregate transmit power in the
                 upstream direction during initialization and Showtime. It
                 ranges from 0 to 510 units of 0.1 dBm (0 to 255 physical
                 values are 0 to 25.5 dBm, 256 to 510 physical values are
                 -25.5 to -0.1 dBm).
                 Unit: 0.1 dBm
                "
            REFERENCE    "ITU-T G.997.1, paragraph 7.3.1.2"
            DEFVAL       { 125 }
            ::= { hwXdslSpectrumProfModeSpecEntry 5 }

        hwXdslSpectrumProfMaxAggRxPwrUs  OBJECT-TYPE
            SYNTAX      Integer32(-255..255)
            UNITS       "0.1 dBm"
            MAX-ACCESS  read-create
            STATUS      current
            DESCRIPTION
                "The maximum upstream aggregate receive power over the relevant
                 set of sub-carriers.  The xTU-C should verify that the
                 upstream power cutback is such that this maximum aggregate
                 receive power value is honored.  It ranges from -255 to 255
                 units of 0.1 dBm (physical values are -25.5 to 25.5 dBm).
                 A value of all means that there is no limit.
                 Unit: 0.1 dBm
                "
            REFERENCE    "ITU-T G.997.1, paragraph 7.3.1.2"
            DEFVAL       { 125 }
            ::= { hwXdslSpectrumProfModeSpecEntry 6 }

        hwXdslSpectrumProfPsdMaskDs   OBJECT-TYPE
            SYNTAX      HwXdslPsdMaskDs
            MAX-ACCESS  read-create
            STATUS      current
            DESCRIPTION
                "This configuration parameter defines the downstream PSD mask
                 applicable at the U-C2 reference point.
                 This MIB PSD mask may impose PSD restrictions in addition
                 to the Limit PSD mask defined in the relevant Recommendation
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup.
                "
            REFERENCE    "ITU-T G.997.1(200604), paragraph 7.3.1.2.9"
            ::= { hwXdslSpectrumProfModeSpecEntry 7 }

        hwXdslSpectrumProfPsdMaskUs   OBJECT-TYPE
            SYNTAX      HwXdslPsdMaskUs
            MAX-ACCESS  read-create
            STATUS      current
            DESCRIPTION
                "This configuration parameter defines the upstream PSD
                 mask applicable at the U R2 reference point. This MIB
                 PSD mask may impose PSD restrictions in addition to the
                 Limit PSD mask defined in the relevant Recommendations
                 (e.g., ITU-T Recommendations G.992.3, G.993.2).
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup.
                "
            REFERENCE    "ITU-T G.997.1(200604), paragraph 7.3.1.2.12"
            ::= { hwXdslSpectrumProfModeSpecEntry 8 }

        hwXdslSpectrumProfUpsPsdMaskSelection    OBJECT-TYPE
            SYNTAX      HwXdslUpsPsdMaskSelection
            MAX-ACCESS  read-create
            STATUS      current
            DESCRIPTION
                "This configuration parameter defines which upstream PSD mask is enabled.
                 This parameter is used only for Annexes J and M of ITU T Recs G.992.3 and G.992.5.
                 As only one selection parameter is defined in the MIB,
                 the same selection value applies to all relevant modes enabled in the XTSE line configuration parameter.
                 It ranges from 1 to 9 and selects the mask with the following definition
                 This object is defaulted adlu-32/eu-32.
                "
            REFERENCE    "ITU-T G.997.1 (amendment 1), 7.3.1.1.10"
            ::= { hwXdslSpectrumProfModeSpecEntry 9 }

        hwXdslSpectrumProfPmMode  OBJECT-TYPE
            SYNTAX      HwXdslLConfProfPmMode
            MAX-ACCESS  read-create
            STATUS      current
            DESCRIPTION
                "Power management state enabling.  Defines the power states the
                 ATU-C or ATU-R may autonomously transition to on this line.
                 Options:
                 1. allowTransitionsToIdle (0)
                 2. allowTransitionsToLowPower (1)
                 A bit with a '1' value means that the ATU is allowed to transit
                 into the respective state and a '0' value means that the ATU is
                 not allowed to transit into the respective state.
                "
            REFERENCE    "ITU-T G.997.1, paragraph 7.3.1.1.4"
            DEFVAL  { allowTransitionsToIdle }
            ::= { hwXdslSpectrumProfModeSpecEntry 10 }

        hwXdslSpectrumProfL0Time  OBJECT-TYPE
            SYNTAX      Unsigned32 (0..255)
            UNITS       "seconds"
            MAX-ACCESS  read-create
            STATUS      current
            DESCRIPTION
                "This minimum time (in seconds) between an Exit from the L2
                 state and the next Entry into the L2 state.  It ranges from 0
                 to 255 seconds.
                 Unit: seconds
                "
            REFERENCE    "ITU-T G.997.1, paragraph 7.3.1.1.5"
            DEFVAL       { 255 }
            ::= { hwXdslSpectrumProfModeSpecEntry 11 }

        hwXdslSpectrumProfL2Time  OBJECT-TYPE
            SYNTAX      Unsigned32 (0..255)
            UNITS       "seconds"
            MAX-ACCESS  read-create
            STATUS      current
            DESCRIPTION
                "This minimum time (in seconds) between an Entry into the
                 L2 state and the first Power Trim in the L2 state and between
                 two consecutive Power Trims in the L2 State.
                 It ranges from 0 to 255 seconds.
                 Unit: seconds
                "
            REFERENCE    "ITU-T G.997.1, paragraph 7.3.1.1.6"
            DEFVAL       { 30 }
            ::= { hwXdslSpectrumProfModeSpecEntry 12 }

        hwXdslSpectrumProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 Unit: dB
                "
            REFERENCE    "ITU-T G.997.1 (amendment 1), 7.3.1.1.7"
            DEFVAL       { 3 }
            ::= { hwXdslSpectrumProfModeSpecEntry 13 }

        hwXdslSpectrumProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims.
                 Unit: dB
                "
            REFERENCE    "ITU-T G.997.1 (amendment 1), 7.3.1.1.9"
            DEFVAL       { 9 }
            ::= { hwXdslSpectrumProfModeSpecEntry 14 }

        hwXdslSpectrumProfModeSpecRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwXdslSpectrumProfModeSpecEntry 15 }

        --    hwXdslSpectrumProfSubProfTable
        hwXdslSpectrumProfSubProfTable  OBJECT-TYPE
            SYNTAX      SEQUENCE  OF  HwXdslSpectrumProfSubProfEntry
            MAX-ACCESS  not-accessible
            STATUS      current
            DESCRIPTION
                "The table hwXdslSpectrumProfSubProfTable extends the
                 XDSL line configuration profile by profile parameters.
                 The indexes of this table are hwXdslSpectrumProfName,
                 hwXdslSpectrumProfXdslMode, and hwXdslSpectrumProfSubProfiles.
                "
            ::= { hwXdslProfileTIMode 4 }

        hwXdslSpectrumProfSubProfEntry  OBJECT-TYPE
            SYNTAX      HwXdslSpectrumProfSubProfEntry
            MAX-ACCESS  not-accessible
            STATUS      current
            DESCRIPTION
                "The table hwXdslSpectrumProfSubProfTable extends the
                 XDSL line configuration profile by profile parameters.
                 The indexes of this entry are hwXdslSpectrumProfName,
                 hwXdslSpectrumProfXdslMode, and hwXdslSpectrumProfSubProfiles.
                "
            INDEX  { hwXdslSpectrumProfName, hwXdslSpectrumProfXdslMode, hwXdslSpectrumProfSubProfiles}
            ::= { hwXdslSpectrumProfSubProfTable 1 }

        HwXdslSpectrumProfSubProfEntry ::=
            SEQUENCE {
              hwXdslSpectrumProfSubProfiles          HwXdslSubProfiles,
              hwXdslSpectrumProfSubProfilesWeight    HwXdslSubProfilesWeight,
              hwXdslSpectrumProfPsdClassMask         HwXdslTIPsdClassMask,
              hwXdslSpectrumProfPsdLimitMask         HwXdslPsdLimitMask,
              hwXdslSpectrumProfUs0PsdMask           HwXdslUs0PsdMask,
              hwXdslSpectrumProfUs0Disable           HwXdslUs0Disable,
              hwXdslSpectrumProfSubProfRowStatus     RowStatus
            }

        hwXdslSpectrumProfSubProfiles    OBJECT-TYPE
            SYNTAX      HwXdslSubProfiles
            MAX-ACCESS  not-accessible
            STATUS      current
            DESCRIPTION
                "This configuration parameter contains the G.993.2 profiles
                 to be allowed by the near-end xTU on this line.
                 This object is defaulted Profile17a.
                "
            REFERENCE    "ITU-T G.997.1 (amendment 1), 7.3.1.1.11"

            ::= { hwXdslSpectrumProfSubProfEntry 1 }

        hwXdslSpectrumProfSubProfilesWeight    OBJECT-TYPE
            SYNTAX      HwXdslSubProfilesWeight
            MAX-ACCESS  read-create
            STATUS      current
            DESCRIPTION
                "This configuration parameter contains the G.993.2 profiles' weight
                 to be allowed by the near-end xTU on this line. This object is defaulted
                 priorityWeight1.
                "
            REFERENCE    "ITU-T G.997.1 (amendment 1), 7.3.1.1.11"
            ::= { hwXdslSpectrumProfSubProfEntry 2 }

        hwXdslSpectrumProfPsdClassMask    OBJECT-TYPE
            SYNTAX      HwXdslTIPsdClassMask
            MAX-ACCESS  read-create
            STATUS      current
            DESCRIPTION
                "(CLASSMASK).
                 In order to reduce the number of configuration
                 possibilities, the limit Power Spectral Density masks
                 (see LIMITMASK) are grouped in PSD mask classes.
                 Each class is designed such that the PSD levels of each
                 limit PSD mask of a specific class are equal in their
                 respective passband above 276 kHz.
                 This parameter is defined per XDSL Annex enabled in the
                 xdsl2LConfProfXtuTransSysEna object. It selects a single
                 PSD mask class per Annex that is activated at the
                 VTU-O. This object is defaulted  A998/B997M1c/C998.
                "
            REFERENCE    "ITU-T G.997.1, paragraph #7.3.1.1.12"
            ::= { hwXdslSpectrumProfSubProfEntry 3 }

        hwXdslSpectrumProfPsdLimitMask    OBJECT-TYPE
            SYNTAX      HwXdslPsdLimitMask
            MAX-ACCESS  read-create
            STATUS      current
            DESCRIPTION
                "(LIMITMASK).
                 This configuration parameter contains the G.993.2 limit
                 PSD masks of the selected PSD mask class, enabled by the
                 near-end xTU on this line for each class of profiles.
                 This parameter is defined per XDSL Annex enabled in the
                 xdsl2LConfProfXtuTransSysEna object.
                 Through this parameter several limit PSD masks of the
                 selected PSD mask class (xdsl2LConfProfClassMask) may be
                 enabled. The enabling parameter is coded in a bitmap
                 representation (0 if the associated mask is not allowed,
                 1 if it is allowed).This object is defaulted AnnexB998-M2x-B.
                "
            REFERENCE    "ITU-T G.997.1, paragraph #7.3.1.1.13"
            ::= { hwXdslSpectrumProfSubProfEntry 4 }

        hwXdslSpectrumProfUs0PsdMask    OBJECT-TYPE
            SYNTAX      HwXdslUs0PsdMask
            MAX-ACCESS  read-create
            STATUS      current
            DESCRIPTION
                "This parameter contains the US0 PSD masks to be allowed by
                 the near-end xTU on the line. This parameter is only defined for G.993.2 Annex A.
                 It is represented as a bitmap (0 if not allowed and 1 if allowed) with the following definitions.
                 This object is defaulted ADLU-32/EU-32.
                "
            REFERENCE    "ITU-T G.997.1 (amendment 1), 7.3.1.1.15"
            ::= { hwXdslSpectrumProfSubProfEntry 5 }

        hwXdslSpectrumProfUs0Disable    OBJECT-TYPE
            SYNTAX      HwXdslUs0Disable
            MAX-ACCESS  read-create
            STATUS      current
            DESCRIPTION
                "This configuration parameter indicates if the use of US0 is disabled
                 for each limit PSD mask enabled in the LIMITMASK parameter. This object is defaulted Unused.
                "
            REFERENCE    "ITU-T G.997.1 (amendment 1), 7.3.1.1.14"
            ::= { hwXdslSpectrumProfSubProfEntry 6 }

        hwXdslSpectrumProfSubProfRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwXdslSpectrumProfSubProfEntry 7 }


        --        hwXdslDpboProfTable
        hwXdslDpboProfTable  OBJECT-TYPE
            SYNTAX      SEQUENCE  OF  HwXdslDpboProfEntry
            MAX-ACCESS  not-accessible
            STATUS      current
            DESCRIPTION
                "The table hwXdslDpboProfTable contains XDSL DPBO
                 configuration.
                 The index of this table is hwXdslDpboProfName.
                 A default profile with an index of 'DEFVAL' will
                 always exist and its parameters will be set to vendor-specific
                 values, unless otherwise specified in this document.
                "
            ::= { hwXdslProfileTIMode 5 }

        hwXdslDpboProfEntry  OBJECT-TYPE
            SYNTAX      HwXdslDpboProfEntry
            MAX-ACCESS  not-accessible
            STATUS      current
            DESCRIPTION
                "The table hwXdslDpboProfTable contains XDSL DPBO
                 configuration.
                 The index of this entry is hwXdslDpboProfName.
                 A default profile with an index of 'DEFVAL' will
                 always exist and its parameters will be set to vendor-specific
                 values, unless otherwise specified in this document.
                "
            INDEX  { IMPLIED hwXdslDpboProfName }
            ::= { hwXdslDpboProfTable 1 }

        HwXdslDpboProfEntry  ::=
            SEQUENCE {
              hwXdslDpboProfName       OCTET STRING,
              hwXdslDpboProfWkMdMask   Unsigned32,
              hwXdslDpboProfEpsd       HwXdslDpboEpsd,
              hwXdslDpboProfEsel       Unsigned32,
              hwXdslDpboProfEscm       HwXdslDpboEscm,
              hwXdslDpboProfMus       Unsigned32,
              hwXdslDpboProfFmin        Unsigned32,
              hwXdslDpboProfFmax        Unsigned32,
              hwXdslDpboProfRowStatus  RowStatus,
              hwXdslDpboProfEselMin    Unsigned32
            }

        hwXdslDpboProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { hwXdslDpboProfEntry 1 }

        hwXdslDpboProfWkMdMask  OBJECT-TYPE
            SYNTAX      Unsigned32 (0..511)
            MAX-ACCESS  read-create
            STATUS      current
            DESCRIPTION
                "This configuration parameter defines the current enabled DPBO working mode mask.
                 DPBO working mode enabling:1-ADSL, 2-ADSL2+ 3-VDSL2.
                 Options:
                 1. current enabled dpbo work mode:ADSL
                 2. current enabled dpbo work mode:ADSL2+
                 3. current enabled dpbo work mode:ADSL,ADSL2+
                 4. current enabled dpbo work mode:VDSL2
                 5. current enabled dpbo work mode:ADSL,VDSL2
                 6. current enabled dpbo work mode:ADSL2+,VDSL2
                 7. current enabled dpbo work mode:ADSL,ADSL2+,VDSL2
                "
            DEFVAL       { 7 }
            ::= { hwXdslDpboProfEntry 2 }

        hwXdslDpboProfEpsd  OBJECT-TYPE
            SYNTAX      HwXdslDpboEpsd
            MAX-ACCESS  read-create
            STATUS      current
            DESCRIPTION
               "This parameter defines the PSD mask that is assumed to be permitted at the exchange.
                This parameter shall use the same format as PSDMASKds.The maximum number of breakpoints
                for DPBOEPSD is 16.
                This is a string of 16 pairs of values in the following
                structure:
                Octets 0+1 - Index of 1st sub-carrier used in the context
                             of a first breakpoint.
                Octet 2    - The PSD reduction for the sub-carrier indicated in
                            octets 0 and 1.
                Octets 3-5 - Same, for a 2nd breakpoint.
                Octets 6-8 - Same, for a 3rd breakpoint.
                This architecture continues until octets 45-47, which are
                associated with a 16th breakpoint.
                Each subcarrier index is an unsigned number in the range 1 and
                NSCds.  Each PSD reduction value is in the range 0 (0dBm/Hz) to
                255 (-127.5dBm/Hz) with steps of 0.5dBm/Hz.  Valid values are
                in the range 0 to 190 (0 to -95dBm/Hz).
                When the number of breakpoints is less than 16, all remaining
                octets are set to the value 0xff.
               "
             REFERENCE    "ITU-T G.997.1(200604), paragraph 7.3.1.2.13"
            ::= { hwXdslDpboProfEntry 3 }

        hwXdslDpboProfEsel  OBJECT-TYPE
            SYNTAX      Unsigned32 (0..511)
            UNITS       "0.5dB"
            MAX-ACCESS  read-create
            STATUS      current
            DESCRIPTION
               "This configuration parameter defines the assumed electrical length of
                cables (E-side cables) connecting exchange based DSL services to a remote
                flexibility point (cabinet), that hosts the xTU-C that is subject to
                spectrally shaped downstream power back-off depending on this length.
                For this parameter the electrical length is defined as the loss (in dB)
                of an equivalent length of hypothetical cable at a reference frequency
                defined by the network operator or in spectrum management regulations.
                DPBOESEL shall be coded as an unsigned integer representing an electrical
                length from 0 dB (coded as 0) to 255.5 dB (coded as 511) in steps of 0.5 dB.
                All values in the range are valid.If DPBOESEL is set to zero, the DPBO in
                this section shall be disabled.
                Unit: 0.5dB
               "
             REFERENCE    "ITU-T G.997.1(200604), paragraph 7.3.1.2.13"
             DEFVAL       { 0 }
            ::= { hwXdslDpboProfEntry 4 }

        hwXdslDpboProfEscm  OBJECT-TYPE
            SYNTAX      HwXdslDpboEscm
            MAX-ACCESS  read-create
            STATUS      current
            DESCRIPTION
                "This configuration parameter defines a cable model in terms of three scalars
                 DPBOESCMA, DPBOESCMB and DPBOESCMC that shall be used to describe the frequency
                 dependent loss of E-side cables.Parameters DPBOESCMA, DPBOESCMB, DPBOESCMC shall be
                 coded as unsigned integers representing a scalar value from -1 (coded as 0) to 1.5
                 (coded as 640) in step of 1/256. All values in the range are valid.
                 Octets 0+1 DPBOESCMA
                 Octets 2+3 DPBOESCMB
                 Octets 4+5 DPBOESCMC
                "
             REFERENCE    "ITU-T G.997.1(200604), paragraph 7.3.1.2.13"
            ::= { hwXdslDpboProfEntry 5 }

        hwXdslDpboProfMus  OBJECT-TYPE
            SYNTAX      Unsigned32 (0..255)
            UNITS       "-0.5dBm/Hz"
            MAX-ACCESS  read-create
            STATUS      current
            DESCRIPTION
                "DPBOMUS defines the assumed Minimum Usable receive Signal PSD (in dBm/Hz) for
                 exchange based services, used to modify parameter DPBOFMAX defined below. It
                 shall be coded as an unsigned integer representing a PSD level from 0 dBm/Hz
                 (coded as 0) to -127.5 dBm/Hz (coded as 255) in steps of 0.5 dBm/Hz.
                 All values in the range are valid.
                 Unit: -0.5dBm/Hz
                "
             REFERENCE    "ITU-T G.997.1(200604), paragraph 7.3.1.2.13"
             DEFVAL       { 180 }
            ::= { hwXdslDpboProfEntry 6 }

        hwXdslDpboProfFmin  OBJECT-TYPE
            SYNTAX      Unsigned32 (0..2048)
            UNITS       "4.3125 KHz"
            MAX-ACCESS  read-create
            STATUS      current
            DESCRIPTION
                "DPBOFMIN defines the minimum frequency from which the DPBO shall be applied.
                 It shall be coded as a 16 bits unsigned integer representing a frequency in
                 multiple of 4.3125 KHz. The range of valid values is from 0 kHz (coded as 0)
                 to 8832 kHz (coded as 2048).
                 Unit: 4.3125 KHz
                "
             REFERENCE    "ITU-T G.997.1(200604), paragraph 7.3.1.2.13"
             DEFVAL       { 0 }
            ::= { hwXdslDpboProfEntry 7 }

        hwXdslDpboProfFmax  OBJECT-TYPE
            SYNTAX      Unsigned32 (32..6956)
            UNITS       "4.3125 KHz"
            MAX-ACCESS  read-create
            STATUS      current
            DESCRIPTION
                "DPBOFMAX defines the maximum frequency at which DPBO may be applied. It shall be
                 coded as a 16 bits unsigned integer representing a frequency in multiple of 4.3125 KHz.
                 The range of valid values is from 138 kHz (coded as 32) to 29997.75 kHz (coded as 6956).
                 Unit: 4.3125 KHz
                "
             REFERENCE    "ITU-T G.997.1(200604), paragraph 7.3.1.2.13"
             DEFVAL       { 511 }
            ::= { hwXdslDpboProfEntry 8 }

        hwXdslDpboProfRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwXdslDpboProfEntry 9 }

        hwXdslDpboProfEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and XDSL provision of additional KVz areas from this KVz
                 using cross-cables to additional KVz), including the KVz at the MSAN site. This value must
                 be adjustable as the minimum requirement via the SNMP interface in the configuration profile
                 for each XDSL2 port, and is set individually for each MSAN site and usage. As an option,
                 As an option, adjustment can be done for each MSAN or line card, thus taking effect for
                 entire port groups. It is used only for determining the MUF.
                 Unit: 0.5dB
                "
            ::= { hwXdslDpboProfEntry 65535 }

        --        hwXdslUpboProfTable
        hwXdslUpboProfTable  OBJECT-TYPE
            SYNTAX      SEQUENCE  OF  HwXdslUpboProfEntry
            MAX-ACCESS  not-accessible
            STATUS      current
            DESCRIPTION
                "The table hwXdslUpboProfTable contains XDSL upbo
                 configuration. The index of this table is hwXdslUpboProfName.
                 A default profile with an index of 'DEFVAL' will
                 always exist and its parameters will be set to vendor-specific
                 values, unless otherwise specified in this document.
                "
            ::= { hwXdslProfileTIMode 6 }

        hwXdslUpboProfEntry  OBJECT-TYPE
            SYNTAX      HwXdslUpboProfEntry
            MAX-ACCESS  not-accessible
            STATUS      current
            DESCRIPTION
                "The table hwXdslUpboProfTable contains XDSL upbo
                 configuration .
                 The index of this entry is hwXdslUpboProfName.
                 A default profile with an index of 'DEFVAL' will
                 always exist and its parameters will be set to vendor-specific
                 values, unless otherwise specified in this document.
                "
            INDEX  { IMPLIED hwXdslUpboProfName }
            ::= { hwXdslUpboProfTable 1 }

        HwXdslUpboProfEntry  ::=
            SEQUENCE {
              hwXdslUpboProfName        OCTET STRING,
              hwXdslUpboProfPsdBand     HwXdslUpboPsdBand,
              hwXdslUpboProfKl          Unsigned32,
              hwXdslUpboProfKlf         HwXdslUpboKlf,
              hwXdslUpboProfKlAuto     Unsigned32,
              hwXdslUpboProfRowStatus   RowStatus,
              hwXdslUpboProfBoostMode   HwXdslUpboBoostMode,
              hwXdslUpboProfKl0RefBand  HwXdslUpboKl0RefBand
            }

        hwXdslUpboProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { hwXdslUpboProfEntry 1 }

        hwXdslUpboProfPsdBand  OBJECT-TYPE
            SYNTAX      HwXdslUpboPsdBand
            MAX-ACCESS  read-create
            STATUS      current
            DESCRIPTION
                "This parameter defines the UPBO reference PSD used to compute the upstream power back-off
                 for each upstream band. A UPBOPSD defined for each band shall consist of two
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps
                 of 0.01 dBm/Hz. The UPBO reference PSD at the frequency f expressed in MHz shall be equal
                 to '-a-b(SQRT(f))'. The set of parameter values a = 40 dBm/Hz, b = 0 dBm/Hz is a special configuration
                 to disable UPBO in the respective upstream band.
                 Octets 0+1 -   a[0]
                 Octets 2+3 -   b[0]
                 Octets 4+5 -   a[1]
                 Octets 6+7 -   b[1]
                 Octets 8+9 -   a[2]
                 Octets 10+11 - b[2]
                 Octets 12+13 - a[3]
                 Octets 14+15 - b[3]
                 Octets 16+17 - a[4]
                 Octets 18+19 - b[4]
                "
           REFERENCE    "ITU-T G.997.1(200604), paragraph 7.3.1.2.14"
           ::= { hwXdslUpboProfEntry 2 }

        hwXdslUpboProfKl  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0)
                 to 128 dB (coded as 1280) in steps of 0.1 dB.
                 Unit: 0.1 dB
                "
            REFERENCE    "ITU-T G.997.1(200604), paragraph 7.3.1.2.14"
            DEFVAL       { 0 }
            ::= { hwXdslUpboProfEntry 3 }

        hwXdslUpboProfKlf  OBJECT-TYPE
            SYNTAX      HwXdslUpboKlf
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                "
            REFERENCE    "ITU-T G.997.1(200604), paragraph 7.3.1.2.14"
            DEFVAL       { auto }
            ::= { hwXdslUpboProfEntry 4 }

        hwXdslUpboProfKlAuto  OBJECT-TYPE
            SYNTAX      Unsigned32(1..4)
            MAX-ACCESS  read-create
            STATUS      current
            DESCRIPTION
                "This parameter defines the mode in which kl0 is computed when HwXdslUpboKlf is auto.
                 The value is defined as below:
                 1-max(kl0CO,kl0CPE)
                 2-min(kl0CO,kl0CPE)
                 3-kl0CO
                 4-kl0CPE
                 The default value is 3
                 "
            DEFVAL       { 3 }
            ::= { hwXdslUpboProfEntry 5 }

        hwXdslUpboProfRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwXdslUpboProfEntry 6 }

        hwXdslUpboProfBoostMode  OBJECT-TYPE
            SYNTAX      HwXdslUpboBoostMode
            MAX-ACCESS  read-create
                  STATUS      current
            DESCRIPTION
               "This object indicates whether the equalized FEXT UPBO method is supported or not.
               Options:
               1. disable(1)  - The Equalized FEXT UPBO method is not supported
               2. enable(2)   - The Equalized FEXT UPBO method is supported
              "
            DEFVAL       { enable }
            ::= { hwXdslUpboProfEntry 65535 }

        hwXdslUpboProfKl0RefBand  OBJECT-TYPE
            SYNTAX      HwXdslUpboKl0RefBand
            MAX-ACCESS  read-create
            STATUS      current
            DESCRIPTION
               "Octets 0+1 - length[1]
                Octets 2+3 - length[2]
                Octets 4+5 - length[3]
                Octets 6+7 - length[4]
               "
            REFERENCE
               "This parameter defines the UPBO reference electrical length used to compute the
                upstream power back-off for each upstream band except US0, for the optional Equalized FEXT UPBO
                method. The value ranges from 1.8 to 63.5 dB in steps of 0.1 dB with special value 0.The special
                value 0 indicates optional Equalized FEXT UPBO method is not supported.
               "
            ::= { hwXdslUpboProfEntry 65536 }

        --        hwXdslNoiseMarginProfTable
        hwXdslNoiseMarginProfTable  OBJECT-TYPE
            SYNTAX      SEQUENCE  OF  HwXdslNoiseMarginProfEntry
            MAX-ACCESS  not-accessible
            STATUS      current
            DESCRIPTION
                "The table hwXdslNoiseMarginProfTable contains XDSL noise margin
                 configuration.
                 The index of this table is hwXdslNoiseMarginProfName.
                 A default profile with an index of 'DEFVAL' will
                 always exist and its parameters will be set to vendor-specific
                 values, unless otherwise specified in this document.
                "
            ::= { hwXdslProfileTIMode 7 }

        hwXdslNoiseMarginProfEntry  OBJECT-TYPE
            SYNTAX      HwXdslNoiseMarginProfEntry
            MAX-ACCESS  not-accessible
            STATUS      current
            DESCRIPTION
                "The table hwXdslNoiseMarginProfTable contains XDSL noise margin
                 configuration.
                 The index of this entry is hwXdslNoiseMarginProfName.
                 A default profile with an index of 'DEFVAL' will
                 always exist and its parameters will be set to vendor-specific
                 values, unless otherwise specified in this document.
                "
            INDEX  { IMPLIED hwXdslNoiseMarginProfName }
            ::= { hwXdslNoiseMarginProfTable 1 }

        HwXdslNoiseMarginProfEntry  ::=
            SEQUENCE {
              hwXdslNoiseMarginProfName              OCTET STRING,
              hwXdslNoiseMarginProfTargetSnrmDs      Unsigned32,
              hwXdslNoiseMarginProfTargetSnrmUs      Unsigned32,
              hwXdslNoiseMarginProfMaxSnrmDs         Unsigned32,
              hwXdslNoiseMarginProfMaxSnrmUs         Unsigned32,
              hwXdslNoiseMarginProfMinSnrmDs         Unsigned32,
              hwXdslNoiseMarginProfMinSnrmUs         Unsigned32,
              hwXdslNoiseMarginProfRaUsNrmDs         Unsigned32,
              hwXdslNoiseMarginProfRaUsNrmUs         Unsigned32,
              hwXdslNoiseMarginProfRaUsTimeDs        Unsigned32,
              hwXdslNoiseMarginProfRaUsTimeUs        Unsigned32,
              hwXdslNoiseMarginProfRaDsNrmsDs        Unsigned32,
              hwXdslNoiseMarginProfRaDsNrmsUs        Unsigned32,
              hwXdslNoiseMarginProfRaDsTimeDs        Unsigned32,
              hwXdslNoiseMarginProfRaDsTimeUs        Unsigned32,
              hwXdslNoiseMarginProfDsThresholdDs     Unsigned32,
              hwXdslNoiseMarginProfUsThresholdDs     Unsigned32,
              hwXdslNoiseMarginProfDsThresholdUs     Unsigned32,
              hwXdslNoiseMarginProfUsThresholdUs     Unsigned32,
              hwXdslNoiseMarginProfRowStatus         RowStatus
            }

        hwXdslNoiseMarginProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { hwXdslNoiseMarginProfEntry 1 }

        hwXdslNoiseMarginProfTargetSnrmDs  OBJECT-TYPE
            SYNTAX      Unsigned32(0..310)
            UNITS       "0.1 dB"
            MAX-ACCESS  read-create
            STATUS      current
            DESCRIPTION
                "The minimum Noise Margin the xTU-R receiver shall achieve,
                 relative to the BER requirement for each of the downstream
                 bearer channels, to successfully complete initialization.
                 The target noise margin ranges from 0 to 310 units of 0.1 dB
                 (Physical values are 0 to 31 dB).
                 Unit: 0.1 dB
                "
            REFERENCE    "ITU-T G.997.1, paragraph 7.3.1.3.1"
            DEFVAL       { 60 }
            ::= { hwXdslNoiseMarginProfEntry 2 }

        hwXdslNoiseMarginProfTargetSnrmUs  OBJECT-TYPE
            SYNTAX      Unsigned32(0..310)
            UNITS       "0.1 dB"
            MAX-ACCESS  read-create
            STATUS      current
            DESCRIPTION
                "The minimum Noise Margin the xTU-C receiver shall achieve,
                 relative to the BER requirement for each of the upstream
                 bearer channels, to successfully complete initialization.
                 The target noise margin ranges from 0 to 310 units of 0.1 dB
                 (Physical values are 0 to 31 dB).
                 Unit: 0.1 dB
                "
            REFERENCE    "ITU-T G.997.1, paragraph 7.3.1.3.2"
            DEFVAL       { 60 }
            ::= { hwXdslNoiseMarginProfEntry 3 }

        hwXdslNoiseMarginProfMaxSnrmDs  OBJECT-TYPE
            SYNTAX      Unsigned32
            UNITS       "0.1 dB"
            MAX-ACCESS  read-create
            STATUS      current
            DESCRIPTION
                "The maximum Noise Margin the xTU-R receiver shall try to
                 sustain.  If the Noise Margin is above this level, the xTU-R
                 shall request that the xTU-C reduce the xTU-C transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.3"
            DEFVAL       { 310 }
            ::= { hwXdslNoiseMarginProfEntry 4 }

        hwXdslNoiseMarginProfMaxSnrmUs  OBJECT-TYPE
            SYNTAX      Unsigned32
            UNITS       "0.1 dB"
            MAX-ACCESS  read-create
            STATUS      current
            DESCRIPTION
                "The maximum Noise Margin the xTU-C receiver shall try to
                 sustain.  If the Noise Margin is above this level, the xTU-C
                 shall request that the xTU-R reduce the xTU-R transmit power
                 to get a noise margin below this limit (if this functionality
                 is supported).  The maximum noise margin ranges from 0 to 310
                 units of 0.1 dB (Physical values are 0 to 31 dB).  A value of
                 all 1's means that there is no maximum.
                 Unit: 0.1 dB
                "
            REFERENCE    "ITU-T G.997.1, paragraph 7.3.1.3.4"
            DEFVAL       { 310 }
            ::= { hwXdslNoiseMarginProfEntry 5 }

        hwXdslNoiseMarginProfMinSnrmDs  OBJECT-TYPE
            SYNTAX      Unsigned32(0..310)
            UNITS       "0.1 dB"
            MAX-ACCESS  read-create
            STATUS      current
            DESCRIPTION
                "The minimum Noise Margin the xTU-R receiver shall tolerate.
                 If the noise margin falls below this level, the xTU-R shall
                 request that the xTU-C increase the xTU-C transmit power.
                 If an increase to xTU-C transmit power is not possible, a
                 loss-of-margin (LOM) defect occurs, the xTU-R shall fail and
                 attempt to reinitialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.5"
            DEFVAL       { 10 }
            ::= { hwXdslNoiseMarginProfEntry 6 }

        hwXdslNoiseMarginProfMinSnrmUs  OBJECT-TYPE
            SYNTAX      Unsigned32(0..310)
            UNITS       "0.1 dB"
            MAX-ACCESS  read-create
            STATUS      current
            DESCRIPTION
                "The minimum Noise Margin the xTU-C receiver shall tolerate.
                 If the noise margin falls below this level, the xTU-C shall
                 request that the xTU-R increase the xTU-R transmit power.
                 If an increase of xTU-R transmit power is not possible, a
                 loss-of-margin (LOM) defect occurs, the xTU-C shall fail and
                 attempt to re-initialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.6"
            DEFVAL       { 10 }
            ::= { hwXdslNoiseMarginProfEntry 7 }

        hwXdslNoiseMarginProfRaUsNrmDs  OBJECT-TYPE
            SYNTAX      Unsigned32(0..310)
            UNITS       "0.1 dB"
            MAX-ACCESS  read-create
            STATUS      current
            DESCRIPTION
                "The Downstream Up-Shift Noise Margin value, to be used when
                 hwXdslLineConfRaModeDs is set to DynamicRa.  If the downstream
                 noise margin is above this value and stays above it for
                 more than the time specified by the hwXdslServProfRaUsTimeDs,
                 the xTU-R shall attempt to increase the downstream net data
                 rate.  The Downstream Up-shift Noise Margin ranges from 0 to
                 310 units of 0.1 dB (Physical values are 0 to 31 dB).
                 Unit: 0.1 dB
                "
            REFERENCE    "ITU-T G.997.1, paragraph 7.3.1.4.3"
            DEFVAL       { 310 }
            ::= { hwXdslNoiseMarginProfEntry 8 }

        hwXdslNoiseMarginProfRaUsNrmUs  OBJECT-TYPE
            SYNTAX      Unsigned32(0..310)
            UNITS       "0.1 dB"
            MAX-ACCESS  read-create
            STATUS      current
            DESCRIPTION
                "The Upstream Up-Shift Noise Margin value, to be used when
                 hwXdslLineConfRaModeUs is set to DynamicRa.  If the upstream
                 noise margin is above this value and stays above it for more
                 than the time specified by the hwXdslLineConfRaUsTimeUs, the
                 xTU-C shall attempt to increase the upstream net data rate.
                 The Upstream Up-shift Noise Margin ranges from 0 to 310 units
                 of 0.1 dB (Physical values are 0 to 31 dB).
                 Unit: 0.1 dB
                "
            REFERENCE    "ITU-T G.997.1, paragraph 7.3.1.4.4"
            DEFVAL       { 310 }
            ::= { hwXdslNoiseMarginProfEntry 9 }

        hwXdslNoiseMarginProfRaUsTimeDs  OBJECT-TYPE
            SYNTAX      Unsigned32(0..16383)
            UNITS       "seconds"
            MAX-ACCESS  read-create
            STATUS      current
            DESCRIPTION
                "The Downstream Up-Shift Time Interval, to be used when
                 hwXdslLineConfRaModeDs is set to DynamicRa.  The interval of
                 time that the downstream noise margin should stay above the
                 Downstream Up-shift Noise Margin before the xTU-R shall
                 attempt to increase the downstream net data rate.
                 Unit: seconds
                "
            REFERENCE    "ITU-T G.997.1, paragraph 7.3.1.4.5"
            DEFVAL       { 3600 }
            ::= { hwXdslNoiseMarginProfEntry 10 }

        hwXdslNoiseMarginProfRaUsTimeUs  OBJECT-TYPE
            SYNTAX      Unsigned32(0..16383)
            UNITS       "seconds"
            MAX-ACCESS  read-create
            STATUS      current
            DESCRIPTION
                "The Upstream Up-Shift Time Interval, to be used when
                 hwXdslLineConfRaModeUs is set to DynamicRa.  The interval of
                 time the upstream noise margin should stay above the
                 Upstream Up-shift Noise Margin before the xTU-C shall
                 attempt to increase the upstream net data rate.
                 Unit: seconds
                "
            REFERENCE    "ITU-T G.997.1, paragraph 7.3.1.4.6"
            DEFVAL       { 3600 }
            ::= { hwXdslNoiseMarginProfEntry 11 }

        hwXdslNoiseMarginProfRaDsNrmsDs  OBJECT-TYPE
            SYNTAX      Unsigned32(0..310)
            UNITS       "0.1 dB"
            MAX-ACCESS  read-create
            STATUS      current
            DESCRIPTION
                "The Downstream Down-Shift Noise Margin value, to be used when
                 hwXdslLineConfRaModeDs is set to DynamicRa.  If the downstream
                 noise margin is below this value and stays below that for more
                 than the time specified by the hwXdslLineConfRaDsTimeDs, the
                 xTU-R shall attempt to decrease the downstream net data rate.
                 The Downstream Down-shift Noise Margin ranges from 0 to 310
                 units of 0.1 dB (Physical values are 0 to 31 dB).
                 Unit: 0.1 dB
                "
            REFERENCE    "ITU-T G.997.1, paragraph 7.3.1.4.7"
            DEFVAL       { 10 }
            ::= { hwXdslNoiseMarginProfEntry 12 }

        hwXdslNoiseMarginProfRaDsNrmsUs  OBJECT-TYPE
            SYNTAX      Unsigned32(0..310)
            UNITS       "0.1 dB"
            MAX-ACCESS  read-create
            STATUS      current
            DESCRIPTION
                "The Upstream Down-shift Noise Margin value, to be used when
                 hwXdslLineConfRaModeUs is set to DynamicRa.  If the upstream
                 noise margin is below this value and stays below that for more
                 than the time specified by the hwXdslLineConfRaDsTimeUs, the
                 xTU-C shall attempt to decrease the upstream net data rate.
                 The Upstream Down-shift Noise Margin ranges from 0 to 310
                 units of 0.1 dB (Physical values are 0 to 31 dB).
                 Unit: 0.1 dB
                "

            REFERENCE    "ITU-T G.997.1, paragraph 7.3.1.4.8"
            DEFVAL       { 10 }
            ::= { hwXdslNoiseMarginProfEntry 13 }

        hwXdslNoiseMarginProfRaDsTimeDs  OBJECT-TYPE
            SYNTAX      Unsigned32(0..16383)
            UNITS       "seconds"
            MAX-ACCESS  read-create
            STATUS      current
            DESCRIPTION
                "The Downstream Down-shift Time Interval, to be used when
                 hwXdslLineConfRaModeDs is set to DynamicRa.  The interval of
                 time the downstream noise margin should stay below the
                 Downstream Down-shift Noise Margin before the xTU-R shall
                 attempt to decrease the downstream net data rate.
                 Unit: seconds
                "
            REFERENCE    "ITU-T G.997.1, paragraph 7.3.1.4.9"
            DEFVAL       { 3600 }
            ::= { hwXdslNoiseMarginProfEntry 14 }

        hwXdslNoiseMarginProfRaDsTimeUs  OBJECT-TYPE
            SYNTAX      Unsigned32(0..16383)
            UNITS       "seconds"
            MAX-ACCESS  read-create
            STATUS      current
            DESCRIPTION
                "The Upstream Down-Shift Time Interval, to be used when
                 hwXdslLineConfRaModeUs is set to DynamicRa.  The interval of
                 time the upstream noise margin should stay below the Upstream
                 Down-shift Noise Margin before the xTU-C shall attempt to
                 decrease the upstream net data rate.
                 Unit: seconds
                "
            REFERENCE    "ITU-T G.997.1, paragraph 7.3.1.4.10"
            DEFVAL       { 3600 }
            ::= { hwXdslNoiseMarginProfEntry 15 }

        hwXdslNoiseMarginProfDsThresholdDs  OBJECT-TYPE
            SYNTAX      Unsigned32(0..200000000)
            UNITS       "bits/second"
            MAX-ACCESS  read-create
            STATUS      current
            DESCRIPTION
                "Data Rate Threshold Down-shift for downstream direction.  A
                 'Down-shift rate change' event is triggered when the actual
                 downstream data rate is below the data rate at the last entry
                 into Showtime, by more than the threshold.  The parameter is
                 coded in bit/s.
                 Unit: bits/second
                "
            REFERENCE    "ITU-T G.997.1, paragraph 7.3.2.6"
            DEFVAL       { 0 }
            ::= { hwXdslNoiseMarginProfEntry 16 }

        hwXdslNoiseMarginProfUsThresholdDs  OBJECT-TYPE
            SYNTAX      Unsigned32(0..200000000)
            UNITS       "bits/second"
            MAX-ACCESS  read-create
            STATUS      current
            DESCRIPTION
                "Data Rate Threshold Up shift for downstream direction.  An
                 'Up-shift rate change' event is triggered when the actual
                 downstream data rate exceeds, by more than the threshold, the
                 data rate at the last entry into Showtime.  The parameter is
                 coded in bit/s.
                 Unit: bits/second
                "
            REFERENCE    "ITU-T G.997.1, paragraph 7.3.2.6"
            DEFVAL       { 0 }
            ::= { hwXdslNoiseMarginProfEntry 17 }

        hwXdslNoiseMarginProfDsThresholdUs  OBJECT-TYPE
            SYNTAX      Unsigned32(0..200000000)
            UNITS       "bits/second"
            MAX-ACCESS  read-create
            STATUS      current
            DESCRIPTION
                "Data Rate Threshold Down-shift for upstream direction.  A
                 'Down-shift rate change' event is triggered when the actual
                 upstream data rate is below the data rate at the last entry
                 into Showtime, by more than the threshold.  The parameter is
                 coded in bit/s.
                 Unit: bits/second
                "
            REFERENCE    "ITU-T G.997.1, paragraph 7.3.2.6"
            DEFVAL       { 0 }
            ::= { hwXdslNoiseMarginProfEntry 18 }

        hwXdslNoiseMarginProfUsThresholdUs  OBJECT-TYPE
            SYNTAX      Unsigned32(0..200000000)
            UNITS       "bits/second"
            MAX-ACCESS  read-create
            STATUS      current
            DESCRIPTION
                "Data Rate Threshold Up shift for upstream direction.  An
                 'Up-shift rate change' event is triggered when the actual
                 upstream data rate exceeds, by more than the threshold, the
                 data rate at the last entry into Showtime.  The parameter is
                 coded in bit/s.
                 Unit: bits/second
                "
            REFERENCE    "ITU-T G.997.1, paragraph 7.3.2.6"
            DEFVAL       { 0 }
            ::= { hwXdslNoiseMarginProfEntry 19 }

        hwXdslNoiseMarginProfRowStatus  OBJECT-TYPE
            SYNTAX      RowStatus
            MAX-ACCESS  read-create
            STATUS      current
            DESCRIPTION
                "This object is used to create a new row or to modify or
                delete an existing row in this table.

                A profile is activated by setting this object to 'active'.
                When 'active' is set, the system will validate the profile.

                Before a profile can be deleted or taken out of service
                (by setting this object to 'destroy' or 'outOfService'),
                it must be not referenced from all associated
                lines.
               "
            ::= { hwXdslNoiseMarginProfEntry 20 }

          --        hwXdslDelayInpProfTable
        hwXdslDelayInpProfTable  OBJECT-TYPE
            SYNTAX      SEQUENCE  OF  HwXdslDelayInpProfEntry
            MAX-ACCESS  not-accessible
            STATUS      current
            DESCRIPTION
                "The table hwXdslDelayInpProfTable contains XDSL delay inp
                 configuration. The index of this table is hwXdslDelayInpProfName.
                 A default profile with an index of 'DEFVAL' will
                 always exist and its parameters will be set to vendor-specific
                 values, unless otherwise specified in this document.
                "
            ::= { hwXdslProfileTIMode 8 }

        hwXdslDelayInpProfEntry  OBJECT-TYPE
            SYNTAX      HwXdslDelayInpProfEntry
            MAX-ACCESS  not-accessible
            STATUS      current
            DESCRIPTION
                "The table hwXdslDelayInpProfTable contains XDSL delay inp
                 configuration. The index of this entry is hwXdslDelayInpProfName.
                 A default profile with an index of 'DEFVAL' will
                 always exist and its parameters will be set to vendor-specific
                 values, unless otherwise specified in this document.
                "
            INDEX  { IMPLIED hwXdslDelayInpProfName }
            ::= { hwXdslDelayInpProfTable 1 }

        HwXdslDelayInpProfEntry  ::=
            SEQUENCE {
              hwXdslDelayInpProfName                     OCTET STRING,
              hwXdslDelayInpProfForceINP                 HwXdslForceINP,
              hwXdslDelayInpProfCh1MaxDelayDs            Unsigned32,
              hwXdslDelayInpProfCh1MaxDelayUs            Unsigned32,
              hwXdslDelayInpProfCh1MinProtectionDs       HwXdslSymbolProtectionDs,
              hwXdslDelayInpProfCh1MinProtectionUs       HwXdslSymbolProtectionUs,
              hwXdslDelayInpProfCh2MaxDelayDs            Unsigned32,
              hwXdslDelayInpProfCh2MaxDelayUs            Unsigned32,
              hwXdslDelayInpProfCh2MinProtectionDs       HwXdslSymbolProtectionDs,
              hwXdslDelayInpProfCh2MinProtectionUs       HwXdslSymbolProtectionUs,
              hwXdslDelayInpProfRowStatus                RowStatus,
              hwXdslDelayInpProfCh1PhyRcontrolDs          HwXdslPhyRControl,
              hwXdslDelayInpProfCh1PhyRcontrolUs          HwXdslPhyRControl,
              hwXdslDelayInpProfCh1INPmaxDs   HwXdslSymbolProtectionDs,
              hwXdslDelayInpProfCh1INPmaxUs   HwXdslSymbolProtectionUs,
              hwXdslDelayInpProfCh1MinRtxRatioDs          Integer32,
              hwXdslDelayInpProfCh1MinRtxRatioUs          Integer32,
              hwXdslDelayInpProfCh1MinRSoverheadDs       Integer32,
              hwXdslDelayInpProfCh1MinRSoverheadUs  Integer32,
              hwXdslDelayInpProfCh2PhyRcontrolDs          HwXdslPhyRControl,
              hwXdslDelayInpProfCh2PhyRcontrolUs         HwXdslPhyRControl,
              hwXdslDelayInpProfCh2INPmaxDs   HwXdslSymbolProtectionDs,
              hwXdslDelayInpProfCh2INPmaxUs   HwXdslSymbolProtectionUs,
              hwXdslDelayInpProfCh2MinRtxRatioDs          Integer32,
              hwXdslDelayInpProfCh2MinRtxRatioUs          Integer32,
              hwXdslDelayInpProfCh2MinRSoverheadDs  Integer32,
              hwXdslDelayInpProfCh2MinRSoverheadUs  Integer32,
              hwXdslDelayInpProfCh1MaxDelayRtxDs       Unsigned32,
              hwXdslDelayInpProfCh1MaxDelayRtxUs       Unsigned32,
              hwXdslDelayInpProfCh1MinDelayRtxDs       Unsigned32,
              hwXdslDelayInpProfCh1MinDelayRtxUs       Unsigned32,
              hwXdslDelayInpProfCh1MinInpShineRtxDs    Unsigned32,
              hwXdslDelayInpProfCh1MinInpShineRtxUs    Unsigned32,
              hwXdslDelayInpProfCh1MinInp8ShineRtxDs   Unsigned32,
              hwXdslDelayInpProfCh1MinInp8ShineRtxUs   Unsigned32,
              hwXdslDelayInpProfCh1ShineRatioRtxDs     Unsigned32,
              hwXdslDelayInpProfCh1ShineRatioRtxUs     Unsigned32,
              hwXdslDelayInpProfCh1MinInpReinRtxDs     Unsigned32,
              hwXdslDelayInpProfCh1MinInpReinRtxUs     Unsigned32,
              hwXdslDelayInpProfCh1MinInp8ReinRtxDs    Unsigned32,
              hwXdslDelayInpProfCh1MinInp8ReinRtxUs    Unsigned32,
              hwXdslDelayInpProfCh1IatReinRtxDs        INTEGER,
              hwXdslDelayInpProfCh1IatReinRtxUs        INTEGER
              }

        hwXdslDelayInpProfName  OBJECT-TYPE
            SYNTAX      OCTET STRING (SIZE(1..32))
            MAX-ACCESS  not-accessible
            STATUS      current
            DESCRIPTION
                "This object identifies a row in this table."
            REFERENCE    "DSL Forum TR-90, paragraph 5.1.4"
            ::= { hwXdslDelayInpProfEntry 1 }

        hwXdslDelayInpProfForceINP  OBJECT-TYPE
            SYNTAX      HwXdslForceINP
            MAX-ACCESS  read-create
            STATUS      current
            DESCRIPTION
               "This parameter indicates that the framer settings of the
                bearer shall be selected such that the impulse noise protection
                computed according to the formula specified in the relevant
                Recommendation is greater or equal to the minimal impulse noise
                protection requirement.
                This flag shall have the same value for all the bearers of one
                line in the same direction.
                 "
            REFERENCE    "ITU-T G.997.1, paragraph 7.3.2.5"
            DEFVAL       { force }
            ::= { hwXdslDelayInpProfEntry 2 }

        hwXdslDelayInpProfCh1MaxDelayDs  OBJECT-TYPE
            SYNTAX      Unsigned32(0..200)
            UNITS       "milliseconds"
            MAX-ACCESS  read-create
            STATUS      current
            DESCRIPTION
                "If retransmission is not used in downstream direction,this parameter
                 is maximum interleave delay on downstream direction. The maximum
                 one-way interleaving delay introduced by the PMS-TC on
                 Downstream direction. The XTUs shall choose the S (factor)
                 and D (depth) values such that the actual one-way interleaving
                 delay (hwXdslChanStatusActDelay) is as close as possible to,
                 but less than or equal to, hwXdslChanConfMaxDelayDs. The
                 delay is coded in ms, with the value 0 indicating no delay
                 bound is being imposed.
                 Unit: milliseconds
                "
            REFERENCE    "ITU-T G.997.1, paragraph 7.3.2.2"
            DEFVAL       { 20 }
            ::= { hwXdslDelayInpProfEntry 3 }

        hwXdslDelayInpProfCh1MaxDelayUs  OBJECT-TYPE
            SYNTAX      Unsigned32(0..200)
            UNITS       "milliseconds"
            MAX-ACCESS  read-create
            STATUS      current
            DESCRIPTION
                "If retransmission is not used in upstream direction.  The maximum
                 one-way interleaving delay introduced by the PMS-TC on
                 Upstream direction. The XTUs shall choose the S (factor) and
                 D (depth) values such that the actual one-way interleaving
                 delay (hwXdslChanStatusActDelay) is as close as possible to,
                 but less than or equal to, hwXdslChanConfMaxDelayUs.  The
                 delay is coded in ms, with the value 0 indicating no delay
                 bound is being imposed.
                 Unit: milliseconds
                "
            REFERENCE    "ITU-T G.997.1, paragraph 7.3.2.2"
            DEFVAL       { 20 }
            ::= { hwXdslDelayInpProfEntry 4 }

        hwXdslDelayInpProfCh1MinProtectionDs  OBJECT-TYPE
            SYNTAX      HwXdslSymbolProtectionDs
            UNITS       "symbols"
            MAX-ACCESS  read-create
            STATUS      current
            DESCRIPTION
                "If retransmission is not used in downstream direction,this parameter
                 is minimum impulse noise protection for the bearer channel on downstream
                 direction. The minimum impulse noise protection for the bearer channel,
                 expressed in symbols. The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslDelayInpProfEntry 5 }

        hwXdslDelayInpProfCh1MinProtectionUs  OBJECT-TYPE
            SYNTAX      HwXdslSymbolProtectionUs
            UNITS       "symbols"
            MAX-ACCESS  read-create
            STATUS      current
            DESCRIPTION
                "If retransmission is not used in upstream direction,this parameter
                 is minimum impulse noise protection for the bearer channel on upstream
                 direction. The minimum impulse noise protection for the bearer channel,
                 expressed in symbols. The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslDelayInpProfEntry 6 }

        hwXdslDelayInpProfCh2MaxDelayDs  OBJECT-TYPE
            SYNTAX      Unsigned32(0..200)
            UNITS       "milliseconds"
            MAX-ACCESS  read-create
            STATUS      current
            DESCRIPTION
                "Maximum Interleave Delay on Downstream direction.  The maximum
                 one-way interleaving delay introduced by the PMS-TC on
                 Downstream direction.  The XTUs shall choose the S (factor)
                 and D (depth) values such that the actual one-way interleaving
                 delay (hwXdslChanStatusActDelay) is as close as possible to,
                 but less than or equal to, hwXdslChanConfMaxDelayDs.  The
                 delay is coded in ms, with the value 0 indicating no delay
                 bound is being imposed.
                 Unit: milliseconds
                "
            REFERENCE    "ITU-T G.997.1, paragraph 7.3.2.2"
            DEFVAL       { 20 }
            ::= { hwXdslDelayInpProfEntry 7 }

        hwXdslDelayInpProfCh2MaxDelayUs  OBJECT-TYPE
            SYNTAX      Unsigned32(0..200)
            UNITS       "milliseconds"
            MAX-ACCESS  read-create
            STATUS      current
            DESCRIPTION
                "Maximum Interleave Delay on Upstream direction.  The maximum
                 one-way interleaving delay introduced by the PMS-TC on
                 Upstream direction.  The XTUs shall choose the S (factor) and
                 D (depth) values such that the actual one-way interleaving
                 delay (hwXdslChanStatusActDelay) is as close as possible to,
                 but less than or equal to, hwXdslChanConfMaxDelayUs.  The
                 delay is coded in ms, with the value 0 indicating no delay
                 bound is being imposed.
                 Unit: milliseconds
                "
            REFERENCE    "ITU-T G.997.1, paragraph 7.3.2.2"
            DEFVAL       { 20 }
            ::= { hwXdslDelayInpProfEntry 8 }

        hwXdslDelayInpProfCh2MinProtectionDs  OBJECT-TYPE
            SYNTAX      HwXdslSymbolProtectionDs
            UNITS       "symbols"
            MAX-ACCESS  read-create
            STATUS      current
            DESCRIPTION
                "Minimum Impulse Noise Protection on Downstream direction.  The
                 minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslDelayInpProfEntry 9 }

        hwXdslDelayInpProfCh2MinProtectionUs  OBJECT-TYPE
            SYNTAX      HwXdslSymbolProtectionUs
            UNITS       "symbols"
            MAX-ACCESS  read-create
            STATUS      current
            DESCRIPTION
                "Minimum Impulse Noise Protection on Upstream direction.  The
                 minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslDelayInpProfEntry 10 }

        hwXdslDelayInpProfRowStatus  OBJECT-TYPE
            SYNTAX      RowStatus
            MAX-ACCESS  read-create
            STATUS      current
            DESCRIPTION
                "This object is used to create a new row or to modify or
                 delete an existing row in this table.
                 A profile is activated by setting this object to 'active'.
                 When 'active' is set, the system will validate the profile.
                 Before a profile can be deleted or taken out of service
                 (by setting this object to 'destroy' or 'outOfService'),
                 it must be not referenced from all associated
                 lines.
                "
            ::= { hwXdslDelayInpProfEntry 11 }


        hwXdslDelayInpProfCh1PhyRcontrolDs OBJECT-TYPE
            SYNTAX      HwXdslPhyRControl
            MAX-ACCESS  read-write
            STATUS      current
            DESCRIPTION
                "To enable or disable the retransmission function on downstream direction."
            DEFVAL { 2 }
            ::= { hwXdslDelayInpProfEntry 12 }

        hwXdslDelayInpProfCh1PhyRcontrolUs OBJECT-TYPE
            SYNTAX      HwXdslPhyRControl
            MAX-ACCESS  read-write
            STATUS      current
            DESCRIPTION
                "To enable or disable the retransmission function on upstream direction."
            DEFVAL { 2 }
            ::= { hwXdslDelayInpProfEntry 13 }

        hwXdslDelayInpProfCh1INPmaxDs OBJECT-TYPE
            SYNTAX      HwXdslSymbolProtectionDs
            UNITS       "DMT Symbol"
            MAX-ACCESS  read-write
            STATUS      current
            DESCRIPTION
                "Maximum Impulse Noise Protection on downstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)

                 The value multiply 1/2 is the real value of Noise Protection values.
                 Unit: DMT Symbol
          "
            DEFVAL { 1 }
            ::= { hwXdslDelayInpProfEntry 14 }

        hwXdslDelayInpProfCh1INPmaxUs OBJECT-TYPE
            SYNTAX      HwXdslSymbolProtectionUs
            UNITS       "DMT Symbol"
            MAX-ACCESS  read-write
            STATUS      current
            DESCRIPTION
                "Maximum Impulse Noise Protection on upstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)

                 The value multiply 1/2 is the real value of Noise Protection values.
                 Unit: DMT Symbol
               "
            DEFVAL { 1 }
            ::= { hwXdslDelayInpProfEntry 15 }

        hwXdslDelayInpProfCh1MinRtxRatioDs OBJECT-TYPE
            SYNTAX      Integer32 (0..255)
            UNITS       "1/256"
            MAX-ACCESS  read-write
            STATUS      current
            DESCRIPTION
                "Minimum rtxratio on downstream direction.
                 Unit: 1/256
                "
            DEFVAL { 0 }
            ::= { hwXdslDelayInpProfEntry 16 }

        hwXdslDelayInpProfCh1MinRtxRatioUs OBJECT-TYPE
            SYNTAX      Integer32 (0..255)
            UNITS       "1/256"
            MAX-ACCESS  read-write
            STATUS      current
            DESCRIPTION
                "Minimum rtxratio on upstream direction.
                 Unit: 1/256
                "
            DEFVAL { 0 }
            ::= { hwXdslDelayInpProfEntry 17 }

        hwXdslDelayInpProfCh1MinRSoverheadDs OBJECT-TYPE
            SYNTAX      Integer32 (0..128)
            UNITS       "1/256"
            MAX-ACCESS  read-write
            STATUS      current
            DESCRIPTION
                "The minimum value of R/N on downstream direction.
                 Unit: 1/256
                "
            DEFVAL { 0 }
            ::= { hwXdslDelayInpProfEntry 18 }

        hwXdslDelayInpProfCh1MinRSoverheadUs OBJECT-TYPE
            SYNTAX      Integer32 (0..128)
            UNITS       "1/256"
            MAX-ACCESS  read-write
            STATUS      current
            DESCRIPTION
                "The minimum value of R/N on upstream direction.
                 Unit: 1/256
                "
            DEFVAL { 0 }
            ::= { hwXdslDelayInpProfEntry 19 }

        hwXdslDelayInpProfCh2PhyRcontrolDs OBJECT-TYPE
            SYNTAX      HwXdslPhyRControl
            MAX-ACCESS  read-write
            STATUS      current
            DESCRIPTION
                "To enable or disable the retransmission function on downstream direction."
            DEFVAL { 2 }
            ::= { hwXdslDelayInpProfEntry 20 }

        hwXdslDelayInpProfCh2PhyRcontrolUs OBJECT-TYPE
            SYNTAX      HwXdslPhyRControl
            MAX-ACCESS  read-write
            STATUS      current
            DESCRIPTION
                "To enable or disable the retransmission function on upstream direction."
            DEFVAL { 2 }
            ::= { hwXdslDelayInpProfEntry 21 }

        hwXdslDelayInpProfCh2INPmaxDs OBJECT-TYPE
            SYNTAX      HwXdslSymbolProtectionDs
            UNITS       "DMT Symbol"
            MAX-ACCESS  read-write
            STATUS      current
            DESCRIPTION
                "Maximum Impulse Noise Protection on downstream direction.
                 Options:
                 1. noProtection(1)
                 2. halfSymbol(2)
                 3. singleSymbol(3)
                 4. twoSymbols(4)
                 5. threeSymbols(5)
                 6. fourSymbols(6)
                 7. fiveSymbols(7)
                 8. sixSymbols(8)
                 9. sevenSymbols(9)
                 10. eightSymbols(10)
                 11. nineSymbols(11)
                 12. tenSymbols(12)
                 13. elevenSymbols(13)
                 14. twelveSymbols(14)
                 15. thirteeSymbols(15)
                 16. fourteenSymbols(16)
                 17. fifteenSymbols(17)
                 18. sixteenSymbols(18)

                 The value multiply 1/2 is the real value of Noise Protection values.
                 Unit: DMT Symbol
          "
            DEFVAL { 1 }
            ::= { hwXdslDelayInpProfEntry 22 }

        hwXdslDelayInpProfCh2INPmaxUs OBJECT-TYPE
            SYNTAX      HwXdslSymbolProtectionUs
            UNITS       "DMT Symbol"
            MAX-ACCESS  read-write
            STATUS      current
            DESCRIPTION
               "Maximum Impulse Noise Protection on upstream direction.
                Options:
                1. noProtection(1)
                2. halfSymbol(2)
                3. singleSymbol(3)
                4. twoSymbols(4)
                5. threeSymbols(5)
                6. fourSymbols(6)
                7. fiveSymbols(7)
                8. sixSymbols(8)
                9. sevenSymbols(9)
                10. eightSymbols(10)
                11. nineSymbols(11)
                12. tenSymbols(12)
                13. elevenSymbols(13)
                14. twelveSymbols(14)
                15. thirteeSymbols(15)
                16. fourteenSymbols(16)
                17. fifteenSymbols(17)
                18. sixteenSymbols(18)

                The value multiply 1/2 is the real value of Noise Protection values.
                Unit: DMT Symbol
               "
            DEFVAL { 1 }
            ::= { hwXdslDelayInpProfEntry 23 }

        hwXdslDelayInpProfCh2MinRtxRatioDs OBJECT-TYPE
            SYNTAX      Integer32 (0..255)
            UNITS       "1/256"
            MAX-ACCESS  read-write
            STATUS      current
            DESCRIPTION
                "Minimum rtxratio on downstream direction.
                 Unit: 1/256
                "
            DEFVAL { 0 }
            ::= { hwXdslDelayInpProfEntry 24 }

        hwXdslDelayInpProfCh2MinRtxRatioUs OBJECT-TYPE
            SYNTAX      Integer32 (0..255)
            UNITS       "1/256"
            MAX-ACCESS  read-write
            STATUS      current
            DESCRIPTION
                "Minimum rtxratio on upstream direction.
                 Unit: 1/256
                "
            DEFVAL { 0 }
            ::= { hwXdslDelayInpProfEntry 25 }

        hwXdslDelayInpProfCh2MinRSoverheadDs OBJECT-TYPE
            SYNTAX      Integer32 (0..128)
            UNITS       "1/256"
            MAX-ACCESS  read-write
            STATUS      current
            DESCRIPTION
                "The minimum value of R/N on downstream direction.
                 Unit: 1/256
                "
            DEFVAL { 0 }
            ::= { hwXdslDelayInpProfEntry 26 }

        hwXdslDelayInpProfCh2MinRSoverheadUs OBJECT-TYPE
            SYNTAX      Integer32 (0..128)
            UNITS       "1/256"
            MAX-ACCESS  read-write
            STATUS      current
            DESCRIPTION
                "The minimum value of R/N on upstream direction.
                 Unit: 1/256
                "
            DEFVAL { 0 }
            ::= { hwXdslDelayInpProfEntry 27 }

        hwXdslDelayInpProfCh1MaxDelayRtxDs  OBJECT-TYPE
            SYNTAX      Unsigned32(1..63)
            UNITS       "milliseconds"
            MAX-ACCESS  read-create
            STATUS      current
            DESCRIPTION
               "If retransmission is used in downstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwXdslDelayInpProfEntry 28 }

        hwXdslDelayInpProfCh1MaxDelayRtxUs  OBJECT-TYPE
            SYNTAX      Unsigned32(1..63)
            UNITS       "milliseconds"
            MAX-ACCESS  read-create
            STATUS      current
            DESCRIPTION
               "If retransmission is used in upstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwXdslDelayInpProfEntry 29 }

        hwXdslDelayInpProfCh1MinDelayRtxDs  OBJECT-TYPE
            SYNTAX      Unsigned32(0..63)
            UNITS       "milliseconds"
            MAX-ACCESS  read-create
            STATUS      current
            DESCRIPTION
               "If retransmission is used in downstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwXdslDelayInpProfEntry 30 }

        hwXdslDelayInpProfCh1MinDelayRtxUs  OBJECT-TYPE
            SYNTAX      Unsigned32(0..63)
            UNITS       "milliseconds"
            MAX-ACCESS  read-create
            STATUS      current
            DESCRIPTION
               "If retransmission is used in upstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwXdslDelayInpProfEntry 31 }

       hwXdslDelayInpProfCh1MinInpShineRtxDs  OBJECT-TYPE
            SYNTAX      Unsigned32(0..63)
            UNITS       "symbols"
            MAX-ACCESS  read-create
            STATUS      current
            DESCRIPTION
               "If retransmission is used in downstream direction, this parameter specifies
                the minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwXdslDelayInpProfEntry 32 }

        hwXdslDelayInpProfCh1MinInpShineRtxUs  OBJECT-TYPE
            SYNTAX      Unsigned32(0..63)
            UNITS       "symbols"
            MAX-ACCESS  read-create
            STATUS      current
            DESCRIPTION
               "If retransmission is used in upstream direction, this parameter specifies the
                minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwXdslDelayInpProfEntry 33 }

       hwXdslDelayInpProfCh1MinInp8ShineRtxDs  OBJECT-TYPE
            SYNTAX      Unsigned32(0..127)
            UNITS       "symbols"
            MAX-ACCESS  read-create
            STATUS      current
            DESCRIPTION
               "If retransmission is used in downstream direction, this parameter specifies
                the minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwXdslDelayInpProfEntry 34 }

        hwXdslDelayInpProfCh1MinInp8ShineRtxUs  OBJECT-TYPE
            SYNTAX      Unsigned32(0..127)
            UNITS       "symbols"
            MAX-ACCESS  read-create
            STATUS      current
            DESCRIPTION
               "If retransmission is used in upstream direction, this parameter specifies the
                minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwXdslDelayInpProfEntry 35 }

        hwXdslDelayInpProfCh1ShineRatioRtxDs  OBJECT-TYPE
            SYNTAX      Unsigned32(0..100)
            MAX-ACCESS  read-create
            STATUS      current
            DESCRIPTION
               "If retransmission is used in downstream direction, this parameter specifies
                the SHINE ratio (detailed definition see G.998.4).
                The values range from 0 to 0.100 in increments of 0.001.
               "
            REFERENCE    "ITU-T G.997.1, paragraph 7.3.2.15"
            DEFVAL       { 0 }
            ::= { hwXdslDelayInpProfEntry 36 }

        hwXdslDelayInpProfCh1ShineRatioRtxUs  OBJECT-TYPE
            SYNTAX      Unsigned32(0..100)
            MAX-ACCESS  read-create
            STATUS      current
            DESCRIPTION
               "If retransmission is used in upstream direction, this parameter specifies
                the SHINE ratio (detailed definition see G.998.4).
                The values range from 0 to 0.100 in increments of 0.001.
               "
            REFERENCE    "ITU-T G.997.1, paragraph 7.3.2.15"
            DEFVAL       { 0 }
            ::= { hwXdslDelayInpProfEntry 37 }

        hwXdslDelayInpProfCh1MinInpReinRtxDs  OBJECT-TYPE
            SYNTAX      Unsigned32(0..7)
            MAX-ACCESS  read-create
            STATUS      current
            DESCRIPTION
               "If retransmission is used in downstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwXdslDelayInpProfEntry 38 }

        hwXdslDelayInpProfCh1MinInpReinRtxUs  OBJECT-TYPE
            SYNTAX      Unsigned32(0..7)
            MAX-ACCESS  read-create
            STATUS      current
            DESCRIPTION
               "If retransmission is used in upstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwXdslDelayInpProfEntry 39 }

        hwXdslDelayInpProfCh1MinInp8ReinRtxDs  OBJECT-TYPE
            SYNTAX      Unsigned32(0..13)
            MAX-ACCESS  read-create
            STATUS      current
            DESCRIPTION
               "If retransmission is used in downstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwXdslDelayInpProfEntry 40 }

        hwXdslDelayInpProfCh1MinInp8ReinRtxUs  OBJECT-TYPE
            SYNTAX      Unsigned32(0..13)
            MAX-ACCESS  read-create
            STATUS      current
            DESCRIPTION
               "If retransmission is used in upstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwXdslDelayInpProfEntry 41 }

        hwXdslDelayInpProfCh1IatReinRtxDs  OBJECT-TYPE
            SYNTAX      INTEGER
                        {
                         frequency100Hz(0),
                   frequency120Hz(1)
                        }
            MAX-ACCESS  read-create
            STATUS      current
            DESCRIPTION
               "If retransmission is used in downstream direction, this parameter specifies
                the inter-arrival time that shall be assumed for REIN protection.
                Options:
          1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwXdslDelayInpProfEntry 42 }

        hwXdslDelayInpProfCh1IatReinRtxUs  OBJECT-TYPE
            SYNTAX      INTEGER
                        {
                         frequency100Hz(0),
                         frequency120Hz(1)
                        }
            MAX-ACCESS  read-create
            STATUS      current
            DESCRIPTION
               "If retransmission is used in upstream direction, this parameter specifies
                the inter-arrival time that shall be assumed for REIN protection.
                Options:
                1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwXdslDelayInpProfEntry 43 }

        hwXdslGfastConfTddProfTable  OBJECT-TYPE
            SYNTAX      SEQUENCE  OF  HwXdslGfastConfTddProfEntry
            MAX-ACCESS  not-accessible
            STATUS      current
            DESCRIPTION
                "The table hwXdslGfastConfTddProfTable contains G.fast tdd-profile
           configuration. The index of this table is hwXdslGfastConfTddProfName.
           A default profile with an index of 'DEFVAL' will
           always exist and its parameters will be set to vendor-specific
           values, unless otherwise specified in this document.
                "
            ::= { hwXdslGfastTddProfile 1 }

        hwXdslGfastConfTddProfEntry  OBJECT-TYPE
            SYNTAX      HwXdslGfastConfTddProfEntry
            MAX-ACCESS  not-accessible
            STATUS      current
            DESCRIPTION
                "The table hwXdslGfastConfTddProfTable contains G.fast tdd-profile
           configuration. The index of this entry is hwXdslGfastConfTddProfName.
           A default profile with an index of 'DEFVAL' will
           always exist and its parameters will be set to vendor-specific
           values, unless otherwise specified in this document.
                 "
            INDEX  { IMPLIED hwXdslGfastConfTddProfName }
            ::= { hwXdslGfastConfTddProfTable 1 }

        HwXdslGfastConfTddProfEntry  ::=
           SEQUENCE {
              hwXdslGfastConfTddProfName                     OCTET STRING,
              hwXdslGfastConfTddProfRowStatus                RowStatus,
              hwXdslGfastConfTddProfSymbolNumPerTddFrame     Unsigned32,
              hwXdslGfastConfTddProfSymbolNumPerTddFrameDs   Unsigned32,
              hwXdslGfastConfTddProfTtrDs                    Unsigned32,
              hwXdslGfastConfTddProfTtrUs                    Unsigned32,
              hwXdslGfastConfTddProfTbudgetDs                Unsigned32,
              hwXdslGfastConfTddProfTbudgetUs                Unsigned32
            }

        hwXdslGfastConfTddProfName  OBJECT-TYPE
            SYNTAX      OCTET STRING (SIZE(1..32))
            MAX-ACCESS  accessible-for-notify
            STATUS      current
            DESCRIPTION
                "This object identifies a row in this table."
            ::= { hwXdslGfastConfTddProfEntry 1 }

        hwXdslGfastConfTddProfRowStatus  OBJECT-TYPE
            SYNTAX      RowStatus
            MAX-ACCESS  read-create
            STATUS      current
            DESCRIPTION
                "This object is used to create a new row or to modify or
                delete an existing row in this table.

                A profile is activated by setting this object to 'active'.
                When 'active' is set, the system will validate the profile.

                Before a profile can be deleted or taken out of service
                (by setting this object to 'destroy' or 'outOfService'),
                it must be not referenced from all associated
                lines.
               "
            ::= { hwXdslGfastConfTddProfEntry 2 }

        hwXdslGfastConfTddProfSymbolNumPerTddFrame  OBJECT-TYPE
            SYNTAX      Unsigned32(23 | 36)
            MAX-ACCESS  read-write
            STATUS      current
            DESCRIPTION
                "The total number of symbol periods in a TDD frame.
                 TDD frame lengths of Mf = 36 and Mf = 23 symbol periods shall be supported.
                "
            REFERENCE    "ITU-T G.9701, paragraph 10.5"
            DEFVAL       { 36 }
            ::= { hwXdslGfastConfTddProfEntry 3 }

        hwXdslGfastConfTddProfSymbolNumPerTddFrameDs  OBJECT-TYPE
            SYNTAX      Unsigned32(6..32)
            MAX-ACCESS  read-write
            STATUS      current
            DESCRIPTION
                "The total number of symbol positions in a TDD frame allocated for downstream transmission.
                 When Mf is 36, Mds values supported from 10 to 32.
                 When Mf is 23, Mds values supported from 6 to 19.
                 The total number of symbol positions in a TDD frame allocated for upstream transmission is calculated as Mus = Mf-1-Mds.
                "
            REFERENCE    "ITU-T G.9701, paragraph 10.5"
            DEFVAL       { 28 }
            ::= { hwXdslGfastConfTddProfEntry 4 }

        hwXdslGfastConfTddProfTtrDs  OBJECT-TYPE
            SYNTAX      Unsigned32(1..32)
            MAX-ACCESS  read-write
            STATUS      current
            DESCRIPTION
                "A parameter received by the FTU-O with the TXOPds primitive,
                 indicating that the first TTRds downstream symbol positions in the logical frame are allocated to
                 the normal operation interval (NOI). The remaining (Mds - TTRds) downstream symbol positions
                 in the logical frame are available for allocation to the discontinuous operation interval (DOI).
                 The range of valid TTRds values is 1 to Mds. The default value is Mds.
                "
            REFERENCE    "ITU-T G.9701, paragraph 10.5"
            ::= { hwXdslGfastConfTddProfEntry 5 }

        hwXdslGfastConfTddProfTtrUs  OBJECT-TYPE
            SYNTAX      Unsigned32(1..25)
            MAX-ACCESS  read-write
            STATUS      current
            DESCRIPTION
                "A parameter received by the FTU-O with the TXOPus primitive,
                 indicating that the first TTRus upstream symbol positions in the logical frame are allocated to
                 the normal operation interval (NOI). The remaining (Mus - TTRus) upstream symbol positions
                 in the logical frame are available for allocation to the discontinuous operation interval (DOI).
                 The range of valid TTRus values is 1 to Mus. The default value is Mus.
                "
            REFERENCE    "ITU-T G.9701, paragraph 10.5"
            ::= { hwXdslGfastConfTddProfEntry 6 }

        hwXdslGfastConfTddProfTbudgetDs  OBJECT-TYPE
            SYNTAX      Unsigned32(1..32)
            MAX-ACCESS  read-write
            STATUS      current
            DESCRIPTION
                "A parameter received by the FTU-O with the TXOPds primitive,
                 indicating that the downstream transmission opportunity consists of a total of
                 TBUDGETds symbol positions in the combined normal operation interval (NOI)
                 and discontinuous operation interval (DOI) of the logical frame.
                 The range of valid values is from 1 to Mds. The default value is Mds.
                "
            REFERENCE    "ITU-T G.9701, paragraph 10.5"
            ::= { hwXdslGfastConfTddProfEntry 7 }

        hwXdslGfastConfTddProfTbudgetUs  OBJECT-TYPE
            SYNTAX      Unsigned32(1..25)
            MAX-ACCESS  read-write
            STATUS      current
            DESCRIPTION
                "A parameter received by the FTU-O with the TXOPus primitive,
                 indicating that the upstream transmission opportunity consists of a total of
                 TBUDGETus symbol positions in the combined normal operation interval (NOI)
                 and discontinuous operation interval (DOI) of the logical frame.
                 The range of valid values is from 1 to Mus. The default value is Mus.
                "
            REFERENCE    "ITU-T G.9701, paragraph 10.5"
            ::= { hwXdslGfastConfTddProfEntry 8 }

               --        hwXdslGfastLineAlarmConfTemplateTable
        hwXdslGfastLineAlarmConfTemplateTable  OBJECT-TYPE
            SYNTAX      SEQUENCE  OF  HwXdslGfastLineAlarmConfTemplateEntry
            MAX-ACCESS  not-accessible
            STATUS      current
            DESCRIPTION
               "The table hwXdslGfastLineAlarmConfTemplateTable contains G.fast line
                alarm configuration template.
                The index of this table is hwXdslGfastLAlarmConfTempTemplateName.
                A default template with an index of 'DEFVAL' will
                always exist and its parameters will be set to vendor
                specific values, unless otherwise specified in this
                document.
               "
            ::= { hwXdslGfastProfileAlarmConf 1 }

        hwXdslGfastLineAlarmConfTemplateEntry  OBJECT-TYPE
            SYNTAX      HwXdslGfastLineAlarmConfTemplateEntry
            MAX-ACCESS  not-accessible
            STATUS      current
            DESCRIPTION
                "The table hwXdslGfastLineAlarmConfTemplateTable contains G.fast line
                 alarm configuration template.
                 The index of this entry is hwXdslGfastLAlarmConfTempTemplateName.
                 A default template with an index of 'DEFVAL' will
                 always exist and its parameters will be set to vendor
                 specific values, unless otherwise specified in this
                 document.
                "
            INDEX  { IMPLIED hwXdslGfastLAlarmConfTempTemplateName }
            ::= { hwXdslGfastLineAlarmConfTemplateTable 1 }

        HwXdslGfastLineAlarmConfTemplateEntry  ::=
            SEQUENCE {
              hwXdslGfastLAlarmConfTempTemplateName      OCTET STRING,
              hwXdslGfastLAlarmConfTempLineProfile       OCTET STRING,
              hwXdslGfastLAlarmConfTempChanConfProfile   OCTET STRING,
              hwXdslGfastLAlarmConfTempRowStatus         RowStatus
            }

        hwXdslGfastLAlarmConfTempTemplateName  OBJECT-TYPE
            SYNTAX      OCTET STRING (SIZE(1..32))
            MAX-ACCESS  not-accessible
            STATUS      current
            DESCRIPTION
                "This object identifies a row in this table."
            ::= { hwXdslGfastLineAlarmConfTemplateEntry 1 }

        hwXdslGfastLAlarmConfTempLineProfile  OBJECT-TYPE
            SYNTAX      OCTET STRING (SIZE(1..32))
            MAX-ACCESS  read-create
            STATUS      current
            DESCRIPTION
                "The value of this object identifies the row in the G.fast Line
                 Thresholds Configuration Profile Table
                 (hwXdslGfastLAlarmConfProfTable) that applies to this G.fast
                 line.
                "
            REFERENCE    "DSL Forum TR-90, paragraph 5.4.1"
            DEFVAL       { "DEFVAL" }
            ::= { hwXdslGfastLineAlarmConfTemplateEntry 2 }

        hwXdslGfastLAlarmConfTempChanConfProfile  OBJECT-TYPE
            SYNTAX      OCTET STRING (SIZE(1..32))
            MAX-ACCESS  read-create
            STATUS      current
            DESCRIPTION
                "The value of this object identifies the row in the G.fast
                 Channel Thresholds Configuration Profile Table
                 (hwXdslGfastChAlarmConfProfileTable) that applies for G.fast
                 bearer channel.  The channel profile name specified here
                 must match the name of an existing row in the
                 hwXdslGfastChAlarmConfProfileTable table.
                "
            REFERENCE    "DSL Forum TR-90, paragraph 5.4.1"
            DEFVAL       { "DEFVAL" }
            ::= { hwXdslGfastLineAlarmConfTemplateEntry 3 }

        hwXdslGfastLAlarmConfTempRowStatus  OBJECT-TYPE
            SYNTAX      RowStatus
            MAX-ACCESS  read-create
            STATUS      current
            DESCRIPTION
                "This object is used to create a new row or to modify or
                delete an existing row in this table.

                A profile is activated by setting this object to 'active'.
                When 'active' is set, the system will validate the profile.

                Before a profile can be deleted or taken out of service
                (by setting this object to 'destroy' or 'outOfService'),
                it must be not referenced from all associated
                lines.
               "
            ::= { hwXdslGfastLineAlarmConfTemplateEntry 4 }

          --      hwXdslGfastLAlarmConfProfTable

        hwXdslGfastLAlarmConfProfTable  OBJECT-TYPE
            SYNTAX      SEQUENCE  OF  HwXdslGfastLAlarmConfProfEntry
            MAX-ACCESS  not-accessible
            STATUS      current
            DESCRIPTION
                "The table hwXdslGfastLAlarmConfProfTable contains G.fast
                 line PM thresholds profiles. The index of this table is
                 hwXdslGfastLAlarmConfProfName.
                 A default profile with an index of 'DEFVAL' will
                 always exist and its parameters will be set to vendor
                 specific values, unless otherwise specified in this
                 document.
                "
            ::= { hwXdslGfastProfileAlarmConf 2 }

        hwXdslGfastLAlarmConfProfEntry  OBJECT-TYPE
            SYNTAX      HwXdslGfastLAlarmConfProfEntry
            MAX-ACCESS  not-accessible
            STATUS      current
            DESCRIPTION
                "The table hwXdslGfastLAlarmConfProfTable contains G.fast
                 line PM thresholds profiles.
                 The index of this entry is hwXdslGfastLAlarmConfProfName.
                 A default profile with an index of 'DEFVAL' will
                 always exist and its parameters will be set to vendor
                 specific values, unless otherwise specified in this
                 document.
                "
            INDEX  { IMPLIED hwXdslGfastLAlarmConfProfName }
            ::= { hwXdslGfastLAlarmConfProfTable 1 }

        HwXdslGfastLAlarmConfProfEntry ::=
             SEQUENCE {
             hwXdslGfastLAlarmConfProfName                      OCTET STRING,
             hwXdslGfastLAlarmConfProfXtucThresh15MinFecs
                                                  HCPerfIntervalThreshold,
             hwXdslGfastLAlarmConfProfXtucThresh15MinEs
                                                  HCPerfIntervalThreshold,
             hwXdslGfastLAlarmConfProfXtucThresh15MinSes
                                                   HCPerfIntervalThreshold,
             hwXdslGfastLAlarmConfProfXtucThresh15MinLoss
                                                   HCPerfIntervalThreshold,
             hwXdslGfastLAlarmConfProfXtucThresh15MinUas
                                                   HCPerfIntervalThreshold,
             hwXdslGfastLAlarmConfProfXturThresh15MinFecs
                                                   HCPerfIntervalThreshold,
             hwXdslGfastLAlarmConfProfXturThresh15MinEs
                                                   HCPerfIntervalThreshold,
             hwXdslGfastLAlarmConfProfXturThresh15MinSes
                                                   HCPerfIntervalThreshold,
             hwXdslGfastLAlarmConfProfXturThresh15MinLoss
                                                   HCPerfIntervalThreshold,
             hwXdslGfastLAlarmConfProfXturThresh15MinUas
                                                   HCPerfIntervalThreshold,
             hwXdslGfastLAlarmConfProfThresh15MinFailedFullInt   Unsigned32,
             hwXdslGfastLAlarmConfProfThresh15MinFailedShrtInt   Unsigned32,
             hwXdslGfastLAlarmConfProfRowStatus                  RowStatus,
             hwXdslGfastLAlarmConfProfThresh15MinFullInt         Unsigned32,
             hwXdslGfastLAlarmConfProfXtucThresh15MinLeftrs      HCPerfIntervalThreshold,
             hwXdslGfastLAlarmConfProfXturThresh15MinLeftrs      HCPerfIntervalThreshold,
             hwXdslGfastLAlarmConfProfDyingGaspAlarmSwitch     INTEGER,
             hwXdslGfastLAlarmConfProfActiveFailAlarmSwitch    INTEGER,
             hwXdslGfastLAlarmConfProfRateChangeAlarmSwitch    INTEGER,
             hwXdslGfastLAlarmConfProfLegacyCpeAlarmSwitch     INTEGER,
             hwXdslGfastLAlarmConfProfVictAbnormalVariationAlarmSwitch INTEGER,
             hwXdslGfastLAlarmConfProfDistAbnormalVariationAlarmSwitch INTEGER,
             hwXdslGfastLAlarmConfProfReceivedESAbnormalAlarmSwitch    INTEGER,
             hwXdslGfastLAlarmConfProfNonVectoringCPEActivatedAlarmSwitch INTEGER,
             hwXdslGfastLAlarmConfProfFreqRetrainReachThresholdAlarmSwitch INTEGER,
             hwXdslGfastLAlarmConfProfPSConfigAbnormalAlarmSwitch INTEGER
             }

        hwXdslGfastLAlarmConfProfName  OBJECT-TYPE
            SYNTAX      OCTET STRING (SIZE(1..32))
            MAX-ACCESS  not-accessible
            STATUS      current
            DESCRIPTION
                "This object identifies a row in this table."
            ::= { hwXdslGfastLAlarmConfProfEntry 1 }

        hwXdslGfastLAlarmConfProfXtucThresh15MinFecs  OBJECT-TYPE
            SYNTAX      HCPerfIntervalThreshold
            UNITS       "seconds"
            MAX-ACCESS  read-create
            STATUS      current
            DESCRIPTION
                "A threshold for the hwXdslPMLCurr15MFecs counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslGfastLAlarmConfProfEntry 2 }

        hwXdslGfastLAlarmConfProfXtucThresh15MinEs  OBJECT-TYPE
            SYNTAX      HCPerfIntervalThreshold
            UNITS       "seconds"
            MAX-ACCESS  read-create
            STATUS      current
            DESCRIPTION
                "A threshold for the hwXdslPMLCurr15MEs counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslGfastLAlarmConfProfEntry 3 }

        hwXdslGfastLAlarmConfProfXtucThresh15MinSes  OBJECT-TYPE
            SYNTAX      HCPerfIntervalThreshold
            UNITS       "seconds"
            MAX-ACCESS  read-create
            STATUS      current
            DESCRIPTION
                "A threshold for the hwXdslPMLCurr15MSes counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslGfastLAlarmConfProfEntry 4 }

        hwXdslGfastLAlarmConfProfXtucThresh15MinLoss  OBJECT-TYPE
            SYNTAX      HCPerfIntervalThreshold
            UNITS       "seconds"
            MAX-ACCESS  read-create
            STATUS      current
            DESCRIPTION
                "A threshold for the hwXdslPMLCurr15MLoss counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslGfastLAlarmConfProfEntry 5 }

        hwXdslGfastLAlarmConfProfXtucThresh15MinUas  OBJECT-TYPE
            SYNTAX      HCPerfIntervalThreshold
            UNITS       "seconds"
            MAX-ACCESS  read-create
            STATUS      current
            DESCRIPTION
                "A threshold for the hwXdslPMLCurr15MUas counter,
                 when hwXdslPMLCurrUnit is XTUC {1}.
                 The value 0 means that no threshold is specified for the
                 associated counter.
                 Unit: seconds
                "
            REFERENCE    "ITU-T G.997.1, paragraph 7.3.1"
            DEFVAL       { 0 }
             ::= { hwXdslGfastLAlarmConfProfEntry 6 }

        hwXdslGfastLAlarmConfProfXturThresh15MinFecs  OBJECT-TYPE
            SYNTAX      HCPerfIntervalThreshold
            UNITS       "seconds"
            MAX-ACCESS  read-create
            STATUS      current
            DESCRIPTION
                "A threshold for the hwXdslPMLCurr15MFecs counter,
                 when hwXdslPMLCurrUnit is XTUR {2}.
                 The value 0 means that no threshold is specified for the
                 associated counter.
                 Unit: seconds
                "
            REFERENCE    "ITU-T G.997.1, paragraph 7.3.1"
            DEFVAL       { 0 }
              ::= { hwXdslGfastLAlarmConfProfEntry 7 }

        hwXdslGfastLAlarmConfProfXturThresh15MinEs  OBJECT-TYPE
            SYNTAX      HCPerfIntervalThreshold
            UNITS       "seconds"
            MAX-ACCESS  read-create
            STATUS      current
            DESCRIPTION
                "A threshold for the hwXdslPMLCurr15MEs counter,
                 when hwXdslPMLCurrUnit is XTUR {2}.
                 The value 0 means that no threshold is specified for the
                 associated counter.
                 Unit: seconds
                "
            REFERENCE    "ITU-T G.997.1, paragraph 7.3.1"
            DEFVAL       { 0 }
            ::= { hwXdslGfastLAlarmConfProfEntry 8 }

        hwXdslGfastLAlarmConfProfXturThresh15MinSes  OBJECT-TYPE
            SYNTAX      HCPerfIntervalThreshold
            UNITS       "seconds"
            MAX-ACCESS  read-create
            STATUS      current
            DESCRIPTION
                "A threshold for the hwXdslPMLCurr15MSes counter,
                 when hwXdslPMLCurrUnit is XTUR {2}.
                 The value 0 means that no threshold is specified for the
                 associated counter.
                 Unit: seconds
                "
            REFERENCE    "ITU-T G.997.1, paragraph 7.3.1"
            DEFVAL       { 0 }
            ::= { hwXdslGfastLAlarmConfProfEntry 9 }

        hwXdslGfastLAlarmConfProfXturThresh15MinLoss  OBJECT-TYPE
            SYNTAX      HCPerfIntervalThreshold
            UNITS       "seconds"
            MAX-ACCESS  read-create
            STATUS      current
            DESCRIPTION
               "A threshold for the hwXdslPMLCurr15MLoss counter,
                when hwXdslPMLCurrUnit is XTUR {2}.
                The value 0 means that no threshold is specified for the
                associated counter.
                Unit: seconds
               "
            REFERENCE    "ITU-T G.997.1, paragraph 7.3.1"
            DEFVAL       { 0 }
            ::= { hwXdslGfastLAlarmConfProfEntry 10 }

        hwXdslGfastLAlarmConfProfXturThresh15MinUas  OBJECT-TYPE
            SYNTAX      HCPerfIntervalThreshold
            UNITS       "seconds"
            MAX-ACCESS  read-create
            STATUS      current
            DESCRIPTION
               "A threshold for the hwXdslPMLCurr15MUas counter,
                when hwXdslPMLCurrUnit is XTUR {2}.
                The value 0 means that no threshold is specified for the
                associated counter.
                Unit: seconds
               "
            REFERENCE    "ITU-T G.997.1, paragraph 7.3.1"
            DEFVAL       { 0 }
            ::= { hwXdslGfastLAlarmConfProfEntry 11 }

        hwXdslGfastLAlarmConfProfThresh15MinFailedFullInt  OBJECT-TYPE
            SYNTAX      Unsigned32
            MAX-ACCESS  read-create
            STATUS      current
            DESCRIPTION
               "A threshold for the hwXdslPMLCurrInit15MfailedFullInits
                counter.
                The value 0 means that no threshold is specified for the
                associated counter.
               "
            REFERENCE    "ITU-T G.997.1, paragraph 7.3.1"
            DEFVAL       { 0 }
            ::= { hwXdslGfastLAlarmConfProfEntry 12 }

        hwXdslGfastLAlarmConfProfThresh15MinFailedShrtInt  OBJECT-TYPE
            SYNTAX      Unsigned32
            MAX-ACCESS  read-create
            STATUS      current
            DESCRIPTION
               "A threshold for the hwXdslPMLCurrInit15MFailedShortInits
                counter.
                The value 0 means that no threshold is specified for the
                associated counter.
               "
            REFERENCE    "ITU-T G.997.1, paragraph 7.3.1"
            DEFVAL       { 0 }
            ::= { hwXdslGfastLAlarmConfProfEntry 13 }

        hwXdslGfastLAlarmConfProfRowStatus  OBJECT-TYPE
            SYNTAX      RowStatus
            MAX-ACCESS  read-create
            STATUS      current
            DESCRIPTION
               "This object is used to create a new row or to modify or
                delete an existing row in this table.

                A profile is activated by setting this object to 'active'.
                When 'active' is set, the system will validate the profile.

                Before a profile can be deleted or taken out of service
                (by setting this object to 'destroy' or 'outOfService'),
                it must be not referenced from all associated
                templates.
               "
            ::= { hwXdslGfastLAlarmConfProfEntry 14 }

        hwXdslGfastLAlarmConfProfThresh15MinFullInt  OBJECT-TYPE
            SYNTAX      Unsigned32
            MAX-ACCESS  read-create
            STATUS      current
            DESCRIPTION
               "A threshold for the hwXdslPMLCurrInit15MFullInits
                counter.
                The value 0 means that no threshold is specified for the
                associated counter.
               "
            REFERENCE    "ITU-T G.997.1, paragraph 7.3.1"
            DEFVAL       { 0 }
              ::= { hwXdslGfastLAlarmConfProfEntry 15 }

        hwXdslGfastLAlarmConfProfXtucThresh15MinLeftrs  OBJECT-TYPE
            SYNTAX      HCPerfIntervalThreshold
            UNITS       "seconds"
            MAX-ACCESS  read-create
            STATUS      current
            DESCRIPTION
               "A threshold for the hwXdslPMLCurr15MLeftrs counter,
                when hwXdslPMLCurrUnit is XTUC {1}.
                The value 0 means that no threshold is specified for the
                associated counter.
                Unit: seconds
               "
            REFERENCE    "ITU-T G.997.1, paragraph 7.3.1"
            DEFVAL       { 0 }
            ::= { hwXdslGfastLAlarmConfProfEntry 16 }

        hwXdslGfastLAlarmConfProfXturThresh15MinLeftrs  OBJECT-TYPE
            SYNTAX      HCPerfIntervalThreshold
            UNITS       "seconds"
            MAX-ACCESS  read-create
            STATUS      current
            DESCRIPTION
               "A threshold for the hwXdslPMLCurr15MLeftrs counter,
                when hwXdslPMLCurrUnit is XTUR {2}.
                The value 0 means that no threshold is specified for the
                associated counter.
                Unit: seconds
               "
            REFERENCE    "ITU-T G.997.1, paragraph 7.3.1"
            DEFVAL       { 0 }
            ::= { hwXdslGfastLAlarmConfProfEntry 17 }

         hwXdslGfastLAlarmConfProfDyingGaspAlarmSwitch OBJECT-TYPE
            SYNTAX INTEGER {
                               enable (1),
                               disable (2)
                           }
            MAX-ACCESS  read-create
            STATUS      current
            DESCRIPTION
                       "This object enable/disable the report of LOSS-OF-POWER
                        alarm in a G.fast line.
                        Options:
                        1. enable(1)  - The report of LOSS-OF-POWER alarm in a G.fast line is enabled
                        2. disable(2) - The report of LOSS-OF-POWER alarm in a G.fast line is disabled
                       "
            DEFVAL       { enable }
            ::= { hwXdslGfastLAlarmConfProfEntry 18 }

        hwXdslGfastLAlarmConfProfActiveFailAlarmSwitch OBJECT-TYPE
            SYNTAX INTEGER {
                               enable (1),
                               disable (2)
                           }
            MAX-ACCESS  read-create
            STATUS      current
            DESCRIPTION
                       "This object enable/disable the active fail alarm switch.
                        Options:
                        1. enable(1)  - The active fail alarm switch is enabled
                        2. disable(2) - The active fail alarm switch is disabled
                       "
            DEFVAL       { enable }
            ::= { hwXdslGfastLAlarmConfProfEntry 19 }

        hwXdslGfastLAlarmConfProfRateChangeAlarmSwitch OBJECT-TYPE
            SYNTAX INTEGER {
                               enable (1),
                               disable (2)
                           }
            MAX-ACCESS  read-create
            STATUS      current
            DESCRIPTION
                       "This object enable/disable the active rate change alarm switch.
                        Options:
                        1. enable(1)  - The active rate change alarm switch is enabled
                        2. disable(2) - The active rate change alarm switch is disabled
                       "
            DEFVAL       { enable }
            ::= { hwXdslGfastLAlarmConfProfEntry 20 }

        hwXdslGfastLAlarmConfProfLegacyCpeAlarmSwitch OBJECT-TYPE
            SYNTAX INTEGER {
                               enable (1),
                               disable (2)
                           }
            MAX-ACCESS  read-create
            STATUS      current
            DESCRIPTION
                       "This object enable/disable the legacy cpe alarm switch.
                        Options:
                        1. enable(1)  - The legacy cpe alarm switch is enabled
                        2. disable(2) - The legacy cpe alarm switch is disabled
                       "
            DEFVAL       { enable }
            ::= { hwXdslGfastLAlarmConfProfEntry 21 }

        hwXdslGfastLAlarmConfProfVictAbnormalVariationAlarmSwitch OBJECT-TYPE
            SYNTAX INTEGER {
                               enable (1),
                               disable (2)
                           }
            MAX-ACCESS  read-create
            STATUS      current
            DESCRIPTION
                       "This object enable/disable alarm switch that the port
                        receives abnormal crosstalk.
                        Options:
                        1. enable(1)  - The alarm switch that the port receives
                                        abnormal crosstalk is enabled
                        2. disable(2) - The alarm switch that the port receives
                                        abnormal crosstalk is disabled
                       "
            DEFVAL       { enable }
            ::= { hwXdslGfastLAlarmConfProfEntry 22 }

        hwXdslGfastLAlarmConfProfDistAbnormalVariationAlarmSwitch OBJECT-TYPE
            SYNTAX INTEGER {
                               enable (1),
                               disable (2)
                           }
            MAX-ACCESS  read-create
            STATUS      current
            DESCRIPTION
                       "This object enable/disable the alarm switch that the port
                        causes abnormal crosstalk.
                        Options:
                        1. enable(1)  - The alarm switch that the port causes
                                        abnormal crosstalk is enabled
                        2. disable(2) - The alarm switch that the port causes
                                        abnormal crosstalk is disabled
                       "
            DEFVAL       { enable }
            ::= { hwXdslGfastLAlarmConfProfEntry 23 }

        hwXdslGfastLAlarmConfProfReceivedESAbnormalAlarmSwitch OBJECT-TYPE
            SYNTAX INTEGER {
                               enable (1),
                               disable (2)
                           }
            MAX-ACCESS  read-create
            STATUS      current
            DESCRIPTION
                       "This object enable/disable the alarm switch that The port
                        receives abnormal error sample messages.
                        Options:
                        1. enable(1)  - The alarm switch that the port receives
                                        abnormal error sample messages is enabled
                        2. disable(2) - The alarm switch that the port receives
                                        abnormal error sample messages is disabled
                       "
            DEFVAL       { enable }
            ::= { hwXdslGfastLAlarmConfProfEntry 24 }

        hwXdslGfastLAlarmConfProfNonVectoringCPEActivatedAlarmSwitch OBJECT-TYPE
            SYNTAX INTEGER {
                               enable (1),
                               disable (2)
                           }
            MAX-ACCESS  read-create
            STATUS      current
            DESCRIPTION
                       "This object enable/disable the alarm switch that the port is
                        activated in none-vectoring mode.
                        Options:
                        1. enable(1)  - The alarm switch that the port is activated
                                        in none-vectoring mode is enabled
                        2. disable(2) - The alarm switch that the port is activated
                                        in none-vectoring mode is disabled
                       "
            DEFVAL       { enable }
            ::= { hwXdslGfastLAlarmConfProfEntry 25 }

        hwXdslGfastLAlarmConfProfFreqRetrainReachThresholdAlarmSwitch OBJECT-TYPE
            SYNTAX INTEGER {
                               enable (1),
                               disable (2)
                           }
            MAX-ACCESS  read-create
            STATUS      current
            DESCRIPTION
                       "This object enable/disable the alarm switch that the port
                        frequently retrain times in 15 minutes reach the threshold.
                        Options:
                        1. enable(1)  - The alarm switch that the port frequently retrain
                                        times in 15 minutes reach the threshold is enabled
                        2. disable(2) - The alarm switch that the port frequently retrain
                                        times in 15 minutes reach the threshold is disabled
                       "
            DEFVAL       { enable }
            ::= { hwXdslGfastLAlarmConfProfEntry 26 }

        hwXdslGfastLAlarmConfProfPSConfigAbnormalAlarmSwitch OBJECT-TYPE
            SYNTAX INTEGER {
                               enable (1),
                               disable (2)
                           }
            MAX-ACCESS  read-create
            STATUS      current
            DESCRIPTION
                       "This object enable/disable the pilot sequence configuration abnormal alarm switch.
                        Options:
                        1. enable(1)  - The pilot sequence configuration abnormal alarm switch is enabled
                        2. disable(2) - The pilot sequence configuration abnormal alarm switch is disabled
                       "
            DEFVAL       { enable }
            ::= { hwXdslGfastLAlarmConfProfEntry 27 }

          --      hwXdslGfastChAlarmConfProfileTable

        hwXdslGfastChAlarmConfProfileTable  OBJECT-TYPE
            SYNTAX      SEQUENCE  OF  HwXdslGfastChAlarmConfProfileEntry
            MAX-ACCESS  not-accessible
            STATUS      current
            DESCRIPTION
                "The table hwXdslGfastChAlarmConfProfileTable contains G.fast
                  channel PM thresholds profiles.
                  The index of this table is hwXdslGfastChAlarmConfProfileName.
                  A default profile with an index of 'DEFVAL' will
                  always exist and its parameters will be set to vendor-specific
                  values, unless otherwise specified in this document.
                 "
            ::= { hwXdslGfastProfileAlarmConf 3 }

        hwXdslGfastChAlarmConfProfileEntry  OBJECT-TYPE
            SYNTAX      HwXdslGfastChAlarmConfProfileEntry
            MAX-ACCESS  not-accessible
            STATUS      current
            DESCRIPTION
                "The table hwXdslGfastChAlarmConfProfileTable contains G.fast
                 channel PM thresholds profiles.
                 The index of this entry is hwXdslGfastChAlarmConfProfileName.
                 A default profile with an index of 'DEFVAL' will
                 always exist and its parameters will be set to vendor-specific
                 values, unless otherwise specified in this document.
                "
            INDEX  { IMPLIED hwXdslGfastChAlarmConfProfileName }
            ::= { hwXdslGfastChAlarmConfProfileTable 1 }

        HwXdslGfastChAlarmConfProfileEntry ::=
             SEQUENCE {
             hwXdslGfastChAlarmConfProfileName                             OCTET STRING,
             hwXdslGfastChAlarmConfProfileXtucThresh15MinCodingViolations  Unsigned32,
             hwXdslGfastChAlarmConfProfileXtucThresh15MinCorrected         Unsigned32,
             hwXdslGfastChAlarmConfProfileXturThresh15MinCodingViolations  Unsigned32,
             hwXdslGfastChAlarmConfProfileXturThresh15MinCorrected         Unsigned32,
             hwXdslGfastChAlarmConfProfileMonitoringRateDs                 Unsigned32,
             hwXdslGfastChAlarmConfProfileMonitoringRateUs                 Unsigned32,
             hwXdslGfastChAlarmConfProfileRowStatus                        RowStatus
             }

        hwXdslGfastChAlarmConfProfileName  OBJECT-TYPE
            SYNTAX      OCTET STRING (SIZE(1..32))
            MAX-ACCESS  not-accessible
            STATUS      current
            DESCRIPTION
               "This object identifies a row in this table."
            ::= { hwXdslGfastChAlarmConfProfileEntry 1 }

        hwXdslGfastChAlarmConfProfileXtucThresh15MinCodingViolations OBJECT-TYPE
            SYNTAX      Unsigned32
            MAX-ACCESS  read-create
            STATUS      current
            DESCRIPTION
               "A threshold for the hwXdslPMChCurr15MCodingViolations
                counter, when hwXdslPMChCurrUnit is XTUC {1}.
                The value 0 means that no threshold is specified for the
                associated counter.
               "
            REFERENCE    "ITU-T G.997.1, paragraph 7.3.2"
            DEFVAL       { 0 }
            ::= { hwXdslGfastChAlarmConfProfileEntry 2 }

        hwXdslGfastChAlarmConfProfileXtucThresh15MinCorrected  OBJECT-TYPE
            SYNTAX      Unsigned32
            MAX-ACCESS  read-create
            STATUS      current
            DESCRIPTION
               "A threshold for the hwXdslPMChCurr15MCorrectedBlocks
                counter, when hwXdslPMChCurrUnit is XTUC {1}.
                The value 0 means that no threshold is specified for the
                associated counter.
               "
            REFERENCE    "ITU-T G.997.1, paragraph 7.3.2"
            DEFVAL       { 0 }
              ::= { hwXdslGfastChAlarmConfProfileEntry 3 }

        hwXdslGfastChAlarmConfProfileXturThresh15MinCodingViolations  OBJECT-TYPE
            SYNTAX      Unsigned32
            MAX-ACCESS  read-create
            STATUS      current
            DESCRIPTION
                "A threshold for the hwXdslPMChCurr15MCodingViolations
                 counter, when hwXdslPMChCurrUnit is XTUR {2}.
                 The value 0 means that no threshold is specified for the
                 associated counter.
                "
            REFERENCE    "ITU-T G.997.1, paragraph 7.3.2"
            DEFVAL       { 0 }
              ::= { hwXdslGfastChAlarmConfProfileEntry 4 }

        hwXdslGfastChAlarmConfProfileXturThresh15MinCorrected  OBJECT-TYPE
            SYNTAX      Unsigned32
            MAX-ACCESS  read-create
            STATUS      current
            DESCRIPTION
                "A threshold for the hwXdslPMChCurr15MCorrectedBlocks
                 counter, when hwXdslPMChCurrUnit is XTUR {2}.
                 The value 0 means that no threshold is specified for the
                 associated counter.
                "
            REFERENCE    "ITU-T G.997.1, paragraph 7.3.2"
            DEFVAL       { 0 }
              ::= { hwXdslGfastChAlarmConfProfileEntry 5 }

        hwXdslGfastChAlarmConfProfileMonitoringRateDs  OBJECT-TYPE
            SYNTAX      Unsigned32(0..2000000000)
            UNITS       "bits/second"
            MAX-ACCESS  read-create
            STATUS      current
            DESCRIPTION
                "The channel monitoring rate downstream.
                 Huawei defined. When the value you set is larger than
                 the value of the rate downstream defined in the channel
                 profile, it will not be successful. The value 0 means
                 that no threshold is specified for the associated
                 counter.
                 Unit: bits/second
                "
            DEFVAL       { 0 }
              ::= { hwXdslGfastChAlarmConfProfileEntry 6 }

        hwXdslGfastChAlarmConfProfileMonitoringRateUs  OBJECT-TYPE
            SYNTAX      Unsigned32(0..2000000000)
            UNITS       "bits/second"
            MAX-ACCESS  read-create
            STATUS      current
            DESCRIPTION
                "The channel monitoring rate upstream.
                 Huawei defined. When the value you set is larger than
                 the value of the rate upstream defined in the channel
                 profile, it will not be successful. The value 0 means
                 that no threshold is specified for the associated
                 counter.
                 Unit: bits/second
                "
            DEFVAL       { 0 }
              ::= { hwXdslGfastChAlarmConfProfileEntry 7 }

        hwXdslGfastChAlarmConfProfileRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwXdslGfastChAlarmConfProfileEntry 8 }



        --  hwXdslTR129LineConfTemplateTable
        hwXdslTR129LineConfTemplateTable  OBJECT-TYPE
            SYNTAX      SEQUENCE  OF  HwXdslTR129LineConfTemplateEntry
            MAX-ACCESS  not-accessible
            STATUS      current
            DESCRIPTION
                "The table hwXdslTR129LineConfTemplateTable contains XDSL line
                 configuration template. The index of this table is
                 hwXdslTR129LineConfTempTemplateName.
                 A default template with an index of 'DEFVAL' will
                 always exist and its parameters will be set to vendor-specific
                 values, unless otherwise specified in this document.
                "
            ::= { hwXdslProfileLine 4 }

        hwXdslTR129LineConfTemplateEntry  OBJECT-TYPE
            SYNTAX      HwXdslTR129LineConfTemplateEntry
            MAX-ACCESS  not-accessible
            STATUS      current
            DESCRIPTION
                "The table hwXdslTR129LineConfTemplateTable contains XDSL line
                 configuration template.
                 The index of this entry is hwXdslTR129LineConfTempTemplateName.
                 A default template with an index of 'DEFVAL' will
                 always exist and its parameters will be set to vendor-specific
                 values, unless otherwise specified in this document.
                "
            INDEX  { IMPLIED hwXdslTR129LineConfTempTemplateName }
            ::= { hwXdslTR129LineConfTemplateTable 1 }

        HwXdslTR129LineConfTemplateEntry  ::=
            SEQUENCE {
              hwXdslTR129LineConfTempTemplateName      OCTET STRING,
              hwXdslTR129LineConfTempLineProfile       OCTET STRING,
              hwXdslTR129LineConfTempChanConfProfile  OCTET STRING,
              hwXdslTR129LineConfTempRowStatus         RowStatus
           }

        hwXdslTR129LineConfTempTemplateName  OBJECT-TYPE
            SYNTAX      OCTET STRING (SIZE(1..32))
            MAX-ACCESS  accessible-for-notify
            STATUS      current
            DESCRIPTION
                "This object identifies a row in this table."
            REFERENCE    "DSL Forum TR-90, paragraph 5.1.4"
            ::= { hwXdslTR129LineConfTemplateEntry 1 }

        hwXdslTR129LineConfTempLineProfile  OBJECT-TYPE
            SYNTAX      OCTET STRING (SIZE(1..32))
            MAX-ACCESS  read-create
            STATUS      current
            DESCRIPTION
                "The value of this object identifies the row in the XDSL Line
                 Configuration Profile Table, (hwXdslTR129LineConfProfTable),
                 which applies for this XDSL line.
                "
            REFERENCE    "DSL Forum TR-90, paragraph 5.1.4"
            DEFVAL       { "DEFVAL" }
            ::= { hwXdslTR129LineConfTemplateEntry 2 }

        hwXdslTR129LineConfTempChanConfProfile  OBJECT-TYPE
            SYNTAX      OCTET STRING (SIZE(1..32))
            MAX-ACCESS  read-create
            STATUS      current
            DESCRIPTION
                "The value of this object identifies the row in the XDSL
                 Channel Configuration Profile Table (hwXdslTR129ChConfProfileTable)
                 that applies to XDSL bearer channel.  The channel profile name
                 specified here must match the name of an existing row in the
                 hwXdslTR129ChConfProfileTable table.
                "
            DEFVAL       { "DEFVAL" }
            ::= { hwXdslTR129LineConfTemplateEntry 3 }


        hwXdslTR129LineConfTempRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 lines.
                "
            ::= { hwXdslTR129LineConfTemplateEntry 4 }
        -- end of hwXdslTR129LineConfTemplateTable

        --  hwXdslTR129LineConfProfTable
        hwXdslTR129LineConfProfTable  OBJECT-TYPE
            SYNTAX      SEQUENCE  OF  HwXdslTR129LineConfProfEntry
            MAX-ACCESS  not-accessible
            STATUS      current
            DESCRIPTION
                "The table hwXdslTR129LineConfProfTable contains XDSL line profile
                 configuration. The index of this table is hwXdslTR129LineConfProfProfileName.
                 A default profile with an index of 'DEFVAL' will
                 always exist and its parameters will be set to vendor-specific
                 values, unless otherwise specified in this document.
                "
            ::= { hwXdslProfileLine 5 }

        hwXdslTR129LineConfProfEntry  OBJECT-TYPE
            SYNTAX      HwXdslTR129LineConfProfEntry
            MAX-ACCESS  not-accessible
            STATUS      current
            DESCRIPTION
                "The table hwXdslTR129LineConfProfTable contains XDSL line profile
                 configuration. The index of this entry is hwXdslTR129LineConfProfProfileName.
                 A default profile with an index of 'DEFVAL' will
                 always exist and its parameters will be set to vendor-specific
                 values, unless otherwise specified in this document.
                "
            INDEX  { IMPLIED hwXdslTR129LineConfProfProfileName }
            ::= { hwXdslTR129LineConfProfTable 1 }

        HwXdslTR129LineConfProfEntry  ::=
           SEQUENCE {
              hwXdslTR129LineConfProfProfileName          OCTET STRING,
              hwXdslTR129LineConfProfScMaskDs             HwXdslScMaskDs,
              hwXdslTR129LineConfProfScMaskUs             HwXdslScMaskUs,
              hwXdslTR129LineConfProfRfiBands             OCTET STRING,
              hwXdslTR129LineConfProfVDSLtoneblackout     OCTET STRING,
              hwXdslTR129LineConfProfRaModeDs             INTEGER,
              hwXdslTR129LineConfProfRaModeUs             INTEGER,
              hwXdslTR129LineConfProfRaUsNrmDs            Unsigned32,
              hwXdslTR129LineConfProfRaUsNrmUs            Unsigned32,
              hwXdslTR129LineConfProfRaUsTimeDs           Unsigned32,
              hwXdslTR129LineConfProfRaUsTimeUs           Unsigned32,
              hwXdslTR129LineConfProfRaDsNrmsDs           Unsigned32,
              hwXdslTR129LineConfProfRaDsNrmsUs           Unsigned32,
              hwXdslTR129LineConfProfRaDsTimeDs           Unsigned32,
              hwXdslTR129LineConfProfRaDsTimeUs           Unsigned32,
              hwXdslTR129LineConfProfTargetSnrmDs         Unsigned32,
              hwXdslTR129LineConfProfTargetSnrmUs         Unsigned32,
              hwXdslTR129LineConfProfMaxSnrmDs            Unsigned32,
              hwXdslTR129LineConfProfMaxSnrmUs            Unsigned32,
              hwXdslTR129LineConfProfMinSnrmDs            Unsigned32,
              hwXdslTR129LineConfProfMinSnrmUs            Unsigned32,
              hwXdslTR129LineConfProfXtuTransSysEna       HwXdslTransmissionModeType,
              hwXdslTR129LineConfProfPmMode               HwXdslLConfProfPmMode,
              hwXdslTR129LineConfProfL0Time               Unsigned32,
              hwXdslTR129LineConfProfL2Time               Unsigned32,
              hwXdslTR129LineConfProfL2Atpr               Unsigned32,
              hwXdslTR129LineConfProfL2Atprt              Unsigned32,
              hwXdslTR129LineConfProfDpboEpsd             HwXdslDpboEpsd,
              hwXdslTR129LineConfProfDpboEsel             Unsigned32,
              hwXdslTR129LineConfProfDpboEscm             HwXdslDpboEscm,
              hwXdslTR129LineConfProfDpboMus     Unsigned32,
              hwXdslTR129LineConfProfDpboFmin          Unsigned32,
              hwXdslTR129LineConfProfDpboFmax    Unsigned32,
              hwXdslTR129LineConfProfUpboPsdBand          HwXdslUpboPsdBand,
              hwXdslTR129LineConfProfUpboKl    Unsigned32,
              hwXdslTR129LineConfProfUpboKlf     HwXdslUpboKlf,
              hwXdslTR129LineConfProfRowStatus            RowStatus,
              hwXdslTR129LineConfProfBitSwapDs            HwXdslBitSwap,
              hwXdslTR129LineConfProfBitSwapUs            HwXdslBitSwap,
              hwXdslTR129LineConfProfUpboBoostMode   HwXdslUpboBoostMode,
              hwXdslTR129LineConfProfDpboEselMin          Unsigned32,
              hwXdslTR129LineConfProfUpboKl0RefBand       HwXdslUpboKl0RefBand,
              hwXdslTR129LineConfProfReferenceClock       INTEGER,
              hwXdslTR129LineConfProfSosTimeDs            Unsigned32,
              hwXdslTR129LineConfProfSosTimeUs            Unsigned32,
              hwXdslTR129LineConfProfSosNtonesDs          Unsigned32,
              hwXdslTR129LineConfProfSosNtonesUs          Unsigned32,
              hwXdslTR129LineConfProfSosCrcDs             Unsigned32,
              hwXdslTR129LineConfProfSosCrcUs             Unsigned32,
              hwXdslTR129LineConfProfMaxSosDs             Unsigned32,
              hwXdslTR129LineConfProfMaxSosUs             Unsigned32,
              hwXdslTR129LineConfProfSnrmoffsetRocDs      Unsigned32,
              hwXdslTR129LineConfProfSnrmoffsetRocUs      Unsigned32,
              hwXdslTR129LineConfProfInpminRocDs          Unsigned32,
              hwXdslTR129LineConfProfInpminRocUs          Unsigned32,
              hwXdslTR129LineConfProfInmIatoDs            Unsigned32,
              hwXdslTR129LineConfProfInmIatsDs            Unsigned32,
              hwXdslTR129LineConfProfInmCcDs              Unsigned32,
              hwXdslTR129LineConfProfInmInpeqModeDs       Unsigned32,
              hwXdslTR129LineConfProfInmIatoUs            Unsigned32,
              hwXdslTR129LineConfProfInmIatsUs            Unsigned32,
              hwXdslTR129LineConfProfInmCcUs                Unsigned32,
              hwXdslTR129LineConfProfInmInpeqModeUs       Unsigned32,
              hwXdslTR129LineConfProfL3Time               Unsigned32,
              hwXdslTR129LineConfProfRtxModeDs            INTEGER,
              hwXdslTR129LineConfProfRtxModeUs            INTEGER,
              hwXdslTR129LineConfProfLeftrThreshDs        Unsigned32,
              hwXdslTR129LineConfProfLeftrThreshUs        Unsigned32,
              hwXdslTR129LineConfProfForceInpDs           TruthValue,
              hwXdslTR129LineConfProfForceInpUs           TruthValue,
              hwXdslTR129LineConfProfAeleMode             Unsigned32,
              hwXdslTR129LineConfProfUpboElmt             Unsigned32,
              hwXdslTR129LineConfProfUpboKlAuto           Unsigned32,

              hwXdslTR129LineConfProfGfastProfiles        HWVOPGfastProfiles,
              hwXdslTR129LineConfProfGfastLineLowFreqEdgeValueDs Gauge32,
              hwXdslTR129LineConfProfGfastCarMaskDs    Xdsl2CarMask,
              hwXdslTR129LineConfProfGfastUpboKL          Gauge32,
              hwXdslTR129LineConfProfGfastUpboKLF         Xdsl2UpboKLF,
              hwXdslTR129LineConfProfGfastKlAuto          Unsigned32,
              hwXdslTR129LineConfProfGfastUpboKLREF       Integer32,
              hwXdslTR129LineConfProfGfastUpboPsdA        Integer32,
              hwXdslTR129LineConfProfGfastUpboPsdB        Integer32,
              hwXdslTR129LineConfProfGfastRfiBands        Xdsl2RfiBands,
              hwXdslTR129LineConfProfGfastIarBands        HWVOPGfastIarBands,
              hwXdslTR129LineConfProfGfastMinSnrmDs       Gauge32,
              hwXdslTR129LineConfProfGfastMinSnrmUs       Gauge32,
              hwXdslTR129LineConfProfGfastTargetSnrmDs    Gauge32,
              hwXdslTR129LineConfProfGfastTargetSnrmUs    Gauge32,
              hwXdslTR129LineConfProfGfastMaxSnrmDs       Gauge32,
              hwXdslTR129LineConfProfGfastMaxSnrmUs       Gauge32,
              hwXdslTR129LineConfProfGfastRaUsNrmDs       Gauge32,
              hwXdslTR129LineConfProfGfastRaUsNrmUs       Gauge32,
              hwXdslTR129LineConfProfGfastRaDsNrmDs       Gauge32,
              hwXdslTR129LineConfProfGfastRaDsNrmUs       Gauge32,
              hwXdslTR129LineConfProfGfastUsTimeDs        Gauge32,
              hwXdslTR129LineConfProfGfastUsTimeUs        Gauge32,
              hwXdslTR129LineConfProfGfastDsTimeDs        Gauge32,
              hwXdslTR129LineConfProfGfastDsTimeUs        Gauge32,
              hwXdslTR129LineConfProfGfastSosFraTimeDs    Unsigned32,
              hwXdslTR129LineConfProfGfastSosFraTimeUs    Unsigned32,
              hwXdslTR129LineConfProfGfastSosFraNtonesDs  Unsigned32,
              hwXdslTR129LineConfProfGfastSosFraNtonesUs  Unsigned32,
              hwXdslTR129LineConfProfGfastSosFraMinRtxUcDs  Unsigned32,
              hwXdslTR129LineConfProfGfastSosFraMinRtxUcUs  Unsigned32,
              hwXdslTR129LineConfProfGfastCarMaskUs        Xdsl2CarMask,
              hwXdslTR129LineConfProfGfastTargetSnrmRmcDs   Gauge32,
              hwXdslTR129LineConfProfGfastTargetSnrmRmcUs   Gauge32,
              hwXdslTR129LineConfProfGfastMinSnrmRmcDs     Gauge32,
              hwXdslTR129LineConfProfGfastMinSnrmRmcUs     Gauge32,
              hwXdslTR129LineConfProfGfastMaxBLRmcDs        Gauge32,
              hwXdslTR129LineConfProfGfastMaxBLRmcUs        Gauge32,
              hwXdslTR129LineConfProfGfastSosFraVenDiscDs     INTEGER,
              hwXdslTR129LineConfProfGfastSosFraVenDiscUs     INTEGER,
              hwXdslTR129LineConfProfGfastLineLowFreqEdgeValueUs Gauge32,
              hwXdslTR129LineConfProfGfastFallbackFreq Gauge32
           }

        hwXdslTR129LineConfProfProfileName  OBJECT-TYPE
            SYNTAX      OCTET STRING (SIZE(1..32))
            MAX-ACCESS  accessible-for-notify
            STATUS      current
            DESCRIPTION
                "This object identifies a row in this table."
            ::= { hwXdslTR129LineConfProfEntry 1 }

        hwXdslTR129LineConfProfScMaskDs  OBJECT-TYPE
            SYNTAX      HwXdslScMaskDs
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 0xffffffff).  Also note that if NSCds &lt; 512, all bits
                 i (NSCds i &lt;= 512) should be set to '1'.
                "
            REFERENCE    "ITU-T G.997.1, paragraph 7.3.1.2.6"
            ::= { hwXdslTR129LineConfProfEntry 2 }

        hwXdslTR129LineConfProfScMaskUs  OBJECT-TYPE
            SYNTAX      HwXdslScMaskUs
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be 0xffffffff).  Also note that if NSCus &lt;
                 64, all bits i (NSCus &lt; i &lt;= 64) should be set to '1'.
                "
            REFERENCE    "ITU-T G.997.1, paragraph 7.3.1.2.7"
            ::= { hwXdslTR129LineConfProfEntry 3 }

        hwXdslTR129LineConfProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
            ::= { hwXdslTR129LineConfProfEntry 4 }

        hwXdslTR129LineConfProfVDSLtoneblackout  OBJECT-TYPE
             SYNTAX      OCTET STRING(SIZE(0..79))
             MAX-ACCESS  read-create
             STATUS      current
             DESCRIPTION
                 "The subset of subcarrier mask that shall be
                  used to mask the subcarriers.
                  It is a string of bands consist of begin tone index
                  and end tone index.
                  for example :0-10,20-50,100-4095
                  It can contain as most as 8 bands.
                 "
             REFERENCE    "ITU-T G.997.1(200604), paragraph 7.3.1.2.8"
            ::= { hwXdslTR129LineConfProfEntry 5 }

        hwXdslTR129LineConfProfRaModeDs  OBJECT-TYPE
            SYNTAX      INTEGER
                        {
                         manual(1),
                         rainit(2),
                         dynamic(3),
                         dynamicwithsos(4)
                        }
            MAX-ACCESS  read-create
            STATUS      current
            DESCRIPTION
                "The mode of operation of a rate-adaptive xTU-C in the transmit
                 direction.
                 Options:
                 1. manual(1)            - No Rate-Adaptation.The initialization
                                           process attempts to synchronize to a
                                           specified rate
                 2. rainit(2)            - Rate-Adaptation during initialization process
                                           only, which attempts to synchronize to a rate
                                           between minimum and maximum specified values
                 3. dynamic(3)           - Rate-Adaptation during show time
                 4. dynamicwithsos(4)    - Rate-Adaptation during show time by SOS and SRA.
                                           In this mode,enabling of SOS and SRA is mandatory.

                "
            REFERENCE    "ITU-T G.997.1, paragraph 7.3.1.4.1"
            DEFVAL       { rainit }
            ::= { hwXdslTR129LineConfProfEntry 6 }

        hwXdslTR129LineConfProfRaModeUs  OBJECT-TYPE
            SYNTAX      INTEGER
                        {
                         manual(1),
                         rainit(2),
                         dynamic(3),
                         dynamicwithsos(4)
                        }
            MAX-ACCESS  read-create
            STATUS      current
            DESCRIPTION
                "The mode of operation of a rate-adaptive xTU-R in the transmit
                 direction.
                 Options:
                 1. manual(1)            - No Rate-Adaptation.The initialization
                                           process attempts to synchronize to a
                                           specified rate
                 2. rainit(2)            - Rate-Adaptation during initialization process
                                           only, which attempts to synchronize to a rate
                                           between minimum and maximum specified values
                 3. dynamic(3)           - Rate-Adaptation during show time
                 4. dynamicwithsos(4)    - Rate-Adaptation during show time by SOS and SRA.
                                           In this mode, enabling of SOS and SRA is mandatory.
                "
            REFERENCE    "ITU-T G.997.1, paragraph 7.3.1.4.2"
            DEFVAL       { rainit }
            ::= { hwXdslTR129LineConfProfEntry 7 }

        hwXdslTR129LineConfProfRaUsNrmDs  OBJECT-TYPE
            SYNTAX      Unsigned32(0..310)
            UNITS       "0.1 dB"
            MAX-ACCESS  read-create
            STATUS      current
            DESCRIPTION
                "The Downstream Up-Shift Noise Margin value, to be used when
                 hwXdslTR129LineConfProfRaModeDs is set to DynamicRa.  If the downstream
                 noise margin is above this value and stays above it for
                 more than the time specified by the hwXdslTR129LineConfProfRaUsTimeDs,
                 the xTU-R shall attempt to increase the downstream net data
                 rate.  The Downstream Up-shift Noise Margin ranges from 0 to
                 310 units of 0.1 dB (Physical values are 0 to 31 dB).
                 Unit: 0.1 dB
                "
            REFERENCE    "ITU-T G.997.1, paragraph 7.3.1.4.3"
            DEFVAL       { 0 }
            ::= { hwXdslTR129LineConfProfEntry 8 }

        hwXdslTR129LineConfProfRaUsNrmUs  OBJECT-TYPE
            SYNTAX      Unsigned32(0..310)
            UNITS       "0.1 dB"
            MAX-ACCESS  read-create
            STATUS      current
            DESCRIPTION
                "The Upstream Up-Shift Noise Margin value, to be used when
                 hwXdslTR129LineConfProfRaModeUs is set to DynamicRa.  If the upstream
                 noise margin is above this value and stays above it for more
                 than the time specified by the hwXdslTR129LineConfProfRaUsTimeUs, the
                 xTU-C shall attempt to increase the upstream net data rate.
                 The Upstream Up-shift Noise Margin ranges from 0 to 310 units
                 of 0.1 dB (Physical values are 0 to 31 dB).
                 Unit: 0.1 dB
                "
            REFERENCE    "ITU-T G.997.1, paragraph 7.3.1.4.4"
            DEFVAL       { 0 }
            ::= { hwXdslTR129LineConfProfEntry 9 }

        hwXdslTR129LineConfProfRaUsTimeDs  OBJECT-TYPE
            SYNTAX      Unsigned32(0..16383)
            UNITS       "seconds"
            MAX-ACCESS  read-create
            STATUS      current
            DESCRIPTION
                "The Downstream Up-Shift Time Interval, to be used when
                 hwXdslTR129LineConfProfRaModeDs is set to DynamicRa.  The interval of
                 time that the downstream noise margin should stay above the
                 Downstream Up-shift Noise Margin before the xTU-R shall
                 attempt to increase the downstream net data rate.
                 Unit: seconds
                "
            REFERENCE    "ITU-T G.997.1, paragraph 7.3.1.4.5"
            DEFVAL       { 0 }
            ::= { hwXdslTR129LineConfProfEntry 10 }

        hwXdslTR129LineConfProfRaUsTimeUs  OBJECT-TYPE
            SYNTAX      Unsigned32(0..16383)
            UNITS       "seconds"
            MAX-ACCESS  read-create
            STATUS      current
            DESCRIPTION
                "The Upstream Up-Shift Time Interval, to be used when
                 hwXdslTR129LineConfProfRaModeUs is set to DynamicRa.  The interval of
                 time the upstream noise margin should stay above the
                 Upstream Up-shift Noise Margin before the xTU-C shall
                 attempt to increase the upstream net data rate.
                 Unit: seconds
                "
            REFERENCE    "ITU-T G.997.1, paragraph 7.3.1.4.6"
            DEFVAL       { 0 }
            ::= { hwXdslTR129LineConfProfEntry 11 }

        hwXdslTR129LineConfProfRaDsNrmsDs  OBJECT-TYPE
            SYNTAX      Unsigned32(0..310)
            UNITS       "0.1 dB"
            MAX-ACCESS  read-create
            STATUS      current
            DESCRIPTION
                "The Downstream Down-Shift Noise Margin value, to be used when
                 hwXdslTR129LineConfProfRaModeDs is set to DynamicRa.  If the downstream
                 noise margin is below this value and stays below that for more
                 than the time specified by the hwXdslTR129LineConfProfRaDsTimeDs, the
                 xTU-R shall attempt to decrease the downstream net data rate.
                 The Downstream Down-shift Noise Margin ranges from 0 to 310
                 units of 0.1 dB (Physical values are 0 to 31 dB).
                 Unit: 0.1 dB
                "
            REFERENCE    "ITU-T G.997.1, paragraph 7.3.1.4.7"
            DEFVAL       { 0 }
            ::= { hwXdslTR129LineConfProfEntry 12 }

        hwXdslTR129LineConfProfRaDsNrmsUs  OBJECT-TYPE
            SYNTAX      Unsigned32(0..310)
            UNITS       "0.1 dB"
            MAX-ACCESS  read-create
            STATUS      current
            DESCRIPTION
                "The Upstream Down-shift Noise Margin value, to be used when
                 hwXdslTR129LineConfProfRaModeUs is set to DynamicRa.  If the upstream
                 noise margin is below this value and stays below that for more
                 than the time specified by the hwXdslTR129LineConfProfRaDsTimeUs, the
                 xTU-C shall attempt to decrease the upstream net data rate.
                 The Upstream Down-shift Noise Margin ranges from 0 to 310
                 units of 0.1 dB (Physical values are 0 to 31 dB).
                 Unit: 0.1 dB
                "
            REFERENCE    "ITU-T G.997.1, paragraph 7.3.1.4.8"
            DEFVAL       { 0 }
            ::= { hwXdslTR129LineConfProfEntry 13 }

        hwXdslTR129LineConfProfRaDsTimeDs  OBJECT-TYPE
            SYNTAX      Unsigned32(0..16383)
            UNITS       "seconds"
            MAX-ACCESS  read-create
            STATUS      current
            DESCRIPTION
                "The Downstream Down-shift Time Interval, to be used when
                 hwXdslTR129LineConfProfRaModeDs is set to DynamicRa.  The interval of
                 time the downstream noise margin should stay below the
                 Downstream Down-shift Noise Margin before the xTU-R shall
                 attempt to decrease the downstream net data rate.
                 Unit: seconds
                "
            REFERENCE    "ITU-T G.997.1, paragraph 7.3.1.4.9"
            DEFVAL       { 0 }
            ::= { hwXdslTR129LineConfProfEntry 14 }

        hwXdslTR129LineConfProfRaDsTimeUs  OBJECT-TYPE
            SYNTAX      Unsigned32(0..16383)
            UNITS       "seconds"
            MAX-ACCESS  read-create
            STATUS      current
            DESCRIPTION
                "The Upstream Down-Shift Time Interval, to be used when
                 hwXdslTR129LineConfProfRaModeUs is set to DynamicRa.  The interval of
                 time the upstream noise margin should stay below the Upstream
                 Down-shift Noise Margin before the xTU-C shall attempt to
                 decrease the upstream net data rate.
                 Unit: seconds
                "
            REFERENCE    "ITU-T G.997.1, paragraph 7.3.1.4.10"
            DEFVAL       { 0 }
            ::= { hwXdslTR129LineConfProfEntry 15 }

        hwXdslTR129LineConfProfTargetSnrmDs  OBJECT-TYPE
            SYNTAX      Unsigned32(0..310)
            UNITS       "0.1 dB"
            MAX-ACCESS  read-create
            STATUS      current
            DESCRIPTION
                "The minimum Noise Margin the xTU-R receiver shall achieve,
                 relative to the BER requirement for each of the downstream
                 bearer channels, to successfully complete initialization.
                 The target noise margin ranges from 0 to 310 units of 0.1 dB
                 (Physical values are 0 to 31 dB).
                 Unit: 0.1 dB
                "
            REFERENCE    "ITU-T G.997.1, paragraph 7.3.1.3.1"
            DEFVAL       { 60 }
            ::= { hwXdslTR129LineConfProfEntry 16 }

        hwXdslTR129LineConfProfTargetSnrmUs  OBJECT-TYPE
            SYNTAX      Unsigned32(0..310)
            UNITS       "0.1 dB"
            MAX-ACCESS  read-create
            STATUS      current
            DESCRIPTION
                "The minimum Noise Margin the xTU-C receiver shall achieve,
                 relative to the BER requirement for each of the upstream
                 bearer channels, to successfully complete initialization.
                 The target noise margin ranges from 0 to 310 units of 0.1 dB
                 (Physical values are 0 to 31 dB).
                 Unit: 0.1 dB
                "
            REFERENCE    "ITU-T G.997.1, paragraph 7.3.1.3.2"
            DEFVAL       { 60 }
            ::= { hwXdslTR129LineConfProfEntry 17 }

        hwXdslTR129LineConfProfMaxSnrmDs  OBJECT-TYPE
            SYNTAX      Unsigned32
            UNITS       "0.1 dB"
            MAX-ACCESS  read-create
            STATUS      current
            DESCRIPTION
                "The maximum Noise Margin the xTU-R receiver shall try to
                 sustain. If the Noise Margin is above this level, the xTU-R
                 shall request that the xTU-C reduce the xTU-C transmit power
                 to get a noise margin below this limit (if this functionality
                 is supported).  The maximum noise margin ranges from 0 to 310
                 units of 0.1 dB (Physical values are 0 to 31 dB).  A value of
                 0xffffffff means that there is no maximum.
                 Unit: 0.1 dB
                "
            REFERENCE    "ITU-T G.997.1, paragraph 7.3.1.3.3"
            DEFVAL       { 300 }
            ::= { hwXdslTR129LineConfProfEntry 18 }

        hwXdslTR129LineConfProfMaxSnrmUs  OBJECT-TYPE
            SYNTAX      Unsigned32
            UNITS       "0.1 dB"
            MAX-ACCESS  read-create
            STATUS      current
            DESCRIPTION
                "The maximum Noise Margin the xTU-C receiver shall try to
                 sustain. If the Noise Margin is above this level, the xTU-C
                 shall request that the xTU-R reduce the xTU-R transmit power
                 to get a noise margin below this limit (if this functionality
                 is supported).  The maximum noise margin ranges from 0 to 310
                 units of 0.1 dB (Physical values are 0 to 31 dB).  A value of
                 0xffffffff means that there is no maximum.
                 Unit: 0.1 dB
                "
            REFERENCE    "ITU-T G.997.1, paragraph 7.3.1.3.4"
            DEFVAL       { 300 }
            ::= { hwXdslTR129LineConfProfEntry 19 }

        hwXdslTR129LineConfProfMinSnrmDs  OBJECT-TYPE
            SYNTAX      Unsigned32(0..310)
            UNITS       "0.1 dB"
            MAX-ACCESS  read-create
            STATUS      current
            DESCRIPTION
                "The minimum Noise Margin the xTU-R receiver shall tolerate.
                 If the noise margin falls below this level, the xTU-R shall
                 request that the xTU-C increase the xTU-C transmit power.
                 If an increase to xTU-C transmit power is not possible, a
                 loss-of-margin (LOM) defect occurs, the xTU-R shall fail and
                 attempt to reinitialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.5"
            DEFVAL       { 0 }
            ::= { hwXdslTR129LineConfProfEntry 20 }

        hwXdslTR129LineConfProfMinSnrmUs  OBJECT-TYPE
            SYNTAX      Unsigned32(0..310)
            UNITS       "0.1 dB"
            MAX-ACCESS  read-create
            STATUS      current
            DESCRIPTION
                "The minimum Noise Margin the xTU-C receiver shall tolerate.
                 If the noise margin falls below this level, the xTU-C shall
                 request that the xTU-R increase the xTU-R transmit power.
                 If an increase of xTU-R transmit power is not possible, a
                 loss-of-margin (LOM) defect occurs, the xTU-C shall fail and
                 attempt to re-initialize and the NMS shall be notified.  The
                 minimum noise margin ranges from 0 to 310 units of
                 0.1 dB (Physical values are 0 to 31 dB).  A value of 0 means
                 that there is no minimum.
                 Unit: 0.1 dB
                "
            REFERENCE    "ITU-T G.997.1, paragraph 7.3.1.3.6"
            DEFVAL       { 0 }
            ::= { hwXdslTR129LineConfProfEntry 21 }

        hwXdslTR129LineConfProfXtuTransSysEna  OBJECT-TYPE
            SYNTAX      HwXdslTransmissionModeType
            MAX-ACCESS  read-create
            STATUS      current
            DESCRIPTION
                "xTU Transmission System Enabling (XTSE).  A list of the
                 different coding types enabled in this profile.  It is coded
                 in a bit-map representation with 1 or more bits set.  A bit
                 set to  '1' means that the XTUs may apply the respective
                 coding for the XDSL line.  A bit set to '0' means that
                 the XTUs cannot apply the respective coding for the XDSL
                 line.  All 'reserved' bits should be set to '0'.
                "
            REFERENCE    "ITU-T G.997.1, paragraph 7.3.1.1.1"
            ::= { hwXdslTR129LineConfProfEntry 22 }

        hwXdslTR129LineConfProfPmMode  OBJECT-TYPE
            SYNTAX      HwXdslLConfProfPmMode
            MAX-ACCESS  read-create
            STATUS      current
            DESCRIPTION
                "Power management state Enabling.  Defines the power states the
                 xTU-C or xTU-R may autonomously transition to on this line.
                 Options:
                 1. allowTransitionsToIdle (0)
                 2. allowTransitionsToLowPower (1)
                 A bit with a '1' value means
                 that the xTU is allowed to transit into the respective state
                 and a '0' value means that the xTU is not allowed
                 to transit into the respective state.
                "
            REFERENCE    "ITU-T G.997.1, paragraph 7.3.1.1.4"
            DEFVAL  { allowTransitionsToIdle }
            ::= { hwXdslTR129LineConfProfEntry 23 }

        hwXdslTR129LineConfProfL0Time  OBJECT-TYPE
            SYNTAX      Unsigned32 (0..255)
            UNITS       "seconds"
            MAX-ACCESS  read-create
            STATUS      current
            DESCRIPTION
                "This minimum time (in seconds) between an Exit from the L2
                 state and the next Entry into the L2 state.
                 Unit: seconds
                "
            REFERENCE    "ITU-T G.997.1, paragraph 7.3.1.1.5"
            DEFVAL       { 255 }
            ::= { hwXdslTR129LineConfProfEntry 24 }

        hwXdslTR129LineConfProfL2Time  OBJECT-TYPE
            SYNTAX      Unsigned32 (0..255)
            UNITS       "seconds"
            MAX-ACCESS  read-create
            STATUS      current
            DESCRIPTION
                "This minimum time (in seconds) between an Entry into the
                 L2 state and the first Power Trim in the L2 state and between
                 two consecutive Power Trims in the L2 State.
                 Unit: seconds
                "
            REFERENCE    "ITU-T G.997.1, paragraph 7.3.1.1.6"
            DEFVAL       { 30 }
            ::= { hwXdslTR129LineConfProfEntry 25 }

        hwXdslTR129LineConfProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 It ranges from 0 dB to 31 dB.
                 Unit: dB
                "
            REFERENCE    "ITU-T G.997.1 (amendment 1), 7.3.1.1.7"
            DEFVAL       { 3 }
            ::= { hwXdslTR129LineConfProfEntry 26 }

        hwXdslTR129LineConfProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims.
                 Unit: dB
                "
            REFERENCE    "ITU-T G.997.1 (amendment 1), 7.3.1.1.9"
            DEFVAL       { 9 }
            ::= { hwXdslTR129LineConfProfEntry 27 }

        hwXdslTR129LineConfProfDpboEpsd  OBJECT-TYPE
            SYNTAX      HwXdslDpboEpsd
            MAX-ACCESS  read-create
            STATUS      current
            DESCRIPTION
                "This parameter defines the PSD mask that is assumed to be permitted at the exchange.
                 This parameter shall use the same format as PSDMASKds.The maximum number of breakpoints
                 for DPBOEPSD is 16.
                 This is a string of 16 pairs of values in the following
                 structure:
                 Octets 0+1 - Index of 1st sub-carrier used in the context
                              of a first breakpoint.
                 Octet 2    - The PSD reduction for the sub-carrier indicated in
                             octets 0 and 1.
                 Octets 3-5 - Same, for a 2nd breakpoint.
                 Octets 6-8 - Same, for a 3rd breakpoint.
                 This architecture continues until octets 45-47, which are
                 associated with a 16th breakpoint.
                 Each subcarrier index is an unsigned number in the range 1 and
                 NSCds.  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.
                "
            REFERENCE    "ITU-T G.997.1(200604), paragraph 7.3.1.2.13"
            ::= { hwXdslTR129LineConfProfEntry 28 }

        hwXdslTR129LineConfProfDpboEsel  OBJECT-TYPE
            SYNTAX      Unsigned32 (0..511)
            UNITS       "0.5dB"
            MAX-ACCESS  read-create
            STATUS      current
            DESCRIPTION
                "This configuration parameter defines the assumed electrical length of
                 cables (E-side cables) connecting exchange based DSL services to a remote
                 flexibility point (cabinet), that hosts the xTU-C that is subject to
                 spectrally shaped downstream power back-off depending on this length.
                 For this parameter the electrical length is defined as the loss (in dB)
                 of an equivalent length of hypothetical cable at a reference frequency
                 defined by the network operator or in spectrum management regulations.
                 DPBOESEL shall be coded as an unsigned integer representing an electrical
                 length from 0 dB (coded as 0) to 255.5 dB (coded as 511) in steps of 0.5 dB.
                 All values in the range are valid.If DPBOESEL is set to zero, the DPBO in
                 this section shall be disabled.
                 Unit: 0.5dB
                "
            REFERENCE    "ITU-T G.997.1(200604), paragraph 7.3.1.2.13"
            ::= { hwXdslTR129LineConfProfEntry 29 }

        hwXdslTR129LineConfProfDpboEscm  OBJECT-TYPE
            SYNTAX      HwXdslDpboEscm
            MAX-ACCESS  read-create
            STATUS      current
            DESCRIPTION
                "This configuration parameter defines a cable model in terms of three scalars
                 DPBOESCMA, DPBOESCMB and DPBOESCMC that shall be used to describe the frequency
                 dependent loss of E-side cables.Parameters DPBOESCMA, DPBOESCMB, DPBOESCMC shall be
                 coded as unsigned integers representing a scalar value from -1 (coded as 0) to 1.5
                 (coded as 640) in step of 1/256. All values in the range are valid.
                 Octets 0+1 DPBOESCMA
                 Octets 2+3 DPBOESCMB
                 Octets 4+5 DPBOESCMC
                "
            REFERENCE    "ITU-T G.997.1(200604), paragraph 7.3.1.2.13"
            ::= { hwXdslTR129LineConfProfEntry 30 }

        hwXdslTR129LineConfProfDpboMus  OBJECT-TYPE
            SYNTAX      Unsigned32 (0..255)
            UNITS       "-0.5dBm/Hz"
            MAX-ACCESS  read-create
            STATUS      current
            DESCRIPTION
                "DPBOMUS defines the assumed Minimum Usable receive Signal PSD (in dBm/Hz) for
                 exchange based services, used to modify parameter DPBOFMAX defined below. It
                 shall be coded as an unsigned integer representing a PSD level from 0 dBm/Hz
                 (coded as 0) to -127.5 dBm/Hz (coded as 255) in steps of 0.5 dBm/Hz.
                 All values in the range are valid.
                 Unit: -0.5dBm/Hz
                "
             REFERENCE    "ITU-T G.997.1(200604), paragraph 7.3.1.2.13"
            ::= { hwXdslTR129LineConfProfEntry 31 }

        hwXdslTR129LineConfProfDpboFmin  OBJECT-TYPE
            SYNTAX      Unsigned32 (0..2048)
            UNITS       "4.3125 KHz"
            MAX-ACCESS  read-create
            STATUS      current
            DESCRIPTION
                "DPBOFMIN defines the minimum frequency from which the DPBO shall be applied.
                 It shall be coded as a 16 bits unsigned integer representing a frequency in
                 multiple of 4.3125 KHz. The range of valid values is from 0 kHz (coded as 0)
                 to 8832 kHz (coded as 2048).
                 Unit: 4.3125 KHz
                "
            REFERENCE    "ITU-T G.997.1(200604), paragraph 7.3.1.2.13"
            ::= { hwXdslTR129LineConfProfEntry 32 }

        hwXdslTR129LineConfProfDpboFmax  OBJECT-TYPE
            SYNTAX      Unsigned32 (32..6956)
            UNITS       "4.3125 KHz"
            MAX-ACCESS  read-create
            STATUS      current
            DESCRIPTION
                "DPBOFMAX defines the maximum frequency at which DPBO may be applied. It shall be
                 coded as a 16 bits unsigned integer representing a frequency in multiple of 4.3125 KHz.
                 The range of valid values is from 138 kHz (coded as 32) to 29997.75 kHz (coded as 6956).
                 Unit: 4.3125 KHz
                "
            REFERENCE    "ITU-T G.997.1(200604), paragraph 7.3.1.2.13"
            ::= { hwXdslTR129LineConfProfEntry 33 }

        hwXdslTR129LineConfProfUpboPsdBand  OBJECT-TYPE
            SYNTAX      HwXdslUpboPsdBand
            MAX-ACCESS  read-create
            STATUS      current
            DESCRIPTION
                "This parameter defines the UPBO reference PSD used to compute the upstream power back-off
                 for each upstream band except US0. A UPBOPSD defined for each band shall consist of two
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps
                 of 0.01 dBm/Hz. The UPBO reference PSD at the frequency f expressed in MHz shall be equal
                 to '-a-b(SQRT(f))'. The set of parameter values a = 40 dBm/Hz, b = 0 dBm/Hz is a special configuration
                 to disable UPBO in the respective upstream band.
                 Octets 0+1 -   a[0]
                 Octets 2+3 -   b[0]
                 Octets 4+5 -   a[1]
                 Octets 6+7 -   b[1]
                 Octets 8+9 -   a[2]
                 Octets 10+11 - b[2]
                 Octets 12+13 - a[3]
                 Octets 14+15 - b[3]
                "
            REFERENCE    "ITU-T G.997.1(200604), paragraph 7.3.1.2.14"
            ::= { hwXdslTR129LineConfProfEntry 34 }

        hwXdslTR129LineConfProfUpboKl  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0)
                 to 128 dB (coded as 1280) in steps of 0.1 dB.
                 Unit: 0.1 dB
                "
            REFERENCE    "ITU-T G.997.1(200604), paragraph 7.3.1.2.14"
            ::= { hwXdslTR129LineConfProfEntry 35 }

        hwXdslTR129LineConfProfUpboKlf  OBJECT-TYPE
            SYNTAX      HwXdslUpboKlf
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                "
            REFERENCE    "ITU-T G.997.1(200604), paragraph 7.3.1.2.14"
            ::= { hwXdslTR129LineConfProfEntry 36 }

        hwXdslTR129LineConfProfRowStatus  OBJECT-TYPE
            SYNTAX      RowStatus
            MAX-ACCESS  read-create
            STATUS      current
            DESCRIPTION
                "This object is used to create a new row or to modify or
                 delete an existing row in this table.
                 A profile is activated by setting this object to 'active'.
                 When 'active' is set, the system will validate the profile.
                 Before a profile can be deleted or taken out of service
                 (by setting this object to 'destroy' or 'outOfService'),
                 it must be not referenced from all associated
                 templates.
                "
            ::= { hwXdslTR129LineConfProfEntry 37 }

        hwXdslTR129LineConfProfReferenceClock  OBJECT-TYPE
            SYNTAX      INTEGER
                   {
                         freeRun(1),
                         system(2)
                   }
            MAX-ACCESS  read-create
            STATUS      current
            DESCRIPTION
                "This object configures the clock reference for the ATU-C in a XDSL Line.
                 Options:
                 1. freeRun(1)  - network timing reference clock mode is freeRun
                 2. system(2)   - network timing reference clock mode is system
                "
            DEFVAL       { freeRun }
            ::= { hwXdslTR129LineConfProfEntry 38 }

        hwXdslTR129LineConfProfBitSwapDs  OBJECT-TYPE
            SYNTAX      HwXdslBitSwap
            MAX-ACCESS  read-create
            STATUS      current
            DESCRIPTION
                "Enables or disables the bit swap downstream of a line."
            DEFVAL       { enable }
            ::= { hwXdslTR129LineConfProfEntry 39 }

        hwXdslTR129LineConfProfBitSwapUs  OBJECT-TYPE
            SYNTAX      HwXdslBitSwap
            MAX-ACCESS  read-create
            STATUS      current
            DESCRIPTION
               "Enables or disables the bit swap upstream of a line."
            DEFVAL       { enable }
            ::= { hwXdslTR129LineConfProfEntry 40 }

        hwXdslTR129LineConfProfUpboBoostMode  OBJECT-TYPE
            SYNTAX      HwXdslUpboBoostMode
            MAX-ACCESS  read-create
            STATUS      current
            DESCRIPTION
              "Options:
               1. disable(1)  - The Equalized FEXT UPBO method is not supported
               2. enable(2)   - The Equalized FEXT UPBO method is supported
              "
            DEFVAL       { enable }
            ::= { hwXdslTR129LineConfProfEntry 41 }

        hwXdslTR129LineConfProfDpboEselMin  OBJECT-TYPE
            SYNTAX      Unsigned32 (0..511)
            UNITS       "0.5dB"
            MAX-ACCESS  read-create
            STATUS      current
            DESCRIPTION
                "DPBOESELMIN in dB is the minimum of all main cable losses for the KVz supplied when using
                 the SOL model (expansion of a KVz and XDSL provision of additional KVz areas from this KVz
                 using cross-cables to additional KVz), including the KVz at the MSAN site. This value must
                 be adjustable as the minimum requirement via the SNMP interface in the configuration profile
                 for each XDSL2 port, and is set individually for each MSAN site and usage. As an option,
                 As an option, adjustment can be done for each MSAN or line card, thus taking effect for
                 entire port groups. It is used only for determining the MUF.
                 Unit: 0.5 dB
                "
            ::= { hwXdslTR129LineConfProfEntry 42 }

        hwXdslTR129LineConfProfUpboKl0RefBand  OBJECT-TYPE
            SYNTAX      HwXdslUpboKl0RefBand
            MAX-ACCESS  read-create
            STATUS      current
            DESCRIPTION
                "This parameter defines the UPBO reference electrical length used to compute the
                 upstream power back-off for each upstream band except US0, for the optional Equalized FEXT UPBO
                 method. The value ranges from 1.8 to 63.5 dB in steps of 0.1 dB with special value 0.The special
                 value 0 indicates optional Equalized FEXT UPBO method is not supported.
                 Octets 0+1 - length[1]
                 Octets 2+3 - length[2]
                 Octets 4+5 - length[3]
                 Octets 6+7 - length[4]
                "

            ::= { hwXdslTR129LineConfProfEntry 43 }

        hwXdslTR129LineConfProfSosTimeDs  OBJECT-TYPE
            SYNTAX      Unsigned32 (0..255)
            UNITS       "64ms"
            MAX-ACCESS  read-create
            STATUS      current
            DESCRIPTION
                "The parameter is used in the specification of the receiver initiated SOS.
                 If the value of this parameter is not zero, the standard SOS triggering criteria are enabled,
                 and the value corresponds with duration of the time window used in the standard SOS triggering
                 criteria in the downstream direction.The special value zero, indicates that the standard SOS
                 triggering criteria are disabled. The valid range of non-zero values is from 64 ms to (255*64) ms
                 in steps of 64ms.
                 Unit: 64ms
                "
            REFERENCE    "ITU-T G.997.1(200811), paragraph 7.3.1.10.1"
            ::= { hwXdslTR129LineConfProfEntry 44 }

        hwXdslTR129LineConfProfSosTimeUs  OBJECT-TYPE
            SYNTAX      Unsigned32 (0..255)
            UNITS       "64ms"
            MAX-ACCESS  read-create
            STATUS      current
            DESCRIPTION
                "The parameter is used in the specification of the receiver initiated SOS.
                 If the value of this parameter is not zero, the standard SOS triggering criteria are enabled,
                 and the value corresponds with duration of the time window used in the standard SOS triggering
                 criteria in the upstream direction.The special value zero, indicates that the standard SOS
                 triggering criteria are disabled. The valid range of non-zero values is from 64 ms to (255*64) ms
                 in steps of 64ms.
                 Unit: 64ms
                "
            REFERENCE    "ITU-T G.997.1(200811), paragraph 7.3.1.10.2"
            ::= { hwXdslTR129LineConfProfEntry 45 }

        hwXdslTR129LineConfProfSosNtonesDs  OBJECT-TYPE
            SYNTAX      Unsigned32 (0..100)
            MAX-ACCESS  read-create
            STATUS      current
            DESCRIPTION
                "This parameter is defined as the minimum percentage of tones in the downstream MEDLEY SET
                 that must be degraded in order to arm the first sub-condition of the standard SOS triggering
                 criteria in the downstream direction. The parameter SOS-NTONES-ds is defined as a percentage of tones.
                 The valid range of values is from 1 to 100 in steps of 1. A special value of 0 indicates that this
                 parameter is not used in the decision criteria.
                "
            REFERENCE    "ITU-T G.997.1(200811), paragraph 7.3.1.10.3"
            ::= { hwXdslTR129LineConfProfEntry 46 }

        hwXdslTR129LineConfProfSosNtonesUs  OBJECT-TYPE
            SYNTAX      Unsigned32 (0..100)
            MAX-ACCESS  read-create
            STATUS      current
            DESCRIPTION
                "This parameter is defined as the minimum percentage of tones in the upstream MEDLEY SET
                 that must be degraded in order to arm the first sub-condition of the standard SOS triggering
                 criteria in the downstream direction. The parameter SOS-NTONES-ds is defined as a percentage of tones.
                 The valid range of values is from 1 to 100 in steps of 1. A special value of 0 indicates that this
                 parameter is not used in the decision criteria.
                "
            REFERENCE    "ITU-T G.997.1(200811), paragraph 7.3.1.10.4"
            ::= { hwXdslTR129LineConfProfEntry 47 }

        hwXdslTR129LineConfProfSosCrcDs  OBJECT-TYPE
            SYNTAX      Unsigned32 (1..65535)
            UNITS       "0.02"
            MAX-ACCESS  read-create
            STATUS      current
            DESCRIPTION
                "This parameter is defined as the minimum number of normalized CRC anomalies received in SOS-TIME-ds
                 seconds in order to arm the second sub-condition of the standard SOS triggering criteria  in the
                 downstream direction. The valid range of SOS-CRC values is 0.02 to 65535*0.02, in steps of 0.02.
                 Unit: 0.02
                "
            REFERENCE    "ITU-T G.997.1(200811), paragraph 7.3.1.10.5"
            ::= { hwXdslTR129LineConfProfEntry 48 }

        hwXdslTR129LineConfProfSosCrcUs  OBJECT-TYPE
            SYNTAX      Unsigned32 (1..65535)
            UNITS       "0.02"
            MAX-ACCESS  read-create
            STATUS      current
            DESCRIPTION
                "This parameter is defined as the minimum number of normalized CRC anomalies received in SOS-TIME-ds
                 seconds in order to arm the second sub-condition of the standard SOS triggering criteria  in the
                 upstream direction. The valid range of SOS-CRC values is 0.02 to 65535*0.02, in steps of 0.02.
                 Unit: 0.02
                "
           REFERENCE    "ITU-T G.997.1(200811), paragraph 7.3.1.10.6"
            ::= { hwXdslTR129LineConfProfEntry 49 }

        hwXdslTR129LineConfProfMaxSosDs  OBJECT-TYPE
            SYNTAX      Unsigned32 (0..15)
            MAX-ACCESS  read-create
            STATUS      current
            DESCRIPTION
                "This parameter is used in G.993.2 de-activation. If the number of successful SOS procedures in the
                 downstream direction performed within a 120-second interval exceeds MAX-SOS-ds, the modem shall transition
                 to the L3 state. The valid range of values is 1 to 15. A special value of 0 indicates that there is no
                 limit on the maximum allowed number of SOS recoveries within this time interval.
                "
            REFERENCE    "ITU-T G.997.1(200811), paragraph 7.3.1.10.7"
            ::= { hwXdslTR129LineConfProfEntry 50 }

        hwXdslTR129LineConfProfMaxSosUs  OBJECT-TYPE
            SYNTAX      Unsigned32 (0..15)
            MAX-ACCESS  read-create
            STATUS      current
            DESCRIPTION
                "This parameter is used in G.993.2 de-activation. If the number of successful SOS procedures in the
                 upstream direction performed within a 120-second interval exceeds MAX-SOS-ds, the modem shall transition
                 to the L3 state. The valid range of values is 1 to 15. A special value of 0 indicates that there is no
                 limit on the maximum allowed number of SOS recoveries within this time interval.
                "
            REFERENCE    "ITU-T G.997.1(200811), paragraph 7.3.1.10.8"
            ::= { hwXdslTR129LineConfProfEntry 51 }

        hwXdslTR129LineConfProfSnrmoffsetRocDs  OBJECT-TYPE
            SYNTAX      Unsigned32 (0..310)
            UNITS       "0.1dB"
            MAX-ACCESS  read-create
            STATUS      current
            DESCRIPTION
                "The parameter is defined as the SNR Margin offset for the ROC channel in the downstream direction.
                 The parameter is used in the specification of the Channel Initialization Policy (see 12.3.7.1/G.993.2).
                 The valid range of SNR margin offset values is from 0 to (310*0.1) dB with 0.1 dB steps.
                 Unit: 0.1dB
                "
            REFERENCE    "ITU-T G.997.1(200811), paragraph 7.3.1.10.9"
            ::= { hwXdslTR129LineConfProfEntry 52 }

        hwXdslTR129LineConfProfSnrmoffsetRocUs  OBJECT-TYPE
            SYNTAX      Unsigned32 (0..310)
            UNITS       "0.1dB"
            MAX-ACCESS  read-create
            STATUS      current
            DESCRIPTION
                "The parameter is defined as the SNR Margin offset for the ROC channel in the upstream direction.
                 The parameter is used in the specification of the Channel Initialization Policy (see 12.3.7.1/G.993.2).
                 The valid range of SNR margin offset values is from 0 to (310*0.1) dB with 0.1 dB steps.
                 Unit: 0.1dB
                "
            REFERENCE    "ITU-T G.997.1(200811), paragraph 7.3.1.10.10"
            ::= { hwXdslTR129LineConfProfEntry 53 }

        hwXdslTR129LineConfProfInpminRocDs  OBJECT-TYPE
            SYNTAX      Unsigned32 (0..16)
            MAX-ACCESS  read-create
            STATUS      current
            DESCRIPTION
                "This parameter contains the minimum impulse noise protection to apply on the ROC in the downstream direction.
                 The minimum impulse noise protection is an integer ranging from 0 to 16.
                "
            REFERENCE    "ITU-T G.997.1(200811), paragraph 7.3.1.10.11"
            ::= { hwXdslTR129LineConfProfEntry 54 }

        hwXdslTR129LineConfProfInpminRocUs  OBJECT-TYPE
            SYNTAX      Unsigned32 (0..16)
            MAX-ACCESS  read-create
            STATUS      current
            DESCRIPTION
                "This parameter contains the minimum impulse noise protection to apply on the robust ROC in the upstream direction.
                 The minimum impulse noise protection is an integer ranging from 0 to 16.
                "
            REFERENCE    "ITU-T G.997.1(200811), paragraph 7.3.1.10.12"
            ::= { hwXdslTR129LineConfProfEntry 55 }

        hwXdslTR129LineConfProfInmIatoDs  OBJECT-TYPE
            SYNTAX      Unsigned32(3..511)
            MAX-ACCESS  read-create
            STATUS      current
            DESCRIPTION
                "The parameter of downstream impulse noise monitoring inter arrival time offset.
                 This is the Inter Arrival Time Offset that the xTU receiver shall use to determine
                 in which bin of the Inter Arrival Time histogram the IAT is reported.
                 The valid values for INMIATO ranges from 3 to 511 DMT symbols in steps of 1 DMT symbol.
                "
            REFERENCE    "ITU-T G.997.1, paragraph 7.3.1.9.1"
            DEFVAL       { 3 }
            ::= { hwXdslTR129LineConfProfEntry 56 }

        hwXdslTR129LineConfProfInmIatsDs  OBJECT-TYPE
            SYNTAX      Unsigned32(0..7)
            MAX-ACCESS  read-create
            STATUS      current
            DESCRIPTION
                "The parameter of downstream impulse noise monitoring inter arrival time step.
                 This is the Inter Arrival Time Step that the xTU receiver shall use to determine
                 in which bin of the Inter Arrival Time histogram the IAT is reported.
                 The valid values for INMIATS ranges from 0 to 7 in steps of 1.
                "
            REFERENCE    "ITU-T G.997.1, paragraph 7.3.1.9.2"
            DEFVAL       { 0 }
            ::= { hwXdslTR129LineConfProfEntry 57 }

        hwXdslTR129LineConfProfInmCcDs  OBJECT-TYPE
            SYNTAX      Unsigned32(0..64)
            MAX-ACCESS  read-create
            STATUS      current
            DESCRIPTION
                "The parameter of Downstream impulse noise monitoring cluster continuation value.
                 This is the Cluster Continuation value that the xTU receiver shall use
                 in the cluster indication process described in the relevant ITU-T Recommendation.
                 The valid values for INMCC range from 0 to 64 DMT symbols in steps of 1 DMT symbol.
                "
            REFERENCE    "ITU-T G.997.1, paragraph 7.3.1.9.3"
            DEFVAL       { 0 }
            ::= { hwXdslTR129LineConfProfEntry 58 }

        hwXdslTR129LineConfProfInmInpeqModeDs  OBJECT-TYPE
            SYNTAX      Unsigned32(0..4)
            MAX-ACCESS  read-create
            STATUS      current
            DESCRIPTION
                "The parameter of Downstream impulse noise monitoring equivalent impulse noise protect mode.
                 This is the INM Equivalent INP Mode that the xTU receiver shall use in the computation of the Equivalent INP,
                 as defined in the relevant ITU-T Recommendation. The valid values for INM_INPEQ_MODE are 0, 1, 2, 3, and 4.
                "
            REFERENCE    "ITU-T G.997.1, paragraph 7.3.1.9.4"
            DEFVAL       { 0 }
            ::= { hwXdslTR129LineConfProfEntry 59 }

        hwXdslTR129LineConfProfInmIatoUs  OBJECT-TYPE
            SYNTAX      Unsigned32(3..511)
            MAX-ACCESS  read-create
            STATUS      current
            DESCRIPTION
                "The parameter of upstream impulse noise monitoring inter arrival time offset.
                 This is the Inter Arrival Time Offset that the xTU receiver shall use to determine
                 in which bin of the Inter Arrival Time histogram the IAT is reported.
                 The valid values for INMIATO ranges from 3 to 511 DMT symbols in steps of 1 DMT symbol.
                "
            REFERENCE    "ITU-T G.997.1, paragraph 7.3.1.9.1"
            DEFVAL       { 3 }
            ::= { hwXdslTR129LineConfProfEntry 60 }

        hwXdslTR129LineConfProfInmIatsUs  OBJECT-TYPE
            SYNTAX      Unsigned32(0..7)
            MAX-ACCESS  read-create
            STATUS      current
            DESCRIPTION
                "The parameter of upstream impulse noise monitoring inter arrival time step.
                 This is the Inter Arrival Time Step that the xTU receiver shall use to determine
                 in which bin of the Inter Arrival Time histogram the IAT is reported.
                 The valid values for INMIATS ranges from 0 to 7 in steps of 1.
                "
            REFERENCE    "ITU-T G.997.1, paragraph 7.3.1.9.2"
            DEFVAL       { 0 }
            ::= { hwXdslTR129LineConfProfEntry 61 }

        hwXdslTR129LineConfProfInmCcUs  OBJECT-TYPE
            SYNTAX      Unsigned32(0..64)
            MAX-ACCESS  read-create
            STATUS      current
            DESCRIPTION
                "The parameter of upstream impulse noise monitoring cluster continuation value.
                 This is the Cluster Continuation value that the xTU receiver shall use
                 in the cluster indication process described in the relevant ITU-T Recommendation.
                 The valid values for INMCC range from 0 to 64 DMT symbols in steps of 1 DMT symbol.
                "
            REFERENCE    "ITU-T G.997.1, paragraph 7.3.1.9.3"
            DEFVAL       { 0 }
            ::= { hwXdslTR129LineConfProfEntry 62 }

        hwXdslTR129LineConfProfInmInpeqModeUs  OBJECT-TYPE
            SYNTAX      Unsigned32(0..4)
            MAX-ACCESS  read-create
            STATUS      current
            DESCRIPTION
                "The parameter of upstream impulse noise monitoring equivalent impulse noise protect mode.
                 This is the INM Equivalent INP Mode that the xTU receiver shall use in the computation of the Equivalent INP,
                 as defined in the relevant ITU-T Recommendation. The valid values for INM_INPEQ_MODE are 0, 1, 2, 3, and 4.
                "
            REFERENCE    "ITU-T G.997.1, paragraph 7.3.1.9.4"
            DEFVAL       { 0 }
            ::= { hwXdslTR129LineConfProfEntry 63 }

        hwXdslTR129LineConfProfL3Time  OBJECT-TYPE
            SYNTAX      Unsigned32 (0..65535)
            UNITS       "seconds"
            MAX-ACCESS  read-create
            STATUS      current
            DESCRIPTION
                "This minimum time (in seconds) between an Entry into the
                 L3 state and the L0 or L2 state.
                 Unit: seconds
                "
            DEFVAL       { 255 }
            ::= { hwXdslTR129LineConfProfEntry 64 }
        hwXdslTR129LineConfProfRtxModeDs  OBJECT-TYPE
            SYNTAX      INTEGER
                        {
                         forbidden(0),
                         preferred(1),
                         forced(2),
                         testmode(3)
                        }
            MAX-ACCESS  read-create
            STATUS      current
            DESCRIPTION
                "The mode of operation of G.998.4 retransmission in downstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwXdslTR129LineConfProfEntry 65 }

        hwXdslTR129LineConfProfRtxModeUs  OBJECT-TYPE
            SYNTAX      INTEGER
                        {
                         forbidden(0),
                         preferred(1),
                         forced(2),
                         testmode(3)
                        }
            MAX-ACCESS  read-create
            STATUS      current
            DESCRIPTION
                "The mode of operation of G.998.4 retransmission in upstream direction.
                 Options:
                 1. forbidden(0)    - G.998.4 retransmission not allowed.
                 2. preferred(1)    - G.998.4 retransmission is preferred.
                 3. forced(2)       - Force the use of the G.998.4 retransmission.
                 4. testmode(3)     - Force the use of the G.998.4 retransmission in test mode.
                "
            REFERENCE    "ITU-T G.997.1, paragraph 7.3.1.11"
            DEFVAL       { forbidden }
            ::= { hwXdslTR129LineConfProfEntry 66 }

        hwXdslTR129LineConfProfLeftrThreshDs  OBJECT-TYPE
            SYNTAX      Unsigned32(0..99)
            UNITS       "0.01"
            MAX-ACCESS  read-create
            STATUS      current
            DESCRIPTION
                "If retransmission is used in downstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwXdslTR129LineConfProfEntry 67 }

        hwXdslTR129LineConfProfLeftrThreshUs  OBJECT-TYPE
            SYNTAX      Unsigned32(0..99)
            UNITS       "0.01"
            MAX-ACCESS  read-create
            STATUS      current
            DESCRIPTION
                "If retransmission is used in upstream direction, this parameter specifies the
                 threshold for declaring a near-end leftr defect. The value is coded as a fraction of the
                 NDR with valid range from 0.01 to 0.99 with increments of 0.01. A special value means the
                 ETR shall be used as the default threshold for declaring a leftr defect.
                "
            REFERENCE    "ITU-T G.997.1, paragraph 7.3.1.12"
            DEFVAL       { 0 }
            ::= { hwXdslTR129LineConfProfEntry 68 }

        hwXdslTR129LineConfProfForceInpDs  OBJECT-TYPE
            SYNTAX TruthValue
            MAX-ACCESS  read-create
            STATUS      current
            DESCRIPTION
                "This parameter indicates that the framer settings of the
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"
            DEFVAL       { false }
            ::= { hwXdslTR129LineConfProfEntry 69 }

        hwXdslTR129LineConfProfForceInpUs  OBJECT-TYPE
            SYNTAX TruthValue
            MAX-ACCESS  read-create
            STATUS      current
            DESCRIPTION
                "This parameter indicates that the framer settings of the
                 bearer shall be selected such that the impulse noise protection
                 computed according to the formula specified in the relevant
                 Recommendation is greater or equal to the minimal impulse noise
                 protection requirement.
                 This flag shall have the same value for all the bearers of one
                 line in the same direction.
                "
            REFERENCE    "ITU-T G.997.1, paragraph 7.3.2.5"
            DEFVAL       { false }
            ::= { hwXdslTR129LineConfProfEntry 70 }

        hwXdslTR129LineConfProfAeleMode  OBJECT-TYPE
            SYNTAX      Unsigned32(0..3)
            MAX-ACCESS  read-create
            STATUS      current
            DESCRIPTION
                "This parameter defines the UPBO electrical length estimation mode to be used
                 in the Alternative Electrical Length Estimation method (ELE-M1) in 7.2.1.3.2.2/G.993.2.
                 The value of this parameter is 0, 1, 2 or 3.
                 0-ELE_M0, 1-ELE_DS, 2-ELE_PB, 3-ELE_MIN
                "
            REFERENCE    "ITU-T G.997.1, paragraph 7.3.1.2.14"
            DEFVAL       { 0 }
            ::= { hwXdslTR129LineConfProfEntry 71 }

        hwXdslTR129LineConfProfUpboElmt  OBJECT-TYPE
            SYNTAX      Unsigned32(0..15)
            MAX-ACCESS  read-create
            STATUS      current
            DESCRIPTION
                "This parameter defines the UPBO electrical length minimum threshold percentile
                 in percent used in the Alternative Electrical Length Estimation method (ELE-M1)
                 in clause 7.2.1.3.2.2/G.993.2.  It is set by network management via the CO-MIB.
                 The parameter ranges from 0 to 15 percent in steps of 1 percent.
                 This value is communicated to the VTU-R via G.994.1 at start-up.
                "
            REFERENCE    "ITU-T G.997.1, paragraph 7.3.1.2.14"
            DEFVAL       { 10 }
            ::= { hwXdslTR129LineConfProfEntry 72 }

        hwXdslTR129LineConfProfUpboKlAuto  OBJECT-TYPE
            SYNTAX      Unsigned32(1..4 | 4294967295)
            MAX-ACCESS  read-create
            STATUS      current
            DESCRIPTION
                "This parameter defines the mode in which kl0 is computed when hwXdslTR129LineConfProfUpboKlf is auto.
                 Options:
                 1--max(kl0_CO,kl0_CPE)
                 2--min(kl0_CO,kl0_CPE)
                 3--kl0_CO
                 4--kl0_CPE
                 4294967295--Invalid value
                "
            DEFVAL       { 1 }
            ::= { hwXdslTR129LineConfProfEntry 73 }

        hwXdslTR129LineConfProfGfastProfiles  OBJECT-TYPE
            SYNTAX HWVOPGfastProfiles
            MAX-ACCESS read-create
            STATUS current
            DESCRIPTION
                "The configuration parameter contains the G.fast profiles to
                 be allowed by the near-end xTU on this line.
                 It is coded in a bitmap representation (0 if not allowed, 1 if allowed).
                 Bit representation:
                 0  G.fast profile 106
                 1  G.fast profile 212
                 Default value: All profiles allowed.
                "
            REFERENCE
                "ITU-T G.9701, paragraph 6"
            ::= { hwXdslTR129LineConfProfEntry 74 }

        hwXdslTR129LineConfProfGfastLineLowFreqEdgeValueDs  OBJECT-TYPE
            SYNTAX Gauge32 (43..1023)
            MAX-ACCESS read-create
            STATUS current
            DESCRIPTION
                "Low-frequency Edge Stop-band Mask(LESM).
                 If a LESM is used, the LESM shall be specified with breakpoints.
                 These breakpoints are specified starting from ftr1, which is the start of the in-band PSD mask, as specified in [ITU-T G.9700].
                 This is not to be confused with ftr3,  which is the start of the in-band part of the LESM.
                "
            REFERENCE
                "ITU-T G.9701, paragraph 7.3.1.1.1"
            DEFVAL { 43 }
            ::= { hwXdslTR129LineConfProfEntry 75 }

        hwXdslTR129LineConfProfGfastCarMaskDs  OBJECT-TYPE
            SYNTAX Xdsl2CarMask
            MAX-ACCESS read-create
            STATUS current
            DESCRIPTION
                "G.fast specific subcarriers mask.
                 This configuration parameter defines the restrictions, additional to the band plan, to determine
                 the set of subcarriers allowed for transmission in downstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwXdslTR129LineConfProfEntry 76 }

        hwXdslTR129LineConfProfGfastUpboKL  OBJECT-TYPE
            SYNTAX Gauge32 (0..1280)
            UNITS "0.1 dB"
            MAX-ACCESS read-create
            STATUS current
            DESCRIPTION
                "This configuration parameter defines the G.fast electrical length expressed in dB at 1MHz, kl0,
                 configured by the DPU-MIB.The value ranges from 0 (coded as 0) to 128 dB (coded as 1280) in steps of 0.1 dB.
                 This parameter is relevant only if hwXdslTR129LineConfProfGfastUpboKLF is set to override(2),
                 which indicates that this parameter's value will override the XTUs' determination of the electrical length.
                 If hwXdslTR129LineConfProfGfastUpboKLF is set either to auto(1) or disableUpbo(3), then this parameter will be ignored.
                 Unit: 0.1 dB.
                "
            REFERENCE
                "ITU-T G.9701, paragraph 7.3.1.4.2.1"
            DEFVAL { 0 }
            ::= { hwXdslTR129LineConfProfEntry 77 }

        hwXdslTR129LineConfProfGfastUpboKLF  OBJECT-TYPE
            SYNTAX Xdsl2UpboKLF
            MAX-ACCESS read-create
            STATUS current
            DESCRIPTION
                "Defines the G.fast upstream power backoff force mode."
            REFERENCE
                "ITU-T G.9701, paragraph 7.3.1.4.2.1"
            DEFVAL { disableUpbo }
            ::= { hwXdslTR129LineConfProfEntry 78 }

        hwXdslTR129LineConfProfGfastKlAuto  OBJECT-TYPE
          SYNTAX      Unsigned32(1..4)
          MAX-ACCESS  read-create
          STATUS      current
          DESCRIPTION
            "This parameter defines the mode in which kl0 is computed when hwXdslTR129LineConfProfGfastUpboKLF is auto.
             Options:
             1--max(kl0_CO,kl0_CPE)
             2--min(kl0_CO,kl0_CPE)
             3--kl0_CO
             4--kl0_CPE
            "
          DEFVAL       { 3 }
            ::= { hwXdslTR129LineConfProfEntry 79 }

        hwXdslTR129LineConfProfGfastUpboKLREF  OBJECT-TYPE
            SYNTAX Integer32 (0 | 18..635)
            UNITS "0.1 dB"
            MAX-ACCESS read-create
            STATUS current
            DESCRIPTION
                "This parameter defines the UPBO reference electrical length used to compute the upstream
                 power back-off, for the optional Equalized FEXT UPBO method.
                 The value ranges from 1.8 to 63.5 dB in steps of 0.1 dB with special value 0.
                 Unit: 0.1 dB.
                "
            REFERENCE
                "ITU-T G.9701, paragraph 7.3.1.4.2.2"
            DEFVAL { 0 }
            ::= { hwXdslTR129LineConfProfEntry 80 }

        hwXdslTR129LineConfProfGfastUpboPsdA  OBJECT-TYPE
            SYNTAX Integer32 (4000..8095)
            UNITS "0.01 dBm/Hz"
            MAX-ACCESS read-create
            STATUS current
            DESCRIPTION
                "This configuration parameter defines the 'a' reference parameter of the UPBO reference PSD
                 used to compute the upstream power back-off.A UPBOPSD shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwXdslTR129LineConfProfGfastUpboPsdA to 4000 and hwXdslTR129LineConfProfGfastUpboPsdB to 0 is a special
                 configuration to disable UPBO.
                 Unit: 0.01 dBm/Hz.
                "
            REFERENCE
                "ITU-T G.9701, paragraph 7.3.1.4"
            DEFVAL { 5650 }
            ::= { hwXdslTR129LineConfProfEntry 81 }

        hwXdslTR129LineConfProfGfastUpboPsdB  OBJECT-TYPE
            SYNTAX Integer32 (0..4095)
            UNITS "0.01 dBm/Hz"
            MAX-ACCESS read-create
            STATUS current
            DESCRIPTION
                "This configuration parameter defines the 'b' reference parameter of the UPBO reference PSD
                 used to compute the upstream power back-off.A UPBOPSD shall consist of two parameters [a, b].
                 Parameter 'a' ranges from 40 dBm/Hz (coded as 4000) to 80.95 dBm/Hz (coded as 8095) in steps of 0.01 dBm/Hz;
                 and parameter 'b' ranges from 0 dBm/Hz (coded as 0) to 40.95 dBm/Hz (coded as 4095) in steps of 0.01 dBm/Hz.
                 The UPBO reference PSD at the frequency 'f' expressed in MHz shall be equal to '-a-b(SQRT(f))'.
                 Setting hwVOPGfastUPBOConfProfPsdA to 4000 and hwVOPGfastUPBOConfProfPsdB to 0 is a special
                 configuration to disable UPBO.
                 Unit: 0.01 dBm/Hz.
                "
            REFERENCE
                "ITU-T G.9701, paragraph 7.3.1.4"
            DEFVAL { 1020 }
            ::= { hwXdslTR129LineConfProfEntry 82 }

        hwXdslTR129LineConfProfGfastRfiBands  OBJECT-TYPE
            SYNTAX Xdsl2RfiBands
            MAX-ACCESS read-create
            STATUS current
            DESCRIPTION
                "This configuration parameter defines the bands where the PSD shall be reduced as specified in ITU-T G.9701 #7.3.1.2.
                 Each band shall be represented by a start and stop subcarrier indices with a subcarrier spacing of 51.75 kHz.
                 Up to 16 bands may be specified.
                 This parameter defines the RFI bands for both upstream and downstream directions.
                 Default value: No RFI bands.
                "
            REFERENCE
                "ITU-T G.9701, paragraph 7.3.1.2 and 12.3.2.1.1"
            ::= { hwXdslTR129LineConfProfEntry 83 }

        hwXdslTR129LineConfProfGfastIarBands  OBJECT-TYPE
            SYNTAX HWVOPGfastIarBands
            MAX-ACCESS read-create
            STATUS current
            DESCRIPTION
                "Defines for each International Amateur Radio (IAR) band whether transmit PSD reduction is enabled or disabled in that band.
                 It is represented as a bitmap (0 if not allowed and 1 if allowed)with the following definitions.
                 Bit representation:
                 0 International amateur radio band 1800 2000 kHz
                 1 International amateur radio band 3500 4000 kHz
                 2 International amateur radio band 7000 7300 kHz
                 3 International amateur radio band 10100 10150 kHz
                 4 International amateur radio band 14000 14350 kHz
                 5 International amateur radio band 18068 18168 kHz
                 6 International amateur radio band 21000 21450 kHz
                 7 International amateur radio band 24890 24990 kHz
                 8 International amateur radio band 28000 29700 kHz
                 9 International amateur radio band 50000 54000 kHz
                 10 International amateur radio band 70000 70500 kHz
                 11 International amateur radio band 144000 148000 kHz
                 Default value: All IAR bands disabled (no PSD reduction).
                "
            REFERENCE
                "ITU-T G.9701, paragraph 7.3.1.2 and 12.3.2.1.1, G.994.1 Table 11.70.8 and 11.70.8.1"
            ::= { hwXdslTR129LineConfProfEntry 84 }

        hwXdslTR129LineConfProfGfastMinSnrmDs  OBJECT-TYPE
            SYNTAX Gauge32 (0..310)
            UNITS "0.1 dB"
            MAX-ACCESS read-create
            STATUS current
            DESCRIPTION
                "The G.fast minimum Noise Margin the xTU-R receiver shall tolerate.
                 If the noise margin falls below this level, the xTU-R shall request that the xTU-C increase
                 the xTU-C transmit power.
                 If an increase of xTU-C transmit power is not possible, a loss-of-margin (LOM) defect occurs,
                 the xTU-R shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.9701, paragraph 12.3.4.2.1"
            DEFVAL { 0 }
            ::= { hwXdslTR129LineConfProfEntry 85 }

        hwXdslTR129LineConfProfGfastMinSnrmUs  OBJECT-TYPE
            SYNTAX Gauge32 (0..310)
            UNITS "0.1 dB"
            MAX-ACCESS read-create
            STATUS current
            DESCRIPTION
                "The G.fast minimum Noise Margin the xTU-C receiver shall tolerate.
                 If the noise margin falls below this level, the xTU-C shall request that the xTU-R increase
                 the xTU-R transmit power.
                 If an increase of xTU-R transmit power is not possible, a loss-of-margin (LOM) defect occurs,
                 the xTU-C shall fail and attempt to re-initialize and the NMS shall be notified.
                 The minimum noise margin ranges from 0 to 310 units of 0.1 dB (Physical values are 0 to 31 dB).
                 A value of 0 means that there is no minimum.
                 Unit: 0.1 dB.
                "
            REFERENCE
                "ITU-T G.9701, paragraph 12.3.4.2.1"
            DEFVAL { 0 }
            ::= { hwXdslTR129LineConfProfEntry 86 }

        hwXdslTR129LineConfProfGfastTargetSnrmDs  OBJECT-TYPE
            SYNTAX Gauge32 (0..310)
            UNITS "0.1 dB"
            MAX-ACCESS read-create
            STATUS current
            DESCRIPTION
                "The G.fast minimum Noise Margin the xTU-R receiver shall achieve, relative to the BER requirement,
                 to successfully complete initialization.
                 The target noise margin ranges from 0 to 310 units of 0.1 dB (Physical values are 0 to 31 dB).
                 Unit: 0.1 dB.
                "
            REFERENCE
                "ITU-T G.9701, paragraph 12.3.3.2.1"
            DEFVAL { 90 }
            ::= { hwXdslTR129LineConfProfEntry 87 }

        hwXdslTR129LineConfProfGfastTargetSnrmUs  OBJECT-TYPE
            SYNTAX Gauge32 (0..310)
            UNITS "0.1 dB"
            MAX-ACCESS read-create
            STATUS current
            DESCRIPTION
                "The G.fast minimum Noise Margin the xTU-C receiver shall achieve, relative to the BER requirement,
                 to successfully complete initialization.
                 The target noise margin ranges from 0 to 310 units of 0.1 dB (Physical values are 0 to 31 dB).
                 Unit: 0.1 dB.
                "
            REFERENCE
                "ITU-T G.9701, paragraph 12.3.3.2.1"
            DEFVAL { 90 }
            ::= { hwXdslTR129LineConfProfEntry 88 }

        hwXdslTR129LineConfProfGfastMaxSnrmDs  OBJECT-TYPE
            SYNTAX Gauge32 (0..310 | 2147483647)
            UNITS "0.1 dB"
            MAX-ACCESS read-create
            STATUS current
            DESCRIPTION
                "The G.fast maximum Noise Margin the xTU-R receiver shall try to sustain.
                 If the Noise Margin is above this level, the xTU-R shall request that the xTU-C reduce
                 the xTU-C transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.9701, paragraph 12.3.7"
            DEFVAL { 310 }
            ::= { hwXdslTR129LineConfProfEntry 89 }

        hwXdslTR129LineConfProfGfastMaxSnrmUs  OBJECT-TYPE
            SYNTAX Gauge32 (0..310 | 2147483647)
            UNITS "0.1 dB"
            MAX-ACCESS read-create
            STATUS current
            DESCRIPTION
                "The G.fast maximum Noise Margin the xTU-C receiver shall try to sustain.
                 If the Noise Margin is above this level, the xTU-C shall request that the xTU-R reduce
                 the xTU-R transmit power to get a noise margin below this limit (if this functionality is supported).
                 The maximum noise margin ranges from 0 to 310 units of 0.1 dB (Physical values are 0 to 31 dB).
                 A value of 0x7FFFFFFF (2147483647) means that there is no maximum.
                 Unit: 0.1 dB.
                "
            REFERENCE
                "ITU-T G.9701, paragraph 12.3.7"
            DEFVAL { 310 }
            ::= { hwXdslTR129LineConfProfEntry 90 }

        hwXdslTR129LineConfProfGfastRaUsNrmDs  OBJECT-TYPE
            SYNTAX Gauge32 (0..310)
            UNITS "0.1 dB"
            MAX-ACCESS read-create
            STATUS current
            DESCRIPTION
                "The G.fast Downstream Up-Shift Noise Margin value.
                 If the downstream noise margin is above this value, and stays above it for more than the time specified by the
                 hwXdslTR129LineConfProfGfastUsTimeDs, the xTU-R shall attempt to increase the Downstream net data rate.
                 The Downstream Up-Shift Noise Margin ranges from 0 to 310 units of 0.1 dB (Physical values are 0 to 31 dB).
                 Unit: 0.1 dB.
                "
            REFERENCE
                "ITU-T G.9701, paragraph 12.3.4.2.1"
            DEFVAL { 120 }
            ::= { hwXdslTR129LineConfProfEntry 91 }

        hwXdslTR129LineConfProfGfastRaUsNrmUs  OBJECT-TYPE
            SYNTAX Gauge32 (0..310)
            UNITS "0.1 dB"
            MAX-ACCESS read-create
            STATUS current
            DESCRIPTION
                "The G.fast Upstream Up-Shift Noise Margin value.
                 If the upstream noise margin is above this value, and stays above it for more than the time specified by the
                 hwXdslTR129LineConfProfGfastUsTimeUs, the xTU-C shall attempt to increase the Upstream net data rate.
                 The Upstream Up-Shift Noise Margin ranges from 0 to 310 units of 0.1 dB (Physical values are 0 to 31 dB).
                 Unit: 0.1 dB.
                "
            REFERENCE
                "ITU-T G.9701, paragraph 12.3.4.2.1"
            DEFVAL { 120 }
            ::= { hwXdslTR129LineConfProfEntry 92 }

        hwXdslTR129LineConfProfGfastRaDsNrmDs  OBJECT-TYPE
            SYNTAX Gauge32 (0..310)
            UNITS "0.1 dB"
            MAX-ACCESS read-create
            STATUS current
            DESCRIPTION
                "The G.fast Downstream Down-Shift Noise Margin value, to be used when hwXdslTR129LineConfProfGfastRaModeDs is set to dynamicRa.
                 If the downstream noise margin is below this value, and stays below it for more than the time specified by the
                 hwXdslTR129LineConfProfGfastDsTimeDs, the xTU-R shall attempt to increase the Downstream net data rate.
                 The Downstream Down-Shift Noise Margin ranges from 0 to 310 units of 0.1 dB (Physical values are 0 to 31 dB).
                 Unit: 0.1 dB.
                "
            REFERENCE
                "ITU-T G.9701, paragraph 12.3.4.2.1"
            DEFVAL { 60 }
            ::= { hwXdslTR129LineConfProfEntry 93 }

        hwXdslTR129LineConfProfGfastRaDsNrmUs  OBJECT-TYPE
            SYNTAX Gauge32 (0..310)
            UNITS "0.1 dB"
            MAX-ACCESS read-create
            STATUS current
            DESCRIPTION
                "The G.fast Upstream Down-shift Noise Margin value.
                 If the upstream noise margin is below this value, and stays below it for more than the time specified by the
                 hwXdslTR129LineConfProfGfastDsTimeUs, the xTU-C shall attempt to increase the Upstream net data rate.
                 The Upstream Down-Shift Noise Margin ranges from 0 to 310 units of 0.1 dB (Physical values are 0 to 31 dB).
                 Unit: 0.1 dB.
                "
            REFERENCE
                "ITU-T G.997.1, paragraph #7.3.1.4.8 (RA-DSNRMus)"
            DEFVAL { 60 }
            ::= { hwXdslTR129LineConfProfEntry 94 }

        hwXdslTR129LineConfProfGfastUsTimeDs  OBJECT-TYPE
            SYNTAX Gauge32 (0..16383)
            UNITS "seconds"
            MAX-ACCESS read-create
            STATUS current
            DESCRIPTION
                "The G.fast Downstream Up-Shift Time Interval, to be used when hwXdslTR129LineConfProfGfastRaModeDs is set to dynamicRa.
                 The interval of time that the downstream noise margin should stay above the Downstream Up-Shift Noise Margin
                 before the xTU-R shall attempt to increase the downstream net data rate.
                 The time interval ranges from 0 to 16383 seconds.
                 Unit: seconds.
                "
            REFERENCE
                "ITU-T G.9701, paragraph 12.3.4.2.1."
            DEFVAL { 8 }
            ::= { hwXdslTR129LineConfProfEntry 95 }

        hwXdslTR129LineConfProfGfastUsTimeUs  OBJECT-TYPE
            SYNTAX Gauge32 (0..16383)
            UNITS "seconds"
            MAX-ACCESS read-create
            STATUS current
            DESCRIPTION
                "The G.fast Upstream Up-Shift Time Interval.
                 The interval of time the upstream noise margin should stay above the Upstream Up-Shift Noise Margin
                 before the xTU-C shall attempt to increase the upstream net data rate.
                 The time interval ranges from 0 to 16383 seconds.
                 Unit: seconds.
                "
            REFERENCE
                "ITU-T G.9701, paragraph 12.3.4.2.1."
            DEFVAL { 8 }
            ::= { hwXdslTR129LineConfProfEntry 96 }

        hwXdslTR129LineConfProfGfastDsTimeDs  OBJECT-TYPE
            SYNTAX Gauge32 (0..16383)
            UNITS "seconds"
            MAX-ACCESS read-create
            STATUS current
            DESCRIPTION
                "The G.fast Downstream Down-shift Time Interval, to be used when hwXdslTR129LineConfProfGfastRaModeDs is set to dynamicRa.
                 The interval of time the downstream noise margin should stay below the Downstream Down-Shift Noise Margin
                 before the xTU-R shall attempt to decrease the downstream net data rate.
                 The time interval ranges from 0 to 16383 seconds.
                 Unit: seconds.
                "
            REFERENCE
                "ITU-T G.9701, paragraph 12.3.4.2.1."
            DEFVAL { 2}
            ::= { hwXdslTR129LineConfProfEntry 97 }

        hwXdslTR129LineConfProfGfastDsTimeUs  OBJECT-TYPE
            SYNTAX Gauge32 (0..16383)
            UNITS "seconds"
            MAX-ACCESS read-create
            STATUS current
            DESCRIPTION
                "The Upstream Down-shift Time Interval.
                 The interval of time the upstream noise margin should stay below the Upstream Down-shift Noise Margin
                 before the xTU-C shall attempt to decrease the upstream net data rate.
                 The time interval ranges from 0 to 16383 seconds.
                 Unit: seconds.
                "
            REFERENCE
                "ITU-T G.9701, paragraph 12.3.4.2.1."
            DEFVAL { 2 }
            ::= { hwXdslTR129LineConfProfEntry 98 }

        hwXdslTR129LineConfProfGfastSosFraTimeDs  OBJECT-TYPE
            SYNTAX      Unsigned32 (0..12)
            UNITS       "1 logical frame length"
            MAX-ACCESS  read-create
            STATUS      current
            DESCRIPTION
                "The parameter is used in the specification of the receiver initiated FRA.
                 If the value of this parameter is not zero, the standard FRA triggering criteria are enabled,
                 and the value corresponds with duration of the time window used in the standard FRA triggering
                 criteria in the downstream direction.The special value zero, indicates that the standard FRA
                 triggering criteria are disabled. The valid range of non-zero values is from 1 to 12
                 in steps of 1 logical frame length.
                 Unit: 1 logical frame length
                "
            REFERENCE    "ITU-T G.9701, paragraph 13.3.1.1.1.1"
            DEFVAL { 8 }
            ::= { hwXdslTR129LineConfProfEntry 99 }

        hwXdslTR129LineConfProfGfastSosFraTimeUs  OBJECT-TYPE
            SYNTAX      Unsigned32 (0..12)
            UNITS       "1 logical frame length"
            MAX-ACCESS  read-create
            STATUS      current
            DESCRIPTION
                "The parameter is used in the specification of the receiver initiated FRA.
                 If the value of this parameter is not zero, the standard FRA triggering criteria are enabled,
                 and the value corresponds with duration of the time window used in the standard FRA triggering
                 criteria in the upstream direction.The special value zero, indicates that the standard FRA
                 triggering criteria are disabled. The valid range of non-zero values is from 1 to 12
                 in steps of 1 logical frame length.
                 Unit: 1 logical frame length
                "
            REFERENCE    "ITU-T G.9701, paragraph 13.3.1.1.1.1"
            DEFVAL { 8 }
            ::= { hwXdslTR129LineConfProfEntry 100 }

        hwXdslTR129LineConfProfGfastSosFraNtonesDs  OBJECT-TYPE
            SYNTAX      Unsigned32 (0..100)
            MAX-ACCESS  read-create
            STATUS      current
            DESCRIPTION
                "This parameter is defined as the minimum percentage of tones that must be degraded in order to arm
                 the first sub-condition of the standard FRA triggering criteria in the downstream direction.
                 The parameter FRA-NTONES-ds is defined as a percentage of tones.
                 The valid range of values is from 1 to 100 in steps of 1. A special value of 0 indicates that this
                 parameter is not used in the decision criteria.
                "
            REFERENCE    "ITU-T G.9701, paragraph 13.3.1.1.1.2"
            DEFVAL { 50 }
            ::= { hwXdslTR129LineConfProfEntry 101 }

        hwXdslTR129LineConfProfGfastSosFraNtonesUs  OBJECT-TYPE
            SYNTAX      Unsigned32 (0..100)
            MAX-ACCESS  read-create
            STATUS      current
            DESCRIPTION
                "This parameter is defined as the minimum percentage of tones that must be degraded in order to arm
                 the first sub-condition of the standard FRA triggering criteria in the upstream direction.
                 The parameter FRA-NTONES-us is defined as a percentage of tones.
                 The valid range of values is from 1 to 100 in steps of 1. A special value of 0 indicates that this
                 parameter is not used in the decision criteria.
                "
            REFERENCE    "ITU-T G.9701, paragraph 13.3.1.1.1.2"
            DEFVAL { 50 }
            ::= { hwXdslTR129LineConfProfEntry 102 }

        hwXdslTR129LineConfProfGfastSosFraMinRtxUcDs  OBJECT-TYPE
            SYNTAX      Unsigned32 (0..1023)
            MAX-ACCESS  read-create
            STATUS      current
            DESCRIPTION
                "This parameter is defined as minimum number of rtx-uc anomalies received throughout a time window
                 equal to FRA-TIME-ds in order to arm the second FRA triggering criteria in the downstream direction.
                 The special value 0 indicates that monitoring of the number of rtx-uc anomalies is disabled.
                "
            REFERENCE    "ITU-T G.9701, paragraph 13.3.1.1.1.3"
            DEFVAL { 150 }
            ::= { hwXdslTR129LineConfProfEntry 103 }

        hwXdslTR129LineConfProfGfastSosFraMinRtxUcUs  OBJECT-TYPE
            SYNTAX      Unsigned32 (0..1023)
            MAX-ACCESS  read-create
            STATUS      current
            DESCRIPTION
                "This parameter is defined as the minimum number of rtx-uc anomalies received throughout a time window
                 equal to FRA-TIME-us in order to arm the second FRA triggering criteria in the upstream direction.
                 The special value 0 indicates that monitoring of the number of rtx-uc anomalies is disabled.
                "
           REFERENCE    "ITU-T G.9701, paragraph 13.3.1.1.1.3"
           DEFVAL { 150 }
            ::= { hwXdslTR129LineConfProfEntry 104 }

         hwXdslTR129LineConfProfGfastCarMaskUs  OBJECT-TYPE
            SYNTAX Xdsl2CarMask
            MAX-ACCESS read-create
            STATUS current
            DESCRIPTION
                "G.fast specific subcarriers mask.
                 This configuration parameter defines the restrictions, additional to the band plan, to determine
                 the set of subcarriers allowed for transmission in upstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwXdslTR129LineConfProfEntry 105 }

          hwXdslTR129LineConfProfGfastTargetSnrmRmcDs OBJECT-TYPE
            SYNTAX Gauge32 (0..310)
            UNITS "0.1 dB"
            MAX-ACCESS read-create
            STATUS current
            DESCRIPTION
                "Defines the downstream RMC noise margin that the FTU-R receiver shall achieve,
                 relative to the BER requirement, or better, to successfully complete initialization.
                 The target noise margin ranges from 0 to 310 units of 0.1 dB (Physical values are 0 to 31 dB).
                 Unit: 0.1 dB.
                "
            REFERENCE
                "ITU-T G.997.2, paragraph 7.1.6.1"
            DEFVAL { 90 }
            ::= { hwXdslTR129LineConfProfEntry 106 }

          hwXdslTR129LineConfProfGfastTargetSnrmRmcUs OBJECT-TYPE
            SYNTAX Gauge32 (0..310)
            UNITS "0.1 dB"
            MAX-ACCESS read-create
            STATUS current
            DESCRIPTION
                "Defines the upstream RMC noise margin that the FTU-O receiver shall achieve,
                 relative to the BER requirement, or better, to successfully complete initialization.
                 The target noise margin ranges from 0 to 310 units of 0.1 dB (Physical values are 0 to 31 dB).
                 Unit: 0.1 dB.
                "
            REFERENCE
                "ITU-T G.997.2, paragraph 7.1.6.2"
            DEFVAL { 90 }
            ::= { hwXdslTR129LineConfProfEntry 107 }

          hwXdslTR129LineConfProfGfastMinSnrmRmcDs OBJECT-TYPE
            SYNTAX Gauge32 (0..310)
            UNITS "0.1 dB"
            MAX-ACCESS read-create
            STATUS current
            DESCRIPTION
                "Defines the downstream minimum noise margin the FTU-R receiver tolerates for the RMC.
                 If the downstream RMC noise margin falls below this level, the FTU-R initiates the RPA procedure.
                 The minimum noise margin ranges from 0 to 310 units of 0.1 dB (Physical values are 0 to 31 dB).
                 A value of 0 means that there is no minimum.
                 Unit: 0.1 dB.
                "
            REFERENCE
                "ITU-T G.997.2, paragraph 7.1.6.3"
            DEFVAL { 0 }
            ::= { hwXdslTR129LineConfProfEntry 108 }

          hwXdslTR129LineConfProfGfastMinSnrmRmcUs OBJECT-TYPE
            SYNTAX Gauge32 (0..310)
            UNITS "0.1 dB"
            MAX-ACCESS read-create
            STATUS current
            DESCRIPTION
                "Defines the upstream minimum noise margin the FTU-O receiver tolerates for the RMC.
                 If the upstream RMC noise margin falls below this level, the FTU-O initiates the RPA procedure.
                 The minimum noise margin ranges from 0 to 310 units of 0.1 dB (Physical values are 0 to 31 dB).
                 A value of 0 means that there is no minimum.
                 Unit: 0.1 dB.
                "
            REFERENCE
                "ITU-T G.997.2, paragraph 7.1.6.4"
            DEFVAL { 0 }
            ::= { hwXdslTR129LineConfProfEntry 109 }

          hwXdslTR129LineConfProfGfastMaxBLRmcDs OBJECT-TYPE
            SYNTAX Gauge32 (2..6)
            MAX-ACCESS read-create
            STATUS current
            DESCRIPTION
                "Defines the maximum allowed bit-loading for the downstream RMC sub-carriers.
                "
            REFERENCE
                "ITU-T G.997.2, paragraph 7.1.6.5"
            DEFVAL { 6 }
            ::= { hwXdslTR129LineConfProfEntry 110 }

          hwXdslTR129LineConfProfGfastMaxBLRmcUs OBJECT-TYPE
            SYNTAX Gauge32 (2..6)
            MAX-ACCESS read-create
            STATUS current
            DESCRIPTION
                "Defines the maximum allowed bit-loading for the upstream RMC sub-carriers.
                "
            REFERENCE
                "ITU-T G.997.2, paragraph 7.1.6.6"
            DEFVAL { 6 }
            ::= { hwXdslTR129LineConfProfEntry 111 }

          hwXdslTR129LineConfProfGfastSosFraVenDiscDs  OBJECT-TYPE
            SYNTAX INTEGER
            {
                disable(1),
                enable(2)
            }
            MAX-ACCESS  read-create
            STATUS      current
            DESCRIPTION
                "Enable or disable vendor discretionary FRA triggering criteria in the downstream direction.
                 Options:
                 1. disable (1)  - Disable vendor discretionary FRA triggering criteria in the downstream direction.
                 2. enable (2)   - Enable vendor discretionary FRA triggering criteria in the downstream direction.
                "
           DEFVAL { disable }
            ::= { hwXdslTR129LineConfProfEntry 112 }

         hwXdslTR129LineConfProfGfastSosFraVenDiscUs  OBJECT-TYPE
            SYNTAX INTEGER
            {
                disable(1),
                enable(2)
            }
            MAX-ACCESS  read-create
            STATUS      current
            DESCRIPTION
                "Enable or disable vendor discretionary FRA triggering criteria in the upstream direction.
                 Options:
                 1. disable (1)  - Disable vendor discretionary FRA triggering criteria in the upstream direction.
                 2. enable (2)   - Enable vendor discretionary FRA triggering criteria in the upstream direction.
                "
           DEFVAL { disable }
            ::= { hwXdslTR129LineConfProfEntry 113 }

        hwXdslTR129LineConfProfGfastLineLowFreqEdgeValueUs  OBJECT-TYPE
            SYNTAX Gauge32 (43..1023)
            MAX-ACCESS read-create
            STATUS current
            DESCRIPTION
                "Low-frequency Edge Stop-band Mask(LESM).
                 If a LESM is used, the LESM shall be specified with breakpoints.
                 These breakpoints are specified starting from ftr1, which is the start of the in-band PSD mask, as specified in [ITU-T G.9700].
                 This is not to be confused with ftr3,  which is the start of the in-band part of the LESM.
                "
            REFERENCE
                "ITU-T G.9701, paragraph 7.3.1.1.1"
            DEFVAL { 43 }
            ::= { hwXdslTR129LineConfProfEntry 114 }

        hwXdslTR129LineConfProfGfastFallbackFreq OBJECT-TYPE
            SYNTAX Gauge32 (43..2047)
            MAX-ACCESS read-create
            STATUS current
            DESCRIPTION
                "G.fast fallback to G.993.2 profile frequency.
                "
            DEFVAL { 43 }
            ::= { hwXdslTR129LineConfProfEntry 115 }

        --  end of hwXdslTR129LineConfProfTable

        --  hwXdslTR129LineConfProfModeSpecTable
        hwXdslTR129LineConfProfModeSpecTable  OBJECT-TYPE
            SYNTAX      SEQUENCE  OF  HwXdslTR129LineConfProfModeSpecEntry
            MAX-ACCESS  not-accessible
            STATUS      current
            DESCRIPTION
                "The table hwXdslTR129LineConfProfModeSpecTable extends the
                 XDSL line configuration profile by XDSL Mode Specific
                 parameters.
                 A row in this table that has an index of
                 hwXdslTR129LineConfProfMode == defMode(1), is called a
                 'mandatory' row.
                 A row in this table that has an index such that
                 hwXdslTR129LineConfProfMode is not equal to defMode(1),
                 is called an 'optional' row.
                 When a row in the hwXdslTR129LineConfProfTable table
                 (the parent row) is created, the SNMP agent will
                 automatically create a 'mandatory' row in this table.
                 When the parent row is deleted, the SNMP agent will
                 automatically delete all associated rows in this table.
                 Any attempt to delete the 'mandatory' row using the
                 hwXdslTR129LineConfProfModeSpecRowStatus attribute will be
                 rejected by the SNMP agent.
                 The manager MAY create an 'optional' row in this table
                 using the hwXdslTR129LineConfProfModeSpecRowStatus attribute if
                 the parent row exists.
                 The manager MAY delete an 'optional' row in this table
                 using the hwXdslTR129LineConfProfModeSpecRowStatus attribute at
                 any time.
                 If the actual transmission mode of a DSL line does not
                 match one of the 'optional' rows in this table, then
                 the line will use the PSD configuration from the
                 'mandatory' row.
                 The indexes of this table are hwXdslTR129LineConfProfProfileName
                 and hwXdslTR129LineConfProfMode.
                "
            ::= { hwXdslProfileLine 6 }

        hwXdslTR129LineConfProfModeSpecEntry  OBJECT-TYPE
            SYNTAX      HwXdslTR129LineConfProfModeSpecEntry
            MAX-ACCESS  not-accessible
            STATUS      current
            DESCRIPTION
                "The table hwXdslTR129LineConfProfModeSpecTable extends the
                 XDSL line configuration profile by XDSL Mode Specific
                 parameters.
                 A row in this table that has an index of
                 hwXdslTR129LineConfProfMode == defMode(1), is called a
                 'mandatory' row.
                 A row in this table that has an index such that
                 hwXdslTR129LineConfProfMode is not equal to defMode(1),
                 is called an 'optional' row.
                 When a row in the hwXdslTR129LineConfProfTable table
                 (the parent row) is created, the SNMP agent will
                 automatically create a 'mandatory' row in this table.
                 When the parent row is deleted, the SNMP agent will
                 automatically delete all associated rows in this table.
                 Any attempt to delete the 'mandatory' row using the
                 hwXdslTR129LineConfProfModeSpecRowStatus attribute will be
                 rejected by the SNMP agent.
                 The manager MAY create an 'optional' row in this table
                 using the hwXdslTR129LineConfProfModeSpecRowStatus attribute if
                 the parent row exists.
                 The manager MAY delete an 'optional' row in this table
                 using the hwXdslTR129LineConfProfModeSpecRowStatus attribute at
                 any time.
                 If the actual transmission mode of a DSL line does not
                 match one of the 'optional' rows in this table, then
                 the line will use the PSD configuration from the
                 'mandatory' row.
                 The indexes of this entry are hwXdslTR129LineConfProfProfileName
                 and hwXdslTR129LineConfProfMode.
                "
            INDEX  { hwXdslTR129LineConfProfProfileName, hwXdslTR129LineConfProfMode }
            ::= { hwXdslTR129LineConfProfModeSpecTable 1 }

        HwXdslTR129LineConfProfModeSpecEntry  ::=
            SEQUENCE {
              hwXdslTR129LineConfProfMode                 INTEGER,
              hwXdslTR129LineConfProfMaxNomAtpDs          Unsigned32,
              hwXdslTR129LineConfProfMaxNomAtpUs          Unsigned32,
              hwXdslTR129LineConfProfPsdMaskDs            HwXdslPsdMaskDs,
              hwXdslTR129LineConfProfPsdMaskUs            HwXdslPsdMaskUs,
              hwXdslTR129LineConfProfPsdMaskSelectUs      Unsigned32,
              hwXdslTR129LineConfProfPSDClassMask         HwXdslPSDClassMask,
              hwXdslTR129LineConfProfProfiles             HwXdslProfiles,
              hwXdslTR129LineConfProfBandOptUsage         HwXdslBandOptUsage,
              hwXdslTR129LineConfProfModeSpecRowStatus    RowStatus,
              hwXdslTR129LineConfProfVirtualNoiseModeDs    HwXdslVirtualNoise,
              hwXdslTR129LineConfProfVirtualNoiseModeUs    HwXdslVirtualNoise,
              hwXdslTR129LineConfProfVirtualNoiseDs        HwXdslVirtualNoiseDs,
              hwXdslTR129LineConfProfVirtualNoiseUs        HwXdslVirtualNoiseUs,
              hwXdslTR129LineConfProfAutoProfile           HwXdslAutoProfile,
              hwXdslTR129LineConfProfGfastPsdMaskDs        HWVOPGfastPsdMask,
              hwXdslTR129LineConfProfGfastPsdMaskUs        HWVOPGfastPsdMask,
              hwXdslTR129LineConfProfGfastMaxNomAtpDs      Unsigned32,
              hwXdslTR129LineConfProfGfastMaxNomAtpUs      Unsigned32
           }

        hwXdslTR129LineConfProfMode    OBJECT-TYPE
            SYNTAX  INTEGER {
                               defMode (1),
                               adsl (2),
                               adsl2Pots (3),
                               adsl2Isdn (4),
                               adsl2PlusPots (5),
                               adsl2PlusIsdn (6),
                               adsl2ReachExtended (7),
                               vdsl2Pots (8),
                               vdsl2Isdn (9),
                               fast (10)
                            }
            MAX-ACCESS  not-accessible
            STATUS      current
            DESCRIPTION
                "The XDSL Mode is a way of categorizing the various XDSL
                 transmission modes into groups, each group (XDSL Mode) shares
                 the same PSD configuration.
                 There should be multiple entries in this table for a given
                 line profile in case multiple bits are set in
                 hwXdslTR129LineConfProfXtuTransSysEna for that profile.
                  Options:
                 1. defMode (1)             - Indicates defMode
                 2. adsl (2)                - Indicates adsl
                 3. adsl2Pots (3)           - Indicates adsl2Pots
                 4. adsl2Isdn (4)           - Indicates adsl2Isdn
                 5. adsl2PlusPots (5)       - Indicates adsl2PlusPots
                 6. adsl2PlusIsdn (6)       - Indicates adsl2PlusIsdn
                 7. adsl2ReachExtended (7)  - Indicates adsl2ReachExtended
                 8. vdsl2Pots (8)           - Indicates vdsl2Pots
                 9. vdsl2Isdn (9)           - Indicates vdsl2Isdn
                 10. fast (10)               - Indicates G.fast mode
                "

            REFERENCE    "DSL Forum TR-90, paragraph 5.1.8"
            ::= { hwXdslTR129LineConfProfModeSpecEntry 1 }


        hwXdslTR129LineConfProfMaxNomAtpDs  OBJECT-TYPE
            SYNTAX      Unsigned32 (0..510 | 4294967295)
            UNITS       "0.1 dBm"
            MAX-ACCESS  read-create
            STATUS      current
            DESCRIPTION
                "The maximum nominal aggregate transmit power in the
                 downstream direction during initialization and Showtime.
                 It ranges from 0 to 510 units of 0.1 dBm  (0 to 255 physical
                 values are 0 to 25.5 dBm, 256 to 510 physical values are
                 -25.5 to -0.1 dBm).
                 Unit: 0.1 dBm
                "
            REFERENCE    "ITU-T G.997.1, paragraph 7.3.1.2"
            DEFVAL       { 145 }
            ::= { hwXdslTR129LineConfProfModeSpecEntry 2 }

        hwXdslTR129LineConfProfMaxNomAtpUs  OBJECT-TYPE
            SYNTAX      Unsigned32 (0..510 | 4294967295)
            UNITS       "0.1 dBm"
            MAX-ACCESS  read-create
            STATUS      current
            DESCRIPTION
                "The maximum nominal aggregate transmit power in the upstream
                 direction during initialization and Showtime.
                 It ranges from 0 to 510 units of 0.1 dBm  (0 to 255 physical
                 values are 0 to 25.5 dBm, 256 to 510 physical values are
                 -25.5 to -0.1 dBm).
                 Unit: 0.1 dBm
                "
            REFERENCE    "ITU-T G.997.1, paragraph 7.3.1.2"
            DEFVAL       { 145 }
            ::= { hwXdslTR129LineConfProfModeSpecEntry 3 }

        hwXdslTR129LineConfProfPsdMaskDs   OBJECT-TYPE
            SYNTAX      HwXdslPsdMaskDs
            MAX-ACCESS  read-create
            STATUS      current
            DESCRIPTION
                "This configuration parameter defines the downstream PSD mask
                 applicable at the U C2 reference point.
                 This MIB PSD mask may impose PSD restrictions in addition
                 to the Limit PSD mask defined in the relevant Recommendation
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup.
                "
            REFERENCE    "ITU-T G.997.1(200604), paragraph 7.3.1.2.9"
            ::= { hwXdslTR129LineConfProfModeSpecEntry 4 }

        hwXdslTR129LineConfProfPsdMaskUs   OBJECT-TYPE
            SYNTAX      HwXdslPsdMaskUs
            MAX-ACCESS  read-create
            STATUS      current
            DESCRIPTION
                "This configuration parameter defines the upstream PSD
                 mask applicable at the U R2 reference point. This MIB
                 PSD mask may impose PSD restrictions in addition to the
                 Limit PSD mask defined in the relevant Recommendations
                 (e.g., ITU-T Recommendations G.992.3, G.993.2).
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup.
                "
            REFERENCE    "ITU-T G.997.1(200604), paragraph 7.3.1.2.12"
            ::= { hwXdslTR129LineConfProfModeSpecEntry 5 }

        hwXdslTR129LineConfProfPsdMaskSelectUs  OBJECT-TYPE
            SYNTAX      Unsigned32(0..9)
            MAX-ACCESS  read-create
            STATUS      current
            DESCRIPTION
                "The selected upstream PSD mask. This parameter is used only
                 for annexes J and M of G.992.3 and G.992.5, and the same
                 selection is used for all relevant enabled bits in
                 hwXdslTR129LineConfProfXtuTransSysEna.
                 The value is defined as below:
                 0-Invalid value
                 1-ADLU-32/EU-32
                 2-ADLU-36/EU-36
                 3-ADLU-40/EU-40
                 4-ADLU-44/EU-44
                 5-ADLU-48/EU-48
                 6-ADLU-52/EU-52
                 7-ADLU-56/EU-56
                 8-ADLU-60/EU-60
                 9-ADLU-64/EU-64
                "
            REFERENCE    "ITU-T G.997.1 (amendment 1), 7.3.1.10"
            ::= { hwXdslTR129LineConfProfModeSpecEntry 6 }

        hwXdslTR129LineConfProfPSDClassMask  OBJECT-TYPE
            SYNTAX      HwXdslPSDClassMask
            MAX-ACCESS  read-create
            STATUS      current
            DESCRIPTION
                "In order to reduce the number of configuration possibilities,
                 the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1-NUS0.
                 -  Class HPE30 Annex B: HPE30-M1-NUS0.
                 -  Class 997E17-M2x Annex B: 997E17-M2x-NUS0.
                 -  Class 997E30-M2x Annex B: 997E30-M2x-NUS0.
                 -  Class 998E17-M2x Annex B: 998E17-M2x-NUS0, 998E17-M2x-NUS0-M, 998E17-M2x-A.
                 -  Class 998ADE17-M2x Annex B: 998ADE17-M2x-NUS0-M, 998ADE17-M2x-A, 998ADE17-M2x-B, 998ADE17-SPE-M2x-A.
                 -  Class 998E30-M2x Annex B: 998E30-M2x-NUS0, 998E30-M2x-NUS0-M.
                 -  Class 998ADE30-M2x Annex B: 998ADE30-M2x-NUS0-M, 998ADE30-M2x-NUS0-A.
                 "
            REFERENCE    "ITU-T G.997.1(200604), paragraph 7.3.1.1.12"
            DEFVAL       { 14 }
            ::= { hwXdslTR129LineConfProfModeSpecEntry 7 }

        hwXdslTR129LineConfProfProfiles  OBJECT-TYPE
            SYNTAX      HwXdslProfiles
            MAX-ACCESS  read-create
            STATUS      current
            DESCRIPTION
                "This configuration parameter contains the G.993.2
                 profiles to be allowed by the near-end xTU on this line.
                "
            REFERENCE    "ITU-T G.997.1(200604), paragraph 7.3.1.1.11"
            DEFVAL       { 5 }
            ::= { hwXdslTR129LineConfProfModeSpecEntry 8 }

        hwXdslTR129LineConfProfBandOptUsage  OBJECT-TYPE
            SYNTAX      HwXdslBandOptUsage
            MAX-ACCESS  read-create
            STATUS      current
            DESCRIPTION
                "Defines the XDSL link use of the optional frequency
                 range [25kHz - 138kHz] (Opt).
                 Options:
                 1. unused(1)        - indicates Opt is unused
                 2. used(2)          - indicates Opt usage is for upstream
                 3. invalidValue(-1) -Invalid value
                 Huawei defined.
                "
            DEFVAL       { unused }
            ::= { hwXdslTR129LineConfProfModeSpecEntry 9 }

        hwXdslTR129LineConfProfModeSpecRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwXdslTR129LineConfProfModeSpecEntry 10 }

        hwXdslTR129LineConfProfVirtualNoiseModeDs  OBJECT-TYPE
            SYNTAX      HwXdslVirtualNoise
            MAX-ACCESS  read-create
            STATUS      current
            DESCRIPTION
               "This parameter enables the transmitter referred
                virtual noise in the downstream direction.
                If set to 1, the virtual noise is disabled.
                If set to 2, the virtual noise is enabled.
               "
            REFERENCE    "ITU-T G.997.1(200604), paragraph 7.3.1.7.1"
            DEFVAL       { disable }
            ::= { hwXdslTR129LineConfProfModeSpecEntry 11 }

        hwXdslTR129LineConfProfVirtualNoiseModeUs  OBJECT-TYPE
            SYNTAX      HwXdslVirtualNoise
            MAX-ACCESS  read-create
            STATUS      current
            DESCRIPTION
               "This parameter enables the transmitter referred
                virtual noise in the upstream direction.
                If set to 1, the virtual noise is disabled.
                If set to 2, the virtual noise is enabled.
               "
            REFERENCE    "ITU-T G.997.1(200604),paragraph 7.3.1.7.2"
            DEFVAL       { disable }
            ::= { hwXdslTR129LineConfProfModeSpecEntry 12 }

        hwXdslTR129LineConfProfVirtualNoiseDs  OBJECT-TYPE
            SYNTAX      HwXdslVirtualNoiseDs
            MAX-ACCESS  read-create
            STATUS      current
            DESCRIPTION
                "This configuration parameter defines the downstream
                 transmitter referred virtual noise (TXREFVNds).
                 The TXREFVNds shall be specified through a set of breakpoints.
                 Each breakpoint shall consist of a subcarrier index,
                 with a subcarrier spacing of 4.3125 kHz,
                 and a noise PSD level (expressed in dBm/Hz) at that subcarrier.
                 The set of breakpoints can then be represented as
                 [(t1, PSD1), (t2, PSD2),..., (tN, PSDN)].
                 The subcarrier index shall be coded as an unsigned integer.
                 The noise level shall be coded as an 8-bit unsigned integer
                 representing the noise level -40 dBm/Hz (coded as 0) to -140 dBm/Hz
                 (coded as 200), in steps of 0.5 dBm/Hz.
                 Values from 201 to 255 are special values indicating a noise
                 level of 0 W/Hz. The maximum number of breakpoints is 32.
                "
            REFERENCE    "ITU-T G.997.1(200604), paragraph 7.3.1.7.3"
            ::= { hwXdslTR129LineConfProfModeSpecEntry 13 }

        hwXdslTR129LineConfProfVirtualNoiseUs  OBJECT-TYPE
            SYNTAX      HwXdslVirtualNoiseUs
            MAX-ACCESS  read-create
            STATUS      current
            DESCRIPTION
                "This configuration parameter defines the upstream
                 transmitter referred virtual noise (TXREFVNus).
                 The TXREFVNus shall be specified through a set of breakpoints.
                 Each breakpoint shall consist of a subcarrier index t,
                 with a subcarrier spacing of 4.3125 kHz, and a noise PSD level
                 (expressed in dBm/Hz) at that subcarrier.
                 The set of breakpoints can then be represented as
                 [(t1, PSD1), (t2, PSD2), ... , (tN, PSDN)].
                 The subcarrier index shall be coded as an unsigned integer.
                 The noise level shall be coded as an 8-bit unsigned integer
                 representing the noise level -40 dBm/Hz (coded as 0) to -140 dBm/Hz
                 (coded as 200), in steps of 0.5 dBm/Hz.
                 Values from 201 to 255 are special values indicating
                 a noise level of 0 W/Hz. The maximum number of breakpoints is 16.
                "
            REFERENCE    "ITU-T G.997.1(200604), paragraph 7.3.1.7.4"
            ::= { hwXdslTR129LineConfProfModeSpecEntry 14 }

        hwXdslTR129LineConfProfAutoProfile  OBJECT-TYPE
            SYNTAX      HwXdslAutoProfile
            MAX-ACCESS  read-create
            STATUS      current
            DESCRIPTION
                 "Enable or disable the G.993.2 profiles adaptive function.
                  If set to 1, the G.993.2 profiles adaptive function is disabled.
                If set to 2, the G.993.2 profiles adaptive function is enabled.
               "
            REFERENCE    "ITU-T G.997.1(200604), paragraph 7.3.1.1.11"
            DEFVAL       { disable }
            ::= { hwXdslTR129LineConfProfModeSpecEntry 15 }

        hwXdslTR129LineConfProfGfastPsdMaskDs  OBJECT-TYPE
            SYNTAX HWVOPGfastPsdMask
            MAX-ACCESS read-create
            STATUS current
            DESCRIPTION
                "The downstream PSD mask applicable at the U-O2 reference point.
                 This parameter may impose PSD restrictions (breakpoints) in addition to the Limit PSD mask
                 defined in the relevant Recommendation (e.g., ITU-T Recs G.9701).
                 This is a string of 32 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 94-95, which are associated with a 32nd breakpoint.
                 Each subcarrier index is an unsigned number in the range 0 and NSCds-1.
                 Each PSD reduction value is in the range 0 (0dBm/Hz) to 255 (-127.5dBm/Hz) with steps of 0.5dBm/Hz.
                 Valid values are in the range 0 to 254 (0 to -127dBm/Hz).
                 When the number of breakpoints is less than 32, all remaining octets are set to the value 0xFF.
                 Note that the content of this object should be correlated with the subcarriers mask and with the RFI setup.
                "
            REFERENCE
                "ITU-T G.9701, paragraph #7.3.1.1"
            ::= { hwXdslTR129LineConfProfModeSpecEntry 16 }

        hwXdslTR129LineConfProfGfastPsdMaskUs  OBJECT-TYPE
            SYNTAX HWVOPGfastPsdMask
            MAX-ACCESS read-create
            STATUS current
            DESCRIPTION
                "The upstream PSD mask applicable at the U-R2 reference point.
                 This parameter may impose PSD restrictions (breakpoints) in addition to the Limit PSD mask
                 defined in the relevant Recommendation (e.g., ITU-T Recs G.9701).
                 This is a string of 16 pairs of values in the following structure:
                 Octets 0-1 - Index of 1st subcarrier used in the context of a first breakpoint.
                 Octet 2    - The PSD reduction for the subcarrier indicated in octets 0 and 1.
                 Octets 3-5 - Same, for a 2nd breakpoint.
                 Octets 6-8 - Same, for a 3rd breakpoint.
                 This architecture continues until octets 9-47, which are associated with a 16th breakpoint.
                 Each subcarrier index is an unsigned number in the range 0 and NSCus-1.
                 Each PSD reduction value is in the range 0 (0dBm/Hz) to 255 (-127.5dBm/Hz) with steps of 0.5dBm/Hz.
                 Valid values are in the range 0 to 254 (0 to -127dBm/Hz).
                 When the number of breakpoints is less than 16, all remaining octets are set to the value 0xFF.
                 Note that the content of this object should be correlated with the subcarriers mask and with the RFI setup.
                "
            REFERENCE
               "ITU-T G.9701, paragraph #7.3.1.1"
            ::= { hwXdslTR129LineConfProfModeSpecEntry 17 }

        hwXdslTR129LineConfProfGfastMaxNomAtpDs  OBJECT-TYPE
            SYNTAX Unsigned32 (0..510 | 4294967295)
            UNITS "0.1 dBm"
            MAX-ACCESS read-create
            STATUS current
            DESCRIPTION
                "The G.fast maximum nominal aggregate transmit power in the downstream direction during initialization and Showtime.
                 It ranges from 0 to 510 units of 0.1 dBm (0 to 255 physical values are 0 to 25.5 dBm, 256 to 510 physical values are -25.5 to -0.1 dBm).
                 Unit: 0.1 dBm.
                "
            DEFVAL { 40 }
            ::= { hwXdslTR129LineConfProfModeSpecEntry 18 }

        hwXdslTR129LineConfProfGfastMaxNomAtpUs  OBJECT-TYPE
            SYNTAX Unsigned32 (0..510 | 4294967295)
            UNITS "0.1 dBm"
            MAX-ACCESS read-create
            STATUS current
            DESCRIPTION
                "The G.fast maximum nominal aggregate transmit power in the upstream direction during initialization and Showtime.
                 It ranges from 0 to 510 units of 0.1 dBm (0 to 255 physical values are 0 to 25.5 dBm, 256 to 510 physical values are -25.5 to -0.1 dBm).
                 Unit: 0.1 dBm.
                "
            DEFVAL { 40 }
            ::= { hwXdslTR129LineConfProfModeSpecEntry 19 }
        -- end of hwXdslTR129LineConfProfModeSpecTable



        -- hwVdslChConfProfileTable
        hwVdslChConfProfileTable  OBJECT-TYPE
            SYNTAX      SEQUENCE  OF  HwVdslChConfProfileEntry
            MAX-ACCESS  not-accessible
            STATUS      current
            DESCRIPTION
               "The table hwVdslChConfProfileTable contains XDSL channel
                profile configuration. The index of this table is
                hwVdslChConfProfProfileName.
                A default profile with an index of 'DEFVAL' will
                always exist and its parameters will be set to vendor-specific
                values, unless otherwise specified in this document.
               "
            ::= { hwXdslProfileChannel 1 }

        hwVdslChConfProfileEntry  OBJECT-TYPE
            SYNTAX      HwVdslChConfProfileEntry
            MAX-ACCESS  not-accessible
            STATUS      current
            DESCRIPTION
               "The table hwVdslChConfProfileTable contains XDSL channel
                profile configuration.
                The index of this entry is hwVdslChConfProfProfileName.
                A default profile with an index of 'DEFVAL' will
                always exist and its parameters will be set to vendor-specific
                values, unless otherwise specified in this document.
               "
            INDEX  { IMPLIED hwVdslChConfProfProfileName }
            ::= { hwVdslChConfProfileTable 1 }

        HwVdslChConfProfileEntry  ::=
           SEQUENCE {
              hwVdslChConfProfProfileName          OCTET STRING,
              hwVdslChConfProfMinDataRateDs        Unsigned32,
              hwVdslChConfProfMinDataRateUs        Unsigned32,
              hwVdslChConfProfMinResDataRateDs     Unsigned32,
              hwVdslChConfProfMinResDataRateUs     Unsigned32,
              hwVdslChConfProfMaxDataRateDs        Unsigned32,
              hwVdslChConfProfMaxDataRateUs        Unsigned32,
              hwVdslChConfProfMinDataRateLowPwrDs  Unsigned32,
              hwVdslChConfProfMinDataRateLowPwrUs  Unsigned32,
              hwVdslChConfProfMaxDelayDs           Unsigned32,
              hwVdslChConfProfMaxDelayUs           Unsigned32,
              hwVdslChConfProfMinProtectionDs      HwXdslSymbolProtectionDs,
              hwVdslChConfProfMinProtectionUs      HwXdslSymbolProtectionUs,
              hwVdslChConfProfMaxBerDs             HwXdslMaxBer,
              hwVdslChConfProfMaxBerUs             HwXdslMaxBer,
              hwVdslChConfProfUsDataRateDs         Unsigned32,
              hwVdslChConfProfDsDataRateDs         Unsigned32,
              hwVdslChConfProfUsDataRateUs         Unsigned32,
              hwVdslChConfProfDsDataRateUs         Unsigned32,
              hwVdslChConfProfImaEnabled           TruthValue,
              hwVdslChConfProfDataPathMode    HwXdslDataPathMode,
              hwVdslChConfProfRowStatus            RowStatus,
              hwVdslChConfProfPhyRcontrolDs        HwXdslPhyRControl,
              hwVdslChConfProfPhyRcontrolUs        HwXdslPhyRControl,
              hwVdslChConfProfInpMaxDs             HwXdslSymbolProtectionDs,
              hwVdslChConfProfInpMaxUs             HwXdslSymbolProtectionDs,
              hwVdslChConfProfMinRtxRatioDs        Unsigned32,
              hwVdslChConfProfMinRtxRatioUs        Unsigned32,
              hwVdslChConfProfMinRSoverheadDs      Unsigned32,
              hwVdslChConfProfMinRSoverheadUs      Unsigned32,
              hwVdslChConfProfErasureDecoding   HwXdslProfSwitchType,
              hwVdslChConfProfMinSosBrDs           Unsigned32,
              hwVdslChConfProfMinSosBrUs           Unsigned32,
              hwVdslChConfProfMinEtrRtxDs          Unsigned32,
              hwVdslChConfProfMinEtrRtxUs          Unsigned32,
              hwVdslChConfProfMaxEtrRtxDs          Unsigned32,
              hwVdslChConfProfMaxEtrRtxUs          Unsigned32,
              hwVdslChConfProfMaxNdrRtxDs          Unsigned32,
              hwVdslChConfProfMaxNdrRtxUs          Unsigned32,
              hwVdslChConfProfMaxDelayRtxDs        Unsigned32,
              hwVdslChConfProfMaxDelayRtxUs        Unsigned32,
              hwVdslChConfProfMinDelayRtxDs        Unsigned32,
              hwVdslChConfProfMinDelayRtxUs        Unsigned32,
              hwVdslChConfProfMinInpShineRtxDs     Unsigned32,
              hwVdslChConfProfMinInpShineRtxUs     Unsigned32,
              hwVdslChConfProfMinInp8ShineRtxDs    Unsigned32,
              hwVdslChConfProfMinInp8ShineRtxUs    Unsigned32,
              hwVdslChConfProfShineRatioRtxDs      Unsigned32,
              hwVdslChConfProfShineRatioRtxUs      Unsigned32,
              hwVdslChConfProfMinInpReinRtxDs      Unsigned32,
              hwVdslChConfProfMinInpReinRtxUs      Unsigned32,
              hwVdslChConfProfMinInp8ReinRtxDs     Unsigned32,
              hwVdslChConfProfMinInp8ReinRtxUs     Unsigned32,
              hwVdslChConfProfIatReinRtxDs         INTEGER,
              hwVdslChConfProfIatReinRtxUs         INTEGER,
              hwVdslChConfProfInitPolicy           INTEGER,
              hwVdslChConfProfMaxDataRateLowPwrDs  Unsigned32,
              hwVdslChConfProfL2MinDataRateToL0ActDataRateDs Integer32,
              hwVdslChConfProfMaxDelayOctetSplit             Gauge32,
              hwVdslChConfProfMaxDelayVar                    Gauge32
           }

        hwVdslChConfProfProfileName  OBJECT-TYPE
            SYNTAX      OCTET STRING (SIZE(1..32))
            MAX-ACCESS  accessible-for-notify
            STATUS      current
            DESCRIPTION
               "This object identifies a row in this table.
               "
            ::= { hwVdslChConfProfileEntry 1 }

        hwVdslChConfProfMinDataRateDs  OBJECT-TYPE
            SYNTAX      Unsigned32(32000..500000000)
            UNITS       "bits/second"
            MAX-ACCESS  read-create
            STATUS      current
            DESCRIPTION
               "If retransmission is not used in downstream direction,this parameter specifics
                minimum data rate for the bearer channel on downstream direction. The rate is
                coded in steps of 1000 bit/s.
                Unit: bits/second
               "
            REFERENCE    "ITU-T G.997.1, paragraph 7.3.2.1"
            ::= { hwVdslChConfProfileEntry 2 }

        hwVdslChConfProfMinDataRateUs  OBJECT-TYPE
            SYNTAX      Unsigned32(32000..500000000)
            UNITS       "bits/second"
            MAX-ACCESS  read-create
            STATUS      current
            DESCRIPTION
               "If retransmission is not used in upstream direction,this parameter specifics
                minimum data rate for the bearer channel on upstream direction. The rate is
                coded in steps of 1000 bit/s
                Unit: bits/second
               "
            REFERENCE    "ITU-T G.997.1, paragraph 7.3.2.1"
            ::= { hwVdslChConfProfileEntry 3 }

        hwVdslChConfProfMinResDataRateDs  OBJECT-TYPE
            SYNTAX      Unsigned32(32000..500000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode in the direction of the bearer channel (i.e.,
                 hwVdslLConfProfRaModeDs) is set to DynamicRa.
                 Unit: bits/second
                "
            REFERENCE    "ITU-T G.997.1, paragraph 7.3.2.1"
            ::= { hwVdslChConfProfileEntry 4 }

        hwVdslChConfProfMinResDataRateUs  OBJECT-TYPE
            SYNTAX      Unsigned32(32000..500000000)
            UNITS       "bits/second"
            MAX-ACCESS  read-create
            STATUS      current
            DESCRIPTION
               "Minimum Reserved Data Rate on Upstream direction.  The minimum
                reserved net data rate for the bearer channel, coded in
                bit/s.  This parameter is used only if the Rate Adaptation
                Mode in the direction of the bearer channel (i.e.,
                hwVdslLConfProfRaModeUs) is set to DynamicRa.
                Unit: bits/second
               "
            REFERENCE    "ITU-T G.997.1, paragraph 7.3.2.1"
            ::= { hwVdslChConfProfileEntry 5 }

        hwVdslChConfProfMaxDataRateDs  OBJECT-TYPE
            SYNTAX      Unsigned32(32000..500000000)
            UNITS       "bits/second"
            MAX-ACCESS  read-create
            STATUS      current
            DESCRIPTION
               "If retransmission is not used in downstream direction,this parameter specifics
                maximum data rate for the bearer channel on downstream direction. The rate is
                coded in steps of 1000 bit/s.
                Unit: bits/second
               "
            REFERENCE    "ITU-T G.997.1, paragraph 7.3.2.1"
            ::= { hwVdslChConfProfileEntry 6 }

        hwVdslChConfProfMaxDataRateUs  OBJECT-TYPE
            SYNTAX      Unsigned32(32000..500000000)
            UNITS       "bits/second"
            MAX-ACCESS  read-create
            STATUS      current
            DESCRIPTION
               "If retransmission is not used in upstream direction,this parameter specifics
                maximum data rate for the bearer channel on upstream direction. The rate is
                coded in steps of 1000 bit/s.
                Unit: bits/second
               "
            REFERENCE    "ITU-T G.997.1, paragraph 7.3.2.1"
            ::= { hwVdslChConfProfileEntry 7 }

        hwVdslChConfProfMinDataRateLowPwrDs  OBJECT-TYPE
            SYNTAX      Unsigned32(0..500000000)
            UNITS       "bits/second"
            MAX-ACCESS  read-create
            STATUS      current
            DESCRIPTION
                "Minimum Data Rate in Low Power state on Downstream direction.
                 The minimum net data rate for the bearer channel, coded in
                 bit/s, during the low power state (L1 in G.992.2, L2 in
                 G.992.3).
                 Unit: bits/second
                "
            REFERENCE    "ITU-T G.997.1, paragraph 7.3.2.1"
            ::= { hwVdslChConfProfileEntry 8 }

        hwVdslChConfProfMinDataRateLowPwrUs  OBJECT-TYPE
            SYNTAX      Unsigned32(0..200000000)
            UNITS       "bits/second"
            MAX-ACCESS  read-create
            STATUS      current
            DESCRIPTION
               "Minimum Data Rate in Low Power state on Upstream direction.
                The minimum net data rate for the bearer channel, coded in
                bit/s, during the low power state (L1 in G.992.2, L2 in
                G.992.3).
                Unit: bits/second
               "
            REFERENCE    "ITU-T G.997.1, paragraph 7.3.2.1"
            ::= { hwVdslChConfProfileEntry 9 }

        hwVdslChConfProfMaxDelayDs  OBJECT-TYPE
            SYNTAX Unsigned32 (0..200 | 255)
            UNITS       "milliseconds"
            MAX-ACCESS  read-create
            STATUS      current
            DESCRIPTION
                "If retransmission is not used in downstream direction,this parameter
                 is maximum interleave delay on downstream direction. The maximum
                 one-way interleaving delay introduced by the PMS-TC on
                 Downstream direction.  The XTUs shall choose the S (factor)
                 and D (depth) values such that the actual one-way interleaving
                 delay (hwXdslChanStatusActDelay) is as close as possible to,
                 but less than or equal to, hwVdslChanConfMaxDelayDs.  The
                 delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { hwVdslChConfProfileEntry 10 }

        hwVdslChConfProfMaxDelayUs  OBJECT-TYPE
            SYNTAX Unsigned32 (0..200 | 255)
            UNITS       "milliseconds"
            MAX-ACCESS  read-create
            STATUS      current
            DESCRIPTION
                "If retransmission is not used in upstream direction,this parameter
                 is maximum interleave delay on upstream direction. The maximum
                 one-way interleaving delay introduced by the PMS-TC on
                 Upstream direction.  The XTUs shall choose the S (factor) and
                 D (depth) values such that the actual one-way interleaving
                 delay (hwXdslChanStatusActDelay) is as close as possible to,
                 but less than or equal to, hwVdslChanConfMaxDelayUs.  The
                 delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { hwVdslChConfProfileEntry 11 }

        hwVdslChConfProfMinProtectionDs  OBJECT-TYPE
            SYNTAX      HwXdslSymbolProtectionDs
            UNITS       "symbols"
            MAX-ACCESS  read-create
            STATUS      current
            DESCRIPTION
                "If retransmission is not used in downstream direction,this parameter
                 is minimum impulse noise protection for the bearer channel on downstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwVdslChConfProfileEntry 12 }

        hwVdslChConfProfMinProtectionUs  OBJECT-TYPE
            SYNTAX      HwXdslSymbolProtectionUs
            UNITS       "symbols"
            MAX-ACCESS  read-create
            STATUS      current
            DESCRIPTION
                "If retransmission is not used in upstream direction,this parameter
                 is minimum impulse noise protection for the bearer channel on upstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwVdslChConfProfileEntry 13 }

        hwVdslChConfProfMaxBerDs  OBJECT-TYPE
            SYNTAX      HwXdslMaxBer
            MAX-ACCESS  read-create
            STATUS      current
            DESCRIPTION
                "Maximum Bit Error Ratio on Downstream direction.  The maximum
                 bit error ratio for the bearer channel.  The parameter can
                 take the following values (for 1E-3, 1E-5 or 1E-7).
                 Options:
                 1. eminus3 (1) - 1E-3
                 2. eminus5 (2) - 1E-5
                 3. eminus7 (3) - 1E-7
                "
            REFERENCE    "ITU-T G.997.1, paragraph 7.3.2.4"
            DEFVAL       { eminus5 }
            ::= { hwVdslChConfProfileEntry 14 }

        hwVdslChConfProfMaxBerUs  OBJECT-TYPE
            SYNTAX      HwXdslMaxBer
            MAX-ACCESS  read-create
            STATUS      current
            DESCRIPTION
                "Maximum Bit Error Ratio on Upstream direction.  The maximum
                 bit error ratio for the bearer channel.  The parameter can
                 take the following values (for 1E-3, 1E-5 or 1E-7).
                 Options:
                 1. eminus3 (1)  - 1E-3
                 2. eminus5 (2)  - 1E-5
                 3. eminus7 (3)  - 1E-7
                 "
            REFERENCE    "ITU-T G.997.1, paragraph 7.3.2.4"
            DEFVAL       { eminus5 }
            ::= { hwVdslChConfProfileEntry 15 }

        hwVdslChConfProfUsDataRateDs  OBJECT-TYPE
            SYNTAX      Unsigned32(0..500000000)
            UNITS       "bits/second"
            MAX-ACCESS  read-create
            STATUS      current
            DESCRIPTION
                "If retransmission is not used in downstream direction,this parameter
                 is data rate threshold up-shift for downstream direction. An
                 'Up-shift rate change' event is triggered when the actual
                 downstream data rate exceeds, by more than the threshold, the
                 data rate at the last entry into Showtime.  The parameter is
                 coded in bit/s.
                 Unit: bits/second
                "
            REFERENCE    "ITU-T G.997.1, paragraph 7.3.2.8"
            ::= { hwVdslChConfProfileEntry 16 }

        hwVdslChConfProfDsDataRateDs  OBJECT-TYPE
            SYNTAX      Unsigned32(0..500000000)
            UNITS       "bits/second"
            MAX-ACCESS  read-create
            STATUS      current
            DESCRIPTION
                "If retransmission is not used in downstream direction,this parameter
                 is data rate threshold down-shift for downstream direction.  A
                 'Down-shift rate change' event is triggered when the actual
                 downstream data rate is below the data rate at the last entry
                 into Showtime, by more than the threshold.  The parameter is
                 coded in bit/s.
                 Unit: bits/second
                "
            REFERENCE    "ITU-T G.997.1, paragraph 7.3.2.8"
            ::= { hwVdslChConfProfileEntry 17 }

        hwVdslChConfProfUsDataRateUs  OBJECT-TYPE
            SYNTAX      Unsigned32(0..500000000)
            UNITS       "bits/second"
            MAX-ACCESS  read-create
            STATUS      current
            DESCRIPTION
                "If retransmission is not used in upstream direction,this parameter
                 is data rate threshold up shift for upstream direction.  An
                 'Up-shift rate change' event is triggered when the actual
                 upstream data rate exceeds, by more than the threshold, the
                 data rate at the last entry into Showtime.  The parameter is
                 coded in bit/s.
                 Unit: bits/second
                 "
            REFERENCE    "ITU-T G.997.1, paragraph 7.3.2.8"
            ::= { hwVdslChConfProfileEntry 18 }

        hwVdslChConfProfDsDataRateUs  OBJECT-TYPE
            SYNTAX      Unsigned32(0..500000000)
            UNITS       "bits/second"
            MAX-ACCESS  read-create
            STATUS      current
            DESCRIPTION
                "If retransmission is not used in upstream direction,this parameter
                 is data rate threshold down-shift for upstream direction.  A
                 'Down-shift rate change' event is triggered when the actual
                 upstream data rate is below the data rate at the last entry
                 into Showtime, by more than the threshold.  The parameter is
                 coded in bit/s.
                 Unit: bits/second
                "
            REFERENCE    "ITU-T G.997.1, paragraph 7.3.2.8"
            ::= { hwVdslChConfProfileEntry 19 }

        hwVdslChConfProfImaEnabled  OBJECT-TYPE
            SYNTAX      TruthValue
            MAX-ACCESS  read-create
            STATUS      current
            DESCRIPTION
                "IMA Mode Enable.  The parameter enables the IMA operation mode
                 in the ATM Data Path.  Relevant only if the channel is of ATM
                 Data Path.  When in 'enable' state, the ATM data path should
                 comply with the requirements for IMA transmission.
                "
            REFERENCE    "ITU-T G.997.1, paragraph 7.3.4.1"
            DEFVAL       { false }
            ::= { hwVdslChConfProfileEntry 20 }

        hwVdslChConfProfDataPathMode  OBJECT-TYPE
            SYNTAX      HwXdslDataPathMode
            MAX-ACCESS  read-create
            STATUS      current
            DESCRIPTION
                "The channel data path mode.
                 Options:
                 1. atm(1)               - ATM
                 2. ptm(2)               - PTM
                 3. both(3)              - ATM and PTM
                 Huawei defined.
                "
            DEFVAL       { both }
            ::= { hwVdslChConfProfileEntry 21 }

        hwVdslChConfProfRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwVdslChConfProfileEntry 22 }
        hwVdslChConfProfPhyRcontrolDs  OBJECT-TYPE
            SYNTAX      HwXdslPhyRControl
            MAX-ACCESS  read-create
            STATUS      current
            DESCRIPTION
                "To enable or disable the retransmission function."
            DEFVAL       { disable }
            ::= { hwVdslChConfProfileEntry 23 }

        hwVdslChConfProfPhyRcontrolUs  OBJECT-TYPE
            SYNTAX      HwXdslPhyRControl
            MAX-ACCESS  read-create
            STATUS      current
            DESCRIPTION
               "To enable or disable the retransmission function."
            DEFVAL       { disable }
            ::= { hwVdslChConfProfileEntry 24 }

        hwVdslChConfProfInpMaxDs  OBJECT-TYPE
            SYNTAX      HwXdslSymbolProtectionDs
            MAX-ACCESS  read-create
            STATUS      current
            DESCRIPTION
               "Maximum Impulse Noise Protection on downstream direction."
            ::= { hwVdslChConfProfileEntry 25 }

        hwVdslChConfProfInpMaxUs  OBJECT-TYPE
            SYNTAX      HwXdslSymbolProtectionDs
            MAX-ACCESS  read-create
            STATUS      current
            DESCRIPTION
               "Maximum Impulse Noise Protection on upstream direction."
            ::= { hwVdslChConfProfileEntry 26 }

        hwVdslChConfProfMinRtxRatioDs  OBJECT-TYPE
            SYNTAX      Unsigned32(0..255)
            MAX-ACCESS  read-create
            STATUS      current
            DESCRIPTION
               "This object is used to config the minimum retransmission band width parameter downstream."
            ::= { hwVdslChConfProfileEntry 27 }

        hwVdslChConfProfMinRtxRatioUs  OBJECT-TYPE
            SYNTAX      Unsigned32(0..255)
            MAX-ACCESS  read-create
            STATUS      current
            DESCRIPTION
               "This object is used to config the minimum retransmission band width parameter upstream."
            ::= { hwVdslChConfProfileEntry 28 }

        hwVdslChConfProfMinRSoverheadDs  OBJECT-TYPE
            SYNTAX      Unsigned32(0..128)
            MAX-ACCESS  read-create
            STATUS      current
            DESCRIPTION
                "This object is used to config the minimum RSoverhead parameter downstream.."
            ::= { hwVdslChConfProfileEntry 29 }

        hwVdslChConfProfMinRSoverheadUs  OBJECT-TYPE
            SYNTAX      Unsigned32(0..128)
            MAX-ACCESS  read-create
            STATUS      current
            DESCRIPTION
               "This object is used to config the minimum RSoverhead parameter upstream.."
            ::= { hwVdslChConfProfileEntry 30 }

        hwVdslChConfProfErasureDecoding  OBJECT-TYPE
            SYNTAX      HwXdslProfSwitchType
            MAX-ACCESS  read-create
            STATUS      current
            DESCRIPTION
               "To enable or disable the erasure decoding of a channel.
                Options:
                1. enable(1)
                2. disable(2)
                "
            DEFVAL       { disable }
            ::= { hwVdslChConfProfileEntry 31 }

        hwVdslChConfProfMinSosBrDs  OBJECT-TYPE
            SYNTAX      Unsigned32(0..65535)
            UNITS       "Kbps"
            MAX-ACCESS  read-create
            STATUS      current
            DESCRIPTION
               "This parameter specifies the minimum net data rate required for a valid SOS request in
                the downstream direction. The valid range of values is from 0 to 65535 Kbps.
                Unit: Kbps
               "
            REFERENCE    "ITU-T G.997.1, paragraph 7.3.2.1.6"
            ::= { hwVdslChConfProfileEntry 32 }

        hwVdslChConfProfMinSosBrUs  OBJECT-TYPE
            SYNTAX      Unsigned32(0..65535)
            UNITS       "Kbps"
            MAX-ACCESS  read-create
            STATUS      current
            DESCRIPTION
               "This parameter specifies the minimum net data rate required for a valid SOS request in
                the upstream direction. The valid range of values is from 0 to 65535 Kbps.
                Unit: Kbps
               "
            REFERENCE    "ITU-T G.997.1, paragraph 7.3.2.1.7"
            ::= { hwVdslChConfProfileEntry 33 }

        hwVdslChConfProfMinEtrRtxDs  OBJECT-TYPE
            SYNTAX      Unsigned32(32000..500000000)
            UNITS       "bits/second"
            MAX-ACCESS  read-create
            STATUS      current
            DESCRIPTION
               "If retransmission is used in downstream direction, this parameter specifies the
                minimum expected throughput for the bearer channel.The values range in steps of
                1000 bit/s.
               "
            REFERENCE    "ITU-T G.997.1, paragraph 7.3.2.1.8"
            ::= { hwVdslChConfProfileEntry 34 }

        hwVdslChConfProfMinEtrRtxUs  OBJECT-TYPE
            SYNTAX      Unsigned32(32000..500000000)
            UNITS       "bits/second"
            MAX-ACCESS  read-create
            STATUS      current
            DESCRIPTION
               "If retransmission is used in upstream direction, this parameter specifies the
                minimum expected throughput for the bearer channel.The values range in steps of
                1000 bit/s.
               "
            REFERENCE    "ITU-T G.997.1, paragraph 7.3.2.1.8"
            ::= { hwVdslChConfProfileEntry 35 }

        hwVdslChConfProfMaxEtrRtxDs  OBJECT-TYPE
            SYNTAX      Unsigned32(32000..500000000)
            UNITS       "bits/second"
            MAX-ACCESS  read-create
            STATUS      current
            DESCRIPTION
               "If retransmission is used in downstream direction, this parameter specifies the
                maximum expected throughput for the bearer channel.The values range in steps of
                1000 bit/s.
               "
            REFERENCE    "ITU-T G.997.1, paragraph 7.3.2.1.9"
            ::= { hwVdslChConfProfileEntry 36 }

        hwVdslChConfProfMaxEtrRtxUs  OBJECT-TYPE
            SYNTAX      Unsigned32(32000..500000000)
            UNITS       "bits/second"
            MAX-ACCESS  read-create
            STATUS      current
            DESCRIPTION
               "If retransmission is used in upstream direction, this parameter specifies the
                maximum expected throughput for the bearer channel.The values range in steps of
                1000 bit/s.
               "
            REFERENCE    "ITU-T G.997.1, paragraph 7.3.2.1.9"
            ::= { hwVdslChConfProfileEntry 37 }

        hwVdslChConfProfMaxNdrRtxDs  OBJECT-TYPE
            SYNTAX      Unsigned32(32000..500000000)
            UNITS       "bits/second"
            MAX-ACCESS  read-create
            STATUS      current
            DESCRIPTION
               "If retransmission is used in downstream direction, this parameter specifies the
                maximum net data rate for the bearer channel. The values range in steps of 1000 bit/s.
               "
            REFERENCE    "ITU-T G.997.1, paragraph 7.3.2.1.10"
            ::= { hwVdslChConfProfileEntry 38 }

        hwVdslChConfProfMaxNdrRtxUs  OBJECT-TYPE
            SYNTAX      Unsigned32(32000..500000000)
            UNITS       "bits/second"
            MAX-ACCESS  read-create
            STATUS      current
            DESCRIPTION
               "If retransmission is used in upstream direction, this parameter specifies the
                maximum net data rate for the bearer channel.The values range in steps of 1000 bit/s.
               "
            REFERENCE    "ITU-T G.997.1, paragraph 7.3.2.1.10"
            ::= { hwVdslChConfProfileEntry 39 }

        hwVdslChConfProfMaxDelayRtxDs  OBJECT-TYPE
            SYNTAX      Unsigned32(1..63)
            UNITS       "milliseconds"
            MAX-ACCESS  read-create
            STATUS      current
            DESCRIPTION
               "If retransmission is used in downstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwVdslChConfProfileEntry 40 }

        hwVdslChConfProfMaxDelayRtxUs  OBJECT-TYPE
            SYNTAX      Unsigned32(1..63)
            UNITS       "milliseconds"
            MAX-ACCESS  read-create
            STATUS      current
            DESCRIPTION
               "If retransmission is used in upstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwVdslChConfProfileEntry 41 }

        hwVdslChConfProfMinDelayRtxDs  OBJECT-TYPE
            SYNTAX      Unsigned32(0..63)
            UNITS       "milliseconds"
            MAX-ACCESS  read-create
            STATUS      current
            DESCRIPTION
               "If retransmission is used in downstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwVdslChConfProfileEntry 42 }

        hwVdslChConfProfMinDelayRtxUs  OBJECT-TYPE
            SYNTAX      Unsigned32(0..63)
            UNITS       "milliseconds"
            MAX-ACCESS  read-create
            STATUS      current
            DESCRIPTION
               "If retransmission is used in upstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwVdslChConfProfileEntry 43 }

        hwVdslChConfProfMinInpShineRtxDs  OBJECT-TYPE
            SYNTAX      Unsigned32(0..63)
            UNITS       "symbols"
            MAX-ACCESS  read-create
            STATUS      current
            DESCRIPTION
               "If retransmission is used in downstream direction, this parameter specifies
                the minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwVdslChConfProfileEntry 44 }

        hwVdslChConfProfMinInpShineRtxUs  OBJECT-TYPE
            SYNTAX      Unsigned32(0..63)
            UNITS       "symbols"
            MAX-ACCESS  read-create
            STATUS      current
            DESCRIPTION
               "If retransmission is used in upstream direction, this parameter specifies the
                minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwVdslChConfProfileEntry 45 }

        hwVdslChConfProfMinInp8ShineRtxDs  OBJECT-TYPE
            SYNTAX      Unsigned32(0..127)
            UNITS       "symbols"
            MAX-ACCESS  read-create
            STATUS      current
            DESCRIPTION
               "If retransmission is used in downstream direction, this parameter specifies
                the minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwVdslChConfProfileEntry 46 }

        hwVdslChConfProfMinInp8ShineRtxUs  OBJECT-TYPE
            SYNTAX      Unsigned32(0..127)
            UNITS       "symbols"
            MAX-ACCESS  read-create
            STATUS      current
            DESCRIPTION
               "If retransmission is used in upstream direction, this parameter specifies the
                minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwVdslChConfProfileEntry 47 }

        hwVdslChConfProfShineRatioRtxDs  OBJECT-TYPE
            SYNTAX      Unsigned32(0..100)
            MAX-ACCESS  read-create
            STATUS      current
            DESCRIPTION
               "If retransmission is used in downstream direction, this parameter specifies
                the SHINE ratio (detailed definition see G.998.4).
                The values range from 0 to 0.100 in increments of 0.001.
               "
            REFERENCE    "ITU-T G.997.1, paragraph 7.3.2.15"
            DEFVAL       { 0 }
            ::= { hwVdslChConfProfileEntry 48 }

        hwVdslChConfProfShineRatioRtxUs  OBJECT-TYPE
            SYNTAX      Unsigned32(0..100)
            MAX-ACCESS  read-create
            STATUS      current
            DESCRIPTION
               "If retransmission is used in upstream direction, this parameter specifies
                the SHINE ratio (detailed definition see G.998.4).
                The values range from 0 to 0.100 in increments of 0.001.
               "
            REFERENCE    "ITU-T G.997.1, paragraph 7.3.2.15"
            DEFVAL       { 0 }
            ::= { hwVdslChConfProfileEntry 49 }

        hwVdslChConfProfMinInpReinRtxDs  OBJECT-TYPE
            SYNTAX      Unsigned32(0..7)
            MAX-ACCESS  read-create
            STATUS      current
            DESCRIPTION
               "If retransmission is used in downstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwVdslChConfProfileEntry 50 }

        hwVdslChConfProfMinInpReinRtxUs  OBJECT-TYPE
            SYNTAX      Unsigned32(0..7)
            MAX-ACCESS  read-create
            STATUS      current
            DESCRIPTION
               "If retransmission is used in upstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwVdslChConfProfileEntry 51 }

        hwVdslChConfProfMinInp8ReinRtxDs  OBJECT-TYPE
            SYNTAX      Unsigned32(0..13)
            MAX-ACCESS  read-create
            STATUS      current
            DESCRIPTION
               "If retransmission is used in downstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwVdslChConfProfileEntry 52 }

        hwVdslChConfProfMinInp8ReinRtxUs  OBJECT-TYPE
            SYNTAX      Unsigned32(0..13)
            MAX-ACCESS  read-create
            STATUS      current
            DESCRIPTION
               "If retransmission is used in upstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwVdslChConfProfileEntry 53 }

        hwVdslChConfProfIatReinRtxDs  OBJECT-TYPE
            SYNTAX      INTEGER
                        {
                         frequency100Hz(0),
                   frequency120Hz(1)
                        }
            MAX-ACCESS  read-create
            STATUS      current
            DESCRIPTION
               "If retransmission is used in downstream direction, this parameter specifies
                the inter-arrival time that shall be assumed for REIN protection.
                Options:
          1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwVdslChConfProfileEntry 54 }

        hwVdslChConfProfIatReinRtxUs  OBJECT-TYPE
            SYNTAX      INTEGER
                        {
                         frequency100Hz(0),
                         frequency120Hz(1)
                        }
            MAX-ACCESS  read-create
            STATUS      current
            DESCRIPTION
               "If retransmission is used in upstream direction, this parameter specifies
                the inter-arrival time that shall be assumed for REIN protection.
                Options:
                1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwVdslChConfProfileEntry 55 }

        hwVdslChConfProfInitPolicy   OBJECT-TYPE
        SYNTAX INTEGER
               {
                   policy0(1),
                   policy1(2),
                   policy2(3)
               }
        MAX-ACCESS read-create
        STATUS current
        DESCRIPTION
            "This parameter indicates which policy shall be applied to
             determine the transceiver configuration parameters at
             initialization. The valid values for CIPOLICY are 0,1 and 2.
             Those policies are defined in the respective recommendations.
             Options:
             1. policy0 (1)      - Policy 0 according to the applicable standard
             2. policy1 (2)      - Policy 1 according to the applicable standard
             3. policy2 (3)      - Policy 2 according to the applicable standard
            "
        REFERENCE
            "ITU-T G.997.1 Amendment 1, paragraph #7.3.2.10 (CIPOLICY)"
        DEFVAL { policy0 }
             ::= { hwVdslChConfProfileEntry 56 }

  hwVdslChConfProfMaxDataRateLowPwrDs  OBJECT-TYPE
            SYNTAX      Unsigned32(0..500000000)
            UNITS       "bits/second"
            MAX-ACCESS  read-create
            STATUS      current
            DESCRIPTION
                "Maximum Data Rate in Low Power state on Downstream direction.
                 The maximum net data rate for the bearer channel, coded in
                 bit/s, during the low power state (L1 in G.992.2, L2 in
                 G.992.3).
                 Unit: bits/second
                "
            REFERENCE    "ITU-T G.997.1, paragraph 7.3.2.1"
            ::= { hwVdslChConfProfileEntry 57 }

  hwVdslChConfProfL2MinDataRateToL0ActDataRateDs  OBJECT-TYPE
            SYNTAX      Integer32(0..99)
            MAX-ACCESS  read-create
            STATUS      current
            DESCRIPTION
                "The ratio between data rate in low power state and data rate in normal state.
                "
            ::= { hwVdslChConfProfileEntry 58 }

  hwVdslChConfProfMaxDelayOctetSplit  OBJECT-TYPE
            SYNTAX Gauge32 (0..100 | 255)
            UNITS "percents"
            MAX-ACCESS read-create
            STATUS current
            DESCRIPTION
                "The line configuration parameter MAXDELAYOCTET-split (MDOSPLIT) defines the percentage of the MAXDELAYOCTET_ext
                 if operating in ITU-T G.998.4 or MAXDELAYOCTET in other cases allocated to the downstream direction. All of the remaining
                 MAXDELAYOCTET or MAXDELAYOCTET_ext shall be allocated for use in the upstream direction.
                 The detailed specification is in ITU-T G.993.2 and ITU-T G.998.4.
                 MDOSPLIT shall be expressed as a percentage, with valid range from 5 percent to 95 percent inclusive, in steps of 1 percent.
                 The value 0% is valid only if the maximum downstream interleaving delay is configured with the special value S1 (see clause 7.3.2.2)
                 and retransmission is disabled in the downstream direction. The value 100% is valid only if the maximum upstream interleaving delay
                 is configured with the special value S1 (see clause 7.3.2.2) and retransmission is disabled in the upstream direction.
                 A special value (255) shall indicate that the VTU-O is allowed to use a vendor discretionary algorithm.
                 NOTE - The special value is introduced to ensure backwards compatibility.
                "
            REFERENCE
                "ITU-T G.997.1, paragraph #7.3.1.14"
            DEFVAL { 255 }
            ::= { hwVdslChConfProfileEntry 59 }

  hwVdslChConfProfMaxDelayVar  OBJECT-TYPE
            SYNTAX Gauge32 (1..255)
            UNITS "0.1 milliseconds"
            MAX-ACCESS read-create
            STATUS current
            DESCRIPTION
                "This optional XDSL specific parameter specifies the maximum value
                 for the delay variation allowed in an OLR procedure.
                 It is ranges from 1 to 254 units of 0.1 milliseconds (i.e., 0.1 to 25.4 milliseconds)
                 with the special value 255 which indicates that no delay variation bound is imposed.
                 Unit: 0.1 milliseconds.
                "
            REFERENCE
                "ITU-T G.997.1 Amendment 1, paragraph #7.3.2.9 (DVMAX)"
            DEFVAL { 255 }
            ::= { hwVdslChConfProfileEntry 60 }

        --        hwXdslTR129ChConfProfileTable
        hwXdslTR129ChConfProfileTable  OBJECT-TYPE
            SYNTAX      SEQUENCE  OF        HwXdslTR129ChConfProfileEntry
            MAX-ACCESS  not-accessible
            STATUS      current
            DESCRIPTION
               "The table hwXdslTR129ChConfProfileTable contains XDSL channel
                profile configuration. The index of this table is
                      hwXdslTR129ChConfProfProfileName.
                A default profile with an index of 'DEFVAL' will
                always exist and its parameters will be set to vendor-specific
                values, unless otherwise specified in this document.
               "
            ::= { hwXdslProfileChannel 2 }

        hwXdslTR129ChConfProfileEntry  OBJECT-TYPE
            SYNTAX            HwXdslTR129ChConfProfileEntry
            MAX-ACCESS  not-accessible
            STATUS      current
            DESCRIPTION
               "The table hwXdslTR129ChConfProfileTable contains XDSL channel
                profile configuration.
                The index of this entry is hwXdslTR129ChConfProfProfileName.
                A default profile with an index of 'DEFVAL' will
                always exist and its parameters will be set to vendor-specific
                values, unless otherwise specified in this document.
               "
            INDEX  { IMPLIED hwXdslTR129ChConfProfProfileName }
            ::= { hwXdslTR129ChConfProfileTable 1 }

       HwXdslTR129ChConfProfileEntry  ::=
           SEQUENCE {
                    hwXdslTR129ChConfProfProfileName          OCTET STRING,
                    hwXdslTR129ChConfProfMinDataRateDs        Unsigned32,
                    hwXdslTR129ChConfProfMinDataRateUs        Unsigned32,
                    hwXdslTR129ChConfProfMinResDataRateDs     Unsigned32,
                    hwXdslTR129ChConfProfMinResDataRateUs     Unsigned32,
                    hwXdslTR129ChConfProfMaxDataRateDs        Unsigned32,
                    hwXdslTR129ChConfProfMaxDataRateUs        Unsigned32,
                    hwXdslTR129ChConfProfMinDataRateLowPwrDs  Unsigned32,
                    hwXdslTR129ChConfProfMaxDelayDs           Unsigned32,
                    hwXdslTR129ChConfProfMaxDelayUs           Unsigned32,
                    hwXdslTR129ChConfProfMinProtectionDs      HwXdslSymbolProtectionDs,
                    hwXdslTR129ChConfProfMinProtectionUs      HwXdslSymbolProtectionUs,
                    hwXdslTR129ChConfProfUsDataRateDs         Unsigned32,
                    hwXdslTR129ChConfProfDsDataRateDs         Unsigned32,
                    hwXdslTR129ChConfProfUsDataRateUs         Unsigned32,
                    hwXdslTR129ChConfProfDsDataRateUs         Unsigned32,
                    hwXdslTR129ChConfProfDataPathMode    HwXdslDataPathMode,
                    hwXdslTR129ChConfProfRowStatus            RowStatus,
                    hwXdslTR129ChConfProfPhyRcontrolDs        HwXdslPhyRControl,
                    hwXdslTR129ChConfProfPhyRcontrolUs        HwXdslPhyRControl,
                    hwXdslTR129ChConfProfInpMaxDs             HwXdslSymbolProtectionDs,
                    hwXdslTR129ChConfProfInpMaxUs             HwXdslSymbolProtectionDs,
                    hwXdslTR129ChConfProfMinRtxRatioDs        Unsigned32,
                    hwXdslTR129ChConfProfMinRtxRatioUs        Unsigned32,
                    hwXdslTR129ChConfProfMinRSoverheadDs      Unsigned32,
                    hwXdslTR129ChConfProfMinRSoverheadUs      Unsigned32,
                    hwXdslTR129ChConfProfErasureDecoding   HwXdslProfSwitchType,
                    hwXdslTR129ChConfProfMinSosBrDs           Unsigned32,
                    hwXdslTR129ChConfProfMinSosBrUs           Unsigned32,
                    hwXdslTR129ChConfProfMinEtrRtxDs          Unsigned32,
                    hwXdslTR129ChConfProfMinEtrRtxUs          Unsigned32,
                    hwXdslTR129ChConfProfMaxEtrRtxDs          Unsigned32,
                    hwXdslTR129ChConfProfMaxEtrRtxUs          Unsigned32,
                    hwXdslTR129ChConfProfMaxNdrRtxDs          Unsigned32,
                    hwXdslTR129ChConfProfMaxNdrRtxUs          Unsigned32,
                    hwXdslTR129ChConfProfMaxDelayRtxDs        Unsigned32,
                    hwXdslTR129ChConfProfMaxDelayRtxUs        Unsigned32,
                    hwXdslTR129ChConfProfMinDelayRtxDs        Unsigned32,
                    hwXdslTR129ChConfProfMinDelayRtxUs        Unsigned32,
                    hwXdslTR129ChConfProfMinInpShineRtxDs     Unsigned32,
                    hwXdslTR129ChConfProfMinInpShineRtxUs     Unsigned32,
                    hwXdslTR129ChConfProfMinInp8ShineRtxDs    Unsigned32,
                    hwXdslTR129ChConfProfMinInp8ShineRtxUs    Unsigned32,
                    hwXdslTR129ChConfProfShineRatioRtxDs      Unsigned32,
                    hwXdslTR129ChConfProfShineRatioRtxUs      Unsigned32,
                    hwXdslTR129ChConfProfMinInpReinRtxDs      Unsigned32,
                    hwXdslTR129ChConfProfMinInpReinRtxUs      Unsigned32,
                    hwXdslTR129ChConfProfMinInp8ReinRtxDs     Unsigned32,
                    hwXdslTR129ChConfProfMinInp8ReinRtxUs     Unsigned32,
                    hwXdslTR129ChConfProfIatReinRtxDs         INTEGER,
                    hwXdslTR129ChConfProfIatReinRtxUs         INTEGER,
                    hwXdslTR129ChConfProfInitPolicy           INTEGER,
                    hwXdslTR129ChConfProfMaxDataRateLowPwrDs  Unsigned32,
                    hwXdslTR129ChConfProfL2MinDataRateToL0ActDataRateDs Integer32,
                    hwXdslTR129ChConfProfMaxDelayOctetSplit             Gauge32,
                    hwXdslTR129ChConfProfMaxDelayVar                    Gauge32,
                    hwXdslTR129ChConfProfGfastMinEtrDs                  Gauge32,
                    hwXdslTR129ChConfProfGfastfMaxNdrDs                 Gauge32,
                    hwXdslTR129ChConfProfGfastUsDataRateDs              Gauge32,
                    hwXdslTR129ChConfProfGfastDsDataRateDs              Gauge32,
                     hwXdslTR129ChConfProfGfastMinEtrUs                 Gauge32,
                    hwXdslTR129ChConfProfGfastfMaxNdrUs                 Gauge32,
                    hwXdslTR129ChConfProfGfastUsDataRateUs              Gauge32,
                    hwXdslTR129ChConfProfGfastDsDataRateUs              Gauge32,
                    hwXdslTR129ChConfProfGfastMaxDelayRtxDs          Gauge32,
                    hwXdslTR129ChConfProfGfastMaxDelayRtxUs          Gauge32,
                    hwXdslTR129ChConfProfGfastMinInpShineRtxDs       Gauge32,
                    hwXdslTR129ChConfProfGfastMinInpShineRtxUs       Gauge32,
                    hwXdslTR129ChConfProfGfastShineRatioRtxDs        Gauge32,
                    hwXdslTR129ChConfProfGfastShineRatioRtxUs        Gauge32,
                    hwXdslTR129ChConfProfGfastMinInpReinRtxDs        Gauge32,
                    hwXdslTR129ChConfProfGfastMinInpReinRtxUs        Gauge32,
                    hwXdslTR129ChConfProfGfastIatReinRtxDs           INTEGER,
                    hwXdslTR129ChConfProfGfastIatReinRtxUs           INTEGER,
                    hwXdslTR129ChConfProfGfastMinRNRatioRtxDs        Gauge32,
                    hwXdslTR129ChConfProfGfastMinRNRatioRtxUs        Gauge32,
                    hwXdslTR129ChConfProfGfastLowANDEFTRThresholdDs  Gauge32,
                    hwXdslTR129ChConfProfGfastLowANDEFTRThresholdUs  Gauge32
           }

              hwXdslTR129ChConfProfProfileName  OBJECT-TYPE
            SYNTAX      OCTET STRING (SIZE(1..32))
            MAX-ACCESS  accessible-for-notify
            STATUS      current
            DESCRIPTION
               "This object identifies a row in this table.
               "
            ::= { hwXdslTR129ChConfProfileEntry 1 }

              hwXdslTR129ChConfProfMinDataRateDs  OBJECT-TYPE
            SYNTAX      Unsigned32(32000..200000000)
            UNITS       "bits/second"
            MAX-ACCESS  read-create
            STATUS      current
            DESCRIPTION
               "If retransmission is not used in downstream direction,this parameter specifics
                minimum data rate for the bearer channel on downstream direction. The rate is
                coded in steps of 1000 bit/s.
                Unit: bits/second
               "
            REFERENCE    "ITU-T G.997.1, paragraph 7.3.2.1"
            ::= { hwXdslTR129ChConfProfileEntry 2 }

              hwXdslTR129ChConfProfMinDataRateUs  OBJECT-TYPE
            SYNTAX      Unsigned32(32000..200000000)
            UNITS       "bits/second"
            MAX-ACCESS  read-create
            STATUS      current
            DESCRIPTION
               "If retransmission is not used in upstream direction,this parameter specifics
                minimum data rate for the bearer channel on upstream direction. The rate is
                coded in steps of 1000 bit/s
                Unit: bits/second
               "
            REFERENCE    "ITU-T G.997.1, paragraph 7.3.2.1"
            ::= { hwXdslTR129ChConfProfileEntry 3 }

              hwXdslTR129ChConfProfMinResDataRateDs  OBJECT-TYPE
            SYNTAX      Unsigned32(32000..200000000)
            UNITS       "bits/second"
            MAX-ACCESS  read-create
            STATUS      current
            DESCRIPTION
                "Minimum Reserved Data Rate on Downstream direction.  The
                 minimum reserved net data rate for the bearer channel, coded
                 in bit/s.  This parameter is used only if the Rate Adaptation
                 Mode in the direction of the bearer channel (i.e.,
                 hwXdslTR129LineConfRaModeDs) is set to DynamicRa.
                 Unit: bits/second
                "
            REFERENCE    "ITU-T G.997.1, paragraph 7.3.2.1"
            ::= { hwXdslTR129ChConfProfileEntry 4 }

              hwXdslTR129ChConfProfMinResDataRateUs  OBJECT-TYPE
            SYNTAX      Unsigned32(32000..200000000)
            UNITS       "bits/second"
            MAX-ACCESS  read-create
            STATUS      current
            DESCRIPTION
               "Minimum Reserved Data Rate on Upstream direction.  The minimum
                reserved net data rate for the bearer channel, coded in
                bit/s.  This parameter is used only if the Rate Adaptation
                Mode in the direction of the bearer channel (i.e.,
                hwXdslTR129LineConfRaModeUs) is set to DynamicRa.
                Unit: bits/second
               "
            REFERENCE    "ITU-T G.997.1, paragraph 7.3.2.1"
            ::= { hwXdslTR129ChConfProfileEntry 5 }

              hwXdslTR129ChConfProfMaxDataRateDs  OBJECT-TYPE
            SYNTAX      Unsigned32(32000..200000000)
            UNITS       "bits/second"
            MAX-ACCESS  read-create
            STATUS      current
            DESCRIPTION
               "If retransmission is not used in downstream direction,this parameter specifics
                maximum data rate for the bearer channel on downstream direction. The rate is
                coded in steps of 1000 bit/s.
                Unit: bits/second
               "
            REFERENCE    "ITU-T G.997.1, paragraph 7.3.2.1"
            ::= { hwXdslTR129ChConfProfileEntry 6 }

              hwXdslTR129ChConfProfMaxDataRateUs  OBJECT-TYPE
            SYNTAX      Unsigned32(32000..200000000)
            UNITS       "bits/second"
            MAX-ACCESS  read-create
            STATUS      current
            DESCRIPTION
               "If retransmission is not used in upstream direction,this parameter specifics
                maximum data rate for the bearer channel on upstream direction. The rate is
                coded in steps of 1000 bit/s.
                Unit: bits/second
               "
            REFERENCE    "ITU-T G.997.1, paragraph 7.3.2.1"
            ::= { hwXdslTR129ChConfProfileEntry 7 }

          hwXdslTR129ChConfProfMinDataRateLowPwrDs  OBJECT-TYPE
            SYNTAX      Unsigned32(0..200000000)
            UNITS       "bits/second"
            MAX-ACCESS  read-create
            STATUS      current
            DESCRIPTION
               "Minimum Data Rate in Low Power state on Downstream direction.
                The minimum net data rate for the bearer channel, coded in
                bit/s, during the low power state (L1 in G.992.2, L2 in
                G.992.3).
                Unit: bits/second
               "
            REFERENCE    "ITU-T G.997.1, paragraph 7.3.2.1"
            ::= { hwXdslTR129ChConfProfileEntry 8 }

              hwXdslTR129ChConfProfMaxDelayDs  OBJECT-TYPE
            SYNTAX Unsigned32 (0..200 | 255)
            UNITS       "milliseconds"
            MAX-ACCESS  read-create
            STATUS      current
            DESCRIPTION
                "If retransmission is not used in downstream direction,this parameter
                 is maximum interleave delay on downstream direction. The maximum
                 one-way interleaving delay introduced by the PMS-TC on
                 Downstream direction.  The XTUs shall choose the S (factor)
                 and D (depth) values such that the actual one-way interleaving
                 delay (hwXdslChStatusActDelay) is as close as possible to,
                 but less than or equal to hwXdslTR129ChConfProfMaxDelayDs.  The
                 delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { hwXdslTR129ChConfProfileEntry 9 }

              hwXdslTR129ChConfProfMaxDelayUs  OBJECT-TYPE
            SYNTAX Unsigned32 (0..200 | 255)
            UNITS       "milliseconds"
            MAX-ACCESS  read-create
            STATUS      current
            DESCRIPTION
                "If retransmission is not used in upstream direction,this parameter
                 is maximum interleave delay on upstream direction. The maximum
                 one-way interleaving delay introduced by the PMS-TC on
                 Upstream direction.  The XTUs shall choose the S (factor) and
                 D (depth) values such that the actual one-way interleaving
                 delay (hwXdslChStatusActDelay) is as close as possible to,
                 but less than or equal to, hwXdslTR129ChConfProfMaxDelayUs.  The
                 delay is coded in ms, with the value 0 indicating no delay bound is being imposed.

                 The delay is coded in ms, with the special values 0, 1 and 255.
                 - The value 0 indicates no delay bound is being imposed.
                 - The value 1 indicates the Fast Latency Path shall be used in the G.992.1 operating mode
                   and S and D shall be selected such that S <= 1 and D = 1 in ITU-T Recs G.992.2, G.992.3
                   and G.992.4 operating modes (G.997.1 special value S1).
                 - The value 255 indicates a delay bound of 1 ms in ITU-T Recs G.993.2 (G.997.1 special value S2).
                 Unit: milliseconds
                "
            REFERENCE    "ITU-T G.997.1, paragraph 7.3.2.2 (Maximum interleaving delay)"
            ::= { hwXdslTR129ChConfProfileEntry 10 }

              hwXdslTR129ChConfProfMinProtectionDs  OBJECT-TYPE
            SYNTAX      HwXdslSymbolProtectionDs
            UNITS       "symbols"
            MAX-ACCESS  read-create
            STATUS      current
            DESCRIPTION
                "If retransmission is not used in downstream direction,this parameter
                 is minimum impulse noise protection for the bearer channel on downstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslTR129ChConfProfileEntry 11 }

              hwXdslTR129ChConfProfMinProtectionUs  OBJECT-TYPE
            SYNTAX      HwXdslSymbolProtectionUs
            UNITS       "symbols"
            MAX-ACCESS  read-create
            STATUS      current
            DESCRIPTION
                "If retransmission is not used in upstream direction,this parameter
                 is minimum impulse noise protection for the bearer channel on upstream
                 direction. The minimum impulse noise protection for the bearer channel,
                 expressed in symbols.  The parameter can take the following
                 values: noProtection (i.e., INP not required), halfSymbol
                 (i.e., INP length is 1/2 symbol) and 1-16 symbols in steps
                 of 1 symbol.
                 Unit: symbols
                "
            REFERENCE    "ITU-T G.997.1, paragraph 7.3.2.3"
            DEFVAL       { noProtection }
            ::= { hwXdslTR129ChConfProfileEntry 12 }


          hwXdslTR129ChConfProfUsDataRateDs  OBJECT-TYPE
            SYNTAX      Unsigned32(0..200000000)
            UNITS       "bits/second"
            MAX-ACCESS  read-create
            STATUS      current
            DESCRIPTION
                "If retransmission is not used in downstream direction,this parameter
                 is data rate threshold up-shift for downstream direction. An
                 'Up-shift rate change' event is triggered when the actual
                 downstream data rate exceeds, by more than the threshold, the
                 data rate at the last entry into Showtime.  The parameter is
                 coded in bit/s.
                 Unit: bits/second
                "
            REFERENCE    "ITU-T G.997.1, paragraph 7.3.2.8"
            ::= { hwXdslTR129ChConfProfileEntry 13 }

              hwXdslTR129ChConfProfDsDataRateDs  OBJECT-TYPE
            SYNTAX      Unsigned32(0..200000000)
            UNITS       "bits/second"
            MAX-ACCESS  read-create
            STATUS      current
            DESCRIPTION
                "If retransmission is not used in downstream direction,this parameter
                 is data rate threshold down-shift for downstream direction.  A
                 'Down-shift rate change' event is triggered when the actual
                 downstream data rate is below the data rate at the last entry
                 into Showtime, by more than the threshold.  The parameter is
                 coded in bit/s.
                 Unit: bits/second
                "
            REFERENCE    "ITU-T G.997.1, paragraph 7.3.2.8"
            ::= { hwXdslTR129ChConfProfileEntry 14 }

              hwXdslTR129ChConfProfUsDataRateUs  OBJECT-TYPE
            SYNTAX      Unsigned32(0..200000000)
            UNITS       "bits/second"
            MAX-ACCESS  read-create
            STATUS      current
            DESCRIPTION
                "If retransmission is not used in upstream direction,this parameter
                 is data rate threshold up shift for upstream direction.  An
                 'Up-shift rate change' event is triggered when the actual
                 upstream data rate exceeds, by more than the threshold, the
                 data rate at the last entry into Showtime.  The parameter is
                 coded in bit/s.
                 Unit: bits/second
                 "
            REFERENCE    "ITU-T G.997.1, paragraph 7.3.2.8"
            ::= { hwXdslTR129ChConfProfileEntry 15 }

              hwXdslTR129ChConfProfDsDataRateUs  OBJECT-TYPE
            SYNTAX      Unsigned32(0..200000000)
            UNITS       "bits/second"
            MAX-ACCESS  read-create
            STATUS      current
            DESCRIPTION
                "If retransmission is not used in upstream direction,this parameter
                 is data rate threshold down-shift for upstream direction.  A
                 'Down-shift rate change' event is triggered when the actual
                 upstream data rate is below the data rate at the last entry
                 into Showtime, by more than the threshold.  The parameter is
                 coded in bit/s.
                 Unit: bits/second
                "
            REFERENCE    "ITU-T G.997.1, paragraph 7.3.2.8"
            ::= { hwXdslTR129ChConfProfileEntry 16 }

              hwXdslTR129ChConfProfDataPathMode  OBJECT-TYPE
            SYNTAX      HwXdslDataPathMode
            MAX-ACCESS  read-create
            STATUS      current
            DESCRIPTION
                "The channel data path mode.
                 Options:
                 1. atm(1)               - ATM
                 2. ptm(2)               - PTM
                 3. both(3)              - ATM and PTM
                 Huawei defined.
                "
            DEFVAL       { both }
            ::= { hwXdslTR129ChConfProfileEntry 17 }

              hwXdslTR129ChConfProfRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwXdslTR129ChConfProfileEntry 18 }

          hwXdslTR129ChConfProfPhyRcontrolDs  OBJECT-TYPE
            SYNTAX      HwXdslPhyRControl
            MAX-ACCESS  read-create
            STATUS      current
            DESCRIPTION
                "To enable or disable the retransmission function."
            DEFVAL       { disable }
            ::= { hwXdslTR129ChConfProfileEntry 19 }

           hwXdslTR129ChConfProfPhyRcontrolUs  OBJECT-TYPE
            SYNTAX      HwXdslPhyRControl
            MAX-ACCESS  read-create
            STATUS      current
            DESCRIPTION
               "To enable or disable the retransmission function."
            DEFVAL       { disable }
            ::= { hwXdslTR129ChConfProfileEntry 20 }

              hwXdslTR129ChConfProfInpMaxDs  OBJECT-TYPE
            SYNTAX      HwXdslSymbolProtectionDs
            MAX-ACCESS  read-create
            STATUS      current
            DESCRIPTION
               "Maximum Impulse Noise Protection on downstream direction."
            ::= { hwXdslTR129ChConfProfileEntry 21 }

              hwXdslTR129ChConfProfInpMaxUs  OBJECT-TYPE
            SYNTAX      HwXdslSymbolProtectionDs
            MAX-ACCESS  read-create
            STATUS      current
            DESCRIPTION
               "Maximum Impulse Noise Protection on upstream direction."
            ::= { hwXdslTR129ChConfProfileEntry 22 }

              hwXdslTR129ChConfProfMinRtxRatioDs  OBJECT-TYPE
            SYNTAX      Unsigned32(0..255)
            MAX-ACCESS  read-create
            STATUS      current
            DESCRIPTION
               "This object is used to config the minimum retransmission band width parameter downstream."
            ::= { hwXdslTR129ChConfProfileEntry 23 }

              hwXdslTR129ChConfProfMinRtxRatioUs  OBJECT-TYPE
            SYNTAX      Unsigned32(0..255)
            MAX-ACCESS  read-create
            STATUS      current
            DESCRIPTION
               "This object is used to config the minimum retransmission band width parameter upstream."
            ::= { hwXdslTR129ChConfProfileEntry 24 }

              hwXdslTR129ChConfProfMinRSoverheadDs  OBJECT-TYPE
            SYNTAX      Unsigned32(0..128)
            MAX-ACCESS  read-create
            STATUS      current
            DESCRIPTION
                "This object is used to config the minimum RSoverhead parameter downstream.."
            ::= { hwXdslTR129ChConfProfileEntry 25 }

              hwXdslTR129ChConfProfMinRSoverheadUs  OBJECT-TYPE
            SYNTAX      Unsigned32(0..128)
            MAX-ACCESS  read-create
            STATUS      current
            DESCRIPTION
               "This object is used to config the minimum RSoverhead parameter upstream.."
            ::= { hwXdslTR129ChConfProfileEntry 26 }

              hwXdslTR129ChConfProfErasureDecoding  OBJECT-TYPE
            SYNTAX      HwXdslProfSwitchType
            MAX-ACCESS  read-create
            STATUS      current
            DESCRIPTION
               "To enable or disable the erasure decoding of a channel.
                Options:
                1. enable(1)
                2. disable(2)
                "
            DEFVAL       { disable }
            ::= { hwXdslTR129ChConfProfileEntry 27 }

              hwXdslTR129ChConfProfMinSosBrDs  OBJECT-TYPE
            SYNTAX      Unsigned32(0..65535)
            UNITS       "Kbps"
            MAX-ACCESS  read-create
            STATUS      current
            DESCRIPTION
               "This parameter specifies the minimum net data rate required for a valid SOS request in
                the downstream direction. The valid range of values is from 0 to 65535 Kbps.
                Unit: Kbps
               "
            REFERENCE    "ITU-T G.997.1, paragraph 7.3.2.1.6"
            ::= { hwXdslTR129ChConfProfileEntry 28 }

              hwXdslTR129ChConfProfMinSosBrUs  OBJECT-TYPE
            SYNTAX      Unsigned32(0..65535)
            UNITS       "Kbps"
            MAX-ACCESS  read-create
            STATUS      current
            DESCRIPTION
               "This parameter specifies the minimum net data rate required for a valid SOS request in
                the upstream direction. The valid range of values is from 0 to 65535 Kbps.
                Unit: Kbps
               "
            REFERENCE    "ITU-T G.997.1, paragraph 7.3.2.1.7"
            ::= { hwXdslTR129ChConfProfileEntry 29 }

              hwXdslTR129ChConfProfMinEtrRtxDs  OBJECT-TYPE
            SYNTAX      Unsigned32(32000..200000000)
            UNITS       "bits/second"
            MAX-ACCESS  read-create
            STATUS      current
            DESCRIPTION
               "If retransmission is used in downstream direction, this parameter specifies the
                minimum expected throughput for the bearer channel.The values range in steps of
                1000 bit/s.
               "
            REFERENCE    "ITU-T G.997.1, paragraph 7.3.2.1.8"
            ::= { hwXdslTR129ChConfProfileEntry 30 }

              hwXdslTR129ChConfProfMinEtrRtxUs  OBJECT-TYPE
            SYNTAX      Unsigned32(32000..200000000)
            UNITS       "bits/second"
            MAX-ACCESS  read-create
            STATUS      current
            DESCRIPTION
               "If retransmission is used in upstream direction, this parameter specifies the
                minimum expected throughput for the bearer channel.The values range in steps of
                1000 bit/s.
               "
            REFERENCE    "ITU-T G.997.1, paragraph 7.3.2.1.8"
            ::= { hwXdslTR129ChConfProfileEntry 31 }

              hwXdslTR129ChConfProfMaxEtrRtxDs  OBJECT-TYPE
            SYNTAX      Unsigned32(32000..200000000)
            UNITS       "bits/second"
            MAX-ACCESS  read-create
            STATUS      current
            DESCRIPTION
               "If retransmission is used in downstream direction, this parameter specifies the
                maximum expected throughput for the bearer channel.The values range in steps of
                1000 bit/s.
               "
            REFERENCE    "ITU-T G.997.1, paragraph 7.3.2.1.9"
            ::= { hwXdslTR129ChConfProfileEntry 32 }

              hwXdslTR129ChConfProfMaxEtrRtxUs  OBJECT-TYPE
            SYNTAX      Unsigned32(32000..200000000)
            UNITS       "bits/second"
            MAX-ACCESS  read-create
            STATUS      current
            DESCRIPTION
               "If retransmission is used in upstream direction, this parameter specifies the
                maximum expected throughput for the bearer channel.The values range in steps of
                1000 bit/s.
               "
            REFERENCE    "ITU-T G.997.1, paragraph 7.3.2.1.9"
            ::= { hwXdslTR129ChConfProfileEntry 33 }

              hwXdslTR129ChConfProfMaxNdrRtxDs  OBJECT-TYPE
            SYNTAX      Unsigned32(32000..200000000)
            UNITS       "bits/second"
            MAX-ACCESS  read-create
            STATUS      current
            DESCRIPTION
               "If retransmission is used in downstream direction, this parameter specifies the
                maximum net data rate for the bearer channel. The values range in steps of 1000 bit/s.
               "
            REFERENCE    "ITU-T G.997.1, paragraph 7.3.2.1.10"
            ::= { hwXdslTR129ChConfProfileEntry 34 }

              hwXdslTR129ChConfProfMaxNdrRtxUs  OBJECT-TYPE
            SYNTAX      Unsigned32(32000..200000000)
            UNITS       "bits/second"
            MAX-ACCESS  read-create
            STATUS      current
            DESCRIPTION
               "If retransmission is used in upstream direction, this parameter specifies the
                maximum net data rate for the bearer channel.The values range in steps of 1000 bit/s.
               "
            REFERENCE    "ITU-T G.997.1, paragraph 7.3.2.1.10"
            ::= { hwXdslTR129ChConfProfileEntry 35 }

              hwXdslTR129ChConfProfMaxDelayRtxDs  OBJECT-TYPE
            SYNTAX      Unsigned32(1..63)
            UNITS       "milliseconds"
            MAX-ACCESS  read-create
            STATUS      current
            DESCRIPTION
               "If retransmission is used in downstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwXdslTR129ChConfProfileEntry 36 }

              hwXdslTR129ChConfProfMaxDelayRtxUs  OBJECT-TYPE
            SYNTAX      Unsigned32(1..63)
            UNITS       "milliseconds"
            MAX-ACCESS  read-create
            STATUS      current
            DESCRIPTION
               "If retransmission is used in upstream direction, this parameter specifies
                the maximum for the instantaneous delay due to the effect of retransmission only
                (see G.998.4 for detailed specification). The delay ranges from 1 to 63 ms by steps of 1 ms.
                Unit: milliseconds
               "
            REFERENCE    "ITU-T G.997.1, paragraph 7.3.2.11"
            ::= { hwXdslTR129ChConfProfileEntry 37 }

              hwXdslTR129ChConfProfMinDelayRtxDs  OBJECT-TYPE
            SYNTAX      Unsigned32(0..63)
            UNITS       "milliseconds"
            MAX-ACCESS  read-create
            STATUS      current
            DESCRIPTION
               "If retransmission is used in downstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwXdslTR129ChConfProfileEntry 38 }

              hwXdslTR129ChConfProfMinDelayRtxUs  OBJECT-TYPE
            SYNTAX      Unsigned32(0..63)
            UNITS       "milliseconds"
            MAX-ACCESS  read-create
            STATUS      current
            DESCRIPTION
               "If retransmission is used in upstream direction, this parameter specifies
                the minimum for the instantaneous delay due to the effect of retransmission only
                (see G.998.4 for detailed specification). The delay ranges from 0 to 63 ms by steps of 1 ms.
                Unit: milliseconds
               "
            REFERENCE    "ITU-T G.997.1, paragraph 7.3.2.12"
            ::= { hwXdslTR129ChConfProfileEntry 39 }

              hwXdslTR129ChConfProfMinInpShineRtxDs  OBJECT-TYPE
            SYNTAX      Unsigned32(0..63)
            UNITS       "symbols"
            MAX-ACCESS  read-create
            STATUS      current
            DESCRIPTION
               "If retransmission is used in downstream direction, this parameter specifies
                the minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwXdslTR129ChConfProfileEntry 40 }

              hwXdslTR129ChConfProfMinInpShineRtxUs  OBJECT-TYPE
            SYNTAX      Unsigned32(0..63)
            UNITS       "symbols"
            MAX-ACCESS  read-create
            STATUS      current
            DESCRIPTION
               "If retransmission is used in upstream direction, this parameter specifies the
                minimum impulse noise protection against SHINE for the bearer channel if it is
                transported over DMT symbols with a subcarrier spacing of 4.3125 kHz. The impulse
                noise protection is expressed in DMT symbols with a subcarrier spacing of 4.3125 kHz
                and can take any integer value from 0 to 63, inclusive.
                Unit: symbols
               "
            REFERENCE    "ITU-T G.997.1, paragraph 7.3.2.13"
            DEFVAL       { 0 }
            ::= { hwXdslTR129ChConfProfileEntry 41 }

              hwXdslTR129ChConfProfMinInp8ShineRtxDs  OBJECT-TYPE
            SYNTAX      Unsigned32(0..127)
            UNITS       "symbols"
            MAX-ACCESS  read-create
            STATUS      current
            DESCRIPTION
               "If retransmission is used in downstream direction, this parameter specifies
                the minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwXdslTR129ChConfProfileEntry 42 }

              hwXdslTR129ChConfProfMinInp8ShineRtxUs  OBJECT-TYPE
            SYNTAX      Unsigned32(0..127)
            UNITS       "symbols"
            MAX-ACCESS  read-create
            STATUS      current
            DESCRIPTION
               "If retransmission is used in upstream direction, this parameter specifies the
                minimum impulse noise protection against SHINE for the bearer channel if it is
                transported over DMT symbols with a subcarrier spacing of 8.625 kHz. The impulse
                noise protection is expressed in DMT symbols with a subcarrier spacing of 8.625 kHz
                and can take any integer value from 0 to 127, inclusive.
                Unit: symbols
               "
            REFERENCE    "ITU-T G.997.1, paragraph 7.3.2.14"
            DEFVAL       { 0 }
            ::= { hwXdslTR129ChConfProfileEntry 43 }

              hwXdslTR129ChConfProfShineRatioRtxDs  OBJECT-TYPE
            SYNTAX      Unsigned32(0..100)
            MAX-ACCESS  read-create
            STATUS      current
            DESCRIPTION
               "If retransmission is used in downstream direction, this parameter specifies
                the SHINE ratio (detailed definition see G.998.4).
                The values range from 0 to 0.100 in increments of 0.001.
               "
            REFERENCE    "ITU-T G.997.1, paragraph 7.3.2.15"
            DEFVAL       { 0 }
            ::= { hwXdslTR129ChConfProfileEntry 44 }

              hwXdslTR129ChConfProfShineRatioRtxUs  OBJECT-TYPE
            SYNTAX      Unsigned32(0..100)
            MAX-ACCESS  read-create
            STATUS      current
            DESCRIPTION
               "If retransmission is used in upstream direction, this parameter specifies
                the SHINE ratio (detailed definition see G.998.4).
                The values range from 0 to 0.100 in increments of 0.001.
               "
            REFERENCE    "ITU-T G.997.1, paragraph 7.3.2.15"
            DEFVAL       { 0 }
            ::= { hwXdslTR129ChConfProfileEntry 45 }

              hwXdslTR129ChConfProfMinInpReinRtxDs  OBJECT-TYPE
            SYNTAX      Unsigned32(0..7)
            MAX-ACCESS  read-create
            STATUS      current
            DESCRIPTION
               "If retransmission is used in downstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwXdslTR129ChConfProfileEntry 46 }

              hwXdslTR129ChConfProfMinInpReinRtxUs  OBJECT-TYPE
            SYNTAX      Unsigned32(0..7)
            MAX-ACCESS  read-create
            STATUS      current
            DESCRIPTION
               "If retransmission is used in upstream direction, this parameter specifies
                the minimum impulse noise protection against REIN for the bearer channel if it is
                transported over DMT symbols with a subcarrier spacing of 4.3125 kHz. The impulse
                noise protection is expressed in DMT symbols with a subcarrier spacing of 4.3125 kHz
                and can take any integer value from 0 to 7, inclusive.
               "
            REFERENCE    "ITU-T G.997.1, paragraph 7.3.2.16"
            DEFVAL       { 0 }
            ::= { hwXdslTR129ChConfProfileEntry 47 }

              hwXdslTR129ChConfProfMinInp8ReinRtxDs  OBJECT-TYPE
            SYNTAX      Unsigned32(0..13)
            MAX-ACCESS  read-create
            STATUS      current
            DESCRIPTION
               "If retransmission is used in downstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwXdslTR129ChConfProfileEntry 48 }

              hwXdslTR129ChConfProfMinInp8ReinRtxUs  OBJECT-TYPE
            SYNTAX      Unsigned32(0..13)
            MAX-ACCESS  read-create
            STATUS      current
            DESCRIPTION
               "If retransmission is used in upstream direction, this parameter specifies
                the minimum impulse noise protection against REIN for the bearer channel if it is
                transported over DMT symbols with a subcarrier spacing of 8.625 kHz. The impulse
                noise protection is expressed in DMT symbols with a subcarrier spacing of 8.625 kHz
                and can take any integer value from 0 to 13, inclusive.
               "
            REFERENCE    "ITU-T G.997.1, paragraph 7.3.2.17"
            DEFVAL       { 0 }
            ::= { hwXdslTR129ChConfProfileEntry 49 }

              hwXdslTR129ChConfProfIatReinRtxDs  OBJECT-TYPE
            SYNTAX      INTEGER
                        {
                         frequency100Hz(0),
                   frequency120Hz(1)
                        }
            MAX-ACCESS  read-create
            STATUS      current
            DESCRIPTION
               "If retransmission is used in downstream direction, this parameter specifies
                the inter-arrival time that shall be assumed for REIN protection.
                Options:
          1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwXdslTR129ChConfProfileEntry 50 }

              hwXdslTR129ChConfProfIatReinRtxUs  OBJECT-TYPE
            SYNTAX      INTEGER
                        {
                         frequency100Hz(0),
                         frequency120Hz(1)
                        }
            MAX-ACCESS  read-create
            STATUS      current
            DESCRIPTION
               "If retransmission is used in upstream direction, this parameter specifies
                the inter-arrival time that shall be assumed for REIN protection.
                Options:
                1. frequency100Hz(0)    - an inter-arrival time derived from a REIN at 100 Hz
                2. frequency120Hz(1)    - an inter-arrival time derived from a REIN at 120 Hz
               "
            REFERENCE    "ITU-T G.997.1, paragraph 7.3.2.18"
            DEFVAL       { frequency100Hz }
            ::= { hwXdslTR129ChConfProfileEntry 51 }

              hwXdslTR129ChConfProfInitPolicy   OBJECT-TYPE
        SYNTAX INTEGER
               {
                   policy0(1),
                   policy1(2),
                   policy2(3)
               }
        MAX-ACCESS read-create
        STATUS current
        DESCRIPTION
            "This parameter indicates which policy shall be applied to
             determine the transceiver configuration parameters at
             initialization. The valid values for CIPOLICY are 0,1 and 2.
             Those policies are defined in the respective recommendations.
             Options:
             1. policy0 (1)      - Policy 0 according to the applicable standard
             2. policy1 (2)      - Policy 1 according to the applicable standard
             3. policy2 (3)      - Policy 2 according to the applicable standard
            "
        REFERENCE
            "ITU-T G.997.1 Amendment 1, paragraph #7.3.2.10 (CIPOLICY)"
        DEFVAL { policy0 }
          ::= { hwXdslTR129ChConfProfileEntry 52 }

        hwXdslTR129ChConfProfMaxDataRateLowPwrDs  OBJECT-TYPE
            SYNTAX      Unsigned32(0..200000000)
            UNITS       "bits/second"
            MAX-ACCESS  read-create
            STATUS      current
            DESCRIPTION
                "Maximum Data Rate in Low Power state on Downstream direction.
                 The maximum net data rate for the bearer channel, coded in
                 bit/s, during the low power state (L1 in G.992.2, L2 in
                 G.992.3).
                 Unit: bits/second
                "
            REFERENCE    "ITU-T G.997.1, paragraph 7.3.2.1"
            ::= { hwXdslTR129ChConfProfileEntry 53 }

        hwXdslTR129ChConfProfL2MinDataRateToL0ActDataRateDs  OBJECT-TYPE
            SYNTAX      Integer32(0..99)
            MAX-ACCESS  read-create
            STATUS      current
            DESCRIPTION
                "The ratio between data rate in low power state and data rate in normal state.
                "
            ::= { hwXdslTR129ChConfProfileEntry 54 }

        hwXdslTR129ChConfProfMaxDelayOctetSplit  OBJECT-TYPE
            SYNTAX Gauge32 (0..100 | 255)
            UNITS "percents"
            MAX-ACCESS read-create
            STATUS current
            DESCRIPTION
                "The line configuration parameter MAXDELAYOCTET-split (MDOSPLIT) defines the percentage of the MAXDELAYOCTET_ext
                 if operating in ITU-T G.998.4 or MAXDELAYOCTET in other cases allocated to the downstream direction. All of the remaining
                 MAXDELAYOCTET or MAXDELAYOCTET_ext shall be allocated for use in the upstream direction.
                 The detailed specification is in ITU-T G.993.2 and ITU-T G.998.4.
                 MDOSPLIT shall be expressed as a percentage, with valid range from 5 percent to 95 percent inclusive, in steps of 1 percent.
                 The value 0% is valid only if the maximum downstream interleaving delay is configured with the special value S1 (see clause 7.3.2.2)
                 and retransmission is disabled in the downstream direction. The value 100% is valid only if the maximum upstream interleaving delay
                 is configured with the special value S1 (see clause 7.3.2.2) and retransmission is disabled in the upstream direction.
                 A special value (255) shall indicate that the VTU-O is allowed to use a vendor discretionary algorithm.
                 NOTE - The special value is introduced to ensure backwards compatibility.
                "
            REFERENCE
                "ITU-T G.997.1, paragraph #7.3.1.14"
            DEFVAL { 255 }
            ::= { hwXdslTR129ChConfProfileEntry 55 }

        hwXdslTR129ChConfProfMaxDelayVar  OBJECT-TYPE
            SYNTAX Gauge32 (1..255)
            UNITS "0.1 milliseconds"
            MAX-ACCESS read-create
            STATUS current
            DESCRIPTION
                "This optional XDSL specific parameter specifies the maximum value
                 for the delay variation allowed in an OLR procedure.
                 It is ranges from 1 to 254 units of 0.1 milliseconds (i.e., 0.1 to 25.4 milliseconds)
                 with the special value 255 which indicates that no delay variation bound is imposed.
                 Unit: 0.1 milliseconds.
                "
            REFERENCE
                "ITU-T G.997.1 Amendment 1, paragraph #7.3.2.9 (DVMAX)"
            DEFVAL { 255 }
            ::= { hwXdslTR129ChConfProfileEntry 56 }

        hwXdslTR129ChConfProfGfastMinEtrDs  OBJECT-TYPE
            SYNTAX      Gauge32 (32000..2000000000)
            UNITS       "bit/s"
            MAX-ACCESS  read-create
            STATUS      current
            DESCRIPTION
               "This parameter specifies the minimum expected throughput for the downstream bearer channel.
                The values range in steps of 1000 bit/s.
                Unit: bit/s
               "
            DEFVAL { 32000 }
            ::= { hwXdslTR129ChConfProfileEntry 57 }

              hwXdslTR129ChConfProfGfastfMaxNdrDs  OBJECT-TYPE
            SYNTAX      Gauge32 (32000..2000000000)
            UNITS       "bit/s"
            MAX-ACCESS  read-create
            STATUS      current
            DESCRIPTION
               "This parameter specifies the G.fast maximum net data rate for the downstream bearer channel.
                The values range in steps of 1000 bit/s.
                Unit: bit/s
               "
            DEFVAL { 2000000000 }
            ::= { hwXdslTR129ChConfProfileEntry 58 }

               hwXdslTR129ChConfProfGfastUsDataRateDs  OBJECT-TYPE
            SYNTAX Gauge32 (0..2000000000)
            UNITS "bit/s"
            MAX-ACCESS read-create
            STATUS current
            DESCRIPTION
                "This parameter is a threshold on the G.fast net data rate up-shift achieved over one or more
                 downstream bearer channel data rate adaptations. An up-shift rate change alarm (event) is triggered
                 when the actual data rate exceeds the data rate at the last entry into showtime by more than the
                 threshold.
                 The data rate threshold is coded in bit/s.
                 Unit: bit/s.
                "
            DEFVAL { 0 }
            ::= { hwXdslTR129ChConfProfileEntry 59 }

              hwXdslTR129ChConfProfGfastDsDataRateDs  OBJECT-TYPE
            SYNTAX Gauge32 (0..2000000000)
            UNITS "bit/s"
            MAX-ACCESS read-create
            STATUS current
            DESCRIPTION
                "This parameter is a threshold on the G.fast net data rate down-shift achieved over one or more
                 bearer channel data rate adaptations. A down-shift rate change alarm (event) is triggered when
                 the actual data rate is below the data rate at the last entry into showtime by more than the
                 threshold.
                 The data rate threshold is coded in bit/s.
                 Unit: bit/s.
                "
            DEFVAL { 0 }
            ::= { hwXdslTR129ChConfProfileEntry 60 }


              hwXdslTR129ChConfProfGfastMinEtrUs  OBJECT-TYPE
            SYNTAX      Gauge32 (32000..2000000000)
            UNITS       "bit/s"
            MAX-ACCESS  read-create
            STATUS      current
            DESCRIPTION
               "This parameter specifies the minimum expected throughput for the upstream bearer channel.
                The values range in steps of 1000 bit/s.
                Unit: bit/s
               "
            DEFVAL { 32000 }
            ::= { hwXdslTR129ChConfProfileEntry 61 }

              hwXdslTR129ChConfProfGfastfMaxNdrUs  OBJECT-TYPE
            SYNTAX      Gauge32 (32000..2000000000)
            UNITS       "bit/s"
            MAX-ACCESS  read-create
            STATUS      current
            DESCRIPTION
               "This parameter specifies the G.fast maximum net data rate for the upstream bearer channel.
                The values range in steps of 1000 bit/s.
                Unit: bit/s
               "
            DEFVAL { 2000000000 }
            ::= { hwXdslTR129ChConfProfileEntry 62 }

              hwXdslTR129ChConfProfGfastUsDataRateUs  OBJECT-TYPE
            SYNTAX Gauge32 (0..2000000000)
            UNITS "bit/s"
            MAX-ACCESS read-create
            STATUS current
            DESCRIPTION
                "This parameter is a threshold on the G.fast net data rate up-shift achieved over one or more
                 upstream bearer channel data rate adaptations. An up-shift rate change alarm (event) is triggered
                 when the actual data rate exceeds the data rate at the last entry into showtime by more than the
                 threshold.
                 The data rate threshold is coded in bit/s.
                 Unit: bit/s.
                "
            DEFVAL { 0 }
            ::= { hwXdslTR129ChConfProfileEntry 63 }

              hwXdslTR129ChConfProfGfastDsDataRateUs  OBJECT-TYPE
            SYNTAX Gauge32 (0..2000000000)
            UNITS "bit/s"
            MAX-ACCESS read-create
            STATUS current
            DESCRIPTION
                "This parameter is a threshold on the G.fast net data rate down-shift achieved over one or more
                 upstream bearer channel data rate adaptations. A down-shift rate change alarm (event) is triggered
                 when the actual data rate is below the data rate at the last entry into showtime by more than the
                 threshold.
                 The data rate threshold is coded in bit/s.
                 Unit: bit/s.
                "
            DEFVAL { 0 }
            ::= { hwXdslTR129ChConfProfileEntry 64 }


              hwXdslTR129ChConfProfGfastMaxDelayRtxDs  OBJECT-TYPE
            SYNTAX Gauge32 (4..252)
            UNITS "0.25 milliseconds"
            MAX-ACCESS read-create
            STATUS current
            DESCRIPTION
                "This parameter specifies the G.fast downstream maximum allowed delay for retransmission.
                 The delay values range from 1 to 63 ms in steps of 0.25 ms, it is 16 ms if the delay is longer than 16 ms.
                 Unit: 0.25 milliseconds.
                "
            REFERENCE
                "ITU-T G.9701, paragraph 11.4.2.4"
            DEFVAL { 40 }
            ::= { hwXdslTR129ChConfProfileEntry 65 }

              hwXdslTR129ChConfProfGfastMaxDelayRtxUs  OBJECT-TYPE
            SYNTAX Gauge32 (4..252)
            UNITS "0.25 milliseconds"
            MAX-ACCESS read-create
            STATUS current
            DESCRIPTION
                "This parameter specifies the G.fast upstream maximum allowed delay for retransmission.
                 The delay values range from 1 to 63 ms in steps of 0.25 ms, it is 16 ms if the delay is longer than 16 ms.
                 Unit: 0.25 milliseconds.
                "
            REFERENCE
                "ITU-T G.9701, paragraph 11.4.2.4"
            DEFVAL { 40 }
            ::= { hwXdslTR129ChConfProfileEntry 66 }

              hwXdslTR129ChConfProfGfastMinInpShineRtxDs  OBJECT-TYPE
            SYNTAX      Gauge32 (0..520)
            UNITS       "symbols"
            MAX-ACCESS  read-create
            STATUS      current
            DESCRIPTION
               "This parameter specifies the G.fast downstream minimum impulse noise protection against SHINE for the bearer channel
                if it is transported over DMT symbols with a subcarrier spacing of 51.75 kHz.
                The impulse noise protection is expressed in DMT symbols with a subcarrier spacing of 51.75 kHz
                and can take any integer value from 0 to 520, inclusive.
                Unit: symbols
               "
            REFERENCE    "ITU-T G.9701, paragraph 11.4.2.6"
            DEFVAL       { 0 }
            ::= { hwXdslTR129ChConfProfileEntry 67 }

              hwXdslTR129ChConfProfGfastMinInpShineRtxUs  OBJECT-TYPE
            SYNTAX      Gauge32 (0..520)
            UNITS       "symbols"
            MAX-ACCESS  read-create
            STATUS      current
            DESCRIPTION
               "This parameter specifies the G.fast upstream minimum impulse noise protection against SHINE for the bearer channel
                if it is transported over DMT symbols with a subcarrier spacing of 51.75 kHz.
                The impulse noise protection is expressed in DMT symbols with a subcarrier spacing of 51.75 kHz
                and can take any integer value from 0 to 520, inclusive.
                Unit: symbols
               "
            REFERENCE    "ITU-T G.9701, paragraph 11.4.2.6"
            DEFVAL       { 0 }
            ::= { hwXdslTR129ChConfProfileEntry 68 }

              hwXdslTR129ChConfProfGfastShineRatioRtxDs  OBJECT-TYPE
            SYNTAX      Gauge32 (0..100)
            MAX-ACCESS  read-create
            STATUS      current
            DESCRIPTION
               "This parameter specifies the G.fast downstream SHINE ratio.
                The values range from 0 to 0.1 in increments of 0.001.
               "
            REFERENCE    "ITU-T G.9701, paragraph 11.4.2.7"
            DEFVAL       { 0 }
            ::= { hwXdslTR129ChConfProfileEntry 69 }

              hwXdslTR129ChConfProfGfastShineRatioRtxUs  OBJECT-TYPE
            SYNTAX      Gauge32 (0..100)
            MAX-ACCESS  read-create
            STATUS      current
            DESCRIPTION
               "This parameter specifies the G.fast upstream SHINE ratio.
                The values range from 0 to 0.1 in increments of 0.001.
               "
            REFERENCE    "ITU-T G.9701, paragraph 11.4.2.7"
            DEFVAL       { 0 }
            ::= { hwXdslTR129ChConfProfileEntry 70 }

              hwXdslTR129ChConfProfGfastMinInpReinRtxDs  OBJECT-TYPE
            SYNTAX      Gauge32 (0..63)
            MAX-ACCESS  read-create
            STATUS      current
            DESCRIPTION
               "This parameter specifies the G.fast downstream minimum impulse noise protection against REIN for the bearer channel
                if it is transported over DMT symbols with a subcarrier spacing of 51.75 kHz.
                The impulse noise protection is expressed in DMT symbols with a subcarrier spacing of 51.75 kHz
                and can take any integer value from 0 to 63, inclusive.
               "
            REFERENCE    "ITU-T G.9701, paragraph 11.4.2.8"
            DEFVAL       { 0 }
            ::= { hwXdslTR129ChConfProfileEntry 71 }

              hwXdslTR129ChConfProfGfastMinInpReinRtxUs  OBJECT-TYPE
            SYNTAX      Gauge32 (0..63)
            MAX-ACCESS  read-create
            STATUS      current
            DESCRIPTION
               "This parameter specifies the G.fast upstream minimum impulse noise protection against REIN for the bearer channel
                if it is transported over DMT symbols with a subcarrier spacing of 51.75 kHz.
                The impulse noise protection is expressed in DMT symbols with a subcarrier spacing of 51.75 kHz
                and can take any integer value from 0 to 63, inclusive.
               "
            REFERENCE    "ITU-T G.9701, paragraph 11.4.2.8"
            DEFVAL       { 0 }
            ::= { hwXdslTR129ChConfProfileEntry 72 }

              hwXdslTR129ChConfProfGfastIatReinRtxDs  OBJECT-TYPE
            SYNTAX      INTEGER
                        {
                         frequency100Hz(0),
                         frequency120Hz(1),
                         frequency300Hz(2),
                         frequency360Hz(3)
                        }
            MAX-ACCESS  read-create
            STATUS      current
            DESCRIPTION
               "This parameter specifies the G.fast downstream inter-arrival time that shall be assumed for REIN protection.
                Options:
                 1. frequency100Hz(0)  - an inter-arrival time derived from a REIN at 100 Hz
                 2. frequency120Hz(1)  - an inter-arrival time derived from a REIN at 120 Hz
                 3. frequency300Hz(2)  - an inter-arrival time derived from a REIN at 300 Hz
                 4. frequency360Hz(3)  - an inter-arrival time derived from a REIN at 360 Hz
               "
            REFERENCE    "ITU-T G.9701, paragraph 11.4.2.9"
            DEFVAL       { frequency100Hz }
            ::= { hwXdslTR129ChConfProfileEntry 73 }

              hwXdslTR129ChConfProfGfastIatReinRtxUs  OBJECT-TYPE
            SYNTAX      INTEGER
                        {
                         frequency100Hz(0),
                         frequency120Hz(1),
                         frequency300Hz(2),
                         frequency360Hz(3)
                        }
            MAX-ACCESS  read-create
            STATUS      current
            DESCRIPTION
               "This parameter specifies the G.fast upstream inter-arrival time that shall be assumed for REIN protection.
                Options:
                 1. frequency100Hz(0)  - an inter-arrival time derived from a REIN at 100 Hz
                 2. frequency120Hz(1)  - an inter-arrival time derived from a REIN at 120 Hz
                 3. frequency300Hz(2)  - an inter-arrival time derived from a REIN at 300 Hz
                 4. frequency360Hz(3)  - an inter-arrival time derived from a REIN at 360 Hz
               "
            REFERENCE    "ITU-T G.9701, paragraph 11.4.2.9"
            DEFVAL       { frequency100Hz }
            ::= { hwXdslTR129ChConfProfileEntry 74 }

              hwXdslTR129ChConfProfGfastMinRNRatioRtxDs  OBJECT-TYPE
            SYNTAX      Gauge32 (0..8)
            MAX-ACCESS  read-create
            STATUS      current
            DESCRIPTION
               "This parameter specifies the G.fast downstream minimum Reed-Solomon RFEC/NFEC ratio.
                The ratio is computed as the number of redundancy bytes (RFEC) divided by the total
                number of bytes (NFEC) in each Reed-Solomon codeword.
                The values range from 0 to 8/32 in steps of 1/32.
                Unit: 1/32
               "
            REFERENCE    "ITU-T G.9701, paragraph 11.4.2.11"
            DEFVAL       { 0 }
            ::= { hwXdslTR129ChConfProfileEntry 75 }

              hwXdslTR129ChConfProfGfastMinRNRatioRtxUs  OBJECT-TYPE
            SYNTAX      Gauge32 (0..8)
            MAX-ACCESS  read-create
            STATUS      current
            DESCRIPTION
               "This parameter specifies the G.fast upstream minimum Reed-Solomon RFEC/NFEC ratio.
                The ratio is computed as the number of redundancy bytes (RFEC) divided by the total
                number of bytes (NFEC) in each Reed-Solomon codeword.
                The values range from 0 to 8/32 in steps of 1/32.
                Unit: 1/32
               "
            REFERENCE    "ITU-T G.9701, paragraph 11.4.2.11"
            DEFVAL       { 0 }
            ::= { hwXdslTR129ChConfProfileEntry 76 }

              hwXdslTR129ChConfProfGfastLowANDEFTRThresholdDs  OBJECT-TYPE
            SYNTAX Gauge32 (0..2000000000)
            UNITS "bit/s"
            MAX-ACCESS read-create
            STATUS current
            DESCRIPTION
                "Defines the value of the low all-NOI data error-free throughput rate threshold.
                 The data rate threshold is coded in bit/s.
                 Unit: bit/s.
                "
            DEFVAL { 0 }
            ::= { hwXdslTR129ChConfProfileEntry 77 }

              hwXdslTR129ChConfProfGfastLowANDEFTRThresholdUs  OBJECT-TYPE
            SYNTAX Gauge32 (0..2000000000)
            UNITS "bit/s"
            MAX-ACCESS read-create
            STATUS current
            DESCRIPTION
                "Defines the value of the low all-NOI data error-free throughput rate threshold.
                 The data rate threshold is coded in bit/s.
                 Unit: bit/s.
                "
            DEFVAL { 0 }
            ::= { hwXdslTR129ChConfProfileEntry 78 }




        --  end of hwXdslTR129ChConfProfileTable


        --        hwXdslLineAlarmConfTemplateTable
        hwXdslLineAlarmConfTemplateTable  OBJECT-TYPE
            SYNTAX      SEQUENCE  OF  HwXdslLineAlarmConfTemplateEntry
            MAX-ACCESS  not-accessible
            STATUS      current
            DESCRIPTION
               "The table hwXdslLineAlarmConfTemplateTable contains XDSL line
                alarm configuration template.
                The index of this table is hwXdslLAlarmConfTempTemplateName.
                A default template with an index of 'DEFVAL' will
                always exist and its parameters will be set to vendor
                specific values, unless otherwise specified in this
                document.
               "
            ::= { hwXdslProfileAlarmConf 1 }

        hwXdslLineAlarmConfTemplateEntry  OBJECT-TYPE
            SYNTAX      HwXdslLineAlarmConfTemplateEntry
            MAX-ACCESS  not-accessible
            STATUS      current
            DESCRIPTION
                "The table hwXdslLineAlarmConfTemplateTable contains XDSL line
                 alarm configuration template.
                 The index of this entry is hwXdslLAlarmConfTempTemplateName.
                 A default template with an index of 'DEFVAL' will
                 always exist and its parameters will be set to vendor
                 specific values, unless otherwise specified in this
                 document.
                "
            INDEX  { IMPLIED hwXdslLAlarmConfTempTemplateName }
            ::= { hwXdslLineAlarmConfTemplateTable 1 }

        HwXdslLineAlarmConfTemplateEntry  ::=
            SEQUENCE {
              hwXdslLAlarmConfTempTemplateName      OCTET STRING,
              hwXdslLAlarmConfTempLineProfile       OCTET STRING,
              hwXdslLAlarmConfTempChan1ConfProfile  OCTET STRING,
              hwXdslLAlarmConfTempChan2ConfProfile  OCTET STRING,
              hwXdslLAlarmConfTempChan3ConfProfile  OCTET STRING,
              hwXdslLAlarmConfTempChan4ConfProfile  OCTET STRING,
              hwXdslLAlarmConfTempRowStatus         RowStatus
            }

        hwXdslLAlarmConfTempTemplateName  OBJECT-TYPE
            SYNTAX      OCTET STRING (SIZE(1..32))
            MAX-ACCESS  not-accessible
            STATUS      current
            DESCRIPTION
                "This object identifies a row in this table."
            ::= { hwXdslLineAlarmConfTemplateEntry 1 }

        hwXdslLAlarmConfTempLineProfile  OBJECT-TYPE
            SYNTAX      OCTET STRING (SIZE(1..32))
            MAX-ACCESS  read-create
            STATUS      current
            DESCRIPTION
                "The value of this object identifies the row in the XDSL Line
                 Thresholds Configuration Profile Table
                 (hwXdslLineAlarmConfProfileTable) that applies to this XDSL2
                 line.
                "
            REFERENCE    "DSL Forum TR-90, paragraph 5.4.1"
            DEFVAL       { "DEFVAL" }
            ::= { hwXdslLineAlarmConfTemplateEntry 2 }

        hwXdslLAlarmConfTempChan1ConfProfile  OBJECT-TYPE
            SYNTAX      OCTET STRING (SIZE(1..32))
            MAX-ACCESS  read-create
            STATUS      current
            DESCRIPTION
                "The value of this object identifies the row in the XDSL2
                 Channel Thresholds Configuration Profile Table
                 (hwXdslChAlarmConfProfileTable) that applies for XDSL
                 bearer channel #1.  The channel profile name specified here
                 must match the name of an existing row in the
                 hwXdslChAlarmConfProfileTable table.
                "
            REFERENCE    "DSL Forum TR-90, paragraph 5.4.1"
            DEFVAL       { "DEFVAL" }
            ::= { hwXdslLineAlarmConfTemplateEntry 3 }

        hwXdslLAlarmConfTempChan2ConfProfile  OBJECT-TYPE
            SYNTAX      OCTET STRING (SIZE(0..32))
            MAX-ACCESS  read-create
            STATUS      current
            DESCRIPTION
                "The value of this object identifies the row in the XDSL2
                 Channel Thresholds Configuration Profile Table
                 (hwXdslChAlarmConfProfileTable) that applies for XDSL
                 bearer channel #2.  The channel profile name specified here
                 must match the name of an existing row in the
                 hwXdslChAlarmConfProfileTable table.  If the channel is unused,
                 then the object is set to a zero length string.
                "
            REFERENCE    "DSL Forum TR-90, paragraph 5.4.1"
            ::= { hwXdslLineAlarmConfTemplateEntry 4 }

        hwXdslLAlarmConfTempChan3ConfProfile  OBJECT-TYPE
            SYNTAX      OCTET STRING (SIZE(0..32))
            MAX-ACCESS  read-create
            STATUS      current
            DESCRIPTION
                "The value of this object identifies the row in the XDSL2
                 Channel Thresholds Configuration Profile Table
                 (hwXdslChAlarmConfProfileTable) that applies for XDSL
                 bearer channel #3.  The channel profile name specified here
                 must match the name of an existing row in the
                 hwXdslChAlarmConfProfileTable table.
                 This object may be set to a non-zero length string only if
                 hwXdslLAlarmConfTempChan2ConfProfile contains a non-zero
                 length string.
                "
            REFERENCE    "DSL Forum TR-90, paragraph 5.4.1"
            ::= { hwXdslLineAlarmConfTemplateEntry 5 }

        hwXdslLAlarmConfTempChan4ConfProfile  OBJECT-TYPE
            SYNTAX      OCTET STRING (SIZE(0..32))
            MAX-ACCESS  read-create
            STATUS      current
            DESCRIPTION
                "The value of this object identifies the row in the XDSL2
                 Channel Thresholds Configuration Profile Table
                 (hwXdslChAlarmConfProfileTable) that applies for XDSL
                 bearer channel #4.  The channel profile name specified here
                 must match the name of an existing row in the
                 hwXdslChAlarmConfProfileTable table.
                 This object may be set to a non-zero length string only if
                 hwXdslLAlarmConfTempChan3ConfProfile contains a non-zero
                 length string.
                "
            REFERENCE    "DSL Forum TR-90, paragraph 5.4.1"
            ::= { hwXdslLineAlarmConfTemplateEntry 6 }

        hwXdslLAlarmConfTempRowStatus  OBJECT-TYPE
            SYNTAX      RowStatus
            MAX-ACCESS  read-create
            STATUS      current
            DESCRIPTION
                "This object is used to create a new row or to modify or
                delete an existing row in this table.

                A profile is activated by setting this object to 'active'.
                When 'active' is set, the system will validate the profile.

                Before a profile can be deleted or taken out of service
                (by setting this object to 'destroy' or 'outOfService'),
                it must be not referenced from all associated
                lines.
               "
            ::= { hwXdslLineAlarmConfTemplateEntry 7 }

          --      hwXdslLineAlarmConfProfileTable

        hwXdslLineAlarmConfProfileTable  OBJECT-TYPE
            SYNTAX      SEQUENCE  OF  HwXdslLineAlarmConfProfileEntry
            MAX-ACCESS  not-accessible
            STATUS      current
            DESCRIPTION
                "The table hwXdslLineAlarmConfProfileTable contains XDSL2
                 line PM thresholds profiles. The index of this table is
                 hwXdslLineAlarmConfProfileName.
                 A default profile with an index of 'DEFVAL' will
                 always exist and its parameters will be set to vendor
                 specific values, unless otherwise specified in this
                 document.
                "
            ::= { hwXdslProfileAlarmConf 2 }

        hwXdslLineAlarmConfProfileEntry  OBJECT-TYPE
            SYNTAX      HwXdslLineAlarmConfProfileEntry
            MAX-ACCESS  not-accessible
            STATUS      current
            DESCRIPTION
                "The table hwXdslLineAlarmConfProfileTable contains XDSL2
                 line PM thresholds profiles.
                 The index of this entry is hwXdslLineAlarmConfProfileName.
                 A default profile with an index of 'DEFVAL' will
                 always exist and its parameters will be set to vendor
                 specific values, unless otherwise specified in this
                 document.
                "
            INDEX  { IMPLIED hwXdslLineAlarmConfProfileName }
            ::= { hwXdslLineAlarmConfProfileTable 1 }

        HwXdslLineAlarmConfProfileEntry ::=
             SEQUENCE {
             hwXdslLineAlarmConfProfileName                      OCTET STRING,
             hwXdslLineAlarmConfProfileXtucThresh15MinFecs
                                                  HCPerfIntervalThreshold,
             hwXdslLineAlarmConfProfileXtucThresh15MinEs
                                                  HCPerfIntervalThreshold,
             hwXdslLineAlarmConfProfileXtucThresh15MinSes
                                                   HCPerfIntervalThreshold,
             hwXdslLineAlarmConfProfileXtucThresh15MinLoss
                                                   HCPerfIntervalThreshold,
             hwXdslLineAlarmConfProfileXtucThresh15MinUas
                                                   HCPerfIntervalThreshold,
             hwXdslLineAlarmConfProfileXturThresh15MinFecs
                                                   HCPerfIntervalThreshold,
             hwXdslLineAlarmConfProfileXturThresh15MinEs
                                                   HCPerfIntervalThreshold,
             hwXdslLineAlarmConfProfileXturThresh15MinSes
                                                   HCPerfIntervalThreshold,
             hwXdslLineAlarmConfProfileXturThresh15MinLoss
                                                   HCPerfIntervalThreshold,
             hwXdslLineAlarmConfProfileXturThresh15MinUas
                                                   HCPerfIntervalThreshold,
             hwXdslLineAlarmConfProfileThresh15MinFailedFullInt   Unsigned32,
             hwXdslLineAlarmConfProfileThresh15MinFailedShrtInt   Unsigned32,
             hwXdslLineAlarmConfProfileRowStatus                  RowStatus,
             hwXdslLineAlarmConfProfileThresh15MinFullInt         Unsigned32,
             hwXdslLineAlarmConfProfileXtucThresh15MinLeftrs      HCPerfIntervalThreshold,
             hwXdslLineAlarmConfProfileXturThresh15MinLeftrs      HCPerfIntervalThreshold,
             hwXdslLineAlarmConfProfileDyingGaspAlarmSwitch     INTEGER,
             hwXdslLineAlarmConfProfileActiveFailAlarmSwitch    INTEGER,
             hwXdslLineAlarmConfProfileRateChangeAlarmSwitch    INTEGER,
             hwXdslLineAlarmConfProfileLegacyCpeAlarmSwitch     INTEGER,
             hwXdslLineAlarmConfProfileVictAbnormalVariationAlarmSwitch INTEGER,
             hwXdslLineAlarmConfProfileDistAbnormalVariationAlarmSwitch INTEGER,
             hwXdslLineAlarmConfProfileReceivedESAbnormalAlarmSwitch    INTEGER,
             hwXdslLineAlarmConfProfileNonVectoringCPEActivatedAlarmSwitch INTEGER,
             hwXdslLineAlarmConfProfileFreqRetrainReachThresholdAlarmSwitch INTEGER,
             hwXdslLineAlarmConfProfilePSConfigAbnormalAlarmSwitch INTEGER
             }

        hwXdslLineAlarmConfProfileName  OBJECT-TYPE
            SYNTAX      OCTET STRING (SIZE(1..32))
            MAX-ACCESS  not-accessible
            STATUS      current
            DESCRIPTION
                "This object identifies a row in this table."
            ::= { hwXdslLineAlarmConfProfileEntry 1 }

        hwXdslLineAlarmConfProfileXtucThresh15MinFecs  OBJECT-TYPE
            SYNTAX      HCPerfIntervalThreshold
            UNITS       "seconds"
            MAX-ACCESS  read-create
            STATUS      current
            DESCRIPTION
                "A threshold for the hwXdslPMLCurr15MFecs counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslLineAlarmConfProfileEntry 2 }

        hwXdslLineAlarmConfProfileXtucThresh15MinEs  OBJECT-TYPE
            SYNTAX      HCPerfIntervalThreshold
            UNITS       "seconds"
            MAX-ACCESS  read-create
            STATUS      current
            DESCRIPTION
                "A threshold for the hwXdslPMLCurr15MEs counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslLineAlarmConfProfileEntry 3 }

        hwXdslLineAlarmConfProfileXtucThresh15MinSes  OBJECT-TYPE
            SYNTAX      HCPerfIntervalThreshold
            UNITS       "seconds"
            MAX-ACCESS  read-create
            STATUS      current
            DESCRIPTION
                "A threshold for the hwXdslPMLCurr15MSes counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslLineAlarmConfProfileEntry 4 }

        hwXdslLineAlarmConfProfileXtucThresh15MinLoss  OBJECT-TYPE
            SYNTAX      HCPerfIntervalThreshold
            UNITS       "seconds"
            MAX-ACCESS  read-create
            STATUS      current
            DESCRIPTION
                "A threshold for the hwXdslPMLCurr15MLoss counter,
                 when hwXdslPMLCurrUnit is XTUC {1}.
                 The value 0 means that no threshold is specified for the
                 associated counter.
                 Unit: seconds
                "
            REFERENCE    "ITU-T G.997.1, paragraph 7.3.1"
            DEFVAL       { 0 }
              ::= { hwXdslLineAlarmConfProfileEntry 5 }

        hwXdslLineAlarmConfProfileXtucThresh15MinUas  OBJECT-TYPE
            SYNTAX      HCPerfIntervalThreshold
            UNITS       "seconds"
            MAX-ACCESS  read-create
            STATUS      current
            DESCRIPTION
                "A threshold for the hwXdslPMLCurr15MUas counter,
                 when hwXdslPMLCurrUnit is XTUC {1}.
                 The value 0 means that no threshold is specified for the
                 associated counter.
                 Unit: seconds
                "
            REFERENCE    "ITU-T G.997.1, paragraph 7.3.1"
            DEFVAL       { 0 }
             ::= { hwXdslLineAlarmConfProfileEntry 6 }

        hwXdslLineAlarmConfProfileXturThresh15MinFecs  OBJECT-TYPE
            SYNTAX      HCPerfIntervalThreshold
            UNITS       "seconds"
            MAX-ACCESS  read-create
            STATUS      current
            DESCRIPTION
                "A threshold for the hwXdslPMLCurr15MFecs counter,
                 when hwXdslPMLCurrUnit is XTUR {2}.
                 The value 0 means that no threshold is specified for the
                 associated counter.
                 Unit: seconds
                "
            REFERENCE    "ITU-T G.997.1, paragraph 7.3.1"
            DEFVAL       { 0 }
              ::= { hwXdslLineAlarmConfProfileEntry 7 }

        hwXdslLineAlarmConfProfileXturThresh15MinEs  OBJECT-TYPE
            SYNTAX      HCPerfIntervalThreshold
            UNITS       "seconds"
            MAX-ACCESS  read-create
            STATUS      current
            DESCRIPTION
                "A threshold for the hwXdslPMLCurr15MEs counter,
                 when hwXdslPMLCurrUnit is XTUR {2}.
                 The value 0 means that no threshold is specified for the
                 associated counter.
                 Unit: seconds
                "
            REFERENCE    "ITU-T G.997.1, paragraph 7.3.1"
            DEFVAL       { 0 }
            ::= { hwXdslLineAlarmConfProfileEntry 8 }

        hwXdslLineAlarmConfProfileXturThresh15MinSes  OBJECT-TYPE
            SYNTAX      HCPerfIntervalThreshold
            UNITS       "seconds"
            MAX-ACCESS  read-create
            STATUS      current
            DESCRIPTION
                "A threshold for the hwXdslPMLCurr15MSes counter,
                 when hwXdslPMLCurrUnit is XTUR {2}.
                 The value 0 means that no threshold is specified for the
                 associated counter.
                 Unit: seconds
                "
            REFERENCE    "ITU-T G.997.1, paragraph 7.3.1"
            DEFVAL       { 0 }
            ::= { hwXdslLineAlarmConfProfileEntry 9 }

        hwXdslLineAlarmConfProfileXturThresh15MinLoss  OBJECT-TYPE
            SYNTAX      HCPerfIntervalThreshold
            UNITS       "seconds"
            MAX-ACCESS  read-create
            STATUS      current
            DESCRIPTION
               "A threshold for the hwXdslPMLCurr15MLoss counter,
                when hwXdslPMLCurrUnit is XTUR {2}.
                The value 0 means that no threshold is specified for the
                associated counter.
                Unit: seconds
               "
            REFERENCE    "ITU-T G.997.1, paragraph 7.3.1"
            DEFVAL       { 0 }
            ::= { hwXdslLineAlarmConfProfileEntry 10 }

        hwXdslLineAlarmConfProfileXturThresh15MinUas  OBJECT-TYPE
            SYNTAX      HCPerfIntervalThreshold
            UNITS       "seconds"
            MAX-ACCESS  read-create
            STATUS      current
            DESCRIPTION
               "A threshold for the hwXdslPMLCurr15MUas counter,
                when hwXdslPMLCurrUnit is XTUR {2}.
                The value 0 means that no threshold is specified for the
                associated counter.
                Unit: seconds
               "
            REFERENCE    "ITU-T G.997.1, paragraph 7.3.1"
            DEFVAL       { 0 }
            ::= { hwXdslLineAlarmConfProfileEntry 11 }

        hwXdslLineAlarmConfProfileThresh15MinFailedFullInt  OBJECT-TYPE
            SYNTAX      Unsigned32
            MAX-ACCESS  read-create
            STATUS      current
            DESCRIPTION
               "A threshold for the hwXdslPMLCurrInit15MfailedFullInits
                counter.
                The value 0 means that no threshold is specified for the
                associated counter.
               "
            REFERENCE    "ITU-T G.997.1, paragraph 7.3.1"
            DEFVAL       { 0 }
            ::= { hwXdslLineAlarmConfProfileEntry 12 }

        hwXdslLineAlarmConfProfileThresh15MinFailedShrtInt  OBJECT-TYPE
            SYNTAX      Unsigned32
            MAX-ACCESS  read-create
            STATUS      current
            DESCRIPTION
               "A threshold for the hwXdslPMLCurrInit15MFailedShortInits
                counter.
                The value 0 means that no threshold is specified for the
                associated counter.
               "
            REFERENCE    "ITU-T G.997.1, paragraph 7.3.1"
            DEFVAL       { 0 }
            ::= { hwXdslLineAlarmConfProfileEntry 13 }

        hwXdslLineAlarmConfProfileRowStatus  OBJECT-TYPE
            SYNTAX      RowStatus
            MAX-ACCESS  read-create
            STATUS      current
            DESCRIPTION
               "This object is used to create a new row or to modify or
                delete an existing row in this table.

                A profile is activated by setting this object to 'active'.
                When 'active' is set, the system will validate the profile.

                Before a profile can be deleted or taken out of service
                (by setting this object to 'destroy' or 'outOfService'),
                it must be not referenced from all associated
                templates.
               "
            ::= { hwXdslLineAlarmConfProfileEntry 14 }

        hwXdslLineAlarmConfProfileThresh15MinFullInt  OBJECT-TYPE
            SYNTAX      Unsigned32
            MAX-ACCESS  read-create
            STATUS      current
            DESCRIPTION
               "A threshold for the hwXdslPMLCurrInit15MFullInits
                counter.
                The value 0 means that no threshold is specified for the
                associated counter.
               "
            REFERENCE    "ITU-T G.997.1, paragraph 7.3.1"
            DEFVAL       { 0 }
              ::= { hwXdslLineAlarmConfProfileEntry 15 }

        hwXdslLineAlarmConfProfileXtucThresh15MinLeftrs  OBJECT-TYPE
            SYNTAX      HCPerfIntervalThreshold
            UNITS       "seconds"
            MAX-ACCESS  read-create
            STATUS      current
            DESCRIPTION
               "A threshold for the hwXdslPMLCurr15MLeftrs counter,
                when hwXdslPMLCurrUnit is XTUC {1}.
                The value 0 means that no threshold is specified for the
                associated counter.
                Unit: seconds
               "
            REFERENCE    "ITU-T G.997.1, paragraph 7.3.1"
            DEFVAL       { 0 }
            ::= { hwXdslLineAlarmConfProfileEntry 16 }

        hwXdslLineAlarmConfProfileXturThresh15MinLeftrs  OBJECT-TYPE
            SYNTAX      HCPerfIntervalThreshold
            UNITS       "seconds"
            MAX-ACCESS  read-create
            STATUS      current
            DESCRIPTION
               "A threshold for the hwXdslPMLCurr15MLeftrs counter,
                when hwXdslPMLCurrUnit is XTUR {2}.
                The value 0 means that no threshold is specified for the
                associated counter.
                Unit: seconds
               "
            REFERENCE    "ITU-T G.997.1, paragraph 7.3.1"
            DEFVAL       { 0 }
            ::= { hwXdslLineAlarmConfProfileEntry 17 }

         hwXdslLineAlarmConfProfileDyingGaspAlarmSwitch OBJECT-TYPE
            SYNTAX INTEGER {
                               enable (1),
                               disable (2)
                           }
            MAX-ACCESS  read-create
            STATUS      current
            DESCRIPTION
                       "This object enable/disable the report of LOSS-OF-POWER
                        alarm in a XDSL line.
                        Options:
                        1. enable(1)  - The report of LOSS-OF-POWER alarm in a VDSL line is enabled
                        2. disable(2) - The report of LOSS-OF-POWER alarm in a VDSL line is disabled
                       "
            DEFVAL       { enable }
            ::= { hwXdslLineAlarmConfProfileEntry 18 }

        hwXdslLineAlarmConfProfileActiveFailAlarmSwitch OBJECT-TYPE
            SYNTAX INTEGER {
                               enable (1),
                               disable (2)
                           }
            MAX-ACCESS  read-create
            STATUS      current
            DESCRIPTION
                       "This object enable/disable the active fail alarm switch.
                        Options:
                        1. enable(1)  - The active fail alarm switch is enabled
                        2. disable(2) - The active fail alarm switch is disabled
                       "
            DEFVAL       { enable }
            ::= { hwXdslLineAlarmConfProfileEntry 19 }

        hwXdslLineAlarmConfProfileRateChangeAlarmSwitch OBJECT-TYPE
            SYNTAX INTEGER {
                               enable (1),
                               disable (2)
                           }
            MAX-ACCESS  read-create
            STATUS      current
            DESCRIPTION
                       "This object enable/disable the active rate change alarm switch.
                        Options:
                        1. enable(1)  - The active rate change alarm switch is enabled
                        2. disable(2) - The active rate change alarm switch is disabled
                       "
            DEFVAL       { enable }
            ::= { hwXdslLineAlarmConfProfileEntry 20 }

        hwXdslLineAlarmConfProfileLegacyCpeAlarmSwitch OBJECT-TYPE
            SYNTAX INTEGER {
                               enable (1),
                               disable (2)
                           }
            MAX-ACCESS  read-create
            STATUS      current
            DESCRIPTION
                       "This object enable/disable the legacy cpe alarm switch.
                        Options:
                        1. enable(1)  - The legacy cpe alarm switch is enabled
                        2. disable(2) - The legacy cpe alarm switch is disabled
                       "
            DEFVAL       { enable }
            ::= { hwXdslLineAlarmConfProfileEntry 21 }

        hwXdslLineAlarmConfProfileVictAbnormalVariationAlarmSwitch OBJECT-TYPE
            SYNTAX INTEGER {
                               enable (1),
                               disable (2)
                           }
            MAX-ACCESS  read-create
            STATUS      current
            DESCRIPTION
                       "This object enable/disable alarm switch that the port
                        receives abnormal crosstalk.
                        Options:
                        1. enable(1)  - The alarm switch that the port receives
                                        abnormal crosstalk is enabled
                        2. disable(2) - The alarm switch that the port receives
                                        abnormal crosstalk is disabled
                       "
            DEFVAL       { enable }
            ::= { hwXdslLineAlarmConfProfileEntry 22 }

        hwXdslLineAlarmConfProfileDistAbnormalVariationAlarmSwitch OBJECT-TYPE
            SYNTAX INTEGER {
                               enable (1),
                               disable (2)
                           }
            MAX-ACCESS  read-create
            STATUS      current
            DESCRIPTION
                       "This object enable/disable the alarm switch that the port
                        causes abnormal crosstalk.
                        Options:
                        1. enable(1)  - The alarm switch that the port causes
                                        abnormal crosstalk is enabled
                        2. disable(2) - The alarm switch that the port causes
                                        abnormal crosstalk is disabled
                       "
            DEFVAL       { enable }
            ::= { hwXdslLineAlarmConfProfileEntry 23 }

        hwXdslLineAlarmConfProfileReceivedESAbnormalAlarmSwitch OBJECT-TYPE
            SYNTAX INTEGER {
                               enable (1),
                               disable (2)
                           }
            MAX-ACCESS  read-create
            STATUS      current
            DESCRIPTION
                       "This object enable/disable the alarm switch that The port
                        receives abnormal error sample messages.
                        Options:
                        1. enable(1)  - The alarm switch that the port receives
                                        abnormal error sample messages is enabled
                        2. disable(2) - The alarm switch that the port receives
                                        abnormal error sample messages is disabled
                       "
            DEFVAL       { enable }
            ::= { hwXdslLineAlarmConfProfileEntry 24 }

        hwXdslLineAlarmConfProfileNonVectoringCPEActivatedAlarmSwitch OBJECT-TYPE
            SYNTAX INTEGER {
                               enable (1),
                               disable (2)
                           }
            MAX-ACCESS  read-create
            STATUS      current
            DESCRIPTION
                       "This object enable/disable the alarm switch that the port is
                        activated in none-vectoring mode.
                        Options:
                        1. enable(1)  - The alarm switch that the port is activated
                                        in none-vectoring mode is enabled
                        2. disable(2) - The alarm switch that the port is activated
                                        in none-vectoring mode is disabled
                       "
            DEFVAL       { enable }
            ::= { hwXdslLineAlarmConfProfileEntry 25 }

        hwXdslLineAlarmConfProfileFreqRetrainReachThresholdAlarmSwitch OBJECT-TYPE
            SYNTAX INTEGER {
                               enable (1),
                               disable (2)
                           }
            MAX-ACCESS  read-create
            STATUS      current
            DESCRIPTION
                       "This object enable/disable the alarm switch that the port
                        frequently retrain times in 15 minutes reach the threshold.
                        Options:
                        1. enable(1)  - The alarm switch that the port frequently retrain
                                        times in 15 minutes reach the threshold is enabled
                        2. disable(2) - The alarm switch that the port frequently retrain
                                        times in 15 minutes reach the threshold is disabled
                       "
            DEFVAL       { enable }
            ::= { hwXdslLineAlarmConfProfileEntry 26 }

        hwXdslLineAlarmConfProfilePSConfigAbnormalAlarmSwitch OBJECT-TYPE
            SYNTAX INTEGER {
                               enable (1),
                               disable (2)
                           }
            MAX-ACCESS  read-create
            STATUS      current
            DESCRIPTION
                       "This object enable/disable the pilot sequence configuration abnormal alarm switch.
                        Options:
                        1. enable(1)  - The pilot sequence configuration abnormal alarm switch is enabled
                        2. disable(2) - The pilot sequence configuration abnormal alarm switch is disabled
                       "
            DEFVAL       { enable }
            ::= { hwXdslLineAlarmConfProfileEntry 27 }

          --      hwXdslChAlarmConfProfileTable

        hwXdslChAlarmConfProfileTable  OBJECT-TYPE
            SYNTAX      SEQUENCE  OF  HwXdslChAlarmConfProfileEntry
            MAX-ACCESS  not-accessible
            STATUS      current
            DESCRIPTION
                "The table hwXdslChAlarmConfProfileTable contains XDSL2
                  channel PM thresholds profiles.
                  The index of this table is hwXdslChAlarmConfProfileName.
                  A default profile with an index of 'DEFVAL' will
                  always exist and its parameters will be set to vendor-specific
                  values, unless otherwise specified in this document.
                 "
            ::= { hwXdslProfileAlarmConf 3 }

        hwXdslChAlarmConfProfileEntry  OBJECT-TYPE
            SYNTAX      HwXdslChAlarmConfProfileEntry
            MAX-ACCESS  not-accessible
            STATUS      current
            DESCRIPTION
                "The table hwXdslChAlarmConfProfileTable contains XDSL2
                 channel PM thresholds profiles.
                 The index of this entry is hwXdslChAlarmConfProfileName.
                 A default profile with an index of 'DEFVAL' will
                 always exist and its parameters will be set to vendor-specific
                 values, unless otherwise specified in this document.
                "
            INDEX  { IMPLIED hwXdslChAlarmConfProfileName }
            ::= { hwXdslChAlarmConfProfileTable 1 }

        HwXdslChAlarmConfProfileEntry ::=
             SEQUENCE {
             hwXdslChAlarmConfProfileName                             OCTET STRING,
             hwXdslChAlarmConfProfileXtucThresh15MinCodingViolations  Unsigned32,
             hwXdslChAlarmConfProfileXtucThresh15MinCorrected         Unsigned32,
             hwXdslChAlarmConfProfileXturThresh15MinCodingViolations  Unsigned32,
             hwXdslChAlarmConfProfileXturThresh15MinCorrected         Unsigned32,
             hwXdslChAlarmConfProfileMonitoringRateDs              Unsigned32,
             hwXdslChAlarmConfProfileMonitoringRateUs        Unsigned32,
             hwXdslChAlarmConfProfileRowStatus                        RowStatus
             }

        hwXdslChAlarmConfProfileName  OBJECT-TYPE
            SYNTAX      OCTET STRING (SIZE(1..32))
            MAX-ACCESS  not-accessible
            STATUS      current
            DESCRIPTION
               "This object identifies a row in this table."
            ::= { hwXdslChAlarmConfProfileEntry 1 }

        hwXdslChAlarmConfProfileXtucThresh15MinCodingViolations OBJECT-TYPE
            SYNTAX      Unsigned32
            MAX-ACCESS  read-create
            STATUS      current
            DESCRIPTION
               "A threshold for the hwXdslPMChCurr15MCodingViolations
                counter, when hwXdslPMChCurrUnit is XTUC {1}.
                The value 0 means that no threshold is specified for the
                associated counter.
               "
            REFERENCE    "ITU-T G.997.1, paragraph 7.3.2"
            DEFVAL       { 0 }
            ::= { hwXdslChAlarmConfProfileEntry 2 }

        hwXdslChAlarmConfProfileXtucThresh15MinCorrected  OBJECT-TYPE
            SYNTAX      Unsigned32
            MAX-ACCESS  read-create
            STATUS      current
            DESCRIPTION
               "A threshold for the hwXdslPMChCurr15MCorrectedBlocks
                counter, when hwXdslPMChCurrUnit is XTUC {1}.
                The value 0 means that no threshold is specified for the
                associated counter.
               "
            REFERENCE    "ITU-T G.997.1, paragraph 7.3.2"
            DEFVAL       { 0 }
              ::= { hwXdslChAlarmConfProfileEntry 3 }

        hwXdslChAlarmConfProfileXturThresh15MinCodingViolations  OBJECT-TYPE
            SYNTAX      Unsigned32
            MAX-ACCESS  read-create
            STATUS      current
            DESCRIPTION
                "A threshold for the hwXdslPMChCurr15MCodingViolations
                 counter, when hwXdslPMChCurrUnit is XTUR {2}.
                 The value 0 means that no threshold is specified for the
                 associated counter.
                "
            REFERENCE    "ITU-T G.997.1, paragraph 7.3.2"
            DEFVAL       { 0 }
              ::= { hwXdslChAlarmConfProfileEntry 4 }

        hwXdslChAlarmConfProfileXturThresh15MinCorrected  OBJECT-TYPE
            SYNTAX      Unsigned32
            MAX-ACCESS  read-create
            STATUS      current
            DESCRIPTION
                "A threshold for the hwXdslPMChCurr15MCorrectedBlocks
                 counter, when hwXdslPMChCurrUnit is XTUR {2}.
                 The value 0 means that no threshold is specified for the
                 associated counter.
                "
            REFERENCE    "ITU-T G.997.1, paragraph 7.3.2"
            DEFVAL       { 0 }
              ::= { hwXdslChAlarmConfProfileEntry 5 }

        hwXdslChAlarmConfProfileMonitoringRateDs  OBJECT-TYPE
            SYNTAX      Unsigned32(0..500000000)
            UNITS       "bits/second"
            MAX-ACCESS  read-create
            STATUS      current
            DESCRIPTION
                "The channel monitoring rate downstream.
                 Huawei defined. When the value you set is larger than
                 the value of the rate downstream defined in the channel
                 profile, it will not be successful. The value 0 means
                 that no threshold is specified for the associated
                 counter.
                 Unit: bits/second
                "
            DEFVAL       { 0 }
              ::= { hwXdslChAlarmConfProfileEntry 6 }

        hwXdslChAlarmConfProfileMonitoringRateUs  OBJECT-TYPE
            SYNTAX      Unsigned32(0..500000000)
            UNITS       "bits/second"
            MAX-ACCESS  read-create
            STATUS      current
            DESCRIPTION
                "The channel monitoring rate upstream.
                 Huawei defined. When the value you set is larger than
                 the value of the rate upstream defined in the channel
                 profile, it will not be successful. The value 0 means
                 that no threshold is specified for the associated
                 counter.
                 Unit: bits/second
                "
            DEFVAL       { 0 }
              ::= { hwXdslChAlarmConfProfileEntry 7 }

        hwXdslChAlarmConfProfileRowStatus  OBJECT-TYPE
            SYNTAX      RowStatus
            MAX-ACCESS  read-create
            STATUS      current
            DESCRIPTION
                "This object is used to create a new row or to modify or
                 delete an existing row in this table.

                 A profile is activated by setting this object to 'active'.
                 When 'active' is set, the system will validate the profile.

                 Before a profile can be deleted or taken out of service
                 (by setting this object to 'destroy' or 'outOfService'),
                 it must be not referenced from all associated
                 templates.
                "
            ::= { hwXdslChAlarmConfProfileEntry 8 }

          --          PM line current counters
        hwXdslPMLineCurrTable  OBJECT-TYPE
            SYNTAX      SEQUENCE  OF  HwXdslPMLineCurrEntry
            MAX-ACCESS  not-accessible
            STATUS      current
            DESCRIPTION
                "The table hwXdslPMLineCurrTable contains current Performance
                 Monitoring results of XDSL line.
                 The indexes of this table are an interface index where the
                 interface has an ifType of VDSL2/FAST and the termination
                 unit.
                "
            ::= { hwXdslPMLine 1 }

        hwXdslPMLineCurrEntry  OBJECT-TYPE
            SYNTAX      HwXdslPMLineCurrEntry
            MAX-ACCESS  not-accessible
            STATUS      current
            DESCRIPTION
                "The table hwXdslPMLineCurrTable contains current Performance
                 Monitoring results of XDSL line.
                 The indexes of this entry are an interface index where the
                 interface has an ifType of VDSL2/FAST and the termination
                 unit.
                "
            INDEX  { ifIndex, hwXdslPMLCurrUnit }
            ::= { hwXdslPMLineCurrTable 1 }

        HwXdslPMLineCurrEntry  ::=
            SEQUENCE {
              hwXdslPMLCurrUnit                    HwXdslUnit,
              hwXdslPMLCurrValidIntervals          Unsigned32,
              hwXdslPMLCurrInvalidIntervals        Unsigned32,
              hwXdslPMLCurr15MTimeElapsed          HCPerfTimeElapsed,
              hwXdslPMLCurr15MFecs                 Counter32,
              hwXdslPMLCurr15MEs                   Counter32,
              hwXdslPMLCurr15MSes                  Counter32,
              hwXdslPMLCurr15MLoss                 Counter32,
              hwXdslPMLCurr15MUas                  Counter32,
              hwXdslPMLCurr1DayValidIntervals      Unsigned32,
              hwXdslPMLCurr1DayInvalidIntervals    Unsigned32,
              hwXdslPMLCurr1DayTimeElapsed         HCPerfTimeElapsed,
              hwXdslPMLCurr1DayFecs                Counter32,
              hwXdslPMLCurr1DayEs                  Counter32,
              hwXdslPMLCurr1DaySes                 Counter32,
              hwXdslPMLCurr1DayLoss                Counter32,
              hwXdslPMLCurr1DayUas                 Counter32,
              hwXdslPMLEverBeforeFecs              Counter32,
              hwXdslPMLEverBeforeEs                Counter32,
              hwXdslPMLEverBeforeSes               Counter32,
              hwXdslPMLEverBeforeLoss              Counter32,
              hwXdslPMLEverBeforeUas               Counter32,
              hwXdslPMLCurr15MLofs                 Counter32,
              hwXdslPMLCurr15MLols                 Counter32,
              hwXdslPMLCurr15MLops                 Counter32,
              hwXdslPMLCurr1DayLofs                Counter32,
              hwXdslPMLCurr1DayLols                Counter32,
              hwXdslPMLCurr1DayLops                Counter32,
              hwXdslPMLEverBeforeLofs              Counter32,
              hwXdslPMLEverBeforeLols              Counter32,
              hwXdslPMLEverBeforeLops              Counter32,
              hwXdslPMLCurr15MSosSuccess           Counter32,
              hwXdslPMLCurr1DaySosSuccess          Counter32,
              hwXdslPMLEverBeforeSosSuccess        Counter32,
              hwXdslPMLCurr15MInmainpeq            OCTET STRING,
              hwXdslPMLCurr15MInmame               Counter32,
              hwXdslPMLCurr15MInmaiat              OCTET STRING,
              hwXdslPMLCurr1DayInmainpeq           OCTET STRING,
              hwXdslPMLCurr1DayInmame              Counter32,
              hwXdslPMLCurr1DayInmaiat             OCTET STRING,
              hwXdslPMLEverBeforeInmainpeq         OCTET STRING,
              hwXdslPMLEverBeforeInmame            Counter32,
              hwXdslPMLEverBeforeInmaiat           OCTET STRING,
              hwXdslPMLineCurr15MStartTime         DateAndTime,
              hwXdslPMLineCurr1DayStartTime        DateAndTime,
              hwXdslPMLCurr15MLeftrs               Counter32,
              hwXdslPMLCurr15MEfb                  Counter32,
              hwXdslPMLCurr15MMinEftr              Counter32,
              hwXdslPMLCurr1DayLeftrs              Counter32,
              hwXdslPMLCurr1DayEfb                 Counter32,
              hwXdslPMLCurr1DayMinEftr             Counter32,
              hwXdslPMLEverBeforeLeftrs            Counter32,
              hwXdslPMLEverBeforeEfb               Counter32,
              hwXdslPMLEverBeforeMinEftr           Counter32,
              hwXdslPMLEverBeforeSraDownShiftEvent    Counter32,
              hwXdslPMLEverBeforeSraUpShiftEvent      Counter32,
              hwXdslPMLCurr15MSraDownShiftEvent       Counter32,
              hwXdslPMLCurr15MSraUpShiftEvent         Counter32,
              hwXdslPMLCurr1DaySraDownShiftEvent      Counter32,
              hwXdslPMLCurr1DaySraUpShiftEvent        Counter32,
              hwXdslPMLEverBeforeDisorderLeavingEvent Counter32,
              hwXdslPMLEverBeforeLof                  Counter32,
              hwXdslPMLEverBeforeLos                  Counter32,
              hwXdslPMLEverBeforeLop                  Counter32,
              hwXdslPMLEverBeforeLom                  Counter32,
              hwXdslPMLCurr15MDisorderLeavingEvent    Counter32,
              hwXdslPMLCurr1DayDisorderLeavingEvent   Counter32,
              hwXdslPMLCurr15MLof                Counter32,
              hwXdslPMLCurr15MLos                Counter32,
              hwXdslPMLCurr15MLop                Counter32,
              hwXdslPMLCurr15MLom                Counter32,
              hwXdslPMLCurr1DayLof               Counter32,
              hwXdslPMLCurr1DayLos               Counter32,
              hwXdslPMLCurr1DayLop               Counter32,
              hwXdslPMLCurr1DayLom               Counter32,
              hwXdslPMLCurr15MLors               Counter32,
              hwXdslPMLCurr15MLor                Counter32,
              hwXdslPMLCurr15MRpaSuccess         Counter32,
              hwXdslPMLCurr1DayLors              Counter32,
              hwXdslPMLCurr1DayLor               Counter32,
              hwXdslPMLCurr1DayRpaSuccess        Counter32,
              hwXdslPMLEverBeforeLors            Counter32,
              hwXdslPMLEverBeforeLor             Counter32,
              hwXdslPMLEverBeforeRpaSuccess      Counter32,
              hwXdslPMLCurr15MBitswapSuccess     Counter32,
              hwXdslPMLCurr15MTigaSuccess        Counter32,
              hwXdslPMLCurr1DayBitswapSuccess    Counter32,
              hwXdslPMLCurr1DayTigaSuccess       Counter32,
              hwXdslPMLEverBeforeBitswapSuccess  Counter32,
              hwXdslPMLEverBeforeTigaSuccess     Counter32
            }

        hwXdslPMLCurrUnit  OBJECT-TYPE
            SYNTAX      HwXdslUnit
            MAX-ACCESS  not-accessible
            STATUS      current
            DESCRIPTION
                "The termination unit XTUC{1} or XTUR{2}."
            ::= { hwXdslPMLineCurrEntry 1 }

        hwXdslPMLCurrValidIntervals  OBJECT-TYPE
            SYNTAX      Unsigned32
            MAX-ACCESS  read-only
            STATUS      current
            DESCRIPTION
                "Valid intervals."
            ::= { hwXdslPMLineCurrEntry 2 }

        hwXdslPMLCurrInvalidIntervals  OBJECT-TYPE
            SYNTAX      Unsigned32
            MAX-ACCESS  read-only
            STATUS      current
            DESCRIPTION
                "Invalid intervals."
            ::= { hwXdslPMLineCurrEntry 3 }

        hwXdslPMLCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { hwXdslPMLineCurrEntry 4 }

        hwXdslPMLCurr15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwXdslPMLineCurrEntry 5 }

        hwXdslPMLCurr15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;=1 OR LPR &gt;= 1
                 xTU-R: FEBE &gt;= 1 for one or more bearer channels OR
                        LOS-FE &gt;=1 OR RDI &gt;=1 OR LPR-FE &gt;=1 .
                 This parameter is inhibited during UAS.
                 Unit: seconds
                "
            REFERENCE    "ITU-T G.997.1, paragraph 7.2.1"
            ::= { hwXdslPMLineCurrEntry 6 }

        hwXdslPMLCurr15MSes  OBJECT-TYPE
            SYNTAX      Counter32
            UNITS       "seconds"
            MAX-ACCESS  read-only
            STATUS      current
            DESCRIPTION
                "Count of seconds during this interval that there was:
                 xTU-C:  If G.998.4 is supported and retransmission is enabled
                         in the near-end received direction, a SES is declared
                         if during a 1-second interval, there is one or more
                         severe loss of error-free throughput (seftr) defect
                         in the near-end received direction.
                         Or else, an SES is declared if, during a 1 second interval,
                         there are 18 or more CRC 8 anomalies in one or more of the
                         received bearer channels, or one or more LOS defects, or
                         one or more SEF defects, or one or more LPR defects.

                 xTU-R: If G.998.4 is supported and retransmission is enabled in the
                        far-end received direction, a SES-LFE is declared if during
                        a 1-second interval, there is one or more severe loss of
                        error-free throughput (seftr) defect in the far-end received
                        direction.
                        Or else, an SES is declared if, during a 1 second interval,
                        there are 18 or more FEBE anomalies in one or more of the
                        transmitted bearer channels, or one or more far end LOS
                        defects, or one or more RDI defects, or one or more LPR FE
                        defects.
                 This parameter is inhibited during UAS.
                 Unit: seconds
                "
            REFERENCE    "ITU-T G.997.1, paragraph 7.2.1"
            ::= { hwXdslPMLineCurrEntry 7 }

        hwXdslPMLCurr15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwXdslPMLineCurrEntry 8 }

        hwXdslPMLCurr15MUas  OBJECT-TYPE
            SYNTAX      Counter32
            UNITS       "seconds"
            MAX-ACCESS  read-only
            STATUS      current
            DESCRIPTION
                "Count of seconds in Unavailability State during this
                 interval.  Unavailability begins at the onset of 10
                 contiguous severely-errored seconds, and ends at the
                 onset of 10 contiguous seconds with no severely-errored
                 seconds.
                 Unit: seconds
                "
            REFERENCE    "ITU-T G.997.1, paragraph 7.2.1"
            ::= { hwXdslPMLineCurrEntry 9 }

        hwXdslPMLCurr1DayValidIntervals  OBJECT-TYPE
            SYNTAX      Unsigned32
            MAX-ACCESS  read-only
            STATUS      current
            DESCRIPTION
                "Valid intervals."
            ::= { hwXdslPMLineCurrEntry 10 }

        hwXdslPMLCurr1DayInvalidIntervals  OBJECT-TYPE
            SYNTAX      Unsigned32
            MAX-ACCESS  read-only
            STATUS      current
            DESCRIPTION
                "Invalid intervals."
            ::= { hwXdslPMLineCurrEntry 11 }

        hwXdslPMLCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { hwXdslPMLineCurrEntry 12 }

        hwXdslPMLCurr1DayFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwXdslPMLineCurrEntry 13 }

        hwXdslPMLCurr1DayEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwXdslPMLineCurrEntry 14 }

        hwXdslPMLCurr1DaySes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Unit: seconds
                "
            REFERENCE    "ITU-T G.997.1, paragraph 7.2.1"
            ::= { hwXdslPMLineCurrEntry 15 }

        hwXdslPMLCurr1DayLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwXdslPMLineCurrEntry 16 }

        hwXdslPMLCurr1DayUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwXdslPMLineCurrEntry 17 }

        hwXdslPMLEverBeforeFecs  OBJECT-TYPE
            SYNTAX      Counter32
            UNITS       "seconds"
            MAX-ACCESS  read-only
            STATUS      current
            DESCRIPTION
                "Count of seconds since agent reset that there was at least
                 one FEC correction event for one or more bearer channels in
                 this line. This parameter is inhibited during UAS or SES.
                 Huawei defined.
                 Unit: seconds
                "
            ::= { hwXdslPMLineCurrEntry 18 }

        hwXdslPMLEverBeforeEs  OBJECT-TYPE
            SYNTAX      Counter32
            UNITS       "seconds"
            MAX-ACCESS  read-only
            STATUS      current
            DESCRIPTION
                "Count of seconds since agent reset that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Huawei defined.
                 Unit: seconds
                "
            ::= { hwXdslPMLineCurrEntry 19 }

        hwXdslPMLEverBeforeSes  OBJECT-TYPE
            SYNTAX      Counter32
            UNITS       "seconds"
            MAX-ACCESS  read-only
            STATUS      current
            DESCRIPTION
                "Count of seconds since agent reset that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Huawei defined.
                 Unit: seconds
                "
            ::= { hwXdslPMLineCurrEntry 20 }

        hwXdslPMLEverBeforeLoss  OBJECT-TYPE
            SYNTAX      Counter32
            UNITS       "seconds"
            MAX-ACCESS  read-only
            STATUS      current
            DESCRIPTION
                "Count of seconds since agent reset that there was LOS (or
                 LOS-FE for xTU-R).
                 Huawei defined.
                 Unit: seconds
                "
            ::= { hwXdslPMLineCurrEntry 21 }

        hwXdslPMLEverBeforeUas  OBJECT-TYPE
            SYNTAX      Counter32
            UNITS       "seconds"
            MAX-ACCESS  read-only
            STATUS      current
            DESCRIPTION
                "Count of seconds in Unavailability State since agent reset.
                 Unavailability begins at the onset of 10 contiguous severely
                 -errored seconds, and ends at the onset of 10 contiguous
                 seconds with no severely-errored seconds.
                 Huawei defined.
                 Unit: seconds
                "
            ::= { hwXdslPMLineCurrEntry 22 }

        hwXdslPMLCurr15MLofs  OBJECT-TYPE
            SYNTAX      Counter32
            UNITS       "seconds"
            MAX-ACCESS  read-only
            STATUS      current
            DESCRIPTION
                "Count of seconds in the current 15 minute interval when there was Loss of Framing.
                 Unit: seconds
                "
            ::= { hwXdslPMLineCurrEntry 23 }

        hwXdslPMLCurr15MLols  OBJECT-TYPE
            SYNTAX      Counter32
            UNITS       "seconds"
            MAX-ACCESS  read-only
            STATUS      current
            DESCRIPTION
                "Count of seconds in the current 15 minute interval when there was Loss of Link.
                 Unit: seconds
                "
            ::= { hwXdslPMLineCurrEntry 24 }

        hwXdslPMLCurr15MLops  OBJECT-TYPE
            SYNTAX      Counter32
            UNITS       "seconds"
            MAX-ACCESS  read-only
            STATUS      current
            DESCRIPTION
                "Count of seconds in the current 15 minute interval when there was Loss of Power.
                 Unit: seconds
                "
            ::= { hwXdslPMLineCurrEntry 25 }

        hwXdslPMLCurr1DayLofs  OBJECT-TYPE
            SYNTAX      Counter32
            UNITS       "seconds"
            MAX-ACCESS  read-only
            STATUS      current
            DESCRIPTION
                "Count of the number of seconds when there was Loss of Framing during the current day.
                 Unit: seconds
                "
            ::= { hwXdslPMLineCurrEntry 26 }

        hwXdslPMLCurr1DayLols  OBJECT-TYPE
            SYNTAX      Counter32
            UNITS       "seconds"
            MAX-ACCESS  read-only
            STATUS      current
            DESCRIPTION
                "Count of the number of seconds when there was Loss of Link during the current day.
                 Unit: seconds
                "
            ::= { hwXdslPMLineCurrEntry 27 }

        hwXdslPMLCurr1DayLops  OBJECT-TYPE
            SYNTAX      Counter32
            UNITS       "seconds"
            MAX-ACCESS  read-only
            STATUS      current
            DESCRIPTION
                "Count of the number of seconds when there was Loss of Power during the current day.
                 Unit: seconds
                "
            ::= { hwXdslPMLineCurrEntry 28 }

        hwXdslPMLEverBeforeLofs  OBJECT-TYPE
            SYNTAX      Counter32
            UNITS       "seconds"
            MAX-ACCESS  read-only
            STATUS      current
            DESCRIPTION
                "Count of the number of seconds when there was Loss of Framing since agent reset.
                 Unit: seconds
                "
            ::= { hwXdslPMLineCurrEntry 29 }

        hwXdslPMLEverBeforeLols  OBJECT-TYPE
            SYNTAX      Counter32
            UNITS       "seconds"
            MAX-ACCESS  read-only
            STATUS      current
            DESCRIPTION
                "Count of the number of seconds when there was Loss of Link since agent reset.
                 Unit: seconds
                "
            ::= { hwXdslPMLineCurrEntry 30 }

        hwXdslPMLEverBeforeLops  OBJECT-TYPE
            SYNTAX      Counter32
            UNITS       "seconds"
            MAX-ACCESS  read-only
            STATUS      current
            DESCRIPTION
                "Count of the number of seconds when there was Loss of Power since agent reset.
                 Unit: seconds
                "
            ::= { hwXdslPMLineCurrEntry 31 }

        hwXdslPMLCurr15MSosSuccess  OBJECT-TYPE
            SYNTAX      Counter32
            UNITS       "times"
            MAX-ACCESS  read-only
            STATUS      current
            DESCRIPTION
                "If the line is activated as G9701 of hwXdslLineStatusXtuTransSys,
                 the parameter is count of the total number of successful FRA procedures
                 initiated in the current 15 minute. Otherwise, the parameter is count of
                 the total number of successful SOS procedures initiated in the current
                 15 minute.
                 Unit: times
                "
            REFERENCE    "ITU-T G.997.1, paragraph 7.2.1"
            ::= { hwXdslPMLineCurrEntry 32 }

        hwXdslPMLCurr1DaySosSuccess  OBJECT-TYPE
            SYNTAX      Counter32
            UNITS       "times"
            MAX-ACCESS  read-only
            STATUS      current
            DESCRIPTION
                "If the line is activated as G9701 of hwXdslLineStatusXtuTransSys,
                 the parameter is count of the total number of successful FRA procedures
                 initiated during the current day. Otherwise, the parameter is count of
                 the total number of successful SOS procedures initiated during the current day.
                 Unit: times
                "
            REFERENCE    "ITU-T G.997.1, paragraph 7.2.1"
            ::= { hwXdslPMLineCurrEntry 33 }

        hwXdslPMLEverBeforeSosSuccess  OBJECT-TYPE
            SYNTAX      Counter32
            UNITS       "times"
            MAX-ACCESS  read-only
            STATUS      current
            DESCRIPTION
                "If the line is activated as G9701 of hwXdslLineStatusXtuTransSys,
                 the parameter is count of the total number of successful FRA procedures
                 initiated since agent reset. Otherwise, the parameter is count of
                 the total number of successful SOS procedures initiated since agent reset.
                 Unit: times
                "
            REFERENCE    "ITU-T G.997.1, paragraph 7.2.1"
            ::= { hwXdslPMLineCurrEntry 34 }

        hwXdslPMLCurr15MInmainpeq  OBJECT-TYPE
            SYNTAX      OCTET STRING  (SIZE(0..68))
            MAX-ACCESS  read-only
            STATUS      current
            DESCRIPTION
                "This parameter is a count of the INMAINPEQi anomalies occurring on the line during current 15 minutes.
                 Each INMAINPEQ needs 4 bytes, Each four bytes, arranged in descending significance order from left to right,
                 correspond to one INMAINPEQ. For example, bytes 0-3 correspond to INMAINPEQ1, bytes 4-7 correspond to INMAINPEQ2.
                 The later is deduced in the same way. The INMAINPEQ value can be converted into a decimal value. For example,
                 the decimal value of 00 00 00 F0 is 240.
                "
            REFERENCE    "ITU-T G.997.1, paragraph 7.2.1"
            ::= { hwXdslPMLineCurrEntry 35 }

        hwXdslPMLCurr15MInmame  OBJECT-TYPE
            SYNTAX      Counter32
            MAX-ACCESS  read-only
            STATUS      current
            DESCRIPTION
                "This parameter is a count of the INMAME anomalies
                 occurring on the line during current 15 minutes.
                "
            REFERENCE    "ITU-T G.997.1, paragraph 7.2.1"
            ::= { hwXdslPMLineCurrEntry 36 }

        hwXdslPMLCurr15MInmaiat  OBJECT-TYPE
            SYNTAX      OCTET STRING  (SIZE(0..32))
            MAX-ACCESS  read-only
            STATUS      current
            DESCRIPTION
                "This parameter is a count of the INMAIATi anomalies occurring on the line during current 15 minutes.
                 Each INMAIAT needs 4 bytes. Each four bytes, arranged in descending significance order from left to right,
                 correspond to one INMAIAT. For example,bytes 0-3 correspond to INMAIAT0, bytes 4-7 correspond to INMAIAT1.
                 The later is deduced in the same way. The INMAIAT value can be converted into a decimal value. For example,
                 the decimal value of 00 00 00 F0 is 240.
                "
            REFERENCE    "ITU-T G.997.1, paragraph 7.2.1"
            ::= { hwXdslPMLineCurrEntry 37 }

        hwXdslPMLCurr1DayInmainpeq  OBJECT-TYPE
            SYNTAX      OCTET STRING  (SIZE(0..68))
            MAX-ACCESS  read-only
            STATUS      current
            DESCRIPTION
                "This parameter is a count of the INMAINPEQi anomalies occurring on the line during current 1 day.
                Each INMAINPEQ needs 4 bytes, Each four bytes, arranged in descending significance order from left to right,
                correspond to one INMAINPEQ. For example, bytes 0-3 correspond to INMAINPEQ1, bytes 4-7 correspond to INMAINPEQ2.
                The later is deduced in the same way. The INMAINPEQ value can be converted into a decimal value. For example,
                the decimal value of 00 00 00 F0 is 240.
                "
            REFERENCE    "ITU-T G.997.1, paragraph 7.2.1"
            ::= { hwXdslPMLineCurrEntry 38 }

        hwXdslPMLCurr1DayInmame  OBJECT-TYPE
            SYNTAX      Counter32
            MAX-ACCESS  read-only
            STATUS      current
            DESCRIPTION
                "This parameter is a count of the INMAME anomalies
                 occurring on the line during current 1 day.
                "
            REFERENCE    "ITU-T G.997.1, paragraph 7.2.1"
            ::= { hwXdslPMLineCurrEntry 39 }

        hwXdslPMLCurr1DayInmaiat  OBJECT-TYPE
            SYNTAX      OCTET STRING  (SIZE(0..32))
            MAX-ACCESS  read-only
            STATUS      current
            DESCRIPTION
                "This parameter is a count of the INMAIATi anomalies occurring on the line during current 1 day.
                Each INMAIAT needs 4 bytes. Each four bytes, arranged in descending significance order from left to right,
                correspond to one INMAIAT. For example,bytes 0-3 correspond to INMAIAT0, bytes 4-7 correspond to INMAIAT1.
                The later is deduced in the same way. The INMAIAT value can be converted into a decimal value. For example,
                the decimal value of 00 00 00 F0 is 240.
                "
            REFERENCE    "ITU-T G.997.1, paragraph 7.2.1"
            ::= { hwXdslPMLineCurrEntry 40 }

        hwXdslPMLEverBeforeInmainpeq  OBJECT-TYPE
            SYNTAX      OCTET STRING  (SIZE(0..68))
            MAX-ACCESS  read-only
            STATUS      current
            DESCRIPTION
                "This parameter is a count of the INMAINPEQi anomalies occurring on the line ever before.
                 Each INMAINPEQ needs 4 bytes, Each four bytes, arranged in descending significance order from left to right,
                 correspond to one INMAINPEQ. For example, bytes 0-3 correspond to INMAINPEQ1, bytes 4-7 correspond to INMAINPEQ2.
                 The later is deduced in the same way. The INMAINPEQ value can be converted into a decimal value. For example,
                 the decimal value of 00 00 00 F0 is 240.
                "
            REFERENCE    "ITU-T G.997.1, paragraph 7.2.1"
            ::= { hwXdslPMLineCurrEntry 41 }

        hwXdslPMLEverBeforeInmame  OBJECT-TYPE
            SYNTAX      Counter32
            MAX-ACCESS  read-only
            STATUS      current
            DESCRIPTION
                "This parameter is a count of the INMAME anomalies
                 occurring on the line ever before.
                "
            REFERENCE    "ITU-T G.997.1, paragraph 7.2.1"
            ::= { hwXdslPMLineCurrEntry 42 }

        hwXdslPMLEverBeforeInmaiat  OBJECT-TYPE
            SYNTAX      OCTET STRING  (SIZE(0..32))
            MAX-ACCESS  read-only
            STATUS      current
            DESCRIPTION
                "This parameter is a count of the INMAIATi anomalies occurring on the line ever before.
                 Each INMAIAT needs 4 bytes. Each four bytes, arranged in descending significance order from left to right,
                 correspond to one INMAIAT. For example,bytes 0-3 correspond to INMAIAT0, bytes 4-7 correspond to INMAIAT1.
                 The later is deduced in the same way. The INMAIAT value can be converted into a decimal value. For example,
                 the decimal value of 00 00 00 F0 is 240.
                "
            REFERENCE    "ITU-T G.997.1, paragraph 7.2.1"
            ::= { hwXdslPMLineCurrEntry 43 }

        hwXdslPMLineCurr15MStartTime  OBJECT-TYPE
            SYNTAX      DateAndTime
            MAX-ACCESS  read-only
            STATUS      current
            DESCRIPTION
                "Start time of the current 15-minute performance statistics."
            ::= { hwXdslPMLineCurrEntry 44 }

        hwXdslPMLineCurr1DayStartTime  OBJECT-TYPE
            SYNTAX      DateAndTime
            MAX-ACCESS  read-only
            STATUS      current
            DESCRIPTION
                "Start time of the current 1-day performance statistics."
            ::= { hwXdslPMLineCurrEntry 45 }

        hwXdslPMLCurr15MLeftrs     OBJECT-TYPE
            SYNTAX      Counter32
            MAX-ACCESS  read-only
            STATUS      current
            DESCRIPTION
                "If retransmission is used in a given transmit direction, this parameter
                 is a count of the seconds with a near-end leftr defect present observed
                 over the 15 minutes accumulation period.
                "
            REFERENCE    "ITU-T G.997.1, paragraph 7.2.1.1.6 7.2.1.2.6"
            ::= { hwXdslPMLineCurrEntry 46 }

        hwXdslPMLCurr15MEfb        OBJECT-TYPE
            SYNTAX      Counter32
            MAX-ACCESS  read-only
            STATUS      current
            DESCRIPTION
                "If retransmission is used in a given transmit direction, this parameter
                 is a count of the number of error-free bits observed over the 15 minutes
                 accumulation period.
                "
            REFERENCE    "ITU-T G.997.1, paragraph 7.2.1.1.7 7.2.1.2.7"
            ::= { hwXdslPMLineCurrEntry 47 }

        hwXdslPMLCurr15MMinEftr    OBJECT-TYPE
            SYNTAX      Counter32
            MAX-ACCESS  read-only
            STATUS      current
            DESCRIPTION
                "If retransmission is used in a given transmit direction, this parameter
                 reports the minimum of the EFTR(Error-free throughput rate) observed
                 over the 15 minutes accumulation period.
                "
            REFERENCE    "ITU-T G.997.1, paragraph 7.2.1.1.8 7.2.1.2.8"
            ::= { hwXdslPMLineCurrEntry 48 }
        hwXdslPMLCurr1DayLeftrs    OBJECT-TYPE
            SYNTAX      Counter32
            MAX-ACCESS  read-only
            STATUS      current
            DESCRIPTION
                "If retransmission is used in a given transmit direction, this parameter
                 is a count of the seconds with a near-end leftr defect present observed
                 over the 24 hours accumulation period.
                "
            REFERENCE    "ITU-T G.997.1, paragraph 7.2.1.1.6 7.2.1.2.6"
            ::= { hwXdslPMLineCurrEntry 49 }

        hwXdslPMLCurr1DayEfb       OBJECT-TYPE
            SYNTAX      Counter32
            MAX-ACCESS  read-only
            STATUS      current
            DESCRIPTION
                "If retransmission is used in a given transmit direction, this parameter
                 is a count of the number of error-free bits observed over the 24 hours
                 accumulation period.
                "
            REFERENCE    "ITU-T G.997.1, paragraph 7.2.1.1.7 7.2.1.2.7"
            ::= { hwXdslPMLineCurrEntry 50 }

        hwXdslPMLCurr1DayMinEftr   OBJECT-TYPE
            SYNTAX      Counter32
            MAX-ACCESS  read-only
            STATUS      current
            DESCRIPTION
                "If retransmission is used in a given transmit direction, this parameter
                 reports the minimum of the EFTR(Error-free throughput rate) observed
                 over the 24 hours accumulation period.
                "
            REFERENCE    "ITU-T G.997.1, paragraph 7.2.1.1.8 7.2.1.2.8"
            ::= { hwXdslPMLineCurrEntry 51}

        hwXdslPMLEverBeforeLeftrs  OBJECT-TYPE
            SYNTAX      Counter32
            MAX-ACCESS  read-only
            STATUS      current
            DESCRIPTION
                "If retransmission is used in a given transmit direction, this parameter
                 is a count of the seconds with a near-end leftr defect present observed
                 ever before.
                "
            REFERENCE    "ITU-T G.997.1, paragraph 7.2.1.1.6 7.2.1.2.6"
            ::= { hwXdslPMLineCurrEntry 52 }

        hwXdslPMLEverBeforeEfb     OBJECT-TYPE
            SYNTAX      Counter32
            MAX-ACCESS  read-only
            STATUS      current
            DESCRIPTION
                "If retransmission is used in a given transmit direction, this parameter
                 is a count of the number of error-free bits observed ever before.
                "
            REFERENCE    "ITU-T G.997.1, paragraph 7.2.1.1.7 7.2.1.2.7"
            ::= { hwXdslPMLineCurrEntry 53 }

        hwXdslPMLEverBeforeMinEftr OBJECT-TYPE
            SYNTAX      Counter32
            MAX-ACCESS  read-only
            STATUS      current
            DESCRIPTION
                "If retransmission is used in a given transmit direction, this parameter
                 reports the minimum of the EFTR(Error-free throughput rate) observed
                 ever before.
                "
            REFERENCE    "ITU-T G.997.1, paragraph 7.2.1.1.8 7.2.1.2.8"
            ::= { hwXdslPMLineCurrEntry 54 }

        hwXdslPMLEverBeforeSraDownShiftEvent OBJECT-TYPE
            SYNTAX      Counter32
            MAX-ACCESS  read-only
            STATUS      current
            DESCRIPTION
                "This parameter is a count of sra down-shift event occurring on the line ever before."
            ::= { hwXdslPMLineCurrEntry 55 }

        hwXdslPMLEverBeforeSraUpShiftEvent OBJECT-TYPE
            SYNTAX      Counter32
            MAX-ACCESS  read-only
            STATUS      current
            DESCRIPTION
                "This parameter is a count of sra up-shift event occurring on the line ever before."
            ::= { hwXdslPMLineCurrEntry 56 }

        hwXdslPMLCurr15MSraDownShiftEvent OBJECT-TYPE
            SYNTAX      Counter32
            MAX-ACCESS  read-only
            STATUS      current
            DESCRIPTION
                "This parameter is a count of sra down-shift event occurring on the line over the 15 minutes accumulation period."
            ::= { hwXdslPMLineCurrEntry 57 }

        hwXdslPMLCurr15MSraUpShiftEvent OBJECT-TYPE
            SYNTAX      Counter32
            MAX-ACCESS  read-only
            STATUS      current
            DESCRIPTION
                "This parameter is a count of sra up-shift event occurring on the line over the 15 minutes accumulation period."
            ::= { hwXdslPMLineCurrEntry 58 }

        hwXdslPMLCurr1DaySraDownShiftEvent OBJECT-TYPE
            SYNTAX      Counter32
            MAX-ACCESS  read-only
            STATUS      current
            DESCRIPTION
                "This parameter is a count of sra down-shift event occurring on the line during current 1 day."
            ::= { hwXdslPMLineCurrEntry 59 }

        hwXdslPMLCurr1DaySraUpShiftEvent OBJECT-TYPE
            SYNTAX      Counter32
            MAX-ACCESS  read-only
            STATUS      current
            DESCRIPTION
                "This parameter is a count of sra up-shift event occurring on the line during current 1 day."
            ::= { hwXdslPMLineCurrEntry 60 }

        hwXdslPMLEverBeforeDisorderLeavingEvent OBJECT-TYPE
            SYNTAX      Counter32
            MAX-ACCESS  read-only
            STATUS      current
            DESCRIPTION
                "This parameter is a count of disorder leaving event occurring on the line ever before."
            ::= { hwXdslPMLineCurrEntry 61 }

        hwXdslPMLEverBeforeLof OBJECT-TYPE
            SYNTAX      Counter32
            MAX-ACCESS  read-only
            STATUS      current
            DESCRIPTION
                "This parameter is a count of loss of frame failure occurring on the line ever before."
            ::= { hwXdslPMLineCurrEntry 62 }

        hwXdslPMLEverBeforeLos OBJECT-TYPE
            SYNTAX      Counter32
            MAX-ACCESS  read-only
            STATUS      current
            DESCRIPTION
                "This parameter is a count of loss of signal failure occurring on the line ever before."
            ::= { hwXdslPMLineCurrEntry 63 }

        hwXdslPMLEverBeforeLop OBJECT-TYPE
            SYNTAX      Counter32
            MAX-ACCESS  read-only
            STATUS      current
            DESCRIPTION
                "This parameter is a count of loss of power failure occurring on the line ever before."
            ::= { hwXdslPMLineCurrEntry 64 }

        hwXdslPMLEverBeforeLom OBJECT-TYPE
            SYNTAX      Counter32
            MAX-ACCESS  read-only
            STATUS      current
            DESCRIPTION
                "This parameter is a count of loss of margin failure occurring on the line ever before."
            ::= { hwXdslPMLineCurrEntry 65 }

        hwXdslPMLCurr15MDisorderLeavingEvent OBJECT-TYPE
            SYNTAX      Counter32
            MAX-ACCESS  read-only
            STATUS      current
            DESCRIPTION
                "This parameter is a count of disorder leaving event occurring on the line during current 15 minutes."
            ::= { hwXdslPMLineCurrEntry 66 }

        hwXdslPMLCurr1DayDisorderLeavingEvent OBJECT-TYPE
            SYNTAX      Counter32
            MAX-ACCESS  read-only
            STATUS      current
            DESCRIPTION
                "This parameter is a count of disorder leaving event occurring on the line during current 1 day."
            ::= { hwXdslPMLineCurrEntry 67 }

        hwXdslPMLCurr15MLof OBJECT-TYPE
            SYNTAX      Counter32
            MAX-ACCESS  read-only
            STATUS      current
            DESCRIPTION
                "This parameter is a count of loss of frame failure occurring on the line during current 15 minutes."
            ::= { hwXdslPMLineCurrEntry 68 }

        hwXdslPMLCurr15MLos OBJECT-TYPE
            SYNTAX      Counter32
            MAX-ACCESS  read-only
            STATUS      current
            DESCRIPTION
                "This parameter is a count of loss of signal failure occurring on the line during current 15 minutes."
            ::= { hwXdslPMLineCurrEntry 69 }

        hwXdslPMLCurr15MLop OBJECT-TYPE
            SYNTAX      Counter32
            MAX-ACCESS  read-only
            STATUS      current
            DESCRIPTION
                "This parameter is a count of loss of power failure occurring on the line during current 15 minutes."
            ::= { hwXdslPMLineCurrEntry 70 }

        hwXdslPMLCurr15MLom OBJECT-TYPE
            SYNTAX      Counter32
            MAX-ACCESS  read-only
            STATUS      current
            DESCRIPTION
                "This parameter is a count of loss of margin failure occurring on the line during current 15 minutes."
            ::= { hwXdslPMLineCurrEntry 71 }

        hwXdslPMLCurr1DayLof OBJECT-TYPE
            SYNTAX      Counter32
            MAX-ACCESS  read-only
            STATUS      current
            DESCRIPTION
                "This parameter is a count of loss of frame failure occurring on the line during current 1 day."
            ::= { hwXdslPMLineCurrEntry 72 }

        hwXdslPMLCurr1DayLos OBJECT-TYPE
            SYNTAX      Counter32
            MAX-ACCESS  read-only
            STATUS      current
            DESCRIPTION
                "This parameter is a count of loss of signal failure occurring on the line during current 1 day."
            ::= { hwXdslPMLineCurrEntry 73 }

        hwXdslPMLCurr1DayLop OBJECT-TYPE
            SYNTAX      Counter32
            MAX-ACCESS  read-only
            STATUS      current
            DESCRIPTION
                "This parameter is a count of loss of power failure occurring on the line during current 1 day."
            ::= { hwXdslPMLineCurrEntry 74 }

        hwXdslPMLCurr1DayLom OBJECT-TYPE
            SYNTAX      Counter32
            MAX-ACCESS  read-only
            STATUS      current
            DESCRIPTION
                "This parameter is a count of loss of margin failure occurring on the line during current 1 day."
            ::= { hwXdslPMLineCurrEntry 75 }

        hwXdslPMLCurr15MLors OBJECT-TYPE
            SYNTAX      Counter32
            MAX-ACCESS  read-only
            STATUS      current
            DESCRIPTION
                "This parameter is a count of LOR second occurring on the line during current 15 minutes."
            ::= { hwXdslPMLineCurrEntry 76 }

        hwXdslPMLCurr15MLor OBJECT-TYPE
            SYNTAX      Counter32
            MAX-ACCESS  read-only
            STATUS      current
            DESCRIPTION
                "This parameter is a count of loss of RMC failure occurring on the line during current 15 minutes."
            ::= { hwXdslPMLineCurrEntry 77 }

        hwXdslPMLCurr15MRpaSuccess OBJECT-TYPE
            SYNTAX      Counter32
            MAX-ACCESS  read-only
            STATUS      current
            DESCRIPTION
                "This parameter is a count of the successful RPA primitives occurring on the line during current 15 minutes."
            ::= { hwXdslPMLineCurrEntry 78 }

        hwXdslPMLCurr1DayLors OBJECT-TYPE
            SYNTAX      Counter32
            MAX-ACCESS  read-only
            STATUS      current
            DESCRIPTION
                "This parameter is a count of LOR second occurring on the line during current 1 day."
            ::= { hwXdslPMLineCurrEntry 79 }

        hwXdslPMLCurr1DayLor OBJECT-TYPE
            SYNTAX      Counter32
            MAX-ACCESS  read-only
            STATUS      current
            DESCRIPTION
                "This parameter is a count of loss of RMC failure occurring on the line during current 1 day."
            ::= { hwXdslPMLineCurrEntry 80 }

        hwXdslPMLCurr1DayRpaSuccess OBJECT-TYPE
            SYNTAX      Counter32
            MAX-ACCESS  read-only
            STATUS      current
            DESCRIPTION
                "This parameter is a count of the successful RPA primitives occurring on the line during current 1 day."
            ::= { hwXdslPMLineCurrEntry 81 }

        hwXdslPMLEverBeforeLors OBJECT-TYPE
            SYNTAX      Counter32
            MAX-ACCESS  read-only
            STATUS      current
            DESCRIPTION
                "This parameter is a count of LOR second occurring on the line during ever before."
            ::= { hwXdslPMLineCurrEntry 82 }

        hwXdslPMLEverBeforeLor OBJECT-TYPE
            SYNTAX      Counter32
            MAX-ACCESS  read-only
            STATUS      current
            DESCRIPTION
                "This parameter is a count of loss of RMC failure occurring on the line during ever before."
            ::= { hwXdslPMLineCurrEntry 83 }

        hwXdslPMLEverBeforeRpaSuccess OBJECT-TYPE
            SYNTAX      Counter32
            MAX-ACCESS  read-only
            STATUS      current
            DESCRIPTION
                "This parameter is a count of the successful RPA primitives occurring on the line during ever before."
            ::= { hwXdslPMLineCurrEntry 84 }

        hwXdslPMLCurr15MBitswapSuccess OBJECT-TYPE
            SYNTAX      Counter32
            MAX-ACCESS  read-only
            STATUS      current
            DESCRIPTION
                "This parameter is a count of the successful bit swap primitives occurring on the line during current 15 minutes."
            ::= { hwXdslPMLineCurrEntry 85 }

        hwXdslPMLCurr15MTigaSuccess OBJECT-TYPE
            SYNTAX      Counter32
            MAX-ACCESS  read-only
            STATUS      current
            DESCRIPTION
                "This parameter is a count of the successful TIGA primitives occurring on the line during current 15 minutes."
            ::= { hwXdslPMLineCurrEntry 86 }

        hwXdslPMLCurr1DayBitswapSuccess OBJECT-TYPE
            SYNTAX      Counter32
            MAX-ACCESS  read-only
            STATUS      current
            DESCRIPTION
                "This parameter is a count of the successful bit swap primitives occurring on the line during current 1 day."
            ::= { hwXdslPMLineCurrEntry 87 }

        hwXdslPMLCurr1DayTigaSuccess OBJECT-TYPE
            SYNTAX      Counter32
            MAX-ACCESS  read-only
            STATUS      current
            DESCRIPTION
                "This parameter is a count of the successful TIGA primitives occurring on the line during current 1 day."
            ::= { hwXdslPMLineCurrEntry 88 }

        hwXdslPMLEverBeforeBitswapSuccess OBJECT-TYPE
            SYNTAX      Counter32
            MAX-ACCESS  read-only
            STATUS      current
            DESCRIPTION
                "This parameter is a count of the successful bit swap primitives occurring on the line during ever before."
            ::= { hwXdslPMLineCurrEntry 89 }

        hwXdslPMLEverBeforeTigaSuccess OBJECT-TYPE
            SYNTAX      Counter32
            MAX-ACCESS  read-only
            STATUS      current
            DESCRIPTION
                "This parameter is a count of the successful TIGA primitives occurring on the line during ever before."
            ::= { hwXdslPMLineCurrEntry 90 }

          --          PM line init current counters

        hwXdslPMLineCurrInitTable   OBJECT-TYPE
            SYNTAX      SEQUENCE  OF  HwXdslPMLineCurrInitEntry
            MAX-ACCESS  not-accessible
            STATUS      current
            DESCRIPTION
                "The table hwXdslPMLineCurrInitTable contains current
                 initialization counters of XDSL line.
                 The indexes of this table are an interface index where the
                 interface has an ifType of VDSL2/FAST and the termination
                 unit.
                "
            ::= { hwXdslPMLine 2 }

        hwXdslPMLineCurrInitEntry  OBJECT-TYPE
            SYNTAX      HwXdslPMLineCurrInitEntry
            MAX-ACCESS  not-accessible
            STATUS      current
            DESCRIPTION
                "The table hwXdslPMLineCurrInitTable contains current
                 initialization counters of XDSL line.
                 The indexes of this entry are an interface index where the
                 interface has an ifType of VDSL2/FAST and the termination
                 unit.
                "
            INDEX  { ifIndex }
            ::= { hwXdslPMLineCurrInitTable 1 }

        HwXdslPMLineCurrInitEntry  ::=
            SEQUENCE {
              hwXdslPMLCurrInit15MTimeElapsed          Unsigned32,
              hwXdslPMLCurrInit15MFullInits            Unsigned32,
              hwXdslPMLCurrInit15MFailedFullInits      Unsigned32,
              hwXdslPMLCurrInit15MShortInits           Unsigned32,
              hwXdslPMLCurrInit15MFailedShortInits     Unsigned32,
              hwXdslPMLCurrInit1DayTimeElapsed         Unsigned32,
              hwXdslPMLCurrInit1DayFullInits           Unsigned32,
              hwXdslPMLCurrInit1DayFailedFullInits     Unsigned32,
              hwXdslPMLCurrInit1DayShortInits          Unsigned32,
              hwXdslPMLCurrInit1DayFailedShortInits    Unsigned32,
              hwXdslPMLInitEverBeforeFullInits         Unsigned32,
              hwXdslPMLInitEverBeforeFailedFullInits   Unsigned32,
              hwXdslPMLInitEverBeforeShortInits        Unsigned32,
              hwXdslPMLInitEverBeforeFailedShortInits  Unsigned32,
              hwXdslPMLineCurrInit15MStartTime         DateAndTime,
              hwXdslPMLineCurrInit1DayStartTime        DateAndTime,
              hwXdslPMLineCurrInit15MAbnormalReInit    Unsigned32,
              hwXdslPMLineCurrInit1DayAbnormalReInit   Unsigned32,
              hwXdslPMLineCurrInitEverBeforeAbnormalReInit   Unsigned32
            }

        hwXdslPMLCurrInit15MTimeElapsed  OBJECT-TYPE
            SYNTAX      Unsigned32
            UNITS       "seconds"
            MAX-ACCESS  read-only
            STATUS      current
            DESCRIPTION
                "Total elapsed seconds in this interval.
                 Unit: seconds
                "
            ::= { hwXdslPMLineCurrInitEntry 1 }

        hwXdslPMLCurrInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwXdslPMLineCurrInitEntry 2 }

        hwXdslPMLCurrInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwXdslPMLineCurrInitEntry 3 }

        hwXdslPMLCurrInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwXdslPMLineCurrInitEntry 4 }

        hwXdslPMLCurrInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwXdslPMLineCurrInitEntry 5 }

        hwXdslPMLCurrInit1DayTimeElapsed  OBJECT-TYPE
            SYNTAX      Unsigned32
            UNITS       "seconds"
            MAX-ACCESS  read-only
            STATUS      current
            DESCRIPTION
                "Total elapsed seconds in this interval.
                 Unit: seconds
                "
            ::= { hwXdslPMLineCurrInitEntry 6 }

        hwXdslPMLCurrInit1DayFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwXdslPMLineCurrInitEntry 7 }

        hwXdslPMLCurrInit1DayFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwXdslPMLineCurrInitEntry 8 }

        hwXdslPMLCurrInit1DayShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwXdslPMLineCurrInitEntry 9 }

        hwXdslPMLCurrInit1DayFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwXdslPMLineCurrInitEntry 10 }

        hwXdslPMLInitEverBeforeFullInits  OBJECT-TYPE
            SYNTAX      Unsigned32
            MAX-ACCESS  read-only
            STATUS      current
            DESCRIPTION
                "Count of full initializations attempted on the line
                 (successful and failed) since agent reset.
                 Huawei defined.
                "
            ::= { hwXdslPMLineCurrInitEntry 11 }

        hwXdslPMLInitEverBeforeFailedFullInits  OBJECT-TYPE
            SYNTAX      Unsigned32
            MAX-ACCESS  read-only
            STATUS      current
            DESCRIPTION
                "Count of failed full initializations on the line since agent
                 reset.
                 Huawei defined.
                "
            ::= { hwXdslPMLineCurrInitEntry 12 }

        hwXdslPMLInitEverBeforeShortInits  OBJECT-TYPE
            SYNTAX      Unsigned32
            MAX-ACCESS  read-only
            STATUS      current
            DESCRIPTION
                "Count of short initializations attempted on the line
                 (successful and failed) since agent reset.
                 Huawei defined.
                "
            ::= { hwXdslPMLineCurrInitEntry 13 }

        hwXdslPMLInitEverBeforeFailedShortInits  OBJECT-TYPE
            SYNTAX      Unsigned32
            MAX-ACCESS  read-only
            STATUS      current
            DESCRIPTION
                "Count of failed short initializations on the line since agent
                 reset.
                 Huawei defined.
                "
            ::= { hwXdslPMLineCurrInitEntry 14 }

        hwXdslPMLineCurrInit15MStartTime  OBJECT-TYPE
            SYNTAX      DateAndTime
            MAX-ACCESS  read-only
            STATUS      current
            DESCRIPTION
                "Start time of the current initializations 15-minute performance statistics."
            ::= { hwXdslPMLineCurrInitEntry 15 }

        hwXdslPMLineCurrInit1DayStartTime  OBJECT-TYPE
            SYNTAX      DateAndTime
            MAX-ACCESS  read-only
            STATUS      current
            DESCRIPTION
                "Start time of the current initializations 1-day performance statistics."
            ::= { hwXdslPMLineCurrInitEntry 16 }

        hwXdslPMLineCurrInit15MAbnormalReInit  OBJECT-TYPE
            SYNTAX      Unsigned32
            MAX-ACCESS  read-only
            STATUS      current
            DESCRIPTION
                "Count of abnormal re-init on the line during this interval.
                 Huawei defined.
                 The invalid value is 4294967295.
                "
            ::= { hwXdslPMLineCurrInitEntry 17 }

        hwXdslPMLineCurrInit1DayAbnormalReInit  OBJECT-TYPE
            SYNTAX      Unsigned32
            MAX-ACCESS  read-only
            STATUS      current
            DESCRIPTION
                "Count of abnormal re-init on the line during this interval.
                 Huawei defined.
                 The invalid value is 4294967295.
                "
            ::= { hwXdslPMLineCurrInitEntry 18 }

        hwXdslPMLineCurrInitEverBeforeAbnormalReInit  OBJECT-TYPE
            SYNTAX      Unsigned32
            MAX-ACCESS  read-only
            STATUS      current
            DESCRIPTION
                "Count of abnormal re-init on the line since agent reset.
                 Huawei defined.
                 The invalid value is 4294967295.
                "
            ::= { hwXdslPMLineCurrInitEntry 19 }

          --       PM line history 15 Minutes
        hwXdslPMLineHist15MinTable    OBJECT-TYPE
            SYNTAX      SEQUENCE  OF  HwXdslPMLineHist15MinEntry
            MAX-ACCESS  not-accessible
            STATUS      current
            DESCRIPTION
                "The table hwXdslPMLineHist15MinTable contains PM line history
                 for 15min intervals of XDSL line.
                 The indexes of this table are an interface index where the
                 interface has an ifType of VDSL2/FAST, the termination unit,
                 and an interval number.
                "
            ::= { hwXdslPMLine 3 }

        hwXdslPMLineHist15MinEntry  OBJECT-TYPE
            SYNTAX      HwXdslPMLineHist15MinEntry
            MAX-ACCESS  not-accessible
            STATUS      current
            DESCRIPTION
                "The table hwXdslPMLineHist15MinTable contains PM line history
                 for 15min intervals of XDSL line.
                 The indexes of this entry are an interface index where the
                 interface has an ifType of VDSL2/FAST, the termination unit,
                 and an interval number.
                "
            INDEX  { ifIndex,
                     hwXdslPMLHist15MUnit,
                     hwXdslPMLHist15MInterval }
            ::= { hwXdslPMLineHist15MinTable 1 }

        HwXdslPMLineHist15MinEntry  ::=
            SEQUENCE {
              hwXdslPMLHist15MUnit                 HwXdslUnit,
              hwXdslPMLHist15MInterval             Unsigned32,
              hwXdslPMLHist15MMonitoredTime        Unsigned32,
              hwXdslPMLHist15MFecs                 Counter32,
              hwXdslPMLHist15MEs                   Counter32,
              hwXdslPMLHist15MSes                  Counter32,
              hwXdslPMLHist15MLoss                 Counter32,
              hwXdslPMLHist15MUas                  Counter32,
              hwXdslPMLHist15MValidInterval        TruthValue,
              hwXdslPMLHist15MLofs                 Counter32,
              hwXdslPMLHist15MLols                 Counter32,
              hwXdslPMLHist15MLops                 Counter32,
              hwXdslPMLHist15MSosSuccess           Counter32,
              hwXdslPMLHist15MInmainpeq            OCTET STRING,
              hwXdslPMLHist15MInmame               Counter32,
              hwXdslPMLHist15MInmaiat              OCTET STRING,
              hwXdslPMLHist15MStartTime            DateAndTime,
              hwXdslPMLHist15MLeftrs               Counter32,
              hwXdslPMLHist15MEfb                  Counter32,
              hwXdslPMLHist15MMinEftr              Counter32,
              hwXdslPMLHist15MSraDownShiftEvent  Counter32,
              hwXdslPMLHist15MSraUpShiftEvent    Counter32,
              hwXdslPMLHist15MDisorderLeavingEvent Counter32,
              hwXdslPMLHist15MLof                Counter32,
              hwXdslPMLHist15MLos                Counter32,
              hwXdslPMLHist15MLop                Counter32,
              hwXdslPMLHist15MLom                Counter32,
              hwXdslPMLineHist15MLors            Counter32,
              hwXdslPMLineHist15MLor             Counter32,
              hwXdslPMLineHist15MRpaSuccess      Counter32,
              hwXdslPMLineHist15MBitswapSuccess  Counter32,
              hwXdslPMLineHist15MTigaSuccess     Counter32
            }

        hwXdslPMLHist15MUnit  OBJECT-TYPE
            SYNTAX      HwXdslUnit
            MAX-ACCESS  not-accessible
            STATUS      current
            DESCRIPTION
                "The termination unit XTUC{1} or XTUR{2}."
            ::= { hwXdslPMLineHist15MinEntry 1 }

        hwXdslPMLHist15MInterval  OBJECT-TYPE
            SYNTAX      Unsigned32
            MAX-ACCESS  not-accessible
            STATUS      current
            DESCRIPTION
                "The interval number."
            ::= { hwXdslPMLineHist15MinEntry 2 }

        hwXdslPMLHist15MMonitoredTime  OBJECT-TYPE
            SYNTAX      Unsigned32
            UNITS       "seconds"
            MAX-ACCESS  read-only
            STATUS      current
            DESCRIPTION
                "Total seconds monitored in this interval.
                 Unit: seconds
                "
            ::= { hwXdslPMLineHist15MinEntry 3 }

        hwXdslPMLHist15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwXdslPMLineHist15MinEntry 4 }

        hwXdslPMLHist15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwXdslPMLineHist15MinEntry 5 }

        hwXdslPMLHist15MSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { hwXdslPMLineHist15MinEntry 6 }

        hwXdslPMLHist15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwXdslPMLineHist15MinEntry 7 }

        hwXdslPMLHist15MUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwXdslPMLineHist15MinEntry 8 }

        hwXdslPMLHist15MValidInterval  OBJECT-TYPE
            SYNTAX      TruthValue
            MAX-ACCESS  read-only
            STATUS      current
            DESCRIPTION
                "This variable indicates if the data for this interval is
                 valid.
                "
            ::= { hwXdslPMLineHist15MinEntry 9 }

        hwXdslPMLHist15MLofs  OBJECT-TYPE
            SYNTAX      Counter32
            UNITS       "seconds"
            MAX-ACCESS  read-only
            STATUS      current
            DESCRIPTION
                "Count of seconds in the interval when there was Loss of Framing.
                 Unit: seconds
                "
            ::= { hwXdslPMLineHist15MinEntry 10 }

        hwXdslPMLHist15MLols  OBJECT-TYPE
            SYNTAX      Counter32
            UNITS       "seconds"
            MAX-ACCESS  read-only
            STATUS      current
            DESCRIPTION
                "Count of seconds in the interval when there was Loss of Link.
                 Unit: seconds
                "
            ::= { hwXdslPMLineHist15MinEntry 11 }

        hwXdslPMLHist15MLops  OBJECT-TYPE
            SYNTAX      Counter32
            UNITS       "seconds"
            MAX-ACCESS  read-only
            STATUS      current
            DESCRIPTION
                "Count of seconds in the interval when there was Loss of Power.
                 Unit: seconds
                "
            ::= { hwXdslPMLineHist15MinEntry 12 }

        hwXdslPMLHist15MSosSuccess  OBJECT-TYPE
            SYNTAX      Counter32
            UNITS       "times"
            MAX-ACCESS  read-only
            STATUS      current
            DESCRIPTION
                "If the line is activated as G9701 of hwXdslLineStatusXtuTransSys,
                 the parameter is count of the total number of successful FRA procedures
                 initiated in the interval. Otherwise, the parameter is count of
                 the total number of successful SOS procedures initiated in the interval.
                 Unit: times
                "
            REFERENCE    "ITU-T G.997.1, paragraph 7.2.1"
            ::= { hwXdslPMLineHist15MinEntry 13 }

        hwXdslPMLHist15MInmainpeq  OBJECT-TYPE
            SYNTAX      OCTET STRING  (SIZE(0..68))
            MAX-ACCESS  read-only
            STATUS      current
            DESCRIPTION
                "This parameter is a count of the INMAINPEQi anomalies occurring on the line over the 15 minutes accumulation period.
                 Each INMAINPEQ needs 4 bytes, Each four bytes, arranged in descending significance order from left to right,
                 correspond to one INMAINPEQ. For example, bytes 0-3 correspond to INMAINPEQ1, bytes 4-7 correspond to INMAINPEQ2.
                 The later is deduced in the same way. The INMAINPEQ value can be converted into a decimal value. For example,
                 the decimal value of 00 00 00 F0 is 240.
                "
            REFERENCE    "ITU-T G.997.1, paragraph 7.2.1"
            ::= { hwXdslPMLineHist15MinEntry 14 }

        hwXdslPMLHist15MInmame  OBJECT-TYPE
            SYNTAX      Counter32
            MAX-ACCESS  read-only
            STATUS      current
            DESCRIPTION
                "This parameter is a count of the INMAME anomalies
                 occurring on the line over the 15 minutes accumulation period.
                "
            REFERENCE    "ITU-T G.997.1, paragraph 7.2.1"
            ::= { hwXdslPMLineHist15MinEntry 15}

        hwXdslPMLHist15MInmaiat  OBJECT-TYPE
            SYNTAX      OCTET STRING  (SIZE(0..32))
            MAX-ACCESS  read-only
            STATUS      current
            DESCRIPTION
                "This parameter is a count of the INMAIATi anomalies occurring on the line over the 15 minutes accumulation period.
                 Each INMAIAT needs 4 bytes. Each four bytes, arranged in descending significance order from left to right,
                 correspond to one INMAIAT. For example,bytes 0-3 correspond to INMAIAT0, bytes 4-7 correspond to INMAIAT1.
                 The later is deduced in the same way. The INMAIAT value can be converted into a decimal value. For example,
                 the decimal value of 00 00 00 F0 is 240.
                "
            REFERENCE    "ITU-T G.997.1, paragraph 7.2.1"
            ::= { hwXdslPMLineHist15MinEntry 16}

        hwXdslPMLHist15MStartTime  OBJECT-TYPE
            SYNTAX      DateAndTime
            MAX-ACCESS  read-only
            STATUS      current
            DESCRIPTION
                "Start time of the historical 15-minute performance statistics."
            ::= { hwXdslPMLineHist15MinEntry 17 }

        hwXdslPMLHist15MLeftrs     OBJECT-TYPE
            SYNTAX      Counter32
            MAX-ACCESS  read-only
            STATUS      current
            DESCRIPTION
                "If retransmission is used in a given transmit direction, this parameter
                 is a count of the seconds with a near-end leftr defect present observed
                 over the 15 minutes accumulation period.
                "
            REFERENCE    "ITU-T G.997.1, paragraph 7.2.1.1.6 7.2.1.2.6"
            ::= { hwXdslPMLineHist15MinEntry 18 }

        hwXdslPMLHist15MEfb        OBJECT-TYPE
            SYNTAX      Counter32
            MAX-ACCESS  read-only
            STATUS      current
            DESCRIPTION
                "If retransmission is used in a given transmit direction, this parameter
                 is a count of the number of error-free bits observed over the 15 minutes
                 accumulation period.
                "
            REFERENCE    "ITU-T G.997.1, paragraph 7.2.1.1.7 7.2.1.2.7"
            ::= { hwXdslPMLineHist15MinEntry 19 }

        hwXdslPMLHist15MMinEftr    OBJECT-TYPE
            SYNTAX      Counter32
            MAX-ACCESS  read-only
            STATUS      current
            DESCRIPTION
                "If retransmission is used in a given transmit direction, this parameter
                 reports the minimum of the EFTR(Error-free throughput rate) observed
                 over the 15 minutes accumulation period.
                "
            REFERENCE    "ITU-T G.997.1, paragraph 7.2.1.1.8 7.2.1.2.8"
            ::= { hwXdslPMLineHist15MinEntry 20 }

        hwXdslPMLHist15MSraDownShiftEvent OBJECT-TYPE
            SYNTAX      Counter32
            MAX-ACCESS  read-only
            STATUS      current
            DESCRIPTION
                "This parameter is a count of sra down-shift event occurring on the line over the 15 minutes accumulation period."
            ::= { hwXdslPMLineHist15MinEntry 21 }

        hwXdslPMLHist15MSraUpShiftEvent OBJECT-TYPE
            SYNTAX      Counter32
            MAX-ACCESS  read-only
            STATUS      current
            DESCRIPTION
                "This parameter is a count of sra up-shift event occurring on the line over the 15 minutes accumulation period."
            ::= { hwXdslPMLineHist15MinEntry 22 }

        hwXdslPMLHist15MDisorderLeavingEvent OBJECT-TYPE
            SYNTAX      Counter32
            MAX-ACCESS  read-only
            STATUS      current
            DESCRIPTION
                "This parameter is a count of disorder leaving event occurring on the line over the 15 minutes accumulation period."
            ::= { hwXdslPMLineHist15MinEntry 23 }

        hwXdslPMLHist15MLof OBJECT-TYPE
            SYNTAX      Counter32
            MAX-ACCESS  read-only
            STATUS      current
            DESCRIPTION
                "This parameter is a count of loss of frame failure occurring on the line over the 15 minutes accumulation period."
            ::= { hwXdslPMLineHist15MinEntry 24 }

        hwXdslPMLHist15MLos OBJECT-TYPE
            SYNTAX      Counter32
            MAX-ACCESS  read-only
            STATUS      current
            DESCRIPTION
                "This parameter is a count of loss of signal failure occurring on the line over the 15 minutes accumulation period."
            ::= { hwXdslPMLineHist15MinEntry 25 }

        hwXdslPMLHist15MLop OBJECT-TYPE
            SYNTAX      Counter32
            MAX-ACCESS  read-only
            STATUS      current
            DESCRIPTION
                "This parameter is a count of loss of power failure occurring on the line over the 15 minutes accumulation period."
            ::= { hwXdslPMLineHist15MinEntry 26 }

        hwXdslPMLHist15MLom OBJECT-TYPE
            SYNTAX      Counter32
            MAX-ACCESS  read-only
            STATUS      current
            DESCRIPTION
                "This parameter is a count of loss of margin failure occurring on the line over the 15 minutes accumulation period."
            ::= { hwXdslPMLineHist15MinEntry 27 }

        hwXdslPMLineHist15MLors OBJECT-TYPE
            SYNTAX      Counter32
            MAX-ACCESS  read-only
            STATUS      current
            DESCRIPTION
                "This parameter is a count of LOR second occurring on the line over the 15 minutes accumulation period."
            ::= { hwXdslPMLineHist15MinEntry 28 }

        hwXdslPMLineHist15MLor OBJECT-TYPE
            SYNTAX      Counter32
            MAX-ACCESS  read-only
            STATUS      current
            DESCRIPTION
                "This parameter is a count of loss of RMC failure occurring on the line over the 15 minutes accumulation period."
            ::= { hwXdslPMLineHist15MinEntry 29 }

        hwXdslPMLineHist15MRpaSuccess OBJECT-TYPE
            SYNTAX      Counter32
            MAX-ACCESS  read-only
            STATUS      current
            DESCRIPTION
                "This parameter is a count of the successful RPA primitives occurring on the line over the 15 minutes accumulation period."
            ::= { hwXdslPMLineHist15MinEntry 30 }

        hwXdslPMLineHist15MBitswapSuccess OBJECT-TYPE
            SYNTAX      Counter32
            MAX-ACCESS  read-only
            STATUS      current
            DESCRIPTION
                "This parameter is a count of the successful Bitswap primitives occurring on the line over the 15 minutes accumulation period."
            ::= { hwXdslPMLineHist15MinEntry 31 }

        hwXdslPMLineHist15MTigaSuccess OBJECT-TYPE
            SYNTAX      Counter32
            MAX-ACCESS  read-only
            STATUS      current
            DESCRIPTION
                "This parameter is a count of the successful TIGA primitives occurring on the line over the 15 minutes accumulation period."
            ::= { hwXdslPMLineHist15MinEntry 32 }

          --       PM line history 1 Day
        hwXdslPMLineHist1DayTable     OBJECT-TYPE
            SYNTAX      SEQUENCE  OF  HwXdslPMLineHist1DayEntry
            MAX-ACCESS  not-accessible
            STATUS      current
            DESCRIPTION
                "The table hwXdslPMLineHist1DayTable contains PM line history
                 for 24 hours intervals of XDSL line.
                 The indexes of this table are an interface index where the
                 interface has an ifType of VDSL2/FAST, the termination unit
                 and an interval number.
                "
            ::= { hwXdslPMLine 4 }

        hwXdslPMLineHist1DayEntry  OBJECT-TYPE
            SYNTAX      HwXdslPMLineHist1DayEntry
            MAX-ACCESS  not-accessible
            STATUS      current
            DESCRIPTION
                "The table hwXdslPMLineHist1DayTable contains PM line history
                 for 24 hours intervals of XDSL line.
                 The indexes of this entry are an interface index where the
                 interface has an ifType of VDSL2/FAST, the termination unit
                 and an interval number.
                "
            INDEX  { ifIndex,
                     hwXdslPMLHist1DUnit,
                     hwXdslPMLHist1DInterval }
            ::= { hwXdslPMLineHist1DayTable 1 }

        HwXdslPMLineHist1DayEntry  ::=
            SEQUENCE {
              hwXdslPMLHist1DUnit              HwXdslUnit,
              hwXdslPMLHist1DInterval          Unsigned32,
              hwXdslPMLHist1DMonitoredTime     Unsigned32,
              hwXdslPMLHist1DFecs              Counter32,
              hwXdslPMLHist1DEs                Counter32,
              hwXdslPMLHist1DSes               Counter32,
              hwXdslPMLHist1DLoss              Counter32,
              hwXdslPMLHist1DUas               Counter32,
              hwXdslPMLHist1DValidInterval     TruthValue,
              hwXdslPMLHist1DLofs              Counter32,
              hwXdslPMLHist1DLols              Counter32,
              hwXdslPMLHist1DLops              Counter32,
              hwXdslPMLHist1DSosSuccess        Counter32,
              hwXdslPMLHist1DInmainpeq         OCTET STRING,
              hwXdslPMLHist1DInmame            Counter32,
              hwXdslPMLHist1DInmaiat           OCTET STRING,
              hwXdslPMLHist1DStartTime         DateAndTime,
              hwXdslPMLHist1DLeftrs            Counter32,
              hwXdslPMLHist1DEfb               Counter32,
              hwXdslPMLHist1DMinEftr           Counter32,
              hwXdslPMLHist1DSraDownShiftEvent  Counter32,
              hwXdslPMLHist1DSraUpShiftEvent    Counter32,
              hwXdslPMLHist1DDisorderLeavingEvent Counter32,
              hwXdslPMLHist1DLof             Counter32,
              hwXdslPMLHist1DLos             Counter32,
              hwXdslPMLHist1DLop             Counter32,
              hwXdslPMLHist1DLom             Counter32,
              hwXdslPMLineHist1DayLors       Counter32,
              hwXdslPMLineHist1DayLor        Counter32,
              hwXdslPMLineHist1DayRpaSuccess Counter32,
              hwXdslPMLineHist1DayBitswapSuccess    Counter32,
              hwXdslPMLineHist1DayTigaSuccess       Counter32
            }

        hwXdslPMLHist1DUnit  OBJECT-TYPE
            SYNTAX      HwXdslUnit
            MAX-ACCESS  not-accessible
            STATUS      current
            DESCRIPTION
                "The termination unit."
            ::= { hwXdslPMLineHist1DayEntry 1 }

        hwXdslPMLHist1DInterval  OBJECT-TYPE
            SYNTAX      Unsigned32
            MAX-ACCESS  not-accessible
            STATUS      current
            DESCRIPTION
                "The interval number."
            ::= { hwXdslPMLineHist1DayEntry 2 }

        hwXdslPMLHist1DMonitoredTime  OBJECT-TYPE
            SYNTAX      Unsigned32
            UNITS       "seconds"
            MAX-ACCESS  read-only
            STATUS      current
            DESCRIPTION
                "Total seconds monitored in this interval.
                 Unit: seconds
                "
            ::= { hwXdslPMLineHist1DayEntry 3 }

        hwXdslPMLHist1DFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwXdslPMLineHist1DayEntry 4 }

        hwXdslPMLHist1DEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwXdslPMLineHist1DayEntry 5 }

        hwXdslPMLHist1DSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;&gt; 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { hwXdslPMLineHist1DayEntry 6 }

        hwXdslPMLHist1DLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwXdslPMLineHist1DayEntry 7 }

        hwXdslPMLHist1DUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwXdslPMLineHist1DayEntry 8 }

        hwXdslPMLHist1DValidInterval  OBJECT-TYPE
            SYNTAX      TruthValue
            MAX-ACCESS  read-only
            STATUS      current
            DESCRIPTION
                "This variable indicates if the data for this interval is
                 valid.
                "
            ::= { hwXdslPMLineHist1DayEntry 9 }

        hwXdslPMLHist1DLofs  OBJECT-TYPE
            SYNTAX      Counter32
            UNITS       "seconds"
            MAX-ACCESS  read-only
            STATUS      current
            DESCRIPTION
                "Count of seconds during this interval that there was Loss of Framing.
                 Unit: seconds
                "
            ::= { hwXdslPMLineHist1DayEntry 10 }

        hwXdslPMLHist1DLols  OBJECT-TYPE
            SYNTAX      Counter32
            UNITS       "seconds"
            MAX-ACCESS  read-only
            STATUS      current
            DESCRIPTION
                "Count of seconds during this interval that there was Loss of Link.
                 Unit: seconds
                "
            ::= { hwXdslPMLineHist1DayEntry 11 }

        hwXdslPMLHist1DLops  OBJECT-TYPE
            SYNTAX      Counter32
            UNITS       "seconds"
            MAX-ACCESS  read-only
            STATUS      current
            DESCRIPTION
                "Count of seconds during this interval that there was Loss of Power.
                 Unit: seconds
                "
            ::= { hwXdslPMLineHist1DayEntry 12 }

        hwXdslPMLHist1DSosSuccess  OBJECT-TYPE
            SYNTAX      Counter32
            UNITS       "times"
            MAX-ACCESS  read-only
            STATUS      current
            DESCRIPTION
                "If the line is activated as G9701 of hwXdslLineStatusXtuTransSys,
                 the parameter is count of the total number of successful FRA procedures
                 initiated during this interval. Otherwise, the parameter is count of
                 the total number of successful SOS procedures initiated during this interval.
                 Unit: times
                "
            REFERENCE    "ITU-T G.997.1, paragraph 7.2.1"
            ::= { hwXdslPMLineHist1DayEntry 13 }


        hwXdslPMLHist1DInmainpeq  OBJECT-TYPE
            SYNTAX      OCTET STRING  (SIZE(0..68))
            MAX-ACCESS  read-only
            STATUS      current
            DESCRIPTION
                "This parameter is a count of the INMAINPEQi anomalies occurring on the line over the 24 hours accumulation period.
                 Each INMAINPEQ needs 4 bytes, Each four bytes, arranged in descending significance order from left to right,
                 correspond to one INMAINPEQ. For example, bytes 0-3 correspond to INMAINPEQ1, bytes 4-7 correspond to INMAINPEQ2.
                 The later is deduced in the same way. The INMAINPEQ value can be converted into a decimal value. For example,
                 the decimal value of 00 00 00 F0 is 240.
                "
            REFERENCE    "ITU-T G.997.1, paragraph 7.2.1"
            ::= { hwXdslPMLineHist1DayEntry 14 }

        hwXdslPMLHist1DInmame  OBJECT-TYPE
            SYNTAX      Counter32
            MAX-ACCESS  read-only
            STATUS      current
            DESCRIPTION
                "This parameter is a count of the INMAME anomalies
                 occurring on the line over the 24 hours accumulation period.
                "
            REFERENCE    "ITU-T G.997.1, paragraph 7.2.1"
            ::= { hwXdslPMLineHist1DayEntry 15 }

        hwXdslPMLHist1DInmaiat  OBJECT-TYPE
            SYNTAX      OCTET STRING  (SIZE(0..32))
            MAX-ACCESS  read-only
            STATUS      current
            DESCRIPTION
                "This parameter is a count of the INMAIATi anomalies occurring on the line over the 24 hours accumulation period.
                 Each INMAIAT needs 4 bytes. Each four bytes, arranged in descending significance order from left to right,
                 correspond to one INMAIAT. For example,bytes 0-3 correspond to INMAIAT0, bytes 4-7 correspond to INMAIAT1.
                 The later is deduced in the same way. The INMAIAT value can be converted into a decimal value. For example,
                 the decimal value of 00 00 00 F0 is 240.
                "
            REFERENCE    "ITU-T G.997.1, paragraph 7.2.1"
            ::= { hwXdslPMLineHist1DayEntry 16 }

        hwXdslPMLHist1DStartTime  OBJECT-TYPE
            SYNTAX      DateAndTime
            MAX-ACCESS  read-only
            STATUS      current
            DESCRIPTION
                "Start time of the historical 1-day performance statistics."
            ::= { hwXdslPMLineHist1DayEntry 17 }

       hwXdslPMLHist1DLeftrs     OBJECT-TYPE
            SYNTAX      Counter32
            MAX-ACCESS  read-only
            STATUS      current
            DESCRIPTION
                "If retransmission is used in a given transmit direction, this parameter
                 is a count of the seconds with a near-end leftr defect present observed
                 over the 24 hours accumulation period.
                "
            REFERENCE    "ITU-T G.997.1, paragraph 7.2.1.1.6 7.2.1.2.6"
            ::= { hwXdslPMLineHist1DayEntry 18 }

        hwXdslPMLHist1DEfb        OBJECT-TYPE
            SYNTAX      Counter32
            MAX-ACCESS  read-only
            STATUS      current
            DESCRIPTION
                "If retransmission is used in a given transmit direction, this parameter
                 is a count of the number of error-free bits observed over the 24 hours
                 accumulation period.
                "
            REFERENCE    "ITU-T G.997.1, paragraph 7.2.1.1.7 7.2.1.2.7"
            ::= { hwXdslPMLineHist1DayEntry 19 }

        hwXdslPMLHist1DMinEftr    OBJECT-TYPE
            SYNTAX      Counter32
            MAX-ACCESS  read-only
            STATUS      current
            DESCRIPTION
                "If retransmission is used in a given transmit direction, this parameter
                 reports the minimum of the EFTR(Error-free throughput rate) observed
                 over the 24 hours accumulation period.
                "
            REFERENCE    "ITU-T G.997.1, paragraph 7.2.1.1.8 7.2.1.2.8"
            ::= { hwXdslPMLineHist1DayEntry 20 }

        hwXdslPMLHist1DSraDownShiftEvent OBJECT-TYPE
            SYNTAX      Counter32
            MAX-ACCESS  read-only
            STATUS      current
            DESCRIPTION
                "This parameter is a count of sra down-shift event occurring on the line over the 24 hours accumulation period."
            ::= { hwXdslPMLineHist1DayEntry 21 }

        hwXdslPMLHist1DSraUpShiftEvent OBJECT-TYPE
            SYNTAX      Counter32
            MAX-ACCESS  read-only
            STATUS      current
            DESCRIPTION
                "This parameter is a count of sra up-shift event occurring on the line over the 24 hours accumulation period."
            ::= { hwXdslPMLineHist1DayEntry 22 }

        hwXdslPMLHist1DDisorderLeavingEvent OBJECT-TYPE
            SYNTAX      Counter32
            MAX-ACCESS  read-only
            STATUS      current
            DESCRIPTION
                "This parameter is a count of disorder leaving event occurring on the line over the 24 hours accumulation period."
            ::= { hwXdslPMLineHist1DayEntry 23 }

        hwXdslPMLHist1DLof OBJECT-TYPE
            SYNTAX      Counter32
            MAX-ACCESS  read-only
            STATUS      current
            DESCRIPTION
                "This parameter is a count of loss of frame failure occurring on the line over the 24 hours accumulation period."
            ::= { hwXdslPMLineHist1DayEntry 24 }

        hwXdslPMLHist1DLos OBJECT-TYPE
            SYNTAX      Counter32
            MAX-ACCESS  read-only
            STATUS      current
            DESCRIPTION
                "This parameter is a count of loss of signal failure occurring on the line over the 24 hours accumulation period."
            ::= { hwXdslPMLineHist1DayEntry 25 }

        hwXdslPMLHist1DLop OBJECT-TYPE
            SYNTAX      Counter32
            MAX-ACCESS  read-only
            STATUS      current
            DESCRIPTION
                "This parameter is a count of loss of power failure occurring on the line over the 24 hours accumulation period."
            ::= { hwXdslPMLineHist1DayEntry 26 }

        hwXdslPMLHist1DLom OBJECT-TYPE
            SYNTAX      Counter32
            MAX-ACCESS  read-only
            STATUS      current
            DESCRIPTION
                "This parameter is a count of loss of margin failure occurring on the line over the 24 hours accumulation period."
            ::= { hwXdslPMLineHist1DayEntry 27 }

        hwXdslPMLineHist1DayLors OBJECT-TYPE
            SYNTAX      Counter32
            MAX-ACCESS  read-only
            STATUS      current
            DESCRIPTION
                "This parameter is a count of LOR second occurring on the line over the 24 hours accumulation period."
            ::= { hwXdslPMLineHist1DayEntry 28 }

        hwXdslPMLineHist1DayLor OBJECT-TYPE
            SYNTAX      Counter32
            MAX-ACCESS  read-only
            STATUS      current
            DESCRIPTION
                "This parameter is a count of loss of RMC failure occurring on the line over the 24 hours accumulation period."
            ::= { hwXdslPMLineHist1DayEntry 29 }

        hwXdslPMLineHist1DayRpaSuccess OBJECT-TYPE
            SYNTAX      Counter32
            MAX-ACCESS  read-only
            STATUS      current
            DESCRIPTION
                "This parameter is a count of the successful RPA primitives occurring on the line over the 24 hours accumulation period."
            ::= { hwXdslPMLineHist1DayEntry 30 }

        hwXdslPMLineHist1DayBitswapSuccess OBJECT-TYPE
            SYNTAX      Counter32
            MAX-ACCESS  read-only
            STATUS      current
            DESCRIPTION
                "This parameter is a count of the successful Bitswap primitives occurring on the line over the 24 hours accumulation period."
            ::= { hwXdslPMLineHist1DayEntry 31 }

        hwXdslPMLineHist1DayTigaSuccess OBJECT-TYPE
            SYNTAX      Counter32
            MAX-ACCESS  read-only
            STATUS      current
            DESCRIPTION
                "This parameter is a count of the successful TIGA primitives occurring on the line over the 24 hours accumulation period."
            ::= { hwXdslPMLineHist1DayEntry 32 }

          --     PM line init history 15 Minutes

        hwXdslPMLineInitHist15MinTable      OBJECT-TYPE
            SYNTAX      SEQUENCE  OF  HwXdslPMLineInitHist15MinEntry
            MAX-ACCESS  not-accessible
            STATUS      current
            DESCRIPTION
                "The table hwXdslPMLineInitHist15MinTable contains PM line
                 initialization history for 15 minutes intervals of XDSL line.
                 The indexes of this table are an interface index where the
                 interface has an ifType of VDSL2/FAST and an interval number.
                "
            ::= { hwXdslPMLine 5 }

        hwXdslPMLineInitHist15MinEntry  OBJECT-TYPE
            SYNTAX      HwXdslPMLineInitHist15MinEntry
            MAX-ACCESS  not-accessible
            STATUS      current
            DESCRIPTION
                "The table hwXdslPMLineInitHist15MinTable contains PM line
                 initialization history for 15 minutes intervals of XDSL line.
                 The indexes of this entry are an interface index where the
                 interface has an ifType of VDSL2/FAST and an interval number.
                "
            INDEX  { ifIndex,
                     hwXdslPMLHistInit15MInterval }
            ::= { hwXdslPMLineInitHist15MinTable 1 }

        HwXdslPMLineInitHist15MinEntry  ::=
            SEQUENCE {
              hwXdslPMLHistInit15MInterval              Unsigned32,
              hwXdslPMLHistInit15MMonitoredTime         Unsigned32,
              hwXdslPMLHistInit15MFullInits             Unsigned32,
              hwXdslPMLHistInit15MFailedFullInits       Unsigned32,
              hwXdslPMLHistInit15MShortInits            Unsigned32,
              hwXdslPMLHistInit15MFailedShortInits      Unsigned32,
              hwXdslPMLHistInit15MValidInterval         TruthValue,
              hwXdslPMLHistInit15MStartTime             DateAndTime,
              hwXdslPMLHistInit15MAbnormalReInit        Unsigned32
            }

        hwXdslPMLHistInit15MInterval  OBJECT-TYPE
            SYNTAX      Unsigned32
            MAX-ACCESS  not-accessible
            STATUS      current
            DESCRIPTION
                "The interval number."
            ::= { hwXdslPMLineInitHist15MinEntry 1 }

        hwXdslPMLHistInit15MMonitoredTime  OBJECT-TYPE
            SYNTAX      Unsigned32
            UNITS       "seconds"
            MAX-ACCESS  read-only
            STATUS      current
            DESCRIPTION
                "Total seconds monitored in this interval.
                 Unit: seconds
                "
            ::= { hwXdslPMLineInitHist15MinEntry 2 }

        hwXdslPMLHistInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwXdslPMLineInitHist15MinEntry 3 }

        hwXdslPMLHistInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwXdslPMLineInitHist15MinEntry 4 }

        hwXdslPMLHistInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwXdslPMLineInitHist15MinEntry 5 }

        hwXdslPMLHistInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwXdslPMLineInitHist15MinEntry 6 }

        hwXdslPMLHistInit15MValidInterval  OBJECT-TYPE
            SYNTAX      TruthValue
            MAX-ACCESS  read-only
            STATUS      current
            DESCRIPTION
                "This variable indicates if the data for this interval is
                 valid.
                "
            ::= { hwXdslPMLineInitHist15MinEntry 7 }

        hwXdslPMLHistInit15MStartTime  OBJECT-TYPE
            SYNTAX      DateAndTime
            MAX-ACCESS  read-only
            STATUS      current
            DESCRIPTION
                "Start time of the historical initializations 15-minute performance statistics."
            ::= { hwXdslPMLineInitHist15MinEntry 8 }

        hwXdslPMLHistInit15MAbnormalReInit  OBJECT-TYPE
            SYNTAX      Unsigned32
            MAX-ACCESS  read-only
            STATUS      current
            DESCRIPTION
                "Count of abnormal re-init on the line during this
                 interval.
                 The invalid value is 4294967295.
                "
            ::= { hwXdslPMLineInitHist15MinEntry 9 }

          --       PM line init history 1 Day
        hwXdslPMLineInitHist1DayTable       OBJECT-TYPE
            SYNTAX      SEQUENCE  OF  HwXdslPMLineInitHist1DayEntry
            MAX-ACCESS  not-accessible
            STATUS      current
            DESCRIPTION
                "The table hwXdslPMLineInitHist1DayTable contains PM line
                 initialization history for 24 hours intervals of XDSL line.
                 The indexes of this table are an interface index where the
                 interface has an ifType of VDSL2/FAST and an interval number.
                "
            ::= { hwXdslPMLine 6 }

        hwXdslPMLineInitHist1DayEntry  OBJECT-TYPE
            SYNTAX      HwXdslPMLineInitHist1DayEntry
            MAX-ACCESS  not-accessible
            STATUS      current
            DESCRIPTION
                "The table hwXdslPMLineInitHist1DayTable contains PM line
                 initialization history for 24 hours intervals of XDSL line.
                 The indexes of this entry are an interface index where the
                 interface has an ifType of VDSL2/FAST and an interval number.
                "
            INDEX  { ifIndex,
                     hwXdslPMLHistinit1DInterval }
            ::= { hwXdslPMLineInitHist1DayTable 1 }

        HwXdslPMLineInitHist1DayEntry  ::=
            SEQUENCE {
              hwXdslPMLHistinit1DInterval              Unsigned32,
              hwXdslPMLHistinit1DMonitoredTime         Unsigned32,
              hwXdslPMLHistinit1DFullInits             Unsigned32,
              hwXdslPMLHistinit1DFailedFullInits       Unsigned32,
              hwXdslPMLHistinit1DShortInits            Unsigned32,
              hwXdslPMLHistinit1DFailedShortInits      Unsigned32,
              hwXdslPMLHistinit1DValidInterval         TruthValue,
              hwXdslPMLHistinit1DStartTime             DateAndTime,
              hwXdslPMLHistinit1DAbnormalReInit        Unsigned32
            }

        hwXdslPMLHistinit1DInterval  OBJECT-TYPE
            SYNTAX      Unsigned32
            MAX-ACCESS  not-accessible
            STATUS      current
            DESCRIPTION
                "The interval number."
            ::= { hwXdslPMLineInitHist1DayEntry 1 }

        hwXdslPMLHistinit1DMonitoredTime  OBJECT-TYPE
            SYNTAX      Unsigned32
            UNITS       "seconds"
            MAX-ACCESS  read-only
            STATUS      current
            DESCRIPTION
                "Total seconds monitored in this interval."
            ::= { hwXdslPMLineInitHist1DayEntry 2 }

        hwXdslPMLHistinit1DFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
             ::= { hwXdslPMLineInitHist1DayEntry 3 }

        hwXdslPMLHistinit1DFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwXdslPMLineInitHist1DayEntry 4 }

        hwXdslPMLHistinit1DShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwXdslPMLineInitHist1DayEntry 5 }

        hwXdslPMLHistinit1DFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwXdslPMLineInitHist1DayEntry 6 }

        hwXdslPMLHistinit1DValidInterval  OBJECT-TYPE
            SYNTAX      TruthValue
            MAX-ACCESS  read-only
            STATUS      current
            DESCRIPTION
                "This variable indicates if the data for this interval is
                 valid.
                "
            ::= { hwXdslPMLineInitHist1DayEntry 7 }

        hwXdslPMLHistinit1DStartTime  OBJECT-TYPE
            SYNTAX      DateAndTime
            MAX-ACCESS  read-only
            STATUS      current
            DESCRIPTION
                "Start time of the historical initializations 1-day performance statistics."
            ::= { hwXdslPMLineInitHist1DayEntry 8 }

        hwXdslPMLHistinit1DAbnormalReInit  OBJECT-TYPE
            SYNTAX      Unsigned32
            MAX-ACCESS  read-only
            STATUS      current
            DESCRIPTION
                "Count of abnormal re-init on the line during this
                 interval.
                 The invalid value is 4294967295.
                "
            ::= { hwXdslPMLineInitHist1DayEntry 9 }

        --          PM ont xdsl port line current counters
       hwOntXdslPMLineCurrTable  OBJECT-TYPE
            SYNTAX      SEQUENCE  OF  HwOntXdslPMLineCurrEntry
            MAX-ACCESS  not-accessible
            STATUS      current
            DESCRIPTION
                "The table hwOntXdslPMLineCurrTable contains current Performance
                 Monitoring results of the ONT XDSL port line.
                 The indexes of this table are ifIndex, hwOntObjectIndex, hwOntUniPhyType, hwOntXdslPortid
                 and the termination unit.
                "
            ::= { hwXdslPMLine 7 }
        hwOntXdslPMLineCurrEntry  OBJECT-TYPE
            SYNTAX      HwOntXdslPMLineCurrEntry
            MAX-ACCESS  not-accessible
            STATUS      current
            DESCRIPTION
                "The table hwOntXdslPMLineCurrTable contains current Performance
                 Monitoring results of the ONT XDSL port line.
                 The indexes of this entry are ifIndex, hwOntObjectIndex, hwOntUniPhyType, hwOntXdslPortid
                 and the termination unit.
                "
            INDEX  { ifIndex,
                     hwOntObjectIndex,
                     hwOntUniPhyType,
                     hwOntXdslPortid,
                     hwOntXdslPMLCurrUnit }
            ::= { hwOntXdslPMLineCurrTable 1 }
        HwOntXdslPMLineCurrEntry  ::=
            SEQUENCE {
              hwOntXdslPMLCurrUnit                    HwXdslUnit,
              hwOntXdslPMLCurrValidIntervals          Unsigned32,
              hwOntXdslPMLCurrInvalidIntervals        Unsigned32,
              hwOntXdslPMLCurr15MTimeElapsed          HCPerfTimeElapsed,
              hwOntXdslPMLCurr15MFecs                 Counter32,
              hwOntXdslPMLCurr15MEs                   Counter32,
              hwOntXdslPMLCurr15MSes                  Counter32,
              hwOntXdslPMLCurr15MLoss                 Counter32,
              hwOntXdslPMLCurr15MUas                  Counter32,
              hwOntXdslPMLCurr1DayValidIntervals      Unsigned32,
              hwOntXdslPMLCurr1DayInvalidIntervals    Unsigned32,
              hwOntXdslPMLCurr1DayTimeElapsed         HCPerfTimeElapsed,
              hwOntXdslPMLCurr1DayFecs                Counter32,
              hwOntXdslPMLCurr1DayEs                  Counter32,
              hwOntXdslPMLCurr1DaySes                 Counter32,
              hwOntXdslPMLCurr1DayLoss                Counter32,
              hwOntXdslPMLCurr1DayUas                 Counter32,
              hwOntXdslPMLEverBeforeFecs              Counter32,
              hwOntXdslPMLEverBeforeEs                Counter32,
              hwOntXdslPMLEverBeforeSes               Counter32,
              hwOntXdslPMLEverBeforeLoss              Counter32,
              hwOntXdslPMLEverBeforeUas               Counter32,
              hwOntXdslPMLCurr15MLofs                 Counter32,
              hwOntXdslPMLCurr15MLols                 Counter32,
              hwOntXdslPMLCurr15MLops                 Counter32,
              hwOntXdslPMLCurr1DayLofs                Counter32,
              hwOntXdslPMLCurr1DayLols                Counter32,
              hwOntXdslPMLCurr1DayLops                Counter32,
              hwOntXdslPMLEverBeforeLofs              Counter32,
              hwOntXdslPMLEverBeforeLols              Counter32,
              hwOntXdslPMLEverBeforeLops              Counter32,
              hwOntXdslPMLCurr15MSosSuccess           Counter32,
              hwOntXdslPMLCurr1DaySosSuccess          Counter32,
              hwOntXdslPMLEverBeforeSosSuccess        Counter32,
              hwOntXdslPMLCurr15MInmainpeq            OCTET STRING,
              hwOntXdslPMLCurr15MInmame               Counter32,
              hwOntXdslPMLCurr15MInmaiat              OCTET STRING,
              hwOntXdslPMLCurr1DayInmainpeq           OCTET STRING,
              hwOntXdslPMLCurr1DayInmame              Counter32,
              hwOntXdslPMLCurr1DayInmaiat             OCTET STRING,
              hwOntXdslPMLEverBeforeInmainpeq         OCTET STRING,
              hwOntXdslPMLEverBeforeInmame            Counter32,
              hwOntXdslPMLEverBeforeInmaiat           OCTET STRING,
              hwOntXdslPMLineCurr15MStartTime         DateAndTime,
              hwOntXdslPMLineCurr1DayStartTime        DateAndTime,
              hwOntXdslPMLCurr15MLeftrs               Counter32,
              hwOntXdslPMLCurr15MEfb                  Counter32,
              hwOntXdslPMLCurr15MMinEftr              Counter32,
              hwOntXdslPMLCurr1DayLeftrs              Counter32,
              hwOntXdslPMLCurr1DayEfb                 Counter32,
              hwOntXdslPMLCurr1DayMinEftr             Counter32,
              hwOntXdslPMLEverBeforeLeftrs            Counter32,
              hwOntXdslPMLEverBeforeEfb               Counter32,
              hwOntXdslPMLEverBeforeMinEftr           Counter32
            }
        hwOntXdslPMLCurrUnit  OBJECT-TYPE
            SYNTAX      HwXdslUnit
            MAX-ACCESS  not-accessible
            STATUS      current
            DESCRIPTION
                "The termination unit XTUC{1} or XTUR{2}."
            ::= { hwOntXdslPMLineCurrEntry 1 }
        hwOntXdslPMLCurrValidIntervals  OBJECT-TYPE
            SYNTAX      Unsigned32
            MAX-ACCESS  read-only
            STATUS      current
            DESCRIPTION
                "Valid intervals."
            ::= { hwOntXdslPMLineCurrEntry 2 }
        hwOntXdslPMLCurrInvalidIntervals  OBJECT-TYPE
            SYNTAX      Unsigned32
            MAX-ACCESS  read-only
            STATUS      current
            DESCRIPTION
                "Invalid intervals."
            ::= { hwOntXdslPMLineCurrEntry 3 }
        hwOntXdslPMLCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { hwOntXdslPMLineCurrEntry 4 }
        hwOntXdslPMLCurr15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwOntXdslPMLineCurrEntry 5 }
        hwOntXdslPMLCurr15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;=1 OR LPR &gt;= 1
                 xTU-R: FEBE &gt;= 1 for one or more bearer channels OR
                        LOS-FE &gt;=1 OR RDI &gt;=1 OR LPR-FE &gt;=1 .
                 This parameter is inhibited during UAS.
                 Unit: seconds
                "
            REFERENCE    "ITU-T G.997.1, paragraph 7.2.1"
            ::= { hwOntXdslPMLineCurrEntry 6 }
        hwOntXdslPMLCurr15MSes  OBJECT-TYPE
            SYNTAX      Counter32
            UNITS       "seconds"
            MAX-ACCESS  read-only
            STATUS      current
            DESCRIPTION
                "Count of seconds during this interval that there was:
                 xTU-C:  If G.998.4 is supported and retransmission is enabled
                         in the near-end received direction, a SES is declared
                         if during a 1-second interval, there is one or more
                         severe loss of error-free throughput (seftr) defect
                         in the near-end received direction.
                         Or else, an SES is declared if, during a 1 second interval,
                         there are 18 or more CRC 8 anomalies in one or more of the
                         received bearer channels, or one or more LOS defects, or
                         one or more SEF defects, or one or more LPR defects.
                 xTU-R: If G.998.4 is supported and retransmission is enabled in the
                        far-end received direction, a SES-LFE is declared if during
                        a 1-second interval, there is one or more severe loss of
                        error-free throughput (seftr) defect in the far-end received
                        direction.
                        Or else, an SES is declared if, during a 1 second interval,
                        there are 18 or more FEBE anomalies in one or more of the
                        transmitted bearer channels, or one or more far end LOS
                        defects, or one or more RDI defects, or one or more LPR FE
                        defects.
                 This parameter is inhibited during UAS.
                 Unit: seconds
                "
            REFERENCE    "ITU-T G.997.1, paragraph 7.2.1"
            ::= { hwOntXdslPMLineCurrEntry 7 }
        hwOntXdslPMLCurr15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwOntXdslPMLineCurrEntry 8 }
        hwOntXdslPMLCurr15MUas  OBJECT-TYPE
            SYNTAX      Counter32
            UNITS       "seconds"
            MAX-ACCESS  read-only
            STATUS      current
            DESCRIPTION
                "Count of seconds in Unavailability State during this
                 interval.  Unavailability begins at the onset of 10
                 contiguous severely-errored seconds, and ends at the
                 onset of 10 contiguous seconds with no severely-errored
                 seconds.
                 Unit: seconds
                "
            REFERENCE    "ITU-T G.997.1, paragraph 7.2.1"
            ::= { hwOntXdslPMLineCurrEntry 9 }
        hwOntXdslPMLCurr1DayValidIntervals  OBJECT-TYPE
            SYNTAX      Unsigned32
            MAX-ACCESS  read-only
            STATUS      current
            DESCRIPTION
                "Valid intervals."
            ::= { hwOntXdslPMLineCurrEntry 10 }
        hwOntXdslPMLCurr1DayInvalidIntervals  OBJECT-TYPE
            SYNTAX      Unsigned32
            MAX-ACCESS  read-only
            STATUS      current
            DESCRIPTION
                "Invalid intervals."
            ::= { hwOntXdslPMLineCurrEntry 11 }
        hwOntXdslPMLCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { hwOntXdslPMLineCurrEntry 12 }
        hwOntXdslPMLCurr1DayFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwOntXdslPMLineCurrEntry 13 }
        hwOntXdslPMLCurr1DayEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwOntXdslPMLineCurrEntry 14 }
        hwOntXdslPMLCurr1DaySes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Unit: seconds
                "
            REFERENCE    "ITU-T G.997.1, paragraph 7.2.1"
            ::= { hwOntXdslPMLineCurrEntry 15 }
        hwOntXdslPMLCurr1DayLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwOntXdslPMLineCurrEntry 16 }
        hwOntXdslPMLCurr1DayUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwOntXdslPMLineCurrEntry 17 }
        hwOntXdslPMLEverBeforeFecs  OBJECT-TYPE
            SYNTAX      Counter32
            UNITS       "seconds"
            MAX-ACCESS  read-only
            STATUS      current
            DESCRIPTION
                "Count of seconds since agent reset that there was at least
                 one FEC correction event for one or more bearer channels in
                 this line. This parameter is inhibited during UAS or SES.
                 Huawei defined.
                 Unit: seconds
                "
            ::= { hwOntXdslPMLineCurrEntry 18 }
        hwOntXdslPMLEverBeforeEs  OBJECT-TYPE
            SYNTAX      Counter32
            UNITS       "seconds"
            MAX-ACCESS  read-only
            STATUS      current
            DESCRIPTION
                "Count of seconds since agent reset that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Huawei defined.
                 Unit: seconds
                "
            ::= { hwOntXdslPMLineCurrEntry 19 }
        hwOntXdslPMLEverBeforeSes  OBJECT-TYPE
            SYNTAX      Counter32
            UNITS       "seconds"
            MAX-ACCESS  read-only
            STATUS      current
            DESCRIPTION
                "Count of seconds since agent reset that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1
                 This parameter is inhibited during UAS.
                 Huawei defined.
                 Unit: seconds
                "
            ::= { hwOntXdslPMLineCurrEntry 20 }
        hwOntXdslPMLEverBeforeLoss  OBJECT-TYPE
            SYNTAX      Counter32
            UNITS       "seconds"
            MAX-ACCESS  read-only
            STATUS      current
            DESCRIPTION
                "Count of seconds since agent reset that there was LOS (or
                 LOS-FE for xTU-R).
                 Huawei defined.
                 Unit: seconds
                "
            ::= { hwOntXdslPMLineCurrEntry 21 }

        hwOntXdslPMLEverBeforeUas  OBJECT-TYPE
            SYNTAX      Counter32
            UNITS       "seconds"
            MAX-ACCESS  read-only
            STATUS      current
            DESCRIPTION
                "Count of seconds in Unavailability State since agent reset.
                 Unavailability begins at the onset of 10 contiguous severely
                 -errored seconds, and ends at the onset of 10 contiguous
                 seconds with no severely-errored seconds.
                 Huawei defined.
                 Unit: seconds
                "
            ::= { hwOntXdslPMLineCurrEntry 22 }

        hwOntXdslPMLCurr15MLofs  OBJECT-TYPE
            SYNTAX      Counter32
            UNITS       "seconds"
            MAX-ACCESS  read-only
            STATUS      current
            DESCRIPTION
                "Count of seconds in the current 15 minute interval when there was Loss of Framing.
                 Unit: seconds
                "
            ::= { hwOntXdslPMLineCurrEntry 23 }

        hwOntXdslPMLCurr15MLols  OBJECT-TYPE
            SYNTAX      Counter32
            UNITS       "seconds"
            MAX-ACCESS  read-only
            STATUS      current
            DESCRIPTION
                "Count of seconds in the current 15 minute interval when there was Loss of Link.
                 Unit: seconds
                "
            ::= { hwOntXdslPMLineCurrEntry 24 }

        hwOntXdslPMLCurr15MLops  OBJECT-TYPE
            SYNTAX      Counter32
            UNITS       "seconds"
            MAX-ACCESS  read-only
            STATUS      current
            DESCRIPTION
                "Count of seconds in the current 15 minute interval when there was Loss of Power.
                 Unit: seconds
                "
            ::= { hwOntXdslPMLineCurrEntry 25 }

        hwOntXdslPMLCurr1DayLofs  OBJECT-TYPE
            SYNTAX      Counter32
            UNITS       "seconds"
            MAX-ACCESS  read-only
            STATUS      current
            DESCRIPTION
                "Count of the number of seconds when there was Loss of Framing during the current day.
                 Unit: seconds
                "
            ::= { hwOntXdslPMLineCurrEntry 26 }

        hwOntXdslPMLCurr1DayLols  OBJECT-TYPE
            SYNTAX      Counter32
            UNITS       "seconds"
            MAX-ACCESS  read-only
            STATUS      current
            DESCRIPTION
                "Count of the number of seconds when there was Loss of Link during the current day.
                 Unit: seconds
                "
            ::= { hwOntXdslPMLineCurrEntry 27 }

        hwOntXdslPMLCurr1DayLops  OBJECT-TYPE
            SYNTAX      Counter32
            UNITS       "seconds"
            MAX-ACCESS  read-only
            STATUS      current
            DESCRIPTION
                "Count of the number of seconds when there was Loss of Power during the current day.
                 Unit: seconds
                "
            ::= { hwOntXdslPMLineCurrEntry 28 }

        hwOntXdslPMLEverBeforeLofs  OBJECT-TYPE
            SYNTAX      Counter32
            UNITS       "seconds"
            MAX-ACCESS  read-only
            STATUS      current
            DESCRIPTION
                "Count of the number of seconds when there was Loss of Framing since agent reset.
                 Unit: seconds
                "
            ::= { hwOntXdslPMLineCurrEntry 29 }

        hwOntXdslPMLEverBeforeLols  OBJECT-TYPE
            SYNTAX      Counter32
            UNITS       "seconds"
            MAX-ACCESS  read-only
            STATUS      current
            DESCRIPTION
                "Count of the number of seconds when there was Loss of Link since agent reset.
                 Unit: seconds
                "
            ::= { hwOntXdslPMLineCurrEntry 30 }

        hwOntXdslPMLEverBeforeLops  OBJECT-TYPE
            SYNTAX      Counter32
            UNITS       "seconds"
            MAX-ACCESS  read-only
            STATUS      current
            DESCRIPTION
                "Count of the number of seconds when there was Loss of Power since agent reset.
                 Unit: seconds
                "
            ::= { hwOntXdslPMLineCurrEntry 31 }

        hwOntXdslPMLCurr15MSosSuccess  OBJECT-TYPE
            SYNTAX      Counter32
            UNITS       "times"
            MAX-ACCESS  read-only
            STATUS      current
            DESCRIPTION
                "Count of the total number of successful SOS procedures initiated in the current 15 minute.
                 Unit: times
                "
            REFERENCE    "ITU-T G.997.1, paragraph 7.2.1"
            ::= { hwOntXdslPMLineCurrEntry 32 }

        hwOntXdslPMLCurr1DaySosSuccess  OBJECT-TYPE
            SYNTAX      Counter32
            UNITS       "times"
            MAX-ACCESS  read-only
            STATUS      current
            DESCRIPTION
                "Count of the total number of successful SOS procedures initiated during the current day.
                 Unit: times
                "
            REFERENCE    "ITU-T G.997.1, paragraph 7.2.1"
            ::= { hwOntXdslPMLineCurrEntry 33 }

        hwOntXdslPMLEverBeforeSosSuccess  OBJECT-TYPE
            SYNTAX      Counter32
            UNITS       "times"
            MAX-ACCESS  read-only
            STATUS      current
            DESCRIPTION
                "Count of the total number of successful SOS procedures initiated since agent reset.
                 Unit: times
                "
            REFERENCE    "ITU-T G.997.1, paragraph 7.2.1"
            ::= { hwOntXdslPMLineCurrEntry 34 }

        hwOntXdslPMLCurr15MInmainpeq  OBJECT-TYPE
            SYNTAX      OCTET STRING  (SIZE(0..68))
            MAX-ACCESS  read-only
            STATUS      current
            DESCRIPTION
                "This parameter is a count of the INMAINPEQi anomalies
                 occurring on the line during current 15 minutes.
                "
            REFERENCE    "ITU-T G.997.1, paragraph 7.2.1"
            ::= { hwOntXdslPMLineCurrEntry 35 }

        hwOntXdslPMLCurr15MInmame  OBJECT-TYPE
            SYNTAX      Counter32
            MAX-ACCESS  read-only
            STATUS      current
            DESCRIPTION
                "This parameter is a count of the INMAME anomalies
                 occurring on the line during current 15 minutes.
                "
            REFERENCE    "ITU-T G.997.1, paragraph 7.2.1"
            ::= { hwOntXdslPMLineCurrEntry 36 }

        hwOntXdslPMLCurr15MInmaiat  OBJECT-TYPE
            SYNTAX      OCTET STRING  (SIZE(0..32))
            MAX-ACCESS  read-only
            STATUS      current
            DESCRIPTION
                "This parameter is a count of the INMAIATi anomalies
                 occurring on the line during current 15 minutes.
                "
            REFERENCE    "ITU-T G.997.1, paragraph 7.2.1"
            ::= { hwOntXdslPMLineCurrEntry 37 }

        hwOntXdslPMLCurr1DayInmainpeq  OBJECT-TYPE
            SYNTAX      OCTET STRING  (SIZE(0..68))
            MAX-ACCESS  read-only
            STATUS      current
            DESCRIPTION
                "This parameter is a count of the INMAINPEQi anomalies
                 occurring on the line during current 1 day.
                "
            REFERENCE    "ITU-T G.997.1, paragraph 7.2.1"
            ::= { hwOntXdslPMLineCurrEntry 38 }

        hwOntXdslPMLCurr1DayInmame  OBJECT-TYPE
            SYNTAX      Counter32
            MAX-ACCESS  read-only
            STATUS      current
            DESCRIPTION
                "This parameter is a count of the INMAME anomalies
                 occurring on the line during current 1 day.
                "
            REFERENCE    "ITU-T G.997.1, paragraph 7.2.1"
            ::= { hwOntXdslPMLineCurrEntry 39 }

        hwOntXdslPMLCurr1DayInmaiat  OBJECT-TYPE
            SYNTAX      OCTET STRING  (SIZE(0..32))
            MAX-ACCESS  read-only
            STATUS      current
            DESCRIPTION
                "This parameter is a count of the INMAIATi anomalies
                 occurring on the line during current 1 day.
                "
            REFERENCE    "ITU-T G.997.1, paragraph 7.2.1"
            ::= { hwOntXdslPMLineCurrEntry 40 }

        hwOntXdslPMLEverBeforeInmainpeq  OBJECT-TYPE
            SYNTAX      OCTET STRING  (SIZE(0..68))
            MAX-ACCESS  read-only
            STATUS      current
            DESCRIPTION
                "This parameter is a count of the INMAINPEQi anomalies
                 occurring on the line ever before.
                "
            REFERENCE    "ITU-T G.997.1, paragraph 7.2.1"
            ::= { hwOntXdslPMLineCurrEntry 41 }

        hwOntXdslPMLEverBeforeInmame  OBJECT-TYPE
            SYNTAX      Counter32
            MAX-ACCESS  read-only
            STATUS      current
            DESCRIPTION
                "This parameter is a count of the INMAME anomalies
                 occurring on the line ever before.
                "
            REFERENCE    "ITU-T G.997.1, paragraph 7.2.1"
            ::= { hwOntXdslPMLineCurrEntry 42 }

        hwOntXdslPMLEverBeforeInmaiat  OBJECT-TYPE
            SYNTAX      OCTET STRING  (SIZE(0..32))
            MAX-ACCESS  read-only
            STATUS      current
            DESCRIPTION
                "This parameter is a count of the INMAIATi anomalies
                 occurring on the line ever before.
                "
            REFERENCE    "ITU-T G.997.1, paragraph 7.2.1"
            ::= { hwOntXdslPMLineCurrEntry 43 }

        hwOntXdslPMLineCurr15MStartTime  OBJECT-TYPE
            SYNTAX      DateAndTime
            MAX-ACCESS  read-only
            STATUS      current
            DESCRIPTION
                "Start time of the current 15-minute performance statistics."
            ::= { hwOntXdslPMLineCurrEntry 44 }

        hwOntXdslPMLineCurr1DayStartTime  OBJECT-TYPE
            SYNTAX      DateAndTime
            MAX-ACCESS  read-only
            STATUS      current
            DESCRIPTION
                "Start time of the current 1-day performance statistics."
            ::= { hwOntXdslPMLineCurrEntry 45 }

        hwOntXdslPMLCurr15MLeftrs     OBJECT-TYPE
            SYNTAX      Counter32
            MAX-ACCESS  read-only
            STATUS      current
            DESCRIPTION
                "If retransmission is used in a given transmit direction, this parameter
                 is a count of the seconds with a near-end leftr defect present observed
                 over the 15 minutes accumulation period.
                 Currently, this leaf is reserved, and it is not supported.
                "
            REFERENCE    "ITU-T G.997.1, paragraph 7.2.1.1.6 7.2.1.2.6"
            ::= { hwOntXdslPMLineCurrEntry 46 }

        hwOntXdslPMLCurr15MEfb        OBJECT-TYPE
            SYNTAX      Counter32
            MAX-ACCESS  read-only
            STATUS      current
            DESCRIPTION
                "If retransmission is used in a given transmit direction, this parameter
                 is a count of the number of error-free bits observed over the 15 minutes
                 accumulation period.
                 Currently, this leaf is reserved, and it is not supported.
                "
            REFERENCE    "ITU-T G.997.1, paragraph 7.2.1.1.7 7.2.1.2.7"
            ::= { hwOntXdslPMLineCurrEntry 47 }

        hwOntXdslPMLCurr15MMinEftr    OBJECT-TYPE
            SYNTAX      Counter32
            MAX-ACCESS  read-only
            STATUS      current
            DESCRIPTION
                "If retransmission is used in a given transmit direction, this parameter
                 reports the minimum of the EFTR(Error-free throughput rate) observed
                 over the 15 minutes accumulation period.
                 Currently, this leaf is reserved, and it is not supported.
                "
            REFERENCE    "ITU-T G.997.1, paragraph 7.2.1.1.8 7.2.1.2.8"
            ::= { hwOntXdslPMLineCurrEntry 48 }
        hwOntXdslPMLCurr1DayLeftrs    OBJECT-TYPE
            SYNTAX      Counter32
            MAX-ACCESS  read-only
            STATUS      current
            DESCRIPTION
                "If retransmission is used in a given transmit direction, this parameter
                 is a count of the seconds with a near-end leftr defect present observed
                 over the 24 hours accumulation period.
                 Currently, this leaf is reserved, and it is not supported.
                "
            REFERENCE    "ITU-T G.997.1, paragraph 7.2.1.1.6 7.2.1.2.6"
            ::= { hwOntXdslPMLineCurrEntry 49 }

        hwOntXdslPMLCurr1DayEfb       OBJECT-TYPE
            SYNTAX      Counter32
            MAX-ACCESS  read-only
            STATUS      current
            DESCRIPTION
                "If retransmission is used in a given transmit direction, this parameter
                 is a count of the number of error-free bits observed over the 24 hours
                 accumulation period.
                 Currently, this leaf is reserved, and it is not supported.
                "
            REFERENCE    "ITU-T G.997.1, paragraph 7.2.1.1.7 7.2.1.2.7"
            ::= { hwOntXdslPMLineCurrEntry 50 }

        hwOntXdslPMLCurr1DayMinEftr   OBJECT-TYPE
            SYNTAX      Counter32
            MAX-ACCESS  read-only
            STATUS      current
            DESCRIPTION
                "If retransmission is used in a given transmit direction, this parameter
                 reports the minimum of the EFTR(Error-free throughput rate) observed
                 over the 24 hours accumulation period.
                 Currently, this leaf is reserved, and it is not supported.
               "
            REFERENCE    "ITU-T G.997.1, paragraph 7.2.1.1.8 7.2.1.2.8"
            ::= { hwOntXdslPMLineCurrEntry 51}

        hwOntXdslPMLEverBeforeLeftrs  OBJECT-TYPE
            SYNTAX      Counter32
            MAX-ACCESS  read-only
            STATUS      current
            DESCRIPTION
                "If retransmission is used in a given transmit direction, this parameter
                 is a count of the seconds with a near-end leftr defect present observed
                 ever before.
                 Currently, this leaf is reserved, and it is not supported.
               "
            REFERENCE    "ITU-T G.997.1, paragraph 7.2.1.1.6 7.2.1.2.6"
            ::= { hwOntXdslPMLineCurrEntry 52 }

        hwOntXdslPMLEverBeforeEfb     OBJECT-TYPE
            SYNTAX      Counter32
            MAX-ACCESS  read-only
            STATUS      current
            DESCRIPTION
                "If retransmission is used in a given transmit direction, this parameter
                 is a count of the number of error-free bits observed ever before.
                 Currently, this leaf is reserved, and it is not supported.
                "
            REFERENCE    "ITU-T G.997.1, paragraph 7.2.1.1.7 7.2.1.2.7"
            ::= { hwOntXdslPMLineCurrEntry 53 }

        hwOntXdslPMLEverBeforeMinEftr OBJECT-TYPE
            SYNTAX      Counter32
            MAX-ACCESS  read-only
            STATUS      current
            DESCRIPTION
                "If retransmission is used in a given transmit direction, this parameter
                 reports the minimum of the EFTR(Error-free throughput rate) observed
                 ever before.
                 Currently, this leaf is reserved, and it is not supported.
                "
            REFERENCE    "ITU-T G.997.1, paragraph 7.2.1.1.8 7.2.1.2.8"
            ::= { hwOntXdslPMLineCurrEntry 54 }

          --          PM ont xdsl port line init current counters

        hwOntXdslPMLineCurrInitTable   OBJECT-TYPE
            SYNTAX      SEQUENCE  OF  HwOntXdslPMLineCurrInitEntry
            MAX-ACCESS  not-accessible
            STATUS      current
            DESCRIPTION
                "The table hwOntXdslPMLineCurrInitTable contains current
                 initialization counters of the ONT XDSL port line.
                 The indexes of this table are ifIndex, hwOntObjectIndex,
                 hwOntUniPhyType and hwOntXdslPortid.
                "
            ::= { hwXdslPMLine 8 }

        hwOntXdslPMLineCurrInitEntry  OBJECT-TYPE
            SYNTAX      HwOntXdslPMLineCurrInitEntry
            MAX-ACCESS  not-accessible
            STATUS      current
            DESCRIPTION
                "The table hwOntXdslPMLineCurrInitTable contains current
                 initialization counters of the ONT XDSL port line.
                 The indexes of this entry are ifIndex, hwOntObjectIndex,
                 hwOntUniPhyType and hwOntXdslPortid.
                "
            INDEX  { ifIndex,
                     hwOntObjectIndex,
                     hwOntUniPhyType,
                     hwOntXdslPortid }
            ::= { hwOntXdslPMLineCurrInitTable 1 }

        HwOntXdslPMLineCurrInitEntry  ::=
            SEQUENCE {
              hwOntXdslPMLCurrInit15MTimeElapsed          Unsigned32,
              hwOntXdslPMLCurrInit15MFullInits            Unsigned32,
              hwOntXdslPMLCurrInit15MFailedFullInits      Unsigned32,
              hwOntXdslPMLCurrInit15MShortInits           Unsigned32,
              hwOntXdslPMLCurrInit15MFailedShortInits     Unsigned32,
              hwOntXdslPMLCurrInit1DayTimeElapsed         Unsigned32,
              hwOntXdslPMLCurrInit1DayFullInits           Unsigned32,
              hwOntXdslPMLCurrInit1DayFailedFullInits     Unsigned32,
              hwOntXdslPMLCurrInit1DayShortInits          Unsigned32,
              hwOntXdslPMLCurrInit1DayFailedShortInits    Unsigned32,
              hwOntXdslPMLInitEverBeforeFullInits         Unsigned32,
              hwOntXdslPMLInitEverBeforeFailedFullInits   Unsigned32,
              hwOntXdslPMLInitEverBeforeShortInits        Unsigned32,
              hwOntXdslPMLInitEverBeforeFailedShortInits  Unsigned32,
              hwOntXdslPMLineCurrInit15MStartTime         DateAndTime,
              hwOntXdslPMLineCurrInit1DayStartTime        DateAndTime
            }

        hwOntXdslPMLCurrInit15MTimeElapsed  OBJECT-TYPE
            SYNTAX      Unsigned32
            UNITS       "seconds"
            MAX-ACCESS  read-only
            STATUS      current
            DESCRIPTION
                "Total elapsed seconds in this interval.
                 Unit: seconds
                "
            ::= { hwOntXdslPMLineCurrInitEntry 1 }

        hwOntXdslPMLCurrInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwOntXdslPMLineCurrInitEntry 2 }

        hwOntXdslPMLCurrInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwOntXdslPMLineCurrInitEntry 3 }

        hwOntXdslPMLCurrInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwOntXdslPMLineCurrInitEntry 4 }

        hwOntXdslPMLCurrInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwOntXdslPMLineCurrInitEntry 5 }

        hwOntXdslPMLCurrInit1DayTimeElapsed  OBJECT-TYPE
            SYNTAX      Unsigned32
            UNITS       "seconds"
            MAX-ACCESS  read-only
            STATUS      current
            DESCRIPTION
                "Total elapsed seconds in this interval.
                 Unit: seconds
                "
            ::= { hwOntXdslPMLineCurrInitEntry 6 }

        hwOntXdslPMLCurrInit1DayFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwOntXdslPMLineCurrInitEntry 7 }

        hwOntXdslPMLCurrInit1DayFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwOntXdslPMLineCurrInitEntry 8 }

        hwOntXdslPMLCurrInit1DayShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwOntXdslPMLineCurrInitEntry 9 }

        hwOntXdslPMLCurrInit1DayFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwOntXdslPMLineCurrInitEntry 10 }

        hwOntXdslPMLInitEverBeforeFullInits  OBJECT-TYPE
            SYNTAX      Unsigned32
            MAX-ACCESS  read-only
            STATUS      current
            DESCRIPTION
                "Count of full initializations attempted on the line
                 (successful and failed) since agent reset.
                 Huawei defined.
                "
            ::= { hwOntXdslPMLineCurrInitEntry 11 }

        hwOntXdslPMLInitEverBeforeFailedFullInits  OBJECT-TYPE
            SYNTAX      Unsigned32
            MAX-ACCESS  read-only
            STATUS      current
            DESCRIPTION
                "Count of failed full initializations on the line since agent
                 reset.
                 Huawei defined.
                "
            ::= { hwOntXdslPMLineCurrInitEntry 12 }

        hwOntXdslPMLInitEverBeforeShortInits  OBJECT-TYPE
            SYNTAX      Unsigned32
            MAX-ACCESS  read-only
            STATUS      current
            DESCRIPTION
                "Count of short initializations attempted on the line
                 (successful and failed) since agent reset.
                 Huawei defined.
                "
            ::= { hwOntXdslPMLineCurrInitEntry 13 }

        hwOntXdslPMLInitEverBeforeFailedShortInits  OBJECT-TYPE
            SYNTAX      Unsigned32
            MAX-ACCESS  read-only
            STATUS      current
            DESCRIPTION
                "Count of failed short initializations on the line since agent
                 reset.
                 Huawei defined.
                "
            ::= { hwOntXdslPMLineCurrInitEntry 14 }

        hwOntXdslPMLineCurrInit15MStartTime  OBJECT-TYPE
            SYNTAX      DateAndTime
            MAX-ACCESS  read-only
            STATUS      current
            DESCRIPTION
                "Start time of the current initializations 15-minute performance statistics."
            ::= { hwOntXdslPMLineCurrInitEntry 15 }

        hwOntXdslPMLineCurrInit1DayStartTime  OBJECT-TYPE
            SYNTAX      DateAndTime
            MAX-ACCESS  read-only
            STATUS      current
            DESCRIPTION
                "Start time of the current initializations 1-day performance statistics."
            ::= { hwOntXdslPMLineCurrInitEntry 16 }

          --       PM ont port xdsl line history 15 Minutes
        hwOntXdslPMLineHist15MinTable    OBJECT-TYPE
            SYNTAX      SEQUENCE  OF  HwOntXdslPMLineHist15MinEntry
            MAX-ACCESS  not-accessible
            STATUS      current
            DESCRIPTION
                "The table hwOntXdslPMLineHist15MinTable contains PM line history
                 for 15min intervals of the ONT port XDSL line.
                 The indexes of this table are ifIndex, hwOntObjectIndex, hwOntUniPhyType,
                 hwOntXdslPortid, the termination unit and an interval number.
                "
            ::= { hwXdslPMLine 9 }

        hwOntXdslPMLineHist15MinEntry  OBJECT-TYPE
            SYNTAX      HwOntXdslPMLineHist15MinEntry
            MAX-ACCESS  not-accessible
            STATUS      current
            DESCRIPTION
                "The table hwOntXdslPMLineHist15MinTable contains PM line history
                 for 15min intervals of the ONT port XDSL line.
                 The indexes of this entry are ifIndex, hwOntObjectIndex, hwOntUniPhyType,
                 hwOntXdslPortid, the termination unit and an interval number.
                "
            INDEX  { ifIndex,
                     hwOntObjectIndex,
                     hwOntUniPhyType,
                     hwOntXdslPortid,
                     hwOntXdslPMLHist15MUnit,
                     hwOntXdslPMLHist15MInterval }
            ::= { hwOntXdslPMLineHist15MinTable 1 }

        HwOntXdslPMLineHist15MinEntry  ::=
            SEQUENCE {
              hwOntXdslPMLHist15MUnit                 HwXdslUnit,
              hwOntXdslPMLHist15MInterval             Unsigned32,
              hwOntXdslPMLHist15MMonitoredTime        Unsigned32,
              hwOntXdslPMLHist15MFecs                 Counter32,
              hwOntXdslPMLHist15MEs                   Counter32,
              hwOntXdslPMLHist15MSes                  Counter32,
              hwOntXdslPMLHist15MLoss                 Counter32,
              hwOntXdslPMLHist15MUas                  Counter32,
              hwOntXdslPMLHist15MValidInterval        TruthValue,
              hwOntXdslPMLHist15MLofs                 Counter32,
              hwOntXdslPMLHist15MLols                 Counter32,
              hwOntXdslPMLHist15MLops                 Counter32,
              hwOntXdslPMLHist15MSosSuccess           Counter32,
              hwOntXdslPMLHist15MInmainpeq            OCTET STRING,
              hwOntXdslPMLHist15MInmame               Counter32,
              hwOntXdslPMLHist15MInmaiat              OCTET STRING,
              hwOntXdslPMLHist15MStartTime            DateAndTime,
              hwOntXdslPMLHist15MLeftrs               Counter32,
              hwOntXdslPMLHist15MEfb                  Counter32,
              hwOntXdslPMLHist15MMinEftr              Counter32
            }

        hwOntXdslPMLHist15MUnit  OBJECT-TYPE
            SYNTAX      HwXdslUnit
            MAX-ACCESS  not-accessible
            STATUS      current
            DESCRIPTION
                "The termination unit XTUC{1} or XTUR{2}."
            ::= { hwOntXdslPMLineHist15MinEntry 1 }

        hwOntXdslPMLHist15MInterval  OBJECT-TYPE
            SYNTAX      Unsigned32
            MAX-ACCESS  not-accessible
            STATUS      current
            DESCRIPTION
                "The interval number."
            ::= { hwOntXdslPMLineHist15MinEntry 2 }

        hwOntXdslPMLHist15MMonitoredTime  OBJECT-TYPE
            SYNTAX      Unsigned32
            UNITS       "seconds"
            MAX-ACCESS  read-only
            STATUS      current
            DESCRIPTION
                "Total seconds monitored in this interval.
                 Unit: seconds
                "
            ::= { hwOntXdslPMLineHist15MinEntry 3 }

        hwOntXdslPMLHist15MFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwOntXdslPMLineHist15MinEntry 4 }

        hwOntXdslPMLHist15MEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwOntXdslPMLineHist15MinEntry 5 }

        hwOntXdslPMLHist15MSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;= 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { hwOntXdslPMLineHist15MinEntry 6 }

        hwOntXdslPMLHist15MLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwOntXdslPMLineHist15MinEntry 7 }

        hwOntXdslPMLHist15MUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwOntXdslPMLineHist15MinEntry 8 }

        hwOntXdslPMLHist15MValidInterval  OBJECT-TYPE
            SYNTAX      TruthValue
            MAX-ACCESS  read-only
            STATUS      current
            DESCRIPTION
                "This variable indicates if the data for this interval is
                 valid.
                "
            ::= { hwOntXdslPMLineHist15MinEntry 9 }

        hwOntXdslPMLHist15MLofs  OBJECT-TYPE
            SYNTAX      Counter32
            UNITS       "seconds"
            MAX-ACCESS  read-only
            STATUS      current
            DESCRIPTION
                "Count of seconds in the interval when there was Loss of Framing.
                 Unit: seconds
                "
            ::= { hwOntXdslPMLineHist15MinEntry 10 }

        hwOntXdslPMLHist15MLols  OBJECT-TYPE
            SYNTAX      Counter32
            UNITS       "seconds"
            MAX-ACCESS  read-only
            STATUS      current
            DESCRIPTION
                "Count of seconds in the interval when there was Loss of Link.
                 Unit: seconds
                "
            ::= { hwOntXdslPMLineHist15MinEntry 11 }

        hwOntXdslPMLHist15MLops  OBJECT-TYPE
            SYNTAX      Counter32
            UNITS       "seconds"
            MAX-ACCESS  read-only
            STATUS      current
            DESCRIPTION
                "Count of seconds in the interval when there was Loss of Power.
                 Unit: seconds
                "
            ::= { hwOntXdslPMLineHist15MinEntry 12 }

        hwOntXdslPMLHist15MSosSuccess  OBJECT-TYPE
            SYNTAX      Counter32
            UNITS       "times"
            MAX-ACCESS  read-only
            STATUS      current
            DESCRIPTION
                "Count of the total number of successful SOS procedures initiated in the interval.
                 Unit: times
                "
            REFERENCE    "ITU-T G.997.1, paragraph 7.2.1"
            ::= { hwOntXdslPMLineHist15MinEntry 13 }

        hwOntXdslPMLHist15MInmainpeq  OBJECT-TYPE
            SYNTAX      OCTET STRING  (SIZE(0..68))
            MAX-ACCESS  read-only
            STATUS      current
            DESCRIPTION
                "This parameter is a count of the INMAINPEQi anomalies
                 occurring on the line over the 15 minutes accumulation period.
                "
            REFERENCE    "ITU-T G.997.1, paragraph 7.2.1"
            ::= { hwOntXdslPMLineHist15MinEntry 14 }

        hwOntXdslPMLHist15MInmame  OBJECT-TYPE
            SYNTAX      Counter32
            MAX-ACCESS  read-only
            STATUS      current
            DESCRIPTION
                "This parameter is a count of the INMAME anomalies
                 occurring on the line over the 15 minutes accumulation period.
                "
            REFERENCE    "ITU-T G.997.1, paragraph 7.2.1"
            ::= { hwOntXdslPMLineHist15MinEntry 15}

        hwOntXdslPMLHist15MInmaiat  OBJECT-TYPE
            SYNTAX      OCTET STRING  (SIZE(0..32))
            MAX-ACCESS  read-only
            STATUS      current
            DESCRIPTION
                "This parameter is a count of the INMAIATi anomalies
                 occurring on the line over the 15 minutes accumulation period.
                "
            REFERENCE    "ITU-T G.997.1, paragraph 7.2.1"
            ::= { hwOntXdslPMLineHist15MinEntry 16}

        hwOntXdslPMLHist15MStartTime  OBJECT-TYPE
            SYNTAX      DateAndTime
            MAX-ACCESS  read-only
            STATUS      current
            DESCRIPTION
                "Start time of the historical 15-minute performance statistics."
            ::= { hwOntXdslPMLineHist15MinEntry 17 }

        hwOntXdslPMLHist15MLeftrs     OBJECT-TYPE
            SYNTAX      Counter32
            MAX-ACCESS  read-only
            STATUS      current
            DESCRIPTION
                "If retransmission is used in a given transmit direction, this parameter
                 is a count of the seconds with a near-end leftr defect present observed
                 over the 15 minutes accumulation period.
                 Currently, this leaf is reserved, and it is not supported.
                "
            REFERENCE    "ITU-T G.997.1, paragraph 7.2.1.1.6 7.2.1.2.6"
            ::= { hwOntXdslPMLineHist15MinEntry 18 }

        hwOntXdslPMLHist15MEfb        OBJECT-TYPE
            SYNTAX      Counter32
            MAX-ACCESS  read-only
            STATUS      current
            DESCRIPTION
                "If retransmission is used in a given transmit direction, this parameter
                 is a count of the number of error-free bits observed over the 15 minutes
                 accumulation period.
                 Currently, this leaf is reserved, and it is not supported.
                "
            REFERENCE    "ITU-T G.997.1, paragraph 7.2.1.1.7 7.2.1.2.7"
            ::= { hwOntXdslPMLineHist15MinEntry 19 }

        hwOntXdslPMLHist15MMinEftr    OBJECT-TYPE
            SYNTAX      Counter32
            MAX-ACCESS  read-only
            STATUS      current
            DESCRIPTION
                "If retransmission is used in a given transmit direction, this parameter
                 reports the minimum of the EFTR(Error-free throughput rate) observed
                 over the 15 minutes accumulation period.
                 Currently, this leaf is reserved, and it is not supported.
               "
            REFERENCE    "ITU-T G.997.1, paragraph 7.2.1.1.8 7.2.1.2.8"
            ::= { hwOntXdslPMLineHist15MinEntry 20 }

          --       PM ont xdsl port line history 1 Day

        hwOntXdslPMLineHist1DayTable     OBJECT-TYPE
            SYNTAX      SEQUENCE  OF  HwOntXdslPMLineHist1DayEntry
            MAX-ACCESS  not-accessible
            STATUS      current
            DESCRIPTION
                "The table hwOntXdslPMLineHist1DayTable contains PM line history
                 for 24 hours intervals of the ONT XDSL port line.
                 The indexes of this table are ifIndex, hwOntObjectIndex, hwOntUniPhyType,
                 hwOntXdslPortid, the termination unit
                 and an interval number.
                "
            ::= { hwXdslPMLine 10 }

        hwOntXdslPMLineHist1DayEntry  OBJECT-TYPE
            SYNTAX      HwOntXdslPMLineHist1DayEntry
            MAX-ACCESS  not-accessible
            STATUS      current
            DESCRIPTION
                "The table hwOntXdslPMLineHist1DayTable contains PM line history
                 for 24 hours intervals of the ONT XDSL port line.
                 The indexes of this entry are ifIndex, hwOntObjectIndex, hwOntUniPhyType,
                 hwOntXdslPortid, the termination unit
                 and an interval number.
                "
            INDEX  { ifIndex,
                     hwOntObjectIndex,
                     hwOntUniPhyType,
                     hwOntXdslPortid,
                     hwOntXdslPMLHist1DUnit,
                     hwOntXdslPMLHist1DInterval }
            ::= { hwOntXdslPMLineHist1DayTable 1 }

        HwOntXdslPMLineHist1DayEntry  ::=
            SEQUENCE {
              hwOntXdslPMLHist1DUnit              HwXdslUnit,
              hwOntXdslPMLHist1DInterval          Unsigned32,
              hwOntXdslPMLHist1DMonitoredTime     Unsigned32,
              hwOntXdslPMLHist1DFecs              Counter32,
              hwOntXdslPMLHist1DEs                Counter32,
              hwOntXdslPMLHist1DSes               Counter32,
              hwOntXdslPMLHist1DLoss              Counter32,
              hwOntXdslPMLHist1DUas               Counter32,
              hwOntXdslPMLHist1DValidInterval     TruthValue,
              hwOntXdslPMLHist1DLofs              Counter32,
              hwOntXdslPMLHist1DLols              Counter32,
              hwOntXdslPMLHist1DLops              Counter32,
              hwOntXdslPMLHist1DSosSuccess        Counter32,
              hwOntXdslPMLHist1DInmainpeq         OCTET STRING,
              hwOntXdslPMLHist1DInmame            Counter32,
              hwOntXdslPMLHist1DInmaiat           OCTET STRING,
              hwOntXdslPMLHist1DStartTime         DateAndTime,
              hwOntXdslPMLHist1DLeftrs            Counter32,
              hwOntXdslPMLHist1DEfb               Counter32,
              hwOntXdslPMLHist1DMinEftr           Counter32
            }

        hwOntXdslPMLHist1DUnit  OBJECT-TYPE
            SYNTAX      HwXdslUnit
            MAX-ACCESS  not-accessible
            STATUS      current
            DESCRIPTION
                "The termination unit."
            ::= { hwOntXdslPMLineHist1DayEntry 1 }

        hwOntXdslPMLHist1DInterval  OBJECT-TYPE
            SYNTAX      Unsigned32
            MAX-ACCESS  not-accessible
            STATUS      current
            DESCRIPTION
                "The interval number."
            ::= { hwOntXdslPMLineHist1DayEntry 2 }

        hwOntXdslPMLHist1DMonitoredTime  OBJECT-TYPE
            SYNTAX      Unsigned32
            UNITS       "seconds"
            MAX-ACCESS  read-only
            STATUS      current
            DESCRIPTION
                "Total seconds monitored in this interval.
                 Unit: seconds
                "
            ::= { hwOntXdslPMLineHist1DayEntry 3 }

        hwOntXdslPMLHist1DFecs  OBJECT-TYPE
            SYNTAX      Counter32
            UNITS       "seconds"
            MAX-ACCESS  read-only
            STATUS      current
            DESCRIPTION
                "Count of seconds during this interval that there was at least
                 one FEC correction event for one or more bearer channels in
                 this line.  This parameter is inhibited during UAS or SES.
                 Unit: seconds
                "
            REFERENCE    "ITU-T G.997.1, paragraph 7.2.1"
            ::= { hwOntXdslPMLineHist1DayEntry 4 }

        hwOntXdslPMLHist1DEs  OBJECT-TYPE
            SYNTAX      Counter32
            UNITS       "seconds"
            MAX-ACCESS  read-only
            STATUS      current
            DESCRIPTION
                "Count of seconds during this interval that there was:
                 xTU-C: CRC-8 &gt;= 1 for one or more bearer channels OR
                        LOS &gt;= 1 OR SEF &gt;= 1 OR LPR &gt;= 1
                 xTU-R: FEBE &gt;= 1 for one or more bearer channels OR
                        LOS-FE &gt;= 1 OR RDI &gt;= 1 OR LPR-FE &gt;= 1.
                 This parameter is inhibited during UAS.
                 Unit: seconds
                "
            REFERENCE    "ITU-T G.997.1, paragraph 7.2.1"
            ::= { hwOntXdslPMLineHist1DayEntry 5 }

        hwOntXdslPMLHist1DSes  OBJECT-TYPE
            SYNTAX      Counter32
            UNITS       "seconds"
            MAX-ACCESS  read-only
            STATUS      current
            DESCRIPTION
                "Count of seconds during this interval that there was:
                 xTU-C: (CRC-8 summed over all bearer channels) &gt;= 18 OR
                        LOS &gt;= 1 OR SEF &gt;&gt; 1 OR LPR &gt;= 1
                 xTU-R: (FEBE summed over all bearer channels) &gt;= 18 OR
                        LOS-FE &gt;= 1 OR RDI &gt;= 1 OR LPR-FE &gt;= 1.
                 This parameter is inhibited during UAS.
                 Unit: seconds
                "
            REFERENCE    "ITU-T G.997.1, paragraph 7.2.1"
            ::= { hwOntXdslPMLineHist1DayEntry 6 }

        hwOntXdslPMLHist1DLoss  OBJECT-TYPE
            SYNTAX      Counter32
            UNITS       "seconds"
            MAX-ACCESS  read-only
            STATUS      current
            DESCRIPTION
                "Count of seconds during this interval that there was LOS (or
                 LOS-FE for xTU-R).
                 Unit: seconds
                "
            REFERENCE    "ITU-T G.997.1, paragraph 7.2.1"
            ::= { hwOntXdslPMLineHist1DayEntry 7 }

        hwOntXdslPMLHist1DUas  OBJECT-TYPE
            SYNTAX      Counter32
            UNITS       "seconds"
            MAX-ACCESS  read-only
            STATUS      current
            DESCRIPTION
                "Count of seconds in Unavailability State during this interval.
                 Unavailability begins at the onset of 10 contiguous severely
                 -errored seconds, and ends at the onset of 10 contiguous
                 seconds with no severely-errored seconds.
                 Unit: seconds
                "
            REFERENCE    "ITU-T G.997.1, paragraph 7.2.1"
            ::= { hwOntXdslPMLineHist1DayEntry 8 }

        hwOntXdslPMLHist1DValidInterval  OBJECT-TYPE
            SYNTAX      TruthValue
            MAX-ACCESS  read-only
            STATUS      current
            DESCRIPTION
                "This variable indicates if the data for this interval is
                 valid.
                "
            ::= { hwOntXdslPMLineHist1DayEntry 9 }

        hwOntXdslPMLHist1DLofs  OBJECT-TYPE
            SYNTAX      Counter32
            UNITS       "seconds"
            MAX-ACCESS  read-only
            STATUS      current
            DESCRIPTION
                "Count of seconds during this interval that there was Loss of Framing.
                 Unit: seconds
                "
            ::= { hwOntXdslPMLineHist1DayEntry 10 }

        hwOntXdslPMLHist1DLols  OBJECT-TYPE
            SYNTAX      Counter32
            UNITS       "seconds"
            MAX-ACCESS  read-only
            STATUS      current
            DESCRIPTION
                "Count of seconds during this interval that there was Loss of Link.
                 Unit: seconds
                "
            ::= { hwOntXdslPMLineHist1DayEntry 11 }

        hwOntXdslPMLHist1DLops  OBJECT-TYPE
            SYNTAX      Counter32
            UNITS       "seconds"
            MAX-ACCESS  read-only
            STATUS      current
            DESCRIPTION
                "Count of seconds during this interval that there was Loss of Power.
                 Unit: seconds
                "
            ::= { hwOntXdslPMLineHist1DayEntry 12 }

        hwOntXdslPMLHist1DSosSuccess  OBJECT-TYPE
            SYNTAX      Counter32
            UNITS       "times"
            MAX-ACCESS  read-only
            STATUS      current
            DESCRIPTION
                "Count of the total number of successful SOS procedures initiated during this interval.
                 Unit: times
                "
            REFERENCE    "ITU-T G.997.1, paragraph 7.2.1"
            ::= { hwOntXdslPMLineHist1DayEntry 13 }

        hwOntXdslPMLHist1DInmainpeq  OBJECT-TYPE
            SYNTAX      OCTET STRING  (SIZE(0..68))
            MAX-ACCESS  read-only
            STATUS      current
            DESCRIPTION
                "This parameter is a count of the INMAINPEQi anomalies
                 occurring on the line over the 24 hours accumulation period.
                "
            REFERENCE    "ITU-T G.997.1, paragraph 7.2.1"
            ::= { hwOntXdslPMLineHist1DayEntry 14 }

        hwOntXdslPMLHist1DInmame  OBJECT-TYPE
            SYNTAX      Counter32
            MAX-ACCESS  read-only
            STATUS      current
            DESCRIPTION
                "This parameter is a count of the INMAME anomalies
                 occurring on the line over the 24 hours accumulation period.
                "
            REFERENCE    "ITU-T G.997.1, paragraph 7.2.1"
            ::= { hwOntXdslPMLineHist1DayEntry 15 }

        hwOntXdslPMLHist1DInmaiat  OBJECT-TYPE
            SYNTAX      OCTET STRING  (SIZE(0..32))
            MAX-ACCESS  read-only
            STATUS      current
            DESCRIPTION
                "This parameter is a count of the INMAIATi anomalies
                 occurring on the line over the 24 hours accumulation period.
                "
            REFERENCE    "ITU-T G.997.1, paragraph 7.2.1"
            ::= { hwOntXdslPMLineHist1DayEntry 16 }

        hwOntXdslPMLHist1DStartTime  OBJECT-TYPE
            SYNTAX      DateAndTime
            MAX-ACCESS  read-only
            STATUS      current
            DESCRIPTION
                "Start time of the historical 1-day performance statistics."
            ::= { hwOntXdslPMLineHist1DayEntry 17 }

       hwOntXdslPMLHist1DLeftrs     OBJECT-TYPE
            SYNTAX      Counter32
            MAX-ACCESS  read-only
            STATUS      current
            DESCRIPTION
                "If retransmission is used in a given transmit direction, this parameter
                 is a count of the seconds with a near-end leftr defect present observed
                 over the 24 hours accumulation period.
                 Currently, this leaf is reserved, and it is not supported.
                "
            REFERENCE    "ITU-T G.997.1, paragraph 7.2.1.1.6 7.2.1.2.6"
            ::= { hwOntXdslPMLineHist1DayEntry 18 }

        hwOntXdslPMLHist1DEfb        OBJECT-TYPE
            SYNTAX      Counter32
            MAX-ACCESS  read-only
            STATUS      current
            DESCRIPTION
                "If retransmission is used in a given transmit direction, this parameter
                 is a count of the number of error-free bits observed over the 24 hours
                 accumulation period.
                 Currently, this leaf is reserved, and it is not supported.
                "
            REFERENCE    "ITU-T G.997.1, paragraph 7.2.1.1.7 7.2.1.2.7"
            ::= { hwOntXdslPMLineHist1DayEntry 19 }

        hwOntXdslPMLHist1DMinEftr    OBJECT-TYPE
            SYNTAX      Counter32
            MAX-ACCESS  read-only
            STATUS      current
            DESCRIPTION
                "If retransmission is used in a given transmit direction, this parameter
                 reports the minimum of the EFTR(Error-free throughput rate) observed
                 over the 24 hours accumulation period.
                 Currently, this leaf is reserved, and it is not supported.
                "
            REFERENCE    "ITU-T G.997.1, paragraph 7.2.1.1.8 7.2.1.2.8"
            ::= { hwOntXdslPMLineHist1DayEntry 20 }

           --     PM ont port xdsl line init history 15 Minutes

        hwOntXdslPMLineInitHist15MinTable      OBJECT-TYPE
            SYNTAX      SEQUENCE  OF  HwOntXdslPMLineInitHist15MinEntry
            MAX-ACCESS  not-accessible
            STATUS      current
            DESCRIPTION
                "The table hwOntXdslPMLineInitHist15MinTable contains PM line
                 initialization history for 15 minutes intervals of the
                 ONT XDSL port line.
                 The indexes of this table are ifIndex, hwOntObjectIndex, hwOntUniPhyType,
                 hwOntXdslPortid and an interval number.
                "
            ::= { hwXdslPMLine 11 }

        hwOntXdslPMLineInitHist15MinEntry  OBJECT-TYPE
            SYNTAX      HwOntXdslPMLineInitHist15MinEntry
            MAX-ACCESS  not-accessible
            STATUS      current
            DESCRIPTION
                "The table hwOntXdslPMLineInitHist15MinTable contains PM line
                 initialization history for 15 minutes intervals of the
                 ONT XDSL port line.
                 The indexes of this entry are ifIndex, hwOntObjectIndex, hwOntUniPhyType,
                 hwOntXdslPortid and an interval number.
                "
            INDEX  { ifIndex,
                   hwOntObjectIndex,
                   hwOntUniPhyType,
                     hwOntXdslPortid,
                     hwOntXdslPMLHistInit15MInterval }
            ::= { hwOntXdslPMLineInitHist15MinTable 1 }

        HwOntXdslPMLineInitHist15MinEntry  ::=
            SEQUENCE {
              hwOntXdslPMLHistInit15MInterval              Unsigned32,
              hwOntXdslPMLHistInit15MMonitoredTime         Unsigned32,
              hwOntXdslPMLHistInit15MFullInits             Unsigned32,
              hwOntXdslPMLHistInit15MFailedFullInits       Unsigned32,
              hwOntXdslPMLHistInit15MShortInits            Unsigned32,
              hwOntXdslPMLHistInit15MFailedShortInits      Unsigned32,
              hwOntXdslPMLHistInit15MValidInterval         TruthValue,
              hwOntXdslPMLHistInit15MStartTime             DateAndTime
            }

        hwOntXdslPMLHistInit15MInterval  OBJECT-TYPE
            SYNTAX      Unsigned32
            MAX-ACCESS  not-accessible
            STATUS      current
            DESCRIPTION
                "The interval number."
            ::= { hwOntXdslPMLineInitHist15MinEntry 1 }

        hwOntXdslPMLHistInit15MMonitoredTime  OBJECT-TYPE
            SYNTAX      Unsigned32
            UNITS       "seconds"
            MAX-ACCESS  read-only
            STATUS      current
            DESCRIPTION
                "Total seconds monitored in this interval.
                 Unit: seconds
                "
            ::= { hwOntXdslPMLineInitHist15MinEntry 2 }

        hwOntXdslPMLHistInit15MFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
            ::= { hwOntXdslPMLineInitHist15MinEntry 3 }

        hwOntXdslPMLHistInit15MFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwOntXdslPMLineInitHist15MinEntry 4 }

        hwOntXdslPMLHistInit15MShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwOntXdslPMLineInitHist15MinEntry 5 }

        hwOntXdslPMLHistInit15MFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwOntXdslPMLineInitHist15MinEntry 6 }

        hwOntXdslPMLHistInit15MValidInterval  OBJECT-TYPE
            SYNTAX      TruthValue
            MAX-ACCESS  read-only
            STATUS      current
            DESCRIPTION
                "This variable indicates if the data for this interval is
                 valid.
                "
            ::= { hwOntXdslPMLineInitHist15MinEntry 7 }

        hwOntXdslPMLHistInit15MStartTime  OBJECT-TYPE
            SYNTAX      DateAndTime
            MAX-ACCESS  read-only
            STATUS      current
            DESCRIPTION
                "Start time of the historical initializations 15-minute performance statistics."
            ::= { hwOntXdslPMLineInitHist15MinEntry 8 }

           --       PM ont xdsl port line init history 1 Day
        hwOntXdslPMLineInitHist1DayTable       OBJECT-TYPE
            SYNTAX      SEQUENCE  OF  HwOntXdslPMLineInitHist1DayEntry
            MAX-ACCESS  not-accessible
            STATUS      current
            DESCRIPTION
                "The table hwOntXdslPMLineInitHist1DayTable contains PM line
                 initialization history for 24 hours intervals of the ONT
                 XDSL port line.
                 The indexes of this table are ifIndex, hwOntObjectIndex, hwOntUniPhyType,
                 hwOntXdslPortid and an interval number.
                "
            ::= { hwXdslPMLine 12 }

        hwOntXdslPMLineInitHist1DayEntry  OBJECT-TYPE
            SYNTAX      HwOntXdslPMLineInitHist1DayEntry
            MAX-ACCESS  not-accessible
            STATUS      current
            DESCRIPTION
                "The table hwOntXdslPMLineInitHist1DayTable contains PM line
                 initialization history for 24 hours intervals of the ONT
                 XDSL port line.
                 The indexes of this entry are ifIndex, hwOntObjectIndex, hwOntUniPhyType,
                 hwOntXdslPortid and an interval number.
                "
            INDEX  { ifIndex,
                   hwOntObjectIndex,
                   hwOntUniPhyType,
                     hwOntXdslPortid,
                     hwOntXdslPMLHistinit1DInterval }
            ::= { hwOntXdslPMLineInitHist1DayTable 1 }

        HwOntXdslPMLineInitHist1DayEntry  ::=
            SEQUENCE {
              hwOntXdslPMLHistinit1DInterval              Unsigned32,
              hwOntXdslPMLHistinit1DMonitoredTime         Unsigned32,
              hwOntXdslPMLHistinit1DFullInits             Unsigned32,
              hwOntXdslPMLHistinit1DFailedFullInits       Unsigned32,
              hwOntXdslPMLHistinit1DShortInits            Unsigned32,
              hwOntXdslPMLHistinit1DFailedShortInits      Unsigned32,
              hwOntXdslPMLHistinit1DValidInterval         TruthValue,
              hwOntXdslPMLHistinit1DStartTime             DateAndTime
            }

        hwOntXdslPMLHistinit1DInterval  OBJECT-TYPE
            SYNTAX      Unsigned32
            MAX-ACCESS  not-accessible
            STATUS      current
            DESCRIPTION
                "The interval number."
            ::= { hwOntXdslPMLineInitHist1DayEntry 1 }

        hwOntXdslPMLHistinit1DMonitoredTime  OBJECT-TYPE
            SYNTAX      Unsigned32
            UNITS       "seconds"
            MAX-ACCESS  read-only
            STATUS      current
            DESCRIPTION
                "Total seconds monitored in this interval."
            ::= { hwOntXdslPMLineInitHist1DayEntry 2 }

        hwOntXdslPMLHistinit1DFullInits  OBJECT-TYPE
            SYNTAX      Unsigned32
            MAX-ACCESS  read-only
            STATUS      current
            DESCRIPTION
                "Count of full initializations attempted on the line
                 (successful and failed) during this interval.
                "
            REFERENCE    "ITU-T G.997.1, paragraph 7.2.1"
             ::= { hwOntXdslPMLineInitHist1DayEntry 3 }

        hwOntXdslPMLHistinit1DFailedFullInits  OBJECT-TYPE
            SYNTAX      Unsigned32
            MAX-ACCESS  read-only
            STATUS      current
            DESCRIPTION
                "Count of failed full initializations on the line during this
                 interval.
                "
            REFERENCE    "ITU-T G.997.1, paragraph 7.2.1"
            ::= { hwOntXdslPMLineInitHist1DayEntry 4 }

        hwOntXdslPMLHistinit1DShortInits  OBJECT-TYPE
            SYNTAX      Unsigned32
            MAX-ACCESS  read-only
            STATUS      current
            DESCRIPTION
                "Count of short initializations attempted on the line
                 (successful and failed) during this interval.
                "
            REFERENCE    "ITU-T G.997.1, paragraph 7.2.1"
            ::= { hwOntXdslPMLineInitHist1DayEntry 5 }

        hwOntXdslPMLHistinit1DFailedShortInits  OBJECT-TYPE
            SYNTAX      Unsigned32
            MAX-ACCESS  read-only
            STATUS      current
            DESCRIPTION
                "Count of failed short initializations on the line during this
                 interval.
                "
            REFERENCE    "ITU-T G.997.1, paragraph 7.2.1"
            ::= { hwOntXdslPMLineInitHist1DayEntry 6 }

        hwOntXdslPMLHistinit1DValidInterval  OBJECT-TYPE
            SYNTAX      TruthValue
            MAX-ACCESS  read-only
            STATUS      current
            DESCRIPTION
                "This variable indicates if the data for this interval is
                 valid.
                "
            ::= { hwOntXdslPMLineInitHist1DayEntry 7 }

        hwOntXdslPMLHistinit1DStartTime  OBJECT-TYPE
            SYNTAX      DateAndTime
            MAX-ACCESS  read-only
            STATUS      current
            DESCRIPTION
                "Start time of the historical initializations 1-day performance statistics."
            ::= { hwOntXdslPMLineInitHist1DayEntry 8 }

          --          PM channel current counters
        hwXdslPMChCurrTable        OBJECT-TYPE
            SYNTAX      SEQUENCE  OF  HwXdslPMChCurrEntry
            MAX-ACCESS  not-accessible
            STATUS      current
            DESCRIPTION
                "The table hwXdslPMChCurrTable contains current Performance
                 Monitoring results of XDSL channel.
                 The indexes of this table are an interface index where
                 the interface has an ifType value which is applicable
                 for a DSL channel and the termination unit.
                "
            ::= { hwXdslPMChannel 1 }

        hwXdslPMChCurrEntry  OBJECT-TYPE
            SYNTAX      HwXdslPMChCurrEntry
            MAX-ACCESS  not-accessible
            STATUS      current
            DESCRIPTION
                "The table hwXdslPMChCurrTable contains current Performance
                 Monitoring results of XDSL channel.
                 The indexes of this entry are an interface index where
                 the interface has an ifType value which is applicable
                 for a DSL channel and the termination unit.
                "
            INDEX  { ifIndex, hwXdslPMChCurrUnit }
            ::= { hwXdslPMChCurrTable 1 }

        HwXdslPMChCurrEntry  ::=
            SEQUENCE {
              hwXdslPMChCurrUnit                     HwXdslUnit,
              hwXdslPMChCurrValidIntervals           Unsigned32,
              hwXdslPMChCurrInvalidIntervals         Unsigned32,
              hwXdslPMChCurr15MTimeElapsed           HCPerfTimeElapsed,
              hwXdslPMChCurr15MCodingViolations      Unsigned32,
              hwXdslPMChCurr15MCorrectedBlocks       Unsigned32,
              hwXdslPMChCurr1DayValidIntervals       Unsigned32,
              hwXdslPMChCurr1DayInvalidIntervals     Unsigned32,
              hwXdslPMChCurr1DayTimeElapsed          HCPerfTimeElapsed,
              hwXdslPMChCurr1DayCodingViolations     Unsigned32,
              hwXdslPMChCurr1DayCorrectedBlocks      Unsigned32,
              hwXdslPMChEverBeforeCodingViolations   Unsigned32,
              hwXdslPMChEverBeforeCorrectedBlocks    Unsigned32,
              hwXdslPMChCurr15MEncodedBlocks         Unsigned32,
              hwXdslPMChCurr15MUncorrectableBlocks   Unsigned32,
              hwXdslPMChCurr1DayEncodedBlocks        Unsigned32,
              hwXdslPMChCurr1DayUncorrectableBlocks  Unsigned32,
              hwXdslPMChEverBeforeEncodedBlocks      Unsigned32,
              hwXdslPMChEverBeforeUncorrectableBlocks Unsigned32,
              hwXdslPMChCurr15MAtmCells              Counter32,
              hwXdslPMChCurr15MPtmPackets            Counter32,
              hwXdslPMChCurr1DayAtmCells             Counter32,
              hwXdslPMChCurr1DayPtmPackets           Counter32,
              hwXdslPMChEverBeforeAtmCells           Counter64,
              hwXdslPMChEverBeforePtmPackets         Counter64,
              hwXdslPMChCurr15MRtxCW                 Counter32,
              hwXdslPMChCurr15MRtxCorrectedCW        Counter32,
              hwXdslPMChCurr15MRtxUncorrectedCW      Counter32,
              hwXdslPMChCurr1DayRtxCW                Counter32,
              hwXdslPMChCurr1DayRtxCorrectedCW       Counter32,
              hwXdslPMChCurr1DayRtxUncorrectedCW     Counter32,
              hwXdslPMChEverBeforeRtxCW              Counter32,
              hwXdslPMChEverBeforeRtxCorrectedCW     Counter32,
              hwXdslPMChEverBeforeRtxUncorrectedCW   Counter32,
              hwXdslPMChCurr15MStartTime             DateAndTime,
              hwXdslPMChCurr1DayStartTime            DateAndTime,
              hwXdslPMChCurr15MLANDEFTRS             Integer32,
              hwXdslPMChCurr1DayLANDEFTRS            Integer32,
              hwXdslPMChEverBeforeLANDEFTRS          Counter32,
              hwXdslPMChCurr15MANDEFTRDS             Integer32,
              hwXdslPMChCurr1DayANDEFTRDS            Integer32,
              hwXdslPMChEverBeforeANDEFTRDS          Counter32,
              hwXdslPMChCurr15MMINANDEFTR            Counter32,
              hwXdslPMChCurr1DayMINANDEFTR           Counter32,
              hwXdslPMChEverBeforeMINANDEFTR         Counter32,
              hwXdslPMChCurr15MMAXANDEFTR            Counter32,
              hwXdslPMChCurr1DayMAXANDEFTR           Counter32,
              hwXdslPMChEverBeforeMAXANDEFTR         Counter32,
              hwXdslPMChCurr15MSUMANDEFTR            Counter32,
              hwXdslPMChCurr1DaySUMANDEFTR           Counter32,
              hwXdslPMChEverBeforeSUMANDEFTR         Counter64
            }

        hwXdslPMChCurrUnit  OBJECT-TYPE
            SYNTAX      HwXdslUnit
            MAX-ACCESS  not-accessible
            STATUS      current
            DESCRIPTION
                "The termination unit."
            ::= { hwXdslPMChCurrEntry 1 }

        hwXdslPMChCurrValidIntervals  OBJECT-TYPE
            SYNTAX      Unsigned32
            MAX-ACCESS  read-only
            STATUS      current
            DESCRIPTION
                "Valid intervals."
            ::= { hwXdslPMChCurrEntry 2 }

        hwXdslPMChCurrInvalidIntervals  OBJECT-TYPE
            SYNTAX      Unsigned32
            MAX-ACCESS  read-only
            STATUS      current
            DESCRIPTION
                "Invalid intervals."
             ::= { hwXdslPMChCurrEntry 3 }

        hwXdslPMChCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { hwXdslPMChCurrEntry 4 }

        hwXdslPMChCurr15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
           ::= { hwXdslPMChCurrEntry 5 }

        hwXdslPMChCurr15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwXdslPMChCurrEntry 6 }

        hwXdslPMChCurr1DayValidIntervals  OBJECT-TYPE
            SYNTAX      Unsigned32
            MAX-ACCESS  read-only
            STATUS      current
            DESCRIPTION
                "Valid intervals."
            ::= { hwXdslPMChCurrEntry 7 }

        hwXdslPMChCurr1DayInvalidIntervals  OBJECT-TYPE
            SYNTAX      Unsigned32
            MAX-ACCESS  read-only
            STATUS      current
            DESCRIPTION
                "Invalid intervals."
            ::= { hwXdslPMChCurrEntry 8 }

        hwXdslPMChCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { hwXdslPMChCurrEntry 9 }

        hwXdslPMChCurr1DayCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwXdslPMChCurrEntry 10 }

        hwXdslPMChCurr1DayCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwXdslPMChCurrEntry 11 }


        hwXdslPMChEverBeforeCodingViolations  OBJECT-TYPE
            SYNTAX      Unsigned32
            MAX-ACCESS  read-only
            STATUS      current
            DESCRIPTION
                "Count of CRC-8 (FEBE for xTU-R) anomalies occurring in the
                 channel since agent reset.  This parameter is inhibited
                 during UAS or SES.  If the CRC is applied over multiple
                 channels, then each related CRC-8 (or FEBE) anomaly should
                 increment each of the counters related to the individual
                 channels.
                 Huawei defined.
                "
            ::= { hwXdslPMChCurrEntry 12 }

        hwXdslPMChEverBeforeCorrectedBlocks  OBJECT-TYPE
            SYNTAX      Unsigned32
            MAX-ACCESS  read-only
            STATUS      current
            DESCRIPTION
                "Count of FEC (FFEC for xTU-R) anomalies (corrected code words)
                 occurring in the channel since agent reset.  This parameter
                 is inhibited during UAS or SES.  If the FEC is applied over
                 multiple channels, then each related FEC (or FFEC) anomaly
                 should increment each of the counters related to the
                 individual channels.
                 Huawei defined.
                "
            ::= { hwXdslPMChCurrEntry 13 }

        hwXdslPMChCurr15MEncodedBlocks  OBJECT-TYPE
            SYNTAX      Unsigned32
            MAX-ACCESS  read-only
            STATUS      current
            DESCRIPTION
                "Count of all encoded blocks received
                 on this channel within the current 15 minute interval.
                "
            ::= { hwXdslPMChCurrEntry 14 }

        hwXdslPMChCurr15MUncorrectableBlocks  OBJECT-TYPE
            SYNTAX      Unsigned32
            MAX-ACCESS  read-only
            STATUS      current
            DESCRIPTION
                "Count of all blocks received with
                 uncorrectable errors on this channel within the current 15 minute interval.
                "
            ::= { hwXdslPMChCurrEntry 15 }

        hwXdslPMChCurr1DayEncodedBlocks  OBJECT-TYPE
            SYNTAX      Unsigned32
            MAX-ACCESS  read-only
            STATUS      current
            DESCRIPTION
                "Count of all encoded blocks received on this channel during the current day."
            ::= { hwXdslPMChCurrEntry 16 }

        hwXdslPMChCurr1DayUncorrectableBlocks  OBJECT-TYPE
            SYNTAX      Unsigned32
            MAX-ACCESS  read-only
            STATUS      current
            DESCRIPTION
                "Count of all blocks received with uncorrectable errors on this channel during the current day."
            ::= { hwXdslPMChCurrEntry 17 }

        hwXdslPMChEverBeforeEncodedBlocks  OBJECT-TYPE
            SYNTAX      Unsigned32
            MAX-ACCESS  read-only
            STATUS      current
            DESCRIPTION
                "Count of all encoded blocks received on this
                 channel since agent reset.
                "
            ::= { hwXdslPMChCurrEntry 18 }

        hwXdslPMChEverBeforeUncorrectableBlocks  OBJECT-TYPE
            SYNTAX      Unsigned32
            MAX-ACCESS  read-only
            STATUS      current
            DESCRIPTION
                "Count of all blocks received with uncorrectable
                 errors since agent reset.
                "
            ::= { hwXdslPMChCurrEntry 19 }

        hwXdslPMChCurr15MAtmCells  OBJECT-TYPE
            SYNTAX      Counter32
            MAX-ACCESS  read-only
            STATUS      current
            DESCRIPTION
                "Count of Atm Cells received
                 within the current 15 minute interval.
                "
            ::= { hwXdslPMChCurrEntry 20 }

        hwXdslPMChCurr15MPtmPackets  OBJECT-TYPE
            SYNTAX      Counter32
            MAX-ACCESS  read-only
            STATUS      current
            DESCRIPTION
                "Count of Ptm Packet received
                 within the current 15 minute interval.
                "
            ::= { hwXdslPMChCurrEntry 21 }

        hwXdslPMChCurr1DayAtmCells  OBJECT-TYPE
            SYNTAX      Counter32
            MAX-ACCESS  read-only
            STATUS      current
            DESCRIPTION
                "Count of Atm Cells received
                 during the current day.
                "
            ::= { hwXdslPMChCurrEntry 22 }

        hwXdslPMChCurr1DayPtmPackets  OBJECT-TYPE
            SYNTAX      Counter32
            MAX-ACCESS  read-only
            STATUS      current
            DESCRIPTION
                "Count of Ptm Packets received
                 during the current day.
                "
            ::= { hwXdslPMChCurrEntry 23 }

        hwXdslPMChEverBeforeAtmCells  OBJECT-TYPE
            SYNTAX      Counter64
            MAX-ACCESS  read-only
            STATUS      current
            DESCRIPTION
                "Count of Atm Cells received
                 since agent reset.
                "
            ::= { hwXdslPMChCurrEntry 24 }

        hwXdslPMChEverBeforePtmPackets  OBJECT-TYPE
            SYNTAX      Counter64
            MAX-ACCESS  read-only
            STATUS      current
            DESCRIPTION
               "Count of Ptm Packets received
                since agent reset."
            ::= { hwXdslPMChCurrEntry 25 }

        hwXdslPMChCurr15MRtxCW  OBJECT-TYPE
            SYNTAX      Counter32
            MAX-ACCESS  read-only
            STATUS      current
            DESCRIPTION
               "Count of units request retransmission within the current 15 minute interval."
            ::= { hwXdslPMChCurrEntry 26 }

        hwXdslPMChCurr15MRtxCorrectedCW  OBJECT-TYPE
            SYNTAX      Counter32
            MAX-ACCESS  read-only
            STATUS      current
            DESCRIPTION
                "Count of units corrected by retransmission within the current 15 minute interval."
            ::= { hwXdslPMChCurrEntry 27 }

        hwXdslPMChCurr15MRtxUncorrectedCW  OBJECT-TYPE
            SYNTAX      Counter32
            MAX-ACCESS  read-only
            STATUS      current
            DESCRIPTION
                "Count of units uncorrected by retransmission within the current 15 minute interval."
            ::= { hwXdslPMChCurrEntry 28 }

        hwXdslPMChCurr1DayRtxCW  OBJECT-TYPE
            SYNTAX      Counter32
            MAX-ACCESS  read-only
            STATUS      current
            DESCRIPTION
                "Count of units request retransmission during the current day."
            ::= { hwXdslPMChCurrEntry 29 }

        hwXdslPMChCurr1DayRtxCorrectedCW  OBJECT-TYPE
            SYNTAX      Counter32
            MAX-ACCESS  read-only
            STATUS      current
            DESCRIPTION
                "Count of units corrected by retransmission during the current day."
            ::= { hwXdslPMChCurrEntry 30 }

        hwXdslPMChCurr1DayRtxUncorrectedCW  OBJECT-TYPE
            SYNTAX      Counter32
            MAX-ACCESS  read-only
            STATUS      current
            DESCRIPTION
                "Count of units uncorrected by retransmission during the current day."
            ::= { hwXdslPMChCurrEntry 31 }

        hwXdslPMChEverBeforeRtxCW  OBJECT-TYPE
            SYNTAX      Counter32
            MAX-ACCESS  read-only
            STATUS      current
            DESCRIPTION
                "Count of units request retransmission since agent reset."
            ::= { hwXdslPMChCurrEntry 32 }

        hwXdslPMChEverBeforeRtxCorrectedCW  OBJECT-TYPE
            SYNTAX      Counter32
            MAX-ACCESS  read-only
            STATUS      current
            DESCRIPTION
                "Count of units corrected by retransmission since agent reset."
            ::= { hwXdslPMChCurrEntry 33 }

        hwXdslPMChEverBeforeRtxUncorrectedCW  OBJECT-TYPE
            SYNTAX      Counter32
            MAX-ACCESS  read-only
            STATUS      current
            DESCRIPTION
                 "Count of units uncorrected by retransmission since agent reset."
            ::= { hwXdslPMChCurrEntry 34 }

        hwXdslPMChCurr15MStartTime  OBJECT-TYPE
            SYNTAX      DateAndTime
            MAX-ACCESS  read-only
            STATUS      current
            DESCRIPTION
                "Start time of the channel current 15-minute performance statistics."
            ::= { hwXdslPMChCurrEntry 35 }

        hwXdslPMChCurr1DayStartTime  OBJECT-TYPE
            SYNTAX      DateAndTime
            MAX-ACCESS  read-only
            STATUS      current
            DESCRIPTION
                "Start time of the channel current 1-day performance statistics."
            ::= { hwXdslPMChCurrEntry 36 }

        --    G.fast ANDEFTR statistics
        hwXdslPMChCurr15MLANDEFTRS  OBJECT-TYPE
            SYNTAX      Integer32
            MAX-ACCESS  read-only
            STATUS      current
            DESCRIPTION
                "Count of the LANDEFTRS seconds current 15-minute.
                The values range from 0 to 900.
                -1 indicate invalid value.
                "
            ::= { hwXdslPMChCurrEntry 37 }

        hwXdslPMChCurr1DayLANDEFTRS  OBJECT-TYPE
            SYNTAX      Integer32
            MAX-ACCESS  read-only
            STATUS      current
            DESCRIPTION
                "Count of the LANDEFTRS seconds current 1-day.
                The values range from 0 to 86400.
                -1 indicate invalid value.
                "
            ::= { hwXdslPMChCurrEntry 38 }

        hwXdslPMChEverBeforeLANDEFTRS  OBJECT-TYPE
            SYNTAX      Counter32
            MAX-ACCESS  read-only
            STATUS      current
            DESCRIPTION
                "Count of the LANDEFTRS seconds since agent reset.
                The values range from 0 to 4294967295.
                "
            ::= { hwXdslPMChCurrEntry 39 }

        hwXdslPMChCurr15MANDEFTRDS  OBJECT-TYPE
            SYNTAX      Integer32
            MAX-ACCESS  read-only
            STATUS      current
            DESCRIPTION
                "Count of the ANDEFTRDS seconds current 15-minute.
                The values range from 0 to 900.
                -1 indicate invalid value.
                "
            ::= { hwXdslPMChCurrEntry 40 }

        hwXdslPMChCurr1DayANDEFTRDS  OBJECT-TYPE
            SYNTAX      Integer32
            MAX-ACCESS  read-only
            STATUS      current
            DESCRIPTION
                "Count of the ANDEFTRDS seconds current 1-day.
                The values range from 0 to 86400.
                -1 indicate invalid value.
                "
            ::= { hwXdslPMChCurrEntry 41 }

        hwXdslPMChEverBeforeANDEFTRDS  OBJECT-TYPE
            SYNTAX      Counter32
            MAX-ACCESS  read-only
            STATUS      current
            DESCRIPTION
                "Count of the ANDEFTRDS seconds since agent reset.
                The values range from 0 to 4294967295.
                "
            ::= { hwXdslPMChCurrEntry 42 }

        hwXdslPMChCurr15MMINANDEFTR  OBJECT-TYPE
            SYNTAX      Counter32
            UNITS       "1000 bit/second"
            MAX-ACCESS  read-only
            STATUS      current
            DESCRIPTION
                "Minimum all NOI with Data symbols EFTR(Kbps) 15-minute.
                The values range from 0 to 4294967295.
                Unit: 1000 bit/second.
                "
            ::= { hwXdslPMChCurrEntry 43 }


        hwXdslPMChCurr1DayMINANDEFTR  OBJECT-TYPE
            SYNTAX      Counter32
            UNITS       "1000 bit/second"
            MAX-ACCESS  read-only
            STATUS      current
            DESCRIPTION
                "Minimum all NOI with Data symbols EFTR(Kbps) current 1-day.
                The values range from 0 to 4294967295.
                Unit: 1000 bit/second.
                "
            ::= { hwXdslPMChCurrEntry 44 }


        hwXdslPMChEverBeforeMINANDEFTR  OBJECT-TYPE
            SYNTAX      Counter32
            UNITS       "1000 bit/second"
            MAX-ACCESS  read-only
            STATUS      current
            DESCRIPTION
                "Minimum all NOI with Data symbols EFTR(Kbps) since agent reset.
                The values range from 0 to 4294967295.
                Unit: 1000 bit/second.
                "
            ::= { hwXdslPMChCurrEntry 45 }

        hwXdslPMChCurr15MMAXANDEFTR  OBJECT-TYPE
            SYNTAX      Counter32
            UNITS       "1000 bit/second"
            MAX-ACCESS  read-only
            STATUS      current
            DESCRIPTION
                "Maximum all NOI with Data symbols EFTR(Kbps) 15-minute.
                The values range from 0 to 4294967295.
                Unit: 1000 bit/second.
                "
            ::= { hwXdslPMChCurrEntry 46 }

        hwXdslPMChCurr1DayMAXANDEFTR  OBJECT-TYPE
            SYNTAX      Counter32
            UNITS       "1000 bit/second"
            MAX-ACCESS  read-only
            STATUS      current
            DESCRIPTION
                "Maximum all NOI with Data symbols EFTR(Kbps) current 1-day.
                The values range from 0 to 4294967295.
                Unit: 1000 bit/second."
            ::= { hwXdslPMChCurrEntry 47 }


        hwXdslPMChEverBeforeMAXANDEFTR  OBJECT-TYPE
            SYNTAX      Counter32
            UNITS       "1000 bit/second"
            MAX-ACCESS  read-only
            STATUS      current
            DESCRIPTION
                "Maximum all NOI with Data symbols EFTR(Kbps) since agent reset.
                The values range from 0 to 4294967295.
                Unit: 1000 bit/second."
            ::= { hwXdslPMChCurrEntry 48 }


        hwXdslPMChCurr15MSUMANDEFTR  OBJECT-TYPE
            SYNTAX      Counter32
            UNITS       "65536 bits"
            MAX-ACCESS  read-only
            STATUS      current
            DESCRIPTION
                "Sum of all NOI with Data symbols EFTR bits(65536 bits) 15-minute.
                The values range from 0 to 4294967295.
                Unit: 65536 bits.
                "
            ::= { hwXdslPMChCurrEntry 49 }


        hwXdslPMChCurr1DaySUMANDEFTR  OBJECT-TYPE
            SYNTAX      Counter32
            UNITS       "65536 bits"
            MAX-ACCESS  read-only
            STATUS      current
            DESCRIPTION
                "Sum of all NOI with Data symbols EFTR bits(65536 bits) current 1-day.
                The values range from 0 to 4294967295.
                Unit: 65536 bits.
                "
            ::= { hwXdslPMChCurrEntry 50 }


        hwXdslPMChEverBeforeSUMANDEFTR  OBJECT-TYPE
            SYNTAX      Counter64
            UNITS       "65536 bits"
            MAX-ACCESS  read-only
            STATUS      current
            DESCRIPTION
                "Sum of all NOI with Data symbols EFTR bits(65536 bits) since agent reset.
                Unit: 65536 bits.
                "
            ::= { hwXdslPMChCurrEntry 51 }

          --    PM channel history 15 Minutes
        hwXdslPMChHist15MinTable         OBJECT-TYPE
            SYNTAX      SEQUENCE  OF  HwXdslPMChHist15MinEntry
            MAX-ACCESS  not-accessible
            STATUS      current
            DESCRIPTION
                "The table hwXdslPMChHist15MinTable contains PM channel history
                 for 15min intervals of XDSL channel.
                 The indexes of this table are an interface index where
                 the interface has an ifType value which is applicable
                 for a DSL channel, the termination unit and the
                 interval number.
                "
            ::= { hwXdslPMChannel 2 }

        hwXdslPMChHist15MinEntry  OBJECT-TYPE
            SYNTAX      HwXdslPMChHist15MinEntry
            MAX-ACCESS  not-accessible
            STATUS      current
            DESCRIPTION
                "The table hwXdslPMChHist15MinTable contains PM channel history
                 for 15min intervals of XDSL channel.
                 The indexes of this entry are an interface index where
                 the interface has an ifType value which is applicable
                 for a DSL channel, the termination unit and the
                 interval number.
                "
            INDEX  { ifIndex,
                     hwXdslPMChHist15MUnit,
                     hwXdslPMChHist15MInterval }
            ::= { hwXdslPMChHist15MinTable 1 }

        HwXdslPMChHist15MinEntry  ::=
            SEQUENCE {
              hwXdslPMChHist15MUnit                     HwXdslUnit,
              hwXdslPMChHist15MInterval                 Unsigned32,
              hwXdslPMChHist15MMonitoredTime            Unsigned32,
              hwXdslPMChHist15MCodingViolations         Unsigned32,
              hwXdslPMChHist15MCorrectedBlocks          Unsigned32,
              hwXdslPMChHist15MValidInterval            TruthValue,
              hwXdslPMChHist15MEncodedBlocks            Unsigned32,
              hwXdslPMChHist15MUncorrectableBlocks      Unsigned32,
              hwXdslPMChHist15MAtmCells                 Counter32,
              hwXdslPMChHist15MPtmPackets               Counter32,
              hwXdslPMChHist15MRtxCW                    Counter32,
              hwXdslPMChHist15MRtxCorrectedCW           Counter32,
              hwXdslPMChHist15MRtxUncorrectedCW         Counter32,
              hwXdslPMChHist15MStartTime                DateAndTime,
              hwXdslPMChHist15MLANDEFTRS                Integer32,
              hwXdslPMChHist15MANDEFTRDS                Integer32,
              hwXdslPMChHist15MMINANDEFTR               Counter32,
              hwXdslPMChHist15MMAXANDEFTR               Counter32,
              hwXdslPMChHist15MSUMANDEFTR               Counter32
            }

        hwXdslPMChHist15MUnit  OBJECT-TYPE
            SYNTAX      HwXdslUnit
            MAX-ACCESS  not-accessible
            STATUS      current
            DESCRIPTION
                "The termination unit."
            ::= { hwXdslPMChHist15MinEntry 1 }

        hwXdslPMChHist15MInterval  OBJECT-TYPE
            SYNTAX      Unsigned32
            MAX-ACCESS  not-accessible
            STATUS      current
            DESCRIPTION
                "The interval number."
            ::= { hwXdslPMChHist15MinEntry 2 }

        hwXdslPMChHist15MMonitoredTime  OBJECT-TYPE
            SYNTAX      Unsigned32
            UNITS       "seconds"
            MAX-ACCESS  read-only
            STATUS      current
            DESCRIPTION
                "Total seconds monitored in this interval.
                 Unit: seconds
                "
            ::= { hwXdslPMChHist15MinEntry 3 }

        hwXdslPMChHist15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwXdslPMChHist15MinEntry 4 }

        hwXdslPMChHist15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwXdslPMChHist15MinEntry 5 }

        hwXdslPMChHist15MValidInterval  OBJECT-TYPE
            SYNTAX      TruthValue
            MAX-ACCESS  read-only
            STATUS      current
            DESCRIPTION
                "This variable indicates if the data for this interval is
                 valid.
                "
            ::= { hwXdslPMChHist15MinEntry 6 }

        hwXdslPMChHist15MEncodedBlocks  OBJECT-TYPE
            SYNTAX      Unsigned32
            MAX-ACCESS  read-only
            STATUS      current
            DESCRIPTION
                "Count of all encoded blocks received on this
                 channel during the interval.
                "
            ::= { hwXdslPMChHist15MinEntry 7 }

        hwXdslPMChHist15MUncorrectableBlocks  OBJECT-TYPE
            SYNTAX      Unsigned32
            MAX-ACCESS  read-only
            STATUS      current
            DESCRIPTION
                "Count of all blocks received with uncorrectable
                 errors on this channel during the interval.
                "
            ::= { hwXdslPMChHist15MinEntry 8 }

        hwXdslPMChHist15MAtmCells  OBJECT-TYPE
            SYNTAX      Counter32
            MAX-ACCESS  read-only
            STATUS      current
            DESCRIPTION
                "Count of Atm Cells received
                 on this channel during the interval.
                "
            ::= { hwXdslPMChHist15MinEntry 9 }

        hwXdslPMChHist15MPtmPackets  OBJECT-TYPE
            SYNTAX      Counter32
            MAX-ACCESS  read-only
            STATUS      current
            DESCRIPTION
                "Count of Ptm Packets received
                 on this channel during the interval.
                "
            ::= { hwXdslPMChHist15MinEntry 10 }

        hwXdslPMChHist15MRtxCW  OBJECT-TYPE
            SYNTAX      Counter32
            MAX-ACCESS  read-only
            STATUS      current
            DESCRIPTION
                "Count of units request retransmission during the
                 serval 15 minute interval of history.
                "
            ::= { hwXdslPMChHist15MinEntry 11 }

        hwXdslPMChHist15MRtxCorrectedCW  OBJECT-TYPE
            SYNTAX      Counter32
            MAX-ACCESS  read-only
            STATUS      current
            DESCRIPTION
                "Count of units corrected by retransmission during the
                 serval 15 minute interval of history.
                "
            ::= { hwXdslPMChHist15MinEntry 12 }

        hwXdslPMChHist15MRtxUncorrectedCW  OBJECT-TYPE
            SYNTAX      Counter32
            MAX-ACCESS  read-only
            STATUS      current
            DESCRIPTION
                "Count of units uncorrected by retransmission during
                 the serval 15 minute interval of history.
                "
            ::= { hwXdslPMChHist15MinEntry 13 }

        hwXdslPMChHist15MStartTime  OBJECT-TYPE
            SYNTAX      DateAndTime
            MAX-ACCESS  read-only
            STATUS      current
            DESCRIPTION
                "Start time of the channel historical 15-minute performance
                 statistics.
                "
            ::= { hwXdslPMChHist15MinEntry 14 }

        --    G.fast ANDEFTR statistics
        hwXdslPMChHist15MLANDEFTRS  OBJECT-TYPE
            SYNTAX      Integer32
            MAX-ACCESS  read-only
            STATUS      current
            DESCRIPTION
                "Count of the LANDEFTRS seconds during the serval 15 minute interval of history.
                The values range from 0 to 900.
                -1 indicate invalid value.
                "
            ::= { hwXdslPMChHist15MinEntry 15 }

        hwXdslPMChHist15MANDEFTRDS  OBJECT-TYPE
            SYNTAX      Integer32
            MAX-ACCESS  read-only
            STATUS      current
            DESCRIPTION
                "Count of the ANDEFTRDS seconds during the serval 15 minute interval of history.
                The values range from 0 to 86400.
                -1 indicate invalid value.
                "
            ::= { hwXdslPMChHist15MinEntry 16 }

        hwXdslPMChHist15MMINANDEFTR  OBJECT-TYPE
            SYNTAX      Counter32
            UNITS       "1000 bit/second"
            MAX-ACCESS  read-only
            STATUS      current
            DESCRIPTION
                "Minimum all NOI with Data symbols EFTR(Kbps) during the serval 15 minute interval of history.
                The values range from 0 to 4294967295.
                Unit: 1000 bit/second.
                "
            ::= { hwXdslPMChHist15MinEntry 17 }

        hwXdslPMChHist15MMAXANDEFTR  OBJECT-TYPE
            SYNTAX      Counter32
            UNITS       "1000 bit/second"
            MAX-ACCESS  read-only
            STATUS      current
            DESCRIPTION
                "Maximum all NOI with Data symbols EFTR(Kbps) during the serval 15 minute interval of history.
                The values range from 0 to 4294967295.
                Unit: 1000 bit/second.
                "
            ::= { hwXdslPMChHist15MinEntry 18 }

        hwXdslPMChHist15MSUMANDEFTR  OBJECT-TYPE
            SYNTAX      Counter32
            UNITS       "65536 bits"
            MAX-ACCESS  read-only
            STATUS      current
            DESCRIPTION
                "Sum of all NOI with Data symbols EFTR bits(65536 bits) during the serval 15 minute interval of history.
                The values range from 0 to 4294967295.
                Unit: 65536 bits.
                "
            ::= { hwXdslPMChHist15MinEntry 19 }

          --        PM channel history 1 Day
        hwXdslPMChHist1DTable         OBJECT-TYPE
            SYNTAX      SEQUENCE  OF  HwXdslPMChHist1DEntry
            MAX-ACCESS  not-accessible
            STATUS      current
            DESCRIPTION
                "The table hwXdslPMChHist1DTable contains PM channel history
                 for 1 day intervals of XDSL2. The indexes of this table are
                 an interface index where
                 the interface has an ifType value which is applicable
                 for a DSL channel, the termination unit and the
                 interval number.
                "
            ::= { hwXdslPMChannel 3 }

        hwXdslPMChHist1DEntry  OBJECT-TYPE
            SYNTAX      HwXdslPMChHist1DEntry
            MAX-ACCESS  not-accessible
            STATUS      current
            DESCRIPTION
                "The table hwXdslPMChHist1DTable contains PM channel history
                 for 1 day intervals of XDSL2.
                 The indexes of this entry are an interface index where
                 the interface has an ifType value which is applicable
                 for a DSL channel, the termination unit and the
                 interval number.
                "
            INDEX  { ifIndex,
                     hwXdslPMChHist1DUnit,
                     hwXdslPMChHist1DInterval }
            ::= { hwXdslPMChHist1DTable 1 }

        HwXdslPMChHist1DEntry  ::=
            SEQUENCE {
               hwXdslPMChHist1DUnit                      HwXdslUnit,
               hwXdslPMChHist1DInterval                  Unsigned32,
               hwXdslPMChHist1DMonitoredTime             Unsigned32,
               hwXdslPMChHist1DCodingViolations          Unsigned32,
               hwXdslPMChHist1DCorrectedBlocks           Unsigned32,
               hwXdslPMChHist1DValidInterval             TruthValue,
               hwXdslPMChHist1DEncodedBlocks             Unsigned32,
               hwXdslPMChHist1DUncorrectableBlocks       Unsigned32,
               hwXdslPMChHist1DAtmCells                  Counter32,
               hwXdslPMChHist1DPtmPackets                Counter32,
               hwXdslPMChHist1DRtxCW                     Counter32,
               hwXdslPMChHist1DRtxCorrectedCW            Counter32,
               hwXdslPMChHist1DRtxUncorrectedCW          Counter32,
               hwXdslPMChHist1DStartTime                 DateAndTime,
               hwXdslPMChHist1DLANDEFTRS                 Integer32,
               hwXdslPMChHist1DANDEFTRDS                 Integer32,
               hwXdslPMChHist1DMINANDEFTR                Counter32,
               hwXdslPMChHist1DMAXANDEFTR                Counter32,
               hwXdslPMChHist1DSUMANDEFTR                Counter32
            }

        hwXdslPMChHist1DUnit  OBJECT-TYPE
            SYNTAX      HwXdslUnit
            MAX-ACCESS  not-accessible
            STATUS      current
            DESCRIPTION
                "The termination unit."
             ::= { hwXdslPMChHist1DEntry 1 }

        hwXdslPMChHist1DInterval  OBJECT-TYPE
            SYNTAX      Unsigned32
            MAX-ACCESS  not-accessible
            STATUS      current
            DESCRIPTION
                "The interval number."
            ::= { hwXdslPMChHist1DEntry 2 }

        hwXdslPMChHist1DMonitoredTime  OBJECT-TYPE
            SYNTAX      Unsigned32
            UNITS       "seconds"
            MAX-ACCESS  read-only
            STATUS      current
            DESCRIPTION
                "Total seconds monitored in this interval.
                 Unit: seconds
                "
            ::= { hwXdslPMChHist1DEntry 3 }

        hwXdslPMChHist1DCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwXdslPMChHist1DEntry 4 }

        hwXdslPMChHist1DCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwXdslPMChHist1DEntry 5 }

        hwXdslPMChHist1DValidInterval  OBJECT-TYPE
            SYNTAX      TruthValue
            MAX-ACCESS  read-only
            STATUS      current
            DESCRIPTION
                "This variable indicates if the data for this interval is
                 valid.
                "
            ::= { hwXdslPMChHist1DEntry 6 }

        hwXdslPMChHist1DEncodedBlocks  OBJECT-TYPE
            SYNTAX      Unsigned32
            MAX-ACCESS  read-only
            STATUS      current
            DESCRIPTION
                "Count of all encoded blocks received on this
                 channel during the interval.
                "
            ::= { hwXdslPMChHist1DEntry 7 }

        hwXdslPMChHist1DUncorrectableBlocks  OBJECT-TYPE
            SYNTAX      Unsigned32
            MAX-ACCESS  read-only
            STATUS      current
            DESCRIPTION
                "Count of all blocks received with uncorrectable
                 errors on this channel during the interval."
            ::= { hwXdslPMChHist1DEntry 8 }

        hwXdslPMChHist1DAtmCells  OBJECT-TYPE
            SYNTAX      Counter32
            MAX-ACCESS  read-only
            STATUS      current
            DESCRIPTION
                "Count of Atm Cells received
                 on this channel during the interval.
                "
            ::= { hwXdslPMChHist1DEntry 9 }

        hwXdslPMChHist1DPtmPackets  OBJECT-TYPE
            SYNTAX      Counter32
            MAX-ACCESS  read-only
            STATUS      current
            DESCRIPTION
                "Count of Ptm Packets received
                 on this channel during the interval.
                "
            ::= { hwXdslPMChHist1DEntry 10 }

        hwXdslPMChHist1DRtxCW  OBJECT-TYPE
            SYNTAX      Counter32
            MAX-ACCESS  read-only
            STATUS      current
            DESCRIPTION
                "Count of units request retransmission within the
                 serval one day interval of history.
                "
            ::= { hwXdslPMChHist1DEntry 11 }

        hwXdslPMChHist1DRtxCorrectedCW  OBJECT-TYPE
            SYNTAX      Counter32
            MAX-ACCESS  read-only
            STATUS      current
            DESCRIPTION
                "Count of units corrected by retransmission during the
                 serval one day interval of history.
                "
            ::= { hwXdslPMChHist1DEntry 12 }

        hwXdslPMChHist1DRtxUncorrectedCW  OBJECT-TYPE
            SYNTAX      Counter32
            MAX-ACCESS  read-only
            STATUS      current
            DESCRIPTION
                "Count of units uncorrected by retransmission during
                 the serval one day interval of history.
                "
            ::= { hwXdslPMChHist1DEntry 13 }

        hwXdslPMChHist1DStartTime  OBJECT-TYPE
            SYNTAX      DateAndTime
            MAX-ACCESS  read-only
            STATUS      current
            DESCRIPTION
                "Start time of the channel historical 1-day performance statistics."
            ::= { hwXdslPMChHist1DEntry 14 }

        --    G.fast ANDEFTR statistics
        hwXdslPMChHist1DLANDEFTRS  OBJECT-TYPE
            SYNTAX      Integer32
            MAX-ACCESS  read-only
            STATUS      current
            DESCRIPTION
                "Count of the LANDEFTRS seconds during the serval one day interval of history.
                The values range from 0 to 900.
                -1 indicate invalid value.
                "
            ::= { hwXdslPMChHist1DEntry 15 }

        hwXdslPMChHist1DANDEFTRDS  OBJECT-TYPE
            SYNTAX      Integer32
            MAX-ACCESS  read-only
            STATUS      current
            DESCRIPTION
                "Count of the ANDEFTRDS seconds during the serval one day interval of history.
                The values range from 0 to 86400.
                -1 indicate invalid value.
                "
            ::= { hwXdslPMChHist1DEntry 16 }

        hwXdslPMChHist1DMINANDEFTR  OBJECT-TYPE
            SYNTAX      Counter32
            UNITS       "1000 bit/second"
            MAX-ACCESS  read-only
            STATUS      current
            DESCRIPTION
                "Minimum all NOI with Data symbols EFTR(Kbps) during the serval one day interval of history.
                The values range from 0 to 4294967295.
                Unit: 1000 bit/second.
                "
            ::= { hwXdslPMChHist1DEntry 17 }

        hwXdslPMChHist1DMAXANDEFTR  OBJECT-TYPE
            SYNTAX      Counter32
            UNITS       "1000 bit/second"
            MAX-ACCESS  read-only
            STATUS      current
            DESCRIPTION
                "Maximum all NOI with Data symbols EFTR(Kbps) during the serval one day interval of history.
                The values range from 0 to 4294967295.
                Unit: 1000 bit/second.
                "
            ::= { hwXdslPMChHist1DEntry 18 }

        hwXdslPMChHist1DSUMANDEFTR  OBJECT-TYPE
            SYNTAX      Counter32
            UNITS       "65536 bits"
            MAX-ACCESS  read-only
            STATUS      current
            DESCRIPTION
                "Sum of all NOI with Data symbols EFTR bits(65536 bits) during the serval one day interval of history.
                The values range from 0 to 4294967295.
                Unit: 65536 bits.
                "
            ::= { hwXdslPMChHist1DEntry 19 }

          --          PM channel chipset statistics
        hwXdslPMChChipStatTable        OBJECT-TYPE
            SYNTAX      SEQUENCE  OF  HwXdslPMChChipStatEntry
            MAX-ACCESS  not-accessible
            STATUS      current
            DESCRIPTION
                "The table hwXdslPMChChipStatTable contains packets and CRC errors on chipset of
                 upstream and downstream of XDSL channel.
                 The indexes of this table are an interface index where
                 the interface has an ifType value which is applicable
                 for a DSL channel and the termination unit.
                "
            ::= { hwXdslPMChannel 4 }

        hwXdslPMChChipStatEntry  OBJECT-TYPE
            SYNTAX      HwXdslPMChChipStatEntry
            MAX-ACCESS  not-accessible
            STATUS      current
            DESCRIPTION
                "The table hwXdslPMChChipStatTable contains packets and CRC errors on chipset of
                 upstream and downstream of XDSL channel.
                 The indexes of this entry are an interface index where
                 the interface has an ifType value which is applicable
                 for a DSL channel and the termination unit.
                "
            INDEX  { ifIndex, hwXdslPMChChipstatUnit }
            ::= { hwXdslPMChChipStatTable 1 }

        HwXdslPMChChipStatEntry  ::=
            SEQUENCE {
               hwXdslPMChChipstatUnit                 HwXdslUnit,
               hwXdslPMChPktsDs                       Unsigned32,
               hwXdslPMChPktsUs                       Unsigned32,
               hwXdslPMChCrcErrsDs                    Unsigned32,
               hwXdslPMChCrcErrsUs                    Unsigned32,
               hwXdslPMChStatAdminStatus              INTEGER

            }

        hwXdslPMChChipstatUnit  OBJECT-TYPE
            SYNTAX      HwXdslUnit
            MAX-ACCESS  not-accessible
            STATUS      current
            DESCRIPTION
                "The termination unit."
            ::= { hwXdslPMChChipStatEntry 1 }

        hwXdslPMChPktsDs  OBJECT-TYPE
            SYNTAX      Unsigned32
            MAX-ACCESS  read-only
            STATUS      current
            DESCRIPTION
                "The number of downstream packets."
             ::= { hwXdslPMChChipStatEntry 2 }

        hwXdslPMChPktsUs  OBJECT-TYPE
            SYNTAX      Unsigned32
            MAX-ACCESS  read-only
            STATUS      current
            DESCRIPTION
                "The number of upstream packets."
            ::= { hwXdslPMChChipStatEntry 3 }

        hwXdslPMChCrcErrsDs  OBJECT-TYPE
            SYNTAX      Unsigned32
            MAX-ACCESS  read-only
            STATUS      current
            DESCRIPTION
                "The number of downstream CRC errors."
             ::= { hwXdslPMChChipStatEntry 4 }

        hwXdslPMChCrcErrsUs  OBJECT-TYPE
            SYNTAX      Unsigned32
            MAX-ACCESS  read-only
            STATUS      current
            DESCRIPTION
                "The number of upstream CRC errors."
            ::= { hwXdslPMChChipStatEntry 5 }

        hwXdslPMChStatAdminStatus OBJECT-TYPE
            SYNTAX  INTEGER {
                        reset(1)
                     }
            MAX-ACCESS  read-write
            STATUS  current
            DESCRIPTION
                "Clear the number of packets transmitted and received,
                 CRC errors upstream and downstream.
                 Options:
                 1. reset(1)       - reset statistic data
                "
            ::= { hwXdslPMChChipStatEntry 6 }

          --          PM ont xdsl port channel current counters
        hwOntXdslPMChCurrTable        OBJECT-TYPE
            SYNTAX      SEQUENCE  OF  HwOntXdslPMChCurrEntry
            MAX-ACCESS  not-accessible
            STATUS      current
            DESCRIPTION
                "The table hwOntXdslPMChCurrTable contains current Performance
                 Monitoring results of XDSL channel.
                 The indexes of this table are ifIndex, hwOntObjectIndex, hwOntUniPhyType,
                 hwOntXdslPortid, hwOntXdslChannelID and hwOntXdslPMChCurrUnit.
                "
            ::= { hwXdslPMChannel 5 }

        hwOntXdslPMChCurrEntry  OBJECT-TYPE
            SYNTAX      HwOntXdslPMChCurrEntry
            MAX-ACCESS  not-accessible
            STATUS      current
            DESCRIPTION
                "The table hwOntXdslPMChCurrTable contains current Performance
                 Monitoring results of XDSL channel.
                 The indexes of this entry are ifIndex, hwOntObjectIndex, hwOntUniPhyType,
                 hwOntXdslPortid, hwOntXdslChannelID and hwOntXdslPMChCurrUnit.
                "
            INDEX  { ifIndex,
               hwOntObjectIndex,
               hwOntUniPhyType,
                   hwOntXdslPortid,
                   hwOntXdslChannelID,
                   hwOntXdslPMChCurrUnit }
            ::= { hwOntXdslPMChCurrTable 1 }

        HwOntXdslPMChCurrEntry  ::=
            SEQUENCE {
              hwOntXdslPMChCurrUnit                     HwXdslUnit,
              hwOntXdslPMChCurrValidIntervals           Unsigned32,
              hwOntXdslPMChCurrInvalidIntervals         Unsigned32,
              hwOntXdslPMChCurr15MTimeElapsed           HCPerfTimeElapsed,
              hwOntXdslPMChCurr15MCodingViolations      Unsigned32,
              hwOntXdslPMChCurr15MCorrectedBlocks       Unsigned32,
              hwOntXdslPMChCurr1DayValidIntervals       Unsigned32,
              hwOntXdslPMChCurr1DayInvalidIntervals     Unsigned32,
              hwOntXdslPMChCurr1DayTimeElapsed          HCPerfTimeElapsed,
              hwOntXdslPMChCurr1DayCodingViolations     Unsigned32,
              hwOntXdslPMChCurr1DayCorrectedBlocks      Unsigned32,
              hwOntXdslPMChEverBeforeCodingViolations   Unsigned32,
              hwOntXdslPMChEverBeforeCorrectedBlocks    Unsigned32,
              hwOntXdslPMChCurr15MEncodedBlocks         Unsigned32,
              hwOntXdslPMChCurr15MUncorrectableBlocks   Unsigned32,
              hwOntXdslPMChCurr1DayEncodedBlocks        Unsigned32,
              hwOntXdslPMChCurr1DayUncorrectableBlocks  Unsigned32,
              hwOntXdslPMChEverBeforeEncodedBlocks      Unsigned32,
              hwOntXdslPMChEverBeforeUncorrectableBlocks Unsigned32,
              hwOntXdslPMChCurr15MAtmCells              Counter32,
              hwOntXdslPMChCurr15MPtmPackets            Counter32,
              hwOntXdslPMChCurr1DayAtmCells             Counter32,
              hwOntXdslPMChCurr1DayPtmPackets           Counter32,
              hwOntXdslPMChEverBeforeAtmCells           Counter64,
              hwOntXdslPMChEverBeforePtmPackets         Counter64,
              hwOntXdslPMChCurr15MRtxCW    Counter32,
              hwOntXdslPMChCurr15MRtxCorrectedCW   Counter32,
              hwOntXdslPMChCurr15MRtxUncorrectedCW      Counter32,
              hwOntXdslPMChCurr1DayRtxCW     Counter32,
              hwOntXdslPMChCurr1DayRtxCorrectedCW       Counter32,
              hwOntXdslPMChCurr1DayRtxUncorrectedCW     Counter32,
              hwOntXdslPMChEverBeforeRtxCW           Counter32,
              hwOntXdslPMChEverBeforeRtxCorrectedCW     Counter32,
              hwOntXdslPMChEverBeforeRtxUncorrectedCW   Counter32,
              hwOntXdslPMChCurr15MStartTime             DateAndTime,
              hwOntXdslPMChCurr1DayStartTime            DateAndTime
            }
        hwOntXdslPMChCurrUnit  OBJECT-TYPE
            SYNTAX      HwXdslUnit
            MAX-ACCESS  not-accessible
            STATUS      current
            DESCRIPTION
                "The termination unit xTU-C(1) or xTU-R(2)."
            ::= { hwOntXdslPMChCurrEntry 1 }
        hwOntXdslPMChCurrValidIntervals  OBJECT-TYPE
            SYNTAX      Unsigned32
            MAX-ACCESS  read-only
            STATUS      current
            DESCRIPTION
                "Valid intervals."
            ::= { hwOntXdslPMChCurrEntry 2 }
        hwOntXdslPMChCurrInvalidIntervals  OBJECT-TYPE
            SYNTAX      Unsigned32
            MAX-ACCESS  read-only
            STATUS      current
            DESCRIPTION
                "Invalid intervals."
             ::= { hwOntXdslPMChCurrEntry 3 }
        hwOntXdslPMChCurr15MTimeElapsed  OBJECT-TYPE
            SYNTAX      HCPerfTimeElapsed
            UNITS       "seconds"
            MAX-ACCESS  read-only
            STATUS      current
            DESCRIPTION
                "Total elapsed seconds in this interval.
                 Unit: seconds
                "
            ::= { hwOntXdslPMChCurrEntry 4 }
        hwOntXdslPMChCurr15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
           ::= { hwOntXdslPMChCurrEntry 5 }
        hwOntXdslPMChCurr15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwOntXdslPMChCurrEntry 6 }
        hwOntXdslPMChCurr1DayValidIntervals  OBJECT-TYPE
            SYNTAX      Unsigned32
            MAX-ACCESS  read-only
            STATUS      current
            DESCRIPTION
                "Valid intervals."
            ::= { hwOntXdslPMChCurrEntry 7 }
        hwOntXdslPMChCurr1DayInvalidIntervals  OBJECT-TYPE
            SYNTAX      Unsigned32
            MAX-ACCESS  read-only
            STATUS      current
            DESCRIPTION
                "Invalid intervals."
            ::= { hwOntXdslPMChCurrEntry 8 }
        hwOntXdslPMChCurr1DayTimeElapsed  OBJECT-TYPE
            SYNTAX      HCPerfTimeElapsed
            UNITS       "seconds"
            MAX-ACCESS  read-only
            STATUS      current
            DESCRIPTION
                "Total elapsed seconds in this interval.
                 Unit: seconds
                "
            ::= { hwOntXdslPMChCurrEntry 9 }
        hwOntXdslPMChCurr1DayCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwOntXdslPMChCurrEntry 10 }
        hwOntXdslPMChCurr1DayCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwOntXdslPMChCurrEntry 11 }
        hwOntXdslPMChEverBeforeCodingViolations  OBJECT-TYPE
            SYNTAX      Unsigned32
            MAX-ACCESS  read-only
            STATUS      current
            DESCRIPTION
                "Count of CRC-8 (FEBE for xTU-R) anomalies occurring in the
                 channel since agent reset.  This parameter is inhibited
                 during UAS or SES.  If the CRC is applied over multiple
                 channels, then each related CRC-8 (or FEBE) anomaly should
                 increment each of the counters related to the individual
                 channels.
                 Huawei defined.
                "
            ::= { hwOntXdslPMChCurrEntry 12 }
        hwOntXdslPMChEverBeforeCorrectedBlocks  OBJECT-TYPE
            SYNTAX      Unsigned32
            MAX-ACCESS  read-only
            STATUS      current
            DESCRIPTION
                "Count of FEC (FFEC for xTU-R) anomalies (corrected code words)
                 occurring in the channel since agent reset.  This parameter
                 is inhibited during UAS or SES.  If the FEC is applied over
                 multiple channels, then each related FEC (or FFEC) anomaly
                 should increment each of the counters related to the
                 individual channels.
                 Huawei defined.
                "
            ::= { hwOntXdslPMChCurrEntry 13 }
        hwOntXdslPMChCurr15MEncodedBlocks  OBJECT-TYPE
            SYNTAX      Unsigned32
            MAX-ACCESS  read-only
            STATUS      current
            DESCRIPTION
                "Count of all encoded blocks received
                 on this channel within the current 15 minute interval.
                "
            ::= { hwOntXdslPMChCurrEntry 14 }
        hwOntXdslPMChCurr15MUncorrectableBlocks  OBJECT-TYPE
            SYNTAX      Unsigned32
            MAX-ACCESS  read-only
            STATUS      current
            DESCRIPTION
                "Count of all blocks received with
                 uncorrectable errors on this channel within the current 15 minute interval.
                "
            ::= { hwOntXdslPMChCurrEntry 15 }
        hwOntXdslPMChCurr1DayEncodedBlocks  OBJECT-TYPE
            SYNTAX      Unsigned32
            MAX-ACCESS  read-only
            STATUS      current
            DESCRIPTION
                "Count of all encoded blocks received on this channel during the current day."
            ::= { hwOntXdslPMChCurrEntry 16 }
        hwOntXdslPMChCurr1DayUncorrectableBlocks  OBJECT-TYPE
            SYNTAX      Unsigned32
            MAX-ACCESS  read-only
            STATUS      current
            DESCRIPTION
                "Count of all blocks received with uncorrectable errors on this channel during the current day."
            ::= { hwOntXdslPMChCurrEntry 17 }
        hwOntXdslPMChEverBeforeEncodedBlocks  OBJECT-TYPE
            SYNTAX      Unsigned32
            MAX-ACCESS  read-only
            STATUS      current
            DESCRIPTION
                "Count of all encoded blocks received on this
                 channel since agent reset.
                "
            ::= { hwOntXdslPMChCurrEntry 18 }
        hwOntXdslPMChEverBeforeUncorrectableBlocks  OBJECT-TYPE
            SYNTAX      Unsigned32
            MAX-ACCESS  read-only
            STATUS      current
            DESCRIPTION
                "Count of all blocks received with uncorrectable
                 errors since agent reset.
                "
            ::= { hwOntXdslPMChCurrEntry 19 }
        hwOntXdslPMChCurr15MAtmCells  OBJECT-TYPE
            SYNTAX      Counter32
            MAX-ACCESS  read-only
            STATUS      current
            DESCRIPTION
                "Count of Atm Cells received
                 within the current 15 minute interval.
                 Currently, this leaf is reserved, and it is not supported.
                "
            ::= { hwOntXdslPMChCurrEntry 20 }
        hwOntXdslPMChCurr15MPtmPackets  OBJECT-TYPE
            SYNTAX      Counter32
            MAX-ACCESS  read-only
            STATUS      current
            DESCRIPTION
                "Count of Ptm Packet received
                 within the current 15 minute interval.
                 Currently, this leaf is reserved, and it is not supported.
                "
            ::= { hwOntXdslPMChCurrEntry 21 }
        hwOntXdslPMChCurr1DayAtmCells  OBJECT-TYPE
            SYNTAX      Counter32
            MAX-ACCESS  read-only
            STATUS      current
            DESCRIPTION
                "Count of Atm Cells received
                 during the current day.
                 Currently, this leaf is reserved, and it is not supported.
                "
            ::= { hwOntXdslPMChCurrEntry 22 }
        hwOntXdslPMChCurr1DayPtmPackets  OBJECT-TYPE
            SYNTAX      Counter32
            MAX-ACCESS  read-only
            STATUS      current
            DESCRIPTION
                "Count of Ptm Packets received
                 during the current day.
                 Currently, this leaf is reserved, and it is not supported.
                "
            ::= { hwOntXdslPMChCurrEntry 23 }
        hwOntXdslPMChEverBeforeAtmCells  OBJECT-TYPE
            SYNTAX      Counter64
            MAX-ACCESS  read-only
            STATUS      current
            DESCRIPTION
                "Count of Atm Cells received
                 since agent reset.
                 Currently, this leaf is reserved, and it is not supported.
                "
            ::= { hwOntXdslPMChCurrEntry 24 }
        hwOntXdslPMChEverBeforePtmPackets  OBJECT-TYPE
            SYNTAX      Counter64
            MAX-ACCESS  read-only
            STATUS      current
            DESCRIPTION
               "Count of Ptm Packets received
                since agent reset.
                Currently, this leaf is reserved, and it is not supported.
                "
            ::= { hwOntXdslPMChCurrEntry 25 }
        hwOntXdslPMChCurr15MRtxCW  OBJECT-TYPE
            SYNTAX      Counter32
            MAX-ACCESS  read-only
            STATUS      current
            DESCRIPTION
               "Count of units request retransmission within the current 15 minute interval.
                Currently, this leaf is reserved, and it is not supported.
               "
            ::= { hwOntXdslPMChCurrEntry 26 }
        hwOntXdslPMChCurr15MRtxCorrectedCW  OBJECT-TYPE
            SYNTAX      Counter32
            MAX-ACCESS  read-only
            STATUS      current
            DESCRIPTION
                "Count of units corrected by retransmission within the current 15 minute interval.
                Currently, this leaf is reserved, and it is not supported.
                "
            ::= { hwOntXdslPMChCurrEntry 27 }
        hwOntXdslPMChCurr15MRtxUncorrectedCW  OBJECT-TYPE
            SYNTAX      Counter32
            MAX-ACCESS  read-only
            STATUS      current
            DESCRIPTION
                "Count of units uncorrected by retransmission within the current 15 minute interval.
                Currently, this leaf is reserved, and it is not supported.
                "
            ::= { hwOntXdslPMChCurrEntry 28 }
        hwOntXdslPMChCurr1DayRtxCW  OBJECT-TYPE
            SYNTAX      Counter32
            MAX-ACCESS  read-only
            STATUS      current
            DESCRIPTION
                "Count of units request retransmission during the current day.
                Currently, this leaf is reserved, and it is not supported.
                "
            ::= { hwOntXdslPMChCurrEntry 29 }
        hwOntXdslPMChCurr1DayRtxCorrectedCW  OBJECT-TYPE
            SYNTAX      Counter32
            MAX-ACCESS  read-only
            STATUS      current
            DESCRIPTION
                "Count of units corrected by retransmission during the current day.
                Currently, this leaf is reserved, and it is not supported.
                "
            ::= { hwOntXdslPMChCurrEntry 30 }
        hwOntXdslPMChCurr1DayRtxUncorrectedCW  OBJECT-TYPE
            SYNTAX      Counter32
            MAX-ACCESS  read-only
            STATUS      current
            DESCRIPTION
                "Count of units uncorrected by retransmission during the current day.
                Currently, this leaf is reserved, and it is not supported.
                "
            ::= { hwOntXdslPMChCurrEntry 31 }
        hwOntXdslPMChEverBeforeRtxCW  OBJECT-TYPE
            SYNTAX      Counter32
            MAX-ACCESS  read-only
            STATUS      current
            DESCRIPTION
                "Count of units request retransmission since agent reset.
                Currently, this leaf is reserved, and it is not supported.
                "
            ::= { hwOntXdslPMChCurrEntry 32 }
        hwOntXdslPMChEverBeforeRtxCorrectedCW  OBJECT-TYPE
            SYNTAX      Counter32
            MAX-ACCESS  read-only
            STATUS      current
            DESCRIPTION
                "Count of units corrected by retransmission since agent reset.
                 Currently, this leaf is reserved, and it is not supported.
                "
            ::= { hwOntXdslPMChCurrEntry 33 }
        hwOntXdslPMChEverBeforeRtxUncorrectedCW  OBJECT-TYPE
            SYNTAX      Counter32
            MAX-ACCESS  read-only
            STATUS      current
            DESCRIPTION
                 "Count of units uncorrected by retransmission since agent reset.
                  Currently, this leaf is reserved, and it is not supported.
                 "
            ::= { hwOntXdslPMChCurrEntry 34 }
        hwOntXdslPMChCurr15MStartTime  OBJECT-TYPE
            SYNTAX      DateAndTime
            MAX-ACCESS  read-only
            STATUS      current
            DESCRIPTION
                "Start time of the channel current 15-minute performance statistics."
            ::= { hwOntXdslPMChCurrEntry 35 }
        hwOntXdslPMChCurr1DayStartTime  OBJECT-TYPE
            SYNTAX      DateAndTime
            MAX-ACCESS  read-only
            STATUS      current
            DESCRIPTION
                "Start time of the channel current 1-day performance statistics."
            ::= { hwOntXdslPMChCurrEntry 36 }
          --    PM ont xdsl port channel history 15 Minutes
        hwOntXdslPMChHist15MinTable         OBJECT-TYPE
            SYNTAX      SEQUENCE  OF  HwOntXdslPMChHist15MinEntry
            MAX-ACCESS  not-accessible
            STATUS      current
            DESCRIPTION
                "The table hwOntXdslPMChHist15MinTable contains PM channel history
                 for 15min intervals of XDSL channel.
                 The indexes of this table are ifIndex, hwOntObjectIndex, hwOntUniPhyType,
                 hwOntXdslPortid, hwOntXdslChannelID, the termination unit and the
                 interval number.
                "
            ::= { hwXdslPMChannel 6 }
        hwOntXdslPMChHist15MinEntry  OBJECT-TYPE
            SYNTAX      HwOntXdslPMChHist15MinEntry
            MAX-ACCESS  not-accessible
            STATUS      current
            DESCRIPTION
                "The table hwOntXdslPMChHist15MinTable contains PM channel history
                 for 15min intervals of XDSL channel.
                 The indexes of this entry are ifIndex, hwOntObjectIndex, hwOntUniPhyType,
                 hwOntXdslPortid, hwOntXdslChannelID, the termination unit and the
                 interval number.
                "
            INDEX  { ifIndex,
                     hwOntObjectIndex,
                     hwOntUniPhyType,
         hwOntXdslPortid,
         hwOntXdslChannelID,
                     hwOntXdslPMChHist15MUnit,
                     hwOntXdslPMChHist15MInterval }
            ::= { hwOntXdslPMChHist15MinTable 1 }
        HwOntXdslPMChHist15MinEntry  ::=
            SEQUENCE {
              hwOntXdslPMChHist15MUnit                     HwXdslUnit,
              hwOntXdslPMChHist15MInterval                 Unsigned32,
              hwOntXdslPMChHist15MMonitoredTime            Unsigned32,
              hwOntXdslPMChHist15MCodingViolations         Unsigned32,
              hwOntXdslPMChHist15MCorrectedBlocks          Unsigned32,
              hwOntXdslPMChHist15MValidInterval            TruthValue,
              hwOntXdslPMChHist15MEncodedBlocks            Unsigned32,
              hwOntXdslPMChHist15MUncorrectableBlocks      Unsigned32,
              hwOntXdslPMChHist15MAtmCells                 Counter32,
              hwOntXdslPMChHist15MPtmPackets               Counter32,
              hwOntXdslPMChHist15MRtxCW       Counter32,
              hwOntXdslPMChHist15MRtxCorrectedCW      Counter32,
              hwOntXdslPMChHist15MRtxUncorrectedCW         Counter32,
              hwOntXdslPMChHist15MStartTime                DateAndTime
            }
        hwOntXdslPMChHist15MUnit  OBJECT-TYPE
            SYNTAX      HwXdslUnit
            MAX-ACCESS  not-accessible
            STATUS      current
            DESCRIPTION
                "The termination unit xTU-C(1) or xTU-R(2)."
            ::= { hwOntXdslPMChHist15MinEntry 1 }
        hwOntXdslPMChHist15MInterval  OBJECT-TYPE
            SYNTAX      Unsigned32
            MAX-ACCESS  not-accessible
            STATUS      current
            DESCRIPTION
                "The interval number."
            ::= { hwOntXdslPMChHist15MinEntry 2 }
        hwOntXdslPMChHist15MMonitoredTime  OBJECT-TYPE
            SYNTAX      Unsigned32
            UNITS       "seconds"
            MAX-ACCESS  read-only
            STATUS      current
            DESCRIPTION
                "Total seconds monitored in this interval.
                 Unit: seconds
                "
            ::= { hwOntXdslPMChHist15MinEntry 3 }
        hwOntXdslPMChHist15MCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwOntXdslPMChHist15MinEntry 4 }
        hwOntXdslPMChHist15MCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwOntXdslPMChHist15MinEntry 5 }
        hwOntXdslPMChHist15MValidInterval  OBJECT-TYPE
            SYNTAX      TruthValue
            MAX-ACCESS  read-only
            STATUS      current
            DESCRIPTION
                "This variable indicates if the data for this interval is
                 valid.
                "
            ::= { hwOntXdslPMChHist15MinEntry 6 }

        hwOntXdslPMChHist15MEncodedBlocks  OBJECT-TYPE
            SYNTAX      Unsigned32
            MAX-ACCESS  read-only
            STATUS      current
            DESCRIPTION
                "Count of all encoded blocks received on this
                 channel during the interval.
                "
            ::= { hwOntXdslPMChHist15MinEntry 7 }

        hwOntXdslPMChHist15MUncorrectableBlocks  OBJECT-TYPE
            SYNTAX      Unsigned32
            MAX-ACCESS  read-only
            STATUS      current
            DESCRIPTION
                "Count of all blocks received with uncorrectable
                 errors on this channel during the interval.
                "
            ::= { hwOntXdslPMChHist15MinEntry 8 }

        hwOntXdslPMChHist15MAtmCells  OBJECT-TYPE
            SYNTAX      Counter32
            MAX-ACCESS  read-only
            STATUS      current
            DESCRIPTION
                "Count of Atm Cells received
                 on this channel during the interval.
                 Currently, this leaf is reserved, and it is not supported.
                "
            ::= { hwOntXdslPMChHist15MinEntry 9 }

        hwOntXdslPMChHist15MPtmPackets  OBJECT-TYPE
            SYNTAX      Counter32
            MAX-ACCESS  read-only
            STATUS      current
            DESCRIPTION
                "Count of Ptm Packets received
                 on this channel during the interval.
                 Currently, this leaf is reserved, and it is not supported.
                "
            ::= { hwOntXdslPMChHist15MinEntry 10 }

        hwOntXdslPMChHist15MRtxCW  OBJECT-TYPE
            SYNTAX      Counter32
            MAX-ACCESS  read-only
            STATUS      current
            DESCRIPTION
                "Count of units request retransmission during the
                 serval 15 minute interval of history.
                 Currently, this leaf is reserved, and it is not supported.
                "
            ::= { hwOntXdslPMChHist15MinEntry 11 }

        hwOntXdslPMChHist15MRtxCorrectedCW  OBJECT-TYPE
            SYNTAX      Counter32
            MAX-ACCESS  read-only
            STATUS      current
            DESCRIPTION
                "Count of units corrected by retransmission during the
                 serval 15 minute interval of history.
                 Currently, this leaf is reserved, and it is not supported.
                "
            ::= { hwOntXdslPMChHist15MinEntry 12 }

        hwOntXdslPMChHist15MRtxUncorrectedCW  OBJECT-TYPE
            SYNTAX      Counter32
            MAX-ACCESS  read-only
            STATUS      current
            DESCRIPTION
                "Count of units uncorrected by retransmission during
                 the serval 15 minute interval of history.
                 Currently, this leaf is reserved, and it is not supported.
                "
            ::= { hwOntXdslPMChHist15MinEntry 13 }

        hwOntXdslPMChHist15MStartTime  OBJECT-TYPE
            SYNTAX      DateAndTime
            MAX-ACCESS  read-only
            STATUS      current
            DESCRIPTION
                "Start time of the channel historical 15-minute performance
                 statistics.
                "
            ::= { hwOntXdslPMChHist15MinEntry 14 }

        --        PM ont xdsl port channel history 1 Day
        hwOntXdslPMChHist1DTable         OBJECT-TYPE
            SYNTAX      SEQUENCE  OF  HwOntXdslPMChHist1DEntry
            MAX-ACCESS  not-accessible
            STATUS      current
            DESCRIPTION
                "The table hwOntXdslPMChHist1DTable contains PM channel history
                 for 1 day intervals of XDSL2.
                 The indexes of this table are ifIndex, hwOntObjectIndex, hwOntUniPhyType, hwOntXdslPortid, hwOntXdslChannelID
                 the termination unit and the interval number.
                "
            ::= { hwXdslPMChannel 7 }

        hwOntXdslPMChHist1DEntry  OBJECT-TYPE
            SYNTAX      HwOntXdslPMChHist1DEntry
            MAX-ACCESS  not-accessible
            STATUS      current
            DESCRIPTION
                "The table hwOntXdslPMChHist1DTable contains PM channel history
                 for 1 day intervals of XDSL2.
                 The indexes of this entry are ifIndex, hwOntObjectIndex, hwOntUniPhyType, hwOntXdslPortid, hwOntXdslChannelID
                 the termination unit and the interval number.
                "
            INDEX  { ifIndex,
                     hwOntObjectIndex,
                     hwOntUniPhyType,
                     hwOntXdslPortid,
                     hwOntXdslChannelID,
                     hwOntXdslPMChHist1DUnit,
                     hwOntXdslPMChHist1DInterval }
            ::= { hwOntXdslPMChHist1DTable 1 }

        HwOntXdslPMChHist1DEntry  ::=
            SEQUENCE {
               hwOntXdslPMChHist1DUnit                      HwXdslUnit,
               hwOntXdslPMChHist1DInterval                  Unsigned32,
               hwOntXdslPMChHist1DMonitoredTime             Unsigned32,
               hwOntXdslPMChHist1DCodingViolations          Unsigned32,
               hwOntXdslPMChHist1DCorrectedBlocks           Unsigned32,
               hwOntXdslPMChHist1DValidInterval             TruthValue,
               hwOntXdslPMChHist1DEncodedBlocks             Unsigned32,
               hwOntXdslPMChHist1DUncorrectableBlocks       Unsigned32,
               hwOntXdslPMChHist1DAtmCells                  Counter32,
               hwOntXdslPMChHist1DPtmPackets                Counter32,
               hwOntXdslPMChHist1DRtxCW        Counter32,
               hwOntXdslPMChHist1DRtxCorrectedCW         Counter32,
               hwOntXdslPMChHist1DRtxUncorrectedCW       Counter32,
               hwOntXdslPMChHist1DStartTime                 DateAndTime
            }

        hwOntXdslPMChHist1DUnit  OBJECT-TYPE
            SYNTAX      HwXdslUnit
            MAX-ACCESS  not-accessible
            STATUS      current
            DESCRIPTION
                "The termination unit xTU-C(1) or xTU-R(2)."
             ::= { hwOntXdslPMChHist1DEntry 1 }

        hwOntXdslPMChHist1DInterval  OBJECT-TYPE
            SYNTAX      Unsigned32
            MAX-ACCESS  not-accessible
            STATUS      current
            DESCRIPTION
                "The interval number."
            ::= { hwOntXdslPMChHist1DEntry 2 }

        hwOntXdslPMChHist1DMonitoredTime  OBJECT-TYPE
            SYNTAX      Unsigned32
            UNITS       "seconds"
            MAX-ACCESS  read-only
            STATUS      current
            DESCRIPTION
                "Total seconds monitored in this interval.
                 Unit: seconds
                "
            ::= { hwOntXdslPMChHist1DEntry 3 }

        hwOntXdslPMChHist1DCodingViolations  OBJECT-TYPE
            SYNTAX      Unsigned32
            MAX-ACCESS  read-only
            STATUS      current
            DESCRIPTION
                "Count of CRC-8 (FEBE for xTU-R) anomalies occurring in the
                 channel during the interval.  This parameter is inhibited
                 during UAS or SES.  If the CRC is applied over multiple
                 channels, then each related CRC-8 (or FEBE) anomaly should
                 increment each of the counters related to the individual
                 channels.
                "
            REFERENCE    "ITU-T G.997.1, paragraph 7.2.2"
            ::= { hwOntXdslPMChHist1DEntry 4 }

        hwOntXdslPMChHist1DCorrectedBlocks  OBJECT-TYPE
            SYNTAX      Unsigned32
            MAX-ACCESS  read-only
            STATUS      current
            DESCRIPTION
                "Count of FEC (FFEC for xTU-R) anomalies (corrected code words)
                 occurring in the channel during the interval.  This parameter
                 is inhibited during UAS or SES.  If the FEC is applied over
                 multiple channels, then each related FEC (or FFEC) anomaly
                 should increment each of the counters related to the
                 individual channels.
                "
            REFERENCE    "ITU-T G.997.1, paragraph 7.2.2"
            ::= { hwOntXdslPMChHist1DEntry 5 }

        hwOntXdslPMChHist1DValidInterval  OBJECT-TYPE
            SYNTAX      TruthValue
            MAX-ACCESS  read-only
            STATUS      current
            DESCRIPTION
                "This variable indicates if the data for this interval is
                 valid.
                "
            ::= { hwOntXdslPMChHist1DEntry 6 }

        hwOntXdslPMChHist1DEncodedBlocks  OBJECT-TYPE
            SYNTAX      Unsigned32
            MAX-ACCESS  read-only
            STATUS      current
            DESCRIPTION
                "Count of all encoded blocks received on this
                 channel during the interval.
                "
            ::= { hwOntXdslPMChHist1DEntry 7 }

        hwOntXdslPMChHist1DUncorrectableBlocks  OBJECT-TYPE
            SYNTAX      Unsigned32
            MAX-ACCESS  read-only
            STATUS      current
            DESCRIPTION
                "Count of all blocks received with uncorrectable
                 errors on this channel during the interval."
            ::= { hwOntXdslPMChHist1DEntry 8 }

        hwOntXdslPMChHist1DAtmCells  OBJECT-TYPE
            SYNTAX      Counter32
            MAX-ACCESS  read-only
            STATUS      current
            DESCRIPTION
                "Count of Atm Cells received
                 on this channel during the interval.
                 Currently, this leaf is reserved, and it is not supported.
                "
            ::= { hwOntXdslPMChHist1DEntry 9 }

        hwOntXdslPMChHist1DPtmPackets  OBJECT-TYPE
            SYNTAX      Counter32
            MAX-ACCESS  read-only
            STATUS      current
            DESCRIPTION
                "Count of Ptm Packets received
                 on this channel during the interval.
                 Currently, this leaf is reserved, and it is not supported.
                "
            ::= { hwOntXdslPMChHist1DEntry 10 }

        hwOntXdslPMChHist1DRtxCW  OBJECT-TYPE
            SYNTAX      Counter32
            MAX-ACCESS  read-only
            STATUS      current
            DESCRIPTION
                "Count of units request retransmission within the
                 serval one day interval of history.
                 Currently, this leaf is reserved, and it is not supported.
                "
            ::= { hwOntXdslPMChHist1DEntry 11 }

        hwOntXdslPMChHist1DRtxCorrectedCW  OBJECT-TYPE
            SYNTAX      Counter32
            MAX-ACCESS  read-only
            STATUS      current
            DESCRIPTION
                "Count of units corrected by retransmission during the
                 serval one day interval of history.
                 Currently, this leaf is reserved, and it is not supported.
                "
            ::= { hwOntXdslPMChHist1DEntry 12 }

        hwOntXdslPMChHist1DRtxUncorrectedCW  OBJECT-TYPE
            SYNTAX      Counter32
            MAX-ACCESS  read-only
            STATUS      current
            DESCRIPTION
                "Count of units uncorrected by retransmission during
                 the serval one day interval of history.
                 Currently, this leaf is reserved, and it is not supported.
               "
            ::= { hwOntXdslPMChHist1DEntry 13 }

        hwOntXdslPMChHist1DStartTime  OBJECT-TYPE
            SYNTAX      DateAndTime
            MAX-ACCESS  read-only
            STATUS      current
            DESCRIPTION
                "Start time of the channel historical 1-day performance statistics."
            ::= { hwOntXdslPMChHist1DEntry 14 }

          --          Notifications Group

        hwXdslLinePerfFECSThreshXtuc NOTIFICATION-TYPE
            OBJECTS
            {
            hwXdslPMLCurr15MFecs,
            hwXdslLineAlarmConfProfileXtucThresh15MinFecs
            }
            STATUS     current
            DESCRIPTION
                "This notification indicates that the FEC seconds threshold
                 has been reached/exceeded for the referred xTU-C.
                "
            ::= { hwXdslNotifications 1 }

        hwXdslLinePerfFECSThreshXtur NOTIFICATION-TYPE
            OBJECTS
            {
            hwXdslPMLCurr15MFecs,
            hwXdslLineAlarmConfProfileXturThresh15MinFecs
            }
            STATUS     current
            DESCRIPTION
                "This notification indicates that the FEC seconds threshold
                 has been reached/exceeded for the referred xTU-R.
                "
            ::= { hwXdslNotifications 2 }

        hwXdslLinePerfESThreshXtuc NOTIFICATION-TYPE
            OBJECTS
            {
            hwXdslPMLCurr15MEs,
            hwXdslLineAlarmConfProfileXtucThresh15MinEs
            }
            STATUS     current
            DESCRIPTION
                "This notification indicates that the errored seconds threshold
                 has been reached/exceeded for the referred xTU-C.
                "
            ::= { hwXdslNotifications 3 }

        hwXdslLinePerfESThreshXtur NOTIFICATION-TYPE
            OBJECTS
            {
            hwXdslPMLCurr15MEs,
            hwXdslLineAlarmConfProfileXturThresh15MinEs
            }
            STATUS     current
            DESCRIPTION
                "This notification indicates that the errored seconds threshold
                 has been reached/exceeded for the referred xTU-R.
                "
            ::= { hwXdslNotifications 4 }

        hwXdslLinePerfSESThreshXtuc NOTIFICATION-TYPE
            OBJECTS
            {
            hwXdslPMLCurr15MSes,
            hwXdslLineAlarmConfProfileXtucThresh15MinSes
            }
            STATUS     current
            DESCRIPTION
                "This notification indicates that the severely-errored seconds
                 threshold has been reached/exceeded for the referred xTU-C.
                "
            ::= { hwXdslNotifications 5 }

        hwXdslLinePerfSESThreshXtur NOTIFICATION-TYPE
            OBJECTS
            {
            hwXdslPMLCurr15MSes,
            hwXdslLineAlarmConfProfileXturThresh15MinSes
            }
            STATUS     current
            DESCRIPTION
                "This notification indicates that the severely-errored seconds
                 threshold has been reached/exceeded for the referred xTU-R.
                "
            ::= { hwXdslNotifications 6 }

        hwXdslLinePerfLOSSThreshXtuc NOTIFICATION-TYPE
            OBJECTS
            {
            hwXdslPMLCurr15MLoss,
            hwXdslLineAlarmConfProfileXtucThresh15MinLoss
            }
            STATUS     current
            DESCRIPTION
                "This notification indicates that the LOS seconds
                 threshold has been reached/exceeded for the referred xTU-C.
                "
            ::= { hwXdslNotifications 7 }

        hwXdslLinePerfLOSSThreshXtur NOTIFICATION-TYPE
            OBJECTS
            {
            hwXdslPMLCurr15MLoss,
            hwXdslLineAlarmConfProfileXturThresh15MinLoss
            }
            STATUS     current
            DESCRIPTION
                "This notification indicates that the LOS seconds
                 threshold has been reached/exceeded for the referred xTU-R.
                "
            ::= { hwXdslNotifications 8 }

        hwXdslLinePerfUASThreshXtuc NOTIFICATION-TYPE
            OBJECTS
            {
            hwXdslPMLCurr15MUas,
            hwXdslLineAlarmConfProfileXtucThresh15MinUas
            }
            STATUS     current
            DESCRIPTION
                "This notification indicates that the unavailable seconds
                 threshold has been reached/exceeded for the referred xTU-C.
                "
            ::= { hwXdslNotifications 9 }

        hwXdslLinePerfUASThreshXtur NOTIFICATION-TYPE
            OBJECTS
            {
            hwXdslPMLCurr15MUas,
            hwXdslLineAlarmConfProfileXturThresh15MinUas
            }
            STATUS     current
            DESCRIPTION
                "This notification indicates that the unavailable seconds
                 threshold has been reached/exceeded for the referred xTU-R.
                "
            ::= { hwXdslNotifications 10 }

        hwXdslLinePerfCodingViolationsThreshXtuc NOTIFICATION-TYPE
            OBJECTS
            {
            hwXdslPMChCurr15MCodingViolations,
            hwXdslChAlarmConfProfileXtucThresh15MinCodingViolations
            }
            STATUS     current
            DESCRIPTION
                "This notification indicates that the coding violations
                 threshold has been reached/exceeded for the referred xTU-C.
                "
            ::= { hwXdslNotifications 11 }

        hwXdslLinePerfCodingViolationsThreshXtur NOTIFICATION-TYPE
            OBJECTS
            {
            hwXdslPMChCurr15MCodingViolations,
            hwXdslChAlarmConfProfileXturThresh15MinCodingViolations
            }
            STATUS     current
            DESCRIPTION
                "This notification indicates that the coding violations
                 threshold has been reached/exceeded for the referred xTU-R.
                "
            ::= { hwXdslNotifications 12 }

        hwXdslLinePerfCorrectedThreshXtuc NOTIFICATION-TYPE
            OBJECTS
            {
            hwXdslPMChCurr15MCorrectedBlocks,
            hwXdslChAlarmConfProfileXtucThresh15MinCorrected
            }
            STATUS     current
            DESCRIPTION
                "This notification indicates that the corrected blocks
                 (FEC events) threshold has been reached/exceeded for the
                 referred xTU-C.
                "
            ::= { hwXdslNotifications 13 }

        hwXdslLinePerfCorrectedThreshXtur NOTIFICATION-TYPE
            OBJECTS
            {
            hwXdslPMChCurr15MCorrectedBlocks,
            hwXdslChAlarmConfProfileXturThresh15MinCorrected
            }
            STATUS     current
            DESCRIPTION
                "This notification indicates that the corrected blocks
                 (FEC events) threshold has been reached/exceeded for the
                 referred xTU-R.
                "
            ::= { hwXdslNotifications 14 }

        hwXdslLinePerfFailedFullInitThresh NOTIFICATION-TYPE
            OBJECTS
            {
            hwXdslPMLCurrInit15MFailedFullInits,
            hwXdslLineAlarmConfProfileThresh15MinFailedFullInt
            }
            STATUS     current
            DESCRIPTION
                "This notification indicates that the failed full
                 initializations threshold has been reached/exceeded for the
                 referred XDSL/XDSL2 or XDSL line.
                "
            ::= { hwXdslNotifications 15 }

        hwXdslLinePerfFailedShortInitThresh NOTIFICATION-TYPE
            OBJECTS
            {
            hwXdslPMLCurrInit15MFailedShortInits,
            hwXdslLineAlarmConfProfileThresh15MinFailedShrtInt
            }
            STATUS     current
            DESCRIPTION
                "This notification indicates that the failed short
                 initializations threshold has been reached/exceeded for the
                 referred XDSL or XDSL line.
                "
            ::= { hwXdslNotifications 16 }

        hwXdslLineStatusChangeXtuc NOTIFICATION-TYPE
            OBJECTS
            {
            hwXdslLineStatusXtuc
            }
            STATUS     current
            DESCRIPTION
                "This notification indicates that a status change is
                 detected for the referred xTU-C.
                "
            ::= { hwXdslNotifications 17 }

        hwXdslLineStatusChangeXtur NOTIFICATION-TYPE
            OBJECTS
            {
            hwXdslLineStatusXtur
            }
            STATUS     current
            DESCRIPTION
                "This notification indicates that a status change is
                 detected for the referred xTU-R.
                "
            ::= { hwXdslNotifications 18 }


        hwXdslLinePerfFullInitThresh NOTIFICATION-TYPE
            OBJECTS
            {
            hwXdslPMLCurrInit15MFullInits,
            hwXdslLineAlarmConfProfileThresh15MinFullInt
            }
            STATUS     current
            DESCRIPTION
                "This notification indicates that the full
                 initializations threshold has been reached/exceeded for the
                 referred XDSL/XDSL2 or XDSL line.
                "
            ::= { hwXdslNotifications 19 }

            -- conformance information

            hwXdslGroups OBJECT IDENTIFIER ::= { hwXdslConformance 1 }
            hwXdslCompliances OBJECT IDENTIFIER ::= { hwXdslConformance 2 }

        hwXdslLineMibCompliance MODULE-COMPLIANCE
            STATUS  current
            DESCRIPTION
                "The compliance statement for SNMP entities which
                 manage XDSL interfaces.
                "
            MODULE  -- this module
            MANDATORY-GROUPS
                {
                hwXdslLineGroup,
                hwXdslChannelStatusGroup,
                hwXdslPrivSCStatusGroup,
                hwXdslDeltGroup,
                hwXdslLineInventoryGroup,
                hwVdslLineConfTemplateGroup,
                hwVdslLineConfProfGroup,
                hwVdslLineConfProfModeSpecGroup,
                hwVdslChConfProfileGroup,
                hwXdslLineAlarmConfTemplateGroup,
                hwXdslPMLineCurrGroup,
                hwXdslPMLineCurrInitGroup,
                hwXdslPMLineHist15MinGroup,
                hwXdslPMLineHist1DayGroup,
                hwXdslPMLineInitHist15MinGroup,
                hwXdslPMLineInitHist1DayGroup,
                hwXdslPMChCurrGroup,
                hwXdslPMChHist15MinGroup,
                hwXdslPMChHist1DGroup
                }

        GROUP  hwXdslChannelStatusAtmGroup
            DESCRIPTION
                "The group of status objects required when the data path
              is ATM."

        GROUP  hwXdslChannelStatusPtmGroup
            DESCRIPTION
                "The group of status objects required when the data path
               is PTM."

        GROUP  hwVdslLineConfProfRaGroup
            DESCRIPTION
                "The group of objects required for controlling the rate
               adaptive behavior of the line."

        GROUP  hwVdslLineConfProfMsgMinGroup
            DESCRIPTION
                "The group of objects required for controlling the rate
               reserved for Overhead traffic."

        GROUP  hwXdslLineAlarmConfProfileGroup
            DESCRIPTION
                "The group of objects that define the alarm thresholds
               on line level PM counters."

        GROUP  hwXdslChAlarmConfProfileGroup
            DESCRIPTION
                "The group of objects that define the alarm thresholds
               on channel level PM counters."

        GROUP  hwVdslChConfProfileAtmGroup
            DESCRIPTION
                "The group of configuration objects required when the data
               path is ATM."

        GROUP  hwVdslChConfProfileMinResGroup
            DESCRIPTION
                "The group of configuration objects required for the
               reserved data rate."

        GROUP  hwXdslPMLineCurrInitShortGroup
            DESCRIPTION
                "The group of PM counters for the current intervals
               short initializations."

        GROUP  hwXdslPMLineInitHist15MinShortGroup
            DESCRIPTION
                "The group of PM counters for the previous 15 minutes
               intervals short initializations."

        GROUP  hwXdslPMLineInitHist1DayShortGroup
            DESCRIPTION
                "The group of PM counters for the previous 24 hours
               intervals short initializations."

        GROUP  hwXdslScalarDeltGroup
            DESCRIPTION
                "The group of objects that report the available memory
               resources for DELT processes."

        GROUP  hwXdslThreshNotificationGroup
            DESCRIPTION
                "The group of thresholds crossing notifications."

        GROUP  hwXdslStatusChangeNotificationGroup
            DESCRIPTION
               "The group of status change notifications."

            ::= { hwXdslCompliances 1 }

        hwXdslLineGroup OBJECT-GROUP
            OBJECTS
                {
                hwXdslLineCnfgTemplate,
                hwXdslLineAlarmCnfgTemplate,
                hwXdslLineCmndConfPmsf,
                hwXdslLineCmndConfLdsf,
                hwXdslLineCmndConfLdsfFailReason,
                hwXdslLineCmndAutomodeColdStart,
                hwXdslLineStatusXtuTransSys,
                hwXdslLineStatusPwrMngState,
                hwXdslLineStatusInitResult,
                hwXdslLineStatusLastStateDs,
                hwXdslLineStatusLastStateUs,
                hwXdslLineStatusXtur,
                hwXdslLineStatusXtuc,
                hwXdslLineStatusLnAttenDs,
                hwXdslLineStatusLnAttenUs,
                hwXdslLineStatusSigAttenDs,
                hwXdslLineStatusSigAttenUs,
                hwXdslLineStatusSnrMarginDs,
                hwXdslLineStatusSnrMarginUs,
                hwXdslLineStatusAttainableRateDs,
                hwXdslLineStatusAttainableRateUs,
                hwXdslLineStatusActPsdDs,
                hwXdslLineStatusActPsdUs,
                hwXdslLineStatusActAtpDs,
                hwXdslLineStatusActAtpUs,
                hwXdslLineBandPlan,
                hwXdslLinePsdMaskClassSelection,
                hwXdslLineCnfgServiceProf,
                hwXdslLineCnfgSpectrumProf,
                hwXdslLineCnfgDpboProf,
                hwXdslLineCnfgUpboProf,
                hwXdslLineCnfgNoiseMarginProf,
                hwXdslLineCnfgDelayINPProf,
                hwXdslUpboProfKl0CpeVal,
                hwXdslLineStatusCodingGainUs,
                hwXdslLineStatusCodingGainDs,
                hwXdslLineStatusPcbDs,
                hwxdslDlmDsmprofile,
                hwXdslLineActmode,
                hwXdslUpboProfKl0CoVal,
                hwXdslUpboRxThreshDs,
                hwXdslUpboRxThreshUs,
                hwXdslLineStatusLineRateDs,
                hwXdslLineStatusLineRateUs,
                hwXdslLineSplitterMode,
                hwXdslLineBackup,
                hwXdslLineBackupPort
                }
            STATUS     current
            DESCRIPTION
                "The group of configuration, status, and commands objects
                 on the line level.
                "
            ::= { hwXdslGroups 1 }

        hwXdslChannelStatusGroup OBJECT-GROUP
            OBJECTS
                {
                hwXdslChStatusChannelNum,
                hwXdslChStatusActDataRate,
                hwXdslChStatusPrevDataRate,
                hwXdslChStatusActDelay
                }
            STATUS     current
            DESCRIPTION
                "The group of status objects on the channel level."
            ::= { hwXdslGroups 2 }

        hwXdslChannelStatusAtmGroup OBJECT-GROUP
            OBJECTS
                {
                hwXdslChStatusAtmStatus
                }
            STATUS     current
            DESCRIPTION
                "The group of status objects on the data path level
                 when it is ATM."
            ::= { hwXdslGroups 3 }

        hwXdslChannelStatusPtmGroup OBJECT-GROUP
            OBJECTS
                {
                hwXdslChStatusPtmStatus
                }
            STATUS     current
            DESCRIPTION
                "The group of status objects on the data path level
                 when it is PTM."
            ::= { hwXdslGroups 4 }

        hwXdslPrivSCStatusGroup OBJECT-GROUP
            OBJECTS
                {
                hwXdslPrivSCStatusMtime,
                hwXdslPrivSCStatusSnr,
                hwXdslPrivSCStatusBitsAlloc,
                hwXdslPrivSCStatusGainAlloc
                }
            STATUS     current
            DESCRIPTION
                "The group of status objects on the sub-carrier level.
                 They are updated as a result of a DELT process."
            ::= { hwXdslGroups 5 }

        hwXdslDeltGroup OBJECT-GROUP
            OBJECTS
                {
                hwXdslSCStatusLinScale,
                hwXdslSCStatusLogMt,
                hwXdslSCStatusQlnMt,
                hwXdslSCStatusAttainableRate,
                hwXdslSCStatusActAtp,
                hwXdslSCStatusRowStatus
                }
            STATUS     current
            DESCRIPTION
                "The group of status objects on the sub-carrier level.
                 They are updated as a result of a DELT process."
            ::= { hwXdslGroups 6 }
        hwXdslLineInventoryGroup OBJECT-GROUP
            OBJECTS
                {
                hwXdslLInvG994VendorId,
                hwXdslLInvSystemVendorId,
                hwXdslLInvVersionNumber,
                hwXdslLInvSerialNumber,
                hwXdslLInvSelfTestResult,
                hwXdslLInvTransmissionCapabilities,
                hwXdslLInvModelId
                }
            STATUS     current
            DESCRIPTION
                "The group of inventory objects per xTU."
            ::= { hwXdslGroups 7 }

        hwVdslLineConfTemplateGroup OBJECT-GROUP
            OBJECTS
                {
                hwVdslLConfTempLineProfile,
                hwVdslLConfTempChan1ConfProfile,
                hwVdslLConfTempChan1RaRatioDs,
                hwVdslLConfTempChan1RaRatioUs,
                hwVdslLConfTempChan2ConfProfile,
                hwVdslLConfTempChan2RaRatioDs,
                hwVdslLConfTempChan2RaRatioUs,
                hwVdslLConfTempChan3ConfProfile,
                hwVdslLConfTempChan3RaRatioDs,
                hwVdslLConfTempChan3RaRatioUs,
                hwVdslLConfTempChan4ConfProfile,
                hwVdslLConfTempChan4RaRatioDs,
                hwVdslLConfTempChan4RaRatioUs,
                hwVdslLConfTempRowStatus
                }
            STATUS     current
            DESCRIPTION
                "The group of objects in a line configuration template."
            ::= { hwXdslGroups 8 }

        hwVdslLineConfProfGroup OBJECT-GROUP
            OBJECTS
                {
                hwVdslLConfProfScMaskDs,
                hwVdslLConfProfScMaskUs,
                hwVdslLConfProfRfiBands,
                hwVdslLConfProfVDSLtoneblackout,
                hwVdslLConfProfRaModeDs,
                hwVdslLConfProfRaModeUs,
                hwVdslLConfProfTargetSnrmDs,
                hwVdslLConfProfTargetSnrmUs,
                hwVdslLConfProfMaxSnrmDs,
                hwVdslLConfProfMaxSnrmUs,
                hwVdslLConfProfMinSnrmDs,
                hwVdslLConfProfMinSnrmUs,
                hwVdslLConfProfXtuTransSysEna,
                hwVdslLConfProfPmMode,
                hwVdslLConfProfL0Time,
                hwVdslLConfProfL2Time,
                hwVdslLConfProfL2Atpr,
                hwVdslLConfProfL2Atprt,
                hwVdslLConfProfDpboEpsd,
                hwVdslLConfProfDpboEsel,
                hwVdslLConfProfDpboEscm,
                hwVdslLConfProfDpboMus,
                hwVdslLConfProfDpboFmin,
                hwVdslLConfProfDpboFmax,
                hwVdslLConfProfUpboPsdBand,
                hwVdslLConfProfUpboKl,
                hwVdslLConfProfUpboKlf,
                hwVdslLConfProfBitSwapDs,
                hwVdslLConfProfBitSwapUs,
                hwVdslLConfProfRowStatus
                }
            STATUS     current
            DESCRIPTION
                "The group of objects in a line configuration profile."
            ::= { hwXdslGroups 9 }

        hwVdslLineConfProfRaGroup OBJECT-GROUP
            OBJECTS
                {
                hwVdslLConfProfRaUsNrmDs,
                hwVdslLConfProfRaUsNrmUs,
                hwVdslLConfProfRaUsTimeDs,
                hwVdslLConfProfRaUsTimeUs,
                hwVdslLConfProfRaDsNrmsDs,
                hwVdslLConfProfRaDsNrmsUs,
                hwVdslLConfProfRaDsTimeDs,
                hwVdslLConfProfRaDsTimeUs
                }
            STATUS     current
            DESCRIPTION
              "The group of objects required for controlling the rate
               adaptive behavior of the line."
            ::= { hwXdslGroups 10 }

        hwVdslLineConfProfMsgMinGroup OBJECT-GROUP
            OBJECTS
                {
                hwVdslLConfProfMsgMinUs,
                hwVdslLConfProfMsgMinDs
                }
            STATUS     current
            DESCRIPTION
                "The group of objects required for controlling the rate
                 reserved for Overhead traffic.
                "
            ::= { hwXdslGroups 11 }

        hwVdslLineConfProfModeSpecGroup OBJECT-GROUP
            OBJECTS
                {
                hwVdslLConfProfMaxNomPsdDs,
                hwVdslLConfProfMaxNomPsdUs,
                hwVdslLConfProfMaxNomAtpDs,
                hwVdslLConfProfMaxNomAtpUs,
                hwVdslLConfProfMaxAggRxPwrUs,
                hwVdslLConfProfPsdMaskDs,
                hwVdslLConfProfPsdMaskUs,
                hwVdslLConfProfPsdMaskSelectUs,
                hwVdslLConfProfModeSpecRowStatus,
                hwVdslConfProfVirtualNoiseModeDs,
                hwVdslConfProfVirtualNoiseModeUs,
                hwVdslConfProfVirtualNoiseDs,
                hwVdslConfProfVirtualNoiseUs,
                hwVdslConfProfAutoProfile
                }
            STATUS     current
            DESCRIPTION
                "The group of objects in a line configuration profile
                 that have an instance for each operation mode allowed.
                "
            ::= { hwXdslGroups 12 }

        hwVdslChConfProfileGroup OBJECT-GROUP
            OBJECTS
                {
                hwVdslChConfProfMinDataRateDs,
                hwVdslChConfProfMinDataRateUs,
                hwVdslChConfProfMaxDataRateDs,
                hwVdslChConfProfMaxDataRateUs,
                hwVdslChConfProfMinDataRateLowPwrDs,
                hwVdslChConfProfMinDataRateLowPwrUs,
                hwVdslChConfProfMaxDelayDs,
                hwVdslChConfProfMaxDelayUs,
                hwVdslChConfProfMinProtectionDs,
                hwVdslChConfProfMinProtectionUs,
                hwVdslChConfProfMaxBerDs,
                hwVdslChConfProfMaxBerUs,
                hwVdslChConfProfUsDataRateDs,
                hwVdslChConfProfDsDataRateDs,
                hwVdslChConfProfUsDataRateUs,
                hwVdslChConfProfDsDataRateUs,
                hwVdslChConfProfRowStatus,
                hwVdslChConfProfPhyRcontrolDs,
                hwVdslChConfProfPhyRcontrolUs,
                hwVdslChConfProfInpMaxDs,
                hwVdslChConfProfInpMaxUs,
                hwVdslChConfProfMinRtxRatioDs,
                hwVdslChConfProfMinRtxRatioUs,
                hwVdslChConfProfMinRSoverheadDs,
                hwVdslChConfProfMinRSoverheadUs,
                hwVdslChConfProfErasureDecoding,
                hwVdslChConfProfMinSosBrDs,
                hwVdslChConfProfMinSosBrUs       ,
                hwVdslChConfProfMinEtrRtxDs      ,
                hwVdslChConfProfMinEtrRtxUs      ,
                hwVdslChConfProfMaxEtrRtxDs      ,
                hwVdslChConfProfMaxEtrRtxUs      ,
                hwVdslChConfProfMaxNdrRtxDs      ,
                hwVdslChConfProfMaxNdrRtxUs      ,
                hwVdslChConfProfMaxDelayRtxDs    ,
                hwVdslChConfProfMaxDelayRtxUs    ,
                hwVdslChConfProfMinDelayRtxDs    ,
                hwVdslChConfProfMinDelayRtxUs    ,
                hwVdslChConfProfMinInpShineRtxDs ,
                hwVdslChConfProfMinInpShineRtxUs ,
                hwVdslChConfProfMinInp8ShineRtxDs,
                hwVdslChConfProfMinInp8ShineRtxUs,
                hwVdslChConfProfShineRatioRtxDs  ,
                hwVdslChConfProfShineRatioRtxUs  ,
                hwVdslChConfProfMinInpReinRtxDs  ,
                hwVdslChConfProfMinInpReinRtxUs  ,
                hwVdslChConfProfMinInp8ReinRtxDs ,
                hwVdslChConfProfMinInp8ReinRtxUs ,
                hwVdslChConfProfIatReinRtxDs     ,
                hwVdslChConfProfIatReinRtxUs
                }
            STATUS     current
            DESCRIPTION
                "The group of objects in a channel configuration profile."
            ::= { hwXdslGroups 13 }

        hwVdslChConfProfileAtmGroup OBJECT-GROUP
            OBJECTS
                {
                hwVdslChConfProfImaEnabled,
                hwXdslChStatusAtmStatus
                }

            STATUS     current
            DESCRIPTION
                "The group of configuration objects required when the data
                 path is ATM.
                "
            ::= { hwXdslGroups 14 }

        hwVdslChConfProfileMinResGroup OBJECT-GROUP
            OBJECTS
                {
                hwVdslChConfProfMinResDataRateDs,
                hwVdslChConfProfMinResDataRateUs
                }
            STATUS     current
            DESCRIPTION
                "The group of configuration objects required for the
                 reserved data rate.
                "
            ::= { hwXdslGroups 15 }

        hwXdslLineAlarmConfTemplateGroup OBJECT-GROUP
            OBJECTS
                {
                hwXdslLAlarmConfTempLineProfile,
                hwXdslLAlarmConfTempChan1ConfProfile,
                hwXdslLAlarmConfTempChan2ConfProfile,
                hwXdslLAlarmConfTempChan3ConfProfile,
                hwXdslLAlarmConfTempChan4ConfProfile,
                hwXdslLAlarmConfTempRowStatus
                }
            STATUS     current
            DESCRIPTION
                "The group of objects in a line alarm
                 template.
                "
            ::= { hwXdslGroups 16 }

        hwXdslLineAlarmConfProfileGroup OBJECT-GROUP
            OBJECTS
                {
                hwXdslLineAlarmConfProfileXtucThresh15MinFecs,
                hwXdslLineAlarmConfProfileXtucThresh15MinEs,
                hwXdslLineAlarmConfProfileXtucThresh15MinSes,
                hwXdslLineAlarmConfProfileXtucThresh15MinLoss,
                hwXdslLineAlarmConfProfileXtucThresh15MinUas,
                hwXdslLineAlarmConfProfileXturThresh15MinFecs,
                hwXdslLineAlarmConfProfileXturThresh15MinEs,
                hwXdslLineAlarmConfProfileXturThresh15MinSes,
                hwXdslLineAlarmConfProfileXturThresh15MinLoss,
                hwXdslLineAlarmConfProfileXturThresh15MinUas,
                hwXdslLineAlarmConfProfileThresh15MinFailedFullInt,
                hwXdslLineAlarmConfProfileThresh15MinFailedShrtInt,
                hwXdslLineAlarmConfProfileRowStatus,
                hwXdslLineAlarmConfProfileThresh15MinFullInt,
                hwXdslLineAlarmConfProfileXtucThresh15MinLeftrs,
                hwXdslLineAlarmConfProfileXturThresh15MinLeftrs
                }
            STATUS     current
            DESCRIPTION
                "The group of objects in a line alarm profile."
            ::= { hwXdslGroups 17 }

        hwXdslChAlarmConfProfileGroup OBJECT-GROUP
            OBJECTS
                {
                hwXdslChAlarmConfProfileXtucThresh15MinCodingViolations,
                hwXdslChAlarmConfProfileXtucThresh15MinCorrected,
                hwXdslChAlarmConfProfileXturThresh15MinCodingViolations,
                hwXdslChAlarmConfProfileXturThresh15MinCorrected,
                hwXdslChAlarmConfProfileMonitoringRateDs,
                hwXdslChAlarmConfProfileMonitoringRateUs,
                hwXdslChAlarmConfProfileRowStatus
                }
            STATUS     current
            DESCRIPTION
                "The group of objects in a channel alarm profile."
            ::= { hwXdslGroups 18 }

        hwXdslPMLineCurrGroup OBJECT-GROUP
            OBJECTS
                {
                hwXdslPMLCurrValidIntervals,
                hwXdslPMLCurrInvalidIntervals,
                hwXdslPMLCurr15MTimeElapsed,
                hwXdslPMLCurr15MFecs,
                hwXdslPMLCurr15MEs,
                hwXdslPMLCurr15MSes,
                hwXdslPMLCurr15MLoss,
                hwXdslPMLCurr15MUas,
                hwXdslPMLCurr1DayValidIntervals,
                hwXdslPMLCurr1DayInvalidIntervals,
                hwXdslPMLCurr1DayTimeElapsed,
                hwXdslPMLCurr1DayFecs,
                hwXdslPMLCurr1DayEs,
                hwXdslPMLCurr1DaySes,
                hwXdslPMLCurr1DayLoss,
                hwXdslPMLCurr1DayUas,
                hwXdslPMLEverBeforeFecs,
                hwXdslPMLEverBeforeEs,
                hwXdslPMLEverBeforeSes,
                hwXdslPMLEverBeforeLoss,
                hwXdslPMLEverBeforeUas
                }
            STATUS     current
            DESCRIPTION
                "The group of objects that report the line level
                 counters for current PM intervals.
                "
            ::= { hwXdslGroups 19 }

        hwXdslPMLineCurrInitGroup OBJECT-GROUP
            OBJECTS
                {
                hwXdslPMLCurrInit15MTimeElapsed,
                hwXdslPMLCurrInit15MFullInits,
                hwXdslPMLCurrInit15MFailedFullInits,
                hwXdslPMLCurrInit1DayTimeElapsed,
                hwXdslPMLCurrInit1DayFullInits,
                hwXdslPMLCurrInit1DayFailedFullInits,
                hwXdslPMLInitEverBeforeFullInits,
                hwXdslPMLInitEverBeforeFailedFullInits
                }
            STATUS     current
            DESCRIPTION
                "The group of objects that report the full
                 initializations counters for current PM intervals.
                "
            ::= { hwXdslGroups 20 }

        hwXdslPMLineCurrInitShortGroup OBJECT-GROUP
            OBJECTS
                {
                hwXdslPMLCurrInit15MShortInits,
                hwXdslPMLCurrInit15MFailedShortInits,
                hwXdslPMLCurrInit1DayShortInits,
                hwXdslPMLCurrInit1DayFailedShortInits,
                hwXdslPMLInitEverBeforeShortInits,
                hwXdslPMLInitEverBeforeFailedShortInits
                }
            STATUS     current
            DESCRIPTION
                "The group of objects that report the short
                 initializations counters for current PM intervals.
                "
            ::= { hwXdslGroups 21 }

        hwXdslPMLineHist15MinGroup OBJECT-GROUP
            OBJECTS
                {
                hwXdslPMLHist15MMonitoredTime,
                hwXdslPMLHist15MFecs,
                hwXdslPMLHist15MEs,
                hwXdslPMLHist15MSes,
                hwXdslPMLHist15MLoss,
                hwXdslPMLHist15MUas,
                hwXdslPMLHist15MValidInterval
                }
            STATUS     current
            DESCRIPTION
                "The group of line level PM counters for the previous
                 15 minutes intervals.
                "
            ::= { hwXdslGroups 22 }

        hwXdslPMLineHist1DayGroup OBJECT-GROUP
            OBJECTS
                {
                hwXdslPMLHist1DMonitoredTime,
                hwXdslPMLHist1DFecs,
                hwXdslPMLHist1DEs,
                hwXdslPMLHist1DSes,
                hwXdslPMLHist1DLoss,
                hwXdslPMLHist1DUas,
                hwXdslPMLHist1DValidInterval
                }
            STATUS     current
            DESCRIPTION
                "The group of line level PM counters for the previous
                 24 hours intervals.
                "
            ::= { hwXdslGroups 23 }

        hwXdslPMLineInitHist15MinGroup OBJECT-GROUP
            OBJECTS
                {
                hwXdslPMLHistInit15MMonitoredTime,
                hwXdslPMLHistInit15MFullInits,
                hwXdslPMLHistInit15MFailedFullInits,
                hwXdslPMLHistInit15MValidInterval
                }
            STATUS     current
            DESCRIPTION
                "The group of PM counters for the previous 15 minutes
                 intervals full initializations.
                "
            ::= { hwXdslGroups 24 }

        hwXdslPMLineInitHist15MinShortGroup OBJECT-GROUP
            OBJECTS
                {
                hwXdslPMLHistInit15MShortInits,
                hwXdslPMLHistInit15MFailedShortInits
                }
            STATUS     current
            DESCRIPTION
                "The group of PM counters for the previous 15 minutes
                 intervals short initializations.
                "
            ::= { hwXdslGroups 25 }

        hwXdslPMLineInitHist1DayGroup OBJECT-GROUP
            OBJECTS
                {
                hwXdslPMLHistinit1DMonitoredTime,
                hwXdslPMLHistinit1DFullInits,
                hwXdslPMLHistinit1DFailedFullInits,
                hwXdslPMLHistinit1DValidInterval
                }
            STATUS     current
            DESCRIPTION
                "The group of PM counters for the previous 24 hours
                 intervals full initializations.
                "
            ::= { hwXdslGroups 26 }

        hwXdslPMLineInitHist1DayShortGroup OBJECT-GROUP
            OBJECTS
                {
                hwXdslPMLHistinit1DShortInits,
                hwXdslPMLHistinit1DFailedShortInits
                }
            STATUS     current
            DESCRIPTION
                "The group of PM counters for the previous 24 hours
                 intervals short initializations.
                "
            ::= { hwXdslGroups 27 }

        hwXdslPMChCurrGroup OBJECT-GROUP
            OBJECTS
                {
                hwXdslPMChCurrValidIntervals,
                hwXdslPMChCurrInvalidIntervals,
                hwXdslPMChCurr15MTimeElapsed,
                hwXdslPMChCurr15MCodingViolations,
                hwXdslPMChCurr15MCorrectedBlocks,
                hwXdslPMChCurr1DayValidIntervals,
                hwXdslPMChCurr1DayInvalidIntervals,
                hwXdslPMChCurr1DayTimeElapsed,
                hwXdslPMChCurr1DayCodingViolations,
                hwXdslPMChCurr1DayCorrectedBlocks,
                hwXdslPMChEverBeforeCodingViolations,
                hwXdslPMChEverBeforeCorrectedBlocks
                }
            STATUS     current
            DESCRIPTION
                "The group of objects that report the channel level
                 counters for current PM intervals.
                "
            ::= { hwXdslGroups 28 }

        hwXdslPMChHist15MinGroup OBJECT-GROUP
            OBJECTS
                {
                hwXdslPMChHist15MMonitoredTime,
                hwXdslPMChHist15MCodingViolations,
                hwXdslPMChHist15MCorrectedBlocks,
                hwXdslPMChHist15MValidInterval
                }
            STATUS     current
            DESCRIPTION
                "The group of objects that report the channel level
                 counters for previous 15 minutes PM intervals.
                "
            ::= { hwXdslGroups 29 }

        hwXdslPMChHist1DGroup OBJECT-GROUP
            OBJECTS
                {
                hwXdslPMChHist1DMonitoredTime,
                hwXdslPMChHist1DCodingViolations,
                hwXdslPMChHist1DCorrectedBlocks,
                hwXdslPMChHist1DValidInterval
                }
            STATUS     current
            DESCRIPTION
                "The group of objects that report the channel level
                 counters for previous 24 hours PM intervals.
                "
            ::= { hwXdslGroups 30 }

        hwXdslScalarDeltGroup OBJECT-GROUP
            OBJECTS
                {
                hwXdslScalarSCMaxInterfaces,
                hwXdslScalarSCAvailInterfaces
                }
            STATUS     current
            DESCRIPTION
                "The group of objects that report the available memory
                 resources for DELT processes.
                "
            ::= { hwXdslGroups 31 }

        hwXdslThreshNotificationGroup NOTIFICATION-GROUP
            NOTIFICATIONS
            {
            hwXdslLinePerfFECSThreshXtuc,
            hwXdslLinePerfFECSThreshXtur,
            hwXdslLinePerfESThreshXtuc,
            hwXdslLinePerfESThreshXtur,
            hwXdslLinePerfSESThreshXtuc,
            hwXdslLinePerfSESThreshXtur,
            hwXdslLinePerfLOSSThreshXtuc,
            hwXdslLinePerfLOSSThreshXtur,
            hwXdslLinePerfUASThreshXtuc,
            hwXdslLinePerfUASThreshXtur,
            hwXdslLinePerfCodingViolationsThreshXtuc,
            hwXdslLinePerfCodingViolationsThreshXtur,
            hwXdslLinePerfCorrectedThreshXtuc,
            hwXdslLinePerfCorrectedThreshXtur,
            hwXdslLinePerfFailedFullInitThresh,
            hwXdslLinePerfFailedShortInitThresh,
            hwXdslLinePerfFullInitThresh
            }
            STATUS      current
            DESCRIPTION
                "This notification indicates alarm when this group supports notifications
                 of significant conditions associated with XDSL2 lines.
                "
            ::= { hwXdslGroups 32 }

        hwXdslStatusChangeNotificationGroup NOTIFICATION-GROUP
            NOTIFICATIONS
            {
            hwXdslLineStatusChangeXtuc,
            hwXdslLineStatusChangeXtur
            }
            STATUS      current
            DESCRIPTION
                "This notification indicates alarm when this group supports notifications
                 of thresholds crossing associated with XDSL2 lines.
                "
            ::= { hwXdslGroups 33 }


             -- mode information

        hwVdslmodecfg  OBJECT-TYPE
            SYNTAX  HwVdslCfgMode
            MAX-ACCESS  read-write
            STATUS  current
            DESCRIPTION
                "This object is used to change VDSL management mode.
                 After the mode being changed, system will automatically
                 save data and reboot.
                "
            ::= { hwXdslMode 1 }

        hwGfastModeCfg  OBJECT-TYPE
            SYNTAX  INTEGER
                    {
                      tr165Mode(1),
                      tr129Mode(2)
                    }
            MAX-ACCESS  read-write
            STATUS  current
            DESCRIPTION
                "This object is used to change G.fast management mode.
                 After the mode being changed, system will automatically
                 save data and reboot.
                 This object is defaulted tr165Mode(1).
                 Options:
                 1. tr165Mode(1)     - G.Fast TR165 management mode
                 2. tr129Mode(2)     - G.Fast TR129 management mode
                "
            ::= { hwXdslMode 2 }

        -- XDSL DPBO ESEL

        hwXdslDpboEselGlobalConfigSwitch   OBJECT-TYPE
            SYNTAX INTEGER
            {
            enabled(1),
            disabled(2)
            }
            MAX-ACCESS  read-write
            STATUS      current
            DESCRIPTION
                "Enable/Disable XDSL port DPBOESEL shall Feature.
                 This object is defaulted disabled(2).
                 Options:
                 1. enabled(1)  - enabled the switch
                 2. disabled(2) - disabled the switch
                "

            ::= { hwXdslGlobalConfig 1 }

        hwXdslDpboEselGlobalConfigValue  OBJECT-TYPE
            SYNTAX      Unsigned32 (0..511)
            UNITS       "0.5dB"
            MAX-ACCESS  read-write
            STATUS      current
            DESCRIPTION
                "This configuration parameter defines the assumed electrical length of
                  cables (E-side cables) connecting exchange based DSL services to a remote
                  flexibility point (cabinet), that hosts the xTU-C that is subject to
                  spectrally shaped downstream power back-off depending on this length.
                  For this parameter the electrical length is defined as the loss (in dB)
                  of an equivalent length of hypothetical cable at a reference frequency
                  defined by the network operator or in spectrum management regulations.
                  DPBOESEL shall be coded as an unsigned integer representing an electrical
                  length from 0 dB (coded as 0) to 255.5 dB (coded as 511) in steps of 0.5 dB.
                  All values in the range are valid.If DPBOESEL is set to zero, the DPBO in
                  this section shall be disabled. This object is defaulted 84.
                  Unit: 0.5dB
                 "
            REFERENCE    "ITU-T G.997.1(200604), paragraph 7.3.1.2.13"

            ::= { hwXdslGlobalConfig 2 }

        hwXdslProfileAutoNegotiationSwitch   OBJECT-TYPE
            SYNTAX INTEGER
            {
            enabled(1),
            disabled(2)
            }
            MAX-ACCESS  read-write
            STATUS      current
            DESCRIPTION
                "Enable/Disable the VDSL2 G993.2 profile auto-negotiation function.
                 Default values:disabled(2).
                 Options:
                 1. enabled(1)  - enabled the switch
                 2. disabled(2) - disabled the switch
                "
            ::= { hwXdslGlobalConfig 3  }

        hwXdslMaximumInterleavedDepth   OBJECT-TYPE
            SYNTAX INTEGER
            {
            maxInterleavedDepth64(1),
            maxInterleavedDepth511(2)
            }
            MAX-ACCESS  read-write
            STATUS      current
            DESCRIPTION
                "Set the XDSL maximum interleaved depth function.
                 Default values:maxInterleavedDepth511(2).
                 Options:
                 1. maxInterleavedDepth64(1)  - it means the interleaving depth up to 64 can be selected
                 2. maxInterleavedDepth511(2) - it means the interleaving depth up to 512 can be selected
                "
            ::= { hwXdslGlobalConfig 4  }

        hwXdslGlobalConfigRfiNotchSwitch   OBJECT-TYPE
            SYNTAX INTEGER
            {
            enabled(1),
            disabled(2)
            }
            MAX-ACCESS  read-write
            STATUS      current
            DESCRIPTION
                "Enable/Disable the global RFI notch function.
                 Default values:disabled(2).
                 Options:
                 1. enabled(1)  - enabled the switch
                 2. disabled(2) - disabled the switch
                "
            ::= { hwXdslGlobalConfig 5  }

        hwXdslGlobalConfigGfastRfiNotchBands OBJECT-TYPE
            SYNTAX Xdsl2RfiBands
            MAX-ACCESS read-write
            STATUS current
            DESCRIPTION
                "This configuration parameter defines the bands where the PSD shall be reduced as specified in ITU-T G.9701 #7.3.1.2.
                 Each band shall be represented by a start and stop subcarrier indices with a subcarrier spacing of 51.75 kHz.
                 Up to 16 bands may be specified.
                 This parameter defines the RFI bands for both upstream and downstream directions.
                 Default value: No RFI bands.
                "
            REFERENCE
                "ITU-T G.9701, paragraph 7.3.1.2 and 12.3.2.1.1"
            ::= { hwXdslGlobalConfig 6  }

        hwXdslGlobalConfigGfastIarNotchBands OBJECT-TYPE
            SYNTAX HWVOPGfastIarBands
            MAX-ACCESS read-write
            STATUS current
            DESCRIPTION
                "Defines for each International Amateur Radio (IAR) band whether transmit PSD reduction is enabled or disabled in that band.
                 It is represented as a bitmap (0 if not allowed and 1 if allowed)with the following definitions.
                 Bit representation:
                 0 International amateur radio band 1800 2000 kHz
                 1 International amateur radio band 3500 4000 kHz
                 2 International amateur radio band 7000 7300 kHz
                 3 International amateur radio band 10100 10150 kHz
                 4 International amateur radio band 14000 14350 kHz
                 5 International amateur radio band 18068 18168 kHz
                 6 International amateur radio band 21000 21450 kHz
                 7 International amateur radio band 24890 24990 kHz
                 8 International amateur radio band 28000 29700 kHz
                 9 International amateur radio band 50000 54000 kHz
                 10 International amateur radio band 70000 70500 kHz
                 11 International amateur radio band 144000 148000 kHz
                 Default value: All IAR bands disabled (no PSD reduction).
                "
            REFERENCE
                "ITU-T G.9701, paragraph 7.3.1.2 and 12.3.2.1.1, G.994.1 Table 11.70.8 and 11.70.8.1"
            ::= { hwXdslGlobalConfig 7  }

        hwXdslGlobalConfigRfiNotchDescription OBJECT-TYPE
            SYNTAX OCTET STRING (SIZE (0..32))
            MAX-ACCESS read-write
            STATUS current
            DESCRIPTION
                "The global RFI notch description."
            ::= { hwXdslGlobalConfig 8 }

        hwXdslVdsl2Profile35bFallbackConfigValue OBJECT-TYPE
            SYNTAX BITS
            {
                profile8a(0),
                profile8b(1),
                profile8c(2),
                profile8d(3),
                profile12a(4),
                profile12b(5),
                profile17a(6),
                profile30a(7),
                --
                reserved1(8),
                reserved2(9),
                reserved3(10),
                reserved4(11),
                reserved5(12),
                reserved6(13),
                reserved7(14),
                reserved8(15)
            }
            MAX-ACCESS read-write
            STATUS current
            DESCRIPTION
                "When the port is configured profile35b and this port does not support
                 profile35b on CPE,the configuration parameter contains the G.993.2 profile
                 to be allowed automatic fallback to profilexx.
                 It is coded in a bitmap representation (0 if not allowed,1 if allowed.
                 Starting from the left,the first represents bit 0).
                 Options:
                 1. profile8a(bit 0)               -enable/disable fallback to profile8a
                 2. profile8b(bit 1)               -enable/disable fallback to profile8b
                 3. profile8c(bit 2)               -enable/disable fallback to profile8c
                 4. profile8d(bit 3)               -enable/disable fallback to profile8d
                 5. profile12a(bit 4)              -enable/disable fallback to profile12a
                 6. profile12b(bit 5)              -enable/disable fallback to profile12b
                 7. profile17a(bit 6)              -enable/disable fallback to profile17a
                 8. profile30a(bit 7)              -enable/disable fallback to profile30a
                 9. reserved1(bit 8)               -reserved1
                 10.reserved2(bit 9)               -reserved2
                 11.reserved3(bit 10)              -reserved3
                 12.reserved4(bit 11)              -reserved4
                 13.reserved5(bit 12)              -reserved5
                 14.reserved6(bit 13)              -reserved6
                 15.reserved7(bit 14)              -reserved7
                 16.reserved8(bit 15)              -reserved8
                 Default value:0x02(enabled fallback to profile17a)
                 "
            ::= { hwXdslGlobalConfig 9 }

        hwXdslGlobalConfigRfiNotchBands OBJECT-TYPE
            SYNTAX Xdsl2RfiBands
            MAX-ACCESS read-write
            STATUS current
            DESCRIPTION
                "This configuration parameter defines the bands where the PSD shall be reduced as specified in ITU-T G.9701 #7.3.1.2.
                 Each band shall be represented by a start and stop subcarrier indices with a subcarrier spacing of 51.75 kHz.
                 Up to 16 bands may be specified.
                 This parameter defines the RFI bands for both upstream and downstream directions.
                 Default value: No RFI bands.
                "
            REFERENCE
                "ITU-T G.9701, paragraph 7.3.1.2 and 12.3.2.1.1"
            ::= { hwXdslGlobalConfig 10  }

        hwXdslToneBlackoutGlobalConfigSwitch   OBJECT-TYPE
            SYNTAX INTEGER
            {
            enabled(1),
            disabled(2)
            }
            MAX-ACCESS  read-write
            STATUS      current
            DESCRIPTION
                "The global tone blackout parameter is enabled or disabled.
                 Default values:disabled(2).
                 Options:
                 1. enabled(1)  - The global tone blackout parameter is enabled.
                 2. disabled(2) - The global tone blackout parameter is disabled.
                "
            ::= { hwXdslGlobalConfig 11  }

        hwXdslVdslToneBlackoutGlobalConfig  OBJECT-TYPE
             SYNTAX      OCTET STRING(SIZE(0..79))
             MAX-ACCESS  read-write
             STATUS      current
             DESCRIPTION
                 "The global subset of subcarrier mask that shall be
                  used to mask the subcarriers.
                  It is a string of bands consist of begin tone index
                  and end tone index.
                  for example :0-10,20-50,100-4095
                  It can contain as most as 8 bands.
                 "
             REFERENCE    "ITU-T G.997.1(200604), paragraph 7.3.1.2.8"
             ::= { hwXdslGlobalConfig 12 }

       hwXdslGfastCarMaskGlobalConfigDs OBJECT-TYPE
            SYNTAX OCTET STRING(SIZE(0..320))
            MAX-ACCESS read-write
            STATUS current
            DESCRIPTION
                "The global g.fast specific subcarriers mask.
                 This configuration parameter defines the restrictions, additional to the band plan, to determine
                 the set of subcarriers allowed for transmission in downstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwXdslGlobalConfig 13 }

        hwXdslGfastCarMaskGlobalConfigUs OBJECT-TYPE
            SYNTAX OCTET STRING(SIZE(0..320))
            MAX-ACCESS read-write
            STATUS current
            DESCRIPTION
                "The global g.fast specific subcarriers mask.
                 This configuration parameter defines the restrictions, additional to the band plan, to determine
                 the set of subcarriers allowed for transmission in upstream directions.
                 The parameter shall describe the not masked subcarriers as one or more frequency bands.
                 Each band is represented by start and stop subcarrier indices with a subcarrier spacing of 51.75kHz.
                 The valid range of subcarrier indices runs from 0 to at least the index of the highest allowed
                 subcarrier in both transmission directions.
                 Up to 32 bands may be specified. Other subcarriers shall be masked.
                "
            REFERENCE
                "ITU-T G.9701, paragraph 7.3.1.3"
            ::= { hwXdslGlobalConfig 14 }

        hwXdslGfastLowFreqEdgeGlobalConfigSwitch OBJECT-TYPE
            SYNTAX INTEGER
            {
            enabled(1),
            disabled(2)
            }
            MAX-ACCESS  read-write
            STATUS      current
            DESCRIPTION
                "The global Low-frequency Edge Stop-band Mask(LESM) parameter is enabled or disabled.
                 Default values:disabled(2).
                 Options:
                 1. enabled(1)  - The global Low-frequency Edge Stop-band Mask parameter is enabled.
                 2. disabled(2) - The global Low-frequency Edge Stop-band Mask parameter is disabled.
                "
            ::= { hwXdslGlobalConfig 15  }

        hwXdslGfastLowFreqEdgeGlobalConfigDs OBJECT-TYPE
            SYNTAX Gauge32 (43..1023)
            MAX-ACCESS read-write
            STATUS current
            DESCRIPTION
                "The global Low-frequency Edge Stop-band Mask(LESM) in downstream directions.
                 If a LESM is used, the LESM shall be specified with breakpoints.
                 These breakpoints are specified starting from ftr1, which is the start of the in-band PSD mask, as specified in [ITU-T G.9700].
                 This is not to be confused with ftr3,  which is the start of the in-band part of the LESM.
                 Default values:43.
                "
            REFERENCE
                "ITU-T G.9701, paragraph 7.3.1.1.1"
            ::= { hwXdslGlobalConfig 16 }

        hwXdslGfastLowFreqEdgeGlobalConfigUs OBJECT-TYPE
            SYNTAX Gauge32 (43..1023)
            MAX-ACCESS read-write
            STATUS current
            DESCRIPTION
                "The global Low-frequency Edge Stop-band Mask(LESM) in upstream directions.
                 If a LESM is used, the LESM shall be specified with breakpoints.
                 These breakpoints are specified starting from ftr1, which is the start of the in-band PSD mask, as specified in [ITU-T G.9700].
                 This is not to be confused with ftr3,  which is the start of the in-band part of the LESM.
                 Default values:43.
                "
            REFERENCE
                "ITU-T G.9701, paragraph 7.3.1.1.1"
            ::= { hwXdslGlobalConfig 17 }

        hwXdslVdsl2LrModeGlobalConfigSwitch OBJECT-TYPE
            SYNTAX INTEGER
            {
            enabled(1),
            disabled(2)
            }
            MAX-ACCESS  read-write
            STATUS      current
            DESCRIPTION
                "The global VDSL2-LR configuration parameter is enabled or disabled.
                 Default values:disabled(2).
                 Options:
                 1. enabled(1)  - The global VDSL2-LR configuration parameter is enabled.
                 2. disabled(2) - The global VDSL2-LR configuration parameter is disabled.
                "
            ::= { hwXdslGlobalConfig 18  }

        hwXdslVdsl2LrMode  OBJECT-TYPE
            SYNTAX BITS
            {
                shortloop(0),
                mediumloop(1),
                longloop(2)
            }
            MAX-ACCESS  read-write
            STATUS      current
            DESCRIPTION
                "This parameter specifies which VDSL2-LR operation types are allowed.
                 The parameter is encoded as a bitmap representation (0 is not allowed, 1 is allowed).
                 Default values:0.
                 Options:
                 1. shortloop(bit 0)               -short loop operation type
                 2. mediumloop(bit 1)              -medium loop operation type
                 3. longloop(bit 2)                -long loop operation type
            "
            ::= { hwXdslGlobalConfig 19 }

         -- XDSL auto delete profile unused

        hwXdslAutoDeleteVdslProfUnusedProfType   OBJECT-TYPE
            SYNTAX INTEGER
            {
            vdsl2LineConfTemplate(1),
            vdsl2LineConfProf(2),
            vdsl2ChConfProfile(3),
            vdsl2LineAlarmConfTemplate(4),
            vdsl2LineAlarmConfProfile(5),
            vdsl2ChAlarmConfProfile(6),
            vdsl2ServProf(7),
            vdsl2SpectrumProf(8),
            vdsl2DpboProf(9),
            vdsl2UpboProf(10),
            vdsl2NoiseMarginProf(11),
            vdsl2DelayInpProf(12),
            vopDataRateConfProf(13),
            vopLineSpectrumConfProf(14),
            vopUPBOConfProf(15),
            vopDPBOConfProf(16),
            vopRFIConfProf(17),
            vopSNRMarginConfProf(18),
            vopINPDelayConfProf(19),
            vopVirtualNoiseConfProf(20),
            vopModeSpecificPSDConfProf(21)
            }
            MAX-ACCESS  read-write
            STATUS      current
            DESCRIPTION
               "The profile type of deleting unused VDSL profile.
               Options:
               1. vdsl2LineConfTemplate(1)          - VDSL2 line template
               2. vdsl2LineConfProf(2)              - VDSL2 line profile
               3. vdsl2ChConfProfile(3)             - VDSL2 channel profile
               4. vdsl2LineAlarmConfTemplate(4)     - VDSL2 alarm template
               5. vdsl2LineAlarmConfProfile(5)      - VDSL2 alarm profile
               6. vdsl2ChAlarmConfProfile(6)        - VDSL2 channel alarm profile
               7. vdsl2ServProf(7)                  - VDSL2 service profile
               8. vdsl2SpectrumProf(8)              - VDSL2 spectrum profile
               9. vdsl2DpboProf(9)                  - VDSL2 dpbo profile
               10. vdsl2UpboProf(10)                - VDSL2 upbo profile
               11. vdsl2NoiseMarginProf(11)         - VDSL2 noise-margin profile
               12. vdsl2DelayInpProf(12)            - VDSL2 inp-delay profile
               13. vopDataRateConfProf(13)          - XDSL data rate profile
               14. vopLineSpectrumConfProf(14)      - XDSL line spectrum profile
               15. vopUPBOConfProf(15)              - XDSL upbo profile
               16. vopDPBOConfProf(16)              - XDSL dpbo profile
               17. vopRFIConfProf(17)               - XDSL rfi profile
               18. vopSNRMarginConfProf(18)         - XDSL noise-margin profile
               19. vopINPDelayConfProf(19)          - XDSL inp-delay profile
               20. vopVirtualNoiseConfProf(20)      - XDSL virtual noise profile
               21. vopModeSpecificPSDConfProf(21)   - XDSL PSD profile
               "

            ::= { hwXdslCfgAutoDeleteProfUnused 1 }

        hwXdslAutoDeleteVdslProfUnusedOperType  OBJECT-TYPE
            SYNTAX INTEGER
            {
                first(1),
                all(2)
            }
            MAX-ACCESS  read-write
            STATUS      current
            DESCRIPTION
                "The operation type of deleting unused XDSL profile.
                 This object is defaulted all(2).
                 Options:
                 1. first(1)   - Delete first profile
                 2. all(2)     - Delete all profile
                "

            ::= { hwXdslCfgAutoDeleteProfUnused 2 }

        hwXdslGfastConfTable  OBJECT-TYPE
            SYNTAX      SEQUENCE  OF  HwXdslGfastConfEntry
            MAX-ACCESS  not-accessible
            STATUS      current
            DESCRIPTION
                "The table hwXdslGfastConfTable contains frame configuration parameters of the G.fast tdd-profile name.
                 The index of this table is hwFrameIndex.
                "
            ::= { hwXdslGfastConf 1 }

        hwXdslGfastConfEntry  OBJECT-TYPE
            SYNTAX      HwXdslGfastConfEntry
            MAX-ACCESS  not-accessible
            STATUS      current
            DESCRIPTION
                "The table hwXdslGfastConfTable contains frame configuration parameters of the G.fast tdd-profile name.
                 The index of this entry is hwFrameIndex.
                "
            INDEX  { hwFrameIndex }
            ::= { hwXdslGfastConfTable 1 }

        HwXdslGfastConfEntry  ::=
            SEQUENCE {
              hwXdslGfastCnfgTddProfile   OCTET STRING
            }

        hwXdslGfastCnfgTddProfile  OBJECT-TYPE
            SYNTAX      OCTET STRING (SIZE(0..32))
            MAX-ACCESS  read-write
            STATUS      current
            DESCRIPTION
                "The value of this object identifies the row in the G.fast tdd-profile config table
                 (hwXdslGfastConfTddProfTable), which applies to G.fast line.
                "
            DEFVAL       { "DEFVAL" }
            ::= { hwXdslGfastConfEntry 1 }

--        hwXdslCfgTrapsVbOids

        hwXdslLinePMThresholdItem OBJECT-TYPE
            SYNTAX OCTET STRING (SIZE (0..1024))
            MAX-ACCESS accessible-for-notify
            STATUS current
            DESCRIPTION
                "Indicate the threshold item."
            ::= { hwXdslCfgTrapsVbOids 1 }

        hwXdslLinePMThresholdValue OBJECT-TYPE
            SYNTAX Integer32
            MAX-ACCESS accessible-for-notify
            STATUS current
            DESCRIPTION
                "XDSL threshold value"
            ::= { hwXdslCfgTrapsVbOids 2 }

        hwXdslPortActFailReason OBJECT-TYPE
            SYNTAX OCTET STRING (SIZE (0..1024))
            MAX-ACCESS accessible-for-notify
            STATUS current
            DESCRIPTION
                "Indicate the the reason of the active port fail."
            ::= { hwXdslCfgTrapsVbOids 3 }

        hwXdslChPMThresholdItem OBJECT-TYPE
            SYNTAX OCTET STRING (SIZE (0..1024))
            MAX-ACCESS accessible-for-notify
            STATUS current
            DESCRIPTION
                "Indicate the threshold value of threshold item ."
            ::= { hwXdslCfgTrapsVbOids 4 }

        hwXdslChPMCurrentValue OBJECT-TYPE
            SYNTAX Integer32
            MAX-ACCESS accessible-for-notify
            STATUS current
            DESCRIPTION
                "Indicate the current value of threshold item."
            ::= { hwXdslCfgTrapsVbOids 5 }

        hwXdslChPMThresholdValue OBJECT-TYPE
            SYNTAX Integer32
            MAX-ACCESS accessible-for-notify
            STATUS current
            DESCRIPTION
                "Indicate the threshold value of threshold item."
            ::= { hwXdslCfgTrapsVbOids 6 }

        hwXdslLineActRateUs OBJECT-TYPE
            SYNTAX Integer32
            MAX-ACCESS accessible-for-notify
            STATUS current
            DESCRIPTION
                "Indicate the line active data rate in
                 the upstream direction.
                "
            ::= { hwXdslCfgTrapsVbOids 7 }

        hwXdslLineActRateDs OBJECT-TYPE
            SYNTAX Integer32
            MAX-ACCESS accessible-for-notify
            STATUS current
            DESCRIPTION
                "Indicate the line active data rate in
                 the downstream direction.
                "
            ::= { hwXdslCfgTrapsVbOids 8 }

        hwXdslChipsetID OBJECT-TYPE
            SYNTAX Integer32
            MAX-ACCESS accessible-for-notify
            STATUS current
            DESCRIPTION
                "ChipsetID, the chipset id of the board."
            ::= { hwXdslCfgTrapsVbOids 9 }

        hwXdslModeSwitchResult OBJECT-TYPE
            SYNTAX  INTEGER {
                       success(0),
                       fail(1)
                    }
            MAX-ACCESS accessible-for-notify
            STATUS current
            DESCRIPTION
                "XDSL mode switch result.
                 Options:
                 1. success(0)  - success
                 2. fail(1)     - fail
                "
            ::= { hwXdslCfgTrapsVbOids 10 }

        hwXdslLinePMCurrentValue OBJECT-TYPE
            SYNTAX Integer32
            MAX-ACCESS accessible-for-notify
            STATUS current
            DESCRIPTION
                "Indicate the current value of threshold item."
            ::= { hwXdslCfgTrapsVbOids 11 }

        hwXdslCfgRequestID OBJECT-TYPE
            SYNTAX Integer32
            MAX-ACCESS accessible-for-notify
            STATUS current
            DESCRIPTION
                "Request ID"
           ::= { hwXdslCfgTrapsVbOids 12 }

        hwACTChngeDesc OBJECT-TYPE
            SYNTAX OCTET STRING (SIZE(1..256))
            MAX-ACCESS accessible-for-notify
            STATUS current
            DESCRIPTION
                "The XDSL port actived rate change description."
            ::= { hwXdslCfgTrapsVbOids 13 }

        hwXdslTemplateType OBJECT-TYPE
            SYNTAX INTEGER {
                 lineConfTemplate(1),
                 alarmConfTemplate(2),
                 spectrumProf(3),
                 dpboProf(4),
                 upboProf(5),
                 serviceProf(6),
                 noiseMarginProf(7),
                 delayInpProf(8),
                 fastAlarmConfTemplate(9),
                 xdsltr129lineConfTemplate(10)
                 }
            MAX-ACCESS accessible-for-notify
            STATUS current
            DESCRIPTION
                "Type of the XDSL profile ID.
                 Options:
                 1. lineConfTemplate(1)        - VDSL2 line template
                 2. alarmConfTemplate(2)       - VDSL2 alarm template
                 3. spectrumProf(3)            - VDSL2 spectrum profile
                 4. dpboProf(4)                - VDSL2 dpbo profile
                 5. upboProf(5)                - VDSL2 upbo profile
                 6. serviceProf(6)             - VDSL2 service profile
                 7. noiseMarginProf(7)         - VDSL2 noise-margin profile
                 8. delayInpProf(8)            - VDSL2 delay-inp profile
                 9. fastAlarmConfTemplate(9)   - G.fast alarm template
                 10.xdsltr129lineConfTemplate(10) - XDSL TR129 line template
                "

            ::= { hwXdslCfgTrapsVbOids 14 }

        hwXdslProfOperType OBJECT-TYPE
            SYNTAX INTEGER {
                 add(1),
                 modify(2),
                 delete(3)
                 }
            MAX-ACCESS accessible-for-notify
            STATUS current
            DESCRIPTION
                "VDSL profile operate type.
                 Options:
                 1.add(1)    - Add a XDSL profile
                 2.modify(2) - Modify a XDSL profile
                 3.delete(3) - Delete a XDSL profile
                "

            ::= { hwXdslCfgTrapsVbOids 15 }

         hwXdslPortAutoDeactiveLineRetrainInfo OBJECT-TYPE
            SYNTAX OCTET STRING (SIZE (0..1024))
            MAX-ACCESS accessible-for-notify
            STATUS current
            DESCRIPTION
                "Indicate the last retrain info of the line."
            ::= { hwXdslCfgTrapsVbOids 16 }

         hwXdslLineVdsl2ProfileConfig OBJECT-TYPE
            SYNTAX OCTET STRING (SIZE(0..32))
            MAX-ACCESS accessible-for-notify
            STATUS current
            DESCRIPTION
                "Indicate the configuration G.993.2 profile."
            ::= { hwXdslCfgTrapsVbOids 17 }

        hwXdslLineVdsl2ProfileFallback OBJECT-TYPE
            SYNTAX OCTET STRING (SIZE(0..32))
            MAX-ACCESS accessible-for-notify
            STATUS current
            DESCRIPTION
                "Indicate the fallback G.993.2 profile."
            ::= { hwXdslCfgTrapsVbOids 18 }


--        XDSL TRAP

        hwVdslModeSwitchTrap NOTIFICATION-TYPE
            OBJECTS {
                    hwXdslModeSwitchResult
                }
            STATUS current
            DESCRIPTION
                "VDSL mode switch trap.
                 This trap message is generated when the XDSL line mode fails
                 to be switched.
                "
            ::= { hwXdslCfgCommonTraps     0 1 }


        hwVdslCurrentModeTrap NOTIFICATION-TYPE
            OBJECTS {
                    hwVdslmodecfg
                }
            STATUS current
            DESCRIPTION
                "VDSL current mode trap.
                 This trap message is generated when the current mode of the VDSL
                 line is reported to the NMS periodically.
                "
            ::= { hwXdslCfgCommonTraps     0 2 }

        hwXdslPortStatusChangeTrap NOTIFICATION-TYPE
            OBJECTS {
                    hwFrameIndex,
                    hwSlotIndex,
                    hwPortIndex,
                    hwPortOperStatus,
                    hwPortPrimaryStatus,
                    hwPortSecondaryStatus
             }
            STATUS current
            DESCRIPTION
                "XDSL port status change trap.
                 This trap message is generated when the port status changes,
                 for example from up to down or from down to up.The parameter
                 information about the trap message describes the current
                 status of the link and the location where the trap message
                 is generated."
            ::= { hwXdslCfgCommonTraps  0 3 }

        hwXdslDeltOperResultTrap NOTIFICATION-TYPE
            OBJECTS {
                    hwXdslCfgRequestID,
                    hwXdslLineCmndConfLdsfFailReason,
                    ifIndex
             }
            STATUS current
            DESCRIPTION
                "XDSL delt trap.
                 This trap message is generated when the result of the DELT performed
                 on the XDSL line is reported.
                "
            ::= { hwXdslCfgCommonTraps 0 4 }

        hwXdslTemplateIDChangeTrap NOTIFICATION-TYPE
            OBJECTS {
                hwConfigChangeIP,
                hwXdslTemplateType,
                ifIndex,
                hwXdslProfName
          }
            STATUS current
            DESCRIPTION
               "XDSL template change trap.
                This trap message is generated when the XDSL templete changed.
               "
            ::= { hwXdslCfgCommonTraps 0 5 }

        hwVdslLConfTempTemplateChangeTrap NOTIFICATION-TYPE
            OBJECTS {
                hwConfigChangeIP,
                hwXdslProfOperType,
                hwVdslLConfTempTemplateName
          }
            STATUS current
            DESCRIPTION
               "XDSL line template change trap.
                This trap message is generated when the XDSL line template changed.
               "
            ::= { hwXdslCfgCommonTraps 0 6 }

        hwVdslLConfProfProfileChangeTrap NOTIFICATION-TYPE
            OBJECTS {
                hwConfigChangeIP,
                hwXdslProfOperType,
                hwVdslLConfProfProfileName
          }
            STATUS current
            DESCRIPTION
               "XDSL line profile change trap.
                This trap message is generated when the XDSL line profile changed.
               "
            ::= { hwXdslCfgCommonTraps 0 7 }

        hwVdslChConfProfProfileChangeTrap NOTIFICATION-TYPE
            OBJECTS {
                hwConfigChangeIP,
                hwXdslProfOperType,
                hwVdslChConfProfProfileName
          }
            STATUS current
            DESCRIPTION
               "XDSL channel profile change trap.
                This trap message is generated when the XDSL channel profile changed.
               "
            ::= { hwXdslCfgCommonTraps 0 8 }

        hwXdslGfastTddProfileChangeTrap NOTIFICATION-TYPE
            OBJECTS {
                hwConfigChangeIP,
                hwXdslProfOperType,
                hwXdslGfastConfTddProfName
          }
            STATUS current
            DESCRIPTION
               "G.fast tdd-profile change trap.
                This trap message is generated when the G.fast tdd-profile changed.
               "
            ::= { hwXdslCfgCommonTraps 0 9 }

        hwXdslGfastFrameTddProfileConfChangeTrap NOTIFICATION-TYPE
            OBJECTS {
                hwConfigChangeIP,
                hwFrameIndex,
                hwXdslGfastConfTddProfName
          }
            STATUS current
            DESCRIPTION
               "This trap message is generated when the G.fast tdd-profile ID of the frame is changed.
               "
            ::= { hwXdslCfgCommonTraps 0 10 }

        hwXdslTR129LineTemplateChangeTrap NOTIFICATION-TYPE
            OBJECTS {
                hwConfigChangeIP,
                hwXdslProfOperType,
                hwXdslTR129LineConfTempTemplateName
          }
            STATUS current
            DESCRIPTION
               "G.Fast line template change trap.
                This trap message is generated when the G.Fast line template changed.
               "
            ::= { hwXdslCfgCommonTraps 0 11 }

        hwXdslTR129LineProfileChangeTrap NOTIFICATION-TYPE
            OBJECTS {
                hwConfigChangeIP,
                hwXdslProfOperType,
                hwXdslTR129LineConfProfProfileName
                }
            STATUS current
            DESCRIPTION
               "G.fast line template change trap.
                This trap message is generated when the G.fast line template changed.
               "
            ::= { hwXdslCfgCommonTraps 0 12 }

          hwXdslTR129ChannelProfileChangeTrap NOTIFICATION-TYPE
            OBJECTS {
                hwConfigChangeIP,
                hwXdslProfOperType,
                hwXdslTR129ChConfProfProfileName
          }
            STATUS current
            DESCRIPTION
               "G.fastline template change trap.
                This trap message is generated when the G.fast line template changed.
               "
            ::= { hwXdslCfgCommonTraps 0 13 }

        hwGfastModeSwitchTrap NOTIFICATION-TYPE
            OBJECTS {
                hwXdslModeSwitchResult
          }
            STATUS current
            DESCRIPTION
               "G.fast line mode switch trap.
                This trap message is generated when the G.fast line mode fails to be switched.
               "
            ::= { hwXdslCfgCommonTraps 0 14 }


        hwGfastCurrentModeTrap NOTIFICATION-TYPE
            OBJECTS {
                       hwGfastModeCfg
                    }
            STATUS current
            DESCRIPTION
                "G.fast current mode trap.
                 This trap message is generated when the current mode of the G.fast
                 line is reported to the NMS periodically.
                "
            ::= { hwXdslCfgCommonTraps     0 15}

     --   XDSL ALARM
        hwXdslAutoDeactivateLackLicensesCfgAlarmTrap NOTIFICATION-TYPE
            OBJECTS {
                    hwFrameIndex,
                    hwSlotIndex
                    }
            STATUS current
            DESCRIPTION
                "This trap message is generated when some xDSL ports or all the xDSL ports
                 are automatically deactivated due to lack of licenses.
                "
            ::= { hwXdslCfgAlarmTraps 0 1 }

        hwXdslPortAutoDeactiveLineFaultAlarmTrap NOTIFICATION-TYPE
            OBJECTS {
                    hwFrameIndex,
                    hwSlotIndex,
                    hwPortIndex,
                    hwXdslPortAutoDeactiveLineRetrainInfo
                    }
            STATUS current
            DESCRIPTION
                "This trap message is generated when the XDSL port is automatically
                 deactivated due to the line fault."
            ::= { hwXdslCfgAlarmTraps 0 2 }

        hwXdslPortReactiveAfterRecoverAlarmTrap NOTIFICATION-TYPE
            OBJECTS {
                    hwFrameIndex,
                    hwSlotIndex,
                    hwPortIndex
                    }
            STATUS current
            DESCRIPTION
                "This trap message is generated when the XDSL port is re-activated
                 after the XDSL line recovers."
            ::= { hwXdslCfgAlarmTraps 0 3 }

        hwXdslPerformanceStatiReachThresholdAlarmTrap NOTIFICATION-TYPE
            OBJECTS {
                    hwFrameIndex,
                    hwSlotIndex,
                    hwPortIndex,
                    hwXdslLinePMThresholdItem,
                    hwXdslLinePMCurrentValue,
                    hwXdslLinePMThresholdValue
                    }
            STATUS current
            DESCRIPTION
                "This trap message is generated when the line performance
                 statistics of the XDSL port reach the threshold."
            ::= { hwXdslCfgAlarmTraps 0 4 }

       hwXdslDownstreamRateLowerThresholdAlarmTrap NOTIFICATION-TYPE
            OBJECTS {
                    hwFrameIndex,
                    hwSlotIndex,
                    hwPortIndex,
                    hwXdslChStatusChannelNum,
                    hwXdslChStatusActDataRate
                    }
            STATUS current
            DESCRIPTION
              "This trap message is generated when the xDSL channel downstream
               rate is lower than the threshold."
            ::= { hwXdslCfgAlarmTraps 0 5 }

        hwXdslActivePortFailConfigParaAlarmTrap NOTIFICATION-TYPE
            OBJECTS {
                    hwFrameIndex,
                    hwSlotIndex,
                    hwPortIndex,
                    hwXdslPortActFailReason
                    }
            STATUS current
            DESCRIPTION
                "This trap message is generated when it fails to activate the port
                 by using the XDSL line configuration parameters."
            ::= { hwXdslCfgAlarmTraps 0 6 }

        hwXdslPerformanceStatisReachThresholdAlarmTrap NOTIFICATION-TYPE
            OBJECTS {
                    hwFrameIndex,
                    hwSlotIndex,
                    hwPortIndex,
                    hwXdslChStatusChannelNum,
                    hwXdslChPMThresholdItem,
                    hwXdslChPMThresholdValue,
                    hwXdslChPMCurrentValue
                    }
            STATUS current
            DESCRIPTION
                "This trap message is generated when the channel performance statistics
                 of the XDSL port reach the threshold."
            ::= { hwXdslCfgAlarmTraps 0 7 }

        hwXdslChannelUpstreamLowerThresholdAlarmTrap NOTIFICATION-TYPE
            OBJECTS {
                    hwFrameIndex,
                    hwSlotIndex,
                    hwPortIndex,
                    hwXdslChStatusChannelNum,
                    hwXdslChStatusActDataRate
                    }
            STATUS current
            DESCRIPTION
              "This trap message is generated when the xDSL channel upstream rate
               is lower than the threshold."
            ::= { hwXdslCfgAlarmTraps 0 8 }

        hwXdslXTURPowerOffAlarmTrap NOTIFICATION-TYPE
            OBJECTS {
                    hwFrameIndex,
                    hwSlotIndex,
                    hwPortIndex
                    }
            STATUS current
            DESCRIPTION
                "This trap message is generated when the VTU-R is powered off."
            ::= { hwXdslCfgAlarmTraps 0 9 }

        hwXdslPortActiveRateChangeAlarmTrap NOTIFICATION-TYPE
            OBJECTS {
                    hwFrameIndex,
                    hwSlotIndex,
                    hwPortIndex,
                    hwXdslLineActRateUs,
                    hwXdslLineActRateDs,
                    hwACTChngeDesc
                    }
            STATUS current
            DESCRIPTION
                "This trap message is generated when the XDSL port actived rate change."
            ::= { hwXdslCfgAlarmTraps 0 10 }

        hwXdslChipsetUnavailableAlarmTrap NOTIFICATION-TYPE
            OBJECTS {
                    hwFrameIndex,
                    hwSlotIndex,
                    hwXdslChipsetID
                    }
            STATUS current
            DESCRIPTION
                "This trap message is generated when the XDSL chipset is unavailable."
            ::= { hwXdslCfgAlarmTraps 0 11 }

        hwXdslChipsetRecoverAlarmTrap NOTIFICATION-TYPE
            OBJECTS {
                    hwFrameIndex,
                    hwSlotIndex,
                    hwXdslChipsetID
                    }
            STATUS current
            DESCRIPTION
                "This trap message is generated when the XDSL chipset recovers from unavailability."
            ::= { hwXdslCfgAlarmTraps 0 12 }

        hwXdslChannelUpstreamExcThreAlarmTrap NOTIFICATION-TYPE
            OBJECTS {
                    hwFrameIndex,
                    hwSlotIndex,
                    hwPortIndex,
                    hwXdslChStatusActDataRate
                    }
            STATUS current
            DESCRIPTION
              "This trap message is generated when the xDSL channel upstream rate
               increases to a value higher than the threshold."
            ::= { hwXdslCfgAlarmTraps 0 13 }

        hwXdslChannelUpstreamRestoreThreAlarmTrap NOTIFICATION-TYPE
            OBJECTS {
                    hwFrameIndex,
                    hwSlotIndex,
                    hwPortIndex,
                    hwXdslChStatusActDataRate
                    }
            STATUS current
            DESCRIPTION
              "This trap message is generated when the xDSL channel upstream rate
               decreases to a value lower than the threshold."
            ::= { hwXdslCfgAlarmTraps 0 14 }

        hwXdslChannelDownstreamExcThreAlarmTrap NOTIFICATION-TYPE
            OBJECTS {
                    hwFrameIndex,
                    hwSlotIndex,
                    hwPortIndex,
                    hwXdslChStatusActDataRate
                    }
            STATUS current
            DESCRIPTION
              "This trap message is generated when the xDSL channel downstream rate
               increases to a value higher than the threshold."
            ::= { hwXdslCfgAlarmTraps 0 15 }

        hwXdslChannelDownstreamRestoreThreAlarmTrap NOTIFICATION-TYPE
            OBJECTS {
                    hwFrameIndex,
                    hwSlotIndex,
                    hwPortIndex,
                    hwXdslChStatusActDataRate
                    }
            STATUS current
            DESCRIPTION
              "This trap message is generated when the xDSL channel downstream rate
               decreases to a value lower than the threshold."
            ::= { hwXdslCfgAlarmTraps 0 16 }

        hwXdslUnSuppVectorPortActFailAlarmTrap NOTIFICATION-TYPE
            OBJECTS {
                    hwFrameIndex,
                    hwSlotIndex,
                    hwPortIndex
                    }
            STATUS current
            DESCRIPTION
              "This trap message is generated when the CPE connected to the port does not
			   support vectoring and cannot be activated in 993.2 mode."
            ::= { hwXdslCfgAlarmTraps 0 17 }

        hwXdslVdsl2Profile35bFallbackFaultAlarmTrap NOTIFICATION-TYPE
            OBJECTS {
                    hwFrameIndex,
                    hwSlotIndex,
                    hwPortIndex,
                    hwXdslLineVdsl2ProfileConfig,
                    hwXdslLineVdsl2ProfileFallback
                    }
            STATUS current
            DESCRIPTION
              "This trap message is generated when G.993.2 profile fallback, such as configuring
			   the profile35b, but the CPE only supports profile17a,
			   and the CPE fallback to activate with profile17a."
            ::= { hwXdslCfgAlarmTraps 0 18 }

        hwXdslVdsl2Profile35bFallbackRecoveryAlarmTrap NOTIFICATION-TYPE
            OBJECTS {
                    hwFrameIndex,
                    hwSlotIndex,
                    hwPortIndex,
                    hwXdslLineVdsl2ProfileConfig
                    }
            STATUS current
            DESCRIPTION
              "This trap message is generated when the CPE restore configuration G.993.2 profile to activate."
            ::= { hwXdslCfgAlarmTraps 0 19 }
    END
