--
--
-- MIB generated by MG-SOFT Visual MIB Builder Version 4.0 Build 347
-- Wednesday, April 12, 2017 at 21:06:05
--

--
-- MIB generated by MG-SOFT Visual MIB Builder Version 4.0 Build 347
-- Friday, April 07, 2017 at 15:59:40
--
--
-- MIB generated by MG-SOFT Visual MIB Builder Version 4.0 Build 349
-- Tuesday, January 24, 2017 at 20:32:39
--
--
-- MIB generated by MG-SOFT Visual MIB Builder Version 4.0 Build 347
-- Monday, January 04, 2016 at 16:03:35
--
--
-- MIB generated by MG-SOFT Visual MIB Builder Version 4.0 Build 347
-- Sunday, January 03, 2016 at 17:32:15
--
--  =================================================================
-- Copyright (C) 2017 by  HUAWEI TECHNOLOGIES. All rights reserved.
--
-- Description: HUAWEI-SECURITY-SAFE-MIB
-- Reference:
-- Version: V1.07
-- History:
--         v1.04
--         modified by w00346671 2017-04-07
-- =================================================================

	HUAWEI-SECURITY-SAFE-MIB DEFINITIONS ::= BEGIN

		IMPORTS
			enterprises
				FROM RFC1155-SMI
			OBJECT-GROUP, MODULE-COMPLIANCE, NOTIFICATION-GROUP
				FROM SNMPv2-CONF
			IpAddress, Integer32, Gauge32, Counter32, Counter64,
			OBJECT-TYPE, MODULE-IDENTITY, NOTIFICATION-TYPE
				FROM SNMPv2-SMI;


		-- 1.3.6.1.4.1.2011.6.122.20
		hwSAFEMIB MODULE-IDENTITY
			LAST-UPDATED "201707131649Z"		-- July 13, 2017 at 16:49 GMT
			ORGANIZATION
				"Huawei Technologies Co.,Ltd."
			CONTACT-INFO
				"Huawei Industrial Base  Bantian, Longgang   Shenzhen 518129   People's Republic of China   Website: http://www.huawei.com   Email: support@huawei.com "
			DESCRIPTION
				"V1.00 The HUAWEI-SECURITY-SA-MIB contains objects to manage the SA product."
                                                                 REVISION "201707131649Z"		-- July 13, 2017 at 16:49 GMT
			DESCRIPTION
				"modified at 20170713"
                                                                REVISION "201706191649Z"		-- June 19, 2017 at 16:49 GMT
			DESCRIPTION
				"modified at 20170619"
			REVISION "201704071441Z"		-- April 07, 2017 at 14:41 GMT
			DESCRIPTION
				"modified at 20170407"
			REVISION "200906301700Z"		-- June 30, 2009 at 17:00 GMT
			DESCRIPTION
				"created at 20151221"
			REVISION "201701241700Z"		-- January 24, 2017 at 17:00 GMT
			DESCRIPTION
				"modified at 20170124"
			REVISION "201702221700Z"		-- February 22, 2017 at 17:00 GMT
			DESCRIPTION
				"modified at 20170222"
			REVISION "201704071441Z"		-- April 07, 2017 at 14:41 GMT
			DESCRIPTION
				"modified at 20170407"
			REVISION "201704071441Z"		-- April 07, 2017 at 14:41 GMT
			DESCRIPTION
				"modified at 20170407"
			::= { hwSecurity 20 }



--
-- Node definitions
--

--  1.3.6.1.4.1.2011.6.122.20
-- April 07, 2017 at 14:41 GMT
-- April 07, 2017 at 14:41 GMT
-- April 07, 2017 at 14:41 GMT
-- February 22, 2017 at 17:00 GMT
-- January 24, 2017 at 17:00 GMT
-- June 30, 2009 at 17:00 GMT
--
-- Node definitions
--
--  1.3.6.1.4.1.2011.6.122.20
-- January 03, 2016 at 17:39 GMT
-- January 27, 2017at 17:00 GMT
-- January 27, 2017at 17:00 GMT
-- June 30, 2009 at 17:00 GMT
-- January 03, 2016 at 17:39 GMT
--
-- Node definitions
--
--  1.3.6.1.4.1.2011.6.122.20
-- January 03, 2016 at 17:39 GMT
-- January 03, 2016 at 17:39 GMT
-- June 30, 2009 at 17:00 GMT
--
-- Node definitions
--
--  1.3.6.1.4.1.2011.6.122.20
-- June 30, 2009 at 17:00 GMT
--
-- Node definitions
--
--  1.3.6.1.4.1.2011.6.122.20
-- June 30, 2009 at 17:00 GMT
--
-- Node definitions
--
--  1.3.6.1.4.1.2011.6.122.20
-- June 30, 2009 at 17:00 GMT
--
-- Node definitions
--
--  1.3.6.1.4.1.2011.6.122.20
-- June 30, 2009 at 17:00 GMT
--
-- Node definitions
--
--  1.3.6.1.4.1.2011.6.122.20
-- June 30, 2009 at 17:00 GMT
--
-- Node definitions
--
-- 1.3.6.1.4.1.2011
-- 1.3.6.1.4.1.2011
-- 1.3.6.1.4.1.2011
-- 1.3.6.1.4.1.2011
-- 1.3.6.1.4.1.2011
-- 1.3.6.1.4.1.2011
-- 1.3.6.1.4.1.2011
-- 1.3.6.1.4.1.2011
		-- 1.3.6.1.4.1.2011
		huawei OBJECT IDENTIFIER ::= { enterprises 2011 }


--         1.3.6.1.4.1.2011.6
-- 1.3.6.1.4.1.2011.6
-- 1.3.6.1.4.1.2011.6
-- 1.3.6.1.4.1.2011.6
-- 1.3.6.1.4.1.2011.6
-- 1.3.6.1.4.1.2011.6
-- 1.3.6.1.4.1.2011.6
-- 1.3.6.1.4.1.2011.6
		-- 1.3.6.1.4.1.2011.6
		huaweiUtility OBJECT IDENTIFIER ::= { huawei 6 }


--         1.3.6.1.4.1.2011.6.122
-- 1.3.6.1.4.1.2011.6.122
-- 1.3.6.1.4.1.2011.6.122
-- 1.3.6.1.4.1.2011.6.122
-- 1.3.6.1.4.1.2011.6.122
-- 1.3.6.1.4.1.2011.6.122
-- 1.3.6.1.4.1.2011.6.122
-- 1.3.6.1.4.1.2011.6.122
		-- 1.3.6.1.4.1.2011.6.122
		hwSecurity OBJECT IDENTIFIER ::= { huaweiUtility 122 }


--         1.3.6.1.4.1.2011.6.122.20.1
-- 1.3.6.1.4.1.2011.6.122.20.1
-- 1.3.6.1.4.1.2011.6.122.20.1
-- 1.3.6.1.4.1.2011.6.122.20.1
-- 1.3.6.1.4.1.2011.6.122.20.1
-- 1.3.6.1.4.1.2011.6.122.20.1
-- 1.3.6.1.4.1.2011.6.122.20.1
-- 1.3.6.1.4.1.2011.6.122.20.1
		-- 1.3.6.1.4.1.2011.6.122.20.1
		hwDeviceObject OBJECT IDENTIFIER ::= { hwSAFEMIB 1 }


--         1.3.6.1.4.1.2011.6.122.20.1.1
-- 1.3.6.1.4.1.2011.6.122.20.1.1
-- 1.3.6.1.4.1.2011.6.122.20.1.1
-- 1.3.6.1.4.1.2011.6.122.20.1.1
-- 1.3.6.1.4.1.2011.6.122.20.1.1
-- 1.3.6.1.4.1.2011.6.122.20.1.1
-- 1.3.6.1.4.1.2011.6.122.20.1.1
-- 1.3.6.1.4.1.2011.6.122.20.1.1
		-- 1.3.6.1.4.1.2011.6.122.20.1.1
		hwSANodeObject OBJECT IDENTIFIER ::= { hwDeviceObject 1 }


--         1.3.6.1.4.1.2011.6.122.20.1.1.1
-- 1.3.6.1.4.1.2011.6.122.20.1.1.1
-- 1.3.6.1.4.1.2011.6.122.20.1.1.1
-- 1.3.6.1.4.1.2011.6.122.20.1.1.1
-- 1.3.6.1.4.1.2011.6.122.20.1.1.1
-- 1.3.6.1.4.1.2011.6.122.20.1.1.1
-- 1.3.6.1.4.1.2011.6.122.20.1.1.1
-- 1.3.6.1.4.1.2011.6.122.20.1.1.1
		-- 1.3.6.1.4.1.2011.6.122.20.1.1.1
		hwSpuSysInfoTable OBJECT-TYPE
			SYNTAX SEQUENCE OF HwSpuSysInfoEntry
			MAX-ACCESS not-accessible
			STATUS current
			DESCRIPTION
				"The SPU system information table"
			::= { hwSANodeObject 1 }


--         1.3.6.1.4.1.2011.6.122.20.1.1.1.1
-- 1.3.6.1.4.1.2011.6.122.20.1.1.1.1
-- 1.3.6.1.4.1.2011.6.122.20.1.1.1.1
-- 1.3.6.1.4.1.2011.6.122.20.1.1.1.1
-- 1.3.6.1.4.1.2011.6.122.20.1.1.1.1
-- 1.3.6.1.4.1.2011.6.122.20.1.1.1.1
-- 1.3.6.1.4.1.2011.6.122.20.1.1.1.1
-- 1.3.6.1.4.1.2011.6.122.20.1.1.1.1
		-- 1.3.6.1.4.1.2011.6.122.20.1.1.1.1
		hwSpuSysInfoEntry OBJECT-TYPE
			SYNTAX HwSpuSysInfoEntry
			MAX-ACCESS not-accessible
			STATUS current
			DESCRIPTION
				"The SPU system information table entry"
			INDEX { hwSpuSysInfoIndex }
			::= { hwSpuSysInfoTable 1 }


		HwSpuSysInfoEntry ::=
			SEQUENCE {
				hwSpuSysInfoIndex
					Gauge32,
				hwSpuSysInfoLocation
					OCTET STRING,
				hwSpuSysInfoType
					INTEGER,
				hwSpuSysInfoIPAddress
					IpAddress,
				hwSpuSysInfoState
					INTEGER
			 }

--         1.3.6.1.4.1.2011.6.122.20.1.1.1.1.1
-- 1.3.6.1.4.1.2011.6.122.20.1.1.1.1.1
-- 1.3.6.1.4.1.2011.6.122.20.1.1.1.1.1
-- 1.3.6.1.4.1.2011.6.122.20.1.1.1.1.1
-- 1.3.6.1.4.1.2011.6.122.20.1.1.1.1.1
-- 1.3.6.1.4.1.2011.6.122.20.1.1.1.1.1
-- 1.3.6.1.4.1.2011.6.122.20.1.1.1.1.1
-- 1.3.6.1.4.1.2011.6.122.20.1.1.1.1.1
		-- 1.3.6.1.4.1.2011.6.122.20.1.1.1.1.1
		hwSpuSysInfoIndex OBJECT-TYPE
			SYNTAX Gauge32 (1..2147483647)
			MAX-ACCESS not-accessible
			STATUS current
			DESCRIPTION
				"The index of the system"
			::= { hwSpuSysInfoEntry 1 }


--         1.3.6.1.4.1.2011.6.122.20.1.1.1.1.2
-- 1.3.6.1.4.1.2011.6.122.20.1.1.1.1.2
-- 1.3.6.1.4.1.2011.6.122.20.1.1.1.1.2
-- 1.3.6.1.4.1.2011.6.122.20.1.1.1.1.2
-- 1.3.6.1.4.1.2011.6.122.20.1.1.1.1.2
-- 1.3.6.1.4.1.2011.6.122.20.1.1.1.1.2
-- 1.3.6.1.4.1.2011.6.122.20.1.1.1.1.2
-- 1.3.6.1.4.1.2011.6.122.20.1.1.1.1.2
		-- 1.3.6.1.4.1.2011.6.122.20.1.1.1.1.2
		hwSpuSysInfoLocation OBJECT-TYPE
			SYNTAX OCTET STRING (SIZE (0..255))
			MAX-ACCESS read-only
			STATUS current
			DESCRIPTION
				"The location of the system"
			::= { hwSpuSysInfoEntry 2 }


--         1.3.6.1.4.1.2011.6.122.20.1.1.1.1.3
-- 1.3.6.1.4.1.2011.6.122.20.1.1.1.1.3
-- 1.3.6.1.4.1.2011.6.122.20.1.1.1.1.3
-- 1.3.6.1.4.1.2011.6.122.20.1.1.1.1.3
-- 1.3.6.1.4.1.2011.6.122.20.1.1.1.1.3
-- 1.3.6.1.4.1.2011.6.122.20.1.1.1.1.3
-- 1.3.6.1.4.1.2011.6.122.20.1.1.1.1.3
-- 1.3.6.1.4.1.2011.6.122.20.1.1.1.1.3
		-- 1.3.6.1.4.1.2011.6.122.20.1.1.1.1.3
		hwSpuSysInfoType OBJECT-TYPE
			SYNTAX INTEGER
				{
				sas(1),
				sps(2)
				}
			MAX-ACCESS read-only
			STATUS current
			DESCRIPTION
				"The system type"
			::= { hwSpuSysInfoEntry 3 }


--         1.3.6.1.4.1.2011.6.122.20.1.1.1.1.4
-- 1.3.6.1.4.1.2011.6.122.20.1.1.1.1.4
-- 1.3.6.1.4.1.2011.6.122.20.1.1.1.1.4
-- 1.3.6.1.4.1.2011.6.122.20.1.1.1.1.4
-- 1.3.6.1.4.1.2011.6.122.20.1.1.1.1.4
-- 1.3.6.1.4.1.2011.6.122.20.1.1.1.1.4
-- 1.3.6.1.4.1.2011.6.122.20.1.1.1.1.4
-- 1.3.6.1.4.1.2011.6.122.20.1.1.1.1.4
		-- 1.3.6.1.4.1.2011.6.122.20.1.1.1.1.4
		hwSpuSysInfoIPAddress OBJECT-TYPE
			SYNTAX IpAddress
			MAX-ACCESS read-only
			STATUS current
			DESCRIPTION
				"The system IP address"
			::= { hwSpuSysInfoEntry 4 }


--         1.3.6.1.4.1.2011.6.122.20.1.1.1.1.5
-- 1.3.6.1.4.1.2011.6.122.20.1.1.1.1.5
-- 1.3.6.1.4.1.2011.6.122.20.1.1.1.1.5
-- 1.3.6.1.4.1.2011.6.122.20.1.1.1.1.5
-- 1.3.6.1.4.1.2011.6.122.20.1.1.1.1.5
-- 1.3.6.1.4.1.2011.6.122.20.1.1.1.1.5
-- 1.3.6.1.4.1.2011.6.122.20.1.1.1.1.5
-- 1.3.6.1.4.1.2011.6.122.20.1.1.1.1.5
		-- 1.3.6.1.4.1.2011.6.122.20.1.1.1.1.5
		hwSpuSysInfoState OBJECT-TYPE
			SYNTAX INTEGER
				{
				normal(1),
				abnormal(2)
				}
			MAX-ACCESS read-only
			STATUS current
			DESCRIPTION
				"The state of the SPU system"
			::= { hwSpuSysInfoEntry 5 }


--         1.3.6.1.4.1.2011.6.122.20.1.1.2
-- 1.3.6.1.4.1.2011.6.122.20.1.1.2
-- 1.3.6.1.4.1.2011.6.122.20.1.1.2
-- 1.3.6.1.4.1.2011.6.122.20.1.1.2
-- 1.3.6.1.4.1.2011.6.122.20.1.1.2
-- 1.3.6.1.4.1.2011.6.122.20.1.1.2
-- 1.3.6.1.4.1.2011.6.122.20.1.1.2
-- 1.3.6.1.4.1.2011.6.122.20.1.1.2
		-- 1.3.6.1.4.1.2011.6.122.20.1.1.2
		hwServiceLinkTable OBJECT-TYPE
			SYNTAX SEQUENCE OF HwServiceLinkEntry
			MAX-ACCESS not-accessible
			STATUS current
			DESCRIPTION
				"The local link table"
			::= { hwSANodeObject 2 }


--         1.3.6.1.4.1.2011.6.122.20.1.1.2.1
-- 1.3.6.1.4.1.2011.6.122.20.1.1.2.1
-- 1.3.6.1.4.1.2011.6.122.20.1.1.2.1
-- 1.3.6.1.4.1.2011.6.122.20.1.1.2.1
-- 1.3.6.1.4.1.2011.6.122.20.1.1.2.1
-- 1.3.6.1.4.1.2011.6.122.20.1.1.2.1
-- 1.3.6.1.4.1.2011.6.122.20.1.1.2.1
-- 1.3.6.1.4.1.2011.6.122.20.1.1.2.1
		-- 1.3.6.1.4.1.2011.6.122.20.1.1.2.1
		hwServiceLinkEntry OBJECT-TYPE
			SYNTAX HwServiceLinkEntry
			MAX-ACCESS not-accessible
			STATUS current
			DESCRIPTION
				"The local link table entry"
			INDEX { hwServiceLinkIndex }
			::= { hwServiceLinkTable 1 }


		HwServiceLinkEntry ::=
			SEQUENCE {
				hwServiceLinkIndex
					Gauge32,
				hwServiceLinkType
					INTEGER,
				hwServiceLinkName
					OCTET STRING,
				hwServiceLinkInsideInterface
					OCTET STRING,
				hwServiceLinkOutsideInterface
					OCTET STRING,
				hwServiceLinkInsideInterfaceState
					INTEGER,
				hwServiceLinkOutsideInterfaceState
					INTEGER,
				hwServiceLinkInsideInterfaceBandWidth
					OCTET STRING,
				hwServiceLinkOutsideInterfaceBandWidth
					OCTET STRING,
				hwServiceLinkBoundGroupNumber
					Gauge32
			 }

--         1.3.6.1.4.1.2011.6.122.20.1.1.2.1.1
-- 1.3.6.1.4.1.2011.6.122.20.1.1.2.1.1
-- 1.3.6.1.4.1.2011.6.122.20.1.1.2.1.1
-- 1.3.6.1.4.1.2011.6.122.20.1.1.2.1.1
-- 1.3.6.1.4.1.2011.6.122.20.1.1.2.1.1
-- 1.3.6.1.4.1.2011.6.122.20.1.1.2.1.1
-- 1.3.6.1.4.1.2011.6.122.20.1.1.2.1.1
-- 1.3.6.1.4.1.2011.6.122.20.1.1.2.1.1
		-- 1.3.6.1.4.1.2011.6.122.20.1.1.2.1.1
		hwServiceLinkIndex OBJECT-TYPE
			SYNTAX Gauge32 (1..320)
			MAX-ACCESS not-accessible
			STATUS current
			DESCRIPTION
				"The number of the link"
			::= { hwServiceLinkEntry 1 }


--         1.3.6.1.4.1.2011.6.122.20.1.1.2.1.2
-- 1.3.6.1.4.1.2011.6.122.20.1.1.2.1.2
-- 1.3.6.1.4.1.2011.6.122.20.1.1.2.1.2
-- 1.3.6.1.4.1.2011.6.122.20.1.1.2.1.2
-- 1.3.6.1.4.1.2011.6.122.20.1.1.2.1.2
-- 1.3.6.1.4.1.2011.6.122.20.1.1.2.1.2
-- 1.3.6.1.4.1.2011.6.122.20.1.1.2.1.2
-- 1.3.6.1.4.1.2011.6.122.20.1.1.2.1.2
		-- 1.3.6.1.4.1.2011.6.122.20.1.1.2.1.2
		hwServiceLinkType OBJECT-TYPE
			SYNTAX INTEGER
				{
				oneg(1),
				twodotfiveg(2),
				teng(3),
				fortyg(4),
				onehundredg(5)
				}
			MAX-ACCESS read-only
			STATUS current
			DESCRIPTION
				"The type of the link"
			::= { hwServiceLinkEntry 2 }


--         1.3.6.1.4.1.2011.6.122.20.1.1.2.1.3
-- 1.3.6.1.4.1.2011.6.122.20.1.1.2.1.3
-- 1.3.6.1.4.1.2011.6.122.20.1.1.2.1.3
-- 1.3.6.1.4.1.2011.6.122.20.1.1.2.1.3
-- 1.3.6.1.4.1.2011.6.122.20.1.1.2.1.3
-- 1.3.6.1.4.1.2011.6.122.20.1.1.2.1.3
-- 1.3.6.1.4.1.2011.6.122.20.1.1.2.1.3
-- 1.3.6.1.4.1.2011.6.122.20.1.1.2.1.3
		-- 1.3.6.1.4.1.2011.6.122.20.1.1.2.1.3
		hwServiceLinkName OBJECT-TYPE
			SYNTAX OCTET STRING (SIZE (0..255))
			MAX-ACCESS read-only
			STATUS current
			DESCRIPTION
				"The name of the link"
			::= { hwServiceLinkEntry 3 }


--         1.3.6.1.4.1.2011.6.122.20.1.1.2.1.4
-- 1.3.6.1.4.1.2011.6.122.20.1.1.2.1.4
-- 1.3.6.1.4.1.2011.6.122.20.1.1.2.1.4
-- 1.3.6.1.4.1.2011.6.122.20.1.1.2.1.4
-- 1.3.6.1.4.1.2011.6.122.20.1.1.2.1.4
-- 1.3.6.1.4.1.2011.6.122.20.1.1.2.1.4
-- 1.3.6.1.4.1.2011.6.122.20.1.1.2.1.4
-- 1.3.6.1.4.1.2011.6.122.20.1.1.2.1.4
		-- 1.3.6.1.4.1.2011.6.122.20.1.1.2.1.4
		hwServiceLinkInsideInterface OBJECT-TYPE
			SYNTAX OCTET STRING (SIZE (0..255))
			MAX-ACCESS read-only
			STATUS current
			DESCRIPTION
				"The inside interface of the link"
			::= { hwServiceLinkEntry 4 }


--         1.3.6.1.4.1.2011.6.122.20.1.1.2.1.5
-- 1.3.6.1.4.1.2011.6.122.20.1.1.2.1.5
-- 1.3.6.1.4.1.2011.6.122.20.1.1.2.1.5
-- 1.3.6.1.4.1.2011.6.122.20.1.1.2.1.5
-- 1.3.6.1.4.1.2011.6.122.20.1.1.2.1.5
-- 1.3.6.1.4.1.2011.6.122.20.1.1.2.1.5
-- 1.3.6.1.4.1.2011.6.122.20.1.1.2.1.5
-- 1.3.6.1.4.1.2011.6.122.20.1.1.2.1.5
		-- 1.3.6.1.4.1.2011.6.122.20.1.1.2.1.5
		hwServiceLinkOutsideInterface OBJECT-TYPE
			SYNTAX OCTET STRING (SIZE (0..255))
			MAX-ACCESS read-only
			STATUS current
			DESCRIPTION
				"The state of the inside interface"
			::= { hwServiceLinkEntry 5 }


--         1.3.6.1.4.1.2011.6.122.20.1.1.2.1.6
-- 1.3.6.1.4.1.2011.6.122.20.1.1.2.1.6
-- 1.3.6.1.4.1.2011.6.122.20.1.1.2.1.6
-- 1.3.6.1.4.1.2011.6.122.20.1.1.2.1.6
-- 1.3.6.1.4.1.2011.6.122.20.1.1.2.1.6
-- 1.3.6.1.4.1.2011.6.122.20.1.1.2.1.6
-- 1.3.6.1.4.1.2011.6.122.20.1.1.2.1.6
-- 1.3.6.1.4.1.2011.6.122.20.1.1.2.1.6
		-- 1.3.6.1.4.1.2011.6.122.20.1.1.2.1.6
		hwServiceLinkInsideInterfaceState OBJECT-TYPE
			SYNTAX INTEGER
				{
				up(1),
				down(2)
				}
			MAX-ACCESS read-only
			STATUS current
			DESCRIPTION
				"The outside of the link"
			::= { hwServiceLinkEntry 6 }


--         1.3.6.1.4.1.2011.6.122.20.1.1.2.1.7
-- 1.3.6.1.4.1.2011.6.122.20.1.1.2.1.7
-- 1.3.6.1.4.1.2011.6.122.20.1.1.2.1.7
-- 1.3.6.1.4.1.2011.6.122.20.1.1.2.1.7
-- 1.3.6.1.4.1.2011.6.122.20.1.1.2.1.7
-- 1.3.6.1.4.1.2011.6.122.20.1.1.2.1.7
-- 1.3.6.1.4.1.2011.6.122.20.1.1.2.1.7
-- 1.3.6.1.4.1.2011.6.122.20.1.1.2.1.7
		-- 1.3.6.1.4.1.2011.6.122.20.1.1.2.1.7
		hwServiceLinkOutsideInterfaceState OBJECT-TYPE
			SYNTAX INTEGER
				{
				up(1),
				down(2)
				}
			MAX-ACCESS read-only
			STATUS current
			DESCRIPTION
				"The state of the outside interface"
			::= { hwServiceLinkEntry 7 }


--         1.3.6.1.4.1.2011.6.122.20.1.1.2.1.8
-- 1.3.6.1.4.1.2011.6.122.20.1.1.2.1.8
-- 1.3.6.1.4.1.2011.6.122.20.1.1.2.1.8
-- 1.3.6.1.4.1.2011.6.122.20.1.1.2.1.8
-- 1.3.6.1.4.1.2011.6.122.20.1.1.2.1.8
-- 1.3.6.1.4.1.2011.6.122.20.1.1.2.1.8
-- 1.3.6.1.4.1.2011.6.122.20.1.1.2.1.8
-- 1.3.6.1.4.1.2011.6.122.20.1.1.2.1.8
		-- 1.3.6.1.4.1.2011.6.122.20.1.1.2.1.8
		hwServiceLinkInsideInterfaceBandWidth OBJECT-TYPE
			SYNTAX OCTET STRING (SIZE (0..255))
			MAX-ACCESS read-only
			STATUS current
			DESCRIPTION
				"Description."
			::= { hwServiceLinkEntry 8 }


--         1.3.6.1.4.1.2011.6.122.20.1.1.2.1.9
-- 1.3.6.1.4.1.2011.6.122.20.1.1.2.1.9
-- 1.3.6.1.4.1.2011.6.122.20.1.1.2.1.9
-- 1.3.6.1.4.1.2011.6.122.20.1.1.2.1.9
-- 1.3.6.1.4.1.2011.6.122.20.1.1.2.1.9
-- 1.3.6.1.4.1.2011.6.122.20.1.1.2.1.9
-- 1.3.6.1.4.1.2011.6.122.20.1.1.2.1.9
-- 1.3.6.1.4.1.2011.6.122.20.1.1.2.1.9
		-- 1.3.6.1.4.1.2011.6.122.20.1.1.2.1.9
		hwServiceLinkOutsideInterfaceBandWidth OBJECT-TYPE
			SYNTAX OCTET STRING (SIZE (0..255))
			MAX-ACCESS read-only
			STATUS current
			DESCRIPTION
				"Description."
			::= { hwServiceLinkEntry 9 }


--         1.3.6.1.4.1.2011.6.122.20.1.1.2.1.10
-- 1.3.6.1.4.1.2011.6.122.20.1.1.2.1.10
-- 1.3.6.1.4.1.2011.6.122.20.1.1.2.1.10
-- 1.3.6.1.4.1.2011.6.122.20.1.1.2.1.10
-- 1.3.6.1.4.1.2011.6.122.20.1.1.2.1.10
-- 1.3.6.1.4.1.2011.6.122.20.1.1.2.1.10
-- 1.3.6.1.4.1.2011.6.122.20.1.1.2.1.10
-- 1.3.6.1.4.1.2011.6.122.20.1.1.2.1.10
		-- 1.3.6.1.4.1.2011.6.122.20.1.1.2.1.10
		hwServiceLinkBoundGroupNumber OBJECT-TYPE
			SYNTAX Gauge32 (0..320)
			MAX-ACCESS read-only
			STATUS current
			DESCRIPTION
				"Description."
			::= { hwServiceLinkEntry 10 }


--         1.3.6.1.4.1.2011.6.122.20.1.1.3
-- 1.3.6.1.4.1.2011.6.122.20.1.1.3
-- 1.3.6.1.4.1.2011.6.122.20.1.1.3
-- 1.3.6.1.4.1.2011.6.122.20.1.1.3
-- 1.3.6.1.4.1.2011.6.122.20.1.1.3
-- 1.3.6.1.4.1.2011.6.122.20.1.1.3
-- 1.3.6.1.4.1.2011.6.122.20.1.1.3
-- 1.3.6.1.4.1.2011.6.122.20.1.1.3
		-- 1.3.6.1.4.1.2011.6.122.20.1.1.3
		hwCascadeInterfaceTable OBJECT-TYPE
			SYNTAX SEQUENCE OF HwCascadeInterfaceEntry
			MAX-ACCESS not-accessible
			STATUS current
			DESCRIPTION
				"Description."
			::= { hwSANodeObject 3 }


--         1.3.6.1.4.1.2011.6.122.20.1.1.3.1
-- 1.3.6.1.4.1.2011.6.122.20.1.1.3.1
-- 1.3.6.1.4.1.2011.6.122.20.1.1.3.1
-- 1.3.6.1.4.1.2011.6.122.20.1.1.3.1
-- 1.3.6.1.4.1.2011.6.122.20.1.1.3.1
-- 1.3.6.1.4.1.2011.6.122.20.1.1.3.1
-- 1.3.6.1.4.1.2011.6.122.20.1.1.3.1
-- 1.3.6.1.4.1.2011.6.122.20.1.1.3.1
		-- 1.3.6.1.4.1.2011.6.122.20.1.1.3.1
		hwCascadeInterfaceEntry OBJECT-TYPE
			SYNTAX HwCascadeInterfaceEntry
			MAX-ACCESS not-accessible
			STATUS current
			DESCRIPTION
				"Description."
			INDEX { hwCascadeInterfaceIndex }
			::= { hwCascadeInterfaceTable 1 }


		HwCascadeInterfaceEntry ::=
			SEQUENCE {
				hwCascadeInterfaceIndex
					Gauge32,
				hwCascadeInterface
					OCTET STRING,
				hwCascadeInterfaceStatus
					OCTET STRING
			 }

--         1.3.6.1.4.1.2011.6.122.20.1.1.3.1.1
-- 1.3.6.1.4.1.2011.6.122.20.1.1.3.1.1
-- 1.3.6.1.4.1.2011.6.122.20.1.1.3.1.1
-- 1.3.6.1.4.1.2011.6.122.20.1.1.3.1.1
-- 1.3.6.1.4.1.2011.6.122.20.1.1.3.1.1
-- 1.3.6.1.4.1.2011.6.122.20.1.1.3.1.1
-- 1.3.6.1.4.1.2011.6.122.20.1.1.3.1.1
-- 1.3.6.1.4.1.2011.6.122.20.1.1.3.1.1
		-- 1.3.6.1.4.1.2011.6.122.20.1.1.3.1.1
		hwCascadeInterfaceIndex OBJECT-TYPE
			SYNTAX Gauge32 (1..12)
			MAX-ACCESS not-accessible
			STATUS current
			DESCRIPTION
				"Description."
			::= { hwCascadeInterfaceEntry 1 }


--         1.3.6.1.4.1.2011.6.122.20.1.1.3.1.2
-- 1.3.6.1.4.1.2011.6.122.20.1.1.3.1.2
-- 1.3.6.1.4.1.2011.6.122.20.1.1.3.1.2
-- 1.3.6.1.4.1.2011.6.122.20.1.1.3.1.2
-- 1.3.6.1.4.1.2011.6.122.20.1.1.3.1.2
-- 1.3.6.1.4.1.2011.6.122.20.1.1.3.1.2
-- 1.3.6.1.4.1.2011.6.122.20.1.1.3.1.2
-- 1.3.6.1.4.1.2011.6.122.20.1.1.3.1.2
		-- 1.3.6.1.4.1.2011.6.122.20.1.1.3.1.2
		hwCascadeInterface OBJECT-TYPE
			SYNTAX OCTET STRING
			MAX-ACCESS read-only
			STATUS current
			DESCRIPTION
				"Description."
			::= { hwCascadeInterfaceEntry 2 }


--         1.3.6.1.4.1.2011.6.122.20.1.1.3.1.3
-- 1.3.6.1.4.1.2011.6.122.20.1.1.3.1.3
-- 1.3.6.1.4.1.2011.6.122.20.1.1.3.1.3
-- 1.3.6.1.4.1.2011.6.122.20.1.1.3.1.3
-- 1.3.6.1.4.1.2011.6.122.20.1.1.3.1.3
-- 1.3.6.1.4.1.2011.6.122.20.1.1.3.1.3
-- 1.3.6.1.4.1.2011.6.122.20.1.1.3.1.3
-- 1.3.6.1.4.1.2011.6.122.20.1.1.3.1.3
		-- 1.3.6.1.4.1.2011.6.122.20.1.1.3.1.3
		hwCascadeInterfaceStatus OBJECT-TYPE
			SYNTAX OCTET STRING
			MAX-ACCESS read-only
			STATUS current
			DESCRIPTION
				"Description."
			::= { hwCascadeInterfaceEntry 3 }


--         1.3.6.1.4.1.2011.6.122.20.1.2
-- 1.3.6.1.4.1.2011.6.122.20.1.2
-- 1.3.6.1.4.1.2011.6.122.20.1.2
-- 1.3.6.1.4.1.2011.6.122.20.1.2
-- 1.3.6.1.4.1.2011.6.122.20.1.2
-- 1.3.6.1.4.1.2011.6.122.20.1.2
-- 1.3.6.1.4.1.2011.6.122.20.1.2
-- 1.3.6.1.4.1.2011.6.122.20.1.2
		-- 1.3.6.1.4.1.2011.6.122.20.1.2
		hwSANodeTraps OBJECT IDENTIFIER ::= { hwDeviceObject 2 }


--         1.3.6.1.4.1.2011.6.122.20.1.2.1
-- 1.3.6.1.4.1.2011.6.122.20.1.2.1
-- 1.3.6.1.4.1.2011.6.122.20.1.2.1
-- 1.3.6.1.4.1.2011.6.122.20.1.2.1
-- 1.3.6.1.4.1.2011.6.122.20.1.2.1
-- 1.3.6.1.4.1.2011.6.122.20.1.2.1
-- 1.3.6.1.4.1.2011.6.122.20.1.2.1
-- 1.3.6.1.4.1.2011.6.122.20.1.2.1
		-- 1.3.6.1.4.1.2011.6.122.20.1.2.1
		hwStateChangeToNormalTrap NOTIFICATION-TYPE
			OBJECTS { hwSpuSysInfoLocation, hwSpuSysInfoType, hwSpuSysInfoIPAddress }
			STATUS current
			DESCRIPTION
				"This object indicates that the status of an VSUF's CPU restores."
			::= { hwSANodeTraps 1 }


--         1.3.6.1.4.1.2011.6.122.20.1.2.2
-- 1.3.6.1.4.1.2011.6.122.20.1.2.2
-- 1.3.6.1.4.1.2011.6.122.20.1.2.2
-- 1.3.6.1.4.1.2011.6.122.20.1.2.2
-- 1.3.6.1.4.1.2011.6.122.20.1.2.2
-- 1.3.6.1.4.1.2011.6.122.20.1.2.2
-- 1.3.6.1.4.1.2011.6.122.20.1.2.2
-- 1.3.6.1.4.1.2011.6.122.20.1.2.2
		-- 1.3.6.1.4.1.2011.6.122.20.1.2.2
		hwStateChangeToAbnormalTrap NOTIFICATION-TYPE
			OBJECTS { hwSpuSysInfoLocation, hwSpuSysInfoType, hwSpuSysInfoIPAddress }
			STATUS current
			DESCRIPTION
				"This object indicates that an VSUF's CPU state becomes abnormal. Possible causes are as follows:
Cause 1: The VSUF's CPU is restarting.
Cause 2: The board in the current slot is not an VSUF."
			::= { hwSANodeTraps 2 }


--         1.3.6.1.4.1.2011.6.122.20.1.2.3
-- 1.3.6.1.4.1.2011.6.122.20.1.2.3
-- 1.3.6.1.4.1.2011.6.122.20.1.2.3
-- 1.3.6.1.4.1.2011.6.122.20.1.2.3
-- 1.3.6.1.4.1.2011.6.122.20.1.2.3
-- 1.3.6.1.4.1.2011.6.122.20.1.2.3
-- 1.3.6.1.4.1.2011.6.122.20.1.2.3
-- 1.3.6.1.4.1.2011.6.122.20.1.2.3
		-- 1.3.6.1.4.1.2011.6.122.20.1.2.3
		hwLinkBandWidthChangeToUnequalTrap NOTIFICATION-TYPE
			OBJECTS { hwServiceLinkInsideInterface, hwServiceLinkOutsideInterface, hwServiceLinkInsideInterfaceBandWidth, hwServiceLinkOutsideInterfaceBandWidth }
			STATUS current
			DESCRIPTION
				"Description."
			::= { hwSANodeTraps 3 }


--         1.3.6.1.4.1.2011.6.122.20.1.2.4
-- 1.3.6.1.4.1.2011.6.122.20.1.2.4
-- 1.3.6.1.4.1.2011.6.122.20.1.2.4
-- 1.3.6.1.4.1.2011.6.122.20.1.2.4
-- 1.3.6.1.4.1.2011.6.122.20.1.2.4
-- 1.3.6.1.4.1.2011.6.122.20.1.2.4
-- 1.3.6.1.4.1.2011.6.122.20.1.2.4
-- 1.3.6.1.4.1.2011.6.122.20.1.2.4
		-- 1.3.6.1.4.1.2011.6.122.20.1.2.4
		hwLinkBandWidthChangeToEqualTrap NOTIFICATION-TYPE
			OBJECTS { hwServiceLinkInsideInterface, hwServiceLinkOutsideInterface, hwServiceLinkInsideInterfaceBandWidth, hwServiceLinkOutsideInterfaceBandWidth }
			STATUS current
			DESCRIPTION
				"Description."
			::= { hwSANodeTraps 4 }


--         1.3.6.1.4.1.2011.6.122.20.1.2.5
-- 1.3.6.1.4.1.2011.6.122.20.1.2.5
-- 1.3.6.1.4.1.2011.6.122.20.1.2.5
-- 1.3.6.1.4.1.2011.6.122.20.1.2.5
-- 1.3.6.1.4.1.2011.6.122.20.1.2.5
-- 1.3.6.1.4.1.2011.6.122.20.1.2.5
-- 1.3.6.1.4.1.2011.6.122.20.1.2.5
-- 1.3.6.1.4.1.2011.6.122.20.1.2.5
		-- 1.3.6.1.4.1.2011.6.122.20.1.2.5
		hwLinkBoundGroupStateChangeToAbnormal NOTIFICATION-TYPE
			OBJECTS { hwServiceLinkBoundGroupNumber }
			STATUS current
			DESCRIPTION
				"This object indicates that a link-bound-group becomes abnormal because links in the group fail."
			::= { hwSANodeTraps 5 }


--         1.3.6.1.4.1.2011.6.122.20.1.2.6
-- 1.3.6.1.4.1.2011.6.122.20.1.2.6
-- 1.3.6.1.4.1.2011.6.122.20.1.2.6
-- 1.3.6.1.4.1.2011.6.122.20.1.2.6
-- 1.3.6.1.4.1.2011.6.122.20.1.2.6
-- 1.3.6.1.4.1.2011.6.122.20.1.2.6
-- 1.3.6.1.4.1.2011.6.122.20.1.2.6
-- 1.3.6.1.4.1.2011.6.122.20.1.2.6
		-- 1.3.6.1.4.1.2011.6.122.20.1.2.6
		hwLinkBoundGroupStateChangeToNormal NOTIFICATION-TYPE
			OBJECTS { hwServiceLinkBoundGroupNumber }
			STATUS current
			DESCRIPTION
				"This object indicates that a link group recovers."
			::= { hwSANodeTraps 6 }


--         1.3.6.1.4.1.2011.6.122.20.1.2.7
-- 1.3.6.1.4.1.2011.6.122.20.1.2.7
-- 1.3.6.1.4.1.2011.6.122.20.1.2.7
-- 1.3.6.1.4.1.2011.6.122.20.1.2.7
-- 1.3.6.1.4.1.2011.6.122.20.1.2.7
-- 1.3.6.1.4.1.2011.6.122.20.1.2.7
-- 1.3.6.1.4.1.2011.6.122.20.1.2.7
-- 1.3.6.1.4.1.2011.6.122.20.1.2.7
		-- 1.3.6.1.4.1.2011.6.122.20.1.2.7
		hwCascadeLinkStateChangeToAbnormal NOTIFICATION-TYPE
			OBJECTS { hwCascadeInterface }
			STATUS current
			DESCRIPTION
				"Description."
			::= { hwSANodeTraps 7 }


--         1.3.6.1.4.1.2011.6.122.20.1.2.8
-- 1.3.6.1.4.1.2011.6.122.20.1.2.8
-- 1.3.6.1.4.1.2011.6.122.20.1.2.8
-- 1.3.6.1.4.1.2011.6.122.20.1.2.8
-- 1.3.6.1.4.1.2011.6.122.20.1.2.8
-- 1.3.6.1.4.1.2011.6.122.20.1.2.8
-- 1.3.6.1.4.1.2011.6.122.20.1.2.8
-- 1.3.6.1.4.1.2011.6.122.20.1.2.8
		-- 1.3.6.1.4.1.2011.6.122.20.1.2.8
		hwCascadeLinkStateChangeToNormal NOTIFICATION-TYPE
			OBJECTS { hwCascadeInterface }
			STATUS current
			DESCRIPTION
				"Description."
			::= { hwSANodeTraps 8 }


--         1.3.6.1.4.1.2011.6.122.20.1.2.9
-- 1.3.6.1.4.1.2011.6.122.20.1.2.9
-- 1.3.6.1.4.1.2011.6.122.20.1.2.9
-- 1.3.6.1.4.1.2011.6.122.20.1.2.9
-- 1.3.6.1.4.1.2011.6.122.20.1.2.9
-- 1.3.6.1.4.1.2011.6.122.20.1.2.9
-- 1.3.6.1.4.1.2011.6.122.20.1.2.9
-- 1.3.6.1.4.1.2011.6.122.20.1.2.9
		-- 1.3.6.1.4.1.2011.6.122.20.1.2.9
		hwCascadeLinkOverloadTrap NOTIFICATION-TYPE
			OBJECTS { hwCascadeInterface }
			STATUS current
			DESCRIPTION
				"Description."
			::= { hwSANodeTraps 9 }


--         1.3.6.1.4.1.2011.6.122.20.1.3
-- 1.3.6.1.4.1.2011.6.122.20.1.3
-- 1.3.6.1.4.1.2011.6.122.20.1.3
-- 1.3.6.1.4.1.2011.6.122.20.1.3
-- 1.3.6.1.4.1.2011.6.122.20.1.3
-- 1.3.6.1.4.1.2011.6.122.20.1.3
-- 1.3.6.1.4.1.2011.6.122.20.1.3
-- 1.3.6.1.4.1.2011.6.122.20.1.3
		-- 1.3.6.1.4.1.2011.6.122.20.1.3
		hwSAClusterObject OBJECT IDENTIFIER ::= { hwDeviceObject 3 }


--         1.3.6.1.4.1.2011.6.122.20.1.3.1
-- 1.3.6.1.4.1.2011.6.122.20.1.3.1
-- 1.3.6.1.4.1.2011.6.122.20.1.3.1
-- 1.3.6.1.4.1.2011.6.122.20.1.3.1
-- 1.3.6.1.4.1.2011.6.122.20.1.3.1
-- 1.3.6.1.4.1.2011.6.122.20.1.3.1
-- 1.3.6.1.4.1.2011.6.122.20.1.3.1
-- 1.3.6.1.4.1.2011.6.122.20.1.3.1
		-- 1.3.6.1.4.1.2011.6.122.20.1.3.1
		hwClusterNodeTable OBJECT-TYPE
			SYNTAX SEQUENCE OF HwClusterNodeEntry
			MAX-ACCESS not-accessible
			STATUS current
			DESCRIPTION
				"Cluster node information table"
			::= { hwSAClusterObject 1 }


--         1.3.6.1.4.1.2011.6.122.20.1.3.1.1
-- 1.3.6.1.4.1.2011.6.122.20.1.3.1.1
-- 1.3.6.1.4.1.2011.6.122.20.1.3.1.1
-- 1.3.6.1.4.1.2011.6.122.20.1.3.1.1
-- 1.3.6.1.4.1.2011.6.122.20.1.3.1.1
-- 1.3.6.1.4.1.2011.6.122.20.1.3.1.1
-- 1.3.6.1.4.1.2011.6.122.20.1.3.1.1
-- 1.3.6.1.4.1.2011.6.122.20.1.3.1.1
		-- 1.3.6.1.4.1.2011.6.122.20.1.3.1.1
		hwClusterNodeEntry OBJECT-TYPE
			SYNTAX HwClusterNodeEntry
			MAX-ACCESS not-accessible
			STATUS current
			DESCRIPTION
				"Cluster node information table entry"
			INDEX { hwClusterNodeIndex }
			::= { hwClusterNodeTable 1 }


		HwClusterNodeEntry ::=
			SEQUENCE {
				hwClusterNodeIndex
					Integer32,
				hwClusterNodeName
					OCTET STRING,
				hwClusterNodeIPAddress
					IpAddress,
				hwClusterNodeRole
					INTEGER,
				hwClusterNodeStatus
					INTEGER,
				hwNormalSPSNumber
					Integer32,
				hwCascadeCfg
					OCTET STRING,
				hwCascadePeerState
					INTEGER,
				hwCascadeSelfState
					INTEGER
			 }

--         1.3.6.1.4.1.2011.6.122.20.1.3.1.1.1
-- 1.3.6.1.4.1.2011.6.122.20.1.3.1.1.1
-- 1.3.6.1.4.1.2011.6.122.20.1.3.1.1.1
-- 1.3.6.1.4.1.2011.6.122.20.1.3.1.1.1
-- 1.3.6.1.4.1.2011.6.122.20.1.3.1.1.1
-- 1.3.6.1.4.1.2011.6.122.20.1.3.1.1.1
-- 1.3.6.1.4.1.2011.6.122.20.1.3.1.1.1
-- 1.3.6.1.4.1.2011.6.122.20.1.3.1.1.1
		-- 1.3.6.1.4.1.2011.6.122.20.1.3.1.1.1
		hwClusterNodeIndex OBJECT-TYPE
			SYNTAX Integer32 (1..255)
			MAX-ACCESS not-accessible
			STATUS current
			DESCRIPTION
				"The number of SA node"
			::= { hwClusterNodeEntry 1 }


--         1.3.6.1.4.1.2011.6.122.20.1.3.1.1.2
-- 1.3.6.1.4.1.2011.6.122.20.1.3.1.1.2
-- 1.3.6.1.4.1.2011.6.122.20.1.3.1.1.2
-- 1.3.6.1.4.1.2011.6.122.20.1.3.1.1.2
-- 1.3.6.1.4.1.2011.6.122.20.1.3.1.1.2
-- 1.3.6.1.4.1.2011.6.122.20.1.3.1.1.2
-- 1.3.6.1.4.1.2011.6.122.20.1.3.1.1.2
-- 1.3.6.1.4.1.2011.6.122.20.1.3.1.1.2
		-- 1.3.6.1.4.1.2011.6.122.20.1.3.1.1.2
		hwClusterNodeName OBJECT-TYPE
			SYNTAX OCTET STRING (SIZE (0..255))
			MAX-ACCESS read-only
			STATUS current
			DESCRIPTION
				"The name of SA node"
			::= { hwClusterNodeEntry 2 }


--         1.3.6.1.4.1.2011.6.122.20.1.3.1.1.3
-- 1.3.6.1.4.1.2011.6.122.20.1.3.1.1.3
-- 1.3.6.1.4.1.2011.6.122.20.1.3.1.1.3
-- 1.3.6.1.4.1.2011.6.122.20.1.3.1.1.3
-- 1.3.6.1.4.1.2011.6.122.20.1.3.1.1.3
-- 1.3.6.1.4.1.2011.6.122.20.1.3.1.1.3
-- 1.3.6.1.4.1.2011.6.122.20.1.3.1.1.3
-- 1.3.6.1.4.1.2011.6.122.20.1.3.1.1.3
		-- 1.3.6.1.4.1.2011.6.122.20.1.3.1.1.3
		hwClusterNodeIPAddress OBJECT-TYPE
			SYNTAX IpAddress
			MAX-ACCESS read-only
			STATUS current
			DESCRIPTION
				"The IP address of SA node"
			::= { hwClusterNodeEntry 3 }


--         1.3.6.1.4.1.2011.6.122.20.1.3.1.1.4
-- 1.3.6.1.4.1.2011.6.122.20.1.3.1.1.4
-- 1.3.6.1.4.1.2011.6.122.20.1.3.1.1.4
-- 1.3.6.1.4.1.2011.6.122.20.1.3.1.1.4
-- 1.3.6.1.4.1.2011.6.122.20.1.3.1.1.4
-- 1.3.6.1.4.1.2011.6.122.20.1.3.1.1.4
-- 1.3.6.1.4.1.2011.6.122.20.1.3.1.1.4
-- 1.3.6.1.4.1.2011.6.122.20.1.3.1.1.4
		-- 1.3.6.1.4.1.2011.6.122.20.1.3.1.1.4
		hwClusterNodeRole OBJECT-TYPE
			SYNTAX INTEGER
				{
				master(1),
				slave(2),
				backup(3)
				}
			MAX-ACCESS read-only
			STATUS current
			DESCRIPTION
				"The role of SA node"
			::= { hwClusterNodeEntry 4 }


--         1.3.6.1.4.1.2011.6.122.20.1.3.1.1.5
-- 1.3.6.1.4.1.2011.6.122.20.1.3.1.1.5
-- 1.3.6.1.4.1.2011.6.122.20.1.3.1.1.5
-- 1.3.6.1.4.1.2011.6.122.20.1.3.1.1.5
-- 1.3.6.1.4.1.2011.6.122.20.1.3.1.1.5
-- 1.3.6.1.4.1.2011.6.122.20.1.3.1.1.5
-- 1.3.6.1.4.1.2011.6.122.20.1.3.1.1.5
-- 1.3.6.1.4.1.2011.6.122.20.1.3.1.1.5
		-- 1.3.6.1.4.1.2011.6.122.20.1.3.1.1.5
		hwClusterNodeStatus OBJECT-TYPE
			SYNTAX INTEGER
				{
				up(1),
				down(2),
				holdon(3)
				}
			MAX-ACCESS read-only
			STATUS current
			DESCRIPTION
				"The status of SA node"
			::= { hwClusterNodeEntry 5 }


--         1.3.6.1.4.1.2011.6.122.20.1.3.1.1.6
-- 1.3.6.1.4.1.2011.6.122.20.1.3.1.1.6
-- 1.3.6.1.4.1.2011.6.122.20.1.3.1.1.6
-- 1.3.6.1.4.1.2011.6.122.20.1.3.1.1.6
-- 1.3.6.1.4.1.2011.6.122.20.1.3.1.1.6
-- 1.3.6.1.4.1.2011.6.122.20.1.3.1.1.6
-- 1.3.6.1.4.1.2011.6.122.20.1.3.1.1.6
-- 1.3.6.1.4.1.2011.6.122.20.1.3.1.1.6
		-- 1.3.6.1.4.1.2011.6.122.20.1.3.1.1.6
		hwNormalSPSNumber OBJECT-TYPE
			SYNTAX Integer32 (0..64)
			MAX-ACCESS read-write
			STATUS current
			DESCRIPTION
				"Description."
			::= { hwClusterNodeEntry 6 }


--         1.3.6.1.4.1.2011.6.122.20.1.3.1.1.7
-- 1.3.6.1.4.1.2011.6.122.20.1.3.1.1.7
-- 1.3.6.1.4.1.2011.6.122.20.1.3.1.1.7
-- 1.3.6.1.4.1.2011.6.122.20.1.3.1.1.7
-- 1.3.6.1.4.1.2011.6.122.20.1.3.1.1.7
-- 1.3.6.1.4.1.2011.6.122.20.1.3.1.1.7
-- 1.3.6.1.4.1.2011.6.122.20.1.3.1.1.7
-- 1.3.6.1.4.1.2011.6.122.20.1.3.1.1.7
		-- 1.3.6.1.4.1.2011.6.122.20.1.3.1.1.7
		hwCascadeCfg OBJECT-TYPE
			SYNTAX OCTET STRING
			MAX-ACCESS read-write
			STATUS current
			DESCRIPTION
				"Description."
			::= { hwClusterNodeEntry 7 }


--         1.3.6.1.4.1.2011.6.122.20.1.3.1.1.8
-- 1.3.6.1.4.1.2011.6.122.20.1.3.1.1.8
-- 1.3.6.1.4.1.2011.6.122.20.1.3.1.1.8
-- 1.3.6.1.4.1.2011.6.122.20.1.3.1.1.8
-- 1.3.6.1.4.1.2011.6.122.20.1.3.1.1.8
-- 1.3.6.1.4.1.2011.6.122.20.1.3.1.1.8
-- 1.3.6.1.4.1.2011.6.122.20.1.3.1.1.8
-- 1.3.6.1.4.1.2011.6.122.20.1.3.1.1.8
		-- 1.3.6.1.4.1.2011.6.122.20.1.3.1.1.8
		hwCascadePeerState OBJECT-TYPE
			SYNTAX INTEGER
				{
				normal(1),
				abnormal(2)
				}
			MAX-ACCESS read-write
			STATUS current
			DESCRIPTION
				"Description."
			::= { hwClusterNodeEntry 8 }


--         1.3.6.1.4.1.2011.6.122.20.1.3.1.1.9
-- 1.3.6.1.4.1.2011.6.122.20.1.3.1.1.9
-- 1.3.6.1.4.1.2011.6.122.20.1.3.1.1.9
-- 1.3.6.1.4.1.2011.6.122.20.1.3.1.1.9
-- 1.3.6.1.4.1.2011.6.122.20.1.3.1.1.9
-- 1.3.6.1.4.1.2011.6.122.20.1.3.1.1.9
-- 1.3.6.1.4.1.2011.6.122.20.1.3.1.1.9
-- 1.3.6.1.4.1.2011.6.122.20.1.3.1.1.9
		-- 1.3.6.1.4.1.2011.6.122.20.1.3.1.1.9
		hwCascadeSelfState OBJECT-TYPE
			SYNTAX INTEGER
				{
				normal(1),
				abnormal(2)
				}
			MAX-ACCESS read-write
			STATUS current
			DESCRIPTION
				"Description."
			::= { hwClusterNodeEntry 9 }


--         1.3.6.1.4.1.2011.6.122.20.1.3.2
-- 1.3.6.1.4.1.2011.6.122.20.1.3.2
-- 1.3.6.1.4.1.2011.6.122.20.1.3.2
-- 1.3.6.1.4.1.2011.6.122.20.1.3.2
-- 1.3.6.1.4.1.2011.6.122.20.1.3.2
-- 1.3.6.1.4.1.2011.6.122.20.1.3.2
-- 1.3.6.1.4.1.2011.6.122.20.1.3.2
-- 1.3.6.1.4.1.2011.6.122.20.1.3.2
		-- 1.3.6.1.4.1.2011.6.122.20.1.3.2
		hwClusterSasTable OBJECT-TYPE
			SYNTAX SEQUENCE OF HwClusterSasEntry
			MAX-ACCESS not-accessible
			STATUS current
			DESCRIPTION
				"Cluster SAS information table"
			::= { hwSAClusterObject 2 }


--         1.3.6.1.4.1.2011.6.122.20.1.3.2.1
-- 1.3.6.1.4.1.2011.6.122.20.1.3.2.1
-- 1.3.6.1.4.1.2011.6.122.20.1.3.2.1
-- 1.3.6.1.4.1.2011.6.122.20.1.3.2.1
-- 1.3.6.1.4.1.2011.6.122.20.1.3.2.1
-- 1.3.6.1.4.1.2011.6.122.20.1.3.2.1
-- 1.3.6.1.4.1.2011.6.122.20.1.3.2.1
-- 1.3.6.1.4.1.2011.6.122.20.1.3.2.1
		-- 1.3.6.1.4.1.2011.6.122.20.1.3.2.1
		hwClusterSasEntry OBJECT-TYPE
			SYNTAX HwClusterSasEntry
			MAX-ACCESS not-accessible
			STATUS current
			DESCRIPTION
				"Cluster SAS information table entry"
			INDEX { hwClusterSasIndex }
			::= { hwClusterSasTable 1 }


		HwClusterSasEntry ::=
			SEQUENCE {
				hwClusterSasIndex
					Gauge32,
				hwClusterSasNodeNumber
					Integer32,
				hwClusterSasSysLocation
					OCTET STRING,
				hwClusterSasSysIPAddress
					IpAddress,
				hwClusterSasMode
					INTEGER
			 }

--         1.3.6.1.4.1.2011.6.122.20.1.3.2.1.1
-- 1.3.6.1.4.1.2011.6.122.20.1.3.2.1.1
-- 1.3.6.1.4.1.2011.6.122.20.1.3.2.1.1
-- 1.3.6.1.4.1.2011.6.122.20.1.3.2.1.1
-- 1.3.6.1.4.1.2011.6.122.20.1.3.2.1.1
-- 1.3.6.1.4.1.2011.6.122.20.1.3.2.1.1
-- 1.3.6.1.4.1.2011.6.122.20.1.3.2.1.1
-- 1.3.6.1.4.1.2011.6.122.20.1.3.2.1.1
		-- 1.3.6.1.4.1.2011.6.122.20.1.3.2.1.1
		hwClusterSasIndex OBJECT-TYPE
			SYNTAX Gauge32
			MAX-ACCESS not-accessible
			STATUS current
			DESCRIPTION
				"The index of the SAS"
			::= { hwClusterSasEntry 1 }


--         1.3.6.1.4.1.2011.6.122.20.1.3.2.1.2
-- 1.3.6.1.4.1.2011.6.122.20.1.3.2.1.2
-- 1.3.6.1.4.1.2011.6.122.20.1.3.2.1.2
-- 1.3.6.1.4.1.2011.6.122.20.1.3.2.1.2
-- 1.3.6.1.4.1.2011.6.122.20.1.3.2.1.2
-- 1.3.6.1.4.1.2011.6.122.20.1.3.2.1.2
-- 1.3.6.1.4.1.2011.6.122.20.1.3.2.1.2
-- 1.3.6.1.4.1.2011.6.122.20.1.3.2.1.2
		-- 1.3.6.1.4.1.2011.6.122.20.1.3.2.1.2
		hwClusterSasNodeNumber OBJECT-TYPE
			SYNTAX Integer32 (0..255)
			MAX-ACCESS read-only
			STATUS current
			DESCRIPTION
				"The device number"
			::= { hwClusterSasEntry 2 }


--         1.3.6.1.4.1.2011.6.122.20.1.3.2.1.3
-- 1.3.6.1.4.1.2011.6.122.20.1.3.2.1.3
-- 1.3.6.1.4.1.2011.6.122.20.1.3.2.1.3
-- 1.3.6.1.4.1.2011.6.122.20.1.3.2.1.3
-- 1.3.6.1.4.1.2011.6.122.20.1.3.2.1.3
-- 1.3.6.1.4.1.2011.6.122.20.1.3.2.1.3
-- 1.3.6.1.4.1.2011.6.122.20.1.3.2.1.3
-- 1.3.6.1.4.1.2011.6.122.20.1.3.2.1.3
		-- 1.3.6.1.4.1.2011.6.122.20.1.3.2.1.3
		hwClusterSasSysLocation OBJECT-TYPE
			SYNTAX OCTET STRING (SIZE (0..255))
			MAX-ACCESS read-only
			STATUS current
			DESCRIPTION
				"The SAS location in the device"
			::= { hwClusterSasEntry 3 }


--         1.3.6.1.4.1.2011.6.122.20.1.3.2.1.4
-- 1.3.6.1.4.1.2011.6.122.20.1.3.2.1.4
-- 1.3.6.1.4.1.2011.6.122.20.1.3.2.1.4
-- 1.3.6.1.4.1.2011.6.122.20.1.3.2.1.4
-- 1.3.6.1.4.1.2011.6.122.20.1.3.2.1.4
-- 1.3.6.1.4.1.2011.6.122.20.1.3.2.1.4
-- 1.3.6.1.4.1.2011.6.122.20.1.3.2.1.4
-- 1.3.6.1.4.1.2011.6.122.20.1.3.2.1.4
		-- 1.3.6.1.4.1.2011.6.122.20.1.3.2.1.4
		hwClusterSasSysIPAddress OBJECT-TYPE
			SYNTAX IpAddress
			MAX-ACCESS read-only
			STATUS current
			DESCRIPTION
				"The SAS IP address"
			::= { hwClusterSasEntry 4 }


--         1.3.6.1.4.1.2011.6.122.20.1.3.2.1.5
-- 1.3.6.1.4.1.2011.6.122.20.1.3.2.1.5
-- 1.3.6.1.4.1.2011.6.122.20.1.3.2.1.5
-- 1.3.6.1.4.1.2011.6.122.20.1.3.2.1.5
-- 1.3.6.1.4.1.2011.6.122.20.1.3.2.1.5
-- 1.3.6.1.4.1.2011.6.122.20.1.3.2.1.5
-- 1.3.6.1.4.1.2011.6.122.20.1.3.2.1.5
-- 1.3.6.1.4.1.2011.6.122.20.1.3.2.1.5
		-- 1.3.6.1.4.1.2011.6.122.20.1.3.2.1.5
		hwClusterSasMode OBJECT-TYPE
			SYNTAX INTEGER
				{
				active(1),
				standby(2),
				main(3),
				wait(4)
				}
			MAX-ACCESS read-only
			STATUS current
			DESCRIPTION
				"The status of SAS"
			::= { hwClusterSasEntry 5 }


--         1.3.6.1.4.1.2011.6.122.20.1.3.3
-- 1.3.6.1.4.1.2011.6.122.20.1.3.3
-- 1.3.6.1.4.1.2011.6.122.20.1.3.3
-- 1.3.6.1.4.1.2011.6.122.20.1.3.3
-- 1.3.6.1.4.1.2011.6.122.20.1.3.3
-- 1.3.6.1.4.1.2011.6.122.20.1.3.3
-- 1.3.6.1.4.1.2011.6.122.20.1.3.3
-- 1.3.6.1.4.1.2011.6.122.20.1.3.3
		-- 1.3.6.1.4.1.2011.6.122.20.1.3.3
		hwClusterMapTable OBJECT-TYPE
			SYNTAX SEQUENCE OF HwClusterMapEntry
			MAX-ACCESS not-accessible
			STATUS current
			DESCRIPTION
				"Cluster map information table"
			::= { hwSAClusterObject 3 }


--         1.3.6.1.4.1.2011.6.122.20.1.3.3.1
-- 1.3.6.1.4.1.2011.6.122.20.1.3.3.1
-- 1.3.6.1.4.1.2011.6.122.20.1.3.3.1
-- 1.3.6.1.4.1.2011.6.122.20.1.3.3.1
-- 1.3.6.1.4.1.2011.6.122.20.1.3.3.1
-- 1.3.6.1.4.1.2011.6.122.20.1.3.3.1
-- 1.3.6.1.4.1.2011.6.122.20.1.3.3.1
-- 1.3.6.1.4.1.2011.6.122.20.1.3.3.1
		-- 1.3.6.1.4.1.2011.6.122.20.1.3.3.1
		hwClusterMapEntry OBJECT-TYPE
			SYNTAX HwClusterMapEntry
			MAX-ACCESS not-accessible
			STATUS current
			DESCRIPTION
				"Map information table entry"
			INDEX { hwClusterMapSasIndex }
			::= { hwClusterMapTable 1 }


		HwClusterMapEntry ::=
			SEQUENCE {
				hwClusterMapSasIndex
					Gauge32,
				hwClusterMapSysSasMode
					INTEGER,
				hwClusterMapNumberOfDG
					Integer32,
				hwClusterMapDevices
					OCTET STRING
			 }

--         1.3.6.1.4.1.2011.6.122.20.1.3.3.1.1
-- 1.3.6.1.4.1.2011.6.122.20.1.3.3.1.1
-- 1.3.6.1.4.1.2011.6.122.20.1.3.3.1.1
-- 1.3.6.1.4.1.2011.6.122.20.1.3.3.1.1
-- 1.3.6.1.4.1.2011.6.122.20.1.3.3.1.1
-- 1.3.6.1.4.1.2011.6.122.20.1.3.3.1.1
-- 1.3.6.1.4.1.2011.6.122.20.1.3.3.1.1
-- 1.3.6.1.4.1.2011.6.122.20.1.3.3.1.1
		-- 1.3.6.1.4.1.2011.6.122.20.1.3.3.1.1
		hwClusterMapSasIndex OBJECT-TYPE
			SYNTAX Gauge32 (1..2147483647)
			MAX-ACCESS not-accessible
			STATUS current
			DESCRIPTION
				"The index of the SAS"
			::= { hwClusterMapEntry 1 }


--         1.3.6.1.4.1.2011.6.122.20.1.3.3.1.2
-- 1.3.6.1.4.1.2011.6.122.20.1.3.3.1.2
-- 1.3.6.1.4.1.2011.6.122.20.1.3.3.1.2
-- 1.3.6.1.4.1.2011.6.122.20.1.3.3.1.2
-- 1.3.6.1.4.1.2011.6.122.20.1.3.3.1.2
-- 1.3.6.1.4.1.2011.6.122.20.1.3.3.1.2
-- 1.3.6.1.4.1.2011.6.122.20.1.3.3.1.2
-- 1.3.6.1.4.1.2011.6.122.20.1.3.3.1.2
		-- 1.3.6.1.4.1.2011.6.122.20.1.3.3.1.2
		hwClusterMapSysSasMode OBJECT-TYPE
			SYNTAX INTEGER
				{
				active(1),
				standby(2),
				main(3)
				}
			MAX-ACCESS read-only
			STATUS current
			DESCRIPTION
				"The SAS mode"
			::= { hwClusterMapEntry 2 }


--         1.3.6.1.4.1.2011.6.122.20.1.3.3.1.3
-- 1.3.6.1.4.1.2011.6.122.20.1.3.3.1.3
-- 1.3.6.1.4.1.2011.6.122.20.1.3.3.1.3
-- 1.3.6.1.4.1.2011.6.122.20.1.3.3.1.3
-- 1.3.6.1.4.1.2011.6.122.20.1.3.3.1.3
-- 1.3.6.1.4.1.2011.6.122.20.1.3.3.1.3
-- 1.3.6.1.4.1.2011.6.122.20.1.3.3.1.3
-- 1.3.6.1.4.1.2011.6.122.20.1.3.3.1.3
		-- 1.3.6.1.4.1.2011.6.122.20.1.3.3.1.3
		hwClusterMapNumberOfDG OBJECT-TYPE
			SYNTAX Integer32 (1..1024)
			MAX-ACCESS read-only
			STATUS current
			DESCRIPTION
				"The domain group number"
			::= { hwClusterMapEntry 3 }


--         1.3.6.1.4.1.2011.6.122.20.1.3.3.1.4
-- 1.3.6.1.4.1.2011.6.122.20.1.3.3.1.4
-- 1.3.6.1.4.1.2011.6.122.20.1.3.3.1.4
-- 1.3.6.1.4.1.2011.6.122.20.1.3.3.1.4
-- 1.3.6.1.4.1.2011.6.122.20.1.3.3.1.4
-- 1.3.6.1.4.1.2011.6.122.20.1.3.3.1.4
-- 1.3.6.1.4.1.2011.6.122.20.1.3.3.1.4
-- 1.3.6.1.4.1.2011.6.122.20.1.3.3.1.4
		-- 1.3.6.1.4.1.2011.6.122.20.1.3.3.1.4
		hwClusterMapDevices OBJECT-TYPE
			SYNTAX OCTET STRING (SIZE (0..255))
			MAX-ACCESS read-only
			STATUS current
			DESCRIPTION
				"Description."
			::= { hwClusterMapEntry 4 }


--         1.3.6.1.4.1.2011.6.122.20.1.3.4
-- 1.3.6.1.4.1.2011.6.122.20.1.3.4
-- 1.3.6.1.4.1.2011.6.122.20.1.3.4
-- 1.3.6.1.4.1.2011.6.122.20.1.3.4
-- 1.3.6.1.4.1.2011.6.122.20.1.3.4
-- 1.3.6.1.4.1.2011.6.122.20.1.3.4
-- 1.3.6.1.4.1.2011.6.122.20.1.3.4
-- 1.3.6.1.4.1.2011.6.122.20.1.3.4
		-- 1.3.6.1.4.1.2011.6.122.20.1.3.4
		hwComponentTable OBJECT-TYPE
			SYNTAX SEQUENCE OF HwComponentEntry
			MAX-ACCESS not-accessible
			STATUS current
			DESCRIPTION
				"The resource table"
			::= { hwSAClusterObject 4 }


--         1.3.6.1.4.1.2011.6.122.20.1.3.4.1
-- 1.3.6.1.4.1.2011.6.122.20.1.3.4.1
-- 1.3.6.1.4.1.2011.6.122.20.1.3.4.1
-- 1.3.6.1.4.1.2011.6.122.20.1.3.4.1
-- 1.3.6.1.4.1.2011.6.122.20.1.3.4.1
-- 1.3.6.1.4.1.2011.6.122.20.1.3.4.1
-- 1.3.6.1.4.1.2011.6.122.20.1.3.4.1
-- 1.3.6.1.4.1.2011.6.122.20.1.3.4.1
		-- 1.3.6.1.4.1.2011.6.122.20.1.3.4.1
		hwComponentEntry OBJECT-TYPE
			SYNTAX HwComponentEntry
			MAX-ACCESS not-accessible
			STATUS current
			DESCRIPTION
				"The resource table entry"
			INDEX { hwComponentIndex }
			::= { hwComponentTable 1 }


		HwComponentEntry ::=
			SEQUENCE {
				hwComponentIndex
					Integer32,
				hwComponentType
					INTEGER,
				hwComponentNumber
					Integer32,
				hwComponentName
					OCTET STRING,
				hwComponentPrimaryIPAddress
					IpAddress,
				hwComponenSecondaryIPAddress
					IpAddress,
				hwComponentPriIPConnStatus
					INTEGER,
				hwComponentSecIPConnStatus
					INTEGER,
				hwComponentUsageMode
					INTEGER
			 }

--         1.3.6.1.4.1.2011.6.122.20.1.3.4.1.1
-- 1.3.6.1.4.1.2011.6.122.20.1.3.4.1.1
-- 1.3.6.1.4.1.2011.6.122.20.1.3.4.1.1
-- 1.3.6.1.4.1.2011.6.122.20.1.3.4.1.1
-- 1.3.6.1.4.1.2011.6.122.20.1.3.4.1.1
-- 1.3.6.1.4.1.2011.6.122.20.1.3.4.1.1
-- 1.3.6.1.4.1.2011.6.122.20.1.3.4.1.1
-- 1.3.6.1.4.1.2011.6.122.20.1.3.4.1.1
		-- 1.3.6.1.4.1.2011.6.122.20.1.3.4.1.1
		hwComponentIndex OBJECT-TYPE
			SYNTAX Integer32 (1..2147483647)
			MAX-ACCESS not-accessible
			STATUS current
			DESCRIPTION
				"The resource index"
			::= { hwComponentEntry 1 }


--         1.3.6.1.4.1.2011.6.122.20.1.3.4.1.2
-- 1.3.6.1.4.1.2011.6.122.20.1.3.4.1.2
-- 1.3.6.1.4.1.2011.6.122.20.1.3.4.1.2
-- 1.3.6.1.4.1.2011.6.122.20.1.3.4.1.2
-- 1.3.6.1.4.1.2011.6.122.20.1.3.4.1.2
-- 1.3.6.1.4.1.2011.6.122.20.1.3.4.1.2
-- 1.3.6.1.4.1.2011.6.122.20.1.3.4.1.2
-- 1.3.6.1.4.1.2011.6.122.20.1.3.4.1.2
		-- 1.3.6.1.4.1.2011.6.122.20.1.3.4.1.2
		hwComponentType OBJECT-TYPE
			SYNTAX INTEGER
				{
				dataanalysisserver(2),
				policyserver(3),
				managementserver(4),
				serviceprobesystem(5),
				serviceanalysesystem(6),
				radiusproxy(7),
				updateserver(8),
				urlhealthcenter(9),
				onlinechargingsystem(10),
				policyandchargingrulesfunction(11),
				quotamanagementserver(13)
				}
			MAX-ACCESS read-only
			STATUS current
			DESCRIPTION
				"The resource type"
			::= { hwComponentEntry 2 }


--         1.3.6.1.4.1.2011.6.122.20.1.3.4.1.3
-- 1.3.6.1.4.1.2011.6.122.20.1.3.4.1.3
-- 1.3.6.1.4.1.2011.6.122.20.1.3.4.1.3
-- 1.3.6.1.4.1.2011.6.122.20.1.3.4.1.3
-- 1.3.6.1.4.1.2011.6.122.20.1.3.4.1.3
-- 1.3.6.1.4.1.2011.6.122.20.1.3.4.1.3
-- 1.3.6.1.4.1.2011.6.122.20.1.3.4.1.3
-- 1.3.6.1.4.1.2011.6.122.20.1.3.4.1.3
		-- 1.3.6.1.4.1.2011.6.122.20.1.3.4.1.3
		hwComponentNumber OBJECT-TYPE
			SYNTAX Integer32
			MAX-ACCESS read-only
			STATUS current
			DESCRIPTION
				"The resource number"
			::= { hwComponentEntry 3 }


--         1.3.6.1.4.1.2011.6.122.20.1.3.4.1.4
-- 1.3.6.1.4.1.2011.6.122.20.1.3.4.1.4
-- 1.3.6.1.4.1.2011.6.122.20.1.3.4.1.4
-- 1.3.6.1.4.1.2011.6.122.20.1.3.4.1.4
-- 1.3.6.1.4.1.2011.6.122.20.1.3.4.1.4
-- 1.3.6.1.4.1.2011.6.122.20.1.3.4.1.4
-- 1.3.6.1.4.1.2011.6.122.20.1.3.4.1.4
-- 1.3.6.1.4.1.2011.6.122.20.1.3.4.1.4
		-- 1.3.6.1.4.1.2011.6.122.20.1.3.4.1.4
		hwComponentName OBJECT-TYPE
			SYNTAX OCTET STRING (SIZE (0..255))
			MAX-ACCESS read-only
			STATUS current
			DESCRIPTION
				"The name of the resouce"
			::= { hwComponentEntry 4 }


--         1.3.6.1.4.1.2011.6.122.20.1.3.4.1.5
-- 1.3.6.1.4.1.2011.6.122.20.1.3.4.1.5
-- 1.3.6.1.4.1.2011.6.122.20.1.3.4.1.5
-- 1.3.6.1.4.1.2011.6.122.20.1.3.4.1.5
-- 1.3.6.1.4.1.2011.6.122.20.1.3.4.1.5
-- 1.3.6.1.4.1.2011.6.122.20.1.3.4.1.5
-- 1.3.6.1.4.1.2011.6.122.20.1.3.4.1.5
-- 1.3.6.1.4.1.2011.6.122.20.1.3.4.1.5
		-- 1.3.6.1.4.1.2011.6.122.20.1.3.4.1.5
		hwComponentPrimaryIPAddress OBJECT-TYPE
			SYNTAX IpAddress
			MAX-ACCESS read-only
			STATUS current
			DESCRIPTION
				"The IP address of the resource"
			::= { hwComponentEntry 5 }


--         1.3.6.1.4.1.2011.6.122.20.1.3.4.1.6
-- 1.3.6.1.4.1.2011.6.122.20.1.3.4.1.6
-- 1.3.6.1.4.1.2011.6.122.20.1.3.4.1.6
-- 1.3.6.1.4.1.2011.6.122.20.1.3.4.1.6
-- 1.3.6.1.4.1.2011.6.122.20.1.3.4.1.6
-- 1.3.6.1.4.1.2011.6.122.20.1.3.4.1.6
-- 1.3.6.1.4.1.2011.6.122.20.1.3.4.1.6
-- 1.3.6.1.4.1.2011.6.122.20.1.3.4.1.6
		-- 1.3.6.1.4.1.2011.6.122.20.1.3.4.1.6
		hwComponenSecondaryIPAddress OBJECT-TYPE
			SYNTAX IpAddress
			MAX-ACCESS read-write
			STATUS current
			DESCRIPTION
				"Description."
			::= { hwComponentEntry 6 }


--         1.3.6.1.4.1.2011.6.122.20.1.3.4.1.7
-- 1.3.6.1.4.1.2011.6.122.20.1.3.4.1.7
-- 1.3.6.1.4.1.2011.6.122.20.1.3.4.1.7
-- 1.3.6.1.4.1.2011.6.122.20.1.3.4.1.7
-- 1.3.6.1.4.1.2011.6.122.20.1.3.4.1.7
-- 1.3.6.1.4.1.2011.6.122.20.1.3.4.1.7
-- 1.3.6.1.4.1.2011.6.122.20.1.3.4.1.7
-- 1.3.6.1.4.1.2011.6.122.20.1.3.4.1.7
		-- 1.3.6.1.4.1.2011.6.122.20.1.3.4.1.7
		hwComponentPriIPConnStatus OBJECT-TYPE
			SYNTAX INTEGER
				{
				up(1),
				down(2)
				}
			MAX-ACCESS read-only
			STATUS current
			DESCRIPTION
				"The connection status with OMC"
			::= { hwComponentEntry 7 }


--         1.3.6.1.4.1.2011.6.122.20.1.3.4.1.8
-- 1.3.6.1.4.1.2011.6.122.20.1.3.4.1.8
-- 1.3.6.1.4.1.2011.6.122.20.1.3.4.1.8
-- 1.3.6.1.4.1.2011.6.122.20.1.3.4.1.8
-- 1.3.6.1.4.1.2011.6.122.20.1.3.4.1.8
-- 1.3.6.1.4.1.2011.6.122.20.1.3.4.1.8
-- 1.3.6.1.4.1.2011.6.122.20.1.3.4.1.8
-- 1.3.6.1.4.1.2011.6.122.20.1.3.4.1.8
		-- 1.3.6.1.4.1.2011.6.122.20.1.3.4.1.8
		hwComponentSecIPConnStatus OBJECT-TYPE
			SYNTAX INTEGER
				{
				up(1),
				down(2)
				}
			MAX-ACCESS read-write
			STATUS current
			DESCRIPTION
				"Description."
			::= { hwComponentEntry 8 }


--         1.3.6.1.4.1.2011.6.122.20.1.3.4.1.9
-- 1.3.6.1.4.1.2011.6.122.20.1.3.4.1.9
-- 1.3.6.1.4.1.2011.6.122.20.1.3.4.1.9
-- 1.3.6.1.4.1.2011.6.122.20.1.3.4.1.9
-- 1.3.6.1.4.1.2011.6.122.20.1.3.4.1.9
-- 1.3.6.1.4.1.2011.6.122.20.1.3.4.1.9
-- 1.3.6.1.4.1.2011.6.122.20.1.3.4.1.9
-- 1.3.6.1.4.1.2011.6.122.20.1.3.4.1.9
		-- 1.3.6.1.4.1.2011.6.122.20.1.3.4.1.9
		hwComponentUsageMode OBJECT-TYPE
			SYNTAX INTEGER
				{
				active(1),
				standby(2),
				main(3),
				wait(4),
				inactive(5)
				}
			MAX-ACCESS read-only
			STATUS current
			DESCRIPTION
				"The usage mode of the resouce"
			::= { hwComponentEntry 9 }


--         1.3.6.1.4.1.2011.6.122.20.1.4
-- 1.3.6.1.4.1.2011.6.122.20.1.4
-- 1.3.6.1.4.1.2011.6.122.20.1.4
-- 1.3.6.1.4.1.2011.6.122.20.1.4
-- 1.3.6.1.4.1.2011.6.122.20.1.4
-- 1.3.6.1.4.1.2011.6.122.20.1.4
-- 1.3.6.1.4.1.2011.6.122.20.1.4
-- 1.3.6.1.4.1.2011.6.122.20.1.4
		-- 1.3.6.1.4.1.2011.6.122.20.1.4
		hwClusterTraps OBJECT IDENTIFIER ::= { hwDeviceObject 4 }


--         1.3.6.1.4.1.2011.6.122.20.1.4.1
-- 1.3.6.1.4.1.2011.6.122.20.1.4.1
-- 1.3.6.1.4.1.2011.6.122.20.1.4.1
-- 1.3.6.1.4.1.2011.6.122.20.1.4.1
-- 1.3.6.1.4.1.2011.6.122.20.1.4.1
-- 1.3.6.1.4.1.2011.6.122.20.1.4.1
-- 1.3.6.1.4.1.2011.6.122.20.1.4.1
-- 1.3.6.1.4.1.2011.6.122.20.1.4.1
		-- 1.3.6.1.4.1.2011.6.122.20.1.4.1
		hwPeerNodeConnectDownTrap NOTIFICATION-TYPE
			OBJECTS { hwClusterNodeName, hwClusterNodeIPAddress, hwClusterNodeRole }
			STATUS current
			DESCRIPTION
				"The connection whih peer OMC became down"
			::= { hwClusterTraps 1 }


--         1.3.6.1.4.1.2011.6.122.20.1.4.2
-- 1.3.6.1.4.1.2011.6.122.20.1.4.2
-- 1.3.6.1.4.1.2011.6.122.20.1.4.2
-- 1.3.6.1.4.1.2011.6.122.20.1.4.2
-- 1.3.6.1.4.1.2011.6.122.20.1.4.2
-- 1.3.6.1.4.1.2011.6.122.20.1.4.2
-- 1.3.6.1.4.1.2011.6.122.20.1.4.2
-- 1.3.6.1.4.1.2011.6.122.20.1.4.2
		-- 1.3.6.1.4.1.2011.6.122.20.1.4.2
		hwPeerNodeConnectUpTrap NOTIFICATION-TYPE
			OBJECTS { hwClusterNodeName, hwClusterNodeIPAddress, hwClusterNodeRole }
			STATUS current
			DESCRIPTION
				"The connection whih peer OMC became down"
			::= { hwClusterTraps 2 }


--         1.3.6.1.4.1.2011.6.122.20.1.4.3
-- 1.3.6.1.4.1.2011.6.122.20.1.4.3
-- 1.3.6.1.4.1.2011.6.122.20.1.4.3
-- 1.3.6.1.4.1.2011.6.122.20.1.4.3
-- 1.3.6.1.4.1.2011.6.122.20.1.4.3
-- 1.3.6.1.4.1.2011.6.122.20.1.4.3
-- 1.3.6.1.4.1.2011.6.122.20.1.4.3
-- 1.3.6.1.4.1.2011.6.122.20.1.4.3
		-- 1.3.6.1.4.1.2011.6.122.20.1.4.3
		hwNodeModeChangeActiveTrap NOTIFICATION-TYPE
			OBJECTS { hwClusterNodeName, hwClusterNodeIPAddress }
			STATUS current
			DESCRIPTION
				"OMC change to active"
			::= { hwClusterTraps 3 }


--         1.3.6.1.4.1.2011.6.122.20.1.4.4
-- 1.3.6.1.4.1.2011.6.122.20.1.4.4
-- 1.3.6.1.4.1.2011.6.122.20.1.4.4
-- 1.3.6.1.4.1.2011.6.122.20.1.4.4
-- 1.3.6.1.4.1.2011.6.122.20.1.4.4
-- 1.3.6.1.4.1.2011.6.122.20.1.4.4
-- 1.3.6.1.4.1.2011.6.122.20.1.4.4
-- 1.3.6.1.4.1.2011.6.122.20.1.4.4
		-- 1.3.6.1.4.1.2011.6.122.20.1.4.4
		hwNodeModeChangeStandbyTrap NOTIFICATION-TYPE
			OBJECTS { hwClusterNodeName, hwClusterNodeIPAddress }
			STATUS current
			DESCRIPTION
				"OMC change to standby"
			::= { hwClusterTraps 4 }


--         1.3.6.1.4.1.2011.6.122.20.1.4.5
-- 1.3.6.1.4.1.2011.6.122.20.1.4.5
-- 1.3.6.1.4.1.2011.6.122.20.1.4.5
-- 1.3.6.1.4.1.2011.6.122.20.1.4.5
-- 1.3.6.1.4.1.2011.6.122.20.1.4.5
-- 1.3.6.1.4.1.2011.6.122.20.1.4.5
-- 1.3.6.1.4.1.2011.6.122.20.1.4.5
-- 1.3.6.1.4.1.2011.6.122.20.1.4.5
		-- 1.3.6.1.4.1.2011.6.122.20.1.4.5
		hwNodeCompConnectUpTrap NOTIFICATION-TYPE
			OBJECTS { hwComponentType, hwComponentNumber, hwComponentName, hwComponentPrimaryIPAddress, hwComponenSecondaryIPAddress,
				hwComponentUsageMode }
			STATUS current
			DESCRIPTION
				"This object indicates that the connection between the master OMC and a back-end component restores."
			::= { hwClusterTraps 5 }


--         1.3.6.1.4.1.2011.6.122.20.1.4.6
-- 1.3.6.1.4.1.2011.6.122.20.1.4.6
-- 1.3.6.1.4.1.2011.6.122.20.1.4.6
-- 1.3.6.1.4.1.2011.6.122.20.1.4.6
-- 1.3.6.1.4.1.2011.6.122.20.1.4.6
-- 1.3.6.1.4.1.2011.6.122.20.1.4.6
-- 1.3.6.1.4.1.2011.6.122.20.1.4.6
-- 1.3.6.1.4.1.2011.6.122.20.1.4.6
		-- 1.3.6.1.4.1.2011.6.122.20.1.4.6
		hwNodeCompConnectDownTrap NOTIFICATION-TYPE
			OBJECTS { hwComponentType, hwComponentNumber, hwComponentName, hwComponentPrimaryIPAddress, hwComponenSecondaryIPAddress,
				hwComponentUsageMode }
			STATUS current
			DESCRIPTION
				"This object indicates that the connection between the master OMC and a back-end component fails. Possible causes are as follows:
Cause 1: The back-end component fails.
Cause 2: The network between the master OMC and a back-end component fails."
			::= { hwClusterTraps 6 }


--         1.3.6.1.4.1.2011.6.122.20.1.4.7
-- 1.3.6.1.4.1.2011.6.122.20.1.4.7
-- 1.3.6.1.4.1.2011.6.122.20.1.4.7
-- 1.3.6.1.4.1.2011.6.122.20.1.4.7
-- 1.3.6.1.4.1.2011.6.122.20.1.4.7
-- 1.3.6.1.4.1.2011.6.122.20.1.4.7
-- 1.3.6.1.4.1.2011.6.122.20.1.4.7
-- 1.3.6.1.4.1.2011.6.122.20.1.4.7
		-- 1.3.6.1.4.1.2011.6.122.20.1.4.7
		hwConfigurationInconsistentTrap NOTIFICATION-TYPE
			OBJECTS { hwClusterNodeName, hwClusterNodeIPAddress }
			STATUS current
			DESCRIPTION
				"Description."
			::= { hwClusterTraps 7 }


--         1.3.6.1.4.1.2011.6.122.20.1.4.8
-- 1.3.6.1.4.1.2011.6.122.20.1.4.8
-- 1.3.6.1.4.1.2011.6.122.20.1.4.8
-- 1.3.6.1.4.1.2011.6.122.20.1.4.8
-- 1.3.6.1.4.1.2011.6.122.20.1.4.8
-- 1.3.6.1.4.1.2011.6.122.20.1.4.8
-- 1.3.6.1.4.1.2011.6.122.20.1.4.8
-- 1.3.6.1.4.1.2011.6.122.20.1.4.8
		-- 1.3.6.1.4.1.2011.6.122.20.1.4.8
		hwSPSAmountInsufficientTrap NOTIFICATION-TYPE
			OBJECTS { hwClusterNodeName, hwClusterNodeIPAddress, hwNormalSPSNumber }
			STATUS current
			DESCRIPTION
				"Description."
			::= { hwClusterTraps 8 }


--         1.3.6.1.4.1.2011.6.122.20.1.4.9
-- 1.3.6.1.4.1.2011.6.122.20.1.4.9
-- 1.3.6.1.4.1.2011.6.122.20.1.4.9
-- 1.3.6.1.4.1.2011.6.122.20.1.4.9
-- 1.3.6.1.4.1.2011.6.122.20.1.4.9
-- 1.3.6.1.4.1.2011.6.122.20.1.4.9
-- 1.3.6.1.4.1.2011.6.122.20.1.4.9
-- 1.3.6.1.4.1.2011.6.122.20.1.4.9
		-- 1.3.6.1.4.1.2011.6.122.20.1.4.9
		hwSPSAmountSufficientTrap NOTIFICATION-TYPE
			OBJECTS { hwClusterNodeName, hwClusterNodeIPAddress, hwNormalSPSNumber }
			STATUS current
			DESCRIPTION
				"Description."
			::= { hwClusterTraps 9 }


--         1.3.6.1.4.1.2011.6.122.20.1.4.10
-- 1.3.6.1.4.1.2011.6.122.20.1.4.10
-- 1.3.6.1.4.1.2011.6.122.20.1.4.10
-- 1.3.6.1.4.1.2011.6.122.20.1.4.10
-- 1.3.6.1.4.1.2011.6.122.20.1.4.10
-- 1.3.6.1.4.1.2011.6.122.20.1.4.10
-- 1.3.6.1.4.1.2011.6.122.20.1.4.10
-- 1.3.6.1.4.1.2011.6.122.20.1.4.10
		-- 1.3.6.1.4.1.2011.6.122.20.1.4.10
		hwCascadeFailedTrap NOTIFICATION-TYPE
			OBJECTS { hwClusterNodeName, hwClusterNodeIPAddress, hwCascadeCfg, hwCascadePeerState, hwCascadeSelfState
				 }
			STATUS current
			DESCRIPTION
				"Description."
			::= { hwClusterTraps 10 }


--         1.3.6.1.4.1.2011.6.122.20.1.4.11
-- 1.3.6.1.4.1.2011.6.122.20.1.4.11
-- 1.3.6.1.4.1.2011.6.122.20.1.4.11
-- 1.3.6.1.4.1.2011.6.122.20.1.4.11
-- 1.3.6.1.4.1.2011.6.122.20.1.4.11
-- 1.3.6.1.4.1.2011.6.122.20.1.4.11
-- 1.3.6.1.4.1.2011.6.122.20.1.4.11
-- 1.3.6.1.4.1.2011.6.122.20.1.4.11
		-- 1.3.6.1.4.1.2011.6.122.20.1.4.11
		hwCascadeSuccessfulTrap NOTIFICATION-TYPE
			OBJECTS { hwClusterNodeName, hwClusterNodeIPAddress, hwCascadeCfg, hwCascadePeerState, hwCascadeSelfState
				 }
			STATUS current
			DESCRIPTION
				"Description."
			::= { hwClusterTraps 11 }


--         1.3.6.1.4.1.2011.6.122.20.1.4.12
-- 1.3.6.1.4.1.2011.6.122.20.1.4.12
-- 1.3.6.1.4.1.2011.6.122.20.1.4.12
-- 1.3.6.1.4.1.2011.6.122.20.1.4.12
-- 1.3.6.1.4.1.2011.6.122.20.1.4.12
-- 1.3.6.1.4.1.2011.6.122.20.1.4.12
-- 1.3.6.1.4.1.2011.6.122.20.1.4.12
-- 1.3.6.1.4.1.2011.6.122.20.1.4.12
		-- 1.3.6.1.4.1.2011.6.122.20.1.4.12
		hwHotBackupConfigurationCheckFailTrap NOTIFICATION-TYPE
			OBJECTS { hwClusterNodeName, hwClusterNodeIPAddress }
			STATUS current
			DESCRIPTION
				"Description."
			::= { hwClusterTraps 12 }


--         1.3.6.1.4.1.2011.6.122.20.1.5
-- 1.3.6.1.4.1.2011.6.122.20.1.5
-- 1.3.6.1.4.1.2011.6.122.20.1.5
-- 1.3.6.1.4.1.2011.6.122.20.1.5
-- 1.3.6.1.4.1.2011.6.122.20.1.5
-- 1.3.6.1.4.1.2011.6.122.20.1.5
-- 1.3.6.1.4.1.2011.6.122.20.1.5
-- 1.3.6.1.4.1.2011.6.122.20.1.5
		-- 1.3.6.1.4.1.2011.6.122.20.1.5
		hwInternBypassObject OBJECT IDENTIFIER ::= { hwDeviceObject 5 }


--         1.3.6.1.4.1.2011.6.122.20.1.5.1
-- 1.3.6.1.4.1.2011.6.122.20.1.5.1
-- 1.3.6.1.4.1.2011.6.122.20.1.5.1
-- 1.3.6.1.4.1.2011.6.122.20.1.5.1
-- 1.3.6.1.4.1.2011.6.122.20.1.5.1
-- 1.3.6.1.4.1.2011.6.122.20.1.5.1
-- 1.3.6.1.4.1.2011.6.122.20.1.5.1
-- 1.3.6.1.4.1.2011.6.122.20.1.5.1
		-- 1.3.6.1.4.1.2011.6.122.20.1.5.1
		hwBypassLinkStateTable OBJECT-TYPE
			SYNTAX SEQUENCE OF HwBypassLinkStateEntry
			MAX-ACCESS not-accessible
			STATUS current
			DESCRIPTION
				"Description."
			::= { hwInternBypassObject 1 }


--         1.3.6.1.4.1.2011.6.122.20.1.5.1.1
-- 1.3.6.1.4.1.2011.6.122.20.1.5.1.1
-- 1.3.6.1.4.1.2011.6.122.20.1.5.1.1
-- 1.3.6.1.4.1.2011.6.122.20.1.5.1.1
-- 1.3.6.1.4.1.2011.6.122.20.1.5.1.1
-- 1.3.6.1.4.1.2011.6.122.20.1.5.1.1
-- 1.3.6.1.4.1.2011.6.122.20.1.5.1.1
-- 1.3.6.1.4.1.2011.6.122.20.1.5.1.1
		-- 1.3.6.1.4.1.2011.6.122.20.1.5.1.1
		hwBypassLinkStateEntry OBJECT-TYPE
			SYNTAX HwBypassLinkStateEntry
			MAX-ACCESS not-accessible
			STATUS current
			DESCRIPTION
				"Description."
			INDEX { hwBypassLinkStateIndex }
			::= { hwBypassLinkStateTable 1 }


		HwBypassLinkStateEntry ::=
			SEQUENCE {
				hwBypassLinkStateIndex
					Gauge32,
				hwBypassLinkStateLink
					OCTET STRING,
				hwBypassLinkStateMode
					INTEGER,
				hwBypassLinkStateChannel0State
					INTEGER,
				hwBypassLinkStateChannel1State
					INTEGER,
				hwBypassLinkStateRIsignal
					OCTET STRING,
				hwBypassLinkCurrentState
					OCTET STRING,
				hwBypassLinkLosTimes
					Integer32,
				hwBypassLinkLinkTimes
					Integer32,
				hwBypassSwitchCurrentPosition
					OCTET STRING,
				hwBypassSwitchWorkingTimes
					Integer32,
				hwBypassSwitchProtectionTimes
					Integer32,
				hwBypassSlotNum
					Integer32,
				hwBypassPowerStatus
					OCTET STRING,
				hwBypassAlarmDescription
					OCTET STRING
			 }

--         1.3.6.1.4.1.2011.6.122.20.1.5.1.1.1
-- 1.3.6.1.4.1.2011.6.122.20.1.5.1.1.1
-- 1.3.6.1.4.1.2011.6.122.20.1.5.1.1.1
-- 1.3.6.1.4.1.2011.6.122.20.1.5.1.1.1
-- 1.3.6.1.4.1.2011.6.122.20.1.5.1.1.1
-- 1.3.6.1.4.1.2011.6.122.20.1.5.1.1.1
-- 1.3.6.1.4.1.2011.6.122.20.1.5.1.1.1
-- 1.3.6.1.4.1.2011.6.122.20.1.5.1.1.1
		-- 1.3.6.1.4.1.2011.6.122.20.1.5.1.1.1
		hwBypassLinkStateIndex OBJECT-TYPE
			SYNTAX Gauge32 (1..2147483647)
			MAX-ACCESS not-accessible
			STATUS current
			DESCRIPTION
				"The sub card number of the bypass"
			::= { hwBypassLinkStateEntry 1 }


--         1.3.6.1.4.1.2011.6.122.20.1.5.1.1.2
-- 1.3.6.1.4.1.2011.6.122.20.1.5.1.1.2
-- 1.3.6.1.4.1.2011.6.122.20.1.5.1.1.2
-- 1.3.6.1.4.1.2011.6.122.20.1.5.1.1.2
-- 1.3.6.1.4.1.2011.6.122.20.1.5.1.1.2
-- 1.3.6.1.4.1.2011.6.122.20.1.5.1.1.2
-- 1.3.6.1.4.1.2011.6.122.20.1.5.1.1.2
-- 1.3.6.1.4.1.2011.6.122.20.1.5.1.1.2
		-- 1.3.6.1.4.1.2011.6.122.20.1.5.1.1.2
		hwBypassLinkStateLink OBJECT-TYPE
			SYNTAX OCTET STRING (SIZE (0..255))
			MAX-ACCESS read-only
			STATUS current
			DESCRIPTION
				"The channel number "
			::= { hwBypassLinkStateEntry 2 }


--         1.3.6.1.4.1.2011.6.122.20.1.5.1.1.3
-- 1.3.6.1.4.1.2011.6.122.20.1.5.1.1.3
-- 1.3.6.1.4.1.2011.6.122.20.1.5.1.1.3
-- 1.3.6.1.4.1.2011.6.122.20.1.5.1.1.3
-- 1.3.6.1.4.1.2011.6.122.20.1.5.1.1.3
-- 1.3.6.1.4.1.2011.6.122.20.1.5.1.1.3
-- 1.3.6.1.4.1.2011.6.122.20.1.5.1.1.3
-- 1.3.6.1.4.1.2011.6.122.20.1.5.1.1.3
		-- 1.3.6.1.4.1.2011.6.122.20.1.5.1.1.3
		hwBypassLinkStateMode OBJECT-TYPE
			SYNTAX INTEGER
				{
				auto(0),
				manual(1),
				force(2),
				lock(3)
				}
			MAX-ACCESS read-write
			STATUS current
			DESCRIPTION
				"Description."
			::= { hwBypassLinkStateEntry 3 }


--         1.3.6.1.4.1.2011.6.122.20.1.5.1.1.4
-- 1.3.6.1.4.1.2011.6.122.20.1.5.1.1.4
-- 1.3.6.1.4.1.2011.6.122.20.1.5.1.1.4
-- 1.3.6.1.4.1.2011.6.122.20.1.5.1.1.4
-- 1.3.6.1.4.1.2011.6.122.20.1.5.1.1.4
-- 1.3.6.1.4.1.2011.6.122.20.1.5.1.1.4
-- 1.3.6.1.4.1.2011.6.122.20.1.5.1.1.4
-- 1.3.6.1.4.1.2011.6.122.20.1.5.1.1.4
		-- 1.3.6.1.4.1.2011.6.122.20.1.5.1.1.4
		hwBypassLinkStateChannel0State OBJECT-TYPE
			SYNTAX INTEGER
				{
				working(0),
				protection(1)
				}
			MAX-ACCESS read-only
			STATUS current
			DESCRIPTION
				"The mode of channel"
			::= { hwBypassLinkStateEntry 4 }


--         1.3.6.1.4.1.2011.6.122.20.1.5.1.1.5
-- 1.3.6.1.4.1.2011.6.122.20.1.5.1.1.5
-- 1.3.6.1.4.1.2011.6.122.20.1.5.1.1.5
-- 1.3.6.1.4.1.2011.6.122.20.1.5.1.1.5
-- 1.3.6.1.4.1.2011.6.122.20.1.5.1.1.5
-- 1.3.6.1.4.1.2011.6.122.20.1.5.1.1.5
-- 1.3.6.1.4.1.2011.6.122.20.1.5.1.1.5
-- 1.3.6.1.4.1.2011.6.122.20.1.5.1.1.5
		-- 1.3.6.1.4.1.2011.6.122.20.1.5.1.1.5
		hwBypassLinkStateChannel1State OBJECT-TYPE
			SYNTAX INTEGER
				{
				working(0),
				protection(1)
				}
			MAX-ACCESS read-only
			STATUS current
			DESCRIPTION
				"Working path"
			::= { hwBypassLinkStateEntry 5 }


--         1.3.6.1.4.1.2011.6.122.20.1.5.1.1.6
-- 1.3.6.1.4.1.2011.6.122.20.1.5.1.1.6
-- 1.3.6.1.4.1.2011.6.122.20.1.5.1.1.6
-- 1.3.6.1.4.1.2011.6.122.20.1.5.1.1.6
-- 1.3.6.1.4.1.2011.6.122.20.1.5.1.1.6
-- 1.3.6.1.4.1.2011.6.122.20.1.5.1.1.6
-- 1.3.6.1.4.1.2011.6.122.20.1.5.1.1.6
-- 1.3.6.1.4.1.2011.6.122.20.1.5.1.1.6
		-- 1.3.6.1.4.1.2011.6.122.20.1.5.1.1.6
		hwBypassLinkStateRIsignal OBJECT-TYPE
			SYNTAX OCTET STRING (SIZE (0..255))
			MAX-ACCESS read-only
			STATUS current
			DESCRIPTION
				"The channel RI signal "
			::= { hwBypassLinkStateEntry 6 }


--         1.3.6.1.4.1.2011.6.122.20.1.5.1.1.7
-- 1.3.6.1.4.1.2011.6.122.20.1.5.1.1.7
-- 1.3.6.1.4.1.2011.6.122.20.1.5.1.1.7
-- 1.3.6.1.4.1.2011.6.122.20.1.5.1.1.7
-- 1.3.6.1.4.1.2011.6.122.20.1.5.1.1.7
-- 1.3.6.1.4.1.2011.6.122.20.1.5.1.1.7
-- 1.3.6.1.4.1.2011.6.122.20.1.5.1.1.7
-- 1.3.6.1.4.1.2011.6.122.20.1.5.1.1.7
		-- 1.3.6.1.4.1.2011.6.122.20.1.5.1.1.7
		hwBypassLinkCurrentState OBJECT-TYPE
			SYNTAX OCTET STRING (SIZE (0..255))
			MAX-ACCESS read-only
			STATUS current
			DESCRIPTION
				"The channel current link status "
			::= { hwBypassLinkStateEntry 7 }


--         1.3.6.1.4.1.2011.6.122.20.1.5.1.1.8
-- 1.3.6.1.4.1.2011.6.122.20.1.5.1.1.8
-- 1.3.6.1.4.1.2011.6.122.20.1.5.1.1.8
-- 1.3.6.1.4.1.2011.6.122.20.1.5.1.1.8
-- 1.3.6.1.4.1.2011.6.122.20.1.5.1.1.8
-- 1.3.6.1.4.1.2011.6.122.20.1.5.1.1.8
-- 1.3.6.1.4.1.2011.6.122.20.1.5.1.1.8
-- 1.3.6.1.4.1.2011.6.122.20.1.5.1.1.8
		-- 1.3.6.1.4.1.2011.6.122.20.1.5.1.1.8
		hwBypassLinkLosTimes OBJECT-TYPE
			SYNTAX Integer32
			MAX-ACCESS read-only
			STATUS current
			DESCRIPTION
				"Working path LOS times"
			::= { hwBypassLinkStateEntry 8 }


--         1.3.6.1.4.1.2011.6.122.20.1.5.1.1.9
-- 1.3.6.1.4.1.2011.6.122.20.1.5.1.1.9
-- 1.3.6.1.4.1.2011.6.122.20.1.5.1.1.9
-- 1.3.6.1.4.1.2011.6.122.20.1.5.1.1.9
-- 1.3.6.1.4.1.2011.6.122.20.1.5.1.1.9
-- 1.3.6.1.4.1.2011.6.122.20.1.5.1.1.9
-- 1.3.6.1.4.1.2011.6.122.20.1.5.1.1.9
-- 1.3.6.1.4.1.2011.6.122.20.1.5.1.1.9
		-- 1.3.6.1.4.1.2011.6.122.20.1.5.1.1.9
		hwBypassLinkLinkTimes OBJECT-TYPE
			SYNTAX Integer32
			MAX-ACCESS read-only
			STATUS current
			DESCRIPTION
				"Working path LINK times"
			::= { hwBypassLinkStateEntry 9 }


--         1.3.6.1.4.1.2011.6.122.20.1.5.1.1.10
-- 1.3.6.1.4.1.2011.6.122.20.1.5.1.1.10
-- 1.3.6.1.4.1.2011.6.122.20.1.5.1.1.10
-- 1.3.6.1.4.1.2011.6.122.20.1.5.1.1.10
-- 1.3.6.1.4.1.2011.6.122.20.1.5.1.1.10
-- 1.3.6.1.4.1.2011.6.122.20.1.5.1.1.10
-- 1.3.6.1.4.1.2011.6.122.20.1.5.1.1.10
-- 1.3.6.1.4.1.2011.6.122.20.1.5.1.1.10
		-- 1.3.6.1.4.1.2011.6.122.20.1.5.1.1.10
		hwBypassSwitchCurrentPosition OBJECT-TYPE
			SYNTAX OCTET STRING (SIZE (0..255))
			MAX-ACCESS read-only
			STATUS current
			DESCRIPTION
				"The current switch position of the link "
			::= { hwBypassLinkStateEntry 10 }


--         1.3.6.1.4.1.2011.6.122.20.1.5.1.1.11
-- 1.3.6.1.4.1.2011.6.122.20.1.5.1.1.11
-- 1.3.6.1.4.1.2011.6.122.20.1.5.1.1.11
-- 1.3.6.1.4.1.2011.6.122.20.1.5.1.1.11
-- 1.3.6.1.4.1.2011.6.122.20.1.5.1.1.11
-- 1.3.6.1.4.1.2011.6.122.20.1.5.1.1.11
-- 1.3.6.1.4.1.2011.6.122.20.1.5.1.1.11
-- 1.3.6.1.4.1.2011.6.122.20.1.5.1.1.11
		-- 1.3.6.1.4.1.2011.6.122.20.1.5.1.1.11
		hwBypassSwitchWorkingTimes OBJECT-TYPE
			SYNTAX Integer32
			MAX-ACCESS read-only
			STATUS current
			DESCRIPTION
				"Times of switching to working channel"
			::= { hwBypassLinkStateEntry 11 }


--         1.3.6.1.4.1.2011.6.122.20.1.5.1.1.12
-- 1.3.6.1.4.1.2011.6.122.20.1.5.1.1.12
-- 1.3.6.1.4.1.2011.6.122.20.1.5.1.1.12
-- 1.3.6.1.4.1.2011.6.122.20.1.5.1.1.12
-- 1.3.6.1.4.1.2011.6.122.20.1.5.1.1.12
-- 1.3.6.1.4.1.2011.6.122.20.1.5.1.1.12
-- 1.3.6.1.4.1.2011.6.122.20.1.5.1.1.12
-- 1.3.6.1.4.1.2011.6.122.20.1.5.1.1.12
		-- 1.3.6.1.4.1.2011.6.122.20.1.5.1.1.12
		hwBypassSwitchProtectionTimes OBJECT-TYPE
			SYNTAX Integer32
			MAX-ACCESS read-only
			STATUS current
			DESCRIPTION
				"Times of switching to protection channel"
			::= { hwBypassLinkStateEntry 12 }


--         1.3.6.1.4.1.2011.6.122.20.1.5.1.1.13
-- 1.3.6.1.4.1.2011.6.122.20.1.5.1.1.13
-- 1.3.6.1.4.1.2011.6.122.20.1.5.1.1.13
-- 1.3.6.1.4.1.2011.6.122.20.1.5.1.1.13
-- 1.3.6.1.4.1.2011.6.122.20.1.5.1.1.13
-- 1.3.6.1.4.1.2011.6.122.20.1.5.1.1.13
-- 1.3.6.1.4.1.2011.6.122.20.1.5.1.1.13
-- 1.3.6.1.4.1.2011.6.122.20.1.5.1.1.13
		-- 1.3.6.1.4.1.2011.6.122.20.1.5.1.1.13
		hwBypassSlotNum OBJECT-TYPE
			SYNTAX Integer32
			MAX-ACCESS read-only
			STATUS current
			DESCRIPTION
				"Slot number"
			::= { hwBypassLinkStateEntry 13 }


--         1.3.6.1.4.1.2011.6.122.20.1.5.1.1.14
-- 1.3.6.1.4.1.2011.6.122.20.1.5.1.1.14
-- 1.3.6.1.4.1.2011.6.122.20.1.5.1.1.14
-- 1.3.6.1.4.1.2011.6.122.20.1.5.1.1.14
-- 1.3.6.1.4.1.2011.6.122.20.1.5.1.1.14
-- 1.3.6.1.4.1.2011.6.122.20.1.5.1.1.14
-- 1.3.6.1.4.1.2011.6.122.20.1.5.1.1.14
-- 1.3.6.1.4.1.2011.6.122.20.1.5.1.1.14
		-- 1.3.6.1.4.1.2011.6.122.20.1.5.1.1.14
		hwBypassPowerStatus OBJECT-TYPE
			SYNTAX OCTET STRING (SIZE (0..255))
			MAX-ACCESS read-only
			STATUS current
			DESCRIPTION
				"Power status"
			::= { hwBypassLinkStateEntry 14 }


--         1.3.6.1.4.1.2011.6.122.20.1.5.1.1.15
-- 1.3.6.1.4.1.2011.6.122.20.1.5.1.1.15
-- 1.3.6.1.4.1.2011.6.122.20.1.5.1.1.15
-- 1.3.6.1.4.1.2011.6.122.20.1.5.1.1.15
-- 1.3.6.1.4.1.2011.6.122.20.1.5.1.1.15
-- 1.3.6.1.4.1.2011.6.122.20.1.5.1.1.15
-- 1.3.6.1.4.1.2011.6.122.20.1.5.1.1.15
-- 1.3.6.1.4.1.2011.6.122.20.1.5.1.1.15
		-- 1.3.6.1.4.1.2011.6.122.20.1.5.1.1.15
		hwBypassAlarmDescription OBJECT-TYPE
			SYNTAX OCTET STRING (SIZE (0..255))
			MAX-ACCESS read-only
			STATUS current
			DESCRIPTION
				"Description"
			::= { hwBypassLinkStateEntry 15 }


--         1.3.6.1.4.1.2011.6.122.20.1.6
-- 1.3.6.1.4.1.2011.6.122.20.1.6
-- 1.3.6.1.4.1.2011.6.122.20.1.6
-- 1.3.6.1.4.1.2011.6.122.20.1.6
-- 1.3.6.1.4.1.2011.6.122.20.1.6
-- 1.3.6.1.4.1.2011.6.122.20.1.6
-- 1.3.6.1.4.1.2011.6.122.20.1.6
-- 1.3.6.1.4.1.2011.6.122.20.1.6
		-- 1.3.6.1.4.1.2011.6.122.20.1.6
		hwInternBypassTraps OBJECT IDENTIFIER ::= { hwDeviceObject 6 }


--         1.3.6.1.4.1.2011.6.122.20.1.6.1
-- 1.3.6.1.4.1.2011.6.122.20.1.6.1
-- 1.3.6.1.4.1.2011.6.122.20.1.6.1
-- 1.3.6.1.4.1.2011.6.122.20.1.6.1
-- 1.3.6.1.4.1.2011.6.122.20.1.6.1
-- 1.3.6.1.4.1.2011.6.122.20.1.6.1
-- 1.3.6.1.4.1.2011.6.122.20.1.6.1
-- 1.3.6.1.4.1.2011.6.122.20.1.6.1
		-- 1.3.6.1.4.1.2011.6.122.20.1.6.1
		hwBypassSwitchWorkingMode NOTIFICATION-TYPE
			OBJECTS { hwBypassLinkStateLink, hwBypassLinkStateChannel1State, hwBypassLinkStateChannel0State, hwBypassLinkStateMode }
			STATUS current
			DESCRIPTION
				"Description."
			::= { hwInternBypassTraps 1 }


--         1.3.6.1.4.1.2011.6.122.20.1.6.2
-- 1.3.6.1.4.1.2011.6.122.20.1.6.2
-- 1.3.6.1.4.1.2011.6.122.20.1.6.2
-- 1.3.6.1.4.1.2011.6.122.20.1.6.2
-- 1.3.6.1.4.1.2011.6.122.20.1.6.2
-- 1.3.6.1.4.1.2011.6.122.20.1.6.2
-- 1.3.6.1.4.1.2011.6.122.20.1.6.2
-- 1.3.6.1.4.1.2011.6.122.20.1.6.2
		-- 1.3.6.1.4.1.2011.6.122.20.1.6.2
		hwBypassLinkState NOTIFICATION-TYPE
			OBJECTS { hwBypassLinkStateLink, hwBypassLinkStateRIsignal, hwBypassLinkCurrentState, hwBypassLinkLosTimes, hwBypassLinkLinkTimes
				 }
			STATUS current
			DESCRIPTION
				"Description."
			::= { hwInternBypassTraps 2 }


--         1.3.6.1.4.1.2011.6.122.20.1.6.3
-- 1.3.6.1.4.1.2011.6.122.20.1.6.3
-- 1.3.6.1.4.1.2011.6.122.20.1.6.3
-- 1.3.6.1.4.1.2011.6.122.20.1.6.3
-- 1.3.6.1.4.1.2011.6.122.20.1.6.3
-- 1.3.6.1.4.1.2011.6.122.20.1.6.3
-- 1.3.6.1.4.1.2011.6.122.20.1.6.3
-- 1.3.6.1.4.1.2011.6.122.20.1.6.3
		-- 1.3.6.1.4.1.2011.6.122.20.1.6.3
		hwBypassLinkSwitchState NOTIFICATION-TYPE
			OBJECTS { hwBypassLinkStateLink, hwBypassSwitchCurrentPosition, hwBypassSwitchWorkingTimes, hwBypassSwitchProtectionTimes }
			STATUS current
			DESCRIPTION
				"Description."
			::= { hwInternBypassTraps 3 }


--         1.3.6.1.4.1.2011.6.122.20.1.6.4
-- 1.3.6.1.4.1.2011.6.122.20.1.6.4
-- 1.3.6.1.4.1.2011.6.122.20.1.6.4
-- 1.3.6.1.4.1.2011.6.122.20.1.6.4
-- 1.3.6.1.4.1.2011.6.122.20.1.6.4
-- 1.3.6.1.4.1.2011.6.122.20.1.6.4
-- 1.3.6.1.4.1.2011.6.122.20.1.6.4
-- 1.3.6.1.4.1.2011.6.122.20.1.6.4
		-- 1.3.6.1.4.1.2011.6.122.20.1.6.4
		hwBypassMonitorState NOTIFICATION-TYPE
			OBJECTS { hwBypassSlotNum, hwBypassPowerStatus, hwBypassAlarmDescription }
			STATUS current
			DESCRIPTION
				"Description."
			::= { hwInternBypassTraps 4 }


--         1.3.6.1.4.1.2011.6.122.20.1.7
-- 1.3.6.1.4.1.2011.6.122.20.1.7
-- 1.3.6.1.4.1.2011.6.122.20.1.7
-- 1.3.6.1.4.1.2011.6.122.20.1.7
-- 1.3.6.1.4.1.2011.6.122.20.1.7
-- 1.3.6.1.4.1.2011.6.122.20.1.7
-- 1.3.6.1.4.1.2011.6.122.20.1.7
-- 1.3.6.1.4.1.2011.6.122.20.1.7
		-- 1.3.6.1.4.1.2011.6.122.20.1.7
		hwSpuEntityObject OBJECT IDENTIFIER ::= { hwDeviceObject 7 }


--         1.3.6.1.4.1.2011.6.122.20.1.7.1
-- 1.3.6.1.4.1.2011.6.122.20.1.7.1
-- 1.3.6.1.4.1.2011.6.122.20.1.7.1
-- 1.3.6.1.4.1.2011.6.122.20.1.7.1
-- 1.3.6.1.4.1.2011.6.122.20.1.7.1
-- 1.3.6.1.4.1.2011.6.122.20.1.7.1
-- 1.3.6.1.4.1.2011.6.122.20.1.7.1
-- 1.3.6.1.4.1.2011.6.122.20.1.7.1
		-- 1.3.6.1.4.1.2011.6.122.20.1.7.1
		hwSpuEntityStateTable OBJECT-TYPE
			SYNTAX SEQUENCE OF HwSpuEntityStateEntry
			MAX-ACCESS not-accessible
			STATUS current
			DESCRIPTION
				"The status of the SPU's entity table"
			::= { hwSpuEntityObject 1 }


--         1.3.6.1.4.1.2011.6.122.20.1.7.1.1
-- 1.3.6.1.4.1.2011.6.122.20.1.7.1.1
-- 1.3.6.1.4.1.2011.6.122.20.1.7.1.1
-- 1.3.6.1.4.1.2011.6.122.20.1.7.1.1
-- 1.3.6.1.4.1.2011.6.122.20.1.7.1.1
-- 1.3.6.1.4.1.2011.6.122.20.1.7.1.1
-- 1.3.6.1.4.1.2011.6.122.20.1.7.1.1
-- 1.3.6.1.4.1.2011.6.122.20.1.7.1.1
		-- 1.3.6.1.4.1.2011.6.122.20.1.7.1.1
		hwSpuEntityStateEntry OBJECT-TYPE
			SYNTAX HwSpuEntityStateEntry
			MAX-ACCESS not-accessible
			STATUS current
			DESCRIPTION
				"The status of the SPU's entity entry"
			INDEX { hwSpuEntityCpuNumber }
			::= { hwSpuEntityStateTable 1 }


		HwSpuEntityStateEntry ::=
			SEQUENCE {
				hwSpuEntityCpuNumber
					Gauge32,
				hwSpuEntityPhysicalIndex
					Gauge32,
				hwSpuEntityLocation
					OCTET STRING,
				hwSpuEntityCpuUsage
					Gauge32,
				hwSpuEntityCpuUsageThreshold
					Integer32,
				hwSpuEntityMemoryUsage
					Gauge32,
				hwSpuEntityMemoryUsageThreshold
					Gauge32,
				hwSpuEntityTemperature
					Integer32,
				hwSpuEntityTemperatureThreshold
					Integer32
			 }

--         1.3.6.1.4.1.2011.6.122.20.1.7.1.1.1
-- 1.3.6.1.4.1.2011.6.122.20.1.7.1.1.1
-- 1.3.6.1.4.1.2011.6.122.20.1.7.1.1.1
-- 1.3.6.1.4.1.2011.6.122.20.1.7.1.1.1
-- 1.3.6.1.4.1.2011.6.122.20.1.7.1.1.1
-- 1.3.6.1.4.1.2011.6.122.20.1.7.1.1.1
-- 1.3.6.1.4.1.2011.6.122.20.1.7.1.1.1
-- 1.3.6.1.4.1.2011.6.122.20.1.7.1.1.1
		-- 1.3.6.1.4.1.2011.6.122.20.1.7.1.1.1
		hwSpuEntityCpuNumber OBJECT-TYPE
			SYNTAX Gauge32 (1..65535)
			MAX-ACCESS not-accessible
			STATUS current
			DESCRIPTION
				"The CPU number of the spu board"
			::= { hwSpuEntityStateEntry 1 }


--         1.3.6.1.4.1.2011.6.122.20.1.7.1.1.2
-- 1.3.6.1.4.1.2011.6.122.20.1.7.1.1.2
-- 1.3.6.1.4.1.2011.6.122.20.1.7.1.1.2
-- 1.3.6.1.4.1.2011.6.122.20.1.7.1.1.2
-- 1.3.6.1.4.1.2011.6.122.20.1.7.1.1.2
-- 1.3.6.1.4.1.2011.6.122.20.1.7.1.1.2
-- 1.3.6.1.4.1.2011.6.122.20.1.7.1.1.2
-- 1.3.6.1.4.1.2011.6.122.20.1.7.1.1.2
		-- 1.3.6.1.4.1.2011.6.122.20.1.7.1.1.2
		hwSpuEntityPhysicalIndex OBJECT-TYPE
			SYNTAX Gauge32 (1..2147483647)
			MAX-ACCESS read-only
			STATUS current
			DESCRIPTION
				"The physical index of entity"
			::= { hwSpuEntityStateEntry 2 }


--         1.3.6.1.4.1.2011.6.122.20.1.7.1.1.3
-- 1.3.6.1.4.1.2011.6.122.20.1.7.1.1.3
-- 1.3.6.1.4.1.2011.6.122.20.1.7.1.1.3
-- 1.3.6.1.4.1.2011.6.122.20.1.7.1.1.3
-- 1.3.6.1.4.1.2011.6.122.20.1.7.1.1.3
-- 1.3.6.1.4.1.2011.6.122.20.1.7.1.1.3
-- 1.3.6.1.4.1.2011.6.122.20.1.7.1.1.3
-- 1.3.6.1.4.1.2011.6.122.20.1.7.1.1.3
		-- 1.3.6.1.4.1.2011.6.122.20.1.7.1.1.3
		hwSpuEntityLocation OBJECT-TYPE
			SYNTAX OCTET STRING (SIZE (0..255))
			MAX-ACCESS read-write
			STATUS current
			DESCRIPTION
				"The CPU location"
			::= { hwSpuEntityStateEntry 3 }


--         1.3.6.1.4.1.2011.6.122.20.1.7.1.1.4
-- 1.3.6.1.4.1.2011.6.122.20.1.7.1.1.4
-- 1.3.6.1.4.1.2011.6.122.20.1.7.1.1.4
-- 1.3.6.1.4.1.2011.6.122.20.1.7.1.1.4
-- 1.3.6.1.4.1.2011.6.122.20.1.7.1.1.4
-- 1.3.6.1.4.1.2011.6.122.20.1.7.1.1.4
-- 1.3.6.1.4.1.2011.6.122.20.1.7.1.1.4
-- 1.3.6.1.4.1.2011.6.122.20.1.7.1.1.4
		-- 1.3.6.1.4.1.2011.6.122.20.1.7.1.1.4
		hwSpuEntityCpuUsage OBJECT-TYPE
			SYNTAX Gauge32 (0..100)
			MAX-ACCESS read-only
			STATUS current
			DESCRIPTION
				"The CPU usage"
			::= { hwSpuEntityStateEntry 4 }


--         1.3.6.1.4.1.2011.6.122.20.1.7.1.1.5
-- 1.3.6.1.4.1.2011.6.122.20.1.7.1.1.5
-- 1.3.6.1.4.1.2011.6.122.20.1.7.1.1.5
-- 1.3.6.1.4.1.2011.6.122.20.1.7.1.1.5
-- 1.3.6.1.4.1.2011.6.122.20.1.7.1.1.5
-- 1.3.6.1.4.1.2011.6.122.20.1.7.1.1.5
-- 1.3.6.1.4.1.2011.6.122.20.1.7.1.1.5
-- 1.3.6.1.4.1.2011.6.122.20.1.7.1.1.5
		-- 1.3.6.1.4.1.2011.6.122.20.1.7.1.1.5
		hwSpuEntityCpuUsageThreshold OBJECT-TYPE
			SYNTAX Integer32 (1..100)
			MAX-ACCESS read-only
			STATUS current
			DESCRIPTION
				"The usage threshold of the CPU"
			::= { hwSpuEntityStateEntry 5 }


--         1.3.6.1.4.1.2011.6.122.20.1.7.1.1.6
-- 1.3.6.1.4.1.2011.6.122.20.1.7.1.1.6
-- 1.3.6.1.4.1.2011.6.122.20.1.7.1.1.6
-- 1.3.6.1.4.1.2011.6.122.20.1.7.1.1.6
-- 1.3.6.1.4.1.2011.6.122.20.1.7.1.1.6
-- 1.3.6.1.4.1.2011.6.122.20.1.7.1.1.6
-- 1.3.6.1.4.1.2011.6.122.20.1.7.1.1.6
-- 1.3.6.1.4.1.2011.6.122.20.1.7.1.1.6
		-- 1.3.6.1.4.1.2011.6.122.20.1.7.1.1.6
		hwSpuEntityMemoryUsage OBJECT-TYPE
			SYNTAX Gauge32 (1..100)
			MAX-ACCESS read-only
			STATUS current
			DESCRIPTION
				"The usage of the memory"
			::= { hwSpuEntityStateEntry 6 }


--         1.3.6.1.4.1.2011.6.122.20.1.7.1.1.7
-- 1.3.6.1.4.1.2011.6.122.20.1.7.1.1.7
-- 1.3.6.1.4.1.2011.6.122.20.1.7.1.1.7
-- 1.3.6.1.4.1.2011.6.122.20.1.7.1.1.7
-- 1.3.6.1.4.1.2011.6.122.20.1.7.1.1.7
-- 1.3.6.1.4.1.2011.6.122.20.1.7.1.1.7
-- 1.3.6.1.4.1.2011.6.122.20.1.7.1.1.7
-- 1.3.6.1.4.1.2011.6.122.20.1.7.1.1.7
		-- 1.3.6.1.4.1.2011.6.122.20.1.7.1.1.7
		hwSpuEntityMemoryUsageThreshold OBJECT-TYPE
			SYNTAX Gauge32 (1..100)
			MAX-ACCESS read-only
			STATUS current
			DESCRIPTION
				"The usage threshold of the memory"
			::= { hwSpuEntityStateEntry 7 }


--         1.3.6.1.4.1.2011.6.122.20.1.7.1.1.8
-- 1.3.6.1.4.1.2011.6.122.20.1.7.1.1.8
-- 1.3.6.1.4.1.2011.6.122.20.1.7.1.1.8
-- 1.3.6.1.4.1.2011.6.122.20.1.7.1.1.8
-- 1.3.6.1.4.1.2011.6.122.20.1.7.1.1.8
-- 1.3.6.1.4.1.2011.6.122.20.1.7.1.1.8
-- 1.3.6.1.4.1.2011.6.122.20.1.7.1.1.8
-- 1.3.6.1.4.1.2011.6.122.20.1.7.1.1.8
		-- 1.3.6.1.4.1.2011.6.122.20.1.7.1.1.8
		hwSpuEntityTemperature OBJECT-TYPE
			SYNTAX Integer32
			MAX-ACCESS read-write
			STATUS current
			DESCRIPTION
				"The temperature usage"
			::= { hwSpuEntityStateEntry 8 }


--         1.3.6.1.4.1.2011.6.122.20.1.7.1.1.9
-- 1.3.6.1.4.1.2011.6.122.20.1.7.1.1.9
-- 1.3.6.1.4.1.2011.6.122.20.1.7.1.1.9
-- 1.3.6.1.4.1.2011.6.122.20.1.7.1.1.9
-- 1.3.6.1.4.1.2011.6.122.20.1.7.1.1.9
-- 1.3.6.1.4.1.2011.6.122.20.1.7.1.1.9
-- 1.3.6.1.4.1.2011.6.122.20.1.7.1.1.9
-- 1.3.6.1.4.1.2011.6.122.20.1.7.1.1.9
		-- 1.3.6.1.4.1.2011.6.122.20.1.7.1.1.9
		hwSpuEntityTemperatureThreshold OBJECT-TYPE
			SYNTAX Integer32
			MAX-ACCESS read-write
			STATUS current
			DESCRIPTION
				"The usgae threshold of the temperature"
			::= { hwSpuEntityStateEntry 9 }


--         1.3.6.1.4.1.2011.6.122.20.1.8
-- 1.3.6.1.4.1.2011.6.122.20.1.8
-- 1.3.6.1.4.1.2011.6.122.20.1.8
-- 1.3.6.1.4.1.2011.6.122.20.1.8
-- 1.3.6.1.4.1.2011.6.122.20.1.8
-- 1.3.6.1.4.1.2011.6.122.20.1.8
-- 1.3.6.1.4.1.2011.6.122.20.1.8
-- 1.3.6.1.4.1.2011.6.122.20.1.8
		-- 1.3.6.1.4.1.2011.6.122.20.1.8
		hwSpuEntityTraps OBJECT IDENTIFIER ::= { hwDeviceObject 8 }


--         1.3.6.1.4.1.2011.6.122.20.1.8.1
-- 1.3.6.1.4.1.2011.6.122.20.1.8.1
-- 1.3.6.1.4.1.2011.6.122.20.1.8.1
-- 1.3.6.1.4.1.2011.6.122.20.1.8.1
-- 1.3.6.1.4.1.2011.6.122.20.1.8.1
-- 1.3.6.1.4.1.2011.6.122.20.1.8.1
-- 1.3.6.1.4.1.2011.6.122.20.1.8.1
-- 1.3.6.1.4.1.2011.6.122.20.1.8.1
		-- 1.3.6.1.4.1.2011.6.122.20.1.8.1
		hwSpuCpuUsageThresholdTrap NOTIFICATION-TYPE
			OBJECTS { hwSpuEntityCpuUsage, hwSpuEntityCpuUsageThreshold, hwSpuEntityLocation }
			STATUS current
			DESCRIPTION
				"The CPU usage exceed the threshold"
			::= { hwSpuEntityTraps 1 }


--         1.3.6.1.4.1.2011.6.122.20.1.8.2
-- 1.3.6.1.4.1.2011.6.122.20.1.8.2
-- 1.3.6.1.4.1.2011.6.122.20.1.8.2
-- 1.3.6.1.4.1.2011.6.122.20.1.8.2
-- 1.3.6.1.4.1.2011.6.122.20.1.8.2
-- 1.3.6.1.4.1.2011.6.122.20.1.8.2
-- 1.3.6.1.4.1.2011.6.122.20.1.8.2
-- 1.3.6.1.4.1.2011.6.122.20.1.8.2
		-- 1.3.6.1.4.1.2011.6.122.20.1.8.2
		hwSpuCpuUsageThresholdRestoreTrap NOTIFICATION-TYPE
			OBJECTS { hwSpuEntityCpuUsage, hwSpuEntityCpuUsageThreshold, hwSpuEntityLocation }
			STATUS current
			DESCRIPTION
				"The CPU usage exceed the threshold"
			::= { hwSpuEntityTraps 2 }


--         1.3.6.1.4.1.2011.6.122.20.1.8.3
-- 1.3.6.1.4.1.2011.6.122.20.1.8.3
-- 1.3.6.1.4.1.2011.6.122.20.1.8.3
-- 1.3.6.1.4.1.2011.6.122.20.1.8.3
-- 1.3.6.1.4.1.2011.6.122.20.1.8.3
-- 1.3.6.1.4.1.2011.6.122.20.1.8.3
-- 1.3.6.1.4.1.2011.6.122.20.1.8.3
-- 1.3.6.1.4.1.2011.6.122.20.1.8.3
		-- 1.3.6.1.4.1.2011.6.122.20.1.8.3
		hwSpuMemUsageThresholdTrap NOTIFICATION-TYPE
			OBJECTS { hwSpuEntityMemoryUsage, hwSpuEntityMemoryUsageThreshold, hwSpuEntityLocation }
			STATUS current
			DESCRIPTION
				"This object indicates that the dynamic memory usage on an SPU exceeds the threshold."
			::= { hwSpuEntityTraps 3 }


--         1.3.6.1.4.1.2011.6.122.20.1.8.4
-- 1.3.6.1.4.1.2011.6.122.20.1.8.4
-- 1.3.6.1.4.1.2011.6.122.20.1.8.4
-- 1.3.6.1.4.1.2011.6.122.20.1.8.4
-- 1.3.6.1.4.1.2011.6.122.20.1.8.4
-- 1.3.6.1.4.1.2011.6.122.20.1.8.4
-- 1.3.6.1.4.1.2011.6.122.20.1.8.4
-- 1.3.6.1.4.1.2011.6.122.20.1.8.4
		-- 1.3.6.1.4.1.2011.6.122.20.1.8.4
		hwSpuMemUsageThresholdRestoreTrap NOTIFICATION-TYPE
			OBJECTS { hwSpuEntityMemoryUsage, hwSpuEntityMemoryUsageThreshold, hwSpuEntityLocation }
			STATUS current
			DESCRIPTION
				"This object indicates that the dynamic memory usage on an SPU restores to a normal range."
			::= { hwSpuEntityTraps 4 }


--         1.3.6.1.4.1.2011.6.122.20.1.8.5
-- 1.3.6.1.4.1.2011.6.122.20.1.8.5
-- 1.3.6.1.4.1.2011.6.122.20.1.8.5
-- 1.3.6.1.4.1.2011.6.122.20.1.8.5
-- 1.3.6.1.4.1.2011.6.122.20.1.8.5
-- 1.3.6.1.4.1.2011.6.122.20.1.8.5
-- 1.3.6.1.4.1.2011.6.122.20.1.8.5
-- 1.3.6.1.4.1.2011.6.122.20.1.8.5
		-- 1.3.6.1.4.1.2011.6.122.20.1.8.5
		hwSpuTemperatureThresholdTrap NOTIFICATION-TYPE
			OBJECTS { hwSpuEntityTemperature, hwSpuEntityTemperatureThreshold, hwSpuEntityLocation }
			STATUS current
			DESCRIPTION
				"The CPU temperature exceeds the threshold"
			::= { hwSpuEntityTraps 5 }


--         1.3.6.1.4.1.2011.6.122.20.1.8.6
-- 1.3.6.1.4.1.2011.6.122.20.1.8.6
-- 1.3.6.1.4.1.2011.6.122.20.1.8.6
-- 1.3.6.1.4.1.2011.6.122.20.1.8.6
-- 1.3.6.1.4.1.2011.6.122.20.1.8.6
-- 1.3.6.1.4.1.2011.6.122.20.1.8.6
-- 1.3.6.1.4.1.2011.6.122.20.1.8.6
-- 1.3.6.1.4.1.2011.6.122.20.1.8.6
		-- 1.3.6.1.4.1.2011.6.122.20.1.8.6
		hwSpuTemperatureThresholdRestoreTrap NOTIFICATION-TYPE
			OBJECTS { hwSpuEntityTemperature, hwSpuEntityTemperatureThreshold, hwSpuEntityLocation }
			STATUS current
			DESCRIPTION
				"The CPU temperature exceeds the threshold"
			::= { hwSpuEntityTraps 6 }


--         1.3.6.1.4.1.2011.6.122.20.1.9
-- 1.3.6.1.4.1.2011.6.122.20.1.9
-- 1.3.6.1.4.1.2011.6.122.20.1.9
-- 1.3.6.1.4.1.2011.6.122.20.1.9
-- 1.3.6.1.4.1.2011.6.122.20.1.9
-- 1.3.6.1.4.1.2011.6.122.20.1.9
-- 1.3.6.1.4.1.2011.6.122.20.1.9
-- 1.3.6.1.4.1.2011.6.122.20.1.9
		-- 1.3.6.1.4.1.2011.6.122.20.1.9
		hwSpuLpuOverLoadObject OBJECT IDENTIFIER ::= { hwDeviceObject 9 }


--         1.3.6.1.4.1.2011.6.122.20.1.9.1
-- 1.3.6.1.4.1.2011.6.122.20.1.9.1
-- 1.3.6.1.4.1.2011.6.122.20.1.9.1
-- 1.3.6.1.4.1.2011.6.122.20.1.9.1
-- 1.3.6.1.4.1.2011.6.122.20.1.9.1
-- 1.3.6.1.4.1.2011.6.122.20.1.9.1
-- 1.3.6.1.4.1.2011.6.122.20.1.9.1
-- 1.3.6.1.4.1.2011.6.122.20.1.9.1
		-- 1.3.6.1.4.1.2011.6.122.20.1.9.1
		hwSpuOverLoadInfoTable OBJECT-TYPE
			SYNTAX SEQUENCE OF HwSpuOverLoadInfoEntry
			MAX-ACCESS not-accessible
			STATUS current
			DESCRIPTION
				"Description."
			::= { hwSpuLpuOverLoadObject 1 }


--         1.3.6.1.4.1.2011.6.122.20.1.9.1.1
-- 1.3.6.1.4.1.2011.6.122.20.1.9.1.1
-- 1.3.6.1.4.1.2011.6.122.20.1.9.1.1
-- 1.3.6.1.4.1.2011.6.122.20.1.9.1.1
-- 1.3.6.1.4.1.2011.6.122.20.1.9.1.1
-- 1.3.6.1.4.1.2011.6.122.20.1.9.1.1
-- 1.3.6.1.4.1.2011.6.122.20.1.9.1.1
-- 1.3.6.1.4.1.2011.6.122.20.1.9.1.1
		-- 1.3.6.1.4.1.2011.6.122.20.1.9.1.1
		hwSpuOverLoadInfoEntry OBJECT-TYPE
			SYNTAX HwSpuOverLoadInfoEntry
			MAX-ACCESS not-accessible
			STATUS current
			DESCRIPTION
				"Description."
			INDEX { hwSpuOverLoadInfoIndex }
			::= { hwSpuOverLoadInfoTable 1 }


		HwSpuOverLoadInfoEntry ::=
			SEQUENCE {
				hwSpuOverLoadInfoIndex
					Gauge32,
				hwSpuOverLoadPackages
					Counter64,
				hwSpuOverLoadBytes
					Counter64
			 }

--         1.3.6.1.4.1.2011.6.122.20.1.9.1.1.1
-- 1.3.6.1.4.1.2011.6.122.20.1.9.1.1.1
-- 1.3.6.1.4.1.2011.6.122.20.1.9.1.1.1
-- 1.3.6.1.4.1.2011.6.122.20.1.9.1.1.1
-- 1.3.6.1.4.1.2011.6.122.20.1.9.1.1.1
-- 1.3.6.1.4.1.2011.6.122.20.1.9.1.1.1
-- 1.3.6.1.4.1.2011.6.122.20.1.9.1.1.1
-- 1.3.6.1.4.1.2011.6.122.20.1.9.1.1.1
		-- 1.3.6.1.4.1.2011.6.122.20.1.9.1.1.1
		hwSpuOverLoadInfoIndex OBJECT-TYPE
			SYNTAX Gauge32 (0..2147483647)
			MAX-ACCESS not-accessible
			STATUS current
			DESCRIPTION
				"Description."
			::= { hwSpuOverLoadInfoEntry 1 }


--         1.3.6.1.4.1.2011.6.122.20.1.9.1.1.2
-- 1.3.6.1.4.1.2011.6.122.20.1.9.1.1.2
-- 1.3.6.1.4.1.2011.6.122.20.1.9.1.1.2
-- 1.3.6.1.4.1.2011.6.122.20.1.9.1.1.2
-- 1.3.6.1.4.1.2011.6.122.20.1.9.1.1.2
-- 1.3.6.1.4.1.2011.6.122.20.1.9.1.1.2
-- 1.3.6.1.4.1.2011.6.122.20.1.9.1.1.2
-- 1.3.6.1.4.1.2011.6.122.20.1.9.1.1.2
		-- 1.3.6.1.4.1.2011.6.122.20.1.9.1.1.2
		hwSpuOverLoadPackages OBJECT-TYPE
			SYNTAX Counter64
			MAX-ACCESS read-only
			STATUS current
			DESCRIPTION
				"Description."
			::= { hwSpuOverLoadInfoEntry 2 }


--         1.3.6.1.4.1.2011.6.122.20.1.9.1.1.3
-- 1.3.6.1.4.1.2011.6.122.20.1.9.1.1.3
-- 1.3.6.1.4.1.2011.6.122.20.1.9.1.1.3
-- 1.3.6.1.4.1.2011.6.122.20.1.9.1.1.3
-- 1.3.6.1.4.1.2011.6.122.20.1.9.1.1.3
-- 1.3.6.1.4.1.2011.6.122.20.1.9.1.1.3
-- 1.3.6.1.4.1.2011.6.122.20.1.9.1.1.3
-- 1.3.6.1.4.1.2011.6.122.20.1.9.1.1.3
		-- 1.3.6.1.4.1.2011.6.122.20.1.9.1.1.3
		hwSpuOverLoadBytes OBJECT-TYPE
			SYNTAX Counter64
			MAX-ACCESS read-only
			STATUS current
			DESCRIPTION
				"Description."
			::= { hwSpuOverLoadInfoEntry 3 }


--         1.3.6.1.4.1.2011.6.122.20.1.9.2
-- 1.3.6.1.4.1.2011.6.122.20.1.9.2
-- 1.3.6.1.4.1.2011.6.122.20.1.9.2
-- 1.3.6.1.4.1.2011.6.122.20.1.9.2
-- 1.3.6.1.4.1.2011.6.122.20.1.9.2
-- 1.3.6.1.4.1.2011.6.122.20.1.9.2
-- 1.3.6.1.4.1.2011.6.122.20.1.9.2
-- 1.3.6.1.4.1.2011.6.122.20.1.9.2
		-- 1.3.6.1.4.1.2011.6.122.20.1.9.2
		hwLpuOverLoadInfoTable OBJECT-TYPE
			SYNTAX SEQUENCE OF HwLpuOverLoadInfoEntry
			MAX-ACCESS not-accessible
			STATUS current
			DESCRIPTION
				"Description."
			::= { hwSpuLpuOverLoadObject 2 }


--         1.3.6.1.4.1.2011.6.122.20.1.9.2.1
-- 1.3.6.1.4.1.2011.6.122.20.1.9.2.1
-- 1.3.6.1.4.1.2011.6.122.20.1.9.2.1
-- 1.3.6.1.4.1.2011.6.122.20.1.9.2.1
-- 1.3.6.1.4.1.2011.6.122.20.1.9.2.1
-- 1.3.6.1.4.1.2011.6.122.20.1.9.2.1
-- 1.3.6.1.4.1.2011.6.122.20.1.9.2.1
-- 1.3.6.1.4.1.2011.6.122.20.1.9.2.1
		-- 1.3.6.1.4.1.2011.6.122.20.1.9.2.1
		hwLpuOverLoadInfoEntry OBJECT-TYPE
			SYNTAX HwLpuOverLoadInfoEntry
			MAX-ACCESS not-accessible
			STATUS current
			DESCRIPTION
				"Description."
			INDEX { hwLpuOverLoadInfoIndex }
			::= { hwLpuOverLoadInfoTable 1 }


		HwLpuOverLoadInfoEntry ::=
			SEQUENCE {
				hwLpuOverLoadInfoIndex
					Gauge32,
				hwLpuOverLoadPackages
					Counter32,
				hwLpuOverLoadBytes
					Counter64
			 }

--         1.3.6.1.4.1.2011.6.122.20.1.9.2.1.1
-- 1.3.6.1.4.1.2011.6.122.20.1.9.2.1.1
-- 1.3.6.1.4.1.2011.6.122.20.1.9.2.1.1
-- 1.3.6.1.4.1.2011.6.122.20.1.9.2.1.1
-- 1.3.6.1.4.1.2011.6.122.20.1.9.2.1.1
-- 1.3.6.1.4.1.2011.6.122.20.1.9.2.1.1
-- 1.3.6.1.4.1.2011.6.122.20.1.9.2.1.1
-- 1.3.6.1.4.1.2011.6.122.20.1.9.2.1.1
		-- 1.3.6.1.4.1.2011.6.122.20.1.9.2.1.1
		hwLpuOverLoadInfoIndex OBJECT-TYPE
			SYNTAX Gauge32 (0..2147483647)
			MAX-ACCESS not-accessible
			STATUS current
			DESCRIPTION
				"Description."
			::= { hwLpuOverLoadInfoEntry 1 }


--         1.3.6.1.4.1.2011.6.122.20.1.9.2.1.2
-- 1.3.6.1.4.1.2011.6.122.20.1.9.2.1.2
-- 1.3.6.1.4.1.2011.6.122.20.1.9.2.1.2
-- 1.3.6.1.4.1.2011.6.122.20.1.9.2.1.2
-- 1.3.6.1.4.1.2011.6.122.20.1.9.2.1.2
-- 1.3.6.1.4.1.2011.6.122.20.1.9.2.1.2
-- 1.3.6.1.4.1.2011.6.122.20.1.9.2.1.2
-- 1.3.6.1.4.1.2011.6.122.20.1.9.2.1.2
		-- 1.3.6.1.4.1.2011.6.122.20.1.9.2.1.2
		hwLpuOverLoadPackages OBJECT-TYPE
			SYNTAX Counter32
			MAX-ACCESS read-only
			STATUS current
			DESCRIPTION
				"Description."
			::= { hwLpuOverLoadInfoEntry 2 }


--         1.3.6.1.4.1.2011.6.122.20.1.9.2.1.3
-- 1.3.6.1.4.1.2011.6.122.20.1.9.2.1.3
-- 1.3.6.1.4.1.2011.6.122.20.1.9.2.1.3
-- 1.3.6.1.4.1.2011.6.122.20.1.9.2.1.3
-- 1.3.6.1.4.1.2011.6.122.20.1.9.2.1.3
-- 1.3.6.1.4.1.2011.6.122.20.1.9.2.1.3
-- 1.3.6.1.4.1.2011.6.122.20.1.9.2.1.3
-- 1.3.6.1.4.1.2011.6.122.20.1.9.2.1.3
		-- 1.3.6.1.4.1.2011.6.122.20.1.9.2.1.3
		hwLpuOverLoadBytes OBJECT-TYPE
			SYNTAX Counter64
			MAX-ACCESS read-only
			STATUS current
			DESCRIPTION
				"Description."
			::= { hwLpuOverLoadInfoEntry 3 }


--         1.3.6.1.4.1.2011.6.122.20.1.10
-- 1.3.6.1.4.1.2011.6.122.20.1.10
-- 1.3.6.1.4.1.2011.6.122.20.1.10
-- 1.3.6.1.4.1.2011.6.122.20.1.10
-- 1.3.6.1.4.1.2011.6.122.20.1.10
-- 1.3.6.1.4.1.2011.6.122.20.1.10
-- 1.3.6.1.4.1.2011.6.122.20.1.10
-- 1.3.6.1.4.1.2011.6.122.20.1.10
		-- 1.3.6.1.4.1.2011.6.122.20.1.10
		hwSpuLpuOverLoadTrap OBJECT IDENTIFIER ::= { hwDeviceObject 10 }


--         1.3.6.1.4.1.2011.6.122.20.1.10.1
-- 1.3.6.1.4.1.2011.6.122.20.1.10.1
-- 1.3.6.1.4.1.2011.6.122.20.1.10.1
-- 1.3.6.1.4.1.2011.6.122.20.1.10.1
-- 1.3.6.1.4.1.2011.6.122.20.1.10.1
-- 1.3.6.1.4.1.2011.6.122.20.1.10.1
-- 1.3.6.1.4.1.2011.6.122.20.1.10.1
-- 1.3.6.1.4.1.2011.6.122.20.1.10.1
		-- 1.3.6.1.4.1.2011.6.122.20.1.10.1
		hwSpuOverLoadTrap NOTIFICATION-TYPE
			OBJECTS { hwSpuOverLoadPackages, hwSpuOverLoadBytes }
			STATUS current
			DESCRIPTION
				"Description."
			::= { hwSpuLpuOverLoadTrap 1 }


--         1.3.6.1.4.1.2011.6.122.20.1.10.2
-- 1.3.6.1.4.1.2011.6.122.20.1.10.2
-- 1.3.6.1.4.1.2011.6.122.20.1.10.2
-- 1.3.6.1.4.1.2011.6.122.20.1.10.2
-- 1.3.6.1.4.1.2011.6.122.20.1.10.2
-- 1.3.6.1.4.1.2011.6.122.20.1.10.2
-- 1.3.6.1.4.1.2011.6.122.20.1.10.2
-- 1.3.6.1.4.1.2011.6.122.20.1.10.2
		-- 1.3.6.1.4.1.2011.6.122.20.1.10.2
		hwLpuOverLoadTrap NOTIFICATION-TYPE
			OBJECTS { hwLpuOverLoadPackages, hwLpuOverLoadBytes }
			STATUS current
			DESCRIPTION
				"Description."
			::= { hwSpuLpuOverLoadTrap 2 }


--         1.3.6.1.4.1.2011.6.122.20.1.11
-- 1.3.6.1.4.1.2011.6.122.20.1.11
-- 1.3.6.1.4.1.2011.6.122.20.1.11
-- 1.3.6.1.4.1.2011.6.122.20.1.11
-- 1.3.6.1.4.1.2011.6.122.20.1.11
-- 1.3.6.1.4.1.2011.6.122.20.1.11
-- 1.3.6.1.4.1.2011.6.122.20.1.11
-- 1.3.6.1.4.1.2011.6.122.20.1.11
		-- 1.3.6.1.4.1.2011.6.122.20.1.11
		hwSpuFlowOverLoadObject OBJECT IDENTIFIER ::= { hwDeviceObject 11 }


--         1.3.6.1.4.1.2011.6.122.20.1.11.1
-- 1.3.6.1.4.1.2011.6.122.20.1.11.1
-- 1.3.6.1.4.1.2011.6.122.20.1.11.1
-- 1.3.6.1.4.1.2011.6.122.20.1.11.1
-- 1.3.6.1.4.1.2011.6.122.20.1.11.1
-- 1.3.6.1.4.1.2011.6.122.20.1.11.1
-- 1.3.6.1.4.1.2011.6.122.20.1.11.1
-- 1.3.6.1.4.1.2011.6.122.20.1.11.1
		-- 1.3.6.1.4.1.2011.6.122.20.1.11.1
		hwSpuFlowOverLoadTable OBJECT-TYPE
			SYNTAX SEQUENCE OF HwSpuFlowOverLoadEntry
			MAX-ACCESS not-accessible
			STATUS current
			DESCRIPTION
				"Description."
			::= { hwSpuFlowOverLoadObject 1 }


--         1.3.6.1.4.1.2011.6.122.20.1.11.1.1
-- 1.3.6.1.4.1.2011.6.122.20.1.11.1.1
-- 1.3.6.1.4.1.2011.6.122.20.1.11.1.1
-- 1.3.6.1.4.1.2011.6.122.20.1.11.1.1
-- 1.3.6.1.4.1.2011.6.122.20.1.11.1.1
-- 1.3.6.1.4.1.2011.6.122.20.1.11.1.1
-- 1.3.6.1.4.1.2011.6.122.20.1.11.1.1
-- 1.3.6.1.4.1.2011.6.122.20.1.11.1.1
		-- 1.3.6.1.4.1.2011.6.122.20.1.11.1.1
		hwSpuFlowOverLoadEntry OBJECT-TYPE
			SYNTAX HwSpuFlowOverLoadEntry
			MAX-ACCESS not-accessible
			STATUS current
			DESCRIPTION
				"Description."
			INDEX { hwSpuFlowOverLoadCpuNumber }
			::= { hwSpuFlowOverLoadTable 1 }


		HwSpuFlowOverLoadEntry ::=
			SEQUENCE {
				hwSpuFlowOverLoadCpuNumber
					Gauge32,
				hwSpuFlowOverLoadPackets
					OCTET STRING,
				hwSpuFlowOverLoadLocation
					OCTET STRING
			 }

--         1.3.6.1.4.1.2011.6.122.20.1.11.1.1.1
-- 1.3.6.1.4.1.2011.6.122.20.1.11.1.1.1
-- 1.3.6.1.4.1.2011.6.122.20.1.11.1.1.1
-- 1.3.6.1.4.1.2011.6.122.20.1.11.1.1.1
-- 1.3.6.1.4.1.2011.6.122.20.1.11.1.1.1
-- 1.3.6.1.4.1.2011.6.122.20.1.11.1.1.1
-- 1.3.6.1.4.1.2011.6.122.20.1.11.1.1.1
-- 1.3.6.1.4.1.2011.6.122.20.1.11.1.1.1
		-- 1.3.6.1.4.1.2011.6.122.20.1.11.1.1.1
		hwSpuFlowOverLoadCpuNumber OBJECT-TYPE
			SYNTAX Gauge32 (0..65535)
			MAX-ACCESS not-accessible
			STATUS current
			DESCRIPTION
				"Description."
			::= { hwSpuFlowOverLoadEntry 1 }


--         1.3.6.1.4.1.2011.6.122.20.1.11.1.1.2
-- 1.3.6.1.4.1.2011.6.122.20.1.11.1.1.2
-- 1.3.6.1.4.1.2011.6.122.20.1.11.1.1.2
-- 1.3.6.1.4.1.2011.6.122.20.1.11.1.1.2
-- 1.3.6.1.4.1.2011.6.122.20.1.11.1.1.2
-- 1.3.6.1.4.1.2011.6.122.20.1.11.1.1.2
-- 1.3.6.1.4.1.2011.6.122.20.1.11.1.1.2
-- 1.3.6.1.4.1.2011.6.122.20.1.11.1.1.2
		-- 1.3.6.1.4.1.2011.6.122.20.1.11.1.1.2
		hwSpuFlowOverLoadPackets OBJECT-TYPE
			SYNTAX OCTET STRING (SIZE (1..255))
			MAX-ACCESS read-only
			STATUS current
			DESCRIPTION
				"Description."
			::= { hwSpuFlowOverLoadEntry 2 }


--         1.3.6.1.4.1.2011.6.122.20.1.11.1.1.3
-- 1.3.6.1.4.1.2011.6.122.20.1.11.1.1.3
-- 1.3.6.1.4.1.2011.6.122.20.1.11.1.1.3
-- 1.3.6.1.4.1.2011.6.122.20.1.11.1.1.3
-- 1.3.6.1.4.1.2011.6.122.20.1.11.1.1.3
-- 1.3.6.1.4.1.2011.6.122.20.1.11.1.1.3
-- 1.3.6.1.4.1.2011.6.122.20.1.11.1.1.3
-- 1.3.6.1.4.1.2011.6.122.20.1.11.1.1.3
		-- 1.3.6.1.4.1.2011.6.122.20.1.11.1.1.3
		hwSpuFlowOverLoadLocation OBJECT-TYPE
			SYNTAX OCTET STRING (SIZE (0..255))
			MAX-ACCESS read-only
			STATUS current
			DESCRIPTION
				"Description."
			::= { hwSpuFlowOverLoadEntry 3 }


--         1.3.6.1.4.1.2011.6.122.20.1.12
-- 1.3.6.1.4.1.2011.6.122.20.1.12
-- 1.3.6.1.4.1.2011.6.122.20.1.12
-- 1.3.6.1.4.1.2011.6.122.20.1.12
-- 1.3.6.1.4.1.2011.6.122.20.1.12
-- 1.3.6.1.4.1.2011.6.122.20.1.12
-- 1.3.6.1.4.1.2011.6.122.20.1.12
-- 1.3.6.1.4.1.2011.6.122.20.1.12
		-- 1.3.6.1.4.1.2011.6.122.20.1.12
		hwSpuFlowOverLoadTraps OBJECT IDENTIFIER ::= { hwDeviceObject 12 }


--         1.3.6.1.4.1.2011.6.122.20.1.12.1
-- 1.3.6.1.4.1.2011.6.122.20.1.12.1
-- 1.3.6.1.4.1.2011.6.122.20.1.12.1
-- 1.3.6.1.4.1.2011.6.122.20.1.12.1
-- 1.3.6.1.4.1.2011.6.122.20.1.12.1
-- 1.3.6.1.4.1.2011.6.122.20.1.12.1
-- 1.3.6.1.4.1.2011.6.122.20.1.12.1
-- 1.3.6.1.4.1.2011.6.122.20.1.12.1
		-- 1.3.6.1.4.1.2011.6.122.20.1.12.1
		hwSpuFlowOverLoadTrap NOTIFICATION-TYPE
			OBJECTS { hwSpuFlowOverLoadLocation, hwSpuFlowOverLoadPackets }
			STATUS current
			DESCRIPTION
				"This object indicates that an VSUF is overloaded with traffic."
			::= { hwSpuFlowOverLoadTraps 1 }


--         1.3.6.1.4.1.2011.6.122.20.1.12.2
-- 1.3.6.1.4.1.2011.6.122.20.1.12.2
-- 1.3.6.1.4.1.2011.6.122.20.1.12.2
-- 1.3.6.1.4.1.2011.6.122.20.1.12.2
-- 1.3.6.1.4.1.2011.6.122.20.1.12.2
-- 1.3.6.1.4.1.2011.6.122.20.1.12.2
-- 1.3.6.1.4.1.2011.6.122.20.1.12.2
-- 1.3.6.1.4.1.2011.6.122.20.1.12.2
		-- 1.3.6.1.4.1.2011.6.122.20.1.12.2
		hwSpuFlowOverLoadRecoverTrap NOTIFICATION-TYPE
			OBJECTS { hwSpuFlowOverLoadLocation, hwSpuFlowOverLoadPackets }
			STATUS current
			DESCRIPTION
				"This object indicates that an VSUF restores from traffic overloading."
			::= { hwSpuFlowOverLoadTraps 2 }


--         1.3.6.1.4.1.2011.6.122.20.1.13
-- 1.3.6.1.4.1.2011.6.122.20.1.13
-- 1.3.6.1.4.1.2011.6.122.20.1.13
-- 1.3.6.1.4.1.2011.6.122.20.1.13
-- 1.3.6.1.4.1.2011.6.122.20.1.13
-- 1.3.6.1.4.1.2011.6.122.20.1.13
-- 1.3.6.1.4.1.2011.6.122.20.1.13
-- 1.3.6.1.4.1.2011.6.122.20.1.13
		-- 1.3.6.1.4.1.2011.6.122.20.1.13
		hwHashModeVerifyTraps OBJECT IDENTIFIER ::= { hwDeviceObject 13 }


--         1.3.6.1.4.1.2011.6.122.20.1.13.1
-- 1.3.6.1.4.1.2011.6.122.20.1.13.1
-- 1.3.6.1.4.1.2011.6.122.20.1.13.1
-- 1.3.6.1.4.1.2011.6.122.20.1.13.1
-- 1.3.6.1.4.1.2011.6.122.20.1.13.1
-- 1.3.6.1.4.1.2011.6.122.20.1.13.1
-- 1.3.6.1.4.1.2011.6.122.20.1.13.1
-- 1.3.6.1.4.1.2011.6.122.20.1.13.1
		-- 1.3.6.1.4.1.2011.6.122.20.1.13.1
		hwHashModeVerifyTrap NOTIFICATION-TYPE
			STATUS current
			DESCRIPTION
				"Description."
			::= { hwHashModeVerifyTraps 1 }


--         1.3.6.1.4.1.2011.6.122.20.1.13.2
-- 1.3.6.1.4.1.2011.6.122.20.1.13.2
-- 1.3.6.1.4.1.2011.6.122.20.1.13.2
-- 1.3.6.1.4.1.2011.6.122.20.1.13.2
-- 1.3.6.1.4.1.2011.6.122.20.1.13.2
-- 1.3.6.1.4.1.2011.6.122.20.1.13.2
-- 1.3.6.1.4.1.2011.6.122.20.1.13.2
-- 1.3.6.1.4.1.2011.6.122.20.1.13.2
		-- 1.3.6.1.4.1.2011.6.122.20.1.13.2
		hwHashModeVerifyRecoverTrap NOTIFICATION-TYPE
			STATUS current
			DESCRIPTION
				"Description."
			::= { hwHashModeVerifyTraps 2 }


--         1.3.6.1.4.1.2011.6.122.20.2
-- 1.3.6.1.4.1.2011.6.122.20.2
-- 1.3.6.1.4.1.2011.6.122.20.2
-- 1.3.6.1.4.1.2011.6.122.20.2
-- 1.3.6.1.4.1.2011.6.122.20.2
-- 1.3.6.1.4.1.2011.6.122.20.2
-- 1.3.6.1.4.1.2011.6.122.20.2
-- 1.3.6.1.4.1.2011.6.122.20.2
		-- 1.3.6.1.4.1.2011.6.122.20.2
		hwServiceObject OBJECT IDENTIFIER ::= { hwSAFEMIB 2 }


--         1.3.6.1.4.1.2011.6.122.20.2.1
-- 1.3.6.1.4.1.2011.6.122.20.2.1
-- 1.3.6.1.4.1.2011.6.122.20.2.1
-- 1.3.6.1.4.1.2011.6.122.20.2.1
-- 1.3.6.1.4.1.2011.6.122.20.2.1
-- 1.3.6.1.4.1.2011.6.122.20.2.1
-- 1.3.6.1.4.1.2011.6.122.20.2.1
-- 1.3.6.1.4.1.2011.6.122.20.2.1
		-- 1.3.6.1.4.1.2011.6.122.20.2.1
		hwServiceBasicObject OBJECT IDENTIFIER ::= { hwServiceObject 1 }


--         1.3.6.1.4.1.2011.6.122.20.2.1.1
-- 1.3.6.1.4.1.2011.6.122.20.2.1.1
-- 1.3.6.1.4.1.2011.6.122.20.2.1.1
-- 1.3.6.1.4.1.2011.6.122.20.2.1.1
-- 1.3.6.1.4.1.2011.6.122.20.2.1.1
-- 1.3.6.1.4.1.2011.6.122.20.2.1.1
-- 1.3.6.1.4.1.2011.6.122.20.2.1.1
-- 1.3.6.1.4.1.2011.6.122.20.2.1.1
		-- 1.3.6.1.4.1.2011.6.122.20.2.1.1
		hwResourceUsageTable OBJECT-TYPE
			SYNTAX SEQUENCE OF HwResourceUsageEntry
			MAX-ACCESS not-accessible
			STATUS current
			DESCRIPTION
				"The resource usage table"
			::= { hwServiceBasicObject 1 }


--         1.3.6.1.4.1.2011.6.122.20.2.1.1.1
-- 1.3.6.1.4.1.2011.6.122.20.2.1.1.1
-- 1.3.6.1.4.1.2011.6.122.20.2.1.1.1
-- 1.3.6.1.4.1.2011.6.122.20.2.1.1.1
-- 1.3.6.1.4.1.2011.6.122.20.2.1.1.1
-- 1.3.6.1.4.1.2011.6.122.20.2.1.1.1
-- 1.3.6.1.4.1.2011.6.122.20.2.1.1.1
-- 1.3.6.1.4.1.2011.6.122.20.2.1.1.1
		-- 1.3.6.1.4.1.2011.6.122.20.2.1.1.1
		hwResourceUsageEntry OBJECT-TYPE
			SYNTAX HwResourceUsageEntry
			MAX-ACCESS not-accessible
			STATUS current
			DESCRIPTION
				"The resource usage entry"
			INDEX { hwResourceUsageIndex }
			::= { hwResourceUsageTable 1 }


		HwResourceUsageEntry ::=
			SEQUENCE {
				hwResourceUsageIndex
					Gauge32,
				hwResourceLocation
					OCTET STRING,
				hwSAResourceType
					INTEGER,
				hwResourceCapacity
					Integer32,
				hwResourceUsage
					Integer32,
				hwResourceLeft
					Integer32
			 }

--         1.3.6.1.4.1.2011.6.122.20.2.1.1.1.1
-- 1.3.6.1.4.1.2011.6.122.20.2.1.1.1.1
-- 1.3.6.1.4.1.2011.6.122.20.2.1.1.1.1
-- 1.3.6.1.4.1.2011.6.122.20.2.1.1.1.1
-- 1.3.6.1.4.1.2011.6.122.20.2.1.1.1.1
-- 1.3.6.1.4.1.2011.6.122.20.2.1.1.1.1
-- 1.3.6.1.4.1.2011.6.122.20.2.1.1.1.1
-- 1.3.6.1.4.1.2011.6.122.20.2.1.1.1.1
		-- 1.3.6.1.4.1.2011.6.122.20.2.1.1.1.1
		hwResourceUsageIndex OBJECT-TYPE
			SYNTAX Gauge32 (1..2147483647)
			MAX-ACCESS not-accessible
			STATUS current
			DESCRIPTION
				"The resource usage index"
			::= { hwResourceUsageEntry 1 }


--         1.3.6.1.4.1.2011.6.122.20.2.1.1.1.2
-- 1.3.6.1.4.1.2011.6.122.20.2.1.1.1.2
-- 1.3.6.1.4.1.2011.6.122.20.2.1.1.1.2
-- 1.3.6.1.4.1.2011.6.122.20.2.1.1.1.2
-- 1.3.6.1.4.1.2011.6.122.20.2.1.1.1.2
-- 1.3.6.1.4.1.2011.6.122.20.2.1.1.1.2
-- 1.3.6.1.4.1.2011.6.122.20.2.1.1.1.2
-- 1.3.6.1.4.1.2011.6.122.20.2.1.1.1.2
		-- 1.3.6.1.4.1.2011.6.122.20.2.1.1.1.2
		hwResourceLocation OBJECT-TYPE
			SYNTAX OCTET STRING (SIZE (0..255))
			MAX-ACCESS read-only
			STATUS current
			DESCRIPTION
				"The resource location"
			::= { hwResourceUsageEntry 2 }


--         1.3.6.1.4.1.2011.6.122.20.2.1.1.1.3
-- 1.3.6.1.4.1.2011.6.122.20.2.1.1.1.3
-- 1.3.6.1.4.1.2011.6.122.20.2.1.1.1.3
-- 1.3.6.1.4.1.2011.6.122.20.2.1.1.1.3
-- 1.3.6.1.4.1.2011.6.122.20.2.1.1.1.3
-- 1.3.6.1.4.1.2011.6.122.20.2.1.1.1.3
-- 1.3.6.1.4.1.2011.6.122.20.2.1.1.1.3
-- 1.3.6.1.4.1.2011.6.122.20.2.1.1.1.3
		-- 1.3.6.1.4.1.2011.6.122.20.2.1.1.1.3
		hwSAResourceType OBJECT-TYPE
			SYNTAX INTEGER
				{
				acts(1),
				ip(2),
				spammerip(3),
				spammeracts(4),
				wormip(5),
				wormvip(6),
				botnetip(7),
				botnetvip(8),
				ddoscleanip(9),
				ddostopnip(10),
				voipsignal(11),
				voipmedia(12),
				urlacts(13),
				urlglbcls(14),
				fup(15),
				ocs(16),
				greennet(17),
				smartnet(18),
				smartbrowse(19),
				ipush(20),
				nets(21),
				gg(22)
				}
			MAX-ACCESS read-only
			STATUS current
			DESCRIPTION
				"The resource type"
			::= { hwResourceUsageEntry 3 }


--         1.3.6.1.4.1.2011.6.122.20.2.1.1.1.4
-- 1.3.6.1.4.1.2011.6.122.20.2.1.1.1.4
-- 1.3.6.1.4.1.2011.6.122.20.2.1.1.1.4
-- 1.3.6.1.4.1.2011.6.122.20.2.1.1.1.4
-- 1.3.6.1.4.1.2011.6.122.20.2.1.1.1.4
-- 1.3.6.1.4.1.2011.6.122.20.2.1.1.1.4
-- 1.3.6.1.4.1.2011.6.122.20.2.1.1.1.4
-- 1.3.6.1.4.1.2011.6.122.20.2.1.1.1.4
		-- 1.3.6.1.4.1.2011.6.122.20.2.1.1.1.4
		hwResourceCapacity OBJECT-TYPE
			SYNTAX Integer32
			MAX-ACCESS read-only
			STATUS current
			DESCRIPTION
				"The resource capacity"
			::= { hwResourceUsageEntry 4 }


--         1.3.6.1.4.1.2011.6.122.20.2.1.1.1.5
-- 1.3.6.1.4.1.2011.6.122.20.2.1.1.1.5
-- 1.3.6.1.4.1.2011.6.122.20.2.1.1.1.5
-- 1.3.6.1.4.1.2011.6.122.20.2.1.1.1.5
-- 1.3.6.1.4.1.2011.6.122.20.2.1.1.1.5
-- 1.3.6.1.4.1.2011.6.122.20.2.1.1.1.5
-- 1.3.6.1.4.1.2011.6.122.20.2.1.1.1.5
-- 1.3.6.1.4.1.2011.6.122.20.2.1.1.1.5
		-- 1.3.6.1.4.1.2011.6.122.20.2.1.1.1.5
		hwResourceUsage OBJECT-TYPE
			SYNTAX Integer32
			MAX-ACCESS read-only
			STATUS current
			DESCRIPTION
				"The resource quantity used"
			::= { hwResourceUsageEntry 5 }


--         1.3.6.1.4.1.2011.6.122.20.2.1.1.1.6
-- 1.3.6.1.4.1.2011.6.122.20.2.1.1.1.6
-- 1.3.6.1.4.1.2011.6.122.20.2.1.1.1.6
-- 1.3.6.1.4.1.2011.6.122.20.2.1.1.1.6
-- 1.3.6.1.4.1.2011.6.122.20.2.1.1.1.6
-- 1.3.6.1.4.1.2011.6.122.20.2.1.1.1.6
-- 1.3.6.1.4.1.2011.6.122.20.2.1.1.1.6
-- 1.3.6.1.4.1.2011.6.122.20.2.1.1.1.6
		-- 1.3.6.1.4.1.2011.6.122.20.2.1.1.1.6
		hwResourceLeft OBJECT-TYPE
			SYNTAX Integer32
			MAX-ACCESS read-only
			STATUS current
			DESCRIPTION
				"The resource quantity left"
			::= { hwResourceUsageEntry 6 }


--         1.3.6.1.4.1.2011.6.122.20.2.1.2
-- 1.3.6.1.4.1.2011.6.122.20.2.1.2
-- 1.3.6.1.4.1.2011.6.122.20.2.1.2
-- 1.3.6.1.4.1.2011.6.122.20.2.1.2
-- 1.3.6.1.4.1.2011.6.122.20.2.1.2
-- 1.3.6.1.4.1.2011.6.122.20.2.1.2
-- 1.3.6.1.4.1.2011.6.122.20.2.1.2
-- 1.3.6.1.4.1.2011.6.122.20.2.1.2
		-- 1.3.6.1.4.1.2011.6.122.20.2.1.2
		hwSACbbFileTable OBJECT-TYPE
			SYNTAX SEQUENCE OF HwSACbbFileEntry
			MAX-ACCESS not-accessible
			STATUS current
			DESCRIPTION
				"The SA CBB library table"
			::= { hwServiceBasicObject 2 }


--         1.3.6.1.4.1.2011.6.122.20.2.1.2.1
-- 1.3.6.1.4.1.2011.6.122.20.2.1.2.1
-- 1.3.6.1.4.1.2011.6.122.20.2.1.2.1
-- 1.3.6.1.4.1.2011.6.122.20.2.1.2.1
-- 1.3.6.1.4.1.2011.6.122.20.2.1.2.1
-- 1.3.6.1.4.1.2011.6.122.20.2.1.2.1
-- 1.3.6.1.4.1.2011.6.122.20.2.1.2.1
-- 1.3.6.1.4.1.2011.6.122.20.2.1.2.1
		-- 1.3.6.1.4.1.2011.6.122.20.2.1.2.1
		hwSACbbFileEntry OBJECT-TYPE
			SYNTAX HwSACbbFileEntry
			MAX-ACCESS not-accessible
			STATUS current
			DESCRIPTION
				"The SA CBB library entry"
			INDEX { hwSACbbEntryIndex }
			::= { hwSACbbFileTable 1 }


		HwSACbbFileEntry ::=
			SEQUENCE {
				hwSACbbEntryIndex
					Gauge32,
				hwSACbbLocation
					OCTET STRING,
				hwSACbbVersion
					Gauge32
			 }

--         1.3.6.1.4.1.2011.6.122.20.2.1.2.1.1
-- 1.3.6.1.4.1.2011.6.122.20.2.1.2.1.1
-- 1.3.6.1.4.1.2011.6.122.20.2.1.2.1.1
-- 1.3.6.1.4.1.2011.6.122.20.2.1.2.1.1
-- 1.3.6.1.4.1.2011.6.122.20.2.1.2.1.1
-- 1.3.6.1.4.1.2011.6.122.20.2.1.2.1.1
-- 1.3.6.1.4.1.2011.6.122.20.2.1.2.1.1
-- 1.3.6.1.4.1.2011.6.122.20.2.1.2.1.1
		-- 1.3.6.1.4.1.2011.6.122.20.2.1.2.1.1
		hwSACbbEntryIndex OBJECT-TYPE
			SYNTAX Gauge32 (1..2147483647)
			MAX-ACCESS not-accessible
			STATUS current
			DESCRIPTION
				"State table index of the SA signature file"
			::= { hwSACbbFileEntry 1 }


--         1.3.6.1.4.1.2011.6.122.20.2.1.2.1.2
-- 1.3.6.1.4.1.2011.6.122.20.2.1.2.1.2
-- 1.3.6.1.4.1.2011.6.122.20.2.1.2.1.2
-- 1.3.6.1.4.1.2011.6.122.20.2.1.2.1.2
-- 1.3.6.1.4.1.2011.6.122.20.2.1.2.1.2
-- 1.3.6.1.4.1.2011.6.122.20.2.1.2.1.2
-- 1.3.6.1.4.1.2011.6.122.20.2.1.2.1.2
-- 1.3.6.1.4.1.2011.6.122.20.2.1.2.1.2
		-- 1.3.6.1.4.1.2011.6.122.20.2.1.2.1.2
		hwSACbbLocation OBJECT-TYPE
			SYNTAX OCTET STRING (SIZE (0..255))
			MAX-ACCESS read-only
			STATUS current
			DESCRIPTION
				"CPU where the SA signature file resides"
			::= { hwSACbbFileEntry 2 }


--         1.3.6.1.4.1.2011.6.122.20.2.1.2.1.3
-- 1.3.6.1.4.1.2011.6.122.20.2.1.2.1.3
-- 1.3.6.1.4.1.2011.6.122.20.2.1.2.1.3
-- 1.3.6.1.4.1.2011.6.122.20.2.1.2.1.3
-- 1.3.6.1.4.1.2011.6.122.20.2.1.2.1.3
-- 1.3.6.1.4.1.2011.6.122.20.2.1.2.1.3
-- 1.3.6.1.4.1.2011.6.122.20.2.1.2.1.3
-- 1.3.6.1.4.1.2011.6.122.20.2.1.2.1.3
		-- 1.3.6.1.4.1.2011.6.122.20.2.1.2.1.3
		hwSACbbVersion OBJECT-TYPE
			SYNTAX Gauge32 (0..2147483647)
			MAX-ACCESS read-only
			STATUS current
			DESCRIPTION
				"SA CBB version"
			::= { hwSACbbFileEntry 3 }


--         1.3.6.1.4.1.2011.6.122.20.2.1.3
-- 1.3.6.1.4.1.2011.6.122.20.2.1.3
-- 1.3.6.1.4.1.2011.6.122.20.2.1.3
-- 1.3.6.1.4.1.2011.6.122.20.2.1.3
-- 1.3.6.1.4.1.2011.6.122.20.2.1.3
-- 1.3.6.1.4.1.2011.6.122.20.2.1.3
-- 1.3.6.1.4.1.2011.6.122.20.2.1.3
-- 1.3.6.1.4.1.2011.6.122.20.2.1.3
		-- 1.3.6.1.4.1.2011.6.122.20.2.1.3
		hwBWListTable OBJECT-TYPE
			SYNTAX SEQUENCE OF HwBWListEntry
			MAX-ACCESS not-accessible
			STATUS current
			DESCRIPTION
				"This table describes blacklist and whitelist information, including the blacklist or whitelist type, SPS location, and version."
			::= { hwServiceBasicObject 3 }


--         1.3.6.1.4.1.2011.6.122.20.2.1.3.1
-- 1.3.6.1.4.1.2011.6.122.20.2.1.3.1
-- 1.3.6.1.4.1.2011.6.122.20.2.1.3.1
-- 1.3.6.1.4.1.2011.6.122.20.2.1.3.1
-- 1.3.6.1.4.1.2011.6.122.20.2.1.3.1
-- 1.3.6.1.4.1.2011.6.122.20.2.1.3.1
-- 1.3.6.1.4.1.2011.6.122.20.2.1.3.1
-- 1.3.6.1.4.1.2011.6.122.20.2.1.3.1
		-- 1.3.6.1.4.1.2011.6.122.20.2.1.3.1
		hwBWListEntry OBJECT-TYPE
			SYNTAX HwBWListEntry
			MAX-ACCESS not-accessible
			STATUS current
			DESCRIPTION
				"Description."
			INDEX { hwBWListEntryIndex }
			::= { hwBWListTable 1 }


		HwBWListEntry ::=
			SEQUENCE {
				hwBWListEntryIndex
					Gauge32,
				hwBWListType
					INTEGER,
				hwBWListLocation
					OCTET STRING,
				hwBWListVersion
					Gauge32
			 }

--         1.3.6.1.4.1.2011.6.122.20.2.1.3.1.1
-- 1.3.6.1.4.1.2011.6.122.20.2.1.3.1.1
-- 1.3.6.1.4.1.2011.6.122.20.2.1.3.1.1
-- 1.3.6.1.4.1.2011.6.122.20.2.1.3.1.1
-- 1.3.6.1.4.1.2011.6.122.20.2.1.3.1.1
-- 1.3.6.1.4.1.2011.6.122.20.2.1.3.1.1
-- 1.3.6.1.4.1.2011.6.122.20.2.1.3.1.1
-- 1.3.6.1.4.1.2011.6.122.20.2.1.3.1.1
		-- 1.3.6.1.4.1.2011.6.122.20.2.1.3.1.1
		hwBWListEntryIndex OBJECT-TYPE
			SYNTAX Gauge32 (1..2147483647)
			MAX-ACCESS not-accessible
			STATUS current
			DESCRIPTION
				"The value of this object identifies the index of a blacklist and whitelist table."
			::= { hwBWListEntry 1 }


--         1.3.6.1.4.1.2011.6.122.20.2.1.3.1.2
-- 1.3.6.1.4.1.2011.6.122.20.2.1.3.1.2
-- 1.3.6.1.4.1.2011.6.122.20.2.1.3.1.2
-- 1.3.6.1.4.1.2011.6.122.20.2.1.3.1.2
-- 1.3.6.1.4.1.2011.6.122.20.2.1.3.1.2
-- 1.3.6.1.4.1.2011.6.122.20.2.1.3.1.2
-- 1.3.6.1.4.1.2011.6.122.20.2.1.3.1.2
-- 1.3.6.1.4.1.2011.6.122.20.2.1.3.1.2
		-- 1.3.6.1.4.1.2011.6.122.20.2.1.3.1.2
		hwBWListType OBJECT-TYPE
			SYNTAX INTEGER
				{
				spammerwhitelist(0),
				spammerblacklist(1),
				spammerserveriplist(2),
				spammeremailaddlist(3),
				voiptelblacklist(4),
				voipipblacklist(5),
				voipurlblacklist(6)
				}
			MAX-ACCESS read-write
			STATUS current
			DESCRIPTION
				"The value of this object identifies a blacklist or whitelist type."
			::= { hwBWListEntry 2 }


--         1.3.6.1.4.1.2011.6.122.20.2.1.3.1.3
-- 1.3.6.1.4.1.2011.6.122.20.2.1.3.1.3
-- 1.3.6.1.4.1.2011.6.122.20.2.1.3.1.3
-- 1.3.6.1.4.1.2011.6.122.20.2.1.3.1.3
-- 1.3.6.1.4.1.2011.6.122.20.2.1.3.1.3
-- 1.3.6.1.4.1.2011.6.122.20.2.1.3.1.3
-- 1.3.6.1.4.1.2011.6.122.20.2.1.3.1.3
-- 1.3.6.1.4.1.2011.6.122.20.2.1.3.1.3
		-- 1.3.6.1.4.1.2011.6.122.20.2.1.3.1.3
		hwBWListLocation OBJECT-TYPE
			SYNTAX OCTET STRING (SIZE (0..255))
			MAX-ACCESS read-only
			STATUS current
			DESCRIPTION
				"This object indicates the CPU location of a blacklist or whitelist."
			::= { hwBWListEntry 3 }


--         1.3.6.1.4.1.2011.6.122.20.2.1.3.1.4
-- 1.3.6.1.4.1.2011.6.122.20.2.1.3.1.4
-- 1.3.6.1.4.1.2011.6.122.20.2.1.3.1.4
-- 1.3.6.1.4.1.2011.6.122.20.2.1.3.1.4
-- 1.3.6.1.4.1.2011.6.122.20.2.1.3.1.4
-- 1.3.6.1.4.1.2011.6.122.20.2.1.3.1.4
-- 1.3.6.1.4.1.2011.6.122.20.2.1.3.1.4
-- 1.3.6.1.4.1.2011.6.122.20.2.1.3.1.4
		-- 1.3.6.1.4.1.2011.6.122.20.2.1.3.1.4
		hwBWListVersion OBJECT-TYPE
			SYNTAX Gauge32 (0..2147483647)
			MAX-ACCESS read-only
			STATUS current
			DESCRIPTION
				"The value of this object identifies the version of a blacklist or whitelist."
			::= { hwBWListEntry 4 }


--         1.3.6.1.4.1.2011.6.122.20.2.1.4
-- 1.3.6.1.4.1.2011.6.122.20.2.1.4
-- 1.3.6.1.4.1.2011.6.122.20.2.1.4
-- 1.3.6.1.4.1.2011.6.122.20.2.1.4
-- 1.3.6.1.4.1.2011.6.122.20.2.1.4
-- 1.3.6.1.4.1.2011.6.122.20.2.1.4
-- 1.3.6.1.4.1.2011.6.122.20.2.1.4
-- 1.3.6.1.4.1.2011.6.122.20.2.1.4
		-- 1.3.6.1.4.1.2011.6.122.20.2.1.4
		hwSpsSasLinkTable OBJECT-TYPE
			SYNTAX SEQUENCE OF HwSpsSasLinkEntry
			MAX-ACCESS not-accessible
			STATUS current
			DESCRIPTION
				"Description."
			::= { hwServiceBasicObject 4 }


--         1.3.6.1.4.1.2011.6.122.20.2.1.4.1
-- 1.3.6.1.4.1.2011.6.122.20.2.1.4.1
-- 1.3.6.1.4.1.2011.6.122.20.2.1.4.1
-- 1.3.6.1.4.1.2011.6.122.20.2.1.4.1
-- 1.3.6.1.4.1.2011.6.122.20.2.1.4.1
-- 1.3.6.1.4.1.2011.6.122.20.2.1.4.1
-- 1.3.6.1.4.1.2011.6.122.20.2.1.4.1
-- 1.3.6.1.4.1.2011.6.122.20.2.1.4.1
		-- 1.3.6.1.4.1.2011.6.122.20.2.1.4.1
		hwSpsSasLinkEntry OBJECT-TYPE
			SYNTAX HwSpsSasLinkEntry
			MAX-ACCESS not-accessible
			STATUS current
			DESCRIPTION
				"Description."
			INDEX { hwSpsSasLinkIndex }
			::= { hwSpsSasLinkTable 1 }


		HwSpsSasLinkEntry ::=
			SEQUENCE {
				hwSpsSasLinkIndex
					Gauge32,
				hwSpsSasLinkSpsLocation
					OCTET STRING,
				hwSpsSasLinkSasLocation
					OCTET STRING,
				hwSpsSasLinkSpsIP
					IpAddress,
				hwSpsSasLinkSasIP
					IpAddress,
				hwSpsSasLinkStatus
					INTEGER
			 }

--         1.3.6.1.4.1.2011.6.122.20.2.1.4.1.1
-- 1.3.6.1.4.1.2011.6.122.20.2.1.4.1.1
-- 1.3.6.1.4.1.2011.6.122.20.2.1.4.1.1
-- 1.3.6.1.4.1.2011.6.122.20.2.1.4.1.1
-- 1.3.6.1.4.1.2011.6.122.20.2.1.4.1.1
-- 1.3.6.1.4.1.2011.6.122.20.2.1.4.1.1
-- 1.3.6.1.4.1.2011.6.122.20.2.1.4.1.1
-- 1.3.6.1.4.1.2011.6.122.20.2.1.4.1.1
		-- 1.3.6.1.4.1.2011.6.122.20.2.1.4.1.1
		hwSpsSasLinkIndex OBJECT-TYPE
			SYNTAX Gauge32 (1..2147483647)
			MAX-ACCESS not-accessible
			STATUS current
			DESCRIPTION
				"Description."
			::= { hwSpsSasLinkEntry 1 }


--         1.3.6.1.4.1.2011.6.122.20.2.1.4.1.2
-- 1.3.6.1.4.1.2011.6.122.20.2.1.4.1.2
-- 1.3.6.1.4.1.2011.6.122.20.2.1.4.1.2
-- 1.3.6.1.4.1.2011.6.122.20.2.1.4.1.2
-- 1.3.6.1.4.1.2011.6.122.20.2.1.4.1.2
-- 1.3.6.1.4.1.2011.6.122.20.2.1.4.1.2
-- 1.3.6.1.4.1.2011.6.122.20.2.1.4.1.2
-- 1.3.6.1.4.1.2011.6.122.20.2.1.4.1.2
		-- 1.3.6.1.4.1.2011.6.122.20.2.1.4.1.2
		hwSpsSasLinkSpsLocation OBJECT-TYPE
			SYNTAX OCTET STRING (SIZE (0..255))
			MAX-ACCESS read-write
			STATUS current
			DESCRIPTION
				"Description."
			::= { hwSpsSasLinkEntry 2 }


--         1.3.6.1.4.1.2011.6.122.20.2.1.4.1.3
-- 1.3.6.1.4.1.2011.6.122.20.2.1.4.1.3
-- 1.3.6.1.4.1.2011.6.122.20.2.1.4.1.3
-- 1.3.6.1.4.1.2011.6.122.20.2.1.4.1.3
-- 1.3.6.1.4.1.2011.6.122.20.2.1.4.1.3
-- 1.3.6.1.4.1.2011.6.122.20.2.1.4.1.3
-- 1.3.6.1.4.1.2011.6.122.20.2.1.4.1.3
-- 1.3.6.1.4.1.2011.6.122.20.2.1.4.1.3
		-- 1.3.6.1.4.1.2011.6.122.20.2.1.4.1.3
		hwSpsSasLinkSasLocation OBJECT-TYPE
			SYNTAX OCTET STRING (SIZE (0..255))
			MAX-ACCESS read-write
			STATUS current
			DESCRIPTION
				"Description."
			::= { hwSpsSasLinkEntry 3 }


--         1.3.6.1.4.1.2011.6.122.20.2.1.4.1.4
-- 1.3.6.1.4.1.2011.6.122.20.2.1.4.1.4
-- 1.3.6.1.4.1.2011.6.122.20.2.1.4.1.4
-- 1.3.6.1.4.1.2011.6.122.20.2.1.4.1.4
-- 1.3.6.1.4.1.2011.6.122.20.2.1.4.1.4
-- 1.3.6.1.4.1.2011.6.122.20.2.1.4.1.4
-- 1.3.6.1.4.1.2011.6.122.20.2.1.4.1.4
-- 1.3.6.1.4.1.2011.6.122.20.2.1.4.1.4
		-- 1.3.6.1.4.1.2011.6.122.20.2.1.4.1.4
		hwSpsSasLinkSpsIP OBJECT-TYPE
			SYNTAX IpAddress
			MAX-ACCESS read-only
			STATUS current
			DESCRIPTION
				"Description."
			::= { hwSpsSasLinkEntry 4 }


--         1.3.6.1.4.1.2011.6.122.20.2.1.4.1.5
-- 1.3.6.1.4.1.2011.6.122.20.2.1.4.1.5
-- 1.3.6.1.4.1.2011.6.122.20.2.1.4.1.5
-- 1.3.6.1.4.1.2011.6.122.20.2.1.4.1.5
-- 1.3.6.1.4.1.2011.6.122.20.2.1.4.1.5
-- 1.3.6.1.4.1.2011.6.122.20.2.1.4.1.5
-- 1.3.6.1.4.1.2011.6.122.20.2.1.4.1.5
-- 1.3.6.1.4.1.2011.6.122.20.2.1.4.1.5
		-- 1.3.6.1.4.1.2011.6.122.20.2.1.4.1.5
		hwSpsSasLinkSasIP OBJECT-TYPE
			SYNTAX IpAddress
			MAX-ACCESS read-only
			STATUS current
			DESCRIPTION
				"Description."
			::= { hwSpsSasLinkEntry 5 }


--         1.3.6.1.4.1.2011.6.122.20.2.1.4.1.6
-- 1.3.6.1.4.1.2011.6.122.20.2.1.4.1.6
-- 1.3.6.1.4.1.2011.6.122.20.2.1.4.1.6
-- 1.3.6.1.4.1.2011.6.122.20.2.1.4.1.6
-- 1.3.6.1.4.1.2011.6.122.20.2.1.4.1.6
-- 1.3.6.1.4.1.2011.6.122.20.2.1.4.1.6
-- 1.3.6.1.4.1.2011.6.122.20.2.1.4.1.6
-- 1.3.6.1.4.1.2011.6.122.20.2.1.4.1.6
		-- 1.3.6.1.4.1.2011.6.122.20.2.1.4.1.6
		hwSpsSasLinkStatus OBJECT-TYPE
			SYNTAX INTEGER
				{
				up(1),
				down(2)
				}
			MAX-ACCESS read-only
			STATUS current
			DESCRIPTION
				"Description."
			::= { hwSpsSasLinkEntry 6 }


--         1.3.6.1.4.1.2011.6.122.20.2.1.5
-- 1.3.6.1.4.1.2011.6.122.20.2.1.5
-- 1.3.6.1.4.1.2011.6.122.20.2.1.5
-- 1.3.6.1.4.1.2011.6.122.20.2.1.5
-- 1.3.6.1.4.1.2011.6.122.20.2.1.5
-- 1.3.6.1.4.1.2011.6.122.20.2.1.5
-- 1.3.6.1.4.1.2011.6.122.20.2.1.5
-- 1.3.6.1.4.1.2011.6.122.20.2.1.5
		-- 1.3.6.1.4.1.2011.6.122.20.2.1.5
		hwSpuCompLinkTable OBJECT-TYPE
			SYNTAX SEQUENCE OF HwSpuCompLinkEntry
			MAX-ACCESS not-accessible
			STATUS current
			DESCRIPTION
				"This table describes component connection information, including the SAS location, back-end component type, IP address and port number of a back-end component connected to a front-end component, and packet statistics."
			::= { hwServiceBasicObject 5 }


--         1.3.6.1.4.1.2011.6.122.20.2.1.5.1
-- 1.3.6.1.4.1.2011.6.122.20.2.1.5.1
-- 1.3.6.1.4.1.2011.6.122.20.2.1.5.1
-- 1.3.6.1.4.1.2011.6.122.20.2.1.5.1
-- 1.3.6.1.4.1.2011.6.122.20.2.1.5.1
-- 1.3.6.1.4.1.2011.6.122.20.2.1.5.1
-- 1.3.6.1.4.1.2011.6.122.20.2.1.5.1
-- 1.3.6.1.4.1.2011.6.122.20.2.1.5.1
		-- 1.3.6.1.4.1.2011.6.122.20.2.1.5.1
		hwSpuCompLinkEntry OBJECT-TYPE
			SYNTAX HwSpuCompLinkEntry
			MAX-ACCESS not-accessible
			STATUS current
			DESCRIPTION
				"Description."
			INDEX { hwSpuCompLinkIndex }
			::= { hwSpuCompLinkTable 1 }


		HwSpuCompLinkEntry ::=
			SEQUENCE {
				hwSpuCompLinkIndex
					Gauge32,
				hwSpuCompLinkSysLocation
					OCTET STRING,
				hwSpuCompLinkComponentType
					INTEGER,
				hwSpuCompLinkCurrentDestIP
					IpAddress,
				hwSpuCompLinkCurrentDestPort
					Gauge32,
				hwSpuCompLinkConnState
					Integer32,
				hwSpuCompLinkNumPacketsSent
					Counter32,
				hwSpuCompLinkBytesSent
					Counter32,
				hwSpuCompLinkNumPacketsRecv
					Counter32,
				hwSpuCompLinkBytesRecv
					Counter32,
				hwSpuCompLinkNumErrPacketsRecv
					Counter32
			 }

--         1.3.6.1.4.1.2011.6.122.20.2.1.5.1.1
-- 1.3.6.1.4.1.2011.6.122.20.2.1.5.1.1
-- 1.3.6.1.4.1.2011.6.122.20.2.1.5.1.1
-- 1.3.6.1.4.1.2011.6.122.20.2.1.5.1.1
-- 1.3.6.1.4.1.2011.6.122.20.2.1.5.1.1
-- 1.3.6.1.4.1.2011.6.122.20.2.1.5.1.1
-- 1.3.6.1.4.1.2011.6.122.20.2.1.5.1.1
-- 1.3.6.1.4.1.2011.6.122.20.2.1.5.1.1
		-- 1.3.6.1.4.1.2011.6.122.20.2.1.5.1.1
		hwSpuCompLinkIndex OBJECT-TYPE
			SYNTAX Gauge32 (1..2147483647)
			MAX-ACCESS not-accessible
			STATUS current
			DESCRIPTION
				"The value of this object identifies the index of a component connection table."
			::= { hwSpuCompLinkEntry 1 }


--         1.3.6.1.4.1.2011.6.122.20.2.1.5.1.2
-- 1.3.6.1.4.1.2011.6.122.20.2.1.5.1.2
-- 1.3.6.1.4.1.2011.6.122.20.2.1.5.1.2
-- 1.3.6.1.4.1.2011.6.122.20.2.1.5.1.2
-- 1.3.6.1.4.1.2011.6.122.20.2.1.5.1.2
-- 1.3.6.1.4.1.2011.6.122.20.2.1.5.1.2
-- 1.3.6.1.4.1.2011.6.122.20.2.1.5.1.2
-- 1.3.6.1.4.1.2011.6.122.20.2.1.5.1.2
		-- 1.3.6.1.4.1.2011.6.122.20.2.1.5.1.2
		hwSpuCompLinkSysLocation OBJECT-TYPE
			SYNTAX OCTET STRING (SIZE (0..255))
			MAX-ACCESS read-only
			STATUS current
			DESCRIPTION
				"This object indicates the location of an SAS."
			::= { hwSpuCompLinkEntry 2 }


--         1.3.6.1.4.1.2011.6.122.20.2.1.5.1.3
-- 1.3.6.1.4.1.2011.6.122.20.2.1.5.1.3
-- 1.3.6.1.4.1.2011.6.122.20.2.1.5.1.3
-- 1.3.6.1.4.1.2011.6.122.20.2.1.5.1.3
-- 1.3.6.1.4.1.2011.6.122.20.2.1.5.1.3
-- 1.3.6.1.4.1.2011.6.122.20.2.1.5.1.3
-- 1.3.6.1.4.1.2011.6.122.20.2.1.5.1.3
-- 1.3.6.1.4.1.2011.6.122.20.2.1.5.1.3
		-- 1.3.6.1.4.1.2011.6.122.20.2.1.5.1.3
		hwSpuCompLinkComponentType OBJECT-TYPE
			SYNTAX INTEGER
				{
				dataanalysisserver(1),
				policyserver(2),
				managementserver(3),
				serviceprobesystem(4),
				serviceanalysesystem(5),
				radiusproxy(6),
				updateserver(7),
				urlhealthcenter(8),
				onlinechargingsystem(9),
				policyandchargingrulesfunction(10),
				quotamanagementserver(11)
				}
			MAX-ACCESS read-only
			STATUS current
			DESCRIPTION
				"The value of this object identifies the type of a back-end component."
			::= { hwSpuCompLinkEntry 3 }


--         1.3.6.1.4.1.2011.6.122.20.2.1.5.1.4
-- 1.3.6.1.4.1.2011.6.122.20.2.1.5.1.4
-- 1.3.6.1.4.1.2011.6.122.20.2.1.5.1.4
-- 1.3.6.1.4.1.2011.6.122.20.2.1.5.1.4
-- 1.3.6.1.4.1.2011.6.122.20.2.1.5.1.4
-- 1.3.6.1.4.1.2011.6.122.20.2.1.5.1.4
-- 1.3.6.1.4.1.2011.6.122.20.2.1.5.1.4
-- 1.3.6.1.4.1.2011.6.122.20.2.1.5.1.4
		-- 1.3.6.1.4.1.2011.6.122.20.2.1.5.1.4
		hwSpuCompLinkCurrentDestIP OBJECT-TYPE
			SYNTAX IpAddress
			MAX-ACCESS read-only
			STATUS current
			DESCRIPTION
				"This object indicates the IP address of a back-end component connected to a front-end component."
			::= { hwSpuCompLinkEntry 4 }


--         1.3.6.1.4.1.2011.6.122.20.2.1.5.1.5
-- 1.3.6.1.4.1.2011.6.122.20.2.1.5.1.5
-- 1.3.6.1.4.1.2011.6.122.20.2.1.5.1.5
-- 1.3.6.1.4.1.2011.6.122.20.2.1.5.1.5
-- 1.3.6.1.4.1.2011.6.122.20.2.1.5.1.5
-- 1.3.6.1.4.1.2011.6.122.20.2.1.5.1.5
-- 1.3.6.1.4.1.2011.6.122.20.2.1.5.1.5
-- 1.3.6.1.4.1.2011.6.122.20.2.1.5.1.5
		-- 1.3.6.1.4.1.2011.6.122.20.2.1.5.1.5
		hwSpuCompLinkCurrentDestPort OBJECT-TYPE
			SYNTAX Gauge32 (1..65535)
			MAX-ACCESS read-only
			STATUS current
			DESCRIPTION
				"This object indicates the port number of a back-end component connected to a front-end component."
			::= { hwSpuCompLinkEntry 5 }


--         1.3.6.1.4.1.2011.6.122.20.2.1.5.1.6
-- 1.3.6.1.4.1.2011.6.122.20.2.1.5.1.6
-- 1.3.6.1.4.1.2011.6.122.20.2.1.5.1.6
-- 1.3.6.1.4.1.2011.6.122.20.2.1.5.1.6
-- 1.3.6.1.4.1.2011.6.122.20.2.1.5.1.6
-- 1.3.6.1.4.1.2011.6.122.20.2.1.5.1.6
-- 1.3.6.1.4.1.2011.6.122.20.2.1.5.1.6
-- 1.3.6.1.4.1.2011.6.122.20.2.1.5.1.6
		-- 1.3.6.1.4.1.2011.6.122.20.2.1.5.1.6
		hwSpuCompLinkConnState OBJECT-TYPE
			SYNTAX Integer32
			MAX-ACCESS read-only
			STATUS current
			DESCRIPTION
				"The value of this object identifies the connection status between a front-end SAS and a back-end component."
			::= { hwSpuCompLinkEntry 6 }


--         1.3.6.1.4.1.2011.6.122.20.2.1.5.1.7
-- 1.3.6.1.4.1.2011.6.122.20.2.1.5.1.7
-- 1.3.6.1.4.1.2011.6.122.20.2.1.5.1.7
-- 1.3.6.1.4.1.2011.6.122.20.2.1.5.1.7
-- 1.3.6.1.4.1.2011.6.122.20.2.1.5.1.7
-- 1.3.6.1.4.1.2011.6.122.20.2.1.5.1.7
-- 1.3.6.1.4.1.2011.6.122.20.2.1.5.1.7
-- 1.3.6.1.4.1.2011.6.122.20.2.1.5.1.7
		-- 1.3.6.1.4.1.2011.6.122.20.2.1.5.1.7
		hwSpuCompLinkNumPacketsSent OBJECT-TYPE
			SYNTAX Counter32
			MAX-ACCESS read-only
			STATUS current
			DESCRIPTION
				"The value of this object identifies the number of sent protocol packets."
			::= { hwSpuCompLinkEntry 7 }


--         1.3.6.1.4.1.2011.6.122.20.2.1.5.1.8
-- 1.3.6.1.4.1.2011.6.122.20.2.1.5.1.8
-- 1.3.6.1.4.1.2011.6.122.20.2.1.5.1.8
-- 1.3.6.1.4.1.2011.6.122.20.2.1.5.1.8
-- 1.3.6.1.4.1.2011.6.122.20.2.1.5.1.8
-- 1.3.6.1.4.1.2011.6.122.20.2.1.5.1.8
-- 1.3.6.1.4.1.2011.6.122.20.2.1.5.1.8
-- 1.3.6.1.4.1.2011.6.122.20.2.1.5.1.8
		-- 1.3.6.1.4.1.2011.6.122.20.2.1.5.1.8
		hwSpuCompLinkBytesSent OBJECT-TYPE
			SYNTAX Counter32
			MAX-ACCESS read-only
			STATUS current
			DESCRIPTION
				"The value of this object identifies the number of bytes of sent protocol packets."
			::= { hwSpuCompLinkEntry 8 }


--         1.3.6.1.4.1.2011.6.122.20.2.1.5.1.9
-- 1.3.6.1.4.1.2011.6.122.20.2.1.5.1.9
-- 1.3.6.1.4.1.2011.6.122.20.2.1.5.1.9
-- 1.3.6.1.4.1.2011.6.122.20.2.1.5.1.9
-- 1.3.6.1.4.1.2011.6.122.20.2.1.5.1.9
-- 1.3.6.1.4.1.2011.6.122.20.2.1.5.1.9
-- 1.3.6.1.4.1.2011.6.122.20.2.1.5.1.9
-- 1.3.6.1.4.1.2011.6.122.20.2.1.5.1.9
		-- 1.3.6.1.4.1.2011.6.122.20.2.1.5.1.9
		hwSpuCompLinkNumPacketsRecv OBJECT-TYPE
			SYNTAX Counter32
			MAX-ACCESS read-only
			STATUS current
			DESCRIPTION
				"The value of this object identifies the number of received protocol packets."
			::= { hwSpuCompLinkEntry 9 }


--         1.3.6.1.4.1.2011.6.122.20.2.1.5.1.10
-- 1.3.6.1.4.1.2011.6.122.20.2.1.5.1.10
-- 1.3.6.1.4.1.2011.6.122.20.2.1.5.1.10
-- 1.3.6.1.4.1.2011.6.122.20.2.1.5.1.10
-- 1.3.6.1.4.1.2011.6.122.20.2.1.5.1.10
-- 1.3.6.1.4.1.2011.6.122.20.2.1.5.1.10
-- 1.3.6.1.4.1.2011.6.122.20.2.1.5.1.10
-- 1.3.6.1.4.1.2011.6.122.20.2.1.5.1.10
		-- 1.3.6.1.4.1.2011.6.122.20.2.1.5.1.10
		hwSpuCompLinkBytesRecv OBJECT-TYPE
			SYNTAX Counter32
			MAX-ACCESS read-only
			STATUS current
			DESCRIPTION
				"The value of this object identifies the number of bytes of received protocol packets."
			::= { hwSpuCompLinkEntry 10 }


--         1.3.6.1.4.1.2011.6.122.20.2.1.5.1.11
-- 1.3.6.1.4.1.2011.6.122.20.2.1.5.1.11
-- 1.3.6.1.4.1.2011.6.122.20.2.1.5.1.11
-- 1.3.6.1.4.1.2011.6.122.20.2.1.5.1.11
-- 1.3.6.1.4.1.2011.6.122.20.2.1.5.1.11
-- 1.3.6.1.4.1.2011.6.122.20.2.1.5.1.11
-- 1.3.6.1.4.1.2011.6.122.20.2.1.5.1.11
-- 1.3.6.1.4.1.2011.6.122.20.2.1.5.1.11
		-- 1.3.6.1.4.1.2011.6.122.20.2.1.5.1.11
		hwSpuCompLinkNumErrPacketsRecv OBJECT-TYPE
			SYNTAX Counter32
			MAX-ACCESS read-only
			STATUS current
			DESCRIPTION
				"The value of this object identifies the number of received invalid protocol packets."
			::= { hwSpuCompLinkEntry 11 }


--         1.3.6.1.4.1.2011.6.122.20.2.1.6
-- 1.3.6.1.4.1.2011.6.122.20.2.1.6
-- 1.3.6.1.4.1.2011.6.122.20.2.1.6
-- 1.3.6.1.4.1.2011.6.122.20.2.1.6
-- 1.3.6.1.4.1.2011.6.122.20.2.1.6
-- 1.3.6.1.4.1.2011.6.122.20.2.1.6
-- 1.3.6.1.4.1.2011.6.122.20.2.1.6
-- 1.3.6.1.4.1.2011.6.122.20.2.1.6
		-- 1.3.6.1.4.1.2011.6.122.20.2.1.6
		hwSAFdiConnectTable OBJECT-TYPE
			SYNTAX SEQUENCE OF HwSAFdiConnectEntry
			MAX-ACCESS not-accessible
			STATUS current
			DESCRIPTION
				"Description."
			::= { hwServiceBasicObject 6 }


--         1.3.6.1.4.1.2011.6.122.20.2.1.6.1
-- 1.3.6.1.4.1.2011.6.122.20.2.1.6.1
-- 1.3.6.1.4.1.2011.6.122.20.2.1.6.1
-- 1.3.6.1.4.1.2011.6.122.20.2.1.6.1
-- 1.3.6.1.4.1.2011.6.122.20.2.1.6.1
-- 1.3.6.1.4.1.2011.6.122.20.2.1.6.1
-- 1.3.6.1.4.1.2011.6.122.20.2.1.6.1
-- 1.3.6.1.4.1.2011.6.122.20.2.1.6.1
		-- 1.3.6.1.4.1.2011.6.122.20.2.1.6.1
		hwSAFdiConnectEntry OBJECT-TYPE
			SYNTAX HwSAFdiConnectEntry
			MAX-ACCESS not-accessible
			STATUS current
			DESCRIPTION
				"Description."
			INDEX { hwSAFdiConnectIndex }
			::= { hwSAFdiConnectTable 1 }


		HwSAFdiConnectEntry ::=
			SEQUENCE {
				hwSAFdiConnectIndex
					Gauge32,
				hwSAFdiConnectLocation
					OCTET STRING,
				hwSysFdiInstanceID
					Counter32,
				hwSysFdiDestMasterIP
					IpAddress,
				hwSysFdiDestBackupIP
					IpAddress
			 }

--         1.3.6.1.4.1.2011.6.122.20.2.1.6.1.1
-- 1.3.6.1.4.1.2011.6.122.20.2.1.6.1.1
-- 1.3.6.1.4.1.2011.6.122.20.2.1.6.1.1
-- 1.3.6.1.4.1.2011.6.122.20.2.1.6.1.1
-- 1.3.6.1.4.1.2011.6.122.20.2.1.6.1.1
-- 1.3.6.1.4.1.2011.6.122.20.2.1.6.1.1
-- 1.3.6.1.4.1.2011.6.122.20.2.1.6.1.1
-- 1.3.6.1.4.1.2011.6.122.20.2.1.6.1.1
		-- 1.3.6.1.4.1.2011.6.122.20.2.1.6.1.1
		hwSAFdiConnectIndex OBJECT-TYPE
			SYNTAX Gauge32 (1..2147483647)
			MAX-ACCESS not-accessible
			STATUS current
			DESCRIPTION
				"Description."
			::= { hwSAFdiConnectEntry 1 }


--         1.3.6.1.4.1.2011.6.122.20.2.1.6.1.2
-- 1.3.6.1.4.1.2011.6.122.20.2.1.6.1.2
-- 1.3.6.1.4.1.2011.6.122.20.2.1.6.1.2
-- 1.3.6.1.4.1.2011.6.122.20.2.1.6.1.2
-- 1.3.6.1.4.1.2011.6.122.20.2.1.6.1.2
-- 1.3.6.1.4.1.2011.6.122.20.2.1.6.1.2
-- 1.3.6.1.4.1.2011.6.122.20.2.1.6.1.2
-- 1.3.6.1.4.1.2011.6.122.20.2.1.6.1.2
		-- 1.3.6.1.4.1.2011.6.122.20.2.1.6.1.2
		hwSAFdiConnectLocation OBJECT-TYPE
			SYNTAX OCTET STRING (SIZE (0..255))
			MAX-ACCESS read-write
			STATUS current
			DESCRIPTION
				"Description."
			::= { hwSAFdiConnectEntry 2 }


--         1.3.6.1.4.1.2011.6.122.20.2.1.6.1.3
-- 1.3.6.1.4.1.2011.6.122.20.2.1.6.1.3
-- 1.3.6.1.4.1.2011.6.122.20.2.1.6.1.3
-- 1.3.6.1.4.1.2011.6.122.20.2.1.6.1.3
-- 1.3.6.1.4.1.2011.6.122.20.2.1.6.1.3
-- 1.3.6.1.4.1.2011.6.122.20.2.1.6.1.3
-- 1.3.6.1.4.1.2011.6.122.20.2.1.6.1.3
-- 1.3.6.1.4.1.2011.6.122.20.2.1.6.1.3
		-- 1.3.6.1.4.1.2011.6.122.20.2.1.6.1.3
		hwSysFdiInstanceID OBJECT-TYPE
			SYNTAX Counter32
			MAX-ACCESS read-only
			STATUS current
			DESCRIPTION
				"Description."
			::= { hwSAFdiConnectEntry 3 }


--         1.3.6.1.4.1.2011.6.122.20.2.1.6.1.4
-- 1.3.6.1.4.1.2011.6.122.20.2.1.6.1.4
-- 1.3.6.1.4.1.2011.6.122.20.2.1.6.1.4
-- 1.3.6.1.4.1.2011.6.122.20.2.1.6.1.4
-- 1.3.6.1.4.1.2011.6.122.20.2.1.6.1.4
-- 1.3.6.1.4.1.2011.6.122.20.2.1.6.1.4
-- 1.3.6.1.4.1.2011.6.122.20.2.1.6.1.4
-- 1.3.6.1.4.1.2011.6.122.20.2.1.6.1.4
		-- 1.3.6.1.4.1.2011.6.122.20.2.1.6.1.4
		hwSysFdiDestMasterIP OBJECT-TYPE
			SYNTAX IpAddress
			MAX-ACCESS read-write
			STATUS current
			DESCRIPTION
				"Description."
			::= { hwSAFdiConnectEntry 4 }


--         1.3.6.1.4.1.2011.6.122.20.2.1.6.1.5
-- 1.3.6.1.4.1.2011.6.122.20.2.1.6.1.5
-- 1.3.6.1.4.1.2011.6.122.20.2.1.6.1.5
-- 1.3.6.1.4.1.2011.6.122.20.2.1.6.1.5
-- 1.3.6.1.4.1.2011.6.122.20.2.1.6.1.5
-- 1.3.6.1.4.1.2011.6.122.20.2.1.6.1.5
-- 1.3.6.1.4.1.2011.6.122.20.2.1.6.1.5
-- 1.3.6.1.4.1.2011.6.122.20.2.1.6.1.5
		-- 1.3.6.1.4.1.2011.6.122.20.2.1.6.1.5
		hwSysFdiDestBackupIP OBJECT-TYPE
			SYNTAX IpAddress
			MAX-ACCESS read-write
			STATUS current
			DESCRIPTION
				"Description."
			::= { hwSAFdiConnectEntry 5 }


--         1.3.6.1.4.1.2011.6.122.20.2.1.7
-- 1.3.6.1.4.1.2011.6.122.20.2.1.7
-- 1.3.6.1.4.1.2011.6.122.20.2.1.7
-- 1.3.6.1.4.1.2011.6.122.20.2.1.7
-- 1.3.6.1.4.1.2011.6.122.20.2.1.7
-- 1.3.6.1.4.1.2011.6.122.20.2.1.7
-- 1.3.6.1.4.1.2011.6.122.20.2.1.7
-- 1.3.6.1.4.1.2011.6.122.20.2.1.7
		-- 1.3.6.1.4.1.2011.6.122.20.2.1.7
		hwSpsRadisInfoTable OBJECT-TYPE
			SYNTAX SEQUENCE OF HwSpsRadisInfoEntry
			MAX-ACCESS not-accessible
			STATUS current
			DESCRIPTION
				"Description."
			::= { hwServiceBasicObject 7 }


--         1.3.6.1.4.1.2011.6.122.20.2.1.7.1
-- 1.3.6.1.4.1.2011.6.122.20.2.1.7.1
-- 1.3.6.1.4.1.2011.6.122.20.2.1.7.1
-- 1.3.6.1.4.1.2011.6.122.20.2.1.7.1
-- 1.3.6.1.4.1.2011.6.122.20.2.1.7.1
-- 1.3.6.1.4.1.2011.6.122.20.2.1.7.1
-- 1.3.6.1.4.1.2011.6.122.20.2.1.7.1
-- 1.3.6.1.4.1.2011.6.122.20.2.1.7.1
		-- 1.3.6.1.4.1.2011.6.122.20.2.1.7.1
		hwSpsRadisInfoEntry OBJECT-TYPE
			SYNTAX HwSpsRadisInfoEntry
			MAX-ACCESS not-accessible
			STATUS current
			DESCRIPTION
				"Description."
			INDEX { hwSpsRadisInfoIndex }
			::= { hwSpsRadisInfoTable 1 }


		HwSpsRadisInfoEntry ::=
			SEQUENCE {
				hwSpsRadisInfoIndex
					Gauge32,
				hwSnifferInfoLocation
					OCTET STRING,
				hwPacketSendCount
					Counter64,
				hwPacketErrCount
					Counter64,
				hwSnifferSrcIPAddress
					IpAddress,
				hwSnifferDstIPAddress
					IpAddress,
				hwSnifferInfoState
					INTEGER
			 }

--         1.3.6.1.4.1.2011.6.122.20.2.1.7.1.1
-- 1.3.6.1.4.1.2011.6.122.20.2.1.7.1.1
-- 1.3.6.1.4.1.2011.6.122.20.2.1.7.1.1
-- 1.3.6.1.4.1.2011.6.122.20.2.1.7.1.1
-- 1.3.6.1.4.1.2011.6.122.20.2.1.7.1.1
-- 1.3.6.1.4.1.2011.6.122.20.2.1.7.1.1
-- 1.3.6.1.4.1.2011.6.122.20.2.1.7.1.1
-- 1.3.6.1.4.1.2011.6.122.20.2.1.7.1.1
		-- 1.3.6.1.4.1.2011.6.122.20.2.1.7.1.1
		hwSpsRadisInfoIndex OBJECT-TYPE
			SYNTAX Gauge32 (0..2147483647)
			MAX-ACCESS not-accessible
			STATUS current
			DESCRIPTION
				"Description."
			::= { hwSpsRadisInfoEntry 1 }


--         1.3.6.1.4.1.2011.6.122.20.2.1.7.1.2
-- 1.3.6.1.4.1.2011.6.122.20.2.1.7.1.2
-- 1.3.6.1.4.1.2011.6.122.20.2.1.7.1.2
-- 1.3.6.1.4.1.2011.6.122.20.2.1.7.1.2
-- 1.3.6.1.4.1.2011.6.122.20.2.1.7.1.2
-- 1.3.6.1.4.1.2011.6.122.20.2.1.7.1.2
-- 1.3.6.1.4.1.2011.6.122.20.2.1.7.1.2
-- 1.3.6.1.4.1.2011.6.122.20.2.1.7.1.2
		-- 1.3.6.1.4.1.2011.6.122.20.2.1.7.1.2
		hwSnifferInfoLocation OBJECT-TYPE
			SYNTAX OCTET STRING (SIZE (0..255))
			MAX-ACCESS read-write
			STATUS current
			DESCRIPTION
				"Description."
			::= { hwSpsRadisInfoEntry 2 }


--         1.3.6.1.4.1.2011.6.122.20.2.1.7.1.3
-- 1.3.6.1.4.1.2011.6.122.20.2.1.7.1.3
-- 1.3.6.1.4.1.2011.6.122.20.2.1.7.1.3
-- 1.3.6.1.4.1.2011.6.122.20.2.1.7.1.3
-- 1.3.6.1.4.1.2011.6.122.20.2.1.7.1.3
-- 1.3.6.1.4.1.2011.6.122.20.2.1.7.1.3
-- 1.3.6.1.4.1.2011.6.122.20.2.1.7.1.3
-- 1.3.6.1.4.1.2011.6.122.20.2.1.7.1.3
		-- 1.3.6.1.4.1.2011.6.122.20.2.1.7.1.3
		hwPacketSendCount OBJECT-TYPE
			SYNTAX Counter64
			MAX-ACCESS read-only
			STATUS current
			DESCRIPTION
				"Description."
			::= { hwSpsRadisInfoEntry 3 }


--         1.3.6.1.4.1.2011.6.122.20.2.1.7.1.4
-- 1.3.6.1.4.1.2011.6.122.20.2.1.7.1.4
-- 1.3.6.1.4.1.2011.6.122.20.2.1.7.1.4
-- 1.3.6.1.4.1.2011.6.122.20.2.1.7.1.4
-- 1.3.6.1.4.1.2011.6.122.20.2.1.7.1.4
-- 1.3.6.1.4.1.2011.6.122.20.2.1.7.1.4
-- 1.3.6.1.4.1.2011.6.122.20.2.1.7.1.4
-- 1.3.6.1.4.1.2011.6.122.20.2.1.7.1.4
		-- 1.3.6.1.4.1.2011.6.122.20.2.1.7.1.4
		hwPacketErrCount OBJECT-TYPE
			SYNTAX Counter64
			MAX-ACCESS read-only
			STATUS current
			DESCRIPTION
				"Description."
			::= { hwSpsRadisInfoEntry 4 }


--         1.3.6.1.4.1.2011.6.122.20.2.1.7.1.5
-- 1.3.6.1.4.1.2011.6.122.20.2.1.7.1.5
-- 1.3.6.1.4.1.2011.6.122.20.2.1.7.1.5
-- 1.3.6.1.4.1.2011.6.122.20.2.1.7.1.5
-- 1.3.6.1.4.1.2011.6.122.20.2.1.7.1.5
-- 1.3.6.1.4.1.2011.6.122.20.2.1.7.1.5
-- 1.3.6.1.4.1.2011.6.122.20.2.1.7.1.5
-- 1.3.6.1.4.1.2011.6.122.20.2.1.7.1.5
		-- 1.3.6.1.4.1.2011.6.122.20.2.1.7.1.5
		hwSnifferSrcIPAddress OBJECT-TYPE
			SYNTAX IpAddress
			MAX-ACCESS read-write
			STATUS current
			DESCRIPTION
				"Description."
			::= { hwSpsRadisInfoEntry 5 }


--         1.3.6.1.4.1.2011.6.122.20.2.1.7.1.6
-- 1.3.6.1.4.1.2011.6.122.20.2.1.7.1.6
-- 1.3.6.1.4.1.2011.6.122.20.2.1.7.1.6
-- 1.3.6.1.4.1.2011.6.122.20.2.1.7.1.6
-- 1.3.6.1.4.1.2011.6.122.20.2.1.7.1.6
-- 1.3.6.1.4.1.2011.6.122.20.2.1.7.1.6
-- 1.3.6.1.4.1.2011.6.122.20.2.1.7.1.6
-- 1.3.6.1.4.1.2011.6.122.20.2.1.7.1.6
		-- 1.3.6.1.4.1.2011.6.122.20.2.1.7.1.6
		hwSnifferDstIPAddress OBJECT-TYPE
			SYNTAX IpAddress
			MAX-ACCESS read-write
			STATUS current
			DESCRIPTION
				"Description."
			::= { hwSpsRadisInfoEntry 6 }


--         1.3.6.1.4.1.2011.6.122.20.2.1.7.1.7
-- 1.3.6.1.4.1.2011.6.122.20.2.1.7.1.7
-- 1.3.6.1.4.1.2011.6.122.20.2.1.7.1.7
-- 1.3.6.1.4.1.2011.6.122.20.2.1.7.1.7
-- 1.3.6.1.4.1.2011.6.122.20.2.1.7.1.7
-- 1.3.6.1.4.1.2011.6.122.20.2.1.7.1.7
-- 1.3.6.1.4.1.2011.6.122.20.2.1.7.1.7
-- 1.3.6.1.4.1.2011.6.122.20.2.1.7.1.7
		-- 1.3.6.1.4.1.2011.6.122.20.2.1.7.1.7
		hwSnifferInfoState OBJECT-TYPE
			SYNTAX INTEGER
				{
				normal(1),
				abnormal(2)
				}
			MAX-ACCESS read-write
			STATUS current
			DESCRIPTION
				"Description."
			::= { hwSpsRadisInfoEntry 7 }


--         1.3.6.1.4.1.2011.6.122.20.2.1.8
-- 1.3.6.1.4.1.2011.6.122.20.2.1.8
-- 1.3.6.1.4.1.2011.6.122.20.2.1.8
-- 1.3.6.1.4.1.2011.6.122.20.2.1.8
-- 1.3.6.1.4.1.2011.6.122.20.2.1.8
-- 1.3.6.1.4.1.2011.6.122.20.2.1.8
-- 1.3.6.1.4.1.2011.6.122.20.2.1.8
-- 1.3.6.1.4.1.2011.6.122.20.2.1.8
		-- 1.3.6.1.4.1.2011.6.122.20.2.1.8
		hwSpsUcssLinkTable OBJECT-TYPE
			SYNTAX SEQUENCE OF HwSpsUcssLinkEntry
			MAX-ACCESS not-accessible
			STATUS current
			DESCRIPTION
				"This table describes SPS and UCSS connection information, including the location and IP address of an SPS and the IP address of the corresponding UCSS."
			::= { hwServiceBasicObject 8 }


--         1.3.6.1.4.1.2011.6.122.20.2.1.8.1
-- 1.3.6.1.4.1.2011.6.122.20.2.1.8.1
-- 1.3.6.1.4.1.2011.6.122.20.2.1.8.1
-- 1.3.6.1.4.1.2011.6.122.20.2.1.8.1
-- 1.3.6.1.4.1.2011.6.122.20.2.1.8.1
-- 1.3.6.1.4.1.2011.6.122.20.2.1.8.1
-- 1.3.6.1.4.1.2011.6.122.20.2.1.8.1
-- 1.3.6.1.4.1.2011.6.122.20.2.1.8.1
		-- 1.3.6.1.4.1.2011.6.122.20.2.1.8.1
		hwSpsUcssLinkEntry OBJECT-TYPE
			SYNTAX HwSpsUcssLinkEntry
			MAX-ACCESS not-accessible
			STATUS current
			DESCRIPTION
				"Description."
			INDEX { hwSpsUcssLinkIndex }
			::= { hwSpsUcssLinkTable 1 }


		HwSpsUcssLinkEntry ::=
			SEQUENCE {
				hwSpsUcssLinkIndex
					Gauge32,
				hwSpsUcssLinkSpsLocation
					OCTET STRING,
				hwSpsUcssLinkSpsIP
					IpAddress,
				hwSpsUcssLinkUcssIP
					IpAddress
			 }

--         1.3.6.1.4.1.2011.6.122.20.2.1.8.1.1
-- 1.3.6.1.4.1.2011.6.122.20.2.1.8.1.1
-- 1.3.6.1.4.1.2011.6.122.20.2.1.8.1.1
-- 1.3.6.1.4.1.2011.6.122.20.2.1.8.1.1
-- 1.3.6.1.4.1.2011.6.122.20.2.1.8.1.1
-- 1.3.6.1.4.1.2011.6.122.20.2.1.8.1.1
-- 1.3.6.1.4.1.2011.6.122.20.2.1.8.1.1
-- 1.3.6.1.4.1.2011.6.122.20.2.1.8.1.1
		-- 1.3.6.1.4.1.2011.6.122.20.2.1.8.1.1
		hwSpsUcssLinkIndex OBJECT-TYPE
			SYNTAX Gauge32
			MAX-ACCESS not-accessible
			STATUS current
			DESCRIPTION
				"The value of this object identifies the index of an SPS and UCSS connection information table."
			::= { hwSpsUcssLinkEntry 1 }


--         1.3.6.1.4.1.2011.6.122.20.2.1.8.1.2
-- 1.3.6.1.4.1.2011.6.122.20.2.1.8.1.2
-- 1.3.6.1.4.1.2011.6.122.20.2.1.8.1.2
-- 1.3.6.1.4.1.2011.6.122.20.2.1.8.1.2
-- 1.3.6.1.4.1.2011.6.122.20.2.1.8.1.2
-- 1.3.6.1.4.1.2011.6.122.20.2.1.8.1.2
-- 1.3.6.1.4.1.2011.6.122.20.2.1.8.1.2
-- 1.3.6.1.4.1.2011.6.122.20.2.1.8.1.2
		-- 1.3.6.1.4.1.2011.6.122.20.2.1.8.1.2
		hwSpsUcssLinkSpsLocation OBJECT-TYPE
			SYNTAX OCTET STRING (SIZE (0..255))
			MAX-ACCESS read-write
			STATUS current
			DESCRIPTION
				"This object indicates the location of an SPS, in the x/y/z format."
			::= { hwSpsUcssLinkEntry 2 }


--         1.3.6.1.4.1.2011.6.122.20.2.1.8.1.3
-- 1.3.6.1.4.1.2011.6.122.20.2.1.8.1.3
-- 1.3.6.1.4.1.2011.6.122.20.2.1.8.1.3
-- 1.3.6.1.4.1.2011.6.122.20.2.1.8.1.3
-- 1.3.6.1.4.1.2011.6.122.20.2.1.8.1.3
-- 1.3.6.1.4.1.2011.6.122.20.2.1.8.1.3
-- 1.3.6.1.4.1.2011.6.122.20.2.1.8.1.3
-- 1.3.6.1.4.1.2011.6.122.20.2.1.8.1.3
		-- 1.3.6.1.4.1.2011.6.122.20.2.1.8.1.3
		hwSpsUcssLinkSpsIP OBJECT-TYPE
			SYNTAX IpAddress
			MAX-ACCESS read-write
			STATUS current
			DESCRIPTION
				"This object indicates the IP address of an SPS, in dotted decimal notation."
			::= { hwSpsUcssLinkEntry 3 }


--         1.3.6.1.4.1.2011.6.122.20.2.1.8.1.4
-- 1.3.6.1.4.1.2011.6.122.20.2.1.8.1.4
-- 1.3.6.1.4.1.2011.6.122.20.2.1.8.1.4
-- 1.3.6.1.4.1.2011.6.122.20.2.1.8.1.4
-- 1.3.6.1.4.1.2011.6.122.20.2.1.8.1.4
-- 1.3.6.1.4.1.2011.6.122.20.2.1.8.1.4
-- 1.3.6.1.4.1.2011.6.122.20.2.1.8.1.4
-- 1.3.6.1.4.1.2011.6.122.20.2.1.8.1.4
		-- 1.3.6.1.4.1.2011.6.122.20.2.1.8.1.4
		hwSpsUcssLinkUcssIP OBJECT-TYPE
			SYNTAX IpAddress
			MAX-ACCESS read-write
			STATUS current
			DESCRIPTION
				"This object indicates the IP address of a UCSS, in dotted decimal notation."
			::= { hwSpsUcssLinkEntry 4 }


--         1.3.6.1.4.1.2011.6.122.20.2.1.9
-- 1.3.6.1.4.1.2011.6.122.20.2.1.9
-- 1.3.6.1.4.1.2011.6.122.20.2.1.9
-- 1.3.6.1.4.1.2011.6.122.20.2.1.9
-- 1.3.6.1.4.1.2011.6.122.20.2.1.9
-- 1.3.6.1.4.1.2011.6.122.20.2.1.9
-- 1.3.6.1.4.1.2011.6.122.20.2.1.9
-- 1.3.6.1.4.1.2011.6.122.20.2.1.9
		-- 1.3.6.1.4.1.2011.6.122.20.2.1.9
		hwSasMessageNumberTable OBJECT-TYPE
			SYNTAX SEQUENCE OF HwSasMessageNumberEntry
			MAX-ACCESS not-accessible
			STATUS current
			DESCRIPTION
				"This table describes SAS message statistics, including the number of online and offline IP addresses and accounts on each SAS."
			::= { hwServiceBasicObject 9 }


--         1.3.6.1.4.1.2011.6.122.20.2.1.9.1
-- 1.3.6.1.4.1.2011.6.122.20.2.1.9.1
-- 1.3.6.1.4.1.2011.6.122.20.2.1.9.1
-- 1.3.6.1.4.1.2011.6.122.20.2.1.9.1
-- 1.3.6.1.4.1.2011.6.122.20.2.1.9.1
-- 1.3.6.1.4.1.2011.6.122.20.2.1.9.1
-- 1.3.6.1.4.1.2011.6.122.20.2.1.9.1
-- 1.3.6.1.4.1.2011.6.122.20.2.1.9.1
		-- 1.3.6.1.4.1.2011.6.122.20.2.1.9.1
		hwSasMessageNumberEntry OBJECT-TYPE
			SYNTAX HwSasMessageNumberEntry
			MAX-ACCESS not-accessible
			STATUS current
			DESCRIPTION
				"Description."
			INDEX { hwSasMessageNumIndex }
			::= { hwSasMessageNumberTable 1 }


		HwSasMessageNumberEntry ::=
			SEQUENCE {
				hwSasMessageNumIndex
					Gauge32,
				hwSasMessageLocation
					OCTET STRING,
				hwSasIPAddress
					IpAddress,
				hwSasMessageType
					INTEGER,
				hwSasMessageIpOnLineNum
					Gauge32,
				hwSasMessageIpOffLineNum
					Gauge32,
				hwSasMessageAccountOnLineNum
					Gauge32,
				hwSasMessageAccountOffLineNum
					Gauge32,
				hwSasMessageTotalNum
					Gauge32
			 }

--         1.3.6.1.4.1.2011.6.122.20.2.1.9.1.1
-- 1.3.6.1.4.1.2011.6.122.20.2.1.9.1.1
-- 1.3.6.1.4.1.2011.6.122.20.2.1.9.1.1
-- 1.3.6.1.4.1.2011.6.122.20.2.1.9.1.1
-- 1.3.6.1.4.1.2011.6.122.20.2.1.9.1.1
-- 1.3.6.1.4.1.2011.6.122.20.2.1.9.1.1
-- 1.3.6.1.4.1.2011.6.122.20.2.1.9.1.1
-- 1.3.6.1.4.1.2011.6.122.20.2.1.9.1.1
		-- 1.3.6.1.4.1.2011.6.122.20.2.1.9.1.1
		hwSasMessageNumIndex OBJECT-TYPE
			SYNTAX Gauge32
			MAX-ACCESS not-accessible
			STATUS current
			DESCRIPTION
				"The value of this object identifies the index of an SAS message statistics table."
			::= { hwSasMessageNumberEntry 1 }


--         1.3.6.1.4.1.2011.6.122.20.2.1.9.1.2
-- 1.3.6.1.4.1.2011.6.122.20.2.1.9.1.2
-- 1.3.6.1.4.1.2011.6.122.20.2.1.9.1.2
-- 1.3.6.1.4.1.2011.6.122.20.2.1.9.1.2
-- 1.3.6.1.4.1.2011.6.122.20.2.1.9.1.2
-- 1.3.6.1.4.1.2011.6.122.20.2.1.9.1.2
-- 1.3.6.1.4.1.2011.6.122.20.2.1.9.1.2
-- 1.3.6.1.4.1.2011.6.122.20.2.1.9.1.2
		-- 1.3.6.1.4.1.2011.6.122.20.2.1.9.1.2
		hwSasMessageLocation OBJECT-TYPE
			SYNTAX OCTET STRING (SIZE (0..255))
			MAX-ACCESS read-write
			STATUS current
			DESCRIPTION
				"This object indicates the location of an SAS, in the x/y/z format."
			::= { hwSasMessageNumberEntry 2 }


--         1.3.6.1.4.1.2011.6.122.20.2.1.9.1.3
-- 1.3.6.1.4.1.2011.6.122.20.2.1.9.1.3
-- 1.3.6.1.4.1.2011.6.122.20.2.1.9.1.3
-- 1.3.6.1.4.1.2011.6.122.20.2.1.9.1.3
-- 1.3.6.1.4.1.2011.6.122.20.2.1.9.1.3
-- 1.3.6.1.4.1.2011.6.122.20.2.1.9.1.3
-- 1.3.6.1.4.1.2011.6.122.20.2.1.9.1.3
-- 1.3.6.1.4.1.2011.6.122.20.2.1.9.1.3
		-- 1.3.6.1.4.1.2011.6.122.20.2.1.9.1.3
		hwSasIPAddress OBJECT-TYPE
			SYNTAX IpAddress
			MAX-ACCESS read-only
			STATUS current
			DESCRIPTION
				"This object indicates the IP address of an SAS, in dotted decimal notation."
			::= { hwSasMessageNumberEntry 3 }


--         1.3.6.1.4.1.2011.6.122.20.2.1.9.1.4
-- 1.3.6.1.4.1.2011.6.122.20.2.1.9.1.4
-- 1.3.6.1.4.1.2011.6.122.20.2.1.9.1.4
-- 1.3.6.1.4.1.2011.6.122.20.2.1.9.1.4
-- 1.3.6.1.4.1.2011.6.122.20.2.1.9.1.4
-- 1.3.6.1.4.1.2011.6.122.20.2.1.9.1.4
-- 1.3.6.1.4.1.2011.6.122.20.2.1.9.1.4
-- 1.3.6.1.4.1.2011.6.122.20.2.1.9.1.4
		-- 1.3.6.1.4.1.2011.6.122.20.2.1.9.1.4
		hwSasMessageType OBJECT-TYPE
			SYNTAX INTEGER
				{
				unknow(1),
				fixed(2),
				g(3),
				c(4),
				wimax(5),
				static(6)
				}
			MAX-ACCESS read-only
			STATUS current
			DESCRIPTION
				"The value of this object identifies an SAS message type."
			::= { hwSasMessageNumberEntry 4 }


--         1.3.6.1.4.1.2011.6.122.20.2.1.9.1.5
-- 1.3.6.1.4.1.2011.6.122.20.2.1.9.1.5
-- 1.3.6.1.4.1.2011.6.122.20.2.1.9.1.5
-- 1.3.6.1.4.1.2011.6.122.20.2.1.9.1.5
-- 1.3.6.1.4.1.2011.6.122.20.2.1.9.1.5
-- 1.3.6.1.4.1.2011.6.122.20.2.1.9.1.5
-- 1.3.6.1.4.1.2011.6.122.20.2.1.9.1.5
-- 1.3.6.1.4.1.2011.6.122.20.2.1.9.1.5
		-- 1.3.6.1.4.1.2011.6.122.20.2.1.9.1.5
		hwSasMessageIpOnLineNum OBJECT-TYPE
			SYNTAX Gauge32
			MAX-ACCESS read-only
			STATUS current
			DESCRIPTION
				"The value of this object identifies the number of IP addresses of online subscribers on an SAS."
			::= { hwSasMessageNumberEntry 5 }


--         1.3.6.1.4.1.2011.6.122.20.2.1.9.1.6
-- 1.3.6.1.4.1.2011.6.122.20.2.1.9.1.6
-- 1.3.6.1.4.1.2011.6.122.20.2.1.9.1.6
-- 1.3.6.1.4.1.2011.6.122.20.2.1.9.1.6
-- 1.3.6.1.4.1.2011.6.122.20.2.1.9.1.6
-- 1.3.6.1.4.1.2011.6.122.20.2.1.9.1.6
-- 1.3.6.1.4.1.2011.6.122.20.2.1.9.1.6
-- 1.3.6.1.4.1.2011.6.122.20.2.1.9.1.6
		-- 1.3.6.1.4.1.2011.6.122.20.2.1.9.1.6
		hwSasMessageIpOffLineNum OBJECT-TYPE
			SYNTAX Gauge32
			MAX-ACCESS read-only
			STATUS current
			DESCRIPTION
				"The value of this object identifies the number of IP addresses of offline subscribers on an SAS."
			::= { hwSasMessageNumberEntry 6 }


--         1.3.6.1.4.1.2011.6.122.20.2.1.9.1.7
-- 1.3.6.1.4.1.2011.6.122.20.2.1.9.1.7
-- 1.3.6.1.4.1.2011.6.122.20.2.1.9.1.7
-- 1.3.6.1.4.1.2011.6.122.20.2.1.9.1.7
-- 1.3.6.1.4.1.2011.6.122.20.2.1.9.1.7
-- 1.3.6.1.4.1.2011.6.122.20.2.1.9.1.7
-- 1.3.6.1.4.1.2011.6.122.20.2.1.9.1.7
-- 1.3.6.1.4.1.2011.6.122.20.2.1.9.1.7
		-- 1.3.6.1.4.1.2011.6.122.20.2.1.9.1.7
		hwSasMessageAccountOnLineNum OBJECT-TYPE
			SYNTAX Gauge32
			MAX-ACCESS read-only
			STATUS current
			DESCRIPTION
				"The value of this object identifies the number of online accounts on an SAS."
			::= { hwSasMessageNumberEntry 7 }


--         1.3.6.1.4.1.2011.6.122.20.2.1.9.1.8
-- 1.3.6.1.4.1.2011.6.122.20.2.1.9.1.8
-- 1.3.6.1.4.1.2011.6.122.20.2.1.9.1.8
-- 1.3.6.1.4.1.2011.6.122.20.2.1.9.1.8
-- 1.3.6.1.4.1.2011.6.122.20.2.1.9.1.8
-- 1.3.6.1.4.1.2011.6.122.20.2.1.9.1.8
-- 1.3.6.1.4.1.2011.6.122.20.2.1.9.1.8
-- 1.3.6.1.4.1.2011.6.122.20.2.1.9.1.8
		-- 1.3.6.1.4.1.2011.6.122.20.2.1.9.1.8
		hwSasMessageAccountOffLineNum OBJECT-TYPE
			SYNTAX Gauge32
			MAX-ACCESS read-only
			STATUS current
			DESCRIPTION
				"The value of this object identifies the number of offline accounts on an SAS."
			::= { hwSasMessageNumberEntry 8 }


--         1.3.6.1.4.1.2011.6.122.20.2.1.9.1.9
-- 1.3.6.1.4.1.2011.6.122.20.2.1.9.1.9
-- 1.3.6.1.4.1.2011.6.122.20.2.1.9.1.9
-- 1.3.6.1.4.1.2011.6.122.20.2.1.9.1.9
-- 1.3.6.1.4.1.2011.6.122.20.2.1.9.1.9
-- 1.3.6.1.4.1.2011.6.122.20.2.1.9.1.9
-- 1.3.6.1.4.1.2011.6.122.20.2.1.9.1.9
-- 1.3.6.1.4.1.2011.6.122.20.2.1.9.1.9
		-- 1.3.6.1.4.1.2011.6.122.20.2.1.9.1.9
		hwSasMessageTotalNum OBJECT-TYPE
			SYNTAX Gauge32
			MAX-ACCESS read-only
			STATUS current
			DESCRIPTION
				"The value of this object identifies the total number of SAS messages."
			::= { hwSasMessageNumberEntry 9 }


--         1.3.6.1.4.1.2011.6.122.20.2.1.10
-- 1.3.6.1.4.1.2011.6.122.20.2.1.10
-- 1.3.6.1.4.1.2011.6.122.20.2.1.10
-- 1.3.6.1.4.1.2011.6.122.20.2.1.10
-- 1.3.6.1.4.1.2011.6.122.20.2.1.10
-- 1.3.6.1.4.1.2011.6.122.20.2.1.10
-- 1.3.6.1.4.1.2011.6.122.20.2.1.10
-- 1.3.6.1.4.1.2011.6.122.20.2.1.10
		-- 1.3.6.1.4.1.2011.6.122.20.2.1.10
		hwSpsMessageNumberTable OBJECT-TYPE
			SYNTAX SEQUENCE OF HwSpsMessageNumberEntry
			MAX-ACCESS not-accessible
			STATUS current
			DESCRIPTION
				"This table describes SPS message statistics, including the location and IP address of each SPS, number of newly created traffic flows, number of newly created traffic flows of unknown protocol types, and number of deleted traffic flows on each SPS."
			::= { hwServiceBasicObject 10 }


--         1.3.6.1.4.1.2011.6.122.20.2.1.10.1
-- 1.3.6.1.4.1.2011.6.122.20.2.1.10.1
-- 1.3.6.1.4.1.2011.6.122.20.2.1.10.1
-- 1.3.6.1.4.1.2011.6.122.20.2.1.10.1
-- 1.3.6.1.4.1.2011.6.122.20.2.1.10.1
-- 1.3.6.1.4.1.2011.6.122.20.2.1.10.1
-- 1.3.6.1.4.1.2011.6.122.20.2.1.10.1
-- 1.3.6.1.4.1.2011.6.122.20.2.1.10.1
		-- 1.3.6.1.4.1.2011.6.122.20.2.1.10.1
		hwSpsMessageNumberEntry OBJECT-TYPE
			SYNTAX HwSpsMessageNumberEntry
			MAX-ACCESS not-accessible
			STATUS current
			DESCRIPTION
				"Description."
			INDEX { hwSpsMessageNumberIndex }
			::= { hwSpsMessageNumberTable 1 }


		HwSpsMessageNumberEntry ::=
			SEQUENCE {
				hwSpsMessageNumberIndex
					Gauge32,
				hwSpsMessageNumberLocation
					OCTET STRING,
				hwSpsIPAddress
					IpAddress,
				hwSpsNewFlowNumber
					Gauge32,
				hwSpsNewTempFlowNumber
					Gauge32,
				hwSpsDeleteFlowNumber
					Gauge32
			 }

--         1.3.6.1.4.1.2011.6.122.20.2.1.10.1.1
-- 1.3.6.1.4.1.2011.6.122.20.2.1.10.1.1
-- 1.3.6.1.4.1.2011.6.122.20.2.1.10.1.1
-- 1.3.6.1.4.1.2011.6.122.20.2.1.10.1.1
-- 1.3.6.1.4.1.2011.6.122.20.2.1.10.1.1
-- 1.3.6.1.4.1.2011.6.122.20.2.1.10.1.1
-- 1.3.6.1.4.1.2011.6.122.20.2.1.10.1.1
-- 1.3.6.1.4.1.2011.6.122.20.2.1.10.1.1
		-- 1.3.6.1.4.1.2011.6.122.20.2.1.10.1.1
		hwSpsMessageNumberIndex OBJECT-TYPE
			SYNTAX Gauge32
			MAX-ACCESS not-accessible
			STATUS current
			DESCRIPTION
				"The value of this object identifies the index of an SPS message statistics table."
			::= { hwSpsMessageNumberEntry 1 }


--         1.3.6.1.4.1.2011.6.122.20.2.1.10.1.2
-- 1.3.6.1.4.1.2011.6.122.20.2.1.10.1.2
-- 1.3.6.1.4.1.2011.6.122.20.2.1.10.1.2
-- 1.3.6.1.4.1.2011.6.122.20.2.1.10.1.2
-- 1.3.6.1.4.1.2011.6.122.20.2.1.10.1.2
-- 1.3.6.1.4.1.2011.6.122.20.2.1.10.1.2
-- 1.3.6.1.4.1.2011.6.122.20.2.1.10.1.2
-- 1.3.6.1.4.1.2011.6.122.20.2.1.10.1.2
		-- 1.3.6.1.4.1.2011.6.122.20.2.1.10.1.2
		hwSpsMessageNumberLocation OBJECT-TYPE
			SYNTAX OCTET STRING (SIZE (0..255))
			MAX-ACCESS read-write
			STATUS current
			DESCRIPTION
				"This object indicates the location of an SPS, in the x/y/z format."
			::= { hwSpsMessageNumberEntry 2 }


--         1.3.6.1.4.1.2011.6.122.20.2.1.10.1.3
-- 1.3.6.1.4.1.2011.6.122.20.2.1.10.1.3
-- 1.3.6.1.4.1.2011.6.122.20.2.1.10.1.3
-- 1.3.6.1.4.1.2011.6.122.20.2.1.10.1.3
-- 1.3.6.1.4.1.2011.6.122.20.2.1.10.1.3
-- 1.3.6.1.4.1.2011.6.122.20.2.1.10.1.3
-- 1.3.6.1.4.1.2011.6.122.20.2.1.10.1.3
-- 1.3.6.1.4.1.2011.6.122.20.2.1.10.1.3
		-- 1.3.6.1.4.1.2011.6.122.20.2.1.10.1.3
		hwSpsIPAddress OBJECT-TYPE
			SYNTAX IpAddress
			MAX-ACCESS read-only
			STATUS current
			DESCRIPTION
				"This object indicates the IP address of an SPS, in dotted decimal notation."
			::= { hwSpsMessageNumberEntry 3 }


--         1.3.6.1.4.1.2011.6.122.20.2.1.10.1.4
-- 1.3.6.1.4.1.2011.6.122.20.2.1.10.1.4
-- 1.3.6.1.4.1.2011.6.122.20.2.1.10.1.4
-- 1.3.6.1.4.1.2011.6.122.20.2.1.10.1.4
-- 1.3.6.1.4.1.2011.6.122.20.2.1.10.1.4
-- 1.3.6.1.4.1.2011.6.122.20.2.1.10.1.4
-- 1.3.6.1.4.1.2011.6.122.20.2.1.10.1.4
-- 1.3.6.1.4.1.2011.6.122.20.2.1.10.1.4
		-- 1.3.6.1.4.1.2011.6.122.20.2.1.10.1.4
		hwSpsNewFlowNumber OBJECT-TYPE
			SYNTAX Gauge32
			MAX-ACCESS read-only
			STATUS current
			DESCRIPTION
				"The value of this object identifies the number of newly created traffic flows on an SPS."
			::= { hwSpsMessageNumberEntry 4 }


--         1.3.6.1.4.1.2011.6.122.20.2.1.10.1.5
-- 1.3.6.1.4.1.2011.6.122.20.2.1.10.1.5
-- 1.3.6.1.4.1.2011.6.122.20.2.1.10.1.5
-- 1.3.6.1.4.1.2011.6.122.20.2.1.10.1.5
-- 1.3.6.1.4.1.2011.6.122.20.2.1.10.1.5
-- 1.3.6.1.4.1.2011.6.122.20.2.1.10.1.5
-- 1.3.6.1.4.1.2011.6.122.20.2.1.10.1.5
-- 1.3.6.1.4.1.2011.6.122.20.2.1.10.1.5
		-- 1.3.6.1.4.1.2011.6.122.20.2.1.10.1.5
		hwSpsNewTempFlowNumber OBJECT-TYPE
			SYNTAX Gauge32
			MAX-ACCESS read-only
			STATUS current
			DESCRIPTION
				"The value of this object identifies the number of newly created traffic flows of unknown protocol types on an SPS."
			::= { hwSpsMessageNumberEntry 5 }


--         1.3.6.1.4.1.2011.6.122.20.2.1.10.1.6
-- 1.3.6.1.4.1.2011.6.122.20.2.1.10.1.6
-- 1.3.6.1.4.1.2011.6.122.20.2.1.10.1.6
-- 1.3.6.1.4.1.2011.6.122.20.2.1.10.1.6
-- 1.3.6.1.4.1.2011.6.122.20.2.1.10.1.6
-- 1.3.6.1.4.1.2011.6.122.20.2.1.10.1.6
-- 1.3.6.1.4.1.2011.6.122.20.2.1.10.1.6
-- 1.3.6.1.4.1.2011.6.122.20.2.1.10.1.6
		-- 1.3.6.1.4.1.2011.6.122.20.2.1.10.1.6
		hwSpsDeleteFlowNumber OBJECT-TYPE
			SYNTAX Gauge32
			MAX-ACCESS read-only
			STATUS current
			DESCRIPTION
				"The value of this object identifies the number of deleted traffic flows on an SPS."
			::= { hwSpsMessageNumberEntry 6 }


--         1.3.6.1.4.1.2011.6.122.20.2.1.11
-- 1.3.6.1.4.1.2011.6.122.20.2.1.11
-- 1.3.6.1.4.1.2011.6.122.20.2.1.11
-- 1.3.6.1.4.1.2011.6.122.20.2.1.11
-- 1.3.6.1.4.1.2011.6.122.20.2.1.11
-- 1.3.6.1.4.1.2011.6.122.20.2.1.11
-- 1.3.6.1.4.1.2011.6.122.20.2.1.11
-- 1.3.6.1.4.1.2011.6.122.20.2.1.11
		-- 1.3.6.1.4.1.2011.6.122.20.2.1.11
		hwBackupGroupTable OBJECT-TYPE
			SYNTAX SEQUENCE OF HwBackupGroupEntry
			MAX-ACCESS not-accessible
			STATUS current
			DESCRIPTION
				"Description."
			::= { hwServiceBasicObject 11 }


--         1.3.6.1.4.1.2011.6.122.20.2.1.11.1
-- 1.3.6.1.4.1.2011.6.122.20.2.1.11.1
-- 1.3.6.1.4.1.2011.6.122.20.2.1.11.1
-- 1.3.6.1.4.1.2011.6.122.20.2.1.11.1
-- 1.3.6.1.4.1.2011.6.122.20.2.1.11.1
-- 1.3.6.1.4.1.2011.6.122.20.2.1.11.1
-- 1.3.6.1.4.1.2011.6.122.20.2.1.11.1
-- 1.3.6.1.4.1.2011.6.122.20.2.1.11.1
		-- 1.3.6.1.4.1.2011.6.122.20.2.1.11.1
		hwBackupGroupEntry OBJECT-TYPE
			SYNTAX HwBackupGroupEntry
			MAX-ACCESS not-accessible
			STATUS current
			DESCRIPTION
				"Description."
			INDEX { hwBackupGroupIndex }
			::= { hwBackupGroupTable 1 }


		HwBackupGroupEntry ::=
			SEQUENCE {
				hwBackupGroupIndex
					Gauge32,
				hwBackupGroupID
					Integer32,
				hwLocalClusterNodeID
					Integer32,
				hwPeerClusterNodeID
					Integer32,
				hwLocalClusterNodeIPAddress
					IpAddress,
				hwPeerClusterNodeIPAddress
					IpAddress,
				hwBackupGroupLocalSlot
					Integer32,
				hwBackupGroupPeerSlot
					Integer32,
				hwBackupGroupLocalState
					INTEGER,
				hwBackupGroupPeerState
					INTEGER
			 }

--         1.3.6.1.4.1.2011.6.122.20.2.1.11.1.1
-- 1.3.6.1.4.1.2011.6.122.20.2.1.11.1.1
-- 1.3.6.1.4.1.2011.6.122.20.2.1.11.1.1
-- 1.3.6.1.4.1.2011.6.122.20.2.1.11.1.1
-- 1.3.6.1.4.1.2011.6.122.20.2.1.11.1.1
-- 1.3.6.1.4.1.2011.6.122.20.2.1.11.1.1
-- 1.3.6.1.4.1.2011.6.122.20.2.1.11.1.1
-- 1.3.6.1.4.1.2011.6.122.20.2.1.11.1.1
		-- 1.3.6.1.4.1.2011.6.122.20.2.1.11.1.1
		hwBackupGroupIndex OBJECT-TYPE
			SYNTAX Gauge32 (1..16)
			MAX-ACCESS not-accessible
			STATUS current
			DESCRIPTION
				"Description."
			::= { hwBackupGroupEntry 1 }


--         1.3.6.1.4.1.2011.6.122.20.2.1.11.1.2
-- 1.3.6.1.4.1.2011.6.122.20.2.1.11.1.2
-- 1.3.6.1.4.1.2011.6.122.20.2.1.11.1.2
-- 1.3.6.1.4.1.2011.6.122.20.2.1.11.1.2
-- 1.3.6.1.4.1.2011.6.122.20.2.1.11.1.2
-- 1.3.6.1.4.1.2011.6.122.20.2.1.11.1.2
-- 1.3.6.1.4.1.2011.6.122.20.2.1.11.1.2
-- 1.3.6.1.4.1.2011.6.122.20.2.1.11.1.2
		-- 1.3.6.1.4.1.2011.6.122.20.2.1.11.1.2
		hwBackupGroupID OBJECT-TYPE
			SYNTAX Integer32 (1..16)
			MAX-ACCESS read-only
			STATUS current
			DESCRIPTION
				"Description."
			::= { hwBackupGroupEntry 2 }


--         1.3.6.1.4.1.2011.6.122.20.2.1.11.1.3
-- 1.3.6.1.4.1.2011.6.122.20.2.1.11.1.3
-- 1.3.6.1.4.1.2011.6.122.20.2.1.11.1.3
-- 1.3.6.1.4.1.2011.6.122.20.2.1.11.1.3
-- 1.3.6.1.4.1.2011.6.122.20.2.1.11.1.3
-- 1.3.6.1.4.1.2011.6.122.20.2.1.11.1.3
-- 1.3.6.1.4.1.2011.6.122.20.2.1.11.1.3
-- 1.3.6.1.4.1.2011.6.122.20.2.1.11.1.3
		-- 1.3.6.1.4.1.2011.6.122.20.2.1.11.1.3
		hwLocalClusterNodeID OBJECT-TYPE
			SYNTAX Integer32 (1..255)
			MAX-ACCESS read-only
			STATUS current
			DESCRIPTION
				"Description."
			::= { hwBackupGroupEntry 3 }


--         1.3.6.1.4.1.2011.6.122.20.2.1.11.1.4
-- 1.3.6.1.4.1.2011.6.122.20.2.1.11.1.4
-- 1.3.6.1.4.1.2011.6.122.20.2.1.11.1.4
-- 1.3.6.1.4.1.2011.6.122.20.2.1.11.1.4
-- 1.3.6.1.4.1.2011.6.122.20.2.1.11.1.4
-- 1.3.6.1.4.1.2011.6.122.20.2.1.11.1.4
-- 1.3.6.1.4.1.2011.6.122.20.2.1.11.1.4
-- 1.3.6.1.4.1.2011.6.122.20.2.1.11.1.4
		-- 1.3.6.1.4.1.2011.6.122.20.2.1.11.1.4
		hwPeerClusterNodeID OBJECT-TYPE
			SYNTAX Integer32 (1..255)
			MAX-ACCESS read-only
			STATUS current
			DESCRIPTION
				"Description."
			::= { hwBackupGroupEntry 4 }


--         1.3.6.1.4.1.2011.6.122.20.2.1.11.1.5
-- 1.3.6.1.4.1.2011.6.122.20.2.1.11.1.5
-- 1.3.6.1.4.1.2011.6.122.20.2.1.11.1.5
-- 1.3.6.1.4.1.2011.6.122.20.2.1.11.1.5
-- 1.3.6.1.4.1.2011.6.122.20.2.1.11.1.5
-- 1.3.6.1.4.1.2011.6.122.20.2.1.11.1.5
-- 1.3.6.1.4.1.2011.6.122.20.2.1.11.1.5
-- 1.3.6.1.4.1.2011.6.122.20.2.1.11.1.5
		-- 1.3.6.1.4.1.2011.6.122.20.2.1.11.1.5
		hwLocalClusterNodeIPAddress OBJECT-TYPE
			SYNTAX IpAddress
			MAX-ACCESS read-only
			STATUS current
			DESCRIPTION
				"Description."
			::= { hwBackupGroupEntry 5 }


--         1.3.6.1.4.1.2011.6.122.20.2.1.11.1.6
-- 1.3.6.1.4.1.2011.6.122.20.2.1.11.1.6
-- 1.3.6.1.4.1.2011.6.122.20.2.1.11.1.6
-- 1.3.6.1.4.1.2011.6.122.20.2.1.11.1.6
-- 1.3.6.1.4.1.2011.6.122.20.2.1.11.1.6
-- 1.3.6.1.4.1.2011.6.122.20.2.1.11.1.6
-- 1.3.6.1.4.1.2011.6.122.20.2.1.11.1.6
-- 1.3.6.1.4.1.2011.6.122.20.2.1.11.1.6
		-- 1.3.6.1.4.1.2011.6.122.20.2.1.11.1.6
		hwPeerClusterNodeIPAddress OBJECT-TYPE
			SYNTAX IpAddress
			MAX-ACCESS read-only
			STATUS current
			DESCRIPTION
				"Description."
			::= { hwBackupGroupEntry 6 }


--         1.3.6.1.4.1.2011.6.122.20.2.1.11.1.7
-- 1.3.6.1.4.1.2011.6.122.20.2.1.11.1.7
-- 1.3.6.1.4.1.2011.6.122.20.2.1.11.1.7
-- 1.3.6.1.4.1.2011.6.122.20.2.1.11.1.7
-- 1.3.6.1.4.1.2011.6.122.20.2.1.11.1.7
-- 1.3.6.1.4.1.2011.6.122.20.2.1.11.1.7
-- 1.3.6.1.4.1.2011.6.122.20.2.1.11.1.7
-- 1.3.6.1.4.1.2011.6.122.20.2.1.11.1.7
		-- 1.3.6.1.4.1.2011.6.122.20.2.1.11.1.7
		hwBackupGroupLocalSlot OBJECT-TYPE
			SYNTAX Integer32 (1..16)
			MAX-ACCESS read-only
			STATUS current
			DESCRIPTION
				"Description."
			::= { hwBackupGroupEntry 7 }


--         1.3.6.1.4.1.2011.6.122.20.2.1.11.1.8
-- 1.3.6.1.4.1.2011.6.122.20.2.1.11.1.8
-- 1.3.6.1.4.1.2011.6.122.20.2.1.11.1.8
-- 1.3.6.1.4.1.2011.6.122.20.2.1.11.1.8
-- 1.3.6.1.4.1.2011.6.122.20.2.1.11.1.8
-- 1.3.6.1.4.1.2011.6.122.20.2.1.11.1.8
-- 1.3.6.1.4.1.2011.6.122.20.2.1.11.1.8
-- 1.3.6.1.4.1.2011.6.122.20.2.1.11.1.8
		-- 1.3.6.1.4.1.2011.6.122.20.2.1.11.1.8
		hwBackupGroupPeerSlot OBJECT-TYPE
			SYNTAX Integer32 (1..16)
			MAX-ACCESS read-only
			STATUS current
			DESCRIPTION
				"Description."
			::= { hwBackupGroupEntry 8 }


--         1.3.6.1.4.1.2011.6.122.20.2.1.11.1.9
-- 1.3.6.1.4.1.2011.6.122.20.2.1.11.1.9
-- 1.3.6.1.4.1.2011.6.122.20.2.1.11.1.9
-- 1.3.6.1.4.1.2011.6.122.20.2.1.11.1.9
-- 1.3.6.1.4.1.2011.6.122.20.2.1.11.1.9
-- 1.3.6.1.4.1.2011.6.122.20.2.1.11.1.9
-- 1.3.6.1.4.1.2011.6.122.20.2.1.11.1.9
-- 1.3.6.1.4.1.2011.6.122.20.2.1.11.1.9
		-- 1.3.6.1.4.1.2011.6.122.20.2.1.11.1.9
		hwBackupGroupLocalState OBJECT-TYPE
			SYNTAX INTEGER
				{
				master(1),
				backup(2)
				}
			MAX-ACCESS read-only
			STATUS current
			DESCRIPTION
				"Description."
			::= { hwBackupGroupEntry 9 }


--         1.3.6.1.4.1.2011.6.122.20.2.1.11.1.10
-- 1.3.6.1.4.1.2011.6.122.20.2.1.11.1.10
-- 1.3.6.1.4.1.2011.6.122.20.2.1.11.1.10
-- 1.3.6.1.4.1.2011.6.122.20.2.1.11.1.10
-- 1.3.6.1.4.1.2011.6.122.20.2.1.11.1.10
-- 1.3.6.1.4.1.2011.6.122.20.2.1.11.1.10
-- 1.3.6.1.4.1.2011.6.122.20.2.1.11.1.10
-- 1.3.6.1.4.1.2011.6.122.20.2.1.11.1.10
		-- 1.3.6.1.4.1.2011.6.122.20.2.1.11.1.10
		hwBackupGroupPeerState OBJECT-TYPE
			SYNTAX INTEGER
				{
				master(1),
				backup(2)
				}
			MAX-ACCESS read-only
			STATUS current
			DESCRIPTION
				"Description."
			::= { hwBackupGroupEntry 10 }


--         1.3.6.1.4.1.2011.6.122.20.2.1.12
-- 1.3.6.1.4.1.2011.6.122.20.2.1.12
-- 1.3.6.1.4.1.2011.6.122.20.2.1.12
-- 1.3.6.1.4.1.2011.6.122.20.2.1.12
-- 1.3.6.1.4.1.2011.6.122.20.2.1.12
-- 1.3.6.1.4.1.2011.6.122.20.2.1.12
-- 1.3.6.1.4.1.2011.6.122.20.2.1.12
-- 1.3.6.1.4.1.2011.6.122.20.2.1.12
		-- 1.3.6.1.4.1.2011.6.122.20.2.1.12
		hwSpsRdasLinkTable OBJECT-TYPE
			SYNTAX SEQUENCE OF HwSpsRdasLinkEntry
			MAX-ACCESS not-accessible
			STATUS current
			DESCRIPTION
				"This table describes SPS and RDAS connection information, including the location of each SPS and IP address of each RDAS."
			::= { hwServiceBasicObject 12 }


--         1.3.6.1.4.1.2011.6.122.20.2.1.12.1
-- 1.3.6.1.4.1.2011.6.122.20.2.1.12.1
-- 1.3.6.1.4.1.2011.6.122.20.2.1.12.1
-- 1.3.6.1.4.1.2011.6.122.20.2.1.12.1
-- 1.3.6.1.4.1.2011.6.122.20.2.1.12.1
-- 1.3.6.1.4.1.2011.6.122.20.2.1.12.1
-- 1.3.6.1.4.1.2011.6.122.20.2.1.12.1
-- 1.3.6.1.4.1.2011.6.122.20.2.1.12.1
		-- 1.3.6.1.4.1.2011.6.122.20.2.1.12.1
		hwSpsRdasLinkEntry OBJECT-TYPE
			SYNTAX HwSpsRdasLinkEntry
			MAX-ACCESS not-accessible
			STATUS current
			DESCRIPTION
				"Description."
			INDEX { hwSpsRdasLinkIndex }
			::= { hwSpsRdasLinkTable 1 }


		HwSpsRdasLinkEntry ::=
			SEQUENCE {
				hwSpsRdasLinkIndex
					Gauge32,
				hwSpsRdasLinkSpsLocation
					OCTET STRING,
				hwSpsRdasLinkRdasIP
					IpAddress
			 }

--         1.3.6.1.4.1.2011.6.122.20.2.1.12.1.1
-- 1.3.6.1.4.1.2011.6.122.20.2.1.12.1.1
-- 1.3.6.1.4.1.2011.6.122.20.2.1.12.1.1
-- 1.3.6.1.4.1.2011.6.122.20.2.1.12.1.1
-- 1.3.6.1.4.1.2011.6.122.20.2.1.12.1.1
-- 1.3.6.1.4.1.2011.6.122.20.2.1.12.1.1
-- 1.3.6.1.4.1.2011.6.122.20.2.1.12.1.1
-- 1.3.6.1.4.1.2011.6.122.20.2.1.12.1.1
		-- 1.3.6.1.4.1.2011.6.122.20.2.1.12.1.1
		hwSpsRdasLinkIndex OBJECT-TYPE
			SYNTAX Gauge32
			MAX-ACCESS not-accessible
			STATUS current
			DESCRIPTION
				"The value of this object identifies the index of an SPS and RDAS connection table."
			::= { hwSpsRdasLinkEntry 1 }


--         1.3.6.1.4.1.2011.6.122.20.2.1.12.1.2
-- 1.3.6.1.4.1.2011.6.122.20.2.1.12.1.2
-- 1.3.6.1.4.1.2011.6.122.20.2.1.12.1.2
-- 1.3.6.1.4.1.2011.6.122.20.2.1.12.1.2
-- 1.3.6.1.4.1.2011.6.122.20.2.1.12.1.2
-- 1.3.6.1.4.1.2011.6.122.20.2.1.12.1.2
-- 1.3.6.1.4.1.2011.6.122.20.2.1.12.1.2
-- 1.3.6.1.4.1.2011.6.122.20.2.1.12.1.2
		-- 1.3.6.1.4.1.2011.6.122.20.2.1.12.1.2
		hwSpsRdasLinkSpsLocation OBJECT-TYPE
			SYNTAX OCTET STRING
			MAX-ACCESS read-write
			STATUS current
			DESCRIPTION
				"This object indicates the location of an SPS, in the x/y/z format."
			::= { hwSpsRdasLinkEntry 2 }


--         1.3.6.1.4.1.2011.6.122.20.2.1.12.1.3
-- 1.3.6.1.4.1.2011.6.122.20.2.1.12.1.3
-- 1.3.6.1.4.1.2011.6.122.20.2.1.12.1.3
-- 1.3.6.1.4.1.2011.6.122.20.2.1.12.1.3
-- 1.3.6.1.4.1.2011.6.122.20.2.1.12.1.3
-- 1.3.6.1.4.1.2011.6.122.20.2.1.12.1.3
-- 1.3.6.1.4.1.2011.6.122.20.2.1.12.1.3
-- 1.3.6.1.4.1.2011.6.122.20.2.1.12.1.3
		-- 1.3.6.1.4.1.2011.6.122.20.2.1.12.1.3
		hwSpsRdasLinkRdasIP OBJECT-TYPE
			SYNTAX IpAddress
			MAX-ACCESS read-write
			STATUS current
			DESCRIPTION
				"This object indicates the IP address of an RDAS, in dotted decimal notation."
			::= { hwSpsRdasLinkEntry 3 }


--         1.3.6.1.4.1.2011.6.122.20.2.1.13
-- 1.3.6.1.4.1.2011.6.122.20.2.1.13
-- 1.3.6.1.4.1.2011.6.122.20.2.1.13
-- 1.3.6.1.4.1.2011.6.122.20.2.1.13
-- 1.3.6.1.4.1.2011.6.122.20.2.1.13
-- 1.3.6.1.4.1.2011.6.122.20.2.1.13
-- 1.3.6.1.4.1.2011.6.122.20.2.1.13
-- 1.3.6.1.4.1.2011.6.122.20.2.1.13
		-- 1.3.6.1.4.1.2011.6.122.20.2.1.13
		hwSpsFragmentTable OBJECT-TYPE
			SYNTAX SEQUENCE OF HwSpsFragmentEntry
			MAX-ACCESS not-accessible
			STATUS current
			DESCRIPTION
				"This table describes SPS fragment information, including the location of the SPS that generates an alarm when the SPS fragment cache is insufficient."
			::= { hwServiceBasicObject 13 }


--         1.3.6.1.4.1.2011.6.122.20.2.1.13.1
-- 1.3.6.1.4.1.2011.6.122.20.2.1.13.1
-- 1.3.6.1.4.1.2011.6.122.20.2.1.13.1
-- 1.3.6.1.4.1.2011.6.122.20.2.1.13.1
-- 1.3.6.1.4.1.2011.6.122.20.2.1.13.1
-- 1.3.6.1.4.1.2011.6.122.20.2.1.13.1
-- 1.3.6.1.4.1.2011.6.122.20.2.1.13.1
-- 1.3.6.1.4.1.2011.6.122.20.2.1.13.1
		-- 1.3.6.1.4.1.2011.6.122.20.2.1.13.1
		hwSpsFragmentEntry OBJECT-TYPE
			SYNTAX HwSpsFragmentEntry
			MAX-ACCESS not-accessible
			STATUS current
			DESCRIPTION
				"Description."
			INDEX { hwSpsFragmentIndex }
			::= { hwSpsFragmentTable 1 }


		HwSpsFragmentEntry ::=
			SEQUENCE {
				hwSpsFragmentIndex
					Gauge32,
				hwSpsFragmentSpsLocation
					OCTET STRING
			 }

--         1.3.6.1.4.1.2011.6.122.20.2.1.13.1.1
-- 1.3.6.1.4.1.2011.6.122.20.2.1.13.1.1
-- 1.3.6.1.4.1.2011.6.122.20.2.1.13.1.1
-- 1.3.6.1.4.1.2011.6.122.20.2.1.13.1.1
-- 1.3.6.1.4.1.2011.6.122.20.2.1.13.1.1
-- 1.3.6.1.4.1.2011.6.122.20.2.1.13.1.1
-- 1.3.6.1.4.1.2011.6.122.20.2.1.13.1.1
-- 1.3.6.1.4.1.2011.6.122.20.2.1.13.1.1
		-- 1.3.6.1.4.1.2011.6.122.20.2.1.13.1.1
		hwSpsFragmentIndex OBJECT-TYPE
			SYNTAX Gauge32
			MAX-ACCESS not-accessible
			STATUS current
			DESCRIPTION
				"The value of this object identifies the index of an SPS fragment table."
			::= { hwSpsFragmentEntry 1 }


--         1.3.6.1.4.1.2011.6.122.20.2.1.13.1.2
-- 1.3.6.1.4.1.2011.6.122.20.2.1.13.1.2
-- 1.3.6.1.4.1.2011.6.122.20.2.1.13.1.2
-- 1.3.6.1.4.1.2011.6.122.20.2.1.13.1.2
-- 1.3.6.1.4.1.2011.6.122.20.2.1.13.1.2
-- 1.3.6.1.4.1.2011.6.122.20.2.1.13.1.2
-- 1.3.6.1.4.1.2011.6.122.20.2.1.13.1.2
-- 1.3.6.1.4.1.2011.6.122.20.2.1.13.1.2
		-- 1.3.6.1.4.1.2011.6.122.20.2.1.13.1.2
		hwSpsFragmentSpsLocation OBJECT-TYPE
			SYNTAX OCTET STRING
			MAX-ACCESS read-write
			STATUS current
			DESCRIPTION
				"This object indicates the location of an SPS, in the x/y/z format."
			::= { hwSpsFragmentEntry 2 }


--         1.3.6.1.4.1.2011.6.122.20.2.1.14
-- 1.3.6.1.4.1.2011.6.122.20.2.1.14
-- 1.3.6.1.4.1.2011.6.122.20.2.1.14
-- 1.3.6.1.4.1.2011.6.122.20.2.1.14
-- 1.3.6.1.4.1.2011.6.122.20.2.1.14
-- 1.3.6.1.4.1.2011.6.122.20.2.1.14
-- 1.3.6.1.4.1.2011.6.122.20.2.1.14
-- 1.3.6.1.4.1.2011.6.122.20.2.1.14
		-- 1.3.6.1.4.1.2011.6.122.20.2.1.14
		hwSasRpdAccountMessageTable OBJECT-TYPE
			SYNTAX SEQUENCE OF HwSasRpdAccountMessageEntry
			MAX-ACCESS not-accessible
			STATUS current
			DESCRIPTION
				"This table describes SAS and RPD information, including the location of each SAS and the IP address of each RPD."
			::= { hwServiceBasicObject 14 }


--         1.3.6.1.4.1.2011.6.122.20.2.1.14.1
-- 1.3.6.1.4.1.2011.6.122.20.2.1.14.1
-- 1.3.6.1.4.1.2011.6.122.20.2.1.14.1
-- 1.3.6.1.4.1.2011.6.122.20.2.1.14.1
-- 1.3.6.1.4.1.2011.6.122.20.2.1.14.1
-- 1.3.6.1.4.1.2011.6.122.20.2.1.14.1
-- 1.3.6.1.4.1.2011.6.122.20.2.1.14.1
-- 1.3.6.1.4.1.2011.6.122.20.2.1.14.1
		-- 1.3.6.1.4.1.2011.6.122.20.2.1.14.1
		hwSasRpdAccountMessageEntry OBJECT-TYPE
			SYNTAX HwSasRpdAccountMessageEntry
			MAX-ACCESS not-accessible
			STATUS current
			DESCRIPTION
				"Description."
			INDEX { hwSasRpdAccountMessageIndex }
			::= { hwSasRpdAccountMessageTable 1 }


		HwSasRpdAccountMessageEntry ::=
			SEQUENCE {
				hwSasRpdAccountMessageIndex
					Gauge32,
				hwSasRpdAccountMessageLocation
					OCTET STRING,
				hwSasRpdAccountMessageRpdIP
					IpAddress
			 }

--         1.3.6.1.4.1.2011.6.122.20.2.1.14.1.1
-- 1.3.6.1.4.1.2011.6.122.20.2.1.14.1.1
-- 1.3.6.1.4.1.2011.6.122.20.2.1.14.1.1
-- 1.3.6.1.4.1.2011.6.122.20.2.1.14.1.1
-- 1.3.6.1.4.1.2011.6.122.20.2.1.14.1.1
-- 1.3.6.1.4.1.2011.6.122.20.2.1.14.1.1
-- 1.3.6.1.4.1.2011.6.122.20.2.1.14.1.1
-- 1.3.6.1.4.1.2011.6.122.20.2.1.14.1.1
		-- 1.3.6.1.4.1.2011.6.122.20.2.1.14.1.1
		hwSasRpdAccountMessageIndex OBJECT-TYPE
			SYNTAX Gauge32
			MAX-ACCESS not-accessible
			STATUS current
			DESCRIPTION
				"The value of this object identifies the index of an SAS and RPD information table."
			::= { hwSasRpdAccountMessageEntry 1 }


--         1.3.6.1.4.1.2011.6.122.20.2.1.14.1.2
-- 1.3.6.1.4.1.2011.6.122.20.2.1.14.1.2
-- 1.3.6.1.4.1.2011.6.122.20.2.1.14.1.2
-- 1.3.6.1.4.1.2011.6.122.20.2.1.14.1.2
-- 1.3.6.1.4.1.2011.6.122.20.2.1.14.1.2
-- 1.3.6.1.4.1.2011.6.122.20.2.1.14.1.2
-- 1.3.6.1.4.1.2011.6.122.20.2.1.14.1.2
-- 1.3.6.1.4.1.2011.6.122.20.2.1.14.1.2
		-- 1.3.6.1.4.1.2011.6.122.20.2.1.14.1.2
		hwSasRpdAccountMessageLocation OBJECT-TYPE
			SYNTAX OCTET STRING
			MAX-ACCESS read-write
			STATUS current
			DESCRIPTION
				"This object indicates the location of an SAS, in the x/y/z format."
			::= { hwSasRpdAccountMessageEntry 2 }


--         1.3.6.1.4.1.2011.6.122.20.2.1.14.1.4
-- 1.3.6.1.4.1.2011.6.122.20.2.1.14.1.4
-- 1.3.6.1.4.1.2011.6.122.20.2.1.14.1.4
-- 1.3.6.1.4.1.2011.6.122.20.2.1.14.1.4
-- 1.3.6.1.4.1.2011.6.122.20.2.1.14.1.4
-- 1.3.6.1.4.1.2011.6.122.20.2.1.14.1.4
-- 1.3.6.1.4.1.2011.6.122.20.2.1.14.1.4
-- 1.3.6.1.4.1.2011.6.122.20.2.1.14.1.4
		-- 1.3.6.1.4.1.2011.6.122.20.2.1.14.1.4
		hwSasRpdAccountMessageRpdIP OBJECT-TYPE
			SYNTAX IpAddress
			MAX-ACCESS read-write
			STATUS current
			DESCRIPTION
				"This object indicates the IP address of an RPD, in dotted decimal notation."
			::= { hwSasRpdAccountMessageEntry 4 }


--         1.3.6.1.4.1.2011.6.122.20.2.1.15
-- 1.3.6.1.4.1.2011.6.122.20.2.1.15
-- 1.3.6.1.4.1.2011.6.122.20.2.1.15
-- 1.3.6.1.4.1.2011.6.122.20.2.1.15
-- 1.3.6.1.4.1.2011.6.122.20.2.1.15
-- 1.3.6.1.4.1.2011.6.122.20.2.1.15
-- 1.3.6.1.4.1.2011.6.122.20.2.1.15
-- 1.3.6.1.4.1.2011.6.122.20.2.1.15
		-- 1.3.6.1.4.1.2011.6.122.20.2.1.15
		hwNPLUS1BackupGroupTable OBJECT-TYPE
			SYNTAX SEQUENCE OF HwNPLUS1BackupGroupEntry
			MAX-ACCESS not-accessible
			STATUS current
			DESCRIPTION
				"Description."
			::= { hwServiceBasicObject 15 }


--         1.3.6.1.4.1.2011.6.122.20.2.1.15.1
-- 1.3.6.1.4.1.2011.6.122.20.2.1.15.1
-- 1.3.6.1.4.1.2011.6.122.20.2.1.15.1
-- 1.3.6.1.4.1.2011.6.122.20.2.1.15.1
-- 1.3.6.1.4.1.2011.6.122.20.2.1.15.1
-- 1.3.6.1.4.1.2011.6.122.20.2.1.15.1
-- 1.3.6.1.4.1.2011.6.122.20.2.1.15.1
-- 1.3.6.1.4.1.2011.6.122.20.2.1.15.1
		-- 1.3.6.1.4.1.2011.6.122.20.2.1.15.1
		hwNPLUS1BackupGroupEntry OBJECT-TYPE
			SYNTAX HwNPLUS1BackupGroupEntry
			MAX-ACCESS not-accessible
			STATUS current
			DESCRIPTION
				"Description."
			INDEX { hwNPLUS1BackupGroupIndex }
			::= { hwNPLUS1BackupGroupTable 1 }


		HwNPLUS1BackupGroupEntry ::=
			SEQUENCE {
				hwNPLUS1BackupGroupIndex
					Gauge32,
				hwNPLUS1BackupGroupID
					Integer32,
				hwNPLUS1BackupGroupBoardList
					OCTET STRING,
				hwNPLUS1BackupGroupBoardType
					OCTET STRING,
				hwNPLUS1BackupIsEnable
					INTEGER
			 }

--         1.3.6.1.4.1.2011.6.122.20.2.1.15.1.1
-- 1.3.6.1.4.1.2011.6.122.20.2.1.15.1.1
-- 1.3.6.1.4.1.2011.6.122.20.2.1.15.1.1
-- 1.3.6.1.4.1.2011.6.122.20.2.1.15.1.1
-- 1.3.6.1.4.1.2011.6.122.20.2.1.15.1.1
-- 1.3.6.1.4.1.2011.6.122.20.2.1.15.1.1
-- 1.3.6.1.4.1.2011.6.122.20.2.1.15.1.1
-- 1.3.6.1.4.1.2011.6.122.20.2.1.15.1.1
		-- 1.3.6.1.4.1.2011.6.122.20.2.1.15.1.1
		hwNPLUS1BackupGroupIndex OBJECT-TYPE
			SYNTAX Gauge32 (1..8)
			MAX-ACCESS not-accessible
			STATUS current
			DESCRIPTION
				"Description."
			::= { hwNPLUS1BackupGroupEntry 1 }


--         1.3.6.1.4.1.2011.6.122.20.2.1.15.1.2
-- 1.3.6.1.4.1.2011.6.122.20.2.1.15.1.2
-- 1.3.6.1.4.1.2011.6.122.20.2.1.15.1.2
-- 1.3.6.1.4.1.2011.6.122.20.2.1.15.1.2
-- 1.3.6.1.4.1.2011.6.122.20.2.1.15.1.2
-- 1.3.6.1.4.1.2011.6.122.20.2.1.15.1.2
-- 1.3.6.1.4.1.2011.6.122.20.2.1.15.1.2
-- 1.3.6.1.4.1.2011.6.122.20.2.1.15.1.2
		-- 1.3.6.1.4.1.2011.6.122.20.2.1.15.1.2
		hwNPLUS1BackupGroupID OBJECT-TYPE
			SYNTAX Integer32 (1..8)
			MAX-ACCESS read-only
			STATUS current
			DESCRIPTION
				"Description."
			::= { hwNPLUS1BackupGroupEntry 2 }


--         1.3.6.1.4.1.2011.6.122.20.2.1.15.1.3
-- 1.3.6.1.4.1.2011.6.122.20.2.1.15.1.3
-- 1.3.6.1.4.1.2011.6.122.20.2.1.15.1.3
-- 1.3.6.1.4.1.2011.6.122.20.2.1.15.1.3
-- 1.3.6.1.4.1.2011.6.122.20.2.1.15.1.3
-- 1.3.6.1.4.1.2011.6.122.20.2.1.15.1.3
-- 1.3.6.1.4.1.2011.6.122.20.2.1.15.1.3
-- 1.3.6.1.4.1.2011.6.122.20.2.1.15.1.3
		-- 1.3.6.1.4.1.2011.6.122.20.2.1.15.1.3
		hwNPLUS1BackupGroupBoardList OBJECT-TYPE
			SYNTAX OCTET STRING (SIZE (0..255))
			MAX-ACCESS read-only
			STATUS current
			DESCRIPTION
				"Description."
			::= { hwNPLUS1BackupGroupEntry 3 }


--         1.3.6.1.4.1.2011.6.122.20.2.1.15.1.4
-- 1.3.6.1.4.1.2011.6.122.20.2.1.15.1.4
-- 1.3.6.1.4.1.2011.6.122.20.2.1.15.1.4
-- 1.3.6.1.4.1.2011.6.122.20.2.1.15.1.4
-- 1.3.6.1.4.1.2011.6.122.20.2.1.15.1.4
-- 1.3.6.1.4.1.2011.6.122.20.2.1.15.1.4
-- 1.3.6.1.4.1.2011.6.122.20.2.1.15.1.4
-- 1.3.6.1.4.1.2011.6.122.20.2.1.15.1.4
		-- 1.3.6.1.4.1.2011.6.122.20.2.1.15.1.4
		hwNPLUS1BackupGroupBoardType OBJECT-TYPE
			SYNTAX OCTET STRING
			MAX-ACCESS read-only
			STATUS current
			DESCRIPTION
				"Description."
			::= { hwNPLUS1BackupGroupEntry 4 }


--       1.3.6.1.4.1.2011.6.122.20.2.1.15.1.5
-- 1.3.6.1.4.1.2011.6.122.20.2.1.15.1.5
-- 1.3.6.1.4.1.2011.6.122.20.2.1.15.1.5
-- 1.3.6.1.4.1.2011.6.122.20.2.1.15.1.5
-- 1.3.6.1.4.1.2011.6.122.20.2.1.15.1.5
-- 1.3.6.1.4.1.2011.6.122.20.2.1.15.1.5
		-- 1.3.6.1.4.1.2011.6.122.20.2.1.15.1.5
		hwNPLUS1BackupIsEnable OBJECT-TYPE
			SYNTAX INTEGER
				{
				disable(0),
				enable(1)
				}
			MAX-ACCESS read-write
			STATUS current
			DESCRIPTION
				"Description."
			::= { hwNPLUS1BackupGroupEntry 5 }


--       1.3.6.1.4.1.2011.6.122.20.2.1.16
-- 1.3.6.1.4.1.2011.6.122.20.2.1.16
-- 1.3.6.1.4.1.2011.6.122.20.2.1.16
-- 1.3.6.1.4.1.2011.6.122.20.2.1.16
-- 1.3.6.1.4.1.2011.6.122.20.2.1.16
-- 1.3.6.1.4.1.2011.6.122.20.2.1.16
		-- 1.3.6.1.4.1.2011.6.122.20.2.1.16
		hwLocalBackupGroupStateTable OBJECT-TYPE
			SYNTAX SEQUENCE OF HwLocalBackupGroupStateEntry
			MAX-ACCESS not-accessible
			STATUS current
			DESCRIPTION
				"Description."
			::= { hwServiceBasicObject 16 }


--       1.3.6.1.4.1.2011.6.122.20.2.1.16.1
-- 1.3.6.1.4.1.2011.6.122.20.2.1.16.1
-- 1.3.6.1.4.1.2011.6.122.20.2.1.16.1
-- 1.3.6.1.4.1.2011.6.122.20.2.1.16.1
-- 1.3.6.1.4.1.2011.6.122.20.2.1.16.1
-- 1.3.6.1.4.1.2011.6.122.20.2.1.16.1
		-- 1.3.6.1.4.1.2011.6.122.20.2.1.16.1
		hwLocalBackupGroupStateEntry OBJECT-TYPE
			SYNTAX HwLocalBackupGroupStateEntry
			MAX-ACCESS not-accessible
			STATUS current
			DESCRIPTION
				"Description."
			INDEX { hwLocalBackupGroupStateCpuIndex }
			::= { hwLocalBackupGroupStateTable 1 }


		HwLocalBackupGroupStateEntry ::=
			SEQUENCE {
				hwLocalBackupGroupStateCpuIndex
					Integer32,
				hwLocalBackupGroupStateCpuLocation
					OCTET STRING,
				hwLocalBackupGroupStateCpuType
					INTEGER,
				hwLocalBackupGroupStateIsEnable
					INTEGER,
				hwLocalBackupGroupStateGroupId
					Integer32,
				hwLocalBackupGroupStateSpuType
					OCTET STRING,
				hwLocalBackupGroupStateCpuMode
					OCTET STRING,
				hwLocalBackupGroupIsStandby
					INTEGER,
				hwLocalBackupSpuTypeInconsist
					INTEGER
			 }

--       1.3.6.1.4.1.2011.6.122.20.2.1.16.1.1
-- 1.3.6.1.4.1.2011.6.122.20.2.1.16.1.1
-- 1.3.6.1.4.1.2011.6.122.20.2.1.16.1.1
-- 1.3.6.1.4.1.2011.6.122.20.2.1.16.1.1
-- 1.3.6.1.4.1.2011.6.122.20.2.1.16.1.1
-- 1.3.6.1.4.1.2011.6.122.20.2.1.16.1.1
		-- 1.3.6.1.4.1.2011.6.122.20.2.1.16.1.1
		hwLocalBackupGroupStateCpuIndex OBJECT-TYPE
			SYNTAX Integer32 (1..2147483647)
			MAX-ACCESS read-write
			STATUS current
			DESCRIPTION
				"Description."
			::= { hwLocalBackupGroupStateEntry 1 }


--       1.3.6.1.4.1.2011.6.122.20.2.1.16.1.2
-- 1.3.6.1.4.1.2011.6.122.20.2.1.16.1.2
-- 1.3.6.1.4.1.2011.6.122.20.2.1.16.1.2
-- 1.3.6.1.4.1.2011.6.122.20.2.1.16.1.2
-- 1.3.6.1.4.1.2011.6.122.20.2.1.16.1.2
-- 1.3.6.1.4.1.2011.6.122.20.2.1.16.1.2
		-- 1.3.6.1.4.1.2011.6.122.20.2.1.16.1.2
		hwLocalBackupGroupStateCpuLocation OBJECT-TYPE
			SYNTAX OCTET STRING
			MAX-ACCESS read-write
			STATUS current
			DESCRIPTION
				"Description."
			::= { hwLocalBackupGroupStateEntry 2 }


--       1.3.6.1.4.1.2011.6.122.20.2.1.16.1.3
-- 1.3.6.1.4.1.2011.6.122.20.2.1.16.1.3
-- 1.3.6.1.4.1.2011.6.122.20.2.1.16.1.3
-- 1.3.6.1.4.1.2011.6.122.20.2.1.16.1.3
-- 1.3.6.1.4.1.2011.6.122.20.2.1.16.1.3
-- 1.3.6.1.4.1.2011.6.122.20.2.1.16.1.3
		-- 1.3.6.1.4.1.2011.6.122.20.2.1.16.1.3
		hwLocalBackupGroupStateCpuType OBJECT-TYPE
			SYNTAX INTEGER
				{
				sas(1),
				sps(2)
				}
			MAX-ACCESS read-write
			STATUS current
			DESCRIPTION
				"Description."
			::= { hwLocalBackupGroupStateEntry 3 }


--       1.3.6.1.4.1.2011.6.122.20.2.1.16.1.4
-- 1.3.6.1.4.1.2011.6.122.20.2.1.16.1.4
-- 1.3.6.1.4.1.2011.6.122.20.2.1.16.1.4
-- 1.3.6.1.4.1.2011.6.122.20.2.1.16.1.4
-- 1.3.6.1.4.1.2011.6.122.20.2.1.16.1.4
-- 1.3.6.1.4.1.2011.6.122.20.2.1.16.1.4
		-- 1.3.6.1.4.1.2011.6.122.20.2.1.16.1.4
		hwLocalBackupGroupStateIsEnable OBJECT-TYPE
			SYNTAX INTEGER
				{
				disable(0),
				enable(1)
				}
			MAX-ACCESS read-write
			STATUS current
			DESCRIPTION
				"Description."
			::= { hwLocalBackupGroupStateEntry 4 }


--       1.3.6.1.4.1.2011.6.122.20.2.1.16.1.5
-- 1.3.6.1.4.1.2011.6.122.20.2.1.16.1.5
-- 1.3.6.1.4.1.2011.6.122.20.2.1.16.1.5
-- 1.3.6.1.4.1.2011.6.122.20.2.1.16.1.5
-- 1.3.6.1.4.1.2011.6.122.20.2.1.16.1.5
-- 1.3.6.1.4.1.2011.6.122.20.2.1.16.1.5
		-- 1.3.6.1.4.1.2011.6.122.20.2.1.16.1.5
		hwLocalBackupGroupStateGroupId OBJECT-TYPE
			SYNTAX Integer32 (1..8)
			MAX-ACCESS read-write
			STATUS current
			DESCRIPTION
				"Description."
			::= { hwLocalBackupGroupStateEntry 5 }


--       1.3.6.1.4.1.2011.6.122.20.2.1.16.1.6
-- 1.3.6.1.4.1.2011.6.122.20.2.1.16.1.6
-- 1.3.6.1.4.1.2011.6.122.20.2.1.16.1.6
-- 1.3.6.1.4.1.2011.6.122.20.2.1.16.1.6
-- 1.3.6.1.4.1.2011.6.122.20.2.1.16.1.6
-- 1.3.6.1.4.1.2011.6.122.20.2.1.16.1.6
		-- 1.3.6.1.4.1.2011.6.122.20.2.1.16.1.6
		hwLocalBackupGroupStateSpuType OBJECT-TYPE
			SYNTAX OCTET STRING
			MAX-ACCESS read-write
			STATUS current
			DESCRIPTION
				"Description."
			::= { hwLocalBackupGroupStateEntry 6 }


--       1.3.6.1.4.1.2011.6.122.20.2.1.16.1.7
-- 1.3.6.1.4.1.2011.6.122.20.2.1.16.1.7
-- 1.3.6.1.4.1.2011.6.122.20.2.1.16.1.7
-- 1.3.6.1.4.1.2011.6.122.20.2.1.16.1.7
-- 1.3.6.1.4.1.2011.6.122.20.2.1.16.1.7
-- 1.3.6.1.4.1.2011.6.122.20.2.1.16.1.7
		-- 1.3.6.1.4.1.2011.6.122.20.2.1.16.1.7
		hwLocalBackupGroupStateCpuMode OBJECT-TYPE
			SYNTAX OCTET STRING
			MAX-ACCESS read-write
			STATUS current
			DESCRIPTION
				"Description."
			::= { hwLocalBackupGroupStateEntry 7 }


--      1.3.6.1.4.1.2011.6.122.20.2.1.16.1.8
-- 1.3.6.1.4.1.2011.6.122.20.2.1.16.1.8
-- 1.3.6.1.4.1.2011.6.122.20.2.1.16.1.8
-- 1.3.6.1.4.1.2011.6.122.20.2.1.16.1.8
-- 1.3.6.1.4.1.2011.6.122.20.2.1.16.1.8
		-- 1.3.6.1.4.1.2011.6.122.20.2.1.16.1.8
		hwLocalBackupGroupIsStandby OBJECT-TYPE
			SYNTAX INTEGER
				{
				no(0),
				yes(1)
				}
			MAX-ACCESS read-write
			STATUS current
			DESCRIPTION
				"Description."
			::= { hwLocalBackupGroupStateEntry 8 }


--      1.3.6.1.4.1.2011.6.122.20.2.1.16.1.9
-- 1.3.6.1.4.1.2011.6.122.20.2.1.16.1.9
-- 1.3.6.1.4.1.2011.6.122.20.2.1.16.1.9
-- 1.3.6.1.4.1.2011.6.122.20.2.1.16.1.9
-- 1.3.6.1.4.1.2011.6.122.20.2.1.16.1.9
		-- 1.3.6.1.4.1.2011.6.122.20.2.1.16.1.9
		hwLocalBackupSpuTypeInconsist OBJECT-TYPE
			SYNTAX INTEGER
				{
				no(0),
				yes(1)
				}
			MAX-ACCESS read-write
			STATUS current
			DESCRIPTION
				"Description."
			::= { hwLocalBackupGroupStateEntry 9 }


--     1.3.6.1.4.1.2011.6.122.20.2.1.17
-- 1.3.6.1.4.1.2011.6.122.20.2.1.17
-- 1.3.6.1.4.1.2011.6.122.20.2.1.17
-- 1.3.6.1.4.1.2011.6.122.20.2.1.17
		-- 1.3.6.1.4.1.2011.6.122.20.2.1.17
		hwSpsLeastNumberTable OBJECT-TYPE
			SYNTAX SEQUENCE OF HwSpsLeastNumberEntry
			MAX-ACCESS not-accessible
			STATUS current
			DESCRIPTION
				"This table describes the least SPS number configured."
			::= { hwServiceBasicObject 17 }


--     1.3.6.1.4.1.2011.6.122.20.2.1.17.1
-- 1.3.6.1.4.1.2011.6.122.20.2.1.17.1
-- 1.3.6.1.4.1.2011.6.122.20.2.1.17.1
-- 1.3.6.1.4.1.2011.6.122.20.2.1.17.1
		-- 1.3.6.1.4.1.2011.6.122.20.2.1.17.1
		hwSpsLeastNumberEntry OBJECT-TYPE
			SYNTAX HwSpsLeastNumberEntry
			MAX-ACCESS not-accessible
			STATUS current
			DESCRIPTION
				"Description."
			INDEX { hwSpsCpuEntityIndex }
			::= { hwSpsLeastNumberTable 1 }


		HwSpsLeastNumberEntry ::=
			SEQUENCE {
				hwSpsLeastNumberCfg
					Integer32,
				hwSpsLeastNumberIndex
					Integer32
			 }

--     1.3.6.1.4.1.2011.6.122.20.2.1.17.1.1
-- 1.3.6.1.4.1.2011.6.122.20.2.1.17.1.1
-- 1.3.6.1.4.1.2011.6.122.20.2.1.17.1.1
-- 1.3.6.1.4.1.2011.6.122.20.2.1.17.1.1
		-- 1.3.6.1.4.1.2011.6.122.20.2.1.17.1.1
		hwSpsLeastNumberCfg OBJECT-TYPE
			SYNTAX Integer32 (1..128)
			MAX-ACCESS read-write
			STATUS current
			DESCRIPTION
				"The value of this object identifies the SPS least number configured."
			::= { hwSpsLeastNumberEntry 1 }


--     1.3.6.1.4.1.2011.6.122.20.2.1.17.1.2
-- 1.3.6.1.4.1.2011.6.122.20.2.1.17.1.2
-- 1.3.6.1.4.1.2011.6.122.20.2.1.17.1.2
-- 1.3.6.1.4.1.2011.6.122.20.2.1.17.1.2
		-- 1.3.6.1.4.1.2011.6.122.20.2.1.17.1.2
		hwSpsLeastNumberIndex OBJECT-TYPE
			SYNTAX Integer32 (1)
			MAX-ACCESS read-write
			STATUS current
			DESCRIPTION
				"The value of this object identifies the index of an SPS least number table."
			::= { hwSpsLeastNumberEntry 2 }


--     1.3.6.1.4.1.2011.6.122.20.2.1.18
-- 1.3.6.1.4.1.2011.6.122.20.2.1.18
-- 1.3.6.1.4.1.2011.6.122.20.2.1.18
-- 1.3.6.1.4.1.2011.6.122.20.2.1.18
		-- 1.3.6.1.4.1.2011.6.122.20.2.1.18
		hwSpsCpuStateTable OBJECT-TYPE
			SYNTAX SEQUENCE OF HwSpsCpuStateEntry
			MAX-ACCESS not-accessible
			STATUS current
			DESCRIPTION
				"This table describes cpu state information of SPS, including the average cpu usage and the threshold and the forwarding queue usage and the overload threshold on SPS."
			::= { hwServiceBasicObject 18 }


--     1.3.6.1.4.1.2011.6.122.20.2.1.18.1
-- 1.3.6.1.4.1.2011.6.122.20.2.1.18.1
-- 1.3.6.1.4.1.2011.6.122.20.2.1.18.1
-- 1.3.6.1.4.1.2011.6.122.20.2.1.18.1
		-- 1.3.6.1.4.1.2011.6.122.20.2.1.18.1
		hwSpsCpuStateEntry OBJECT-TYPE
			SYNTAX HwSpsCpuStateEntry
			MAX-ACCESS not-accessible
			STATUS current
			DESCRIPTION
				"Description."
			INDEX { hwSpsCpuEntityIndex }
			::= { hwSpsCpuStateTable 1 }


		HwSpsCpuStateEntry ::=
			SEQUENCE {
				hwSpsEntityLocation
					OCTET STRING,
				hwSpsAverageCpuUsage
					Integer32,
				hwSpsAverageCpuUsageThreshold
					Integer32,
				hwSpsQueueUsage
					Integer32,
				hwSpsOverloadThreshold
					Integer32,
				hwSpsCpuEntityIndex
					Integer32
			 }

--     1.3.6.1.4.1.2011.6.122.20.2.1.18.1.1
-- 1.3.6.1.4.1.2011.6.122.20.2.1.18.1.1
-- 1.3.6.1.4.1.2011.6.122.20.2.1.18.1.1
-- 1.3.6.1.4.1.2011.6.122.20.2.1.18.1.1
		-- 1.3.6.1.4.1.2011.6.122.20.2.1.18.1.1
		hwSpsEntityLocation OBJECT-TYPE
			SYNTAX OCTET STRING (SIZE (0..255))
			MAX-ACCESS read-write
			STATUS current
			DESCRIPTION
				"This object indicates the location of an SPS, in the slot-id/subcard-id/cpu-id format."
			::= { hwSpsCpuStateEntry 1 }


--     1.3.6.1.4.1.2011.6.122.20.2.1.18.1.2
-- 1.3.6.1.4.1.2011.6.122.20.2.1.18.1.2
-- 1.3.6.1.4.1.2011.6.122.20.2.1.18.1.2
-- 1.3.6.1.4.1.2011.6.122.20.2.1.18.1.2
		-- 1.3.6.1.4.1.2011.6.122.20.2.1.18.1.2
		hwSpsAverageCpuUsage OBJECT-TYPE
			SYNTAX Integer32
			MAX-ACCESS read-write
			STATUS current
			DESCRIPTION
				"The value of this object identifies the average CPU usage of SPS."
			::= { hwSpsCpuStateEntry 2 }


--     1.3.6.1.4.1.2011.6.122.20.2.1.18.1.3
-- 1.3.6.1.4.1.2011.6.122.20.2.1.18.1.3
-- 1.3.6.1.4.1.2011.6.122.20.2.1.18.1.3
-- 1.3.6.1.4.1.2011.6.122.20.2.1.18.1.3
		-- 1.3.6.1.4.1.2011.6.122.20.2.1.18.1.3
		hwSpsAverageCpuUsageThreshold OBJECT-TYPE
			SYNTAX Integer32
			MAX-ACCESS read-write
			STATUS current
			DESCRIPTION
				"The value of this object identifies a CPU usage alarm threshold, in percentage. An alarm is reported when the CPU usage reaches this threshold."
			::= { hwSpsCpuStateEntry 3 }


--     1.3.6.1.4.1.2011.6.122.20.2.1.18.1.4
-- 1.3.6.1.4.1.2011.6.122.20.2.1.18.1.4
-- 1.3.6.1.4.1.2011.6.122.20.2.1.18.1.4
-- 1.3.6.1.4.1.2011.6.122.20.2.1.18.1.4
		-- 1.3.6.1.4.1.2011.6.122.20.2.1.18.1.4
		hwSpsQueueUsage OBJECT-TYPE
			SYNTAX Integer32
			MAX-ACCESS read-write
			STATUS current
			DESCRIPTION
				"The value of this object identifies the SPS forwarding queue usage of SPS."
			::= { hwSpsCpuStateEntry 4 }


--     1.3.6.1.4.1.2011.6.122.20.2.1.18.1.5
-- 1.3.6.1.4.1.2011.6.122.20.2.1.18.1.5
-- 1.3.6.1.4.1.2011.6.122.20.2.1.18.1.5
-- 1.3.6.1.4.1.2011.6.122.20.2.1.18.1.5
		-- 1.3.6.1.4.1.2011.6.122.20.2.1.18.1.5
		hwSpsOverloadThreshold OBJECT-TYPE
			SYNTAX Integer32
			MAX-ACCESS read-write
			STATUS current
			DESCRIPTION
				"The value of this object identifies a forwarding queue usage alarm threshold, in percentage. An alarm is reported when the forwarding queue usage reaches this threshold."
			::= { hwSpsCpuStateEntry 5 }


--     1.3.6.1.4.1.2011.6.122.20.2.1.18.1.6
-- 1.3.6.1.4.1.2011.6.122.20.2.1.18.1.6
-- 1.3.6.1.4.1.2011.6.122.20.2.1.18.1.6
-- 1.3.6.1.4.1.2011.6.122.20.2.1.18.1.6
		-- 1.3.6.1.4.1.2011.6.122.20.2.1.18.1.6
		hwSpsCpuEntityIndex OBJECT-TYPE
			SYNTAX Integer32 (1..2147483647)
			MAX-ACCESS read-write
			STATUS current
			DESCRIPTION
				"The value of this object identifies the index of SPS."
			::= { hwSpsCpuStateEntry 6 }


--         1.3.6.1.4.1.2011.6.122.20.2.2
-- 1.3.6.1.4.1.2011.6.122.20.2.2
-- 1.3.6.1.4.1.2011.6.122.20.2.2
-- 1.3.6.1.4.1.2011.6.122.20.2.2
-- 1.3.6.1.4.1.2011.6.122.20.2.2
-- 1.3.6.1.4.1.2011.6.122.20.2.2
-- 1.3.6.1.4.1.2011.6.122.20.2.2
-- 1.3.6.1.4.1.2011.6.122.20.2.2
		-- 1.3.6.1.4.1.2011.6.122.20.2.2
		hwServiceBasicTrap OBJECT IDENTIFIER ::= { hwServiceObject 2 }


--         1.3.6.1.4.1.2011.6.122.20.2.2.1
-- 1.3.6.1.4.1.2011.6.122.20.2.2.1
-- 1.3.6.1.4.1.2011.6.122.20.2.2.1
-- 1.3.6.1.4.1.2011.6.122.20.2.2.1
-- 1.3.6.1.4.1.2011.6.122.20.2.2.1
-- 1.3.6.1.4.1.2011.6.122.20.2.2.1
-- 1.3.6.1.4.1.2011.6.122.20.2.2.1
-- 1.3.6.1.4.1.2011.6.122.20.2.2.1
		-- 1.3.6.1.4.1.2011.6.122.20.2.2.1
		hwSpuCompLinkAddTrap NOTIFICATION-TYPE
			OBJECTS { hwSpuSysInfoType, hwSpuSysInfoIPAddress, hwSpuCompLinkCurrentDestIP, hwSpuCompLinkCurrentDestPort, hwSpuCompLinkComponentType
				 }
			STATUS current
			DESCRIPTION
				"Description."
			::= { hwServiceBasicTrap 1 }


--         1.3.6.1.4.1.2011.6.122.20.2.2.2
-- 1.3.6.1.4.1.2011.6.122.20.2.2.2
-- 1.3.6.1.4.1.2011.6.122.20.2.2.2
-- 1.3.6.1.4.1.2011.6.122.20.2.2.2
-- 1.3.6.1.4.1.2011.6.122.20.2.2.2
-- 1.3.6.1.4.1.2011.6.122.20.2.2.2
-- 1.3.6.1.4.1.2011.6.122.20.2.2.2
-- 1.3.6.1.4.1.2011.6.122.20.2.2.2
		-- 1.3.6.1.4.1.2011.6.122.20.2.2.2
		hwSpuCompLinkDeleteTrap NOTIFICATION-TYPE
			OBJECTS { hwSpuSysInfoLocation, hwSpuSysInfoType, hwSpuSysInfoIPAddress, hwSpuCompLinkCurrentDestIP, hwSpuCompLinkCurrentDestPort,
				hwSpuCompLinkComponentType }
			STATUS current
			DESCRIPTION
				"Description."
			::= { hwServiceBasicTrap 2 }


--         1.3.6.1.4.1.2011.6.122.20.2.2.3
-- 1.3.6.1.4.1.2011.6.122.20.2.2.3
-- 1.3.6.1.4.1.2011.6.122.20.2.2.3
-- 1.3.6.1.4.1.2011.6.122.20.2.2.3
-- 1.3.6.1.4.1.2011.6.122.20.2.2.3
-- 1.3.6.1.4.1.2011.6.122.20.2.2.3
-- 1.3.6.1.4.1.2011.6.122.20.2.2.3
-- 1.3.6.1.4.1.2011.6.122.20.2.2.3
		-- 1.3.6.1.4.1.2011.6.122.20.2.2.3
		hwSpuCompLinkConnectDownTrap NOTIFICATION-TYPE
			OBJECTS { hwSpuSysInfoLocation, hwSpuSysInfoType, hwSpuSysInfoIPAddress, hwSpuCompLinkCurrentDestIP, hwSpuCompLinkCurrentDestPort,
				hwSpuCompLinkComponentType }
			STATUS current
			DESCRIPTION
				"This object indicates that the connection between a VSUF and a back-end component fails.
Cause 1:The back-end components are faulty.
Cause 2:The network is faulty."
			::= { hwServiceBasicTrap 3 }


--         1.3.6.1.4.1.2011.6.122.20.2.2.4
-- 1.3.6.1.4.1.2011.6.122.20.2.2.4
-- 1.3.6.1.4.1.2011.6.122.20.2.2.4
-- 1.3.6.1.4.1.2011.6.122.20.2.2.4
-- 1.3.6.1.4.1.2011.6.122.20.2.2.4
-- 1.3.6.1.4.1.2011.6.122.20.2.2.4
-- 1.3.6.1.4.1.2011.6.122.20.2.2.4
-- 1.3.6.1.4.1.2011.6.122.20.2.2.4
		-- 1.3.6.1.4.1.2011.6.122.20.2.2.4
		hwSpuCompLinkConnectUpTrap NOTIFICATION-TYPE
			OBJECTS { hwSpuSysInfoLocation, hwSpuSysInfoType, hwSpuSysInfoIPAddress, hwSpuCompLinkCurrentDestIP, hwSpuCompLinkCurrentDestPort,
				hwSpuCompLinkComponentType }
			STATUS current
			DESCRIPTION
				"This object indicates that the connection between a VSUF and a back-end component restores."
			::= { hwServiceBasicTrap 4 }


--         1.3.6.1.4.1.2011.6.122.20.2.2.5
-- 1.3.6.1.4.1.2011.6.122.20.2.2.5
-- 1.3.6.1.4.1.2011.6.122.20.2.2.5
-- 1.3.6.1.4.1.2011.6.122.20.2.2.5
-- 1.3.6.1.4.1.2011.6.122.20.2.2.5
-- 1.3.6.1.4.1.2011.6.122.20.2.2.5
-- 1.3.6.1.4.1.2011.6.122.20.2.2.5
-- 1.3.6.1.4.1.2011.6.122.20.2.2.5
		-- 1.3.6.1.4.1.2011.6.122.20.2.2.5
		hwSpsSasLinkAddTrap NOTIFICATION-TYPE
			OBJECTS { hwSpsSasLinkSpsIP, hwSpsSasLinkSasIP }
			STATUS current
			DESCRIPTION
				"Description."
			::= { hwServiceBasicTrap 5 }


--         1.3.6.1.4.1.2011.6.122.20.2.2.6
-- 1.3.6.1.4.1.2011.6.122.20.2.2.6
-- 1.3.6.1.4.1.2011.6.122.20.2.2.6
-- 1.3.6.1.4.1.2011.6.122.20.2.2.6
-- 1.3.6.1.4.1.2011.6.122.20.2.2.6
-- 1.3.6.1.4.1.2011.6.122.20.2.2.6
-- 1.3.6.1.4.1.2011.6.122.20.2.2.6
-- 1.3.6.1.4.1.2011.6.122.20.2.2.6
		-- 1.3.6.1.4.1.2011.6.122.20.2.2.6
		hwSpsSasLinkDeleteTrap NOTIFICATION-TYPE
			OBJECTS { hwSpsSasLinkSpsIP, hwSpsSasLinkSasIP }
			STATUS current
			DESCRIPTION
				"Description."
			::= { hwServiceBasicTrap 6 }


--         1.3.6.1.4.1.2011.6.122.20.2.2.7
-- 1.3.6.1.4.1.2011.6.122.20.2.2.7
-- 1.3.6.1.4.1.2011.6.122.20.2.2.7
-- 1.3.6.1.4.1.2011.6.122.20.2.2.7
-- 1.3.6.1.4.1.2011.6.122.20.2.2.7
-- 1.3.6.1.4.1.2011.6.122.20.2.2.7
-- 1.3.6.1.4.1.2011.6.122.20.2.2.7
-- 1.3.6.1.4.1.2011.6.122.20.2.2.7
		-- 1.3.6.1.4.1.2011.6.122.20.2.2.7
		hwSpsSasLinkDownTrap NOTIFICATION-TYPE
			OBJECTS { hwSpsSasLinkSpsIP, hwSpsSasLinkSasIP }
			STATUS current
			DESCRIPTION
				"Description."
			::= { hwServiceBasicTrap 7 }


--         1.3.6.1.4.1.2011.6.122.20.2.2.8
-- 1.3.6.1.4.1.2011.6.122.20.2.2.8
-- 1.3.6.1.4.1.2011.6.122.20.2.2.8
-- 1.3.6.1.4.1.2011.6.122.20.2.2.8
-- 1.3.6.1.4.1.2011.6.122.20.2.2.8
-- 1.3.6.1.4.1.2011.6.122.20.2.2.8
-- 1.3.6.1.4.1.2011.6.122.20.2.2.8
-- 1.3.6.1.4.1.2011.6.122.20.2.2.8
		-- 1.3.6.1.4.1.2011.6.122.20.2.2.8
		hwSpsSasLinkUpTrap NOTIFICATION-TYPE
			OBJECTS { hwSpsSasLinkSpsIP, hwSpsSasLinkSasIP }
			STATUS current
			DESCRIPTION
				"Description."
			::= { hwServiceBasicTrap 8 }


--         1.3.6.1.4.1.2011.6.122.20.2.2.9
-- 1.3.6.1.4.1.2011.6.122.20.2.2.9
-- 1.3.6.1.4.1.2011.6.122.20.2.2.9
-- 1.3.6.1.4.1.2011.6.122.20.2.2.9
-- 1.3.6.1.4.1.2011.6.122.20.2.2.9
-- 1.3.6.1.4.1.2011.6.122.20.2.2.9
-- 1.3.6.1.4.1.2011.6.122.20.2.2.9
-- 1.3.6.1.4.1.2011.6.122.20.2.2.9
		-- 1.3.6.1.4.1.2011.6.122.20.2.2.9
		hwResourceNotEnoughTrap NOTIFICATION-TYPE
			OBJECTS { hwResourceLocation, hwSAResourceType, hwResourceUsage }
			STATUS current
			DESCRIPTION
				"Description."
			::= { hwServiceBasicTrap 9 }


--         1.3.6.1.4.1.2011.6.122.20.2.2.10
-- 1.3.6.1.4.1.2011.6.122.20.2.2.10
-- 1.3.6.1.4.1.2011.6.122.20.2.2.10
-- 1.3.6.1.4.1.2011.6.122.20.2.2.10
-- 1.3.6.1.4.1.2011.6.122.20.2.2.10
-- 1.3.6.1.4.1.2011.6.122.20.2.2.10
-- 1.3.6.1.4.1.2011.6.122.20.2.2.10
-- 1.3.6.1.4.1.2011.6.122.20.2.2.10
		-- 1.3.6.1.4.1.2011.6.122.20.2.2.10
		hwBWListSyncErrTrap NOTIFICATION-TYPE
			OBJECTS { hwBWListLocation, hwBWListVersion, hwBWListType }
			STATUS current
			DESCRIPTION
				"Description."
			::= { hwServiceBasicTrap 10 }


--         1.3.6.1.4.1.2011.6.122.20.2.2.11
-- 1.3.6.1.4.1.2011.6.122.20.2.2.11
-- 1.3.6.1.4.1.2011.6.122.20.2.2.11
-- 1.3.6.1.4.1.2011.6.122.20.2.2.11
-- 1.3.6.1.4.1.2011.6.122.20.2.2.11
-- 1.3.6.1.4.1.2011.6.122.20.2.2.11
-- 1.3.6.1.4.1.2011.6.122.20.2.2.11
-- 1.3.6.1.4.1.2011.6.122.20.2.2.11
		-- 1.3.6.1.4.1.2011.6.122.20.2.2.11
		hwSAFdiConnectDownTrap NOTIFICATION-TYPE
			OBJECTS { hwSAFdiConnectLocation, hwSysFdiInstanceID, hwSysFdiDestMasterIP }
			STATUS current
			DESCRIPTION
				"Description."
			::= { hwServiceBasicTrap 11 }


--         1.3.6.1.4.1.2011.6.122.20.2.2.12
-- 1.3.6.1.4.1.2011.6.122.20.2.2.12
-- 1.3.6.1.4.1.2011.6.122.20.2.2.12
-- 1.3.6.1.4.1.2011.6.122.20.2.2.12
-- 1.3.6.1.4.1.2011.6.122.20.2.2.12
-- 1.3.6.1.4.1.2011.6.122.20.2.2.12
-- 1.3.6.1.4.1.2011.6.122.20.2.2.12
-- 1.3.6.1.4.1.2011.6.122.20.2.2.12
		-- 1.3.6.1.4.1.2011.6.122.20.2.2.12
		hwRadiusSnifferNoAckTrap NOTIFICATION-TYPE
			OBJECTS { hwSnifferInfoLocation, hwSnifferSrcIPAddress, hwSnifferDstIPAddress }
			STATUS current
			DESCRIPTION
				"An SPS fails to receive sniffer acknowledgement packets from a RADIUS proxy server. Possible causes are as follows:
Cause 1: The IP address of the RADIUS proxy server is incorrect.
Cause 2: The operating status of the RADIUS proxy server in the State column is displayed as DOWN.A network fault occurs between the Front End and RADIUS proxy server.
The operating status of the RADIUS proxy server is abnormal."
			::= { hwServiceBasicTrap 12 }


--         1.3.6.1.4.1.2011.6.122.20.2.2.13
-- 1.3.6.1.4.1.2011.6.122.20.2.2.13
-- 1.3.6.1.4.1.2011.6.122.20.2.2.13
-- 1.3.6.1.4.1.2011.6.122.20.2.2.13
-- 1.3.6.1.4.1.2011.6.122.20.2.2.13
-- 1.3.6.1.4.1.2011.6.122.20.2.2.13
-- 1.3.6.1.4.1.2011.6.122.20.2.2.13
-- 1.3.6.1.4.1.2011.6.122.20.2.2.13
		-- 1.3.6.1.4.1.2011.6.122.20.2.2.13
		hwRadiusSnifferAckOkTrap NOTIFICATION-TYPE
			OBJECTS { hwSnifferInfoLocation, hwSnifferSrcIPAddress, hwSnifferDstIPAddress }
			STATUS current
			DESCRIPTION
				"An SPS receives sniffer acknowledgement packets from a RADIUS proxy server."
			::= { hwServiceBasicTrap 13 }


--         1.3.6.1.4.1.2011.6.122.20.2.2.14
-- 1.3.6.1.4.1.2011.6.122.20.2.2.14
-- 1.3.6.1.4.1.2011.6.122.20.2.2.14
-- 1.3.6.1.4.1.2011.6.122.20.2.2.14
-- 1.3.6.1.4.1.2011.6.122.20.2.2.14
-- 1.3.6.1.4.1.2011.6.122.20.2.2.14
-- 1.3.6.1.4.1.2011.6.122.20.2.2.14
-- 1.3.6.1.4.1.2011.6.122.20.2.2.14
		-- 1.3.6.1.4.1.2011.6.122.20.2.2.14
		hwSpsUcssLinkDownTrap NOTIFICATION-TYPE
			OBJECTS { hwSpsUcssLinkSpsLocation, hwSpsUcssLinkSpsIP, hwSpsUcssLinkUcssIP }
			STATUS current
			DESCRIPTION
				"An SPS and a UCSS are disconnected.
Cause 1: The network between the SPS and UCSS is faulty.
Cause 2: The UHC is not configured properly.
Cause 3: The UCSS process is faulty."
			::= { hwServiceBasicTrap 14 }


--         1.3.6.1.4.1.2011.6.122.20.2.2.15
-- 1.3.6.1.4.1.2011.6.122.20.2.2.15
-- 1.3.6.1.4.1.2011.6.122.20.2.2.15
-- 1.3.6.1.4.1.2011.6.122.20.2.2.15
-- 1.3.6.1.4.1.2011.6.122.20.2.2.15
-- 1.3.6.1.4.1.2011.6.122.20.2.2.15
-- 1.3.6.1.4.1.2011.6.122.20.2.2.15
-- 1.3.6.1.4.1.2011.6.122.20.2.2.15
		-- 1.3.6.1.4.1.2011.6.122.20.2.2.15
		hwSpsUcssLinkUpTrap NOTIFICATION-TYPE
			OBJECTS { hwSpsUcssLinkSpsLocation, hwSpsUcssLinkSpsIP, hwSpsUcssLinkUcssIP }
			STATUS current
			DESCRIPTION
				"The connection between an SPS and a UCSS recovers."
			::= { hwServiceBasicTrap 15 }


--         1.3.6.1.4.1.2011.6.122.20.2.2.19
-- 1.3.6.1.4.1.2011.6.122.20.2.2.19
-- 1.3.6.1.4.1.2011.6.122.20.2.2.19
-- 1.3.6.1.4.1.2011.6.122.20.2.2.19
-- 1.3.6.1.4.1.2011.6.122.20.2.2.19
-- 1.3.6.1.4.1.2011.6.122.20.2.2.19
-- 1.3.6.1.4.1.2011.6.122.20.2.2.19
-- 1.3.6.1.4.1.2011.6.122.20.2.2.19
		-- 1.3.6.1.4.1.2011.6.122.20.2.2.19
		hwBackupGroupStateChangeToMasterTrap NOTIFICATION-TYPE
			OBJECTS { hwBackupGroupID }
			STATUS current
			DESCRIPTION
				"Description."
			::= { hwServiceBasicTrap 19 }


--         1.3.6.1.4.1.2011.6.122.20.2.2.21
-- 1.3.6.1.4.1.2011.6.122.20.2.2.21
-- 1.3.6.1.4.1.2011.6.122.20.2.2.21
-- 1.3.6.1.4.1.2011.6.122.20.2.2.21
-- 1.3.6.1.4.1.2011.6.122.20.2.2.21
-- 1.3.6.1.4.1.2011.6.122.20.2.2.21
-- 1.3.6.1.4.1.2011.6.122.20.2.2.21
-- 1.3.6.1.4.1.2011.6.122.20.2.2.21
		-- 1.3.6.1.4.1.2011.6.122.20.2.2.21
		hwBackupGroupStateChangeToBackupTrap NOTIFICATION-TYPE
			OBJECTS { hwBackupGroupID }
			STATUS current
			DESCRIPTION
				"Description."
			::= { hwServiceBasicTrap 21 }


--         1.3.6.1.4.1.2011.6.122.20.2.2.22
-- 1.3.6.1.4.1.2011.6.122.20.2.2.22
-- 1.3.6.1.4.1.2011.6.122.20.2.2.22
-- 1.3.6.1.4.1.2011.6.122.20.2.2.22
-- 1.3.6.1.4.1.2011.6.122.20.2.2.22
-- 1.3.6.1.4.1.2011.6.122.20.2.2.22
-- 1.3.6.1.4.1.2011.6.122.20.2.2.22
-- 1.3.6.1.4.1.2011.6.122.20.2.2.22
		-- 1.3.6.1.4.1.2011.6.122.20.2.2.22
		hwSpsRdasLinkDownTrap NOTIFICATION-TYPE
			OBJECTS { hwSpsRdasLinkSpsLocation, hwSpsRdasLinkRdasIP }
			STATUS current
			DESCRIPTION
				"An SPS and an RDAS are disconnected."
			::= { hwServiceBasicTrap 22 }


--         1.3.6.1.4.1.2011.6.122.20.2.2.23
-- 1.3.6.1.4.1.2011.6.122.20.2.2.23
-- 1.3.6.1.4.1.2011.6.122.20.2.2.23
-- 1.3.6.1.4.1.2011.6.122.20.2.2.23
-- 1.3.6.1.4.1.2011.6.122.20.2.2.23
-- 1.3.6.1.4.1.2011.6.122.20.2.2.23
-- 1.3.6.1.4.1.2011.6.122.20.2.2.23
-- 1.3.6.1.4.1.2011.6.122.20.2.2.23
		-- 1.3.6.1.4.1.2011.6.122.20.2.2.23
		hwSpsRdasLinkUpTrap NOTIFICATION-TYPE
			OBJECTS { hwSpsRdasLinkSpsLocation, hwSpsRdasLinkRdasIP }
			STATUS current
			DESCRIPTION
				"The connection between an SPS and an RDAS recovers."
			::= { hwServiceBasicTrap 23 }


--         1.3.6.1.4.1.2011.6.122.20.2.2.25
-- 1.3.6.1.4.1.2011.6.122.20.2.2.25
-- 1.3.6.1.4.1.2011.6.122.20.2.2.25
-- 1.3.6.1.4.1.2011.6.122.20.2.2.25
-- 1.3.6.1.4.1.2011.6.122.20.2.2.25
-- 1.3.6.1.4.1.2011.6.122.20.2.2.25
-- 1.3.6.1.4.1.2011.6.122.20.2.2.25
-- 1.3.6.1.4.1.2011.6.122.20.2.2.25
		-- 1.3.6.1.4.1.2011.6.122.20.2.2.25
		hwSpsFragmentNotEnoughTrap NOTIFICATION-TYPE
			OBJECTS { hwSpsFragmentSpsLocation }
			STATUS current
			DESCRIPTION
				"The fragment buffer of SPS is not enough."
			::= { hwServiceBasicTrap 25 }


--         1.3.6.1.4.1.2011.6.122.20.2.2.26
-- 1.3.6.1.4.1.2011.6.122.20.2.2.26
-- 1.3.6.1.4.1.2011.6.122.20.2.2.26
-- 1.3.6.1.4.1.2011.6.122.20.2.2.26
-- 1.3.6.1.4.1.2011.6.122.20.2.2.26
-- 1.3.6.1.4.1.2011.6.122.20.2.2.26
-- 1.3.6.1.4.1.2011.6.122.20.2.2.26
-- 1.3.6.1.4.1.2011.6.122.20.2.2.26
		-- 1.3.6.1.4.1.2011.6.122.20.2.2.26
		hwSpsFragmentEnoughTrap NOTIFICATION-TYPE
			OBJECTS { hwSpsFragmentSpsLocation }
			STATUS current
			DESCRIPTION
				"The SPS fragment cache becomes sufficient."
			::= { hwServiceBasicTrap 26 }


--         1.3.6.1.4.1.2011.6.122.20.2.2.27
-- 1.3.6.1.4.1.2011.6.122.20.2.2.27
-- 1.3.6.1.4.1.2011.6.122.20.2.2.27
-- 1.3.6.1.4.1.2011.6.122.20.2.2.27
-- 1.3.6.1.4.1.2011.6.122.20.2.2.27
-- 1.3.6.1.4.1.2011.6.122.20.2.2.27
-- 1.3.6.1.4.1.2011.6.122.20.2.2.27
-- 1.3.6.1.4.1.2011.6.122.20.2.2.27
		-- 1.3.6.1.4.1.2011.6.122.20.2.2.27
		hwSasRpdAccountMessageAbnormalTrap NOTIFICATION-TYPE
			OBJECTS { hwSasRpdAccountMessageLocation, hwSasRpdAccountMessageRpdIP }
			STATUS current
			DESCRIPTION
				"The account messages between an SAS and an RPD are not properly exchanged.
Cause 1: The SAS and RPD interconnection fails.
Cause 2: The RPD status is abnormal."
			::= { hwServiceBasicTrap 27 }


--         1.3.6.1.4.1.2011.6.122.20.2.2.28
-- 1.3.6.1.4.1.2011.6.122.20.2.2.28
-- 1.3.6.1.4.1.2011.6.122.20.2.2.28
-- 1.3.6.1.4.1.2011.6.122.20.2.2.28
-- 1.3.6.1.4.1.2011.6.122.20.2.2.28
-- 1.3.6.1.4.1.2011.6.122.20.2.2.28
-- 1.3.6.1.4.1.2011.6.122.20.2.2.28
-- 1.3.6.1.4.1.2011.6.122.20.2.2.28
		-- 1.3.6.1.4.1.2011.6.122.20.2.2.28
		hwSasRpdAccountMessageNormalTrap NOTIFICATION-TYPE
			OBJECTS { hwSasRpdAccountMessageLocation, hwSasRpdAccountMessageRpdIP }
			STATUS current
			DESCRIPTION
				"The account messages between an SAS and an RPD are properly exchanged."
			::= { hwServiceBasicTrap 28 }


--         1.3.6.1.4.1.2011.6.122.20.2.2.29
-- 1.3.6.1.4.1.2011.6.122.20.2.2.29
-- 1.3.6.1.4.1.2011.6.122.20.2.2.29
-- 1.3.6.1.4.1.2011.6.122.20.2.2.29
-- 1.3.6.1.4.1.2011.6.122.20.2.2.29
-- 1.3.6.1.4.1.2011.6.122.20.2.2.29
-- 1.3.6.1.4.1.2011.6.122.20.2.2.29
-- 1.3.6.1.4.1.2011.6.122.20.2.2.29
		-- 1.3.6.1.4.1.2011.6.122.20.2.2.29
		hwNPLUS1HBKEnableSpuNeedResetTrap NOTIFICATION-TYPE
			OBJECTS { hwSpuSysInfoLocation, hwNPLUS1BackupGroupID }
			STATUS current
			DESCRIPTION
				"Description."
			::= { hwServiceBasicTrap 29 }


--         1.3.6.1.4.1.2011.6.122.20.2.2.30
-- 1.3.6.1.4.1.2011.6.122.20.2.2.30
-- 1.3.6.1.4.1.2011.6.122.20.2.2.30
-- 1.3.6.1.4.1.2011.6.122.20.2.2.30
-- 1.3.6.1.4.1.2011.6.122.20.2.2.30
-- 1.3.6.1.4.1.2011.6.122.20.2.2.30
-- 1.3.6.1.4.1.2011.6.122.20.2.2.30
-- 1.3.6.1.4.1.2011.6.122.20.2.2.30
		-- 1.3.6.1.4.1.2011.6.122.20.2.2.30
		hwNPLUS1HBKEnableSpuResetRecoverTrap NOTIFICATION-TYPE
			OBJECTS { hwSpuSysInfoLocation }
			STATUS current
			DESCRIPTION
				"Description."
			::= { hwServiceBasicTrap 30 }


--         1.3.6.1.4.1.2011.6.122.20.2.2.31
-- 1.3.6.1.4.1.2011.6.122.20.2.2.31
-- 1.3.6.1.4.1.2011.6.122.20.2.2.31
-- 1.3.6.1.4.1.2011.6.122.20.2.2.31
-- 1.3.6.1.4.1.2011.6.122.20.2.2.31
-- 1.3.6.1.4.1.2011.6.122.20.2.2.31
-- 1.3.6.1.4.1.2011.6.122.20.2.2.31
-- 1.3.6.1.4.1.2011.6.122.20.2.2.31
		-- 1.3.6.1.4.1.2011.6.122.20.2.2.31
		hwNPLUS1HBKDisableSpuNeedResetTrap NOTIFICATION-TYPE
			OBJECTS { hwSpuSysInfoLocation }
			STATUS current
			DESCRIPTION
				"Description."
			::= { hwServiceBasicTrap 31 }


--         1.3.6.1.4.1.2011.6.122.20.2.2.32
-- 1.3.6.1.4.1.2011.6.122.20.2.2.32
-- 1.3.6.1.4.1.2011.6.122.20.2.2.32
-- 1.3.6.1.4.1.2011.6.122.20.2.2.32
-- 1.3.6.1.4.1.2011.6.122.20.2.2.32
-- 1.3.6.1.4.1.2011.6.122.20.2.2.32
-- 1.3.6.1.4.1.2011.6.122.20.2.2.32
-- 1.3.6.1.4.1.2011.6.122.20.2.2.32
		-- 1.3.6.1.4.1.2011.6.122.20.2.2.32
		hwNPLUS1HBKDisableSpuResetRecoverTrap NOTIFICATION-TYPE
			OBJECTS { hwSpuSysInfoLocation }
			STATUS current
			DESCRIPTION
				"Description."
			::= { hwServiceBasicTrap 32 }


--         1.3.6.1.4.1.2011.6.122.20.2.2.33
-- 1.3.6.1.4.1.2011.6.122.20.2.2.33
-- 1.3.6.1.4.1.2011.6.122.20.2.2.33
-- 1.3.6.1.4.1.2011.6.122.20.2.2.33
-- 1.3.6.1.4.1.2011.6.122.20.2.2.33
-- 1.3.6.1.4.1.2011.6.122.20.2.2.33
-- 1.3.6.1.4.1.2011.6.122.20.2.2.33
-- 1.3.6.1.4.1.2011.6.122.20.2.2.33
		-- 1.3.6.1.4.1.2011.6.122.20.2.2.33
		hwNPLUS1HBKCpuStandbyTrap NOTIFICATION-TYPE
			OBJECTS { hwSpuSysInfoLocation, hwNPLUS1BackupGroupID }
			STATUS current
			DESCRIPTION
				"Description."
			::= { hwServiceBasicTrap 33 }


--         1.3.6.1.4.1.2011.6.122.20.2.2.34
-- 1.3.6.1.4.1.2011.6.122.20.2.2.34
-- 1.3.6.1.4.1.2011.6.122.20.2.2.34
-- 1.3.6.1.4.1.2011.6.122.20.2.2.34
-- 1.3.6.1.4.1.2011.6.122.20.2.2.34
-- 1.3.6.1.4.1.2011.6.122.20.2.2.34
-- 1.3.6.1.4.1.2011.6.122.20.2.2.34
-- 1.3.6.1.4.1.2011.6.122.20.2.2.34
		-- 1.3.6.1.4.1.2011.6.122.20.2.2.34
		hwNPLUS1HBKCpuStanbyRecoverTrap NOTIFICATION-TYPE
			OBJECTS { hwSpuSysInfoLocation }
			STATUS current
			DESCRIPTION
				"Description."
			::= { hwServiceBasicTrap 34 }


--   1.3.6.1.4.1.2011.6.122.20.2.2.35
-- 1.3.6.1.4.1.2011.6.122.20.2.2.35
		-- 1.3.6.1.4.1.2011.6.122.20.2.2.35
		hwPlsCompLinkConnectDownTrap NOTIFICATION-TYPE
			OBJECTS { hwSpuSysInfoLocation, hwSpuSysInfoType, hwSpuSysInfoIPAddress, hwComponentNumber, hwSpuCompLinkCurrentDestIP,
				hwSpuCompLinkCurrentDestPort, hwSpuCompLinkComponentType }
			STATUS current
			DESCRIPTION
				"The connection between the SAS and PLS fails."
			::= { hwServiceBasicTrap 35 }


--   1.3.6.1.4.1.2011.6.122.20.2.2.36
-- 1.3.6.1.4.1.2011.6.122.20.2.2.36
		-- 1.3.6.1.4.1.2011.6.122.20.2.2.36
		hwPlsCompLinkConnectUpTrap NOTIFICATION-TYPE
			OBJECTS { hwSpuSysInfoLocation, hwSpuSysInfoType, hwSpuSysInfoIPAddress, hwComponentNumber, hwSpuCompLinkCurrentDestIP,
				hwSpuCompLinkCurrentDestPort, hwSpuCompLinkComponentType }
			STATUS current
			DESCRIPTION
				"The connection between the SAS and PLS becomes normal."
			::= { hwServiceBasicTrap 36 }


--     1.3.6.1.4.1.2011.6.122.20.2.2.36
-- 1.3.6.1.4.1.2011.6.122.20.2.2.37
-- 1.3.6.1.4.1.2011.6.122.20.2.2.37
-- 1.3.6.1.4.1.2011.6.122.20.2.2.37
		-- 1.3.6.1.4.1.2011.6.122.20.2.2.37
		hwAverageCpuUsageThresholdTrap NOTIFICATION-TYPE
			OBJECTS { hwSpsEntityLocation, hwSpsAverageCpuUsage, hwSpsAverageCpuUsageThreshold }
			STATUS current
			DESCRIPTION
				"This object indicates that the CPU usage of the SPS was overloaded."
			::= { hwServiceBasicTrap 37 }


--    1.3.6.1.4.1.2011.6.122.20.2.2.38
-- 1.3.6.1.4.1.2011.6.122.20.2.2.38
-- 1.3.6.1.4.1.2011.6.122.20.2.2.38
		-- 1.3.6.1.4.1.2011.6.122.20.2.2.38
		hwAverageCpuUsageThresholdRestoreTrap NOTIFICATION-TYPE
			OBJECTS { hwSpsEntityLocation, hwSpsAverageCpuUsage, hwSpsAverageCpuUsageThreshold }
			STATUS current
			DESCRIPTION
				"This object indicates that the CPU usage of the SPS restores to normal."
			::= { hwServiceBasicTrap 38 }


--     1.3.6.1.4.1.2011.6.122.20.2.2.37
-- 1.3.6.1.4.1.2011.6.122.20.2.2.39
-- 1.3.6.1.4.1.2011.6.122.20.2.2.39
-- 1.3.6.1.4.1.2011.6.122.20.2.2.39
		-- 1.3.6.1.4.1.2011.6.122.20.2.2.39
		hwForwardingQueueOverloadTrap NOTIFICATION-TYPE
			OBJECTS { hwSpsEntityLocation, hwSpsQueueUsage, hwSpsOverloadThreshold }
			STATUS current
			DESCRIPTION
				"This object indicates that forwarding queue of SPS overloads in the past one minute."
			::= { hwServiceBasicTrap 39 }


--    1.3.6.1.4.1.2011.6.122.20.2.2.40
-- 1.3.6.1.4.1.2011.6.122.20.2.2.40
-- 1.3.6.1.4.1.2011.6.122.20.2.2.40
		-- 1.3.6.1.4.1.2011.6.122.20.2.2.40
		hwForwardingQueueRestoreTrap NOTIFICATION-TYPE
			OBJECTS { hwSpsEntityLocation, hwSpsQueueUsage, hwSpsOverloadThreshold }
			STATUS current
			DESCRIPTION
				"This object indicates that forwarding queue of SPS restores to normal."
			::= { hwServiceBasicTrap 40 }


--     1.3.6.1.4.1.2011.6.122.20.2.2.41
-- 1.3.6.1.4.1.2011.6.122.20.2.2.41
-- 1.3.6.1.4.1.2011.6.122.20.2.2.41
-- 1.3.6.1.4.1.2011.6.122.20.2.2.41
		-- 1.3.6.1.4.1.2011.6.122.20.2.2.41
		hwSpsLeastNumberBelowTrap NOTIFICATION-TYPE
			OBJECTS { hwSpsLeastNumberCfg }
			STATUS current
			DESCRIPTION
				"This object indicates that the active SPS is below the least number of SPS."
			::= { hwServiceBasicTrap 41 }


--    1.3.6.1.4.1.2011.6.122.20.2.2.42
-- 1.3.6.1.4.1.2011.6.122.20.2.2.42
-- 1.3.6.1.4.1.2011.6.122.20.2.2.42
		-- 1.3.6.1.4.1.2011.6.122.20.2.2.42
		hwSpsLeastNumberEqualTrap NOTIFICATION-TYPE
			OBJECTS { hwSpsLeastNumberCfg }
			STATUS current
			DESCRIPTION
				"This object indicates that the active SPS is equal with the least number of SPS."
			::= { hwServiceBasicTrap 42 }


--         1.3.6.1.4.1.2011.6.122.20.2.3
-- 1.3.6.1.4.1.2011.6.122.20.2.3
-- 1.3.6.1.4.1.2011.6.122.20.2.3
-- 1.3.6.1.4.1.2011.6.122.20.2.3
-- 1.3.6.1.4.1.2011.6.122.20.2.3
-- 1.3.6.1.4.1.2011.6.122.20.2.3
-- 1.3.6.1.4.1.2011.6.122.20.2.3
-- 1.3.6.1.4.1.2011.6.122.20.2.3
		-- 1.3.6.1.4.1.2011.6.122.20.2.3
		hwServiceWirelessObject OBJECT IDENTIFIER ::= { hwServiceObject 3 }


--         1.3.6.1.4.1.2011.6.122.20.2.3.1
-- 1.3.6.1.4.1.2011.6.122.20.2.3.1
-- 1.3.6.1.4.1.2011.6.122.20.2.3.1
-- 1.3.6.1.4.1.2011.6.122.20.2.3.1
-- 1.3.6.1.4.1.2011.6.122.20.2.3.1
-- 1.3.6.1.4.1.2011.6.122.20.2.3.1
-- 1.3.6.1.4.1.2011.6.122.20.2.3.1
-- 1.3.6.1.4.1.2011.6.122.20.2.3.1
		-- 1.3.6.1.4.1.2011.6.122.20.2.3.1
		hwCGInfoTable OBJECT-TYPE
			SYNTAX SEQUENCE OF HwCGInfoEntry
			MAX-ACCESS not-accessible
			STATUS current
			DESCRIPTION
				"Description."
			::= { hwServiceWirelessObject 1 }


--         1.3.6.1.4.1.2011.6.122.20.2.3.1.1
-- 1.3.6.1.4.1.2011.6.122.20.2.3.1.1
-- 1.3.6.1.4.1.2011.6.122.20.2.3.1.1
-- 1.3.6.1.4.1.2011.6.122.20.2.3.1.1
-- 1.3.6.1.4.1.2011.6.122.20.2.3.1.1
-- 1.3.6.1.4.1.2011.6.122.20.2.3.1.1
-- 1.3.6.1.4.1.2011.6.122.20.2.3.1.1
-- 1.3.6.1.4.1.2011.6.122.20.2.3.1.1
		-- 1.3.6.1.4.1.2011.6.122.20.2.3.1.1
		hwCGInfoEntry OBJECT-TYPE
			SYNTAX HwCGInfoEntry
			MAX-ACCESS not-accessible
			STATUS current
			DESCRIPTION
				"Description."
			INDEX { hwCGInfoIndex }
			::= { hwCGInfoTable 1 }


		HwCGInfoEntry ::=
			SEQUENCE {
				hwCGInfoIndex
					Gauge32,
				hwSASLocationConnectCG
					OCTET STRING,
				hwCGIPAddress
					IpAddress,
				hwCGPort
					Gauge32,
				hwCGGrade
					Gauge32,
				hwCGCdrCachePoolUsed
					Gauge32
			 }

--         1.3.6.1.4.1.2011.6.122.20.2.3.1.1.1
-- 1.3.6.1.4.1.2011.6.122.20.2.3.1.1.1
-- 1.3.6.1.4.1.2011.6.122.20.2.3.1.1.1
-- 1.3.6.1.4.1.2011.6.122.20.2.3.1.1.1
-- 1.3.6.1.4.1.2011.6.122.20.2.3.1.1.1
-- 1.3.6.1.4.1.2011.6.122.20.2.3.1.1.1
-- 1.3.6.1.4.1.2011.6.122.20.2.3.1.1.1
-- 1.3.6.1.4.1.2011.6.122.20.2.3.1.1.1
		-- 1.3.6.1.4.1.2011.6.122.20.2.3.1.1.1
		hwCGInfoIndex OBJECT-TYPE
			SYNTAX Gauge32 (1..2147483647)
			MAX-ACCESS not-accessible
			STATUS current
			DESCRIPTION
				"Description."
			::= { hwCGInfoEntry 1 }


--         1.3.6.1.4.1.2011.6.122.20.2.3.1.1.2
-- 1.3.6.1.4.1.2011.6.122.20.2.3.1.1.2
-- 1.3.6.1.4.1.2011.6.122.20.2.3.1.1.2
-- 1.3.6.1.4.1.2011.6.122.20.2.3.1.1.2
-- 1.3.6.1.4.1.2011.6.122.20.2.3.1.1.2
-- 1.3.6.1.4.1.2011.6.122.20.2.3.1.1.2
-- 1.3.6.1.4.1.2011.6.122.20.2.3.1.1.2
-- 1.3.6.1.4.1.2011.6.122.20.2.3.1.1.2
		-- 1.3.6.1.4.1.2011.6.122.20.2.3.1.1.2
		hwSASLocationConnectCG OBJECT-TYPE
			SYNTAX OCTET STRING (SIZE (0..255))
			MAX-ACCESS read-write
			STATUS current
			DESCRIPTION
				"Description."
			::= { hwCGInfoEntry 2 }


--         1.3.6.1.4.1.2011.6.122.20.2.3.1.1.3
-- 1.3.6.1.4.1.2011.6.122.20.2.3.1.1.3
-- 1.3.6.1.4.1.2011.6.122.20.2.3.1.1.3
-- 1.3.6.1.4.1.2011.6.122.20.2.3.1.1.3
-- 1.3.6.1.4.1.2011.6.122.20.2.3.1.1.3
-- 1.3.6.1.4.1.2011.6.122.20.2.3.1.1.3
-- 1.3.6.1.4.1.2011.6.122.20.2.3.1.1.3
-- 1.3.6.1.4.1.2011.6.122.20.2.3.1.1.3
		-- 1.3.6.1.4.1.2011.6.122.20.2.3.1.1.3
		hwCGIPAddress OBJECT-TYPE
			SYNTAX IpAddress
			MAX-ACCESS read-write
			STATUS current
			DESCRIPTION
				"Description."
			::= { hwCGInfoEntry 3 }


--         1.3.6.1.4.1.2011.6.122.20.2.3.1.1.4
-- 1.3.6.1.4.1.2011.6.122.20.2.3.1.1.4
-- 1.3.6.1.4.1.2011.6.122.20.2.3.1.1.4
-- 1.3.6.1.4.1.2011.6.122.20.2.3.1.1.4
-- 1.3.6.1.4.1.2011.6.122.20.2.3.1.1.4
-- 1.3.6.1.4.1.2011.6.122.20.2.3.1.1.4
-- 1.3.6.1.4.1.2011.6.122.20.2.3.1.1.4
-- 1.3.6.1.4.1.2011.6.122.20.2.3.1.1.4
		-- 1.3.6.1.4.1.2011.6.122.20.2.3.1.1.4
		hwCGPort OBJECT-TYPE
			SYNTAX Gauge32 (1..65535)
			MAX-ACCESS read-write
			STATUS current
			DESCRIPTION
				"Description."
			::= { hwCGInfoEntry 4 }


--         1.3.6.1.4.1.2011.6.122.20.2.3.1.1.5
-- 1.3.6.1.4.1.2011.6.122.20.2.3.1.1.5
-- 1.3.6.1.4.1.2011.6.122.20.2.3.1.1.5
-- 1.3.6.1.4.1.2011.6.122.20.2.3.1.1.5
-- 1.3.6.1.4.1.2011.6.122.20.2.3.1.1.5
-- 1.3.6.1.4.1.2011.6.122.20.2.3.1.1.5
-- 1.3.6.1.4.1.2011.6.122.20.2.3.1.1.5
-- 1.3.6.1.4.1.2011.6.122.20.2.3.1.1.5
		-- 1.3.6.1.4.1.2011.6.122.20.2.3.1.1.5
		hwCGGrade OBJECT-TYPE
			SYNTAX Gauge32 (1..10)
			MAX-ACCESS read-write
			STATUS current
			DESCRIPTION
				"Description."
			::= { hwCGInfoEntry 5 }


--         1.3.6.1.4.1.2011.6.122.20.2.3.1.1.6
-- 1.3.6.1.4.1.2011.6.122.20.2.3.1.1.6
-- 1.3.6.1.4.1.2011.6.122.20.2.3.1.1.6
-- 1.3.6.1.4.1.2011.6.122.20.2.3.1.1.6
-- 1.3.6.1.4.1.2011.6.122.20.2.3.1.1.6
-- 1.3.6.1.4.1.2011.6.122.20.2.3.1.1.6
-- 1.3.6.1.4.1.2011.6.122.20.2.3.1.1.6
-- 1.3.6.1.4.1.2011.6.122.20.2.3.1.1.6
		-- 1.3.6.1.4.1.2011.6.122.20.2.3.1.1.6
		hwCGCdrCachePoolUsed OBJECT-TYPE
			SYNTAX Gauge32 (0..100)
			MAX-ACCESS read-write
			STATUS current
			DESCRIPTION
				"Description."
			::= { hwCGInfoEntry 6 }


--         1.3.6.1.4.1.2011.6.122.20.2.3.2
-- 1.3.6.1.4.1.2011.6.122.20.2.3.2
-- 1.3.6.1.4.1.2011.6.122.20.2.3.2
-- 1.3.6.1.4.1.2011.6.122.20.2.3.2
-- 1.3.6.1.4.1.2011.6.122.20.2.3.2
-- 1.3.6.1.4.1.2011.6.122.20.2.3.2
-- 1.3.6.1.4.1.2011.6.122.20.2.3.2
-- 1.3.6.1.4.1.2011.6.122.20.2.3.2
		-- 1.3.6.1.4.1.2011.6.122.20.2.3.2
		hwPCRFInfoTable OBJECT-TYPE
			SYNTAX SEQUENCE OF HwPCRFInfoEntry
			MAX-ACCESS not-accessible
			STATUS current
			DESCRIPTION
				"Description."
			::= { hwServiceWirelessObject 2 }


--         1.3.6.1.4.1.2011.6.122.20.2.3.2.1
-- 1.3.6.1.4.1.2011.6.122.20.2.3.2.1
-- 1.3.6.1.4.1.2011.6.122.20.2.3.2.1
-- 1.3.6.1.4.1.2011.6.122.20.2.3.2.1
-- 1.3.6.1.4.1.2011.6.122.20.2.3.2.1
-- 1.3.6.1.4.1.2011.6.122.20.2.3.2.1
-- 1.3.6.1.4.1.2011.6.122.20.2.3.2.1
-- 1.3.6.1.4.1.2011.6.122.20.2.3.2.1
		-- 1.3.6.1.4.1.2011.6.122.20.2.3.2.1
		hwPCRFInfoEntry OBJECT-TYPE
			SYNTAX HwPCRFInfoEntry
			MAX-ACCESS not-accessible
			STATUS current
			DESCRIPTION
				"Description."
			INDEX { hwPCRFInfoIndex }
			::= { hwPCRFInfoTable 1 }


		HwPCRFInfoEntry ::=
			SEQUENCE {
				hwPCRFInfoIndex
					Gauge32,
				hwSASLocationConnectPCRF
					OCTET STRING,
				hwPCRFHostName
					OCTET STRING,
				hwPCRFIPAddress
					IpAddress,
				hwPCRFPort
					Gauge32,
				hwSASNameConnectPCRF
					OCTET STRING,
				hwSASIPAddressConnectPCRF
					IpAddress,
				hwSASPortConnectPCRF
					Gauge32
			 }

--         1.3.6.1.4.1.2011.6.122.20.2.3.2.1.1
-- 1.3.6.1.4.1.2011.6.122.20.2.3.2.1.1
-- 1.3.6.1.4.1.2011.6.122.20.2.3.2.1.1
-- 1.3.6.1.4.1.2011.6.122.20.2.3.2.1.1
-- 1.3.6.1.4.1.2011.6.122.20.2.3.2.1.1
-- 1.3.6.1.4.1.2011.6.122.20.2.3.2.1.1
-- 1.3.6.1.4.1.2011.6.122.20.2.3.2.1.1
-- 1.3.6.1.4.1.2011.6.122.20.2.3.2.1.1
		-- 1.3.6.1.4.1.2011.6.122.20.2.3.2.1.1
		hwPCRFInfoIndex OBJECT-TYPE
			SYNTAX Gauge32 (1..2147483647)
			MAX-ACCESS not-accessible
			STATUS current
			DESCRIPTION
				"Description."
			::= { hwPCRFInfoEntry 1 }


--         1.3.6.1.4.1.2011.6.122.20.2.3.2.1.2
-- 1.3.6.1.4.1.2011.6.122.20.2.3.2.1.2
-- 1.3.6.1.4.1.2011.6.122.20.2.3.2.1.2
-- 1.3.6.1.4.1.2011.6.122.20.2.3.2.1.2
-- 1.3.6.1.4.1.2011.6.122.20.2.3.2.1.2
-- 1.3.6.1.4.1.2011.6.122.20.2.3.2.1.2
-- 1.3.6.1.4.1.2011.6.122.20.2.3.2.1.2
-- 1.3.6.1.4.1.2011.6.122.20.2.3.2.1.2
		-- 1.3.6.1.4.1.2011.6.122.20.2.3.2.1.2
		hwSASLocationConnectPCRF OBJECT-TYPE
			SYNTAX OCTET STRING (SIZE (0..255))
			MAX-ACCESS read-write
			STATUS current
			DESCRIPTION
				"Description."
			::= { hwPCRFInfoEntry 2 }


--         1.3.6.1.4.1.2011.6.122.20.2.3.2.1.3
-- 1.3.6.1.4.1.2011.6.122.20.2.3.2.1.3
-- 1.3.6.1.4.1.2011.6.122.20.2.3.2.1.3
-- 1.3.6.1.4.1.2011.6.122.20.2.3.2.1.3
-- 1.3.6.1.4.1.2011.6.122.20.2.3.2.1.3
-- 1.3.6.1.4.1.2011.6.122.20.2.3.2.1.3
-- 1.3.6.1.4.1.2011.6.122.20.2.3.2.1.3
-- 1.3.6.1.4.1.2011.6.122.20.2.3.2.1.3
		-- 1.3.6.1.4.1.2011.6.122.20.2.3.2.1.3
		hwPCRFHostName OBJECT-TYPE
			SYNTAX OCTET STRING
			MAX-ACCESS read-write
			STATUS current
			DESCRIPTION
				"Description."
			::= { hwPCRFInfoEntry 3 }


--         1.3.6.1.4.1.2011.6.122.20.2.3.2.1.4
-- 1.3.6.1.4.1.2011.6.122.20.2.3.2.1.4
-- 1.3.6.1.4.1.2011.6.122.20.2.3.2.1.4
-- 1.3.6.1.4.1.2011.6.122.20.2.3.2.1.4
-- 1.3.6.1.4.1.2011.6.122.20.2.3.2.1.4
-- 1.3.6.1.4.1.2011.6.122.20.2.3.2.1.4
-- 1.3.6.1.4.1.2011.6.122.20.2.3.2.1.4
-- 1.3.6.1.4.1.2011.6.122.20.2.3.2.1.4
		-- 1.3.6.1.4.1.2011.6.122.20.2.3.2.1.4
		hwPCRFIPAddress OBJECT-TYPE
			SYNTAX IpAddress
			MAX-ACCESS read-write
			STATUS current
			DESCRIPTION
				"Description."
			::= { hwPCRFInfoEntry 4 }


--         1.3.6.1.4.1.2011.6.122.20.2.3.2.1.5
-- 1.3.6.1.4.1.2011.6.122.20.2.3.2.1.5
-- 1.3.6.1.4.1.2011.6.122.20.2.3.2.1.5
-- 1.3.6.1.4.1.2011.6.122.20.2.3.2.1.5
-- 1.3.6.1.4.1.2011.6.122.20.2.3.2.1.5
-- 1.3.6.1.4.1.2011.6.122.20.2.3.2.1.5
-- 1.3.6.1.4.1.2011.6.122.20.2.3.2.1.5
-- 1.3.6.1.4.1.2011.6.122.20.2.3.2.1.5
		-- 1.3.6.1.4.1.2011.6.122.20.2.3.2.1.5
		hwPCRFPort OBJECT-TYPE
			SYNTAX Gauge32 (1..65535)
			MAX-ACCESS read-write
			STATUS current
			DESCRIPTION
				"Description."
			::= { hwPCRFInfoEntry 5 }


--         1.3.6.1.4.1.2011.6.122.20.2.3.2.1.6
-- 1.3.6.1.4.1.2011.6.122.20.2.3.2.1.6
-- 1.3.6.1.4.1.2011.6.122.20.2.3.2.1.6
-- 1.3.6.1.4.1.2011.6.122.20.2.3.2.1.6
-- 1.3.6.1.4.1.2011.6.122.20.2.3.2.1.6
-- 1.3.6.1.4.1.2011.6.122.20.2.3.2.1.6
-- 1.3.6.1.4.1.2011.6.122.20.2.3.2.1.6
-- 1.3.6.1.4.1.2011.6.122.20.2.3.2.1.6
		-- 1.3.6.1.4.1.2011.6.122.20.2.3.2.1.6
		hwSASNameConnectPCRF OBJECT-TYPE
			SYNTAX OCTET STRING (SIZE (0..255))
			MAX-ACCESS read-write
			STATUS current
			DESCRIPTION
				"Description."
			::= { hwPCRFInfoEntry 6 }


--         1.3.6.1.4.1.2011.6.122.20.2.3.2.1.7
-- 1.3.6.1.4.1.2011.6.122.20.2.3.2.1.7
-- 1.3.6.1.4.1.2011.6.122.20.2.3.2.1.7
-- 1.3.6.1.4.1.2011.6.122.20.2.3.2.1.7
-- 1.3.6.1.4.1.2011.6.122.20.2.3.2.1.7
-- 1.3.6.1.4.1.2011.6.122.20.2.3.2.1.7
-- 1.3.6.1.4.1.2011.6.122.20.2.3.2.1.7
-- 1.3.6.1.4.1.2011.6.122.20.2.3.2.1.7
		-- 1.3.6.1.4.1.2011.6.122.20.2.3.2.1.7
		hwSASIPAddressConnectPCRF OBJECT-TYPE
			SYNTAX IpAddress
			MAX-ACCESS read-write
			STATUS current
			DESCRIPTION
				"Description."
			::= { hwPCRFInfoEntry 7 }


--         1.3.6.1.4.1.2011.6.122.20.2.3.2.1.8
-- 1.3.6.1.4.1.2011.6.122.20.2.3.2.1.8
-- 1.3.6.1.4.1.2011.6.122.20.2.3.2.1.8
-- 1.3.6.1.4.1.2011.6.122.20.2.3.2.1.8
-- 1.3.6.1.4.1.2011.6.122.20.2.3.2.1.8
-- 1.3.6.1.4.1.2011.6.122.20.2.3.2.1.8
-- 1.3.6.1.4.1.2011.6.122.20.2.3.2.1.8
-- 1.3.6.1.4.1.2011.6.122.20.2.3.2.1.8
		-- 1.3.6.1.4.1.2011.6.122.20.2.3.2.1.8
		hwSASPortConnectPCRF OBJECT-TYPE
			SYNTAX Gauge32 (1..65535)
			MAX-ACCESS read-write
			STATUS current
			DESCRIPTION
				"Description."
			::= { hwPCRFInfoEntry 8 }


--         1.3.6.1.4.1.2011.6.122.20.2.3.3
-- 1.3.6.1.4.1.2011.6.122.20.2.3.3
-- 1.3.6.1.4.1.2011.6.122.20.2.3.3
-- 1.3.6.1.4.1.2011.6.122.20.2.3.3
-- 1.3.6.1.4.1.2011.6.122.20.2.3.3
-- 1.3.6.1.4.1.2011.6.122.20.2.3.3
-- 1.3.6.1.4.1.2011.6.122.20.2.3.3
-- 1.3.6.1.4.1.2011.6.122.20.2.3.3
		-- 1.3.6.1.4.1.2011.6.122.20.2.3.3
		hwOCSInfoTable OBJECT-TYPE
			SYNTAX SEQUENCE OF HwOCSInfoEntry
			MAX-ACCESS not-accessible
			STATUS current
			DESCRIPTION
				"Description."
			::= { hwServiceWirelessObject 3 }


--         1.3.6.1.4.1.2011.6.122.20.2.3.3.1
-- 1.3.6.1.4.1.2011.6.122.20.2.3.3.1
-- 1.3.6.1.4.1.2011.6.122.20.2.3.3.1
-- 1.3.6.1.4.1.2011.6.122.20.2.3.3.1
-- 1.3.6.1.4.1.2011.6.122.20.2.3.3.1
-- 1.3.6.1.4.1.2011.6.122.20.2.3.3.1
-- 1.3.6.1.4.1.2011.6.122.20.2.3.3.1
-- 1.3.6.1.4.1.2011.6.122.20.2.3.3.1
		-- 1.3.6.1.4.1.2011.6.122.20.2.3.3.1
		hwOCSInfoEntry OBJECT-TYPE
			SYNTAX HwOCSInfoEntry
			MAX-ACCESS not-accessible
			STATUS current
			DESCRIPTION
				"Description."
			INDEX { hwOCSInfoIndex }
			::= { hwOCSInfoTable 1 }


		HwOCSInfoEntry ::=
			SEQUENCE {
				hwOCSInfoIndex
					Gauge32,
				hwSASLocationConnectOCS
					OCTET STRING,
				hwOCSHostName
					OCTET STRING,
				hwOCSIPAddress
					IpAddress,
				hwOCSPort
					Gauge32,
				hwSASNameConnectOCS
					OCTET STRING,
				hwSASIPAddressConnectOCS
					IpAddress,
				hwSASPortConnectOCS
					Gauge32
			 }

--         1.3.6.1.4.1.2011.6.122.20.2.3.3.1.1
-- 1.3.6.1.4.1.2011.6.122.20.2.3.3.1.1
-- 1.3.6.1.4.1.2011.6.122.20.2.3.3.1.1
-- 1.3.6.1.4.1.2011.6.122.20.2.3.3.1.1
-- 1.3.6.1.4.1.2011.6.122.20.2.3.3.1.1
-- 1.3.6.1.4.1.2011.6.122.20.2.3.3.1.1
-- 1.3.6.1.4.1.2011.6.122.20.2.3.3.1.1
-- 1.3.6.1.4.1.2011.6.122.20.2.3.3.1.1
		-- 1.3.6.1.4.1.2011.6.122.20.2.3.3.1.1
		hwOCSInfoIndex OBJECT-TYPE
			SYNTAX Gauge32 (1..2147483647)
			MAX-ACCESS not-accessible
			STATUS current
			DESCRIPTION
				"Description."
			::= { hwOCSInfoEntry 1 }


--         1.3.6.1.4.1.2011.6.122.20.2.3.3.1.2
-- 1.3.6.1.4.1.2011.6.122.20.2.3.3.1.2
-- 1.3.6.1.4.1.2011.6.122.20.2.3.3.1.2
-- 1.3.6.1.4.1.2011.6.122.20.2.3.3.1.2
-- 1.3.6.1.4.1.2011.6.122.20.2.3.3.1.2
-- 1.3.6.1.4.1.2011.6.122.20.2.3.3.1.2
-- 1.3.6.1.4.1.2011.6.122.20.2.3.3.1.2
-- 1.3.6.1.4.1.2011.6.122.20.2.3.3.1.2
		-- 1.3.6.1.4.1.2011.6.122.20.2.3.3.1.2
		hwSASLocationConnectOCS OBJECT-TYPE
			SYNTAX OCTET STRING (SIZE (0..255))
			MAX-ACCESS read-write
			STATUS current
			DESCRIPTION
				"Description."
			::= { hwOCSInfoEntry 2 }


--         1.3.6.1.4.1.2011.6.122.20.2.3.3.1.3
-- 1.3.6.1.4.1.2011.6.122.20.2.3.3.1.3
-- 1.3.6.1.4.1.2011.6.122.20.2.3.3.1.3
-- 1.3.6.1.4.1.2011.6.122.20.2.3.3.1.3
-- 1.3.6.1.4.1.2011.6.122.20.2.3.3.1.3
-- 1.3.6.1.4.1.2011.6.122.20.2.3.3.1.3
-- 1.3.6.1.4.1.2011.6.122.20.2.3.3.1.3
-- 1.3.6.1.4.1.2011.6.122.20.2.3.3.1.3
		-- 1.3.6.1.4.1.2011.6.122.20.2.3.3.1.3
		hwOCSHostName OBJECT-TYPE
			SYNTAX OCTET STRING (SIZE (0..255))
			MAX-ACCESS read-write
			STATUS current
			DESCRIPTION
				"Description."
			::= { hwOCSInfoEntry 3 }


--         1.3.6.1.4.1.2011.6.122.20.2.3.3.1.4
-- 1.3.6.1.4.1.2011.6.122.20.2.3.3.1.4
-- 1.3.6.1.4.1.2011.6.122.20.2.3.3.1.4
-- 1.3.6.1.4.1.2011.6.122.20.2.3.3.1.4
-- 1.3.6.1.4.1.2011.6.122.20.2.3.3.1.4
-- 1.3.6.1.4.1.2011.6.122.20.2.3.3.1.4
-- 1.3.6.1.4.1.2011.6.122.20.2.3.3.1.4
-- 1.3.6.1.4.1.2011.6.122.20.2.3.3.1.4
		-- 1.3.6.1.4.1.2011.6.122.20.2.3.3.1.4
		hwOCSIPAddress OBJECT-TYPE
			SYNTAX IpAddress
			MAX-ACCESS read-write
			STATUS current
			DESCRIPTION
				"Description."
			::= { hwOCSInfoEntry 4 }


--         1.3.6.1.4.1.2011.6.122.20.2.3.3.1.5
-- 1.3.6.1.4.1.2011.6.122.20.2.3.3.1.5
-- 1.3.6.1.4.1.2011.6.122.20.2.3.3.1.5
-- 1.3.6.1.4.1.2011.6.122.20.2.3.3.1.5
-- 1.3.6.1.4.1.2011.6.122.20.2.3.3.1.5
-- 1.3.6.1.4.1.2011.6.122.20.2.3.3.1.5
-- 1.3.6.1.4.1.2011.6.122.20.2.3.3.1.5
-- 1.3.6.1.4.1.2011.6.122.20.2.3.3.1.5
		-- 1.3.6.1.4.1.2011.6.122.20.2.3.3.1.5
		hwOCSPort OBJECT-TYPE
			SYNTAX Gauge32 (1..65535)
			MAX-ACCESS read-write
			STATUS current
			DESCRIPTION
				"Description."
			::= { hwOCSInfoEntry 5 }


--         1.3.6.1.4.1.2011.6.122.20.2.3.3.1.6
-- 1.3.6.1.4.1.2011.6.122.20.2.3.3.1.6
-- 1.3.6.1.4.1.2011.6.122.20.2.3.3.1.6
-- 1.3.6.1.4.1.2011.6.122.20.2.3.3.1.6
-- 1.3.6.1.4.1.2011.6.122.20.2.3.3.1.6
-- 1.3.6.1.4.1.2011.6.122.20.2.3.3.1.6
-- 1.3.6.1.4.1.2011.6.122.20.2.3.3.1.6
-- 1.3.6.1.4.1.2011.6.122.20.2.3.3.1.6
		-- 1.3.6.1.4.1.2011.6.122.20.2.3.3.1.6
		hwSASNameConnectOCS OBJECT-TYPE
			SYNTAX OCTET STRING (SIZE (0..255))
			MAX-ACCESS read-write
			STATUS current
			DESCRIPTION
				"Description."
			::= { hwOCSInfoEntry 6 }


--         1.3.6.1.4.1.2011.6.122.20.2.3.3.1.7
-- 1.3.6.1.4.1.2011.6.122.20.2.3.3.1.7
-- 1.3.6.1.4.1.2011.6.122.20.2.3.3.1.7
-- 1.3.6.1.4.1.2011.6.122.20.2.3.3.1.7
-- 1.3.6.1.4.1.2011.6.122.20.2.3.3.1.7
-- 1.3.6.1.4.1.2011.6.122.20.2.3.3.1.7
-- 1.3.6.1.4.1.2011.6.122.20.2.3.3.1.7
-- 1.3.6.1.4.1.2011.6.122.20.2.3.3.1.7
		-- 1.3.6.1.4.1.2011.6.122.20.2.3.3.1.7
		hwSASIPAddressConnectOCS OBJECT-TYPE
			SYNTAX IpAddress
			MAX-ACCESS read-write
			STATUS current
			DESCRIPTION
				"Description."
			::= { hwOCSInfoEntry 7 }


--         1.3.6.1.4.1.2011.6.122.20.2.3.3.1.8
-- 1.3.6.1.4.1.2011.6.122.20.2.3.3.1.8
-- 1.3.6.1.4.1.2011.6.122.20.2.3.3.1.8
-- 1.3.6.1.4.1.2011.6.122.20.2.3.3.1.8
-- 1.3.6.1.4.1.2011.6.122.20.2.3.3.1.8
-- 1.3.6.1.4.1.2011.6.122.20.2.3.3.1.8
-- 1.3.6.1.4.1.2011.6.122.20.2.3.3.1.8
-- 1.3.6.1.4.1.2011.6.122.20.2.3.3.1.8
		-- 1.3.6.1.4.1.2011.6.122.20.2.3.3.1.8
		hwSASPortConnectOCS OBJECT-TYPE
			SYNTAX Gauge32 (1..65535)
			MAX-ACCESS read-write
			STATUS current
			DESCRIPTION
				"Description."
			::= { hwOCSInfoEntry 8 }


--         1.3.6.1.4.1.2011.6.122.20.2.3.4
-- 1.3.6.1.4.1.2011.6.122.20.2.3.4
-- 1.3.6.1.4.1.2011.6.122.20.2.3.4
-- 1.3.6.1.4.1.2011.6.122.20.2.3.4
-- 1.3.6.1.4.1.2011.6.122.20.2.3.4
-- 1.3.6.1.4.1.2011.6.122.20.2.3.4
-- 1.3.6.1.4.1.2011.6.122.20.2.3.4
-- 1.3.6.1.4.1.2011.6.122.20.2.3.4
		-- 1.3.6.1.4.1.2011.6.122.20.2.3.4
		hwDRAInfoTable OBJECT-TYPE
			SYNTAX SEQUENCE OF HwDRAInfoEntry
			MAX-ACCESS not-accessible
			STATUS current
			DESCRIPTION
				"Description."
			::= { hwServiceWirelessObject 4 }


--         1.3.6.1.4.1.2011.6.122.20.2.3.4.1
-- 1.3.6.1.4.1.2011.6.122.20.2.3.4.1
-- 1.3.6.1.4.1.2011.6.122.20.2.3.4.1
-- 1.3.6.1.4.1.2011.6.122.20.2.3.4.1
-- 1.3.6.1.4.1.2011.6.122.20.2.3.4.1
-- 1.3.6.1.4.1.2011.6.122.20.2.3.4.1
-- 1.3.6.1.4.1.2011.6.122.20.2.3.4.1
-- 1.3.6.1.4.1.2011.6.122.20.2.3.4.1
		-- 1.3.6.1.4.1.2011.6.122.20.2.3.4.1
		hwDRAInfoEntry OBJECT-TYPE
			SYNTAX HwDRAInfoEntry
			MAX-ACCESS not-accessible
			STATUS current
			DESCRIPTION
				"Description."
			INDEX { hwDRAInfoIndex }
			::= { hwDRAInfoTable 1 }


		HwDRAInfoEntry ::=
			SEQUENCE {
				hwDRAInfoIndex
					Gauge32,
				hwSASLocationConnectDRA
					OCTET STRING,
				hwDRAHostName
					OCTET STRING,
				hwDRAIPAddress
					IpAddress,
				hwDRAPort
					Gauge32,
				hwSASNameConnectDRA
					OCTET STRING,
				hwSASIPAddressConnectDRA
					IpAddress,
				hwSASPortConnectDRA
					Gauge32
			 }

--         1.3.6.1.4.1.2011.6.122.20.2.3.4.1.1
-- 1.3.6.1.4.1.2011.6.122.20.2.3.4.1.1
-- 1.3.6.1.4.1.2011.6.122.20.2.3.4.1.1
-- 1.3.6.1.4.1.2011.6.122.20.2.3.4.1.1
-- 1.3.6.1.4.1.2011.6.122.20.2.3.4.1.1
-- 1.3.6.1.4.1.2011.6.122.20.2.3.4.1.1
-- 1.3.6.1.4.1.2011.6.122.20.2.3.4.1.1
-- 1.3.6.1.4.1.2011.6.122.20.2.3.4.1.1
		-- 1.3.6.1.4.1.2011.6.122.20.2.3.4.1.1
		hwDRAInfoIndex OBJECT-TYPE
			SYNTAX Gauge32
			MAX-ACCESS not-accessible
			STATUS current
			DESCRIPTION
				"Description."
			::= { hwDRAInfoEntry 1 }


--         1.3.6.1.4.1.2011.6.122.20.2.3.4.1.2
-- 1.3.6.1.4.1.2011.6.122.20.2.3.4.1.2
-- 1.3.6.1.4.1.2011.6.122.20.2.3.4.1.2
-- 1.3.6.1.4.1.2011.6.122.20.2.3.4.1.2
-- 1.3.6.1.4.1.2011.6.122.20.2.3.4.1.2
-- 1.3.6.1.4.1.2011.6.122.20.2.3.4.1.2
-- 1.3.6.1.4.1.2011.6.122.20.2.3.4.1.2
-- 1.3.6.1.4.1.2011.6.122.20.2.3.4.1.2
		-- 1.3.6.1.4.1.2011.6.122.20.2.3.4.1.2
		hwSASLocationConnectDRA OBJECT-TYPE
			SYNTAX OCTET STRING (SIZE (0..255))
			MAX-ACCESS read-write
			STATUS current
			DESCRIPTION
				"Description."
			::= { hwDRAInfoEntry 2 }


--         1.3.6.1.4.1.2011.6.122.20.2.3.4.1.3
-- 1.3.6.1.4.1.2011.6.122.20.2.3.4.1.3
-- 1.3.6.1.4.1.2011.6.122.20.2.3.4.1.3
-- 1.3.6.1.4.1.2011.6.122.20.2.3.4.1.3
-- 1.3.6.1.4.1.2011.6.122.20.2.3.4.1.3
-- 1.3.6.1.4.1.2011.6.122.20.2.3.4.1.3
-- 1.3.6.1.4.1.2011.6.122.20.2.3.4.1.3
-- 1.3.6.1.4.1.2011.6.122.20.2.3.4.1.3
		-- 1.3.6.1.4.1.2011.6.122.20.2.3.4.1.3
		hwDRAHostName OBJECT-TYPE
			SYNTAX OCTET STRING (SIZE (0..255))
			MAX-ACCESS read-write
			STATUS current
			DESCRIPTION
				"Description."
			::= { hwDRAInfoEntry 3 }


--         1.3.6.1.4.1.2011.6.122.20.2.3.4.1.4
-- 1.3.6.1.4.1.2011.6.122.20.2.3.4.1.4
-- 1.3.6.1.4.1.2011.6.122.20.2.3.4.1.4
-- 1.3.6.1.4.1.2011.6.122.20.2.3.4.1.4
-- 1.3.6.1.4.1.2011.6.122.20.2.3.4.1.4
-- 1.3.6.1.4.1.2011.6.122.20.2.3.4.1.4
-- 1.3.6.1.4.1.2011.6.122.20.2.3.4.1.4
-- 1.3.6.1.4.1.2011.6.122.20.2.3.4.1.4
		-- 1.3.6.1.4.1.2011.6.122.20.2.3.4.1.4
		hwDRAIPAddress OBJECT-TYPE
			SYNTAX IpAddress
			MAX-ACCESS read-write
			STATUS current
			DESCRIPTION
				"Description."
			::= { hwDRAInfoEntry 4 }


--         1.3.6.1.4.1.2011.6.122.20.2.3.4.1.5
-- 1.3.6.1.4.1.2011.6.122.20.2.3.4.1.5
-- 1.3.6.1.4.1.2011.6.122.20.2.3.4.1.5
-- 1.3.6.1.4.1.2011.6.122.20.2.3.4.1.5
-- 1.3.6.1.4.1.2011.6.122.20.2.3.4.1.5
-- 1.3.6.1.4.1.2011.6.122.20.2.3.4.1.5
-- 1.3.6.1.4.1.2011.6.122.20.2.3.4.1.5
-- 1.3.6.1.4.1.2011.6.122.20.2.3.4.1.5
		-- 1.3.6.1.4.1.2011.6.122.20.2.3.4.1.5
		hwDRAPort OBJECT-TYPE
			SYNTAX Gauge32 (1..65535)
			MAX-ACCESS read-write
			STATUS current
			DESCRIPTION
				"Description."
			::= { hwDRAInfoEntry 5 }


--         1.3.6.1.4.1.2011.6.122.20.2.3.4.1.6
-- 1.3.6.1.4.1.2011.6.122.20.2.3.4.1.6
-- 1.3.6.1.4.1.2011.6.122.20.2.3.4.1.6
-- 1.3.6.1.4.1.2011.6.122.20.2.3.4.1.6
-- 1.3.6.1.4.1.2011.6.122.20.2.3.4.1.6
-- 1.3.6.1.4.1.2011.6.122.20.2.3.4.1.6
-- 1.3.6.1.4.1.2011.6.122.20.2.3.4.1.6
-- 1.3.6.1.4.1.2011.6.122.20.2.3.4.1.6
		-- 1.3.6.1.4.1.2011.6.122.20.2.3.4.1.6
		hwSASNameConnectDRA OBJECT-TYPE
			SYNTAX OCTET STRING (SIZE (0..255))
			MAX-ACCESS read-write
			STATUS current
			DESCRIPTION
				"Description."
			::= { hwDRAInfoEntry 6 }


--         1.3.6.1.4.1.2011.6.122.20.2.3.4.1.7
-- 1.3.6.1.4.1.2011.6.122.20.2.3.4.1.7
-- 1.3.6.1.4.1.2011.6.122.20.2.3.4.1.7
-- 1.3.6.1.4.1.2011.6.122.20.2.3.4.1.7
-- 1.3.6.1.4.1.2011.6.122.20.2.3.4.1.7
-- 1.3.6.1.4.1.2011.6.122.20.2.3.4.1.7
-- 1.3.6.1.4.1.2011.6.122.20.2.3.4.1.7
-- 1.3.6.1.4.1.2011.6.122.20.2.3.4.1.7
		-- 1.3.6.1.4.1.2011.6.122.20.2.3.4.1.7
		hwSASIPAddressConnectDRA OBJECT-TYPE
			SYNTAX IpAddress
			MAX-ACCESS read-write
			STATUS current
			DESCRIPTION
				"Description."
			::= { hwDRAInfoEntry 7 }


--         1.3.6.1.4.1.2011.6.122.20.2.3.4.1.8
-- 1.3.6.1.4.1.2011.6.122.20.2.3.4.1.8
-- 1.3.6.1.4.1.2011.6.122.20.2.3.4.1.8
-- 1.3.6.1.4.1.2011.6.122.20.2.3.4.1.8
-- 1.3.6.1.4.1.2011.6.122.20.2.3.4.1.8
-- 1.3.6.1.4.1.2011.6.122.20.2.3.4.1.8
-- 1.3.6.1.4.1.2011.6.122.20.2.3.4.1.8
-- 1.3.6.1.4.1.2011.6.122.20.2.3.4.1.8
		-- 1.3.6.1.4.1.2011.6.122.20.2.3.4.1.8
		hwSASPortConnectDRA OBJECT-TYPE
			SYNTAX Gauge32 (1..65535)
			MAX-ACCESS read-write
			STATUS current
			DESCRIPTION
				"Description."
			::= { hwDRAInfoEntry 8 }


--         1.3.6.1.4.1.2011.6.122.20.2.3.5
-- 1.3.6.1.4.1.2011.6.122.20.2.3.5
-- 1.3.6.1.4.1.2011.6.122.20.2.3.5
-- 1.3.6.1.4.1.2011.6.122.20.2.3.5
-- 1.3.6.1.4.1.2011.6.122.20.2.3.5
-- 1.3.6.1.4.1.2011.6.122.20.2.3.5
-- 1.3.6.1.4.1.2011.6.122.20.2.3.5
-- 1.3.6.1.4.1.2011.6.122.20.2.3.5
		-- 1.3.6.1.4.1.2011.6.122.20.2.3.5
		hwSasGxPerformanceTable OBJECT-TYPE
			SYNTAX SEQUENCE OF HwSasGxPerformanceEntry
			MAX-ACCESS not-accessible
			STATUS current
			DESCRIPTION
				"Description."
			::= { hwServiceWirelessObject 5 }


--         1.3.6.1.4.1.2011.6.122.20.2.3.5.1
-- 1.3.6.1.4.1.2011.6.122.20.2.3.5.1
-- 1.3.6.1.4.1.2011.6.122.20.2.3.5.1
-- 1.3.6.1.4.1.2011.6.122.20.2.3.5.1
-- 1.3.6.1.4.1.2011.6.122.20.2.3.5.1
-- 1.3.6.1.4.1.2011.6.122.20.2.3.5.1
-- 1.3.6.1.4.1.2011.6.122.20.2.3.5.1
-- 1.3.6.1.4.1.2011.6.122.20.2.3.5.1
		-- 1.3.6.1.4.1.2011.6.122.20.2.3.5.1
		hwSasGxPerformanceEntry OBJECT-TYPE
			SYNTAX HwSasGxPerformanceEntry
			MAX-ACCESS not-accessible
			STATUS current
			DESCRIPTION
				"Description."
			INDEX { hwSasGxPerformanceIndex }
			::= { hwSasGxPerformanceTable 1 }


		HwSasGxPerformanceEntry ::=
			SEQUENCE {
				hwSasGxPerformanceIndex
					Gauge32,
				hwSasGxPerformanceLocation
					OCTET STRING,
				hwSasIPAddressForGxPerformance
					IpAddress,
				hwSasGxTotalSendNumber
					Gauge32,
				hwSasGxTotalRecieveNumber
					Gauge32,
				hwSasGxCCRInitalNumber
					Gauge32,
				hwSasGxCCAInitalNumber
					Gauge32,
				hwSasGxCCRUpdateNumber
					Gauge32,
				hwSasGxCCAUpdateNumber
					Gauge32,
				hwSasGxCCRTerminateNumber
					Gauge32,
				hwSasGxCCATerminateNumber
					Gauge32,
				hwSasGxRARNumber
					Gauge32,
				hwSasGxRAANumber
					Gauge32,
				hwSasGxASRNumber
					Gauge32,
				hwSasGxASANumber
					Gauge32
			 }

--         1.3.6.1.4.1.2011.6.122.20.2.3.5.1.1
-- 1.3.6.1.4.1.2011.6.122.20.2.3.5.1.1
-- 1.3.6.1.4.1.2011.6.122.20.2.3.5.1.1
-- 1.3.6.1.4.1.2011.6.122.20.2.3.5.1.1
-- 1.3.6.1.4.1.2011.6.122.20.2.3.5.1.1
-- 1.3.6.1.4.1.2011.6.122.20.2.3.5.1.1
-- 1.3.6.1.4.1.2011.6.122.20.2.3.5.1.1
-- 1.3.6.1.4.1.2011.6.122.20.2.3.5.1.1
		-- 1.3.6.1.4.1.2011.6.122.20.2.3.5.1.1
		hwSasGxPerformanceIndex OBJECT-TYPE
			SYNTAX Gauge32
			MAX-ACCESS not-accessible
			STATUS current
			DESCRIPTION
				"Description."
			::= { hwSasGxPerformanceEntry 1 }


--         1.3.6.1.4.1.2011.6.122.20.2.3.5.1.2
-- 1.3.6.1.4.1.2011.6.122.20.2.3.5.1.2
-- 1.3.6.1.4.1.2011.6.122.20.2.3.5.1.2
-- 1.3.6.1.4.1.2011.6.122.20.2.3.5.1.2
-- 1.3.6.1.4.1.2011.6.122.20.2.3.5.1.2
-- 1.3.6.1.4.1.2011.6.122.20.2.3.5.1.2
-- 1.3.6.1.4.1.2011.6.122.20.2.3.5.1.2
-- 1.3.6.1.4.1.2011.6.122.20.2.3.5.1.2
		-- 1.3.6.1.4.1.2011.6.122.20.2.3.5.1.2
		hwSasGxPerformanceLocation OBJECT-TYPE
			SYNTAX OCTET STRING (SIZE (0..255))
			MAX-ACCESS read-only
			STATUS current
			DESCRIPTION
				"Description."
			::= { hwSasGxPerformanceEntry 2 }


--         1.3.6.1.4.1.2011.6.122.20.2.3.5.1.3
-- 1.3.6.1.4.1.2011.6.122.20.2.3.5.1.3
-- 1.3.6.1.4.1.2011.6.122.20.2.3.5.1.3
-- 1.3.6.1.4.1.2011.6.122.20.2.3.5.1.3
-- 1.3.6.1.4.1.2011.6.122.20.2.3.5.1.3
-- 1.3.6.1.4.1.2011.6.122.20.2.3.5.1.3
-- 1.3.6.1.4.1.2011.6.122.20.2.3.5.1.3
-- 1.3.6.1.4.1.2011.6.122.20.2.3.5.1.3
		-- 1.3.6.1.4.1.2011.6.122.20.2.3.5.1.3
		hwSasIPAddressForGxPerformance OBJECT-TYPE
			SYNTAX IpAddress
			MAX-ACCESS read-only
			STATUS current
			DESCRIPTION
				"Description."
			::= { hwSasGxPerformanceEntry 3 }


--         1.3.6.1.4.1.2011.6.122.20.2.3.5.1.4
-- 1.3.6.1.4.1.2011.6.122.20.2.3.5.1.4
-- 1.3.6.1.4.1.2011.6.122.20.2.3.5.1.4
-- 1.3.6.1.4.1.2011.6.122.20.2.3.5.1.4
-- 1.3.6.1.4.1.2011.6.122.20.2.3.5.1.4
-- 1.3.6.1.4.1.2011.6.122.20.2.3.5.1.4
-- 1.3.6.1.4.1.2011.6.122.20.2.3.5.1.4
-- 1.3.6.1.4.1.2011.6.122.20.2.3.5.1.4
		-- 1.3.6.1.4.1.2011.6.122.20.2.3.5.1.4
		hwSasGxTotalSendNumber OBJECT-TYPE
			SYNTAX Gauge32
			MAX-ACCESS read-only
			STATUS current
			DESCRIPTION
				"Description."
			::= { hwSasGxPerformanceEntry 4 }


--         1.3.6.1.4.1.2011.6.122.20.2.3.5.1.5
-- 1.3.6.1.4.1.2011.6.122.20.2.3.5.1.5
-- 1.3.6.1.4.1.2011.6.122.20.2.3.5.1.5
-- 1.3.6.1.4.1.2011.6.122.20.2.3.5.1.5
-- 1.3.6.1.4.1.2011.6.122.20.2.3.5.1.5
-- 1.3.6.1.4.1.2011.6.122.20.2.3.5.1.5
-- 1.3.6.1.4.1.2011.6.122.20.2.3.5.1.5
-- 1.3.6.1.4.1.2011.6.122.20.2.3.5.1.5
		-- 1.3.6.1.4.1.2011.6.122.20.2.3.5.1.5
		hwSasGxTotalRecieveNumber OBJECT-TYPE
			SYNTAX Gauge32
			MAX-ACCESS read-only
			STATUS current
			DESCRIPTION
				"Description."
			::= { hwSasGxPerformanceEntry 5 }


--         1.3.6.1.4.1.2011.6.122.20.2.3.5.1.6
-- 1.3.6.1.4.1.2011.6.122.20.2.3.5.1.6
-- 1.3.6.1.4.1.2011.6.122.20.2.3.5.1.6
-- 1.3.6.1.4.1.2011.6.122.20.2.3.5.1.6
-- 1.3.6.1.4.1.2011.6.122.20.2.3.5.1.6
-- 1.3.6.1.4.1.2011.6.122.20.2.3.5.1.6
-- 1.3.6.1.4.1.2011.6.122.20.2.3.5.1.6
-- 1.3.6.1.4.1.2011.6.122.20.2.3.5.1.6
		-- 1.3.6.1.4.1.2011.6.122.20.2.3.5.1.6
		hwSasGxCCRInitalNumber OBJECT-TYPE
			SYNTAX Gauge32
			MAX-ACCESS read-only
			STATUS current
			DESCRIPTION
				"Description."
			::= { hwSasGxPerformanceEntry 6 }


--         1.3.6.1.4.1.2011.6.122.20.2.3.5.1.7
-- 1.3.6.1.4.1.2011.6.122.20.2.3.5.1.7
-- 1.3.6.1.4.1.2011.6.122.20.2.3.5.1.7
-- 1.3.6.1.4.1.2011.6.122.20.2.3.5.1.7
-- 1.3.6.1.4.1.2011.6.122.20.2.3.5.1.7
-- 1.3.6.1.4.1.2011.6.122.20.2.3.5.1.7
-- 1.3.6.1.4.1.2011.6.122.20.2.3.5.1.7
-- 1.3.6.1.4.1.2011.6.122.20.2.3.5.1.7
		-- 1.3.6.1.4.1.2011.6.122.20.2.3.5.1.7
		hwSasGxCCAInitalNumber OBJECT-TYPE
			SYNTAX Gauge32
			MAX-ACCESS read-only
			STATUS current
			DESCRIPTION
				"Description."
			::= { hwSasGxPerformanceEntry 7 }


--         1.3.6.1.4.1.2011.6.122.20.2.3.5.1.8
-- 1.3.6.1.4.1.2011.6.122.20.2.3.5.1.8
-- 1.3.6.1.4.1.2011.6.122.20.2.3.5.1.8
-- 1.3.6.1.4.1.2011.6.122.20.2.3.5.1.8
-- 1.3.6.1.4.1.2011.6.122.20.2.3.5.1.8
-- 1.3.6.1.4.1.2011.6.122.20.2.3.5.1.8
-- 1.3.6.1.4.1.2011.6.122.20.2.3.5.1.8
-- 1.3.6.1.4.1.2011.6.122.20.2.3.5.1.8
		-- 1.3.6.1.4.1.2011.6.122.20.2.3.5.1.8
		hwSasGxCCRUpdateNumber OBJECT-TYPE
			SYNTAX Gauge32
			MAX-ACCESS read-only
			STATUS current
			DESCRIPTION
				"Description."
			::= { hwSasGxPerformanceEntry 8 }


--         1.3.6.1.4.1.2011.6.122.20.2.3.5.1.9
-- 1.3.6.1.4.1.2011.6.122.20.2.3.5.1.9
-- 1.3.6.1.4.1.2011.6.122.20.2.3.5.1.9
-- 1.3.6.1.4.1.2011.6.122.20.2.3.5.1.9
-- 1.3.6.1.4.1.2011.6.122.20.2.3.5.1.9
-- 1.3.6.1.4.1.2011.6.122.20.2.3.5.1.9
-- 1.3.6.1.4.1.2011.6.122.20.2.3.5.1.9
-- 1.3.6.1.4.1.2011.6.122.20.2.3.5.1.9
		-- 1.3.6.1.4.1.2011.6.122.20.2.3.5.1.9
		hwSasGxCCAUpdateNumber OBJECT-TYPE
			SYNTAX Gauge32
			MAX-ACCESS read-only
			STATUS current
			DESCRIPTION
				"Description."
			::= { hwSasGxPerformanceEntry 9 }


--         1.3.6.1.4.1.2011.6.122.20.2.3.5.1.10
-- 1.3.6.1.4.1.2011.6.122.20.2.3.5.1.10
-- 1.3.6.1.4.1.2011.6.122.20.2.3.5.1.10
-- 1.3.6.1.4.1.2011.6.122.20.2.3.5.1.10
-- 1.3.6.1.4.1.2011.6.122.20.2.3.5.1.10
-- 1.3.6.1.4.1.2011.6.122.20.2.3.5.1.10
-- 1.3.6.1.4.1.2011.6.122.20.2.3.5.1.10
-- 1.3.6.1.4.1.2011.6.122.20.2.3.5.1.10
		-- 1.3.6.1.4.1.2011.6.122.20.2.3.5.1.10
		hwSasGxCCRTerminateNumber OBJECT-TYPE
			SYNTAX Gauge32
			MAX-ACCESS read-only
			STATUS current
			DESCRIPTION
				"Description."
			::= { hwSasGxPerformanceEntry 10 }


--         1.3.6.1.4.1.2011.6.122.20.2.3.5.1.11
-- 1.3.6.1.4.1.2011.6.122.20.2.3.5.1.11
-- 1.3.6.1.4.1.2011.6.122.20.2.3.5.1.11
-- 1.3.6.1.4.1.2011.6.122.20.2.3.5.1.11
-- 1.3.6.1.4.1.2011.6.122.20.2.3.5.1.11
-- 1.3.6.1.4.1.2011.6.122.20.2.3.5.1.11
-- 1.3.6.1.4.1.2011.6.122.20.2.3.5.1.11
-- 1.3.6.1.4.1.2011.6.122.20.2.3.5.1.11
		-- 1.3.6.1.4.1.2011.6.122.20.2.3.5.1.11
		hwSasGxCCATerminateNumber OBJECT-TYPE
			SYNTAX Gauge32
			MAX-ACCESS read-only
			STATUS current
			DESCRIPTION
				"Description."
			::= { hwSasGxPerformanceEntry 11 }


--         1.3.6.1.4.1.2011.6.122.20.2.3.5.1.12
-- 1.3.6.1.4.1.2011.6.122.20.2.3.5.1.12
-- 1.3.6.1.4.1.2011.6.122.20.2.3.5.1.12
-- 1.3.6.1.4.1.2011.6.122.20.2.3.5.1.12
-- 1.3.6.1.4.1.2011.6.122.20.2.3.5.1.12
-- 1.3.6.1.4.1.2011.6.122.20.2.3.5.1.12
-- 1.3.6.1.4.1.2011.6.122.20.2.3.5.1.12
-- 1.3.6.1.4.1.2011.6.122.20.2.3.5.1.12
		-- 1.3.6.1.4.1.2011.6.122.20.2.3.5.1.12
		hwSasGxRARNumber OBJECT-TYPE
			SYNTAX Gauge32
			MAX-ACCESS read-only
			STATUS current
			DESCRIPTION
				"Description."
			::= { hwSasGxPerformanceEntry 12 }


--         1.3.6.1.4.1.2011.6.122.20.2.3.5.1.13
-- 1.3.6.1.4.1.2011.6.122.20.2.3.5.1.13
-- 1.3.6.1.4.1.2011.6.122.20.2.3.5.1.13
-- 1.3.6.1.4.1.2011.6.122.20.2.3.5.1.13
-- 1.3.6.1.4.1.2011.6.122.20.2.3.5.1.13
-- 1.3.6.1.4.1.2011.6.122.20.2.3.5.1.13
-- 1.3.6.1.4.1.2011.6.122.20.2.3.5.1.13
-- 1.3.6.1.4.1.2011.6.122.20.2.3.5.1.13
		-- 1.3.6.1.4.1.2011.6.122.20.2.3.5.1.13
		hwSasGxRAANumber OBJECT-TYPE
			SYNTAX Gauge32
			MAX-ACCESS read-only
			STATUS current
			DESCRIPTION
				"Description."
			::= { hwSasGxPerformanceEntry 13 }


--         1.3.6.1.4.1.2011.6.122.20.2.3.5.1.14
-- 1.3.6.1.4.1.2011.6.122.20.2.3.5.1.14
-- 1.3.6.1.4.1.2011.6.122.20.2.3.5.1.14
-- 1.3.6.1.4.1.2011.6.122.20.2.3.5.1.14
-- 1.3.6.1.4.1.2011.6.122.20.2.3.5.1.14
-- 1.3.6.1.4.1.2011.6.122.20.2.3.5.1.14
-- 1.3.6.1.4.1.2011.6.122.20.2.3.5.1.14
-- 1.3.6.1.4.1.2011.6.122.20.2.3.5.1.14
		-- 1.3.6.1.4.1.2011.6.122.20.2.3.5.1.14
		hwSasGxASRNumber OBJECT-TYPE
			SYNTAX Gauge32
			MAX-ACCESS read-only
			STATUS current
			DESCRIPTION
				"Description."
			::= { hwSasGxPerformanceEntry 14 }


--         1.3.6.1.4.1.2011.6.122.20.2.3.5.1.15
-- 1.3.6.1.4.1.2011.6.122.20.2.3.5.1.15
-- 1.3.6.1.4.1.2011.6.122.20.2.3.5.1.15
-- 1.3.6.1.4.1.2011.6.122.20.2.3.5.1.15
-- 1.3.6.1.4.1.2011.6.122.20.2.3.5.1.15
-- 1.3.6.1.4.1.2011.6.122.20.2.3.5.1.15
-- 1.3.6.1.4.1.2011.6.122.20.2.3.5.1.15
-- 1.3.6.1.4.1.2011.6.122.20.2.3.5.1.15
		-- 1.3.6.1.4.1.2011.6.122.20.2.3.5.1.15
		hwSasGxASANumber OBJECT-TYPE
			SYNTAX Gauge32
			MAX-ACCESS read-only
			STATUS current
			DESCRIPTION
				"Description."
			::= { hwSasGxPerformanceEntry 15 }


--         1.3.6.1.4.1.2011.6.122.20.2.3.6
-- 1.3.6.1.4.1.2011.6.122.20.2.3.6
-- 1.3.6.1.4.1.2011.6.122.20.2.3.6
-- 1.3.6.1.4.1.2011.6.122.20.2.3.6
-- 1.3.6.1.4.1.2011.6.122.20.2.3.6
-- 1.3.6.1.4.1.2011.6.122.20.2.3.6
-- 1.3.6.1.4.1.2011.6.122.20.2.3.6
-- 1.3.6.1.4.1.2011.6.122.20.2.3.6
		-- 1.3.6.1.4.1.2011.6.122.20.2.3.6
		hwSasGxErrorTable OBJECT-TYPE
			SYNTAX SEQUENCE OF HwSasGxErrorEntry
			MAX-ACCESS not-accessible
			STATUS current
			DESCRIPTION
				"Description."
			::= { hwServiceWirelessObject 6 }


--         1.3.6.1.4.1.2011.6.122.20.2.3.6.1
-- 1.3.6.1.4.1.2011.6.122.20.2.3.6.1
-- 1.3.6.1.4.1.2011.6.122.20.2.3.6.1
-- 1.3.6.1.4.1.2011.6.122.20.2.3.6.1
-- 1.3.6.1.4.1.2011.6.122.20.2.3.6.1
-- 1.3.6.1.4.1.2011.6.122.20.2.3.6.1
-- 1.3.6.1.4.1.2011.6.122.20.2.3.6.1
-- 1.3.6.1.4.1.2011.6.122.20.2.3.6.1
		-- 1.3.6.1.4.1.2011.6.122.20.2.3.6.1
		hwSasGxErrorEntry OBJECT-TYPE
			SYNTAX HwSasGxErrorEntry
			MAX-ACCESS not-accessible
			STATUS current
			DESCRIPTION
				"Description."
			INDEX { hwSasGxErrorIndex }
			::= { hwSasGxErrorTable 1 }


		HwSasGxErrorEntry ::=
			SEQUENCE {
				hwSasGxErrorIndex
					Gauge32,
				hwSasGxErrorLocation
					OCTET STRING,
				hwSasIPAddressForGxError
					IpAddress,
				hwGxCommunitionInterruptedTimes
					Gauge32,
				hwSasGxCCRInitalRetransmissions
					Gauge32,
				hwSasGxCCRUpdateRetransmissions
					Gauge32,
				hwSasGxCCRTerminateRetransmissions
					Gauge32
			 }

--         1.3.6.1.4.1.2011.6.122.20.2.3.6.1.1
-- 1.3.6.1.4.1.2011.6.122.20.2.3.6.1.1
-- 1.3.6.1.4.1.2011.6.122.20.2.3.6.1.1
-- 1.3.6.1.4.1.2011.6.122.20.2.3.6.1.1
-- 1.3.6.1.4.1.2011.6.122.20.2.3.6.1.1
-- 1.3.6.1.4.1.2011.6.122.20.2.3.6.1.1
-- 1.3.6.1.4.1.2011.6.122.20.2.3.6.1.1
-- 1.3.6.1.4.1.2011.6.122.20.2.3.6.1.1
		-- 1.3.6.1.4.1.2011.6.122.20.2.3.6.1.1
		hwSasGxErrorIndex OBJECT-TYPE
			SYNTAX Gauge32
			MAX-ACCESS not-accessible
			STATUS current
			DESCRIPTION
				"Description."
			::= { hwSasGxErrorEntry 1 }


--         1.3.6.1.4.1.2011.6.122.20.2.3.6.1.2
-- 1.3.6.1.4.1.2011.6.122.20.2.3.6.1.2
-- 1.3.6.1.4.1.2011.6.122.20.2.3.6.1.2
-- 1.3.6.1.4.1.2011.6.122.20.2.3.6.1.2
-- 1.3.6.1.4.1.2011.6.122.20.2.3.6.1.2
-- 1.3.6.1.4.1.2011.6.122.20.2.3.6.1.2
-- 1.3.6.1.4.1.2011.6.122.20.2.3.6.1.2
-- 1.3.6.1.4.1.2011.6.122.20.2.3.6.1.2
		-- 1.3.6.1.4.1.2011.6.122.20.2.3.6.1.2
		hwSasGxErrorLocation OBJECT-TYPE
			SYNTAX OCTET STRING (SIZE (0..255))
			MAX-ACCESS read-only
			STATUS current
			DESCRIPTION
				"Description."
			::= { hwSasGxErrorEntry 2 }


--         1.3.6.1.4.1.2011.6.122.20.2.3.6.1.3
-- 1.3.6.1.4.1.2011.6.122.20.2.3.6.1.3
-- 1.3.6.1.4.1.2011.6.122.20.2.3.6.1.3
-- 1.3.6.1.4.1.2011.6.122.20.2.3.6.1.3
-- 1.3.6.1.4.1.2011.6.122.20.2.3.6.1.3
-- 1.3.6.1.4.1.2011.6.122.20.2.3.6.1.3
-- 1.3.6.1.4.1.2011.6.122.20.2.3.6.1.3
-- 1.3.6.1.4.1.2011.6.122.20.2.3.6.1.3
		-- 1.3.6.1.4.1.2011.6.122.20.2.3.6.1.3
		hwSasIPAddressForGxError OBJECT-TYPE
			SYNTAX IpAddress
			MAX-ACCESS read-only
			STATUS current
			DESCRIPTION
				"Description."
			::= { hwSasGxErrorEntry 3 }


--         1.3.6.1.4.1.2011.6.122.20.2.3.6.1.4
-- 1.3.6.1.4.1.2011.6.122.20.2.3.6.1.4
-- 1.3.6.1.4.1.2011.6.122.20.2.3.6.1.4
-- 1.3.6.1.4.1.2011.6.122.20.2.3.6.1.4
-- 1.3.6.1.4.1.2011.6.122.20.2.3.6.1.4
-- 1.3.6.1.4.1.2011.6.122.20.2.3.6.1.4
-- 1.3.6.1.4.1.2011.6.122.20.2.3.6.1.4
-- 1.3.6.1.4.1.2011.6.122.20.2.3.6.1.4
		-- 1.3.6.1.4.1.2011.6.122.20.2.3.6.1.4
		hwGxCommunitionInterruptedTimes OBJECT-TYPE
			SYNTAX Gauge32
			MAX-ACCESS read-only
			STATUS current
			DESCRIPTION
				"Description."
			::= { hwSasGxErrorEntry 4 }


--         1.3.6.1.4.1.2011.6.122.20.2.3.6.1.5
-- 1.3.6.1.4.1.2011.6.122.20.2.3.6.1.5
-- 1.3.6.1.4.1.2011.6.122.20.2.3.6.1.5
-- 1.3.6.1.4.1.2011.6.122.20.2.3.6.1.5
-- 1.3.6.1.4.1.2011.6.122.20.2.3.6.1.5
-- 1.3.6.1.4.1.2011.6.122.20.2.3.6.1.5
-- 1.3.6.1.4.1.2011.6.122.20.2.3.6.1.5
-- 1.3.6.1.4.1.2011.6.122.20.2.3.6.1.5
		-- 1.3.6.1.4.1.2011.6.122.20.2.3.6.1.5
		hwSasGxCCRInitalRetransmissions OBJECT-TYPE
			SYNTAX Gauge32
			MAX-ACCESS read-only
			STATUS current
			DESCRIPTION
				"Description."
			::= { hwSasGxErrorEntry 5 }


--         1.3.6.1.4.1.2011.6.122.20.2.3.6.1.6
-- 1.3.6.1.4.1.2011.6.122.20.2.3.6.1.6
-- 1.3.6.1.4.1.2011.6.122.20.2.3.6.1.6
-- 1.3.6.1.4.1.2011.6.122.20.2.3.6.1.6
-- 1.3.6.1.4.1.2011.6.122.20.2.3.6.1.6
-- 1.3.6.1.4.1.2011.6.122.20.2.3.6.1.6
-- 1.3.6.1.4.1.2011.6.122.20.2.3.6.1.6
-- 1.3.6.1.4.1.2011.6.122.20.2.3.6.1.6
		-- 1.3.6.1.4.1.2011.6.122.20.2.3.6.1.6
		hwSasGxCCRUpdateRetransmissions OBJECT-TYPE
			SYNTAX Gauge32
			MAX-ACCESS read-only
			STATUS current
			DESCRIPTION
				"Description."
			::= { hwSasGxErrorEntry 6 }


--         1.3.6.1.4.1.2011.6.122.20.2.3.6.1.7
-- 1.3.6.1.4.1.2011.6.122.20.2.3.6.1.7
-- 1.3.6.1.4.1.2011.6.122.20.2.3.6.1.7
-- 1.3.6.1.4.1.2011.6.122.20.2.3.6.1.7
-- 1.3.6.1.4.1.2011.6.122.20.2.3.6.1.7
-- 1.3.6.1.4.1.2011.6.122.20.2.3.6.1.7
-- 1.3.6.1.4.1.2011.6.122.20.2.3.6.1.7
-- 1.3.6.1.4.1.2011.6.122.20.2.3.6.1.7
		-- 1.3.6.1.4.1.2011.6.122.20.2.3.6.1.7
		hwSasGxCCRTerminateRetransmissions OBJECT-TYPE
			SYNTAX Gauge32
			MAX-ACCESS read-only
			STATUS current
			DESCRIPTION
				"Description."
			::= { hwSasGxErrorEntry 7 }


--         1.3.6.1.4.1.2011.6.122.20.2.3.7
-- 1.3.6.1.4.1.2011.6.122.20.2.3.7
-- 1.3.6.1.4.1.2011.6.122.20.2.3.7
-- 1.3.6.1.4.1.2011.6.122.20.2.3.7
-- 1.3.6.1.4.1.2011.6.122.20.2.3.7
-- 1.3.6.1.4.1.2011.6.122.20.2.3.7
-- 1.3.6.1.4.1.2011.6.122.20.2.3.7
-- 1.3.6.1.4.1.2011.6.122.20.2.3.7
		-- 1.3.6.1.4.1.2011.6.122.20.2.3.7
		hwSasGyPerformanceTable OBJECT-TYPE
			SYNTAX SEQUENCE OF HwSasGyPerformanceEntry
			MAX-ACCESS not-accessible
			STATUS current
			DESCRIPTION
				"Description."
			::= { hwServiceWirelessObject 7 }


--         1.3.6.1.4.1.2011.6.122.20.2.3.7.1
-- 1.3.6.1.4.1.2011.6.122.20.2.3.7.1
-- 1.3.6.1.4.1.2011.6.122.20.2.3.7.1
-- 1.3.6.1.4.1.2011.6.122.20.2.3.7.1
-- 1.3.6.1.4.1.2011.6.122.20.2.3.7.1
-- 1.3.6.1.4.1.2011.6.122.20.2.3.7.1
-- 1.3.6.1.4.1.2011.6.122.20.2.3.7.1
-- 1.3.6.1.4.1.2011.6.122.20.2.3.7.1
		-- 1.3.6.1.4.1.2011.6.122.20.2.3.7.1
		hwSasGyPerformanceEntry OBJECT-TYPE
			SYNTAX HwSasGyPerformanceEntry
			MAX-ACCESS not-accessible
			STATUS current
			DESCRIPTION
				"Description."
			INDEX { hwSasGyPerformanceIndex }
			::= { hwSasGyPerformanceTable 1 }


		HwSasGyPerformanceEntry ::=
			SEQUENCE {
				hwSasGyPerformanceIndex
					Gauge32,
				hwSasGyPerformanceLocation
					OCTET STRING,
				hwSasIPAddressForGyPerformance
					IpAddress,
				hwSasGyTotalSendNumber
					Gauge32,
				hwSasGyTotalRecieveNumber
					Gauge32,
				hwSasGyCCRInitalNumber
					Gauge32,
				hwSasGyCCAInitalNumber
					Gauge32,
				hwSasGyCCRUpdateNumber
					Gauge32,
				hwSasGyCCAUpdateNumber
					Gauge32,
				hwSasGyCCRTerminateNumber
					Gauge32,
				hwSasGyCCATerminateNumber
					Gauge32,
				hwSasGyRARNumber
					Gauge32,
				hwSasGyRAANumber
					Gauge32,
				hwSasGyASRNumber
					Gauge32,
				hwSasGyASANumber
					Gauge32
			 }

--         1.3.6.1.4.1.2011.6.122.20.2.3.7.1.1
-- 1.3.6.1.4.1.2011.6.122.20.2.3.7.1.1
-- 1.3.6.1.4.1.2011.6.122.20.2.3.7.1.1
-- 1.3.6.1.4.1.2011.6.122.20.2.3.7.1.1
-- 1.3.6.1.4.1.2011.6.122.20.2.3.7.1.1
-- 1.3.6.1.4.1.2011.6.122.20.2.3.7.1.1
-- 1.3.6.1.4.1.2011.6.122.20.2.3.7.1.1
-- 1.3.6.1.4.1.2011.6.122.20.2.3.7.1.1
		-- 1.3.6.1.4.1.2011.6.122.20.2.3.7.1.1
		hwSasGyPerformanceIndex OBJECT-TYPE
			SYNTAX Gauge32
			MAX-ACCESS not-accessible
			STATUS current
			DESCRIPTION
				"Description."
			::= { hwSasGyPerformanceEntry 1 }


--         1.3.6.1.4.1.2011.6.122.20.2.3.7.1.2
-- 1.3.6.1.4.1.2011.6.122.20.2.3.7.1.2
-- 1.3.6.1.4.1.2011.6.122.20.2.3.7.1.2
-- 1.3.6.1.4.1.2011.6.122.20.2.3.7.1.2
-- 1.3.6.1.4.1.2011.6.122.20.2.3.7.1.2
-- 1.3.6.1.4.1.2011.6.122.20.2.3.7.1.2
-- 1.3.6.1.4.1.2011.6.122.20.2.3.7.1.2
-- 1.3.6.1.4.1.2011.6.122.20.2.3.7.1.2
		-- 1.3.6.1.4.1.2011.6.122.20.2.3.7.1.2
		hwSasGyPerformanceLocation OBJECT-TYPE
			SYNTAX OCTET STRING (SIZE (0..255))
			MAX-ACCESS read-only
			STATUS current
			DESCRIPTION
				"Description."
			::= { hwSasGyPerformanceEntry 2 }


--         1.3.6.1.4.1.2011.6.122.20.2.3.7.1.3
-- 1.3.6.1.4.1.2011.6.122.20.2.3.7.1.3
-- 1.3.6.1.4.1.2011.6.122.20.2.3.7.1.3
-- 1.3.6.1.4.1.2011.6.122.20.2.3.7.1.3
-- 1.3.6.1.4.1.2011.6.122.20.2.3.7.1.3
-- 1.3.6.1.4.1.2011.6.122.20.2.3.7.1.3
-- 1.3.6.1.4.1.2011.6.122.20.2.3.7.1.3
-- 1.3.6.1.4.1.2011.6.122.20.2.3.7.1.3
		-- 1.3.6.1.4.1.2011.6.122.20.2.3.7.1.3
		hwSasIPAddressForGyPerformance OBJECT-TYPE
			SYNTAX IpAddress
			MAX-ACCESS read-only
			STATUS current
			DESCRIPTION
				"Description."
			::= { hwSasGyPerformanceEntry 3 }


--         1.3.6.1.4.1.2011.6.122.20.2.3.7.1.4
-- 1.3.6.1.4.1.2011.6.122.20.2.3.7.1.4
-- 1.3.6.1.4.1.2011.6.122.20.2.3.7.1.4
-- 1.3.6.1.4.1.2011.6.122.20.2.3.7.1.4
-- 1.3.6.1.4.1.2011.6.122.20.2.3.7.1.4
-- 1.3.6.1.4.1.2011.6.122.20.2.3.7.1.4
-- 1.3.6.1.4.1.2011.6.122.20.2.3.7.1.4
-- 1.3.6.1.4.1.2011.6.122.20.2.3.7.1.4
		-- 1.3.6.1.4.1.2011.6.122.20.2.3.7.1.4
		hwSasGyTotalSendNumber OBJECT-TYPE
			SYNTAX Gauge32
			MAX-ACCESS read-only
			STATUS current
			DESCRIPTION
				"Description."
			::= { hwSasGyPerformanceEntry 4 }


--         1.3.6.1.4.1.2011.6.122.20.2.3.7.1.5
-- 1.3.6.1.4.1.2011.6.122.20.2.3.7.1.5
-- 1.3.6.1.4.1.2011.6.122.20.2.3.7.1.5
-- 1.3.6.1.4.1.2011.6.122.20.2.3.7.1.5
-- 1.3.6.1.4.1.2011.6.122.20.2.3.7.1.5
-- 1.3.6.1.4.1.2011.6.122.20.2.3.7.1.5
-- 1.3.6.1.4.1.2011.6.122.20.2.3.7.1.5
-- 1.3.6.1.4.1.2011.6.122.20.2.3.7.1.5
		-- 1.3.6.1.4.1.2011.6.122.20.2.3.7.1.5
		hwSasGyTotalRecieveNumber OBJECT-TYPE
			SYNTAX Gauge32
			MAX-ACCESS read-only
			STATUS current
			DESCRIPTION
				"Description."
			::= { hwSasGyPerformanceEntry 5 }


--         1.3.6.1.4.1.2011.6.122.20.2.3.7.1.6
-- 1.3.6.1.4.1.2011.6.122.20.2.3.7.1.6
-- 1.3.6.1.4.1.2011.6.122.20.2.3.7.1.6
-- 1.3.6.1.4.1.2011.6.122.20.2.3.7.1.6
-- 1.3.6.1.4.1.2011.6.122.20.2.3.7.1.6
-- 1.3.6.1.4.1.2011.6.122.20.2.3.7.1.6
-- 1.3.6.1.4.1.2011.6.122.20.2.3.7.1.6
-- 1.3.6.1.4.1.2011.6.122.20.2.3.7.1.6
		-- 1.3.6.1.4.1.2011.6.122.20.2.3.7.1.6
		hwSasGyCCRInitalNumber OBJECT-TYPE
			SYNTAX Gauge32
			MAX-ACCESS read-only
			STATUS current
			DESCRIPTION
				"Description."
			::= { hwSasGyPerformanceEntry 6 }


--         1.3.6.1.4.1.2011.6.122.20.2.3.7.1.7
-- 1.3.6.1.4.1.2011.6.122.20.2.3.7.1.7
-- 1.3.6.1.4.1.2011.6.122.20.2.3.7.1.7
-- 1.3.6.1.4.1.2011.6.122.20.2.3.7.1.7
-- 1.3.6.1.4.1.2011.6.122.20.2.3.7.1.7
-- 1.3.6.1.4.1.2011.6.122.20.2.3.7.1.7
-- 1.3.6.1.4.1.2011.6.122.20.2.3.7.1.7
-- 1.3.6.1.4.1.2011.6.122.20.2.3.7.1.7
		-- 1.3.6.1.4.1.2011.6.122.20.2.3.7.1.7
		hwSasGyCCAInitalNumber OBJECT-TYPE
			SYNTAX Gauge32
			MAX-ACCESS read-only
			STATUS current
			DESCRIPTION
				"Description."
			::= { hwSasGyPerformanceEntry 7 }


--         1.3.6.1.4.1.2011.6.122.20.2.3.7.1.8
-- 1.3.6.1.4.1.2011.6.122.20.2.3.7.1.8
-- 1.3.6.1.4.1.2011.6.122.20.2.3.7.1.8
-- 1.3.6.1.4.1.2011.6.122.20.2.3.7.1.8
-- 1.3.6.1.4.1.2011.6.122.20.2.3.7.1.8
-- 1.3.6.1.4.1.2011.6.122.20.2.3.7.1.8
-- 1.3.6.1.4.1.2011.6.122.20.2.3.7.1.8
-- 1.3.6.1.4.1.2011.6.122.20.2.3.7.1.8
		-- 1.3.6.1.4.1.2011.6.122.20.2.3.7.1.8
		hwSasGyCCRUpdateNumber OBJECT-TYPE
			SYNTAX Gauge32
			MAX-ACCESS read-only
			STATUS current
			DESCRIPTION
				"Description."
			::= { hwSasGyPerformanceEntry 8 }


--         1.3.6.1.4.1.2011.6.122.20.2.3.7.1.9
-- 1.3.6.1.4.1.2011.6.122.20.2.3.7.1.9
-- 1.3.6.1.4.1.2011.6.122.20.2.3.7.1.9
-- 1.3.6.1.4.1.2011.6.122.20.2.3.7.1.9
-- 1.3.6.1.4.1.2011.6.122.20.2.3.7.1.9
-- 1.3.6.1.4.1.2011.6.122.20.2.3.7.1.9
-- 1.3.6.1.4.1.2011.6.122.20.2.3.7.1.9
-- 1.3.6.1.4.1.2011.6.122.20.2.3.7.1.9
		-- 1.3.6.1.4.1.2011.6.122.20.2.3.7.1.9
		hwSasGyCCAUpdateNumber OBJECT-TYPE
			SYNTAX Gauge32
			MAX-ACCESS read-only
			STATUS current
			DESCRIPTION
				"Description."
			::= { hwSasGyPerformanceEntry 9 }


--         1.3.6.1.4.1.2011.6.122.20.2.3.7.1.10
-- 1.3.6.1.4.1.2011.6.122.20.2.3.7.1.10
-- 1.3.6.1.4.1.2011.6.122.20.2.3.7.1.10
-- 1.3.6.1.4.1.2011.6.122.20.2.3.7.1.10
-- 1.3.6.1.4.1.2011.6.122.20.2.3.7.1.10
-- 1.3.6.1.4.1.2011.6.122.20.2.3.7.1.10
-- 1.3.6.1.4.1.2011.6.122.20.2.3.7.1.10
-- 1.3.6.1.4.1.2011.6.122.20.2.3.7.1.10
		-- 1.3.6.1.4.1.2011.6.122.20.2.3.7.1.10
		hwSasGyCCRTerminateNumber OBJECT-TYPE
			SYNTAX Gauge32
			MAX-ACCESS read-only
			STATUS current
			DESCRIPTION
				"Description."
			::= { hwSasGyPerformanceEntry 10 }


--         1.3.6.1.4.1.2011.6.122.20.2.3.7.1.11
-- 1.3.6.1.4.1.2011.6.122.20.2.3.7.1.11
-- 1.3.6.1.4.1.2011.6.122.20.2.3.7.1.11
-- 1.3.6.1.4.1.2011.6.122.20.2.3.7.1.11
-- 1.3.6.1.4.1.2011.6.122.20.2.3.7.1.11
-- 1.3.6.1.4.1.2011.6.122.20.2.3.7.1.11
-- 1.3.6.1.4.1.2011.6.122.20.2.3.7.1.11
-- 1.3.6.1.4.1.2011.6.122.20.2.3.7.1.11
		-- 1.3.6.1.4.1.2011.6.122.20.2.3.7.1.11
		hwSasGyCCATerminateNumber OBJECT-TYPE
			SYNTAX Gauge32
			MAX-ACCESS read-only
			STATUS current
			DESCRIPTION
				"Description."
			::= { hwSasGyPerformanceEntry 11 }


--         1.3.6.1.4.1.2011.6.122.20.2.3.7.1.12
-- 1.3.6.1.4.1.2011.6.122.20.2.3.7.1.12
-- 1.3.6.1.4.1.2011.6.122.20.2.3.7.1.12
-- 1.3.6.1.4.1.2011.6.122.20.2.3.7.1.12
-- 1.3.6.1.4.1.2011.6.122.20.2.3.7.1.12
-- 1.3.6.1.4.1.2011.6.122.20.2.3.7.1.12
-- 1.3.6.1.4.1.2011.6.122.20.2.3.7.1.12
-- 1.3.6.1.4.1.2011.6.122.20.2.3.7.1.12
		-- 1.3.6.1.4.1.2011.6.122.20.2.3.7.1.12
		hwSasGyRARNumber OBJECT-TYPE
			SYNTAX Gauge32
			MAX-ACCESS read-only
			STATUS current
			DESCRIPTION
				"Description."
			::= { hwSasGyPerformanceEntry 12 }


--         1.3.6.1.4.1.2011.6.122.20.2.3.7.1.13
-- 1.3.6.1.4.1.2011.6.122.20.2.3.7.1.13
-- 1.3.6.1.4.1.2011.6.122.20.2.3.7.1.13
-- 1.3.6.1.4.1.2011.6.122.20.2.3.7.1.13
-- 1.3.6.1.4.1.2011.6.122.20.2.3.7.1.13
-- 1.3.6.1.4.1.2011.6.122.20.2.3.7.1.13
-- 1.3.6.1.4.1.2011.6.122.20.2.3.7.1.13
-- 1.3.6.1.4.1.2011.6.122.20.2.3.7.1.13
		-- 1.3.6.1.4.1.2011.6.122.20.2.3.7.1.13
		hwSasGyRAANumber OBJECT-TYPE
			SYNTAX Gauge32
			MAX-ACCESS read-only
			STATUS current
			DESCRIPTION
				"Description."
			::= { hwSasGyPerformanceEntry 13 }


--         1.3.6.1.4.1.2011.6.122.20.2.3.7.1.14
-- 1.3.6.1.4.1.2011.6.122.20.2.3.7.1.14
-- 1.3.6.1.4.1.2011.6.122.20.2.3.7.1.14
-- 1.3.6.1.4.1.2011.6.122.20.2.3.7.1.14
-- 1.3.6.1.4.1.2011.6.122.20.2.3.7.1.14
-- 1.3.6.1.4.1.2011.6.122.20.2.3.7.1.14
-- 1.3.6.1.4.1.2011.6.122.20.2.3.7.1.14
-- 1.3.6.1.4.1.2011.6.122.20.2.3.7.1.14
		-- 1.3.6.1.4.1.2011.6.122.20.2.3.7.1.14
		hwSasGyASRNumber OBJECT-TYPE
			SYNTAX Gauge32
			MAX-ACCESS read-only
			STATUS current
			DESCRIPTION
				"Description."
			::= { hwSasGyPerformanceEntry 14 }


--         1.3.6.1.4.1.2011.6.122.20.2.3.7.1.15
-- 1.3.6.1.4.1.2011.6.122.20.2.3.7.1.15
-- 1.3.6.1.4.1.2011.6.122.20.2.3.7.1.15
-- 1.3.6.1.4.1.2011.6.122.20.2.3.7.1.15
-- 1.3.6.1.4.1.2011.6.122.20.2.3.7.1.15
-- 1.3.6.1.4.1.2011.6.122.20.2.3.7.1.15
-- 1.3.6.1.4.1.2011.6.122.20.2.3.7.1.15
-- 1.3.6.1.4.1.2011.6.122.20.2.3.7.1.15
		-- 1.3.6.1.4.1.2011.6.122.20.2.3.7.1.15
		hwSasGyASANumber OBJECT-TYPE
			SYNTAX Gauge32
			MAX-ACCESS read-only
			STATUS current
			DESCRIPTION
				"Description."
			::= { hwSasGyPerformanceEntry 15 }


--         1.3.6.1.4.1.2011.6.122.20.2.3.8
-- 1.3.6.1.4.1.2011.6.122.20.2.3.8
-- 1.3.6.1.4.1.2011.6.122.20.2.3.8
-- 1.3.6.1.4.1.2011.6.122.20.2.3.8
-- 1.3.6.1.4.1.2011.6.122.20.2.3.8
-- 1.3.6.1.4.1.2011.6.122.20.2.3.8
-- 1.3.6.1.4.1.2011.6.122.20.2.3.8
-- 1.3.6.1.4.1.2011.6.122.20.2.3.8
		-- 1.3.6.1.4.1.2011.6.122.20.2.3.8
		hwSasGyErrorTable OBJECT-TYPE
			SYNTAX SEQUENCE OF HwSasGyErrorEntry
			MAX-ACCESS not-accessible
			STATUS current
			DESCRIPTION
				"Description."
			::= { hwServiceWirelessObject 8 }


--         1.3.6.1.4.1.2011.6.122.20.2.3.8.1
-- 1.3.6.1.4.1.2011.6.122.20.2.3.8.1
-- 1.3.6.1.4.1.2011.6.122.20.2.3.8.1
-- 1.3.6.1.4.1.2011.6.122.20.2.3.8.1
-- 1.3.6.1.4.1.2011.6.122.20.2.3.8.1
-- 1.3.6.1.4.1.2011.6.122.20.2.3.8.1
-- 1.3.6.1.4.1.2011.6.122.20.2.3.8.1
-- 1.3.6.1.4.1.2011.6.122.20.2.3.8.1
		-- 1.3.6.1.4.1.2011.6.122.20.2.3.8.1
		hwSasGyErrorEntry OBJECT-TYPE
			SYNTAX HwSasGyErrorEntry
			MAX-ACCESS not-accessible
			STATUS current
			DESCRIPTION
				"Description."
			INDEX { hwSasGyErrorIndex }
			::= { hwSasGyErrorTable 1 }


		HwSasGyErrorEntry ::=
			SEQUENCE {
				hwSasGyErrorIndex
					Gauge32,
				hwSasGyErrorLocation
					OCTET STRING,
				hwSasIPAddressForGyError
					IpAddress,
				hwGyCommunitionInterruptedTimes
					Gauge32,
				hwSasGyCCRInitalRetransmissions
					Gauge32,
				hwSasGyCCRUpdateRetransmissions
					Gauge32,
				hwSasGyCCRTerminateRetransmissions
					Gauge32,
				hwOcsFaultDeactiveNumber
					Gauge32,
				hwGyType1ResultCode
					Gauge32,
				hwGyType2ResultCode
					Gauge32,
				hwGyType3ResultCode
					Gauge32,
				hwGyType4ResultCode
					Gauge32,
				hwGyType5ResultCode
					Gauge32
			 }

--         1.3.6.1.4.1.2011.6.122.20.2.3.8.1.1
-- 1.3.6.1.4.1.2011.6.122.20.2.3.8.1.1
-- 1.3.6.1.4.1.2011.6.122.20.2.3.8.1.1
-- 1.3.6.1.4.1.2011.6.122.20.2.3.8.1.1
-- 1.3.6.1.4.1.2011.6.122.20.2.3.8.1.1
-- 1.3.6.1.4.1.2011.6.122.20.2.3.8.1.1
-- 1.3.6.1.4.1.2011.6.122.20.2.3.8.1.1
-- 1.3.6.1.4.1.2011.6.122.20.2.3.8.1.1
		-- 1.3.6.1.4.1.2011.6.122.20.2.3.8.1.1
		hwSasGyErrorIndex OBJECT-TYPE
			SYNTAX Gauge32
			MAX-ACCESS not-accessible
			STATUS current
			DESCRIPTION
				"Description."
			::= { hwSasGyErrorEntry 1 }


--         1.3.6.1.4.1.2011.6.122.20.2.3.8.1.2
-- 1.3.6.1.4.1.2011.6.122.20.2.3.8.1.2
-- 1.3.6.1.4.1.2011.6.122.20.2.3.8.1.2
-- 1.3.6.1.4.1.2011.6.122.20.2.3.8.1.2
-- 1.3.6.1.4.1.2011.6.122.20.2.3.8.1.2
-- 1.3.6.1.4.1.2011.6.122.20.2.3.8.1.2
-- 1.3.6.1.4.1.2011.6.122.20.2.3.8.1.2
-- 1.3.6.1.4.1.2011.6.122.20.2.3.8.1.2
		-- 1.3.6.1.4.1.2011.6.122.20.2.3.8.1.2
		hwSasGyErrorLocation OBJECT-TYPE
			SYNTAX OCTET STRING (SIZE (0..255))
			MAX-ACCESS read-only
			STATUS current
			DESCRIPTION
				"Description."
			::= { hwSasGyErrorEntry 2 }


--         1.3.6.1.4.1.2011.6.122.20.2.3.8.1.3
-- 1.3.6.1.4.1.2011.6.122.20.2.3.8.1.3
-- 1.3.6.1.4.1.2011.6.122.20.2.3.8.1.3
-- 1.3.6.1.4.1.2011.6.122.20.2.3.8.1.3
-- 1.3.6.1.4.1.2011.6.122.20.2.3.8.1.3
-- 1.3.6.1.4.1.2011.6.122.20.2.3.8.1.3
-- 1.3.6.1.4.1.2011.6.122.20.2.3.8.1.3
-- 1.3.6.1.4.1.2011.6.122.20.2.3.8.1.3
		-- 1.3.6.1.4.1.2011.6.122.20.2.3.8.1.3
		hwSasIPAddressForGyError OBJECT-TYPE
			SYNTAX IpAddress
			MAX-ACCESS read-only
			STATUS current
			DESCRIPTION
				"Description."
			::= { hwSasGyErrorEntry 3 }


--         1.3.6.1.4.1.2011.6.122.20.2.3.8.1.4
-- 1.3.6.1.4.1.2011.6.122.20.2.3.8.1.4
-- 1.3.6.1.4.1.2011.6.122.20.2.3.8.1.4
-- 1.3.6.1.4.1.2011.6.122.20.2.3.8.1.4
-- 1.3.6.1.4.1.2011.6.122.20.2.3.8.1.4
-- 1.3.6.1.4.1.2011.6.122.20.2.3.8.1.4
-- 1.3.6.1.4.1.2011.6.122.20.2.3.8.1.4
-- 1.3.6.1.4.1.2011.6.122.20.2.3.8.1.4
		-- 1.3.6.1.4.1.2011.6.122.20.2.3.8.1.4
		hwGyCommunitionInterruptedTimes OBJECT-TYPE
			SYNTAX Gauge32
			MAX-ACCESS read-only
			STATUS current
			DESCRIPTION
				"Description."
			::= { hwSasGyErrorEntry 4 }


--         1.3.6.1.4.1.2011.6.122.20.2.3.8.1.5
-- 1.3.6.1.4.1.2011.6.122.20.2.3.8.1.5
-- 1.3.6.1.4.1.2011.6.122.20.2.3.8.1.5
-- 1.3.6.1.4.1.2011.6.122.20.2.3.8.1.5
-- 1.3.6.1.4.1.2011.6.122.20.2.3.8.1.5
-- 1.3.6.1.4.1.2011.6.122.20.2.3.8.1.5
-- 1.3.6.1.4.1.2011.6.122.20.2.3.8.1.5
-- 1.3.6.1.4.1.2011.6.122.20.2.3.8.1.5
		-- 1.3.6.1.4.1.2011.6.122.20.2.3.8.1.5
		hwSasGyCCRInitalRetransmissions OBJECT-TYPE
			SYNTAX Gauge32
			MAX-ACCESS read-only
			STATUS current
			DESCRIPTION
				"Description."
			::= { hwSasGyErrorEntry 5 }


--         1.3.6.1.4.1.2011.6.122.20.2.3.8.1.6
-- 1.3.6.1.4.1.2011.6.122.20.2.3.8.1.6
-- 1.3.6.1.4.1.2011.6.122.20.2.3.8.1.6
-- 1.3.6.1.4.1.2011.6.122.20.2.3.8.1.6
-- 1.3.6.1.4.1.2011.6.122.20.2.3.8.1.6
-- 1.3.6.1.4.1.2011.6.122.20.2.3.8.1.6
-- 1.3.6.1.4.1.2011.6.122.20.2.3.8.1.6
-- 1.3.6.1.4.1.2011.6.122.20.2.3.8.1.6
		-- 1.3.6.1.4.1.2011.6.122.20.2.3.8.1.6
		hwSasGyCCRUpdateRetransmissions OBJECT-TYPE
			SYNTAX Gauge32
			MAX-ACCESS read-only
			STATUS current
			DESCRIPTION
				"Description."
			::= { hwSasGyErrorEntry 6 }


--         1.3.6.1.4.1.2011.6.122.20.2.3.8.1.7
-- 1.3.6.1.4.1.2011.6.122.20.2.3.8.1.7
-- 1.3.6.1.4.1.2011.6.122.20.2.3.8.1.7
-- 1.3.6.1.4.1.2011.6.122.20.2.3.8.1.7
-- 1.3.6.1.4.1.2011.6.122.20.2.3.8.1.7
-- 1.3.6.1.4.1.2011.6.122.20.2.3.8.1.7
-- 1.3.6.1.4.1.2011.6.122.20.2.3.8.1.7
-- 1.3.6.1.4.1.2011.6.122.20.2.3.8.1.7
		-- 1.3.6.1.4.1.2011.6.122.20.2.3.8.1.7
		hwSasGyCCRTerminateRetransmissions OBJECT-TYPE
			SYNTAX Gauge32
			MAX-ACCESS read-only
			STATUS current
			DESCRIPTION
				"Description."
			::= { hwSasGyErrorEntry 7 }


--         1.3.6.1.4.1.2011.6.122.20.2.3.8.1.8
-- 1.3.6.1.4.1.2011.6.122.20.2.3.8.1.8
-- 1.3.6.1.4.1.2011.6.122.20.2.3.8.1.8
-- 1.3.6.1.4.1.2011.6.122.20.2.3.8.1.8
-- 1.3.6.1.4.1.2011.6.122.20.2.3.8.1.8
-- 1.3.6.1.4.1.2011.6.122.20.2.3.8.1.8
-- 1.3.6.1.4.1.2011.6.122.20.2.3.8.1.8
-- 1.3.6.1.4.1.2011.6.122.20.2.3.8.1.8
		-- 1.3.6.1.4.1.2011.6.122.20.2.3.8.1.8
		hwOcsFaultDeactiveNumber OBJECT-TYPE
			SYNTAX Gauge32
			MAX-ACCESS read-only
			STATUS current
			DESCRIPTION
				"Description."
			::= { hwSasGyErrorEntry 8 }


--         1.3.6.1.4.1.2011.6.122.20.2.3.8.1.9
-- 1.3.6.1.4.1.2011.6.122.20.2.3.8.1.9
-- 1.3.6.1.4.1.2011.6.122.20.2.3.8.1.9
-- 1.3.6.1.4.1.2011.6.122.20.2.3.8.1.9
-- 1.3.6.1.4.1.2011.6.122.20.2.3.8.1.9
-- 1.3.6.1.4.1.2011.6.122.20.2.3.8.1.9
-- 1.3.6.1.4.1.2011.6.122.20.2.3.8.1.9
-- 1.3.6.1.4.1.2011.6.122.20.2.3.8.1.9
		-- 1.3.6.1.4.1.2011.6.122.20.2.3.8.1.9
		hwGyType1ResultCode OBJECT-TYPE
			SYNTAX Gauge32
			MAX-ACCESS read-only
			STATUS current
			DESCRIPTION
				"Description."
			::= { hwSasGyErrorEntry 9 }


--         1.3.6.1.4.1.2011.6.122.20.2.3.8.1.10
-- 1.3.6.1.4.1.2011.6.122.20.2.3.8.1.10
-- 1.3.6.1.4.1.2011.6.122.20.2.3.8.1.10
-- 1.3.6.1.4.1.2011.6.122.20.2.3.8.1.10
-- 1.3.6.1.4.1.2011.6.122.20.2.3.8.1.10
-- 1.3.6.1.4.1.2011.6.122.20.2.3.8.1.10
-- 1.3.6.1.4.1.2011.6.122.20.2.3.8.1.10
-- 1.3.6.1.4.1.2011.6.122.20.2.3.8.1.10
		-- 1.3.6.1.4.1.2011.6.122.20.2.3.8.1.10
		hwGyType2ResultCode OBJECT-TYPE
			SYNTAX Gauge32
			MAX-ACCESS read-only
			STATUS current
			DESCRIPTION
				"Description."
			::= { hwSasGyErrorEntry 10 }


--         1.3.6.1.4.1.2011.6.122.20.2.3.8.1.11
-- 1.3.6.1.4.1.2011.6.122.20.2.3.8.1.11
-- 1.3.6.1.4.1.2011.6.122.20.2.3.8.1.11
-- 1.3.6.1.4.1.2011.6.122.20.2.3.8.1.11
-- 1.3.6.1.4.1.2011.6.122.20.2.3.8.1.11
-- 1.3.6.1.4.1.2011.6.122.20.2.3.8.1.11
-- 1.3.6.1.4.1.2011.6.122.20.2.3.8.1.11
-- 1.3.6.1.4.1.2011.6.122.20.2.3.8.1.11
		-- 1.3.6.1.4.1.2011.6.122.20.2.3.8.1.11
		hwGyType3ResultCode OBJECT-TYPE
			SYNTAX Gauge32
			MAX-ACCESS read-only
			STATUS current
			DESCRIPTION
				"Description."
			::= { hwSasGyErrorEntry 11 }


--         1.3.6.1.4.1.2011.6.122.20.2.3.8.1.12
-- 1.3.6.1.4.1.2011.6.122.20.2.3.8.1.12
-- 1.3.6.1.4.1.2011.6.122.20.2.3.8.1.12
-- 1.3.6.1.4.1.2011.6.122.20.2.3.8.1.12
-- 1.3.6.1.4.1.2011.6.122.20.2.3.8.1.12
-- 1.3.6.1.4.1.2011.6.122.20.2.3.8.1.12
-- 1.3.6.1.4.1.2011.6.122.20.2.3.8.1.12
-- 1.3.6.1.4.1.2011.6.122.20.2.3.8.1.12
		-- 1.3.6.1.4.1.2011.6.122.20.2.3.8.1.12
		hwGyType4ResultCode OBJECT-TYPE
			SYNTAX Gauge32
			MAX-ACCESS read-only
			STATUS current
			DESCRIPTION
				"Description."
			::= { hwSasGyErrorEntry 12 }


--         1.3.6.1.4.1.2011.6.122.20.2.3.8.1.13
-- 1.3.6.1.4.1.2011.6.122.20.2.3.8.1.13
-- 1.3.6.1.4.1.2011.6.122.20.2.3.8.1.13
-- 1.3.6.1.4.1.2011.6.122.20.2.3.8.1.13
-- 1.3.6.1.4.1.2011.6.122.20.2.3.8.1.13
-- 1.3.6.1.4.1.2011.6.122.20.2.3.8.1.13
-- 1.3.6.1.4.1.2011.6.122.20.2.3.8.1.13
-- 1.3.6.1.4.1.2011.6.122.20.2.3.8.1.13
		-- 1.3.6.1.4.1.2011.6.122.20.2.3.8.1.13
		hwGyType5ResultCode OBJECT-TYPE
			SYNTAX Gauge32
			MAX-ACCESS read-only
			STATUS current
			DESCRIPTION
				"Description."
			::= { hwSasGyErrorEntry 13 }


--         1.3.6.1.4.1.2011.6.122.20.2.3.9
-- 1.3.6.1.4.1.2011.6.122.20.2.3.9
-- 1.3.6.1.4.1.2011.6.122.20.2.3.9
-- 1.3.6.1.4.1.2011.6.122.20.2.3.9
-- 1.3.6.1.4.1.2011.6.122.20.2.3.9
-- 1.3.6.1.4.1.2011.6.122.20.2.3.9
-- 1.3.6.1.4.1.2011.6.122.20.2.3.9
-- 1.3.6.1.4.1.2011.6.122.20.2.3.9
		-- 1.3.6.1.4.1.2011.6.122.20.2.3.9
		hwSasGzPerformanceTable OBJECT-TYPE
			SYNTAX SEQUENCE OF HwSasGzPerformanceEntry
			MAX-ACCESS not-accessible
			STATUS current
			DESCRIPTION
				"Description."
			::= { hwServiceWirelessObject 9 }


--         1.3.6.1.4.1.2011.6.122.20.2.3.9.1
-- 1.3.6.1.4.1.2011.6.122.20.2.3.9.1
-- 1.3.6.1.4.1.2011.6.122.20.2.3.9.1
-- 1.3.6.1.4.1.2011.6.122.20.2.3.9.1
-- 1.3.6.1.4.1.2011.6.122.20.2.3.9.1
-- 1.3.6.1.4.1.2011.6.122.20.2.3.9.1
-- 1.3.6.1.4.1.2011.6.122.20.2.3.9.1
-- 1.3.6.1.4.1.2011.6.122.20.2.3.9.1
		-- 1.3.6.1.4.1.2011.6.122.20.2.3.9.1
		hwSasGzPerformanceEntry OBJECT-TYPE
			SYNTAX HwSasGzPerformanceEntry
			MAX-ACCESS not-accessible
			STATUS current
			DESCRIPTION
				"Description."
			INDEX { hwSasGzPerformanceIndex }
			::= { hwSasGzPerformanceTable 1 }


		HwSasGzPerformanceEntry ::=
			SEQUENCE {
				hwSasGzPerformanceIndex
					Gauge32,
				hwSasGzPerformanceLocation
					OCTET STRING,
				hwSasIPAddressForGzPerformance
					IpAddress,
				hwSasGzSendCDRNumber
					Gauge32
			 }

--         1.3.6.1.4.1.2011.6.122.20.2.3.9.1.1
-- 1.3.6.1.4.1.2011.6.122.20.2.3.9.1.1
-- 1.3.6.1.4.1.2011.6.122.20.2.3.9.1.1
-- 1.3.6.1.4.1.2011.6.122.20.2.3.9.1.1
-- 1.3.6.1.4.1.2011.6.122.20.2.3.9.1.1
-- 1.3.6.1.4.1.2011.6.122.20.2.3.9.1.1
-- 1.3.6.1.4.1.2011.6.122.20.2.3.9.1.1
-- 1.3.6.1.4.1.2011.6.122.20.2.3.9.1.1
		-- 1.3.6.1.4.1.2011.6.122.20.2.3.9.1.1
		hwSasGzPerformanceIndex OBJECT-TYPE
			SYNTAX Gauge32
			MAX-ACCESS not-accessible
			STATUS current
			DESCRIPTION
				"Description."
			::= { hwSasGzPerformanceEntry 1 }


--         1.3.6.1.4.1.2011.6.122.20.2.3.9.1.2
-- 1.3.6.1.4.1.2011.6.122.20.2.3.9.1.2
-- 1.3.6.1.4.1.2011.6.122.20.2.3.9.1.2
-- 1.3.6.1.4.1.2011.6.122.20.2.3.9.1.2
-- 1.3.6.1.4.1.2011.6.122.20.2.3.9.1.2
-- 1.3.6.1.4.1.2011.6.122.20.2.3.9.1.2
-- 1.3.6.1.4.1.2011.6.122.20.2.3.9.1.2
-- 1.3.6.1.4.1.2011.6.122.20.2.3.9.1.2
		-- 1.3.6.1.4.1.2011.6.122.20.2.3.9.1.2
		hwSasGzPerformanceLocation OBJECT-TYPE
			SYNTAX OCTET STRING (SIZE (0..255))
			MAX-ACCESS read-only
			STATUS current
			DESCRIPTION
				"Description."
			::= { hwSasGzPerformanceEntry 2 }


--         1.3.6.1.4.1.2011.6.122.20.2.3.9.1.3
-- 1.3.6.1.4.1.2011.6.122.20.2.3.9.1.3
-- 1.3.6.1.4.1.2011.6.122.20.2.3.9.1.3
-- 1.3.6.1.4.1.2011.6.122.20.2.3.9.1.3
-- 1.3.6.1.4.1.2011.6.122.20.2.3.9.1.3
-- 1.3.6.1.4.1.2011.6.122.20.2.3.9.1.3
-- 1.3.6.1.4.1.2011.6.122.20.2.3.9.1.3
-- 1.3.6.1.4.1.2011.6.122.20.2.3.9.1.3
		-- 1.3.6.1.4.1.2011.6.122.20.2.3.9.1.3
		hwSasIPAddressForGzPerformance OBJECT-TYPE
			SYNTAX IpAddress
			MAX-ACCESS read-only
			STATUS current
			DESCRIPTION
				"Description."
			::= { hwSasGzPerformanceEntry 3 }


--         1.3.6.1.4.1.2011.6.122.20.2.3.9.1.4
-- 1.3.6.1.4.1.2011.6.122.20.2.3.9.1.4
-- 1.3.6.1.4.1.2011.6.122.20.2.3.9.1.4
-- 1.3.6.1.4.1.2011.6.122.20.2.3.9.1.4
-- 1.3.6.1.4.1.2011.6.122.20.2.3.9.1.4
-- 1.3.6.1.4.1.2011.6.122.20.2.3.9.1.4
-- 1.3.6.1.4.1.2011.6.122.20.2.3.9.1.4
-- 1.3.6.1.4.1.2011.6.122.20.2.3.9.1.4
		-- 1.3.6.1.4.1.2011.6.122.20.2.3.9.1.4
		hwSasGzSendCDRNumber OBJECT-TYPE
			SYNTAX Gauge32
			MAX-ACCESS read-only
			STATUS current
			DESCRIPTION
				"Description."
			::= { hwSasGzPerformanceEntry 4 }


--         1.3.6.1.4.1.2011.6.122.20.2.3.10
-- 1.3.6.1.4.1.2011.6.122.20.2.3.10
-- 1.3.6.1.4.1.2011.6.122.20.2.3.10
-- 1.3.6.1.4.1.2011.6.122.20.2.3.10
-- 1.3.6.1.4.1.2011.6.122.20.2.3.10
-- 1.3.6.1.4.1.2011.6.122.20.2.3.10
-- 1.3.6.1.4.1.2011.6.122.20.2.3.10
-- 1.3.6.1.4.1.2011.6.122.20.2.3.10
		-- 1.3.6.1.4.1.2011.6.122.20.2.3.10
		hwSasGzErrorTable OBJECT-TYPE
			SYNTAX SEQUENCE OF HwSasGzErrorEntry
			MAX-ACCESS not-accessible
			STATUS current
			DESCRIPTION
				"Description."
			::= { hwServiceWirelessObject 10 }


--         1.3.6.1.4.1.2011.6.122.20.2.3.10.1
-- 1.3.6.1.4.1.2011.6.122.20.2.3.10.1
-- 1.3.6.1.4.1.2011.6.122.20.2.3.10.1
-- 1.3.6.1.4.1.2011.6.122.20.2.3.10.1
-- 1.3.6.1.4.1.2011.6.122.20.2.3.10.1
-- 1.3.6.1.4.1.2011.6.122.20.2.3.10.1
-- 1.3.6.1.4.1.2011.6.122.20.2.3.10.1
-- 1.3.6.1.4.1.2011.6.122.20.2.3.10.1
		-- 1.3.6.1.4.1.2011.6.122.20.2.3.10.1
		hwSasGzErrorEntry OBJECT-TYPE
			SYNTAX HwSasGzErrorEntry
			MAX-ACCESS not-accessible
			STATUS current
			DESCRIPTION
				"Description."
			INDEX { hwSasGzErrorIndex }
			::= { hwSasGzErrorTable 1 }


		HwSasGzErrorEntry ::=
			SEQUENCE {
				hwSasGzErrorIndex
					Gauge32,
				hwSasGzErrorLocation
					OCTET STRING,
				hwSasIPAddressForGzError
					IpAddress,
				hwGzCommunitionInterruptedTimes
					Gauge32,
				hwSasGzAbnormalSignalingNumber
					Gauge32
			 }

--         1.3.6.1.4.1.2011.6.122.20.2.3.10.1.1
-- 1.3.6.1.4.1.2011.6.122.20.2.3.10.1.1
-- 1.3.6.1.4.1.2011.6.122.20.2.3.10.1.1
-- 1.3.6.1.4.1.2011.6.122.20.2.3.10.1.1
-- 1.3.6.1.4.1.2011.6.122.20.2.3.10.1.1
-- 1.3.6.1.4.1.2011.6.122.20.2.3.10.1.1
-- 1.3.6.1.4.1.2011.6.122.20.2.3.10.1.1
-- 1.3.6.1.4.1.2011.6.122.20.2.3.10.1.1
		-- 1.3.6.1.4.1.2011.6.122.20.2.3.10.1.1
		hwSasGzErrorIndex OBJECT-TYPE
			SYNTAX Gauge32
			MAX-ACCESS not-accessible
			STATUS current
			DESCRIPTION
				"Description."
			::= { hwSasGzErrorEntry 1 }


--         1.3.6.1.4.1.2011.6.122.20.2.3.10.1.2
-- 1.3.6.1.4.1.2011.6.122.20.2.3.10.1.2
-- 1.3.6.1.4.1.2011.6.122.20.2.3.10.1.2
-- 1.3.6.1.4.1.2011.6.122.20.2.3.10.1.2
-- 1.3.6.1.4.1.2011.6.122.20.2.3.10.1.2
-- 1.3.6.1.4.1.2011.6.122.20.2.3.10.1.2
-- 1.3.6.1.4.1.2011.6.122.20.2.3.10.1.2
-- 1.3.6.1.4.1.2011.6.122.20.2.3.10.1.2
		-- 1.3.6.1.4.1.2011.6.122.20.2.3.10.1.2
		hwSasGzErrorLocation OBJECT-TYPE
			SYNTAX OCTET STRING (SIZE (0..255))
			MAX-ACCESS read-only
			STATUS current
			DESCRIPTION
				"Description."
			::= { hwSasGzErrorEntry 2 }


--         1.3.6.1.4.1.2011.6.122.20.2.3.10.1.3
-- 1.3.6.1.4.1.2011.6.122.20.2.3.10.1.3
-- 1.3.6.1.4.1.2011.6.122.20.2.3.10.1.3
-- 1.3.6.1.4.1.2011.6.122.20.2.3.10.1.3
-- 1.3.6.1.4.1.2011.6.122.20.2.3.10.1.3
-- 1.3.6.1.4.1.2011.6.122.20.2.3.10.1.3
-- 1.3.6.1.4.1.2011.6.122.20.2.3.10.1.3
-- 1.3.6.1.4.1.2011.6.122.20.2.3.10.1.3
		-- 1.3.6.1.4.1.2011.6.122.20.2.3.10.1.3
		hwSasIPAddressForGzError OBJECT-TYPE
			SYNTAX IpAddress
			MAX-ACCESS read-only
			STATUS current
			DESCRIPTION
				"Description."
			::= { hwSasGzErrorEntry 3 }


--         1.3.6.1.4.1.2011.6.122.20.2.3.10.1.4
-- 1.3.6.1.4.1.2011.6.122.20.2.3.10.1.4
-- 1.3.6.1.4.1.2011.6.122.20.2.3.10.1.4
-- 1.3.6.1.4.1.2011.6.122.20.2.3.10.1.4
-- 1.3.6.1.4.1.2011.6.122.20.2.3.10.1.4
-- 1.3.6.1.4.1.2011.6.122.20.2.3.10.1.4
-- 1.3.6.1.4.1.2011.6.122.20.2.3.10.1.4
-- 1.3.6.1.4.1.2011.6.122.20.2.3.10.1.4
		-- 1.3.6.1.4.1.2011.6.122.20.2.3.10.1.4
		hwGzCommunitionInterruptedTimes OBJECT-TYPE
			SYNTAX Gauge32
			MAX-ACCESS read-only
			STATUS current
			DESCRIPTION
				"Description."
			::= { hwSasGzErrorEntry 4 }


--         1.3.6.1.4.1.2011.6.122.20.2.3.10.1.5
-- 1.3.6.1.4.1.2011.6.122.20.2.3.10.1.5
-- 1.3.6.1.4.1.2011.6.122.20.2.3.10.1.5
-- 1.3.6.1.4.1.2011.6.122.20.2.3.10.1.5
-- 1.3.6.1.4.1.2011.6.122.20.2.3.10.1.5
-- 1.3.6.1.4.1.2011.6.122.20.2.3.10.1.5
-- 1.3.6.1.4.1.2011.6.122.20.2.3.10.1.5
-- 1.3.6.1.4.1.2011.6.122.20.2.3.10.1.5
		-- 1.3.6.1.4.1.2011.6.122.20.2.3.10.1.5
		hwSasGzAbnormalSignalingNumber OBJECT-TYPE
			SYNTAX Gauge32
			MAX-ACCESS read-only
			STATUS current
			DESCRIPTION
				"Description."
			::= { hwSasGzErrorEntry 5 }


--         1.3.6.1.4.1.2011.6.122.20.2.3.11
-- 1.3.6.1.4.1.2011.6.122.20.2.3.11
-- 1.3.6.1.4.1.2011.6.122.20.2.3.11
-- 1.3.6.1.4.1.2011.6.122.20.2.3.11
-- 1.3.6.1.4.1.2011.6.122.20.2.3.11
-- 1.3.6.1.4.1.2011.6.122.20.2.3.11
-- 1.3.6.1.4.1.2011.6.122.20.2.3.11
-- 1.3.6.1.4.1.2011.6.122.20.2.3.11
		-- 1.3.6.1.4.1.2011.6.122.20.2.3.11
		hwSpsLinkBandwidthTable OBJECT-TYPE
			SYNTAX SEQUENCE OF HwSpsLinkBandwidthEntry
			MAX-ACCESS not-accessible
			STATUS current
			DESCRIPTION
				"This table displays real-time bandwidth information of an SPS link, including the link ID, SPS location, permitted upstream and downstream traffic in real time, and discarded upstream and downstream traffic in real time."
			::= { hwServiceWirelessObject 11 }


--         1.3.6.1.4.1.2011.6.122.20.2.3.11.1
-- 1.3.6.1.4.1.2011.6.122.20.2.3.11.1
-- 1.3.6.1.4.1.2011.6.122.20.2.3.11.1
-- 1.3.6.1.4.1.2011.6.122.20.2.3.11.1
-- 1.3.6.1.4.1.2011.6.122.20.2.3.11.1
-- 1.3.6.1.4.1.2011.6.122.20.2.3.11.1
-- 1.3.6.1.4.1.2011.6.122.20.2.3.11.1
-- 1.3.6.1.4.1.2011.6.122.20.2.3.11.1
		-- 1.3.6.1.4.1.2011.6.122.20.2.3.11.1
		hwSpsLinkBandwidthEntry OBJECT-TYPE
			SYNTAX HwSpsLinkBandwidthEntry
			MAX-ACCESS not-accessible
			STATUS current
			DESCRIPTION
				"Description."
			INDEX { hwSpsLinkBandwidthIndex }
			::= { hwSpsLinkBandwidthTable 1 }


		HwSpsLinkBandwidthEntry ::=
			SEQUENCE {
				hwSpsLinkBandwidthIndex
					Gauge32,
				hwSpsLinkId
					Gauge32,
				hwSPSLinkLocation
					OCTET STRING,
				hwUpstreamPassedBandwidth
					Counter64,
				hwDownstreamPassedBandwidth
					Counter64,
				hwUpstreamDiscardedBandwidth
					Counter64,
				hwDownstreamDiscardedBandwidth
					Counter64
			 }

--         1.3.6.1.4.1.2011.6.122.20.2.3.11.1.1
-- 1.3.6.1.4.1.2011.6.122.20.2.3.11.1.1
-- 1.3.6.1.4.1.2011.6.122.20.2.3.11.1.1
-- 1.3.6.1.4.1.2011.6.122.20.2.3.11.1.1
-- 1.3.6.1.4.1.2011.6.122.20.2.3.11.1.1
-- 1.3.6.1.4.1.2011.6.122.20.2.3.11.1.1
-- 1.3.6.1.4.1.2011.6.122.20.2.3.11.1.1
-- 1.3.6.1.4.1.2011.6.122.20.2.3.11.1.1
		-- 1.3.6.1.4.1.2011.6.122.20.2.3.11.1.1
		hwSpsLinkBandwidthIndex OBJECT-TYPE
			SYNTAX Gauge32
			MAX-ACCESS not-accessible
			STATUS current
			DESCRIPTION
				"Link index."
			::= { hwSpsLinkBandwidthEntry 1 }


--         1.3.6.1.4.1.2011.6.122.20.2.3.11.1.2
-- 1.3.6.1.4.1.2011.6.122.20.2.3.11.1.2
-- 1.3.6.1.4.1.2011.6.122.20.2.3.11.1.2
-- 1.3.6.1.4.1.2011.6.122.20.2.3.11.1.2
-- 1.3.6.1.4.1.2011.6.122.20.2.3.11.1.2
-- 1.3.6.1.4.1.2011.6.122.20.2.3.11.1.2
-- 1.3.6.1.4.1.2011.6.122.20.2.3.11.1.2
-- 1.3.6.1.4.1.2011.6.122.20.2.3.11.1.2
		-- 1.3.6.1.4.1.2011.6.122.20.2.3.11.1.2
		hwSpsLinkId OBJECT-TYPE
			SYNTAX Gauge32
			MAX-ACCESS read-only
			STATUS current
			DESCRIPTION
				"Link ID."
			::= { hwSpsLinkBandwidthEntry 2 }


--         1.3.6.1.4.1.2011.6.122.20.2.3.11.1.3
-- 1.3.6.1.4.1.2011.6.122.20.2.3.11.1.3
-- 1.3.6.1.4.1.2011.6.122.20.2.3.11.1.3
-- 1.3.6.1.4.1.2011.6.122.20.2.3.11.1.3
-- 1.3.6.1.4.1.2011.6.122.20.2.3.11.1.3
-- 1.3.6.1.4.1.2011.6.122.20.2.3.11.1.3
-- 1.3.6.1.4.1.2011.6.122.20.2.3.11.1.3
-- 1.3.6.1.4.1.2011.6.122.20.2.3.11.1.3
		-- 1.3.6.1.4.1.2011.6.122.20.2.3.11.1.3
		hwSPSLinkLocation OBJECT-TYPE
			SYNTAX OCTET STRING (SIZE (0..255))
			MAX-ACCESS read-only
			STATUS current
			DESCRIPTION
				"SPS location."
			::= { hwSpsLinkBandwidthEntry 3 }


--         1.3.6.1.4.1.2011.6.122.20.2.3.11.1.4
-- 1.3.6.1.4.1.2011.6.122.20.2.3.11.1.4
-- 1.3.6.1.4.1.2011.6.122.20.2.3.11.1.4
-- 1.3.6.1.4.1.2011.6.122.20.2.3.11.1.4
-- 1.3.6.1.4.1.2011.6.122.20.2.3.11.1.4
-- 1.3.6.1.4.1.2011.6.122.20.2.3.11.1.4
-- 1.3.6.1.4.1.2011.6.122.20.2.3.11.1.4
-- 1.3.6.1.4.1.2011.6.122.20.2.3.11.1.4
		-- 1.3.6.1.4.1.2011.6.122.20.2.3.11.1.4
		hwUpstreamPassedBandwidth OBJECT-TYPE
			SYNTAX Counter64
			UNITS "Kbits/s"
			MAX-ACCESS read-only
			STATUS current
			DESCRIPTION
				"Permitted upstream traffic."
			::= { hwSpsLinkBandwidthEntry 4 }


--         1.3.6.1.4.1.2011.6.122.20.2.3.11.1.5
-- 1.3.6.1.4.1.2011.6.122.20.2.3.11.1.5
-- 1.3.6.1.4.1.2011.6.122.20.2.3.11.1.5
-- 1.3.6.1.4.1.2011.6.122.20.2.3.11.1.5
-- 1.3.6.1.4.1.2011.6.122.20.2.3.11.1.5
-- 1.3.6.1.4.1.2011.6.122.20.2.3.11.1.5
-- 1.3.6.1.4.1.2011.6.122.20.2.3.11.1.5
-- 1.3.6.1.4.1.2011.6.122.20.2.3.11.1.5
		-- 1.3.6.1.4.1.2011.6.122.20.2.3.11.1.5
		hwDownstreamPassedBandwidth OBJECT-TYPE
			SYNTAX Counter64
			UNITS "Kbits/s"
			MAX-ACCESS read-only
			STATUS current
			DESCRIPTION
				"Permitted downstream traffic."
			::= { hwSpsLinkBandwidthEntry 5 }


--         1.3.6.1.4.1.2011.6.122.20.2.3.11.1.6
-- 1.3.6.1.4.1.2011.6.122.20.2.3.11.1.6
-- 1.3.6.1.4.1.2011.6.122.20.2.3.11.1.6
-- 1.3.6.1.4.1.2011.6.122.20.2.3.11.1.6
-- 1.3.6.1.4.1.2011.6.122.20.2.3.11.1.6
-- 1.3.6.1.4.1.2011.6.122.20.2.3.11.1.6
-- 1.3.6.1.4.1.2011.6.122.20.2.3.11.1.6
-- 1.3.6.1.4.1.2011.6.122.20.2.3.11.1.6
		-- 1.3.6.1.4.1.2011.6.122.20.2.3.11.1.6
		hwUpstreamDiscardedBandwidth OBJECT-TYPE
			SYNTAX Counter64
			UNITS "Kbits/s"
			MAX-ACCESS read-only
			STATUS current
			DESCRIPTION
				"Discarded upstream traffic."
			::= { hwSpsLinkBandwidthEntry 6 }


--         1.3.6.1.4.1.2011.6.122.20.2.3.11.1.7
-- 1.3.6.1.4.1.2011.6.122.20.2.3.11.1.7
-- 1.3.6.1.4.1.2011.6.122.20.2.3.11.1.7
-- 1.3.6.1.4.1.2011.6.122.20.2.3.11.1.7
-- 1.3.6.1.4.1.2011.6.122.20.2.3.11.1.7
-- 1.3.6.1.4.1.2011.6.122.20.2.3.11.1.7
-- 1.3.6.1.4.1.2011.6.122.20.2.3.11.1.7
-- 1.3.6.1.4.1.2011.6.122.20.2.3.11.1.7
		-- 1.3.6.1.4.1.2011.6.122.20.2.3.11.1.7
		hwDownstreamDiscardedBandwidth OBJECT-TYPE
			SYNTAX Counter64
			UNITS "Kbits/s"
			MAX-ACCESS read-only
			STATUS current
			DESCRIPTION
				"Discarded downstream traffic."
			::= { hwSpsLinkBandwidthEntry 7 }


--         1.3.6.1.4.1.2011.6.122.20.2.4
-- 1.3.6.1.4.1.2011.6.122.20.2.4
-- 1.3.6.1.4.1.2011.6.122.20.2.4
-- 1.3.6.1.4.1.2011.6.122.20.2.4
-- 1.3.6.1.4.1.2011.6.122.20.2.4
-- 1.3.6.1.4.1.2011.6.122.20.2.4
-- 1.3.6.1.4.1.2011.6.122.20.2.4
-- 1.3.6.1.4.1.2011.6.122.20.2.4
		-- 1.3.6.1.4.1.2011.6.122.20.2.4
		hwServiceWirelessTrap OBJECT IDENTIFIER ::= { hwServiceObject 4 }


--         1.3.6.1.4.1.2011.6.122.20.2.4.1
-- 1.3.6.1.4.1.2011.6.122.20.2.4.1
-- 1.3.6.1.4.1.2011.6.122.20.2.4.1
-- 1.3.6.1.4.1.2011.6.122.20.2.4.1
-- 1.3.6.1.4.1.2011.6.122.20.2.4.1
-- 1.3.6.1.4.1.2011.6.122.20.2.4.1
-- 1.3.6.1.4.1.2011.6.122.20.2.4.1
-- 1.3.6.1.4.1.2011.6.122.20.2.4.1
		-- 1.3.6.1.4.1.2011.6.122.20.2.4.1
		hwCGConnectDownTrap NOTIFICATION-TYPE
			OBJECTS { hwSASLocationConnectCG, hwCGIPAddress, hwCGPort, hwCGGrade }
			STATUS current
			DESCRIPTION
				"Description."
			::= { hwServiceWirelessTrap 1 }


--         1.3.6.1.4.1.2011.6.122.20.2.4.2
-- 1.3.6.1.4.1.2011.6.122.20.2.4.2
-- 1.3.6.1.4.1.2011.6.122.20.2.4.2
-- 1.3.6.1.4.1.2011.6.122.20.2.4.2
-- 1.3.6.1.4.1.2011.6.122.20.2.4.2
-- 1.3.6.1.4.1.2011.6.122.20.2.4.2
-- 1.3.6.1.4.1.2011.6.122.20.2.4.2
-- 1.3.6.1.4.1.2011.6.122.20.2.4.2
		-- 1.3.6.1.4.1.2011.6.122.20.2.4.2
		hwCGConnectUpTrap NOTIFICATION-TYPE
			OBJECTS { hwSASLocationConnectCG, hwCGIPAddress, hwCGPort, hwCGGrade }
			STATUS current
			DESCRIPTION
				"Description."
			::= { hwServiceWirelessTrap 2 }


--         1.3.6.1.4.1.2011.6.122.20.2.4.3
-- 1.3.6.1.4.1.2011.6.122.20.2.4.3
-- 1.3.6.1.4.1.2011.6.122.20.2.4.3
-- 1.3.6.1.4.1.2011.6.122.20.2.4.3
-- 1.3.6.1.4.1.2011.6.122.20.2.4.3
-- 1.3.6.1.4.1.2011.6.122.20.2.4.3
-- 1.3.6.1.4.1.2011.6.122.20.2.4.3
-- 1.3.6.1.4.1.2011.6.122.20.2.4.3
		-- 1.3.6.1.4.1.2011.6.122.20.2.4.3
		hwCGCdrMemOverloadTrap NOTIFICATION-TYPE
			OBJECTS { hwSASLocationConnectCG, hwCGCdrCachePoolUsed }
			STATUS current
			DESCRIPTION
				"Description."
			::= { hwServiceWirelessTrap 3 }


--         1.3.6.1.4.1.2011.6.122.20.2.4.4
-- 1.3.6.1.4.1.2011.6.122.20.2.4.4
-- 1.3.6.1.4.1.2011.6.122.20.2.4.4
-- 1.3.6.1.4.1.2011.6.122.20.2.4.4
-- 1.3.6.1.4.1.2011.6.122.20.2.4.4
-- 1.3.6.1.4.1.2011.6.122.20.2.4.4
-- 1.3.6.1.4.1.2011.6.122.20.2.4.4
-- 1.3.6.1.4.1.2011.6.122.20.2.4.4
		-- 1.3.6.1.4.1.2011.6.122.20.2.4.4
		hwCGCdrMemChangeToNormalTrap NOTIFICATION-TYPE
			OBJECTS { hwSASLocationConnectCG, hwCGCdrCachePoolUsed }
			STATUS current
			DESCRIPTION
				"Description."
			::= { hwServiceWirelessTrap 4 }


--         1.3.6.1.4.1.2011.6.122.20.2.4.5
-- 1.3.6.1.4.1.2011.6.122.20.2.4.5
-- 1.3.6.1.4.1.2011.6.122.20.2.4.5
-- 1.3.6.1.4.1.2011.6.122.20.2.4.5
-- 1.3.6.1.4.1.2011.6.122.20.2.4.5
-- 1.3.6.1.4.1.2011.6.122.20.2.4.5
-- 1.3.6.1.4.1.2011.6.122.20.2.4.5
-- 1.3.6.1.4.1.2011.6.122.20.2.4.5
		-- 1.3.6.1.4.1.2011.6.122.20.2.4.5
		hwCGCdrPoolFullTrap NOTIFICATION-TYPE
			OBJECTS { hwSASLocationConnectCG, hwCGCdrCachePoolUsed }
			STATUS current
			DESCRIPTION
				"Description."
			::= { hwServiceWirelessTrap 5 }


--         1.3.6.1.4.1.2011.6.122.20.2.4.6
-- 1.3.6.1.4.1.2011.6.122.20.2.4.6
-- 1.3.6.1.4.1.2011.6.122.20.2.4.6
-- 1.3.6.1.4.1.2011.6.122.20.2.4.6
-- 1.3.6.1.4.1.2011.6.122.20.2.4.6
-- 1.3.6.1.4.1.2011.6.122.20.2.4.6
-- 1.3.6.1.4.1.2011.6.122.20.2.4.6
-- 1.3.6.1.4.1.2011.6.122.20.2.4.6
		-- 1.3.6.1.4.1.2011.6.122.20.2.4.6
		hwCGCdrPoolFullClearedTrap NOTIFICATION-TYPE
			OBJECTS { hwSASLocationConnectCG, hwCGCdrCachePoolUsed }
			STATUS current
			DESCRIPTION
				"Description."
			::= { hwServiceWirelessTrap 6 }


--         1.3.6.1.4.1.2011.6.122.20.2.4.7
-- 1.3.6.1.4.1.2011.6.122.20.2.4.7
-- 1.3.6.1.4.1.2011.6.122.20.2.4.7
-- 1.3.6.1.4.1.2011.6.122.20.2.4.7
-- 1.3.6.1.4.1.2011.6.122.20.2.4.7
-- 1.3.6.1.4.1.2011.6.122.20.2.4.7
-- 1.3.6.1.4.1.2011.6.122.20.2.4.7
-- 1.3.6.1.4.1.2011.6.122.20.2.4.7
		-- 1.3.6.1.4.1.2011.6.122.20.2.4.7
		hwPCRFConnectDownTrap NOTIFICATION-TYPE
			OBJECTS { hwSASLocationConnectPCRF, hwPCRFHostName, hwPCRFIPAddress, hwPCRFPort, hwSASNameConnectPCRF,
				hwSASIPAddressConnectPCRF, hwSASPortConnectPCRF }
			STATUS current
			DESCRIPTION
				"Description."
			::= { hwServiceWirelessTrap 7 }


--         1.3.6.1.4.1.2011.6.122.20.2.4.8
-- 1.3.6.1.4.1.2011.6.122.20.2.4.8
-- 1.3.6.1.4.1.2011.6.122.20.2.4.8
-- 1.3.6.1.4.1.2011.6.122.20.2.4.8
-- 1.3.6.1.4.1.2011.6.122.20.2.4.8
-- 1.3.6.1.4.1.2011.6.122.20.2.4.8
-- 1.3.6.1.4.1.2011.6.122.20.2.4.8
-- 1.3.6.1.4.1.2011.6.122.20.2.4.8
		-- 1.3.6.1.4.1.2011.6.122.20.2.4.8
		hwPCRFConnectUpTrap NOTIFICATION-TYPE
			OBJECTS { hwSASLocationConnectPCRF, hwPCRFHostName, hwPCRFIPAddress, hwPCRFPort, hwSASNameConnectPCRF,
				hwSASIPAddressConnectPCRF, hwSASPortConnectPCRF }
			STATUS current
			DESCRIPTION
				"Description."
			::= { hwServiceWirelessTrap 8 }


--         1.3.6.1.4.1.2011.6.122.20.2.4.9
-- 1.3.6.1.4.1.2011.6.122.20.2.4.9
-- 1.3.6.1.4.1.2011.6.122.20.2.4.9
-- 1.3.6.1.4.1.2011.6.122.20.2.4.9
-- 1.3.6.1.4.1.2011.6.122.20.2.4.9
-- 1.3.6.1.4.1.2011.6.122.20.2.4.9
-- 1.3.6.1.4.1.2011.6.122.20.2.4.9
-- 1.3.6.1.4.1.2011.6.122.20.2.4.9
		-- 1.3.6.1.4.1.2011.6.122.20.2.4.9
		hwOCSConnectDownTrap NOTIFICATION-TYPE
			OBJECTS { hwSASLocationConnectOCS, hwOCSHostName, hwOCSIPAddress, hwOCSPort, hwSASNameConnectOCS,
				hwSASIPAddressConnectOCS, hwSASPortConnectOCS }
			STATUS current
			DESCRIPTION
				"Description."
			::= { hwServiceWirelessTrap 9 }


--         1.3.6.1.4.1.2011.6.122.20.2.4.10
-- 1.3.6.1.4.1.2011.6.122.20.2.4.10
-- 1.3.6.1.4.1.2011.6.122.20.2.4.10
-- 1.3.6.1.4.1.2011.6.122.20.2.4.10
-- 1.3.6.1.4.1.2011.6.122.20.2.4.10
-- 1.3.6.1.4.1.2011.6.122.20.2.4.10
-- 1.3.6.1.4.1.2011.6.122.20.2.4.10
-- 1.3.6.1.4.1.2011.6.122.20.2.4.10
		-- 1.3.6.1.4.1.2011.6.122.20.2.4.10
		hwOCSConnectUpTrap NOTIFICATION-TYPE
			OBJECTS { hwSASLocationConnectOCS, hwOCSHostName, hwOCSIPAddress, hwOCSPort, hwSASNameConnectOCS,
				hwSASIPAddressConnectOCS, hwSASPortConnectOCS }
			STATUS current
			DESCRIPTION
				"Description."
			::= { hwServiceWirelessTrap 10 }


--         1.3.6.1.4.1.2011.6.122.20.2.4.11
-- 1.3.6.1.4.1.2011.6.122.20.2.4.11
-- 1.3.6.1.4.1.2011.6.122.20.2.4.11
-- 1.3.6.1.4.1.2011.6.122.20.2.4.11
-- 1.3.6.1.4.1.2011.6.122.20.2.4.11
-- 1.3.6.1.4.1.2011.6.122.20.2.4.11
-- 1.3.6.1.4.1.2011.6.122.20.2.4.11
-- 1.3.6.1.4.1.2011.6.122.20.2.4.11
		-- 1.3.6.1.4.1.2011.6.122.20.2.4.11
		hwDRAConnectDownTrap NOTIFICATION-TYPE
			OBJECTS { hwSASLocationConnectDRA, hwDRAHostName, hwDRAIPAddress, hwDRAPort, hwSASNameConnectDRA,
				hwSASIPAddressConnectDRA, hwSASPortConnectDRA }
			STATUS current
			DESCRIPTION
				"Description."
			::= { hwServiceWirelessTrap 11 }


--         1.3.6.1.4.1.2011.6.122.20.2.4.12
-- 1.3.6.1.4.1.2011.6.122.20.2.4.12
-- 1.3.6.1.4.1.2011.6.122.20.2.4.12
-- 1.3.6.1.4.1.2011.6.122.20.2.4.12
-- 1.3.6.1.4.1.2011.6.122.20.2.4.12
-- 1.3.6.1.4.1.2011.6.122.20.2.4.12
-- 1.3.6.1.4.1.2011.6.122.20.2.4.12
-- 1.3.6.1.4.1.2011.6.122.20.2.4.12
		-- 1.3.6.1.4.1.2011.6.122.20.2.4.12
		hwDRAConnectUpTrap NOTIFICATION-TYPE
			OBJECTS { hwSASLocationConnectDRA, hwDRAHostName, hwDRAIPAddress, hwDRAPort, hwSASNameConnectDRA,
				hwSASIPAddressConnectDRA, hwSASPortConnectDRA }
			STATUS current
			DESCRIPTION
				"Description."
			::= { hwServiceWirelessTrap 12 }


--         1.3.6.1.4.1.2011.6.122.20.2.5
-- 1.3.6.1.4.1.2011.6.122.20.2.5
-- 1.3.6.1.4.1.2011.6.122.20.2.5
-- 1.3.6.1.4.1.2011.6.122.20.2.5
-- 1.3.6.1.4.1.2011.6.122.20.2.5
-- 1.3.6.1.4.1.2011.6.122.20.2.5
-- 1.3.6.1.4.1.2011.6.122.20.2.5
-- 1.3.6.1.4.1.2011.6.122.20.2.5
		-- 1.3.6.1.4.1.2011.6.122.20.2.5
		hwServiceVoIPObject OBJECT IDENTIFIER ::= { hwServiceObject 5 }


--         1.3.6.1.4.1.2011.6.122.20.2.6
-- 1.3.6.1.4.1.2011.6.122.20.2.6
-- 1.3.6.1.4.1.2011.6.122.20.2.6
-- 1.3.6.1.4.1.2011.6.122.20.2.6
-- 1.3.6.1.4.1.2011.6.122.20.2.6
-- 1.3.6.1.4.1.2011.6.122.20.2.6
-- 1.3.6.1.4.1.2011.6.122.20.2.6
-- 1.3.6.1.4.1.2011.6.122.20.2.6
		-- 1.3.6.1.4.1.2011.6.122.20.2.6
		hwServiceDDoSObject OBJECT IDENTIFIER ::= { hwServiceObject 6 }


--         1.3.6.1.4.1.2011.6.122.20.2.7
-- 1.3.6.1.4.1.2011.6.122.20.2.7
-- 1.3.6.1.4.1.2011.6.122.20.2.7
-- 1.3.6.1.4.1.2011.6.122.20.2.7
-- 1.3.6.1.4.1.2011.6.122.20.2.7
-- 1.3.6.1.4.1.2011.6.122.20.2.7
-- 1.3.6.1.4.1.2011.6.122.20.2.7
-- 1.3.6.1.4.1.2011.6.122.20.2.7
		-- 1.3.6.1.4.1.2011.6.122.20.2.7
		hwServiceTrap OBJECT IDENTIFIER ::= { hwServiceObject 7 }


--         1.3.6.1.4.1.2011.6.122.20.2.7.1
-- 1.3.6.1.4.1.2011.6.122.20.2.7.1
-- 1.3.6.1.4.1.2011.6.122.20.2.7.1
-- 1.3.6.1.4.1.2011.6.122.20.2.7.1
-- 1.3.6.1.4.1.2011.6.122.20.2.7.1
-- 1.3.6.1.4.1.2011.6.122.20.2.7.1
-- 1.3.6.1.4.1.2011.6.122.20.2.7.1
-- 1.3.6.1.4.1.2011.6.122.20.2.7.1
		-- 1.3.6.1.4.1.2011.6.122.20.2.7.1
		hwServiceTrapVB OBJECT IDENTIFIER ::= { hwServiceTrap 1 }


--         1.3.6.1.4.1.2011.6.122.20.2.7.1.1
-- 1.3.6.1.4.1.2011.6.122.20.2.7.1.1
-- 1.3.6.1.4.1.2011.6.122.20.2.7.1.1
-- 1.3.6.1.4.1.2011.6.122.20.2.7.1.1
-- 1.3.6.1.4.1.2011.6.122.20.2.7.1.1
-- 1.3.6.1.4.1.2011.6.122.20.2.7.1.1
-- 1.3.6.1.4.1.2011.6.122.20.2.7.1.1
-- 1.3.6.1.4.1.2011.6.122.20.2.7.1.1
		-- 1.3.6.1.4.1.2011.6.122.20.2.7.1.1
		hwServiceResourceLocation OBJECT-TYPE
			SYNTAX OCTET STRING
			MAX-ACCESS read-only
			STATUS current
			DESCRIPTION
				"Description."
			::= { hwServiceTrapVB 1 }


--         1.3.6.1.4.1.2011.6.122.20.2.7.1.2
-- 1.3.6.1.4.1.2011.6.122.20.2.7.1.2
-- 1.3.6.1.4.1.2011.6.122.20.2.7.1.2
-- 1.3.6.1.4.1.2011.6.122.20.2.7.1.2
-- 1.3.6.1.4.1.2011.6.122.20.2.7.1.2
-- 1.3.6.1.4.1.2011.6.122.20.2.7.1.2
-- 1.3.6.1.4.1.2011.6.122.20.2.7.1.2
-- 1.3.6.1.4.1.2011.6.122.20.2.7.1.2
		-- 1.3.6.1.4.1.2011.6.122.20.2.7.1.2
		hwServiceResourceType OBJECT-TYPE
			SYNTAX OCTET STRING
			MAX-ACCESS read-only
			STATUS current
			DESCRIPTION
				"Description."
			::= { hwServiceTrapVB 2 }


--         1.3.6.1.4.1.2011.6.122.20.2.7.1.3
-- 1.3.6.1.4.1.2011.6.122.20.2.7.1.3
-- 1.3.6.1.4.1.2011.6.122.20.2.7.1.3
-- 1.3.6.1.4.1.2011.6.122.20.2.7.1.3
-- 1.3.6.1.4.1.2011.6.122.20.2.7.1.3
-- 1.3.6.1.4.1.2011.6.122.20.2.7.1.3
-- 1.3.6.1.4.1.2011.6.122.20.2.7.1.3
-- 1.3.6.1.4.1.2011.6.122.20.2.7.1.3
		-- 1.3.6.1.4.1.2011.6.122.20.2.7.1.3
		hwServiceResourceUsage OBJECT-TYPE
			SYNTAX Integer32
			MAX-ACCESS read-only
			STATUS current
			DESCRIPTION
				"Description."
			::= { hwServiceTrapVB 3 }


--         1.3.6.1.4.1.2011.6.122.20.2.7.1.4
-- 1.3.6.1.4.1.2011.6.122.20.2.7.1.4
-- 1.3.6.1.4.1.2011.6.122.20.2.7.1.4
-- 1.3.6.1.4.1.2011.6.122.20.2.7.1.4
-- 1.3.6.1.4.1.2011.6.122.20.2.7.1.4
-- 1.3.6.1.4.1.2011.6.122.20.2.7.1.4
-- 1.3.6.1.4.1.2011.6.122.20.2.7.1.4
-- 1.3.6.1.4.1.2011.6.122.20.2.7.1.4
		-- 1.3.6.1.4.1.2011.6.122.20.2.7.1.4
		hwServiceResourceVcpuId OBJECT-TYPE
			SYNTAX Integer32
			MAX-ACCESS read-only
			STATUS current
			DESCRIPTION
				"Description."
			::= { hwServiceTrapVB 4 }


--         1.3.6.1.4.1.2011.6.122.20.2.7.1.5
-- 1.3.6.1.4.1.2011.6.122.20.2.7.1.5
-- 1.3.6.1.4.1.2011.6.122.20.2.7.1.5
-- 1.3.6.1.4.1.2011.6.122.20.2.7.1.5
-- 1.3.6.1.4.1.2011.6.122.20.2.7.1.5
-- 1.3.6.1.4.1.2011.6.122.20.2.7.1.5
-- 1.3.6.1.4.1.2011.6.122.20.2.7.1.5
-- 1.3.6.1.4.1.2011.6.122.20.2.7.1.5
		-- 1.3.6.1.4.1.2011.6.122.20.2.7.1.5
		hwCollectorIP OBJECT-TYPE
			SYNTAX IpAddress
			MAX-ACCESS read-write
			STATUS current
			DESCRIPTION
				"Description."
			::= { hwServiceTrapVB 5 }


--         1.3.6.1.4.1.2011.6.122.20.2.7.1.6
-- 1.3.6.1.4.1.2011.6.122.20.2.7.1.6
-- 1.3.6.1.4.1.2011.6.122.20.2.7.1.6
-- 1.3.6.1.4.1.2011.6.122.20.2.7.1.6
-- 1.3.6.1.4.1.2011.6.122.20.2.7.1.6
-- 1.3.6.1.4.1.2011.6.122.20.2.7.1.6
-- 1.3.6.1.4.1.2011.6.122.20.2.7.1.6
-- 1.3.6.1.4.1.2011.6.122.20.2.7.1.6
		-- 1.3.6.1.4.1.2011.6.122.20.2.7.1.6
		hwCollectorPort OBJECT-TYPE
			SYNTAX Gauge32 (1..65535)
			MAX-ACCESS read-write
			STATUS current
			DESCRIPTION
				"Description."
			::= { hwServiceTrapVB 6 }


--         1.3.6.1.4.1.2011.6.122.20.2.7.1.7
-- 1.3.6.1.4.1.2011.6.122.20.2.7.1.7
-- 1.3.6.1.4.1.2011.6.122.20.2.7.1.7
-- 1.3.6.1.4.1.2011.6.122.20.2.7.1.7
-- 1.3.6.1.4.1.2011.6.122.20.2.7.1.7
-- 1.3.6.1.4.1.2011.6.122.20.2.7.1.7
-- 1.3.6.1.4.1.2011.6.122.20.2.7.1.7
-- 1.3.6.1.4.1.2011.6.122.20.2.7.1.7
		-- 1.3.6.1.4.1.2011.6.122.20.2.7.1.7
		hwInterfaceList OBJECT-TYPE
			SYNTAX OCTET STRING
			MAX-ACCESS read-only
			STATUS current
			DESCRIPTION
				"Description."
			DEFVAL { "NULL" }
			::= { hwServiceTrapVB 7 }


--         1.3.6.1.4.1.2011.6.122.20.2.7.1.8
-- 1.3.6.1.4.1.2011.6.122.20.2.7.1.8
-- 1.3.6.1.4.1.2011.6.122.20.2.7.1.8
-- 1.3.6.1.4.1.2011.6.122.20.2.7.1.8
-- 1.3.6.1.4.1.2011.6.122.20.2.7.1.8
-- 1.3.6.1.4.1.2011.6.122.20.2.7.1.8
-- 1.3.6.1.4.1.2011.6.122.20.2.7.1.8
-- 1.3.6.1.4.1.2011.6.122.20.2.7.1.8
		-- 1.3.6.1.4.1.2011.6.122.20.2.7.1.8
		hwRecoverTrapCause OBJECT-TYPE
			SYNTAX OCTET STRING
			MAX-ACCESS read-only
			STATUS current
			DESCRIPTION
				"Description."
			DEFVAL { "consistent" }
			::= { hwServiceTrapVB 8 }


--         1.3.6.1.4.1.2011.6.122.20.2.7.1.9
-- 1.3.6.1.4.1.2011.6.122.20.2.7.1.9
-- 1.3.6.1.4.1.2011.6.122.20.2.7.1.9
-- 1.3.6.1.4.1.2011.6.122.20.2.7.1.9
-- 1.3.6.1.4.1.2011.6.122.20.2.7.1.9
-- 1.3.6.1.4.1.2011.6.122.20.2.7.1.9
-- 1.3.6.1.4.1.2011.6.122.20.2.7.1.9
-- 1.3.6.1.4.1.2011.6.122.20.2.7.1.9
		-- 1.3.6.1.4.1.2011.6.122.20.2.7.1.9
		hwSpammerFTPServeIP OBJECT-TYPE
			SYNTAX IpAddress
			MAX-ACCESS read-write
			STATUS current
			DESCRIPTION
				"Description."
			::= { hwServiceTrapVB 9 }


--         1.3.6.1.4.1.2011.6.122.20.2.7.1.10
-- 1.3.6.1.4.1.2011.6.122.20.2.7.1.10
-- 1.3.6.1.4.1.2011.6.122.20.2.7.1.10
-- 1.3.6.1.4.1.2011.6.122.20.2.7.1.10
-- 1.3.6.1.4.1.2011.6.122.20.2.7.1.10
-- 1.3.6.1.4.1.2011.6.122.20.2.7.1.10
-- 1.3.6.1.4.1.2011.6.122.20.2.7.1.10
-- 1.3.6.1.4.1.2011.6.122.20.2.7.1.10
		-- 1.3.6.1.4.1.2011.6.122.20.2.7.1.10
		hwSpammerFTPServePort OBJECT-TYPE
			SYNTAX Gauge32 (1..65535)
			MAX-ACCESS read-write
			STATUS current
			DESCRIPTION
				"Description."
			::= { hwServiceTrapVB 10 }


--  1.3.6.1.4.1.2011.6.122.20.2.7.1.11
		-- 1.3.6.1.4.1.2011.6.122.20.2.7.1.11
		hwCAExpireTime OBJECT-TYPE
			SYNTAX OCTET STRING (SIZE (0..255))
			MAX-ACCESS read-only
			STATUS current
			DESCRIPTION
				"Expiration time of the certificate used for communication between the QoE board and the SIG Back End."
			::= { hwServiceTrapVB 11 }


--         1.3.6.1.4.1.2011.6.122.20.2.7.2
-- 1.3.6.1.4.1.2011.6.122.20.2.7.2
-- 1.3.6.1.4.1.2011.6.122.20.2.7.2
-- 1.3.6.1.4.1.2011.6.122.20.2.7.2
-- 1.3.6.1.4.1.2011.6.122.20.2.7.2
-- 1.3.6.1.4.1.2011.6.122.20.2.7.2
-- 1.3.6.1.4.1.2011.6.122.20.2.7.2
-- 1.3.6.1.4.1.2011.6.122.20.2.7.2
		-- 1.3.6.1.4.1.2011.6.122.20.2.7.2
		hwServiceTrapConfig OBJECT IDENTIFIER ::= { hwServiceTrap 2 }


--         1.3.6.1.4.1.2011.6.122.20.2.7.2.1
-- 1.3.6.1.4.1.2011.6.122.20.2.7.2.1
-- 1.3.6.1.4.1.2011.6.122.20.2.7.2.1
-- 1.3.6.1.4.1.2011.6.122.20.2.7.2.1
-- 1.3.6.1.4.1.2011.6.122.20.2.7.2.1
-- 1.3.6.1.4.1.2011.6.122.20.2.7.2.1
-- 1.3.6.1.4.1.2011.6.122.20.2.7.2.1
-- 1.3.6.1.4.1.2011.6.122.20.2.7.2.1
		-- 1.3.6.1.4.1.2011.6.122.20.2.7.2.1
		hwCpuBeyondThresholdTrap NOTIFICATION-TYPE
			OBJECTS { hwServiceResourceLocation, hwServiceResourceType, hwServiceResourceUsage, hwServiceResourceVcpuId }
			STATUS current
			DESCRIPTION
				"The CPU usage of an SPS or SAS exceeds the upper threshold."
			::= { hwServiceTrapConfig 1 }


--         1.3.6.1.4.1.2011.6.122.20.2.7.2.2
-- 1.3.6.1.4.1.2011.6.122.20.2.7.2.2
-- 1.3.6.1.4.1.2011.6.122.20.2.7.2.2
-- 1.3.6.1.4.1.2011.6.122.20.2.7.2.2
-- 1.3.6.1.4.1.2011.6.122.20.2.7.2.2
-- 1.3.6.1.4.1.2011.6.122.20.2.7.2.2
-- 1.3.6.1.4.1.2011.6.122.20.2.7.2.2
-- 1.3.6.1.4.1.2011.6.122.20.2.7.2.2
		-- 1.3.6.1.4.1.2011.6.122.20.2.7.2.2
		hwCpuChangeToNormalTrap NOTIFICATION-TYPE
			OBJECTS { hwServiceResourceLocation, hwServiceResourceType, hwServiceResourceUsage, hwServiceResourceVcpuId }
			STATUS current
			DESCRIPTION
				"The CPU usage of an SPS or SAS falls below the lower threshold."
			::= { hwServiceTrapConfig 2 }


--         1.3.6.1.4.1.2011.6.122.20.2.7.2.3
-- 1.3.6.1.4.1.2011.6.122.20.2.7.2.3
-- 1.3.6.1.4.1.2011.6.122.20.2.7.2.3
-- 1.3.6.1.4.1.2011.6.122.20.2.7.2.3
-- 1.3.6.1.4.1.2011.6.122.20.2.7.2.3
-- 1.3.6.1.4.1.2011.6.122.20.2.7.2.3
-- 1.3.6.1.4.1.2011.6.122.20.2.7.2.3
-- 1.3.6.1.4.1.2011.6.122.20.2.7.2.3
		-- 1.3.6.1.4.1.2011.6.122.20.2.7.2.3
		hwMemoryBeyondThresholdTrap NOTIFICATION-TYPE
			OBJECTS { hwServiceResourceLocation, hwServiceResourceType, hwServiceResourceUsage }
			STATUS current
			DESCRIPTION
				"The service system generated an alarm when the service resource usage of the corresponding service system exceeded the threshold (90% of the capacity by default and adjustable)."
			::= { hwServiceTrapConfig 3 }


--         1.3.6.1.4.1.2011.6.122.20.2.7.2.4
-- 1.3.6.1.4.1.2011.6.122.20.2.7.2.4
-- 1.3.6.1.4.1.2011.6.122.20.2.7.2.4
-- 1.3.6.1.4.1.2011.6.122.20.2.7.2.4
-- 1.3.6.1.4.1.2011.6.122.20.2.7.2.4
-- 1.3.6.1.4.1.2011.6.122.20.2.7.2.4
-- 1.3.6.1.4.1.2011.6.122.20.2.7.2.4
-- 1.3.6.1.4.1.2011.6.122.20.2.7.2.4
		-- 1.3.6.1.4.1.2011.6.122.20.2.7.2.4
		hwMemoryChangeToNormalTrap NOTIFICATION-TYPE
			OBJECTS { hwServiceResourceLocation, hwServiceResourceType, hwServiceResourceUsage }
			STATUS current
			DESCRIPTION
				"The alarm was cleared when the service resource usage of the corresponding service system restored to the normal range (70% by default and adjustable)."
			::= { hwServiceTrapConfig 4 }


--         1.3.6.1.4.1.2011.6.122.20.2.7.2.5
-- 1.3.6.1.4.1.2011.6.122.20.2.7.2.5
-- 1.3.6.1.4.1.2011.6.122.20.2.7.2.5
-- 1.3.6.1.4.1.2011.6.122.20.2.7.2.5
-- 1.3.6.1.4.1.2011.6.122.20.2.7.2.5
-- 1.3.6.1.4.1.2011.6.122.20.2.7.2.5
-- 1.3.6.1.4.1.2011.6.122.20.2.7.2.5
-- 1.3.6.1.4.1.2011.6.122.20.2.7.2.5
		-- 1.3.6.1.4.1.2011.6.122.20.2.7.2.5
		hwCollectorConnectDownTrap NOTIFICATION-TYPE
			OBJECTS { hwServiceResourceLocation, hwCollectorIP, hwCollectorPort }
			STATUS current
			DESCRIPTION
				"This object indicates that the link between the SPS and collector fails. Possible causes are as follows:
Cause 1: The SPS and collector are disconnected.
Cause 2: The VSUF is faulty.
Cause 3: A software or hardware error occurs on the collector."
			::= { hwServiceTrapConfig 5 }


--         1.3.6.1.4.1.2011.6.122.20.2.7.2.6
-- 1.3.6.1.4.1.2011.6.122.20.2.7.2.6
-- 1.3.6.1.4.1.2011.6.122.20.2.7.2.6
-- 1.3.6.1.4.1.2011.6.122.20.2.7.2.6
-- 1.3.6.1.4.1.2011.6.122.20.2.7.2.6
-- 1.3.6.1.4.1.2011.6.122.20.2.7.2.6
-- 1.3.6.1.4.1.2011.6.122.20.2.7.2.6
-- 1.3.6.1.4.1.2011.6.122.20.2.7.2.6
		-- 1.3.6.1.4.1.2011.6.122.20.2.7.2.6
		hwCollectorConnectUpTrap NOTIFICATION-TYPE
			OBJECTS { hwServiceResourceLocation, hwCollectorIP, hwCollectorPort }
			STATUS current
			DESCRIPTION
				"This object indicates that the link between the SPS and collector recovers."
			::= { hwServiceTrapConfig 6 }


--         1.3.6.1.4.1.2011.6.122.20.2.7.2.7
-- 1.3.6.1.4.1.2011.6.122.20.2.7.2.7
-- 1.3.6.1.4.1.2011.6.122.20.2.7.2.7
-- 1.3.6.1.4.1.2011.6.122.20.2.7.2.7
-- 1.3.6.1.4.1.2011.6.122.20.2.7.2.7
-- 1.3.6.1.4.1.2011.6.122.20.2.7.2.7
-- 1.3.6.1.4.1.2011.6.122.20.2.7.2.7
-- 1.3.6.1.4.1.2011.6.122.20.2.7.2.7
		-- 1.3.6.1.4.1.2011.6.122.20.2.7.2.7
		hwHashModeInconsistentTrap NOTIFICATION-TYPE
			OBJECTS { hwInterfaceList, hwServiceResourceLocation }
			STATUS current
			DESCRIPTION
				"Description."
			::= { hwServiceTrapConfig 7 }


--         1.3.6.1.4.1.2011.6.122.20.2.7.2.8
-- 1.3.6.1.4.1.2011.6.122.20.2.7.2.8
-- 1.3.6.1.4.1.2011.6.122.20.2.7.2.8
-- 1.3.6.1.4.1.2011.6.122.20.2.7.2.8
-- 1.3.6.1.4.1.2011.6.122.20.2.7.2.8
-- 1.3.6.1.4.1.2011.6.122.20.2.7.2.8
-- 1.3.6.1.4.1.2011.6.122.20.2.7.2.8
-- 1.3.6.1.4.1.2011.6.122.20.2.7.2.8
		-- 1.3.6.1.4.1.2011.6.122.20.2.7.2.8
		hwHashModeInconsistentRecoverTrap NOTIFICATION-TYPE
			OBJECTS { hwRecoverTrapCause, hwServiceResourceLocation }
			STATUS current
			DESCRIPTION
				"Description."
			::= { hwServiceTrapConfig 8 }


--         1.3.6.1.4.1.2011.6.122.20.2.7.2.9
-- 1.3.6.1.4.1.2011.6.122.20.2.7.2.9
-- 1.3.6.1.4.1.2011.6.122.20.2.7.2.9
-- 1.3.6.1.4.1.2011.6.122.20.2.7.2.9
-- 1.3.6.1.4.1.2011.6.122.20.2.7.2.9
-- 1.3.6.1.4.1.2011.6.122.20.2.7.2.9
-- 1.3.6.1.4.1.2011.6.122.20.2.7.2.9
-- 1.3.6.1.4.1.2011.6.122.20.2.7.2.9
		-- 1.3.6.1.4.1.2011.6.122.20.2.7.2.9
		hwSpammerFTPDownTrap NOTIFICATION-TYPE
			OBJECTS { hwServiceResourceLocation, hwSpammerFTPServeIP, hwSpammerFTPServePort }
			STATUS current
			DESCRIPTION
				"This object indicates that the link between the SPS and Spammer FTP server fails."
			::= { hwServiceTrapConfig 9 }


--         1.3.6.1.4.1.2011.6.122.20.2.7.2.10
-- 1.3.6.1.4.1.2011.6.122.20.2.7.2.10
-- 1.3.6.1.4.1.2011.6.122.20.2.7.2.10
-- 1.3.6.1.4.1.2011.6.122.20.2.7.2.10
-- 1.3.6.1.4.1.2011.6.122.20.2.7.2.10
-- 1.3.6.1.4.1.2011.6.122.20.2.7.2.10
-- 1.3.6.1.4.1.2011.6.122.20.2.7.2.10
-- 1.3.6.1.4.1.2011.6.122.20.2.7.2.10
		-- 1.3.6.1.4.1.2011.6.122.20.2.7.2.10
		hwSpammerFTPUpTrap NOTIFICATION-TYPE
			OBJECTS { hwServiceResourceLocation, hwSpammerFTPServeIP, hwSpammerFTPServePort }
			STATUS current
			DESCRIPTION
				"This object indicates that the link between the SPS and Spammer FTP server recovers."
			::= { hwServiceTrapConfig 10 }


--         1.3.6.1.4.1.2011.6.122.20.2.7.2.11
-- 1.3.6.1.4.1.2011.6.122.20.2.7.2.11
-- 1.3.6.1.4.1.2011.6.122.20.2.7.2.11
-- 1.3.6.1.4.1.2011.6.122.20.2.7.2.11
-- 1.3.6.1.4.1.2011.6.122.20.2.7.2.11
-- 1.3.6.1.4.1.2011.6.122.20.2.7.2.11
-- 1.3.6.1.4.1.2011.6.122.20.2.7.2.11
-- 1.3.6.1.4.1.2011.6.122.20.2.7.2.11
		-- 1.3.6.1.4.1.2011.6.122.20.2.7.2.11
		hwIPDbtOverLoadTrap NOTIFICATION-TYPE
			OBJECTS { hwServiceResourceLocation }
			STATUS current
			DESCRIPTION
				"The distributed traffic control service for individual users on the SAS is overloaded."
			::= { hwServiceTrapConfig 11 }


--         1.3.6.1.4.1.2011.6.122.20.2.7.2.12
-- 1.3.6.1.4.1.2011.6.122.20.2.7.2.12
-- 1.3.6.1.4.1.2011.6.122.20.2.7.2.12
-- 1.3.6.1.4.1.2011.6.122.20.2.7.2.12
-- 1.3.6.1.4.1.2011.6.122.20.2.7.2.12
-- 1.3.6.1.4.1.2011.6.122.20.2.7.2.12
-- 1.3.6.1.4.1.2011.6.122.20.2.7.2.12
-- 1.3.6.1.4.1.2011.6.122.20.2.7.2.12
		-- 1.3.6.1.4.1.2011.6.122.20.2.7.2.12
		hwIPDbtOverLoadRecoverTrap NOTIFICATION-TYPE
			OBJECTS { hwServiceResourceLocation }
			STATUS current
			DESCRIPTION
				"The overload alarm of the distributed traffic control service for individual users on the SAS is cleared."
			::= { hwServiceTrapConfig 12 }


--  1.3.6.1.4.1.2011.6.122.20.2.7.2.13
		-- 1.3.6.1.4.1.2011.6.122.20.2.7.2.13
		hwCABeforeExpiredTrap NOTIFICATION-TYPE
			OBJECTS { hwClusterNodeName, hwClusterNodeIPAddress, hwCAExpireTime }
			STATUS current
			DESCRIPTION
				"Certificate to be expired alarm."
			::= { hwServiceTrapConfig 13 }


--  1.3.6.1.4.1.2011.6.122.20.2.7.2.14
		-- 1.3.6.1.4.1.2011.6.122.20.2.7.2.14
		hwCAExpiredTrap NOTIFICATION-TYPE
			OBJECTS { hwClusterNodeName, hwClusterNodeIPAddress }
			STATUS current
			DESCRIPTION
				"Certificate expired alarm."
			::= { hwServiceTrapConfig 14 }


--         1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
		-- 1.3.6.1.4.1.2011.6.122.20.2.8
		hwExtendedFeatureTrap OBJECT IDENTIFIER ::= { hwServiceObject 8 }


--         1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
		-- 1.3.6.1.4.1.2011.6.122.20.2.8.1
		hwExtendedFeatureTrapVB OBJECT IDENTIFIER ::= { hwExtendedFeatureTrap 1 }


--         1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
		-- 1.3.6.1.4.1.2011.6.122.20.2.8.1.1
		hwExtendedFeatureLocation OBJECT-TYPE
			SYNTAX OCTET STRING
			MAX-ACCESS read-only
			STATUS current
			DESCRIPTION
				"Location of the extended feature"
			::= { hwExtendedFeatureTrapVB 1 }


--         1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
		-- 1.3.6.1.4.1.2011.6.122.20.2.8.1.2
		hwExtendedFeatureType OBJECT-TYPE
			SYNTAX OCTET STRING
			MAX-ACCESS read-only
			STATUS current
			DESCRIPTION
				"Type of the extended feature"
			::= { hwExtendedFeatureTrapVB 2 }


--         1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
		-- 1.3.6.1.4.1.2011.6.122.20.2.8.2
		hwExtendedModuleTrapConfig OBJECT IDENTIFIER ::= { hwExtendedFeatureTrap 2 }


--         1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
		-- 1.3.6.1.4.1.2011.6.122.20.2.8.2.1
		hwNeedResetForFeatureLoadTrap NOTIFICATION-TYPE
			OBJECTS { hwExtendedFeatureLocation, hwExtendedFeatureType }
			STATUS current
			DESCRIPTION
				"In scenarios where the flow data record or QoE analysis service is disabled, the SPU is not restarted after the extended-package load command (for loading the expansion package) or the fdr enable command is executed. In this case, the system generates this trap every one hour to remind the user to restart the SPU."
			::= { hwExtendedModuleTrapConfig 1 }


--         1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
		-- 1.3.6.1.4.1.2011.6.122.20.2.8.2.3
		hwNeedResetForFeatureUnloadTrap NOTIFICATION-TYPE
			OBJECTS { hwExtendedFeatureLocation, hwExtendedFeatureType }
			STATUS current
			DESCRIPTION
				"In scenarios where the flow data record or QoE analysis service is enabled through the CLI, the SPU is not restarted after the undo extended-package load command (for uninstalling the expansion package) or the undo fdr enable command is executed. In this case, the system generates this trap every one hour to remind the user to restart the SPU."
			::= { hwExtendedModuleTrapConfig 3 }


--         1.3.6.1.4.1.2011.6.122.20.2.8.2.5
-- 1.3.6.1.4.1.2011.6.122.20.2.8.2.5
-- 1.3.6.1.4.1.2011.6.122.20.2.8.2.5
-- 1.3.6.1.4.1.2011.6.122.20.2.8.2.5
-- 1.3.6.1.4.1.2011.6.122.20.2.8.2.5
-- 1.3.6.1.4.1.2011.6.122.20.2.8.2.5
-- 1.3.6.1.4.1.2011.6.122.20.2.8.2.5
-- 1.3.6.1.4.1.2011.6.122.20.2.8.2.5
		-- 1.3.6.1.4.1.2011.6.122.20.2.8.2.5
		hwNeedResetForFdrMemallocTrap NOTIFICATION-TYPE
			OBJECTS { hwExtendedFeatureLocation }
			STATUS current
			DESCRIPTION
				"In scenarios where the flow data record or QoE analysis service is disabled, the SPU is not restarted after the extended-package load command (for loading the expansion package) or the fdr enable command is executed. In this case, the system generates this trap every one hour to remind the user to restart the SPU."
			::= { hwExtendedModuleTrapConfig 5 }


--         1.3.6.1.4.1.2011.6.122.20.2.8.2.7
-- 1.3.6.1.4.1.2011.6.122.20.2.8.2.7
-- 1.3.6.1.4.1.2011.6.122.20.2.8.2.7
-- 1.3.6.1.4.1.2011.6.122.20.2.8.2.7
-- 1.3.6.1.4.1.2011.6.122.20.2.8.2.7
-- 1.3.6.1.4.1.2011.6.122.20.2.8.2.7
-- 1.3.6.1.4.1.2011.6.122.20.2.8.2.7
-- 1.3.6.1.4.1.2011.6.122.20.2.8.2.7
		-- 1.3.6.1.4.1.2011.6.122.20.2.8.2.7
		hwNeedResetForUndoFdrMemallocTrap NOTIFICATION-TYPE
			OBJECTS { hwExtendedFeatureLocation }
			STATUS current
			DESCRIPTION
				"In scenarios where the flow data record or QoE analysis service is enabled through the CLI, the SPU is not restarted after the undo extended-package load command (for uninstalling the expansion package) or the undo fdr enable command is executed. In this case, the system generates this trap every one hour to remind the user to restart the SPU."
			::= { hwExtendedModuleTrapConfig 7 }


--         1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
-- 1.3.6.1.4.1.2011.6.122.20.2.8
		-- 1.3.6.1.4.1.2011.6.122.20.2.9
		hwSAInstanceTrap OBJECT IDENTIFIER ::= { hwServiceObject 9 }


--         1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
-- 1.3.6.1.4.1.2011.6.122.20.2.8.1
		-- 1.3.6.1.4.1.2011.6.122.20.2.9.1
		hwSAInstanceTrapVB OBJECT IDENTIFIER ::= { hwSAInstanceTrap 1 }


--         1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
-- 1.3.6.1.4.1.2011.6.122.20.2.8.1.1
		-- 1.3.6.1.4.1.2011.6.122.20.2.9.1.1
		hwSAInstanceName OBJECT-TYPE
			SYNTAX OCTET STRING (SIZE (1..64))
			MAX-ACCESS read-only
			STATUS current
			DESCRIPTION
				"SA instance name of the QoE board."
			::= { hwSAInstanceTrapVB 1 }


--         1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
		-- 1.3.6.1.4.1.2011.6.122.20.2.9.1.2
		hwSAinstanceCPUTotalNumber OBJECT-TYPE
			SYNTAX Integer32 (1..64)
			MAX-ACCESS read-only
			STATUS current
			DESCRIPTION
				"Total number of CPUs contained in the SA instance of the QoE board."
			::= { hwSAInstanceTrapVB 2 }


--         1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
		-- 1.3.6.1.4.1.2011.6.122.20.2.9.1.3
		hwSAinstanceCPUActiveNumber OBJECT-TYPE
			SYNTAX Integer32 (1..64)
			MAX-ACCESS read-only
			STATUS current
			DESCRIPTION
				"Number of available CPUs contained in the SA instance of the QoE board."
			::= { hwSAInstanceTrapVB 3 }


--         1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
-- 1.3.6.1.4.1.2011.6.122.20.2.8.1.2
		-- 1.3.6.1.4.1.2011.6.122.20.2.9.1.4
		hwSAinstanceCPULeastActiveNumber OBJECT-TYPE
			SYNTAX Integer32 (1..64)
			MAX-ACCESS read-only
			STATUS current
			DESCRIPTION
				"Minimum number of available CPUs that the SA instance of the QoE board requires."
			::= { hwSAInstanceTrapVB 4 }


--         1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
-- 1.3.6.1.4.1.2011.6.122.20.2.8.2
		-- 1.3.6.1.4.1.2011.6.122.20.2.9.2
		hwSAInstanceTrapConfig OBJECT IDENTIFIER ::= { hwSAInstanceTrap 2 }


--         1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
-- 1.3.6.1.4.1.2011.6.122.20.2.8.2.1
		-- 1.3.6.1.4.1.2011.6.122.20.2.9.2.1
		hwSAInstanceStateChangeToAbnormalTrap NOTIFICATION-TYPE
			OBJECTS { hwSAInstanceName, hwSAinstanceCPUTotalNumber, hwSAinstanceCPUActiveNumber, hwSAinstanceCPULeastActiveNumber }
			STATUS current
			DESCRIPTION
				"The SA instance was faulty."
			::= { hwSAInstanceTrapConfig 1 }


--         1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
-- 1.3.6.1.4.1.2011.6.122.20.2.8.2.3
		-- 1.3.6.1.4.1.2011.6.122.20.2.9.2.2
		hwSAInstanceStateChangeToNormalTrap NOTIFICATION-TYPE
			OBJECTS { hwSAInstanceName, hwSAinstanceCPUTotalNumber, hwSAinstanceCPUActiveNumber, hwSAinstanceCPULeastActiveNumber }
			STATUS current
			DESCRIPTION
				"The SA instance recovered."
			::= { hwSAInstanceTrapConfig 2 }


--         1.3.6.1.4.1.2011.6.122.20.3
-- 1.3.6.1.4.1.2011.6.122.20.3
-- 1.3.6.1.4.1.2011.6.122.20.3
-- 1.3.6.1.4.1.2011.6.122.20.3
-- 1.3.6.1.4.1.2011.6.122.20.3
-- 1.3.6.1.4.1.2011.6.122.20.3
-- 1.3.6.1.4.1.2011.6.122.20.3
-- 1.3.6.1.4.1.2011.6.122.20.3
		-- 1.3.6.1.4.1.2011.6.122.20.3
		hwSALicense OBJECT IDENTIFIER ::= { hwSAFEMIB 3 }


--         1.3.6.1.4.1.2011.6.122.20.3.1
-- 1.3.6.1.4.1.2011.6.122.20.3.1
-- 1.3.6.1.4.1.2011.6.122.20.3.1
-- 1.3.6.1.4.1.2011.6.122.20.3.1
-- 1.3.6.1.4.1.2011.6.122.20.3.1
-- 1.3.6.1.4.1.2011.6.122.20.3.1
-- 1.3.6.1.4.1.2011.6.122.20.3.1
-- 1.3.6.1.4.1.2011.6.122.20.3.1
		-- 1.3.6.1.4.1.2011.6.122.20.3.1
		hwLicenseTable OBJECT-TYPE
			SYNTAX SEQUENCE OF HwLicenseEntry
			MAX-ACCESS not-accessible
			STATUS current
			DESCRIPTION
				"This table describes SA license information, including the number of running SPSs and enabled license functions."
			::= { hwSALicense 1 }


--         1.3.6.1.4.1.2011.6.122.20.3.1.1
-- 1.3.6.1.4.1.2011.6.122.20.3.1.1
-- 1.3.6.1.4.1.2011.6.122.20.3.1.1
-- 1.3.6.1.4.1.2011.6.122.20.3.1.1
-- 1.3.6.1.4.1.2011.6.122.20.3.1.1
-- 1.3.6.1.4.1.2011.6.122.20.3.1.1
-- 1.3.6.1.4.1.2011.6.122.20.3.1.1
-- 1.3.6.1.4.1.2011.6.122.20.3.1.1
		-- 1.3.6.1.4.1.2011.6.122.20.3.1.1
		hwLicenseEntry OBJECT-TYPE
			SYNTAX HwLicenseEntry
			MAX-ACCESS not-accessible
			STATUS current
			DESCRIPTION
				"Description."
			INDEX { hwLicenseServiceID }
			::= { hwLicenseTable 1 }


		HwLicenseEntry ::=
			SEQUENCE {
				hwLicenseServiceID
					Integer32,
				hwActiveSpsNumber
					Integer32,
				hwEnabledFunction
					OCTET STRING
			 }

--         1.3.6.1.4.1.2011.6.122.20.3.1.1.1
-- 1.3.6.1.4.1.2011.6.122.20.3.1.1.1
-- 1.3.6.1.4.1.2011.6.122.20.3.1.1.1
-- 1.3.6.1.4.1.2011.6.122.20.3.1.1.1
-- 1.3.6.1.4.1.2011.6.122.20.3.1.1.1
-- 1.3.6.1.4.1.2011.6.122.20.3.1.1.1
-- 1.3.6.1.4.1.2011.6.122.20.3.1.1.1
-- 1.3.6.1.4.1.2011.6.122.20.3.1.1.1
		-- 1.3.6.1.4.1.2011.6.122.20.3.1.1.1
		hwLicenseServiceID OBJECT-TYPE
			SYNTAX Integer32 (1)
			MAX-ACCESS not-accessible
			STATUS current
			DESCRIPTION
				"The value of this object identifies the license service ID. The value can only be 1."
			::= { hwLicenseEntry 1 }


--         1.3.6.1.4.1.2011.6.122.20.3.1.1.2
-- 1.3.6.1.4.1.2011.6.122.20.3.1.1.2
-- 1.3.6.1.4.1.2011.6.122.20.3.1.1.2
-- 1.3.6.1.4.1.2011.6.122.20.3.1.1.2
-- 1.3.6.1.4.1.2011.6.122.20.3.1.1.2
-- 1.3.6.1.4.1.2011.6.122.20.3.1.1.2
-- 1.3.6.1.4.1.2011.6.122.20.3.1.1.2
-- 1.3.6.1.4.1.2011.6.122.20.3.1.1.2
		-- 1.3.6.1.4.1.2011.6.122.20.3.1.1.2
		hwActiveSpsNumber OBJECT-TYPE
			SYNTAX Integer32 (0..64)
			MAX-ACCESS read-only
			STATUS current
			DESCRIPTION
				"The value of this object identifies the number of SPSs that are processing service traffic."
			::= { hwLicenseEntry 2 }


--         1.3.6.1.4.1.2011.6.122.20.3.1.1.3
-- 1.3.6.1.4.1.2011.6.122.20.3.1.1.3
-- 1.3.6.1.4.1.2011.6.122.20.3.1.1.3
-- 1.3.6.1.4.1.2011.6.122.20.3.1.1.3
-- 1.3.6.1.4.1.2011.6.122.20.3.1.1.3
-- 1.3.6.1.4.1.2011.6.122.20.3.1.1.3
-- 1.3.6.1.4.1.2011.6.122.20.3.1.1.3
-- 1.3.6.1.4.1.2011.6.122.20.3.1.1.3
		-- 1.3.6.1.4.1.2011.6.122.20.3.1.1.3
		hwEnabledFunction OBJECT-TYPE
			SYNTAX OCTET STRING
			MAX-ACCESS read-write
			STATUS current
			DESCRIPTION
				"This object indicates whether the license function is enabled."
			::= { hwLicenseEntry 3 }


--         1.3.6.1.4.1.2011.6.122.20.3.2
-- 1.3.6.1.4.1.2011.6.122.20.3.2
-- 1.3.6.1.4.1.2011.6.122.20.3.2
-- 1.3.6.1.4.1.2011.6.122.20.3.2
-- 1.3.6.1.4.1.2011.6.122.20.3.2
-- 1.3.6.1.4.1.2011.6.122.20.3.2
-- 1.3.6.1.4.1.2011.6.122.20.3.2
-- 1.3.6.1.4.1.2011.6.122.20.3.2
		-- 1.3.6.1.4.1.2011.6.122.20.3.2
		hwSALicenseTraps OBJECT IDENTIFIER ::= { hwSALicense 2 }


--         1.3.6.1.4.1.2011.6.122.20.4
-- 1.3.6.1.4.1.2011.6.122.20.4
-- 1.3.6.1.4.1.2011.6.122.20.4
-- 1.3.6.1.4.1.2011.6.122.20.4
-- 1.3.6.1.4.1.2011.6.122.20.4
-- 1.3.6.1.4.1.2011.6.122.20.4
-- 1.3.6.1.4.1.2011.6.122.20.4
-- 1.3.6.1.4.1.2011.6.122.20.4
		-- 1.3.6.1.4.1.2011.6.122.20.4
		hwSAConformance OBJECT IDENTIFIER ::= { hwSAFEMIB 4 }


--         1.3.6.1.4.1.2011.6.122.20.4.1
-- 1.3.6.1.4.1.2011.6.122.20.4.1
-- 1.3.6.1.4.1.2011.6.122.20.4.1
-- 1.3.6.1.4.1.2011.6.122.20.4.1
-- 1.3.6.1.4.1.2011.6.122.20.4.1
-- 1.3.6.1.4.1.2011.6.122.20.4.1
-- 1.3.6.1.4.1.2011.6.122.20.4.1
-- 1.3.6.1.4.1.2011.6.122.20.4.1
		-- 1.3.6.1.4.1.2011.6.122.20.4.1
		hwSACompliances OBJECT IDENTIFIER ::= { hwSAConformance 1 }


--         1.3.6.1.4.1.2011.6.122.20.4.1.1
-- this module
-- 1.3.6.1.4.1.2011.6.122.20.4.1.1
-- this module
-- 1.3.6.1.4.1.2011.6.122.20.4.1.1
-- this module
-- 1.3.6.1.4.1.2011.6.122.20.4.1.1
-- this module
-- 1.3.6.1.4.1.2011.6.122.20.4.1.1
-- this module
-- 1.3.6.1.4.1.2011.6.122.20.4.1.1
-- this module
-- 1.3.6.1.4.1.2011.6.122.20.4.1.1
-- this module
-- 1.3.6.1.4.1.2011.6.122.20.4.1.1
-- this module
		-- 1.3.6.1.4.1.2011.6.122.20.4.1.1
		hwSAFECompliance MODULE-COMPLIANCE
			STATUS current
			DESCRIPTION
				"The compliance statement for SNMP entities which implement
				version 1 of the hwSAFE MIB."
			MODULE -- this module
				MANDATORY-GROUPS { hwSATrapGroup, hwSAObject }
			::= { hwSACompliances 1 }


--         1.3.6.1.4.1.2011.6.122.20.4.2
-- 1.3.6.1.4.1.2011.6.122.20.4.2
-- 1.3.6.1.4.1.2011.6.122.20.4.2
-- 1.3.6.1.4.1.2011.6.122.20.4.2
-- 1.3.6.1.4.1.2011.6.122.20.4.2
-- 1.3.6.1.4.1.2011.6.122.20.4.2
-- 1.3.6.1.4.1.2011.6.122.20.4.2
-- 1.3.6.1.4.1.2011.6.122.20.4.2
		-- 1.3.6.1.4.1.2011.6.122.20.4.2
		hwSAGroups OBJECT IDENTIFIER ::= { hwSAConformance 2 }


--         1.3.6.1.4.1.2011.6.122.20.4.2.1
-- 1.3.6.1.4.1.2011.6.122.20.4.2.1
-- 1.3.6.1.4.1.2011.6.122.20.4.2.1
-- 1.3.6.1.4.1.2011.6.122.20.4.2.1
-- 1.3.6.1.4.1.2011.6.122.20.4.2.1
-- 1.3.6.1.4.1.2011.6.122.20.4.2.1
-- 1.3.6.1.4.1.2011.6.122.20.4.2.1
-- 1.3.6.1.4.1.2011.6.122.20.4.2.1
		-- 1.3.6.1.4.1.2011.6.122.20.4.2.1
		hwSATrapGroup NOTIFICATION-GROUP
			NOTIFICATIONS { hwStateChangeToNormalTrap, hwStateChangeToAbnormalTrap, hwPeerNodeConnectDownTrap, hwPeerNodeConnectUpTrap, hwNodeModeChangeActiveTrap,
				hwNodeModeChangeStandbyTrap, hwNodeCompConnectUpTrap, hwNodeCompConnectDownTrap, hwSpuCpuUsageThresholdTrap, hwSpuMemUsageThresholdTrap,
				hwSpuCompLinkAddTrap, hwSpuCompLinkDeleteTrap, hwSpuCompLinkConnectDownTrap, hwSpuCompLinkConnectUpTrap, hwSpsSasLinkAddTrap,
				hwSpsSasLinkDeleteTrap, hwSpsSasLinkDownTrap, hwSpsSasLinkUpTrap, hwResourceNotEnoughTrap, hwBWListSyncErrTrap,
				hwSpuTemperatureThresholdTrap, hwLpuOverLoadTrap, hwSpuOverLoadTrap, hwCGCdrMemChangeToNormalTrap, hwCGCdrMemOverloadTrap,
				hwCGConnectUpTrap, hwCGConnectDownTrap, hwBypassSwitchWorkingMode, hwRadiusSnifferAckOkTrap, hwRadiusSnifferNoAckTrap,
				hwSpsUcssLinkUpTrap, hwSpsUcssLinkDownTrap, hwCGCdrPoolFullClearedTrap, hwLinkBandWidthChangeToEqualTrap, hwLinkBandWidthChangeToUnequalTrap,
				hwCGCdrPoolFullTrap, hwMemoryBeyondThresholdTrap, hwMemoryChangeToNormalTrap, hwCpuBeyondThresholdTrap, hwCpuChangeToNormalTrap,
				hwConfigurationInconsistentTrap, hwBackupGroupStateChangeToBackupTrap, hwBackupGroupStateChangeToMasterTrap, hwHotBackupConfigurationCheckFailTrap, hwCascadeSuccessfulTrap,
				hwCascadeFailedTrap, hwSPSAmountSufficientTrap, hwSPSAmountInsufficientTrap, hwCascadeLinkStateChangeToAbnormal, hwCascadeLinkStateChangeToNormal,
				hwCascadeLinkOverloadTrap, hwSAFdiConnectDownTrap, hwBypassLinkState, hwBypassLinkSwitchState, hwOCSConnectUpTrap,
				hwOCSConnectDownTrap, hwPCRFConnectUpTrap, hwPCRFConnectDownTrap, hwBypassMonitorState, hwCollectorConnectUpTrap,
				hwCollectorConnectDownTrap, hwSpsRdasLinkUpTrap, hwSpsRdasLinkDownTrap, hwLinkBoundGroupStateChangeToNormal, hwLinkBoundGroupStateChangeToAbnormal,
				hwSpuCpuUsageThresholdRestoreTrap, hwSpuMemUsageThresholdRestoreTrap, hwSpuTemperatureThresholdRestoreTrap, hwSpuFlowOverLoadRecoverTrap, hwSpuFlowOverLoadTrap,
				hwSpsFragmentEnoughTrap, hwSpsFragmentNotEnoughTrap, hwSasRpdAccountMessageAbnormalTrap, hwNeedResetForFeatureUnloadTrap, hwHashModeVerifyRecoverTrap,
				hwHashModeVerifyTrap, hwHashModeInconsistentRecoverTrap, hwHashModeInconsistentTrap, hwSpammerFTPUpTrap, hwSpammerFTPDownTrap,
				hwIPDbtOverLoadRecoverTrap, hwIPDbtOverLoadTrap, hwNeedResetForUndoFdrMemallocTrap, hwNeedResetForFdrMemallocTrap, hwNPLUS1HBKEnableSpuNeedResetTrap,
				hwNPLUS1HBKDisableSpuNeedResetTrap, hwNPLUS1HBKCpuStanbyRecoverTrap, hwNPLUS1HBKCpuStandbyTrap, hwNPLUS1HBKDisableSpuResetRecoverTrap, hwNPLUS1HBKEnableSpuResetRecoverTrap,
				hwDRAConnectUpTrap, hwDRAConnectDownTrap, hwForwardingQueueOverloadTrap, hwAverageCpuUsageThresholdTrap, hwSpsLeastNumberBelowTrap,
				hwForwardingQueueRestoreTrap, hwSpsLeastNumberEqualTrap, hwAverageCpuUsageThresholdRestoreTrap, hwPlsCompLinkConnectUpTrap, hwPlsCompLinkConnectDownTrap,
				hwCABeforeExpiredTrap, hwCAExpiredTrap, hwSAInstanceStateChangeToNormalTrap, hwSAInstanceStateChangeToAbnormalTrap, hwNeedResetForFeatureLoadTrap,
				hwSasRpdAccountMessageNormalTrap }
			STATUS current
			DESCRIPTION
				"Description."
			::= { hwSAGroups 1 }


--         1.3.6.1.4.1.2011.6.122.20.4.2.2
-- 1.3.6.1.4.1.2011.6.122.20.4.2.2
-- 1.3.6.1.4.1.2011.6.122.20.4.2.2
-- 1.3.6.1.4.1.2011.6.122.20.4.2.2
-- 1.3.6.1.4.1.2011.6.122.20.4.2.2
-- 1.3.6.1.4.1.2011.6.122.20.4.2.2
-- 1.3.6.1.4.1.2011.6.122.20.4.2.2
-- 1.3.6.1.4.1.2011.6.122.20.4.2.2
		-- 1.3.6.1.4.1.2011.6.122.20.4.2.2
		hwSAObject OBJECT-GROUP
			OBJECTS { hwSpuSysInfoLocation, hwSpuSysInfoType, hwSpuSysInfoIPAddress, hwSpuSysInfoState, hwServiceLinkType,
				hwServiceLinkName, hwServiceLinkInsideInterface, hwServiceLinkOutsideInterface, hwServiceLinkInsideInterfaceState, hwServiceLinkOutsideInterfaceState,
				hwClusterNodeName, hwClusterNodeIPAddress, hwClusterNodeRole, hwClusterNodeStatus, hwClusterSasNodeNumber,
				hwClusterSasSysLocation, hwClusterSasSysIPAddress, hwClusterSasMode, hwClusterMapSysSasMode, hwClusterMapNumberOfDG,
				hwClusterMapDevices, hwComponentType, hwComponentNumber, hwComponentName, hwComponentUsageMode,
				hwSpuEntityCpuUsage, hwSpuEntityCpuUsageThreshold, hwSpuEntityMemoryUsage, hwSpuEntityMemoryUsageThreshold, hwResourceLocation,
				hwSAResourceType, hwResourceCapacity, hwResourceUsage, hwResourceLeft, hwSACbbLocation,
				hwSACbbVersion, hwBWListLocation, hwBWListVersion, hwSpsSasLinkSpsIP, hwSpsSasLinkSasIP,
				hwSpsSasLinkStatus, hwSpuCompLinkCurrentDestIP, hwSpuCompLinkCurrentDestPort, hwSpuCompLinkConnState, hwSpuCompLinkNumPacketsSent,
				hwSpuCompLinkBytesSent, hwSpuCompLinkNumPacketsRecv, hwSpuCompLinkBytesRecv, hwSpuCompLinkNumErrPacketsRecv, hwSpuCompLinkComponentType,
				hwBypassLinkStateLink, hwComponentPrimaryIPAddress, hwComponenSecondaryIPAddress, hwComponentSecIPConnStatus, hwComponentPriIPConnStatus,
				hwSpuEntityTemperatureThreshold, hwSpuEntityPhysicalIndex, hwSpuEntityTemperature, hwBypassLinkStateMode, hwBypassLinkStateChannel0State,
				hwBypassLinkStateChannel1State, hwBWListType, hwSpuOverLoadPackages, hwLpuOverLoadBytes, hwSpsSasLinkSasLocation,
				hwSpsSasLinkSpsLocation, hwSpuEntityLocation, hwSnifferInfoState, hwSnifferDstIPAddress, hwSnifferSrcIPAddress,
				hwPacketErrCount, hwPacketSendCount, hwSnifferInfoLocation, hwSysFdiInstanceID, hwSpsUcssLinkUcssIP,
				hwSpsUcssLinkSpsIP, hwSpsUcssLinkSpsLocation, hwServiceLinkOutsideInterfaceBandWidth, hwServiceLinkInsideInterfaceBandWidth, hwSysFdiDestBackupIP,
				hwLpuOverLoadPackages, hwSpuOverLoadBytes, hwSpuCompLinkSysLocation, hwSAFdiConnectLocation, hwSasIPAddress,
				hwSpsIPAddress, hwSpsNewFlowNumber, hwSpsNewTempFlowNumber, hwSpsDeleteFlowNumber, hwBackupGroupPeerState,
				hwBackupGroupPeerSlot, hwBackupGroupID, hwCascadeSelfState, hwCascadePeerState, hwCascadeCfg,
				hwNormalSPSNumber, hwEnabledFunction, hwActiveSpsNumber, hwSysFdiDestMasterIP, hwBypassLinkStateRIsignal,
				hwBypassLinkCurrentState, hwBypassLinkLosTimes, hwBypassLinkLinkTimes, hwBypassSwitchCurrentPosition, hwBypassSwitchWorkingTimes,
				hwBypassSwitchProtectionTimes, hwServiceResourceLocation, hwServiceResourceType, hwServiceResourceUsage, hwCascadeInterfaceStatus,
				hwServiceResourceVcpuId, hwCascadeInterface, hwLocalClusterNodeID, hwPeerClusterNodeID, hwBackupGroupLocalState,
				hwBackupGroupLocalSlot, hwPeerClusterNodeIPAddress, hwOCSPort, hwOCSHostName, hwPCRFPort,
				hwPCRFHostName, hwCGCdrCachePoolUsed, hwCGGrade, hwCGPort, hwLocalClusterNodeIPAddress,
				hwServiceLinkBoundGroupNumber, hwSASLocationConnectCG, hwCGIPAddress, hwSASLocationConnectPCRF, hwPCRFIPAddress,
				hwSASNameConnectPCRF, hwSASIPAddressConnectPCRF, hwSASPortConnectPCRF, hwSASLocationConnectOCS, hwOCSIPAddress,
				hwSASPortConnectOCS, hwSpsMessageNumberLocation, hwBypassAlarmDescription, hwBypassPowerStatus, hwBypassSlotNum,
				hwSasGxPerformanceLocation, hwSasGxTotalSendNumber, hwSasGxTotalRecieveNumber, hwSasGxCCRInitalNumber, hwSasGxCCAInitalNumber,
				hwSasGxCCRUpdateNumber, hwSasGxCCAUpdateNumber, hwSasGxRARNumber, hwSasGxRAANumber, hwSasGxASRNumber,
				hwSasGxASANumber, hwSasGxErrorLocation, hwGxCommunitionInterruptedTimes, hwSasGyPerformanceLocation, hwSasGyTotalSendNumber,
				hwSasGyTotalRecieveNumber, hwSasGyCCRInitalNumber, hwSasGyCCAInitalNumber, hwSasGyCCRUpdateNumber, hwSasGyCCAUpdateNumber,
				hwSasGyCCRTerminateNumber, hwSasGyCCATerminateNumber, hwSasGyRARNumber, hwSasGyRAANumber, hwSasGyASRNumber,
				hwSasGyASANumber, hwSasGyErrorLocation, hwGyCommunitionInterruptedTimes, hwOcsFaultDeactiveNumber, hwSasGzPerformanceLocation,
				hwSasGzSendCDRNumber, hwSasGzErrorLocation, hwGzCommunitionInterruptedTimes, hwSasGzAbnormalSignalingNumber, hwSASIPAddressConnectOCS,
				hwSASNameConnectOCS, hwSasGyCCRInitalRetransmissions, hwSasGyCCRUpdateRetransmissions, hwSasIPAddressForGxPerformance, hwSasIPAddressForGxError,
				hwSasIPAddressForGyPerformance, hwSasIPAddressForGyError, hwSasIPAddressForGzPerformance, hwSasIPAddressForGzError, hwSasGyCCRTerminateRetransmissions,
				hwSasGxCCRInitalRetransmissions, hwSasGxCCRUpdateRetransmissions, hwSasGxCCRTerminateRetransmissions, hwGyType1ResultCode, hwGyType2ResultCode,
				hwGyType3ResultCode, hwGyType4ResultCode, hwGyType5ResultCode, hwSasMessageTotalNum, hwSasMessageAccountOffLineNum,
				hwSasMessageAccountOnLineNum, hwSasMessageIpOffLineNum, hwCollectorPort, hwCollectorIP, hwSpsRdasLinkRdasIP,
				hwSpsRdasLinkSpsLocation, hwSasMessageIpOnLineNum, hwSpuFlowOverLoadLocation, hwSpuFlowOverLoadPackets, hwSpsFragmentSpsLocation,
				hwSasRpdAccountMessageRpdIP, hwSasRpdAccountMessageLocation, hwRecoverTrapCause, hwInterfaceList, hwSpammerFTPServePort,
				hwSpammerFTPServeIP, hwNPLUS1BackupGroupBoardType, hwNPLUS1BackupGroupBoardList, hwNPLUS1BackupGroupID, hwSPSLinkLocation,
				hwUpstreamPassedBandwidth, hwDownstreamPassedBandwidth, hwUpstreamDiscardedBandwidth, hwDownstreamDiscardedBandwidth, hwSASPortConnectDRA,
				hwSASIPAddressConnectDRA, hwSASNameConnectDRA, hwDRAPort, hwDRAIPAddress, hwDRAHostName,
				hwSASLocationConnectDRA, hwSpsLinkId, hwNPLUS1BackupIsEnable, hwLocalBackupGroupStateCpuIndex, hwLocalBackupGroupStateCpuLocation,
				hwLocalBackupGroupStateCpuType, hwLocalBackupGroupStateIsEnable, hwLocalBackupGroupStateGroupId, hwLocalBackupGroupStateSpuType, hwLocalBackupGroupStateCpuMode,
				hwLocalBackupSpuTypeInconsist, hwLocalBackupGroupIsStandby, hwSpsLeastNumberCfg, hwSpsQueueUsage, hwSpsOverloadThreshold,
				hwSpsEntityLocation, hwSpsAverageCpuUsageThreshold, hwSpsAverageCpuUsage, hwSpsCpuEntityIndex, hwSpsLeastNumberIndex,
				hwCAExpireTime, hwSAinstanceCPULeastActiveNumber, hwSAinstanceCPUActiveNumber, hwSAinstanceCPUTotalNumber, hwSAInstanceName,
				hwSasMessageType, hwSasMessageLocation, hwSasGxCCRTerminateNumber, hwSasGxCCATerminateNumber, hwExtendedFeatureLocation,
				hwExtendedFeatureType }
			STATUS current
			DESCRIPTION
				"Description."
			::= { hwSAGroups 2 }



	END

--
--
--
