-- =================================================================
-- Copyright (C) 2019 by HUAWEI TECHNOLOGIES. All rights reserved.
-- Description:  The MIB is used for defining Huawei's GPON management in distributing mode MIB objects.
-- Reference:
-- Version: V2.19
-- ================================================================
       HUAWEI-GPON-MIB DEFINITIONS ::= BEGIN
       IMPORTS
           MODULE-IDENTITY, mib-2, OBJECT-TYPE, Counter32, Counter64, IpAddress,
           Unsigned32, Integer32, zeroDotZero, Gauge32, NOTIFICATION-TYPE
               FROM SNMPv2-SMI
           TruthValue, DateAndTime, RowStatus, MacAddress,TEXTUAL-CONVENTION, DisplayString
               FROM SNMPv2-TC
           ifIndex
               FROM IF-MIB
           MODULE-COMPLIANCE, OBJECT-GROUP
               FROM SNMPv2-CONF
           SnmpAdminString
               FROM SNMP-FRAMEWORK-MIB
           OwnerString, EntryStatus
               FROM RMON-MIB
           huaweiMgmt
               FROM HUAWEI-MIB;

   hwGponDeviceMIB MODULE-IDENTITY

       LAST-UPDATED "201908221000Z"

       ORGANIZATION "Huawei Technologies Co.,Ltd."
       CONTACT-INFO
                    "Huawei Industrial Base
                     Bantian, Longgang
                     Shenzhen 518129
                     People's Republic of China
                     Website: http://www.huawei.com
                     Email: support@huawei.com
                    "
       DESCRIPTION  "The MIB is used for defining Huawei's GPON management in distributing mode MIB objects."

    --  Revision history
           REVISION     "201908221000Z"
           DESCRIPTION  "V2.19, changes in this revision:
                         - Add the hwGponOpticsMDPartNum in table HwGponOltOpticsModuleInformationEntry.
                        "
           REVISION     "201906241000Z"
           DESCRIPTION  "V2.18, changes in this revision:
                         - Add the table of hwGponDeviceGemBundleTable.
                        "
           REVISION     "201902251000Z"
           DESCRIPTION  "V2.17, changes in this revision:
			- Add a enum values of the leaf node hwGponOpticsModuleXponSubType.
                        "
           REVISION     "201901251000Z"
           DESCRIPTION  "V2.16, changes in this revision:
                         - Modify the value range of the leaf hwGponOntRegisterInfoType in table hwGponOntRegisterExInfoTable.
                         - Modify the value range of the leaf hwGponOntRegisterInfoUpTime in table hwGponOntRegisterExInfoTable.
                         - Modify the value range of the leaf hwGponOntRegisterInfoDownTime in table hwGponOntRegisterExInfoTable.
                        "
           REVISION     "201808201000Z"
           DESCRIPTION  "V2.15, changes in this revision:
                         - Add the leaf hwGponDeviceAutoFindOntEquipmentSn in table hwGponDeviceAutoFindOntControlTable.
                         - Add the leaf hwGponDeviceAutoFindOntMac in table hwGponDeviceAutoFindOntControlTable.
                         - Add the leaf hwGponDeviceOntObjectEquipmentSn in table hwGponDeviceOntConfigTable.
                         - Add the leaf hwGponDeviceOntObjectMac in table hwGponDeviceOntConfigTable.
                         - Add seven enum values of the leaf node hwGponOntRegisterInfoDownCause.
                         "
           REVISION     "201806131000Z"
           DESCRIPTION  "V2.14, changes in this revision:
			- Add a enum values of the leaf node hwGponOntRegisterInfoDownCause.
			"
           REVISION     "201803131000Z"
           DESCRIPTION  "V2.13, changes in this revision:
                         - Add leaf hwGponDeviceTcontAsynCommit in table hwGponDeviceTcontProfileTable.
			"
           REVISION     "201802061000Z"
           DESCRIPTION  "V2.12, changes in this revision:
                         - Add the enumerate of leaf hwGponOpticsModuleXponType in table hwGponOltOpticsModuleInformationTable.
                         - Add the enumerate of leaf hwGponOpticsModuleXponSubType in table hwGponOltOpticsModuleInformationTable.
                         - Add the enumerate of leaf hwGponOpticsModuleXponUsedType in table hwGponOltOpticsModuleInformationTable.
                         - Add the enumerate of leaf hwGponOpticsModuleXponEncapsulationType in table hwGponOltOpticsModuleInformationTable.
                         "
           REVISION     "201801311000Z"
           DESCRIPTION  "V2.11, changes in this revision:
                         - Add leaf hwGponDeviceTcontOperateResult in table hwGponDeviceTcontProfileTable.
                         "

           REVISION     "201711080900Z"
           DESCRIPTION  "V2.10, changes in this revision:
                         - Add the leaf hwGponDeviceOltObjectPortReset in table hwGponDeviceOltControlTable.
                         "

            REVISION     "201710261000Z"
            DESCRIPTION  "V2.09, changes in this revision:
                         - Modify the description of the leaf hwGponDeviceTcontPriority in table hwGponDeviceTcontProfileTable.
                         "

           REVISION     "201708101000Z"
           DESCRIPTION  "V2.08, changes in this revision:
                         - Modify the value range of the leaf hwGponDeviceOntMTU in table hwGponDeviceOntExtConfigTable.
                        "

           REVISION     "201707271000Z"
           DESCRIPTION  "V2.07, changes in this revision:
                         - Add the leaf hwGponOntPortUnknownUnicastRate in table hwGponOntPortExtConfigTable.
                         - Add the leaf hwGponOntPortBroadcastRate in table hwGponOntPortExtConfigTable.
                         - Add the leaf hwGponOntPortUnknownMulticastRate in table hwGponOntPortExtConfigTable.
                         - Modify the description of the leaf hwGponOntPortClassProfileIndex in table hwGponOntPortExtConfigTable.
                         "

   	       REVISION     "201707071600Z"
           DESCRIPTION  "V2.06, changes in this revision:
                         - Add a table hwGponDeviceOntPortClassInfoTable.
                         - Add the leaf hwGponOntPortClassProfileIndex in table hwGponOntPortExtConfigTable.
			            "

   	       REVISION     "201706171600Z"
           DESCRIPTION  "V2.05, changes in this revision:
                         - Modify the string length of the leaf hwGponDeviceOltObjectDespt.
			            "

   	       REVISION     "201706061000Z"
           DESCRIPTION  "V2.04, changes in this revision:
                         - Add the leaf hwOntLoadServerPort in table hwOntLoadCtrlTable.
			            "

           REVISION      "201705270900Z"
           DESCRIPTION   "V2.03, changes in this revision:
                         - Add a enum value of the leaf node hwGponDeviceOntMonitorLinkSwitch in table hwGponDeviceOntExtConfigTable.
                         "

           REVISION      "201704220900Z"
           DESCRIPTION   "V2.02, changes in this revision:
                         - Add the leaf hwGponOntEtherStatsStateChangeTimes in table hwGponOntEtherStatsTable.
                         - Add the leaf hwGponOntEtherStatsDuration in table hwGponOntEtherStatsTable.
                         - Add the leaf hwGponOntifEthernetMode in table hwGponOntifEthernetObjectTable.
                         - Add the leaf hwGponOntifEthernetOpticalModuleStatus in table hwGponOntifEthernetObjectTable.
                         - Add the leaf hwGponOntifEthernetOnlineDuration in table hwGponOntifEthernetObjectTable.
                         - Add the leaf hwGponDeviceOntMTU in table hwGponDeviceOntExtConfigTable.
                         - Add the leaf hwGponDeviceOntMonitorLinkSwitch in hwGponDeviceOntExtConfigTable.
                         "

           REVISION      "201608310900Z"
           DESCRIPTION   "V2.01, changes in this revision:
                         - Add the leaf hwGponDeviceOntObjectHostName in table hwGponDeviceOntConfigTable.
                         - Add a enum values of the leaf node hwGponDevicePortidMapObjectPortTypeIndex.
	  		             "

           REVISION      "201608040900Z"
           DESCRIPTION   "V2.00, changes in this revision:
                         - Modify the description of the leaf hwGponDeviceAutoFindOntNniType in table hwGponDeviceAutoFindOntControlTable.
                         - Modify the description of the leaf hwGponDeviceOntObjectNniType in table hwGponDeviceOntConfigTable.
                         "

           REVISION      "201607211100Z"
           DESCRIPTION   "V1.99, changes in this revision:
                         - Add a enum values of the leaf node hwGponOntPortType.
                         - Add a enum values of the leaf node hwGponOntPortVlanCfgOntPhyType.
                         - Add the leaf hwGponDeviceOntProfileWifiPortNum in table hwGponDeviceOntProfileControlTable.
                         "

           REVISION      "201606300900Z"
           DESCRIPTION   "V1.98, changes in this revision:
                         - Add the enumerate of leaf hwGponOpticsModuleXponSubType in table hwGponOltOpticsModuleInformationTable.
                         "

           REVISION      "201606021100Z"
           DESCRIPTION   "V1.97, changes in this revision:
                         - Add a enum values of the leaf node hwGponOntifEthernetSpeed.
                         - Add a enum values of the leaf node hwGponOntifEthernetActualSpeed.
                         - Modify the description of the leaf node hwGponDeviceOntObjectLastDownCause.
                         - Add a enum value of the leaf node hwGponOntRegisterInfoDownCause.
                         "

           REVISION      "201603280900Z"
           DESCRIPTION   "V1.96, changes in this revision:
                         - Add the leaf hwGponDeviceAutoFindOntNniType in table hwGponDeviceAutoFindOntControlTable.
                         - Modify the enmu name and the description of the leaf hwGponDeviceOntObjectNniType in table hwGponDeviceOntConfigTable.
                         "

           REVISION      "201601040900Z"
           DESCRIPTION   "V1.95, changes in this revision:
                         - Add the leaf hwGponDeviceOntObjectNniType in table hwGponDeviceOntConfigTable.
                         "

           REVISION      "201512220900Z"
           DESCRIPTION   "V1.94, changes in this revision:
                         - Add the leaf hwGponOltEthernetStatisticSendBufferOverflowDropPakts in table hwGponOltEtherStatisticTable.
                         "

           REVISION      "201509300900Z"
           DESCRIPTION   "V1.93, changes in this revision:
    			 - Add a enum value of the leaf node hwGponDeviceOntObjectAuthMethod in table hwGponDeviceOntConfigTable.
                         - Modify the description of the leaf hwGponDeviceOntObjectSn  in table hwGponDeviceOntConfigTable.
                         - Add the leaf hwGponDeviceOntObjectActualSn in table hwGponDeviceOntControlTable.
                         "

           REVISION      "201507290900Z"
           DESCRIPTION   "V1.92, changes in this revision:
                         - Modify the description of row status.
                         "
           REVISION      "201506120900Z"
           DESCRIPTION   "V1.91, changes in this revision:
                         - Add the leaf hwGponDeviceOntProfileMaxNumOfAdapPotsPort,hwGponDeviceOntProfileMaxNumOfAdapEthPort,hwGponDeviceOntProfileMaxNumOfAdapVdslPort,hwGponDeviceOntProfileMaxNumOfAdapCatvPort in table hwGponDeviceOntProfileControlTable.
                         "

           REVISION      "201504250900Z"
           DESCRIPTION   "V1.90, changes in this revision:
                         - Add the leaf hwGponDeviceOntLastRangingValue in table hwGponDeviceOntControlTable.
                         "

           REVISION      "201504080900Z"
           DESCRIPTION   "V1.89, changes in this revision:
                         - Modify the value range of the leaf hwGponDeviceOntMulticastMode.
                         - Modify the value range of the leaf hwGponDeviceOntRingCheckDetectingFrequency.
                         - Modify the value range of the leaf hwGponDeviceOntRingCheckResumeInterval.
                         "

           REVISION      "201503300900Z"
           DESCRIPTION   "V1.88, changes in this revision:
                         - Modify the enum values of the leaf hwGponOntRegisterInfoAuthMethod in table hwGponOntRegisterExInfoTable.
                         "

    	   REVISION      "201502090900Z"
           DESCRIPTION   "V1.87, changes in this revision:
                         - Modify the enum values of the leaf hwGponOntifEthernetSpeed in table hwGponOntifEthernetObjectTable.
                         - Modify the enum values of the leaf hwGponOntifEthernetActualSpeed in table hwGponOntifEthernetObjectTable.
                         "

           REVISION      "201501280900Z"
           DESCRIPTION   "V1.86, changes in this revision:
                         - Modify the description of the leaf hwGponOntUniPhyIndex in table hwGponDeviceOntUniLineTestTable.
                         - Modify the description of the leaf hwGponOntPortVlanCfgOntPhyIndex in table hwGponOntPortVlanCfgTable.
                         - Modify the description of the leaf hwGponDeviceOntObjectLastDownCause in table hwGponDeviceOntConfigTable.
                         - Add a enum value of the leaf node hwGponOntRegisterInfoDownCause in table hwGponOntRegisterExInfoTable.
                         "

           REVISION      "201412230900Z"
           DESCRIPTION   "V1.85, changes in this revision:
                         - Modify the description of the leaf hwGponOntOpticsOltRxOntPower in table hwGponDeviceOntOpticsDdmInfoTable.
                         - Modify the description of the leaf hwGponDeviceOntObjectLastDownCause in table hwGponDeviceOntConfigTable.
                         - Modify the description of the leaf hwGponOntRegisterInfoDownCause in table hwGponOntRegisterExInfoTable.
                         - Modify the value range of the leaf hwGponOntPortVlanCfgSPriPolicy.
                         "

           REVISION     "201411260900Z"
           DESCRIPTION  "V1.84, changes in this revision:
                         - Modify the value of hwXponDeviceOntSnmpAuthenticationMode.
                         - Modify the value of hwXponDeviceOntSnmpPrivacyMode.
                         "

           REVISION      "201411250900Z"
           DESCRIPTION   "V1.83, changes in this revision:
                         - Add the leaf hwGponDeviceAutoFindOntCustomizedInfo  in table hwGponDeviceAutoFindOntControlTable
                         - Add the leaf hwGponDeviceOntConfigCustomizedInfo  in table hwGponDeviceOntConfigTable
                         "
           REVISION      "201410230900Z"
           DESCRIPTION   "V1.82, changes in this revision:
                         - Modify the value range of the leaf hwGponDevicePortidMapTrafficTableId, hwGponDeviceOntPortidTrafficTableId and hwGponDeviceOntIgmpForwardPriority.
                         - Modify the MAX-ACCESS value of the leaf hwGponDeviceOntProfileRowStatus, hwGponOntVlanRowStatus, hwGponDeviceAlarmThresholdRowStatus, hwEponDeviceOntProfileRowStatus, hwEponDeviceOntObjectEntryStatus,
                           hwEponOntVlanRowStatus, hwXponDeviceOntSnmpRowStatus, hwGponOntPortVlanTranslationRowStatus, hwOntLoadSelectRowStatus, hwGponOntSnmpStaticRouteRowStatus, hwGponOntPortVlanCfgRowStatus, hwGponDeviceEthPortBundleCfgRowStatus, hwGponDeviceOntUpIgmpMsgForwardRowStatus.
                         "

           REVISION      "201409120900Z"
           DESCRIPTION   "V1.81, changes in this revision:
                         - Modify the value range of the leaf hwGponDeviceOltObjectManualDetectRogueOnt.
                         "

           REVISION      "201407300900Z"
           DESCRIPTION   "V1.80, changes in this revision:
                         - Add leaf hwGponDeviceOpticsDdmAlarmProfileOntCatvRxOpticAlarmUpper and hwGponDeviceOpticsDdmAlarmProfileOntCatvRxOpticAlarmLower in table hwGponDeviceOpticsDdmAlarmProfileInfoTable.
                         - Modify the value range of the leaf hwXponDeviceOntSnmpVersion, hwXponDeviceOntSnmpReadCommunityName, hwXponDeviceOntSnmpWriteCommunityName in table hwXponDeviceOntSnmpProfileTable.
                         - Add the leaf hwXponDeviceOntSnmpUsmUsername, hwXponDeviceOntSnmpAuthenticationMode, hwXponDeviceOntSnmpAuthenticationPassword, hwXponDeviceOntSnmpPrivacyMode, hwXponDeviceOntSnmpPrivacyPassword, hwXponDeviceOntSnmpSecurityLevel in table hwXponDeviceOntSnmpProfileTable.
                         "

           REVISION      "201407100900Z"
           DESCRIPTION   "V1.79, changes in this revision:
                         - Add leaf hwGponOntCatvTxPower in table hwGponOntCatvPortCfgTable.
                         "
            REVISION     "201407060900Z"
            DESCRIPTION  "V1.78, changes in this revision:
                         - Add a enum values of the the leaf node hwGponDeviceTcontAdditionalBandwidth.
                         "
            REVISION     "201406160900Z"
            DESCRIPTION  "V1.77, changes in this revision:
                         - Fix the errors for OMSYS.
                         "

       REVISION     "201402210900Z"
       DESCRIPTION "V1.76, changes in this revision:
                    - Modify the value range of leaf hwGponOpticsModuleXponSubType in table hwGponOltOpticsModuleInformationTable.
                    - Add a enum values of the leaf node hwGponOntRegisterInfoDownCause.
                    - Add a enum values of the leaf node hwGponDeviceOntObjectLastDownCause.
                    - Add a enum values of the leaf node hwGponDynamicMacQueryType.
                    - Add the leaf hwGponDeviceOltObjectFirstIdleGemportid in table hwGponDeviceOltConfigTable.
                    - Add the leaf hwGponDeviceOltObjectManualCheckRogueOnt in table hwGponDeviceOltControlTable.
                    - Modify the leaf hwGponDynamicMacVlanId from read-only to not-accessible.
                    - Modify the leaf hwGponDynamicMacIndex from read-only to not-accessible.
                    - Modify the leaf hwGponDynamicMacQueryType from read-only to not-accessible.
                    - Modify the leaf hwGponDynamicMacQueryPara0 from read-only to not-accessible.
                    - Modify the leaf hwGponDynamicMacQueryPara1 from read-only to not-accessible.
                    - Modify the leaf hwGponDynamicMacQueryPara2 from read-only to not-accessible.
                    - Modify the leaf hwGponDynamicMacQueryPara3 from read-only to not-accessible.
                    - Modify the leaf hwGponOntRegisterInfoIndex from read-only to not-accessible.
                    - Modify the description of hwGponDeviceOntObjectLastDownCause.
                    - Add a enum values of the leaf node hwGponOntRegisterInfoDownCause.
                    - Add leaf hwGponDeviceTcontFixDelay in table hwGponDeviceTcontProfileTable.
                    - Add leaf hwGponDeviceTcontAdditionalBandwidth in table hwGponDeviceTcontProfileTable.
                    - Add leaf hwGponDeviceTcontPriority in table hwGponDeviceTcontProfileTable.
                    - Add leaf hwGponDeviceTcontWeight in table hwGponDeviceTcontProfileTable.
                    "

       REVISION     "201308270900Z"
       DESCRIPTION "V1.75, changes in this revision:
                    - Rename hwGponOntEthPortExtConfigTable to hwGponOntPortExtConfigTable.
                    - Rename hwGponOntEthPortExtConfigEntry to hwGponOntPortExtConfigEntry.
                    - Rename hwGponOntEthPortQinqMode to hwGponOntPortQinqMode.
                    - Rename hwGponOntEthPortPriorityPolicy to hwGponOntPortPriorityPolicy.
                    - Rename hwGponOntEthPortDscpProfileIndex to hwGponOntPortDscpProfileIndex.
                    - Rename hwGponOntEthPortMaxMacAddressNum to hwGponOntPortMaxMacAddressNum.
                    - Rename hwGponOntEthPortIgmpForwardMode to hwGponOntPortUpIgmpForwardMode.
                    - Rename hwGponOntEthPortUpIgmpTransmitMode to hwGponOntPortUpIgmpTransmitMode.
                    - Rename hwGponOntEthPortUpIgmpMsgTranslationVlan to hwGponOntPortUpIgmpMsgTranslationVlan.
                    - Rename hwGponOntEthPortUpIgmpMsgPriority to hwGponOntPortUpIgmpMsgPriority.
                    - Add a enum values of the leaf node hwGponOntPortType.
                    - Add the leaf hwGponDeviceOntProfileVdslPortNum in table hwGponDeviceOntProfileControlTable.
                    - Add a enum values of the leaf node hwGponDevicePortidMapObjectPortType.
                    - Add a enum values of the leaf node hwGponOntVlanPortType.
                    - modify the description of the leaf hwGponDeviceOntObjectIgmpSwitchVlan.
                    - Add a enum values of the leaf node hwGponDevicePortidMapObjectPortTypeIndex.
                    - Add a enum values of the leaf node hwGponOntPortVlanCfgOntPhyType.
                    - Add a table of hwGponDeviceOntUpIgmpMsgConfigTable.
                    - Add the leaf hwGponOntEthPortDownstreamMode in table hwGponOntPortExtConfigTable.
                    - Add the leaf hwGponOntifEthernetPortActualRingStatus in table HwGponOntifEthernetObjectEntry.
                    - Add the leaf hwGponDeviceOntRingCheckSwitch,hwGponDeviceOntRingCheckAutoShutdownSwitch,hwGponDeviceOntRingCheckDetectingFrequency
                      and hwGponDeviceOntRingCheckResumeInterval in table hwGponDeviceOntExtConfigTable.
                    - Modify the leaf name from hwGponDevicePortidMapTrafficTblId to hwGponDevicePortidMapTrafficTableId in table hwGponDevicePortidMapControlTable.
                    - Add the leaf hwGponDevicePortidMapTrafficTableName in table hwGponDevicePortidMapControlTable.
                    - Modify the leaf name from hwGponDeviceOntPortidTrafficTblId to hwGponDeviceOntPortidTrafficTableId in table hwGponDeviceOntPortidControlTable.
                    - Add the leaf hwGponDeviceOntPortidTrafficTableName in table hwGponDeviceOntPortidControlTable.
                    - Modify the leaf name form hwGponOntEthPortUpStreamCarProfile to hwGponOntEthPortUpStreamCarTrafficTableId in table hwGponDeviceOntPortidControlTable.
                    - Add the leaf hwGponOntEthPortUpStreamCarTrafficTableName in table hwGponDeviceOntPortidControlTable.
                    - Modify the leaf name form hwGponOntEthPortDownStreamCarProfile to hwGponOntEthPortDownStreamCarTrafficTableId in table hwGponDeviceOntPortidControlTable.
                    - Add the leaf hwGponOntEthPortDownStreamCarTrafficTableName in table hwGponDeviceOntPortidControlTable.
                    - modify the description of hwGponDeviceOntObjectLastDownCause.
                    "
       REVISION     "201305070000Z"
       DESCRIPTION "V1.74, changes in this revision:
                   - Add the leaf hwGponDeviceOntTr069ManagementIpIndex in table hwGponDeviceOntExtConfigTable.
                   - Add two enum values of the leaf node hwGponOpticsMDConnector.
                   - Modify the description of the leaf hwGponOpticsMDIdentifier in table hwGponOltOpticsModuleInformationTable.
                   - Modify the enum name from bySerialIDOnly to byTwowireOnly and the description of the leaf hwGponOpticsMDExtID in table hwGponOltOpticsModuleInformationTable.
                   - Add a enum values of the leaf node hwGponOpticsMDEncoding.
                   - Modify the description of the leaf hwGponOpticsMDOptions in table hwGponOltOpticsModuleInformationTable.
                   - Modify the description of the leaf hwGponOpticsMDEnhancedOptions in table hwGponOltOpticsModuleInformationTable.
                   - Modify the enum name from includesRev94SFF8472 to includesRev95SFF8472 and the description of the leaf hwGponOpticsMDSFF8472Compliance
                     in table hwGponOltOpticsModuleInformationTable.
                   - Add three enum values of the leaf node hwGponOpticsMDSFF8472Compliance.
                   - Add enum values of the leaf node hwGponOntTDMPortOperateStatus, hwGponDeviceTDMPortCodeMode, hwGponOntTDMPortOnlineState and hwGponDeviceOntTdmPortLoopback.
                   - Add the leaf hwGponOntTDMPortTxClockMode in table hwGponOntTDMPortCfgTable.
                   - Modify the value range of leaf hwGponDeviceEthPortBundleCfgIndex in table hwGponDeviceEthPortBundleCfgTable.
                   "

       REVISION     "201302260000Z"
       DESCRIPTION "V1.73, changes in this revision:
                   - Add a table HwGponDeviceOntMulticastPortIdControlTable.
                   - Add the leaf hwGponOntCatvFrequency in table hwGponOntCatvPortCfgTable.
                   "

       REVISION     "201301210000Z"
       DESCRIPTION "V1.72, changes in this revision:
                   - Add leaves hwGponOntTrafficFlowStatsUpFcsErrorCnt, hwGponOntTrafficFlowStatsUpFrameBitErrorRatio,
                      hwGponOntTrafficFlowStatsUpEthFrameErrorRatio, hwGponOntTrafficFlowStatsUpGemFrameErrorRatio
                      in table hwGponOntTrafficFlowStatsTable.
                   "

       REVISION     "201212040000Z"
       DESCRIPTION "V1.71, changes in this revision:
                   - Add the leaf hwGponDeviceOltObjectEnergySavingFlag in table hwGponDeviceOltControlTable.
                       - Add a enum values of the leaf node hwGponDevicePortidMapObjectPortTypeIndex and hwGponDevicePortidMapObjectPortType.
                   "

       REVISION     "201210230000Z"
       DESCRIPTION "V1.70, changes in this revision:
                   - Add the leaf hwGponDeviceOntMulticastMode in table hwGponDeviceOntExtConfigTable.
                   "

       REVISION     "201207200000Z"
       DESCRIPTION "V1.69, changes in this revision:
                   - Delete unnecessary en dashes.
                   "
       REVISION     "201206180900Z"
       DESCRIPTION "V1.68, changes in this revision:
                   - Delete the leaf node hwGponDeviceOntVoipCfgMethod in table hwGponDeviceOntExtConfigTable, the leaf node hwGponDeviceOntVoipCfgMethod has never been used.
                   "

       REVISION     "201206010900Z"
       DESCRIPTION "V1.67, changes in this revision:
                   - Add the leaf hwOntLoadXmlAES128Key in table hwOntLoadCtrlTable.
                   "

       REVISION     "201204210900Z"
       DESCRIPTION "V1.66, changes in this revision:
                   - Modify the value range of leaf hwOntLoadSelectActiveMode in table hwOntLoadSelectTable.
                   - Modify the value range of leaf hwOntLoadImageActiveMode in table hwOntLoadCtrlTable.
                   - Modify hwGponDeviceOntPoridTcontAverBand to hwGponDeviceOntPortidTcontAverBand.
                   - Modify hwGponDeviceOntPoridTcontMaxBand to hwGponDeviceOntPortidTcontMaxBand.
                   - Modify hwGponDeviceOntPoridTrafficTblId to hwGponDeviceOntPortidTrafficTblId.
                   - Delete the default value of hwGponDeviceOntUpPqColorPolicy and hwGponDeviceOntDownPqColorPolicy.
                     "

       REVISION     "201112280900Z"
       DESCRIPTION "V1.65, changes in this revision:
                    - Add leaf hwGponDeviceOntUpPqColorPolicy and hwGponDeviceOntDownPqColorPolicy in table hwGponDeviceOntExtConfigTable.
                    - Modify the value range of leaf hwGponDevicePortidMapObjectVlanID in table hwGponDevicePortidMapControlTable.
                    - Add leaf hwGponDeviceOntPortidObjectDownPQIndex in table hwGponDeviceOntPortidControlTable.
                    - Modify the definition of the leaf hwGponDeviceOntPortidObjectUpPQIndex in table hwGponDeviceOntPortidControlTable
                    - Modify the description of the leaf hwGponDeviceOntPortidObjectUpPQIndex in table hwGponDeviceOntPortidControlTable
                    - Add leaf hwGponDeviceEncryptionKeyErrorsOfOnuThreshold, hwGponDeviceXgemKeyErrorsOfOnuThreshold and hwGponDeviceXgemHecErrorCountOfOnuThreshold
                     in table hwGponDeviceAlarmProfileTable
                    - Add leaf hwOntLoadSelectPriority and hwOntLoadSelectActiveMode in table hwOntLoadSelectTable.
                    - Add leafs hwGponDeviceRegOntPassword, hwGponDeviceRegOntVendorId, hwGponDeviceRegOntVersion, hwGponDeviceRegOntMainSoftVersion, hwGponDeviceRegOntEquipmentId
                     hwGponDeviceRegOntLoid, hwGponDeviceRegOntCheckcode in table hwGponDeviceOntRegInfoTable.
                     "

       REVISION     "201112051050Z"
       DESCRIPTION "V1.64, changes in this revision:
                   - Modify the type and description of leaf hwGponOntPortVlanCfgEtherType.
                   - Add a enum values of the leaf node hwXponDeviceModeCfg.
                   - Add leaf hwGponOntifEthernetActualDuplex in table hwGponOntifEthernetObjectTable.
                   - Add leaf hwGponOntifEthernetActualSpeed in table hwGponOntifEthernetObjectTable.
                   - Modify the description of leaf hwGponDeviceOltObjectnearest.
                   - Modify the description of leaf hwGponDeviceOltObjectfarthest.
                   - Add leaf hwGponOntTrafficFlowStatsUpFecCodeDecodCorrectCnt in table hwGponOntTrafficFlowStatsTable.
                   - Add leaf hwGponOntTrafficFlowStatsUpFecCodeCnt in table hwGponOntTrafficFlowStatsTable.
                   - Add leaf hwGponOntGemPortTransmittedGemFrames in table hwGponOntGemPortStatsTable.
                   - Modified description of the hwGponOntStatisticsTable.
                   - Modify the definition of the leaf hwGponDeviceOltObjectDnFecEnabled in table hwGponDeviceOltConfigTable.
                   - Add leafs hwGponDeviceUpstreamPQDiscardedBytesThreshold and hwGponDeviceDownstreamPQDiscardedBytesThreshold in table HwGponDeviceAlarmProfileTable.
                   "

       REVISION     "201110270900Z"
       DESCRIPTION "V1.63, changes in this revision:
                    - Modify the word hybrid to Hybrid.
                    - Modify the word Vender to Vendor.
                   "

       REVISION     "201109070900Z"
       DESCRIPTION "V1.62, changes in this revision:
                    - Modify the spelling mistake of word--porfile.
                   "

       REVISION     "201108090900Z"
       DESCRIPTION "V1.61, changes in this revision:
                    - Modify the definition of the leaf node hwGponDeviceRegOntResult.
                   "

       REVISION     "201107200900Z"
       DESCRIPTION "V1.60, changes in this revision:
                    - Add leaf hwGponDeviceRegConflictedIfindex in table hwGponDeviceOntRegInfoTable.
                    - Add leaf hwGponDeviceRegConflictedOntIndex in table hwGponDeviceOntRegInfoTable.
                    - Modify the definition of the leaf node hwGponDeviceRegOntResult.
                    - Add leaf hwGponOntEtherStatsPkts1519toOversizeOctets in table hwGponOntEtherStatsTable.
                   "

       REVISION     "201106280900Z"
       DESCRIPTION  "V1.59, changes in this revision:
                     - Add leaf hwGponOntEthPortMaxMacAddressNum in table hwGponOntEthPortExtConfigTable.
                     - Add leaf hwGponOntEtherStatsSendOctets in table HwGponOntEtherStatsTable for indicates the sent Octets.
                     - Add leaf hwGponOntEtherStatsForwardDropEvents in table HwGponOntEtherStatsTable for indicates the sent DropEvents.
                     - Add leaf hwGponOntEtherStatsSendPkts64Octets in table HwGponOntEtherStatsTable for indicates the sent 65~127-octet frames.
                     - Add leaf hwGponOntEtherStatsSendPkts65to127Octets in table HwGponOntEtherStatsTable for indicates the sent 65~127-octet frames .
                     - Add leaf hwGponOntEtherStatsSendPkts128to255Octets  in table HwGponOntEtherStatsTable for indicates the sent 128~255-octet frames.
                     - Add leaf hwGponOntEtherStatsSendPkts256to511Octets in table HwGponOntEtherStatsTable for indicates the sent 256~511-octet frames.
                     - Add leaf hwGponOntEtherStatsSendPkts512to1023Octets in table HwGponOntEtherStatsTable for indicates the sent 512~1023-octet frames.
                     - Add leaf hwGponOntEtherStatsSendPkts1024to1518Octets in table HwGponOntEtherStatsTable for indicates the sent 1024~1518-octet frames.
                     - Add leaf hwGponOntEtherStatsSendPktsOversize in table HwGponOntEtherStatsTable for indicates the sent oversize frames.
                     - Modify the description of the leaf node hwGponDeviceOntProfilePotsNum in table HwGponDeviceOntProfileControlTable.
                     - Modify the description of the leaf node hwGponDeviceOntProfileCatvUniNum in table HwGponDeviceOntProfileControlTable.
                     - Modify the description of the leaf node hwGponDeviceOntProfileEthNum in table HwGponDeviceOntProfileControlTable.
                     - Move all TRAP objects from HUAWEI-GPON-MIB.mib to HUAWEI-XPON-TRAP-MIB.mib.
                     - Add leaf hwGponOntTrafficFlowStatsUpFecDecodCorrectCnt,hwGponOntTrafficFlowStatsUpFecDecodUnCorrectCnt,
                       hwGponOntTrafficFlowStatsUpHecCheckErrCnt,hwGponOntTrafficFlowStatsDowiAlarmCnt,
                       hwGponOntTrafficFlowStatsClear in table hwGponOntTrafficFlowStatsTable.
                     "

       REVISION     "201105310900Z"
       DESCRIPTION  "V1.58, changes in this revision:
                     - Add leaf hwGponDeviceOntVoipCfgMethod in table hwGponDeviceOntExtConfigTable.
                     - Modify the description of leaf hwGponOntAuthInfoConflictAlarmTrap.
                     - Add leaf hwGponDeviceOntObjectMemoryOccupation, hwGponDeviceOntObjectCpuOccupation,
                     hwGponDeviceOntObjectTemperature in table hwGponDeviceOntControlTable.
                     - Add leaf hwGponDeviceFECCorrectCodeWordsThreshold in table hwGponDeviceAlarmProfileTable.
                     - Modify the type of hwGponDeviceFECUncorrectCodeWordsThreshold from Integer32 to Gauge32.
                     - Modify the enum values of the leaf node hwGponDynamicMacQueryType.
                     - Modify the definition of the leaf node hwGponDynamicMacAddr.
                     - Modify the enum values and definition of the leaf node hwGponOntRegisterInfoDownCause.
                     - Modify the definition of the leaf node hwGponDeviceOntObjectLastDownCause.
                     - Modify the type and description of leaf hwGponOntPortVlanCfgEtherType.
                    "

       REVISION     "201101280900Z"
       DESCRIPTION  "V1.57, changes in this revision:
                     - Modify the enum values of the node of hwGponOntifEthernetDuplex and hwGponOntifEthernetSpeed.
                    "

       REVISION     "201101180900Z"
       DESCRIPTION  "V1.57, changes in this revision:
                     - Add leaf hwGponDeviceFECUncorrectCodeWordsThreshold in table hwGponDeviceAlarmProfileTable.
                     - Delete the default value of the following leave:
                       hwGponDeviceOntReDiscovery, hwGponDevicePortidOntLoopback, hwGponDeviceOntTdmLocalInnerLoopback,
                       hwGponDeviceOntUpIgmpMsgProcMode,hwGponDeviceOntMulticastCtrlMode.
                     - Add leaf hwGponOntEthPortIgmpForwardMode in hwGponOntEthPortExtConfigTable for ONT port IGMP forward mode switch.
                     - Add leaf hwGponOntEthPortUpIgmpTransmitMode in hwGponOntEthPortExtConfigTable for the upstream igmp transmit mode of GPON ONT port.
                     - Add leaf hwGponOntEthPortUpIgmpMsgTranslationVlan in hwGponOntEthPortExtConfigTable for the translation VLAN of GPON ONT port,when the upstream igmp transmit mode is translation or default in the GPON ONT port.
                     - Add leaf hwGponOntEthPortUpIgmpMsgPriority in hwGponOntEthPortExtConfigTable for the upstream igmp packets priority of GPON ONT port.
                    "

       REVISION     "201012100900Z"
       DESCRIPTION  "V1.56, changes in this revision:
                     - Add the node of hwGponDeviceOntAuthEffectMode to set the effect taking mode.
                    "

       REVISION     "201011190900Z"
       DESCRIPTION  "V1.55, changes in this revision:
                     - Modify the description of the following leaves:
                       hwGponDeviceOntObjectLastDownCause
                       hwGponDeviceTcontType
                       hwGponDeviceOntObjectIgmpSwitchVlan
                       hwGponDeviceOntIgmpForwardTranslationVlan
                       hwGponOntPortVlanCfgSPri
                       "

       REVISION     "201011030900Z"
       DESCRIPTION  "V1.54, changes in this revision:
                     - Modify the node of hwGponDeviceOntObjectAuthMethod.
                     - Add the node of hwGponDeviceOntObjectLoid, hwGponDeviceOntObjectCheckcode
                       and hwGponDeviceOntObjectSoftWorkMode to support the LOID and checkcode authentication modes of the ONT.
                     - Add leaf nodes hwGponDeviceAutoFindOntLoid and hwGponDeviceAutoFindOntCheckcode
                       in table hwGponDeviceAutoFindOntControlTable to obtain the LOID and checkcode of the ONT.
                     - Modify the definition of the trap node hwGponOntDiscoveryAlarmTrap, hwGponDiscoveredOntDeletedAlarmTrap,
                       hwGponDistModeOntInfoTrap, hwGponDeviceOntAutoFindTrap and hwGponDeviceOntVersionTrap.
                     - Add leaf nodes hwGponOntRegisterInfoLoid and hwGponOntRegisterInfoCheckcode
                       in table hwGponOntRegisterExInfoTable.
                     - Add leaf hwGponDeviceOntObjectReregisterAuthMode in hwGponDeviceOntConfigTable for Re-Register.
                     - Modify the definition of the leaf node hwGponDistModeOntInfoTrap.
                    "

       REVISION     "201010130900Z"
       DESCRIPTION  "V1.53, changes in this revision:
                     - Add leaf hwGponOntIpconfigDhcpReset in hwGponDeviceOntIpConfigTable for config gpon reset IP host in the DHCP mode.
                     - Change the description of hwGponDeviceOntObjectTimeOut, hwGponOntifEthernetNegotiate, hwGponOntifEthernetFlowCtrlSwitch, hwGponOntPortVlanCfgTlsSwitch and hwGponDeviceOntObjectCRCCode.
                     - Add invalid value for the MIB standardization.
                    "

       REVISION     "201009280900Z"
       DESCRIPTION  "V1.52, changes in this revision:
                     - Modify the description of the whole MIB file."

       REVISION     "201009160900Z"
       DESCRIPTION  "V1.51, changes in this revision:
                     - Modify the definition of the leaf node hwGponDeviceOntBatteryCurStatus."

       REVISION     "201008110900Z"
       DESCRIPTION  "V1.50, changes in this revision:
                     - Add leaf hwGponDeviceOltObjectTcontNumCombined in hwGponDeviceOltControlTable for T-CONT auto-combine.
                     - Add leaf hwGponDeviceOltObjectTcontNumInCard in hwGponDeviceOltControlTable for T-CONT auto-combine.
                     - Add leaf hwGponDeviceOntObjectTcontNumCombined in hwGponDeviceOntControlTable for T-CONT auto-combine.
                     - Modify the description of the lead hwGponDeviceAutoFindOntAge.
                     - Modify the value range of the leaf hwGponDeviceOntObjectAuthMethod, hwGponDeviceOntObjectDbaStatus, hwGponDeviceOntTransparent,
                       hwGponDeviceOntObjectIgmpMode, hwGponDeviceOntMacAddressSwitch, hwGponDeviceOntObjectManageMode, hwGponDeviceOntUpIgmpMsgProcMode."

       REVISION     "201006300900Z"
       DESCRIPTION  "V1.49, changes in this revision:
                     Add the definition of the node, include:hwGponGEMMappingCfgChangeTrap, hwGponONTGEMPortCfgChangeTrap,
                     hwGponOntPortVlanCfgTrap, hwGponDevProfileCfgTrap, hwGponGEMPortCfgChangeTrap, hwGponTcontProfileOperateTrap,
                     hwGponDistModeOntInfoTrap.
                     Modify the definition of the leaf node, include:hwGponDeviceOntRunStateChangeTrap,hwOntLoadFileType
                     hwOntLoadProtocol, hwGponDeviceOntDualUpstreamSupport, hwGponDeviceOntVersionTrap.
                     Add leaf nodes hwGponDeviceOntObjectPGMemberRole in table hwGponDeviceOntConfigTable for trap optimization.
                     Add leaf hwGponDevicePortidMapTransparent in table hwGponDevicePortidMapControlEntry.
                    "

       REVISION     "201006220900Z"
       DESCRIPTION  "V1.48, changes in this revision:
                     Modify chinese character and module name.
                     Modify the definition difference between MIB file and tree.c.
                    "

       REVISION     "201005250900Z"
       DESCRIPTION  "V1.47, changes in this revision:
                     Add a new table hwGponOltDualparentTable for typeb dual parent protect group.
                     Add leaf node hwGponDeviceOntObjectProductDescription in table hwGponDeviceOntConfigTable for get ont product description.
                     Add a new table hwGponOntRegisterExInfoTable.
                     Add a new table hwGponDeviceRogueOntTable.
                     Add leaf node hwGponDeviceOntObjectPrimaryStatus hwGponDeviceOntObjectSecondaryStatus
                     in table hwGponDeviceOntControlTable for getting the PST and SST.
                     Add a enum invalid(255) for the leaf hwOntLoadFileType.
                     Add a enum invalid(255) for the leaf hwOntLoadProtocol.
                     Modify the range from 1..80 to 0..80 for the leaf hwOntLoadFileName.
                     Modify the range from 1..16 to 0..16 for the leaf hwOntLoadUserName.
                     Modify the range from 1..16 to 0..16 for the leaf hwOntLoadPassword.
                    "

       REVISION     "201005050900Z"
       DESCRIPTION  "V1.46, changes in this revision:
                     Modify the errors of the MIB file.
                    "

       REVISION     "201004140900Z"
       DESCRIPTION  "V1.45, changes in this revision:
                     Add an enum ippath (61) for the leaf hwGponDevicePortidMapObjectPortType.
                     Add leaf node hwGponOntPortVlanCfgDscpDefaultPriority in table hwGponOntPortVlanCfgTable for setting the default
                     priority for the dscp-mapping policy.
                     Add leaf node hwGponOntIpIndex in table hwGponDeviceOntIpConfigTable for setting the ip inteface index.
                     Add leaf node hwGponOntIpconfigDscpProfIndex in table hwGponDeviceOntIpConfigTable for setting the dscp profile
                     of the ip interface.
                     Add leaf node hwGponOntIpconfigDscpDefaultPriority in table hwGponDeviceOntIpConfigTable for setting the default
                     priority for the dscp-mapping policy.
                     Modify the description of the leaf node hwGponOntIpConfigVlan and hwGponOntIpConfigPriority.
                     Add leaf node hwGponOntPortVlanCfgTlsSwitch in table hwGponOntPortVlanCfgTable for config the vlan attribute of transparent.
                     Add leaf node hwGponDeviceOntTr069Management in table HwGponDeviceOntExtConfigEntry
                     for non_OMCI management config of the ONT.
                     Add leaf node hwGponOntOpticsDdmAniCATVRxPower in table hwGponDeviceOntOpticsDdmInfoTable for
                     obtaining the CATV receiving optical power of the optical module.
                     Add leaf node hwGponOntPortVlanCfgSPriPolicy in table hwGponOntPortVlanCfgTable for setting S-VLAN priority.
                     Add leaf node hwGponOntEthPortDscpProfileIndex in table hwGponOntEthPortExtConfigTable for setting the dscp
                     profile of the ont eth port.
                     Add leaf node hwGponOntEthPortDscpProfileIndex in table hwGponOntIpHostPortCfgTable for setting the dscp profile of
                     the ont iphost port.
                     Add leaf node hwGponOntEthPortDscpProfileIndex in table hwGponOntMocaPortCfgTable for setting the dscp profile of
                     the ont moca port.
                     Modify the length of the attribute value for the node, include:hwGponDeviceOltCfgOpticAlarmProfileName, hwGponDeviceOntObjectPassword,
                     hwGponDeviceOntObjectRefAlarmProfileName, hwGponDeviceOntObjectVersion, hwGponDeviceOntObjectEquipmentId, hwGponDeviceOntObjectMainSoftVer,
                     hwGponDeviceOntObjectStandbySoftVer, hwGponDeviceOntObjectSnmpProfileName, hwGponDeviceOntCfgOpticAlarmProfileName.
                     Modify the attribute value, include node:hwGponDeviceOltControlLastDownCause, hwGponDeviceOntObjectDiscoveryStatus, hwGponDeviceOntBatteryCurStatus,
                     hwGponDevicePortidOntLoopback, hwGponOntifEthernetDuplex, hwGponOntifEthernetSpeed.
                    "

       REVISION     "201003220900Z"
       DESCRIPTION  "V1.44, changes in this revision:
                     Add leaf notes hwGponOpticsModuleXponType, hwGponOpticsModuleXponSubType, hwGponOpticsModuleXponUsedType
                     and hwGponOpticsModuleXponEncapsulationType in table hwGponOltOpticsModuleInformationTable for the query of
                     Huawei extended information of optical module.
                     "

       REVISION     "201002080900Z"
       DESCRIPTION  "V1.43, changes in this revision:
                     Modify the definition of the trap node hwGponDeviceOntAutoFindTrap, hwGponDiscoveredOntDeletedAlarmTrap,
                     hwGponOntDiscoveryAlarmTrap.
                     Change the data type form SnmpAdminString to MacAddress,include :hwGponOntPhyAddress, hwEponDeviceOntObjectMacAddress, hwEponDeviceAutoFindOntMacAddress.
                     "

       REVISION     "201001120900Z"
       DESCRIPTION  "V1.42, changes in this revision:
                     Add the definition of the trap node.
                     "
       REVISION     "200912310900Z"
       DESCRIPTION  "V1.41, changes in this revision:
                     Add a new table hwGponDynamicMacQueryTable for querying dynamic MAC address of the ONT.
                     Modify the data type of the leaf hwGponOntPhyAddress.
                     Add a enumeration of the leaf hwGponOntIpConfigMode for querying the IP configuration
                     of the ONT.
                    "

       REVISION     "200911280900Z"
       DESCRIPTION  "V1.39, changes in this revision:
                     Add table hwGponDeviceEthPortBundleCfgTable for setting ONT port-bundle.
                     Add leaf node hwGponOntPortVlanCfgEtherType in table hwGponOntPortVlanCfgTable
                     for setting service encapsulation type of ONT port.
                     Add leaf nodes hwGponDeviceOntObjectOMCCEncrypt, hwGponDeviceOntIgmpForwardPriority
                     and hwGponDeviceOntNativeVlanOption for setting the encrypt status of OMCC downstream,
                     the priority of upstream igmp packets and native VLAN option.
                     Add leaf nodes hwGponOntEthPortUpStreamCarProfile and hwGponOntEthPortDownStreamCarProfile
                     in table hwGponOntEthPortExtConfigTable for the upstream and downstream CAR profiles of ONT port.
                     Add enum eth-bundle(254) in hwGponDevicePortidMapObjectPortType leaf node for the eth-bundle port type.
                    "

       REVISION     "200906020900Z"
       DESCRIPTION  "V1.30, changes in this revision:
                     Add table hwGponOntPortVlanCfgTable for setting the VLAN configuration of ONT port.
                     Add leaf node hwGponOntOpticsOltRxOntPower in table hwGponDeviceOntOpticsDdmInfoTable
                     for obtaining the ONT power received by the OLT.
                     Add leaf node hwGponDeviceOntUpFEC in table hwGponDeviceOntExtConfigTable
                     for setting GPON ONT upstream FEC.
                     Add scalar hwGponDeviceDbaBandwidthTypeCfg for setting the type of DBA bandwidth.
                     Add scalar hwGponDeviceDbaAssignmentModeCfg for setting assignment mode of DBA bandwidth.
                    "

       REVISION     "200805300900Z"
       DESCRIPTION  "V1.20, changes in this revision:
                     Add table hwXponDeviceOntSnmpProfileTable for setting MXU SNMP Agent configuration information.
                     Add leaf node hwGponGemportStatisticsClear in table hwGponGemportStatisticsTable
                     for clearing the GEM port statistics information.
                     Add leaf node hwGponOntStatisticsClear in table hwGponOntStatisticsTable for clearing
                     the ONT statistics information.
                     Add leaf node hwGponOltGtcStatisticsClear in table hwGponGtcStatisticTable for clearing
                     GPON port GTC statistics informaion.
                     Add leaf node hwGponOltEtherStatisticClear in table hwGponOltEtherStatisticTable for
                     clearing GPON port Ethernet statistics information.
                     Add leaf node hwGponOntGemPortClear in table hwGponOntGemPortStatsTable for clearing ONT GEM Port
                     statistics information.
                     Add leaf node hwGponDeviceOntBatteryCurStatus in table hwGponDeviceOntControlTable
                     for obtaining ONT battery status.
                     Add leaf node hwGponDeviceOntObjectSnmpProfileName for setting the SNMP profile
                     which the ONT is bound to.
                     Add leaf node hwGponDeviceOntObjectManageMode for setting the ONT management mode.
                    "

       REVISION     "200709100900Z"
       DESCRIPTION  "V1.10, changes in this revision:
                     Modify the OID of the table hwEponDeviceCtcRemoteOntPortVLANTranslationTable
                     from 1.3.6.1.4.1.2011.5.100.1.1.1.46 to 1.3.6.1.4.1.2011.5.100.1.1.1.49.
                     Modify the OID of the table hwEponDeviceCtcRemoteOntPortVLANConfigurationTable
                     from 1.3.6.1.4.1.2011.5.100.1.1.1.45 to 1.3.6.1.4.1.2011.5.100.1.1.1.46.
                     Modify the OID of the table hwEponDeviceCtcRemoteOntMulticastCtrItemTable
                     from 1.3.6.1.4.1.2011.5.100.1.1.1.44 to 1.3.6.1.4.1.2011.5.100.1.1.1.45.
                     Add table hwEponOntCapabilityTable for obtaining the capability of ONT.
                     Add leaf node hwEponOltStatsClear in table hwEponOltStatsTable for clearing
                     EPON port statistics information.
                     Add leaf node hwEponOntELPortStatsClear in table hwEponOntELPortStatsTable
                     for clearing ONT statistics information.
                     Modify the OID of the leaf node hwEponDeviceOltObjectDespt in table hwEponDeviceOltConfigTable
                     from 1.3.6.1.4.1.2011.5.100.1.1.1.33.1.4 to 1.3.6.1.4.1.2011.5.100.1.1.1.33.1.3.
                    "

       REVISION     "200604270900Z"
       DESCRIPTION  "V1.00, Initial version."
       ::= { huaweiMgmt 100 }


   hwGponDeviceObjectMIB OBJECT IDENTIFIER ::= { hwGponDeviceMIB 1}

   hwGponDeviceObjects OBJECT IDENTIFIER ::= { hwGponDeviceObjectMIB  1}

   hwGponDeviceControlObjects OBJECT IDENTIFIER ::= { hwGponDeviceObjects 1}

   hwGponDeviceStatObjects OBJECT IDENTIFIER ::= { hwGponDeviceObjects 2}

   hwGponDeviceLineTestObjects OBJECT IDENTIFIER ::= { hwGponDeviceObjects 16}

--   DisplayString ::= OCTET STRING

   VlanIndex ::= TEXTUAL-CONVENTION
            STATUS current
            DESCRIPTION
                "A value used to index per-VLAN tables: values of 0 and
                 4095 are not permitted; if the value is between 1 and
                 4094 inclusive, it represents an IEEE 802.1Q VLAN-ID with
                 global scope within a given bridged domain (see VlanId
                 textual convention). If the value is greater than 4095
                 then it represents a VLAN with scope local to the
                 particular agent, i.e. one without a global VLAN-ID
                 assigned to it. Such VLANs are outside the scope of
                 IEEE 802.1Q but it is convenient to be able to manage them
                 in the same way using this MIB.
                "
            SYNTAX Unsigned32

   PortList ::= TEXTUAL-CONVENTION
            STATUS current
            DESCRIPTION
                "Each octet within this value specifies a set of eight
                 ports, with the first octet specifying ports 1 through
                 8, the second octet specifying ports 9 through 16 and others.
                 Within each octet, the most significant bit represents
                 the lowest numbered port, and the least significant bit
                 represents the highest numbered port. Thus, each port
                 of the bridge is represented by a single bit within the
                 value of this object. If that bit has a value of '1'
                 then that port is included in the set of ports; the port
                 is not included if its bit has a value of '0'.
                "
            SYNTAX OCTET STRING

    OntList ::= TEXTUAL-CONVENTION
            STATUS current
            DESCRIPTION
                "Each octet within this value specifies a set of eight
                 onts, with the first octet specifying ports 0 through
                 7, the second octet specifying ports 8 through 15 and others.
                 Within each octet, the most significant bit represents
                 the lowest numbered ont, and the least significant bit
                 represents the highest numbered ont. Thus, each ont
                 of the bridge is represented by a single bit within the
                 value of this object. If that bit has a value of '1'
                 then that ont is included in the set of onts; the ont
                 is not included if its bit has a value of '0'.
                "
            SYNTAX OCTET STRING

    -- hwGponDeviceAutoFindOntAge
    hwGponDeviceAutoFindOntAge OBJECT-TYPE
        SYNTAX Integer32
        MAX-ACCESS read-write
        STATUS current
        DESCRIPTION
                "The aging time of the auto-found ONT, which can be 0s (indicating that the ONT will not aging) or a value from 100s to 300s"
        ::= { hwGponDeviceObjects 3 }

    -- hwGponDeviceAutoFindInterval
    hwGponDeviceAutoFindInterval OBJECT-TYPE
        SYNTAX Integer32
        MAX-ACCESS read-write
        STATUS current
        DESCRIPTION
            "Auto find interval, ranging from 1(s) to 10(s)."
        ::= { hwGponDeviceObjects 4 }

    -- hwGponDeviceBroadcastPortId
    hwGponDeviceBroadcastPortId OBJECT-TYPE
        SYNTAX Integer32
        MAX-ACCESS read-write
        STATUS current
        DESCRIPTION
            "The special GEM Port ID used for the broadcast service.
             Ranging from 4000 to 4095.
            "
        ::= { hwGponDeviceObjects 5 }

    -- hwGponDeviceMulticastPortId
    hwGponDeviceMulticastPortId OBJECT-TYPE
        SYNTAX Integer32
        MAX-ACCESS read-write
        STATUS current
        DESCRIPTION
            "The special GEM Port ID used for the multicast service.
             Ranging from 4000 to 4095.
            "
        ::= { hwGponDeviceObjects 6 }

    -- hwGponDeviceInvalidPortId
    hwGponDeviceInvalidPortId  OBJECT-TYPE
        SYNTAX Integer32
        MAX-ACCESS read-write
        STATUS current
        DESCRIPTION
            "Invalid GEM Port ID.
             Ranging from 4000 to 4095.
            "
        ::= { hwGponDeviceObjects 7 }

    hwGponDeviceConfigResume  OBJECT-TYPE
        SYNTAX INTEGER {
            resume(1),
            noresume(2)
        }
        MAX-ACCESS read-write
        STATUS current
        DESCRIPTION
            "This is the policy of the system to resume the configuration of the ONT.
             Options:
             1. resume(1)   -resume the configuration of the ONT
             2. noresume(2) -no resume the configuration of the ONT
            "
        ::= { hwGponDeviceObjects 8 }

     --epon new add scalar node
    hwEponMulticastControlMode  OBJECT-TYPE
        SYNTAX INTEGER {
            ctc(1),
            igmpsnooping(2)
        }
        MAX-ACCESS read-write
        STATUS current
        DESCRIPTION
            "Multicast control mode.
             Options:
             1. ctc(1)          - The multicast control mode is ctc
             2. igmpsnooping(2) - The multicast control mode is igmpsnooping
            "
        ::= { hwGponDeviceObjects 9 }


    hwEponDeviceCtcOui  OBJECT-TYPE
        SYNTAX SnmpAdminString
        MAX-ACCESS read-write
        STATUS current
        DESCRIPTION
            "ID of the organization issuing the extended OAM. It is used to check whether the system supports the extended OAM when it is found.
            "
        ::= { hwGponDeviceObjects 10 }

     hwEponDeviceChangePasswordAge  OBJECT-TYPE
        SYNTAX Integer32
        MAX-ACCESS read-write
        STATUS current
        DESCRIPTION
            "Update period of the encryption key of the ONT.
             Ranging from 1 to 254.
            "
        ::= { hwGponDeviceObjects 11 }

    hwGponDeviceBaseGemport  OBJECT-TYPE
        SYNTAX Integer32
        MAX-ACCESS read-write
        STATUS current
        DESCRIPTION
            "This object is used to set the start GEM port ID of the entire system in the GEM port CoS rate limitation mode.
             Ranging from 128 to 3872.
            "
        ::= { hwGponDeviceObjects 12 }

    -- hwGponDeviceMinBandwidth
    hwGponDeviceMinBandwidth OBJECT-TYPE
        SYNTAX Integer32
        MAX-ACCESS read-write
        STATUS current
        DESCRIPTION
            "The scalar is used to configure the minimum bandwidth of the T-CONTs in the system.
             Ranging from 384 to 1024.
            "
        ::= { hwGponDeviceObjects 13 }

    hwXponDeviceModeCfg  OBJECT-TYPE
        SYNTAX  INTEGER
          {
              distributingmode(1),
              profilemode(2),
              profilemodeAndMerge(3)
          }
        MAX-ACCESS  read-write
        STATUS  current
        DESCRIPTION
            "This object is used to change XPON management mode.
             After the mode being changed, system will automatically
             save data and reboot.
             Options:
             1. distributingmode(1)    - Distributing mode
             2. profilemode(2)         - Profile mode
             3. profilemodeAndMerge(3) - Profile mode and merge the same ONT line-profiles and ONT srv-profiles
            "
        ::= { hwGponDeviceObjects 14 }

     hwGponDeviceAutoDetectRogueOnt  OBJECT-TYPE
        SYNTAX  INTEGER
          {
              on(1),
              off(2)
          }
        MAX-ACCESS read-write
        STATUS  current
        DESCRIPTION
            "This object is used to open/close the switch of rogue ONT automatic detection.
             Options:
             1. on(1)  - Open the switch of rogue ONT automatic detection
             2. off(2) - Close the switch of rogue ONT automatic detection
            "
        ::= { hwGponDeviceObjects 15 }

    -- BEGIN: z00130281 add for gpbd new attribute  2009-05-05
     hwGponDeviceDbaBandwidthTypeCfg  OBJECT-TYPE
        SYNTAX  INTEGER
          {
              gpon(1),
              ethernet(2)
          }
        MAX-ACCESS read-write
        STATUS  current
        DESCRIPTION
            "This object is used to configure the type of DBA bandwidth.
             Options:
             1. gpon(1)     - gpon type
             2. ethernet(2) - ethernet type
            "
        ::= { hwGponDeviceObjects 20 }

     hwGponDeviceDbaAssignmentModeCfg  OBJECT-TYPE
        SYNTAX  INTEGER
          {
              maxbandwidthusage(1),
              minloopdelay(2),
              manual(3)
          }
        MAX-ACCESS read-write
        STATUS  current
        DESCRIPTION
            "This object is used to configure the DBA bandwidth assignment mode.
             Options:
             1. maxbandwidthusage(1) - max bandwidth usage mode
             2. minloopdelay(2)      - min loop delay mode
             3. manual(3)            - manual mode
            "
        ::= { hwGponDeviceObjects 21 }
    -- END: z00130281 add for gpbd new attribute  2009-05-05

    -- Table1 HwGponDeviceOltConfigTable
    hwGponDeviceOltConfigTable OBJECT-TYPE
        SYNTAX  SEQUENCE OF HwGponDeviceOltConfigEntry
        MAX-ACCESS  not-accessible
        STATUS  current
        DESCRIPTION
            "The configuration table of the GPON OLT.
             The index of this table is ifIndex.
            "
        ::= { hwGponDeviceControlObjects 1 }

    hwGponDeviceOltConfigEntry OBJECT-TYPE
        SYNTAX  HwGponDeviceOltConfigEntry
        MAX-ACCESS  not-accessible
        STATUS  current
        DESCRIPTION
            "The configuration table of the GPON OLT.
             The index of this entry is ifIndex.
            "
        INDEX  { ifIndex }
        ::= { hwGponDeviceOltConfigTable 1 }

    HwGponDeviceOltConfigEntry  ::=
        SEQUENCE {
         hwGponDeviceOltObjectnearest                      Integer32,
         hwGponDeviceOltObjectfarthest                     Integer32,
         hwGponDeviceOltObjectDnFecEnabled                 INTEGER,
         hwGponDeviceOltObjectAutofindOntEnable            INTEGER,
         hwGponDeviceOltObjectChangePasswordAge            Integer32,
         hwGponDeviceOltObjectDespt                        OCTET STRING,
         hwGponDeviceOltObjectLeftBandWidth                Integer32,
         hwGponDeviceOltObjectMinBandwidth                 Integer32,
         hwGponDeviceOltObjectAvailableBandWidth           Integer32,
         hwGponDeviceOltCfgOpticAlarmProfileName           OCTET STRING,
         hwGponDeviceOltObjectFirstIdleGemportid           Integer32
        }

    hwGponDeviceOltObjectnearest OBJECT-TYPE
        SYNTAX  Integer32
        MAX-ACCESS  read-write
        STATUS  current
        DESCRIPTION
            "This is the fiber distance between the OLT and the nearest ONT.
             For GPON, the fiber distance between the OLT and the nearest ONT
             is 0 km to 40 km while the maximum fiber distance between the farthest
             and the nearest ONTs is 20 km.
             For XG-PON, the fiber distance between the OLT and the nearest ONT
             is 0 km to 60 km while the maximum fiber distance between the farthest
             and the nearest ONTs is 40 km.
            "
        ::= { hwGponDeviceOltConfigEntry 1 }

    hwGponDeviceOltObjectfarthest OBJECT-TYPE
        SYNTAX  Integer32
        MAX-ACCESS read-write
        STATUS  current
        DESCRIPTION
            "This is the fiber distance between the OLT and the farthest ONT.
             For GPON, the fiber distance between the OLT and the nearest ONT
             is 0 km to 60 km while the maximum fiber distance between the farthest
             and the nearest ONTs is 20 km.
             For XG-PON, the fiber distance between the OLT and the nearest ONT
             is 0 km to 100 km while the maximum fiber distance between the farthest
             and the nearest ONTs is 40 km.
            "
         ::= { hwGponDeviceOltConfigEntry 2 }

    hwGponDeviceOltObjectDnFecEnabled OBJECT-TYPE
        SYNTAX  INTEGER {
               enable (1),
               disable (2)
        }
        MAX-ACCESS  read-write
        STATUS  current
        DESCRIPTION
            "Downstream FEC enable switch.
             Options:
             1. enable (1)  - Enable downstream FEC switch
             2. disable (2) - Disable downstream FEC switch
             For GPON, the default value is disable(2).
             For XG-PON, the default value is enable(1).
            "
        ::= { hwGponDeviceOltConfigEntry 4 }

    hwGponDeviceOltObjectAutofindOntEnable OBJECT-TYPE
        SYNTAX  INTEGER {
                enable (1),
                disable (2)
        }
        MAX-ACCESS read-write
        STATUS  current
        DESCRIPTION
            "ONT auto find enable switch.
             Options:
             1. enable (1)  - Enable ONT auto find switch
             2. disable (2) - Disable ONT auto find switch
            "
        DEFVAL { disable }
        ::= { hwGponDeviceOltConfigEntry 8 }

    hwGponDeviceOltObjectChangePasswordAge OBJECT-TYPE
        SYNTAX  Integer32
        MAX-ACCESS  read-write
        STATUS  current
        DESCRIPTION
            "ONT password update period. 0 means no update, range: 0 or 5~1440 minutes."
        DEFVAL { 0 }
        ::= { hwGponDeviceOltConfigEntry 9 }

    hwGponDeviceOltObjectDespt OBJECT-TYPE
        SYNTAX  OCTET STRING(SIZE(0..80))
        MAX-ACCESS  read-write
        STATUS  current
        DESCRIPTION
            "The port description contains a maximum of 80 characters."
        ::= { hwGponDeviceOltConfigEntry 13 }

    hwGponDeviceOltObjectLeftBandWidth OBJECT-TYPE
        SYNTAX  Integer32
        MAX-ACCESS  read-only
        STATUS  current
        DESCRIPTION
            "The left bandwidth of the port."
        ::= { hwGponDeviceOltConfigEntry 14 }

     hwGponDeviceOltObjectMinBandwidth OBJECT-TYPE
        SYNTAX  Integer32
        MAX-ACCESS  read-write
        STATUS  current
        DESCRIPTION
            "The minimum bandwidth of T-CONTs in the OLT port, range:384Kbps~1024Kbps."
        ::= { hwGponDeviceOltConfigEntry 15 }

     hwGponDeviceOltObjectAvailableBandWidth OBJECT-TYPE
         SYNTAX Integer32
         MAX-ACCESS read-only
         STATUS current
         DESCRIPTION
            "Available BandWidth,units of kbps."
         ::= { hwGponDeviceOltConfigEntry 16 }

     hwGponDeviceOltCfgOpticAlarmProfileName OBJECT-TYPE
          SYNTAX     OCTET STRING (SIZE (0..32))
          MAX-ACCESS   read-write
          STATUS      current
          DESCRIPTION
              "The optical alarm profile name that port bound."
          ::= { hwGponDeviceOltConfigEntry 17 }

     hwGponDeviceOltObjectFirstIdleGemportid OBJECT-TYPE
         SYNTAX Integer32
         MAX-ACCESS read-only
         STATUS current
         DESCRIPTION
            "First idle GEM port ID."
         ::= { hwGponDeviceOltConfigEntry 18 }

    -- Table2 HwGponDeviceOltControlTable
    hwGponDeviceOltControlTable OBJECT-TYPE
        SYNTAX  SEQUENCE OF HwGponDeviceOltControlEntry
        MAX-ACCESS  not-accessible
        STATUS  current
        DESCRIPTION
            "The control table of the GPON OLT.
             The index of this table is ifIndex."
        ::= { hwGponDeviceControlObjects 2 }

    hwGponDeviceOltControlEntry OBJECT-TYPE
        SYNTAX  HwGponDeviceOltControlEntry
        MAX-ACCESS  not-accessible
        STATUS  current
        DESCRIPTION
            "The control table of the GPON OLT.
             The index of this entry is ifIndex."
        INDEX { ifIndex }
        ::= { hwGponDeviceOltControlTable 1 }

    HwGponDeviceOltControlEntry ::=
        SEQUENCE {
         hwGponDeviceOltObjectLaserSwitch               INTEGER,
         hwGponDeviceOltLoopbackGemportid               Integer32,
         hwGponDeviceOltObjectStatus                    INTEGER,
         hwGponDeviceOltObjectManualDetectRogueOnt      INTEGER,
         hwGponDeviceOltObjectIlegalIncurRogueOntExt    INTEGER,
         hwGponDeviceOltObjectOpticMoudleStatus         INTEGER,
         hwGponDeviceOltControlLastUpTime               DateAndTime,
         hwGponDeviceOltControlLastDownTime             DateAndTime,
         hwGponDeviceOltControlLastDownCause            INTEGER,
         hwGponDeviceOltObjectTcontNumCombined          Integer32,
         hwGponDeviceOltObjectTcontNumInCard            Integer32,
         hwGponDeviceOltObjectEnergySavingFlag          INTEGER,
         hwGponDeviceOltObjectManualCheckRogueOnt       INTEGER,
         hwGponDeviceOltObjectPortReset                 INTEGER
        }

    hwGponDeviceOltObjectLaserSwitch OBJECT-TYPE
        SYNTAX  INTEGER {
                on (1),
                off (2)
        }
        MAX-ACCESS  read-write
        STATUS  current
        DESCRIPTION
                "Laser switch of the GPON port.
                 Options:
                 1. on (1)  - Open the laser switch of the GPON port
                 2. off (2) - Close the laser switch of the GPON port
                "
        DEFVAL { on }
        ::= { hwGponDeviceOltControlEntry 1 }

     hwGponDeviceOltLoopbackGemportid OBJECT-TYPE
        SYNTAX  Integer32
        MAX-ACCESS  read-only
        STATUS  current
        DESCRIPTION
            "Loopback GEM port ID."
        ::= { hwGponDeviceOltControlEntry 2 }

     hwGponDeviceOltObjectStatus OBJECT-TYPE
        SYNTAX  INTEGER {
                up (1),
                down (2)
        }
        MAX-ACCESS  read-only
        STATUS  current
        DESCRIPTION
            "The GPON port status in the OLT.
             Options:
             1. up (1)   -normal
             2. down (2) -fault
            "
        ::= { hwGponDeviceOltControlEntry 3 }

        hwGponDeviceOltObjectManualDetectRogueOnt OBJECT-TYPE
        SYNTAX  INTEGER {
                startup (1),
                invalidValue(-1)
        }
        MAX-ACCESS  read-write
        STATUS  current
        DESCRIPTION
            "Rogue ONT manual detection.
             Options:
             1. startup (1) - Rogue ONT manual detection is startup
             2. invalidValue(-1) - Invalid value
            "
        ::= { hwGponDeviceOltControlEntry 4 }

     hwGponDeviceOltObjectIlegalIncurRogueOntExt OBJECT-TYPE
        SYNTAX  INTEGER {
                inexistent (0),
                existent (1),
                invalidValue(-1)
        }
        MAX-ACCESS  read-only
        STATUS  current
        DESCRIPTION
            "Querying whether there are illegal incursionary rogue ONTs under port.
             Options:
             1. inexistent (0)   - There aren't illegal incursionary rogue ONTs under port
             2. existent (1)     - There are illegal incursionary rogue ONTs under port
             3. invalidValue(-1) - Invalid value
            "
        ::= { hwGponDeviceOltControlEntry 5 }

     hwGponDeviceOltObjectOpticMoudleStatus OBJECT-TYPE
        SYNTAX  INTEGER {
                online  (1),
                offline (2),
                invalidValue(-1)
        }
        MAX-ACCESS  read-only
        STATUS  current
        DESCRIPTION
            "The optic module status on GPON port.
             Options:
             1. online  (1)      - The optic module online
             2. offline (2)      - The optic module offline
             3. invalidValue(-1) - Invalid value
            "
        ::= { hwGponDeviceOltControlEntry 6 }

     hwGponDeviceOltControlLastUpTime OBJECT-TYPE
        SYNTAX DateAndTime
        MAX-ACCESS  read-only
        STATUS current
        DESCRIPTION
            "The time for PON port's last up.
             The time starts from 00:00 o'clock on January 1, 1970.
             Unit: seconds
            "
        ::= { hwGponDeviceOltControlEntry 7 }

     hwGponDeviceOltControlLastDownTime OBJECT-TYPE
        SYNTAX DateAndTime
        MAX-ACCESS  read-only
        STATUS current
        DESCRIPTION
            "The time for PON port's last down.
             The time starts from 00:00 o'clock on January 1, 1970.
             Unit: seconds
            "
        ::= { hwGponDeviceOltControlEntry 8 }

     hwGponDeviceOltControlLastDownCause OBJECT-TYPE
        SYNTAX INTEGER{
               los(1),
               opticModuleAbsence(2),
               opticModuleFault(3),
               opticPortClosed(4),
               otherCause(-1)
        }
        MAX-ACCESS  read-only
        STATUS current
        DESCRIPTION
            "The cause of PON port's last down.
             Options:
             1. los(1)                 - Loss of signal
             2. opticModuleAbsence(2)  - Indicates that the optical transceiver is not installed
             3. opticModuleFault(3)    - Indicates that the optical transceiver is faulty
             4. opticPortClosed(4)     - Indicates that the optical port is shut down
             5. otherCause(-1)         - Indicates that the query fails or no information is detected
            "
        ::= { hwGponDeviceOltControlEntry 9 }

     hwGponDeviceOltObjectTcontNumCombined OBJECT-TYPE
        SYNTAX Integer32
        MAX-ACCESS read-only
        STATUS current
        DESCRIPTION
            "The number of the combined T-CONTs."
        ::= { hwGponDeviceOltControlEntry 10 }

     hwGponDeviceOltObjectTcontNumInCard OBJECT-TYPE
        SYNTAX Integer32
        MAX-ACCESS read-only
        STATUS current
        DESCRIPTION
            "The number of T-CONTs in the card."
        ::= { hwGponDeviceOltControlEntry 11 }

     hwGponDeviceOltObjectEnergySavingFlag OBJECT-TYPE
        SYNTAX  INTEGER {
                yes (1),
                no  (2)
        }
        MAX-ACCESS  read-only
        STATUS  current
        DESCRIPTION
                "Energy saving state of the GPON port.
                 Options:
                 1. yes (1)  - The GPON port is in energy saving state
                 2. no (2)   - The GPON port is not in energy saving state
                "
        ::= { hwGponDeviceOltControlEntry 12 }

     hwGponDeviceOltObjectManualCheckRogueOnt OBJECT-TYPE
        SYNTAX  INTEGER {
                startup(1),
                invalid(-1)
        }
        MAX-ACCESS  read-write
        STATUS  current
        DESCRIPTION
                "This object indicates the switch of the rogue ONT manual check.
                 Options:
                 1. startup(1)    - Start up the switch of the rogue ONT manual checked
                 2. invalid(-1)   - Indicates that the query fails or no information is checked
                "
        ::= { hwGponDeviceOltControlEntry 13 }

     hwGponDeviceOltObjectPortReset OBJECT-TYPE
		SYNTAX  INTEGER {
		    reset(1),
		    invalid(-1)
		}
		MAX-ACCESS  read-write
		STATUS  current
		DESCRIPTION
		    "This parameter is used to reset the port.
		     Options:
		     1. reset(1)      - Indicates that the port resets
		     2. invalid(-1)   - Indicates that the query fails or no information is checked
		    "
		::= { hwGponDeviceOltControlEntry 14 }

     -- TABLE3 hwGponDeviceOntProfileControlTable
    hwGponDeviceOntProfileControlTable OBJECT-TYPE
       SYNTAX     SEQUENCE OF HwGponDeviceOntProfileControlEntry
       MAX-ACCESS not-accessible
       STATUS     current
       DESCRIPTION
               "This is the ONT capability set profile table.
                This table is used to create, delete, modify and query an ONT capability
                set profile. Ensure that the profile is not bound with the ONT before you
                delete or modify it.
                The index of this table is hwGponDeviceOntProfileNameIndex, which is the profile name.
               "
       ::= { hwGponDeviceControlObjects 20 }

   hwGponDeviceOntProfileControlEntry OBJECT-TYPE
       SYNTAX     HwGponDeviceOntProfileControlEntry
       MAX-ACCESS not-accessible
       STATUS     current
       DESCRIPTION
               "This is the ONT capability set profile table.
                This table is used to create, delete, modify and query an ONT capability
                set profile. Ensure that the profile is not bound with the ONT before you
                delete or modify it.
                The index of this entry is hwGponDeviceOntProfileNameIndex, which is the profile name.
               "
       INDEX       { IMPLIED hwGponDeviceOntProfileNameIndex }
       ::= { hwGponDeviceOntProfileControlTable 1 }

   HwGponDeviceOntProfileControlEntry ::=
       SEQUENCE {
                hwGponDeviceOntProfileNameIndex          OCTET STRING,
                hwGponDeviceOntProfileRefNum             Integer32,
                hwGponDeviceOntProfilePonAniNum          Integer32,
                hwGponDeviceOntProfileUniConfig          INTEGER,
                hwGponDeviceOntProfileMACBridge          INTEGER,
                hwGponDeviceOntProfilePotsNum            Integer32,
                hwGponDeviceOntProfileIPSupport          Integer32,
                hwGponDeviceOntProfileFeNum              Integer32,
                hwGponDeviceOntProfileGeNum              Integer32,
                hwGponDeviceOntTdmPortType               INTEGER,
                hwGponDeviceOntProfileE1T1TYPE           INTEGER,
                hwGponDeviceOntProfileE1T1Num            Integer32,
                hwGponDeviceOntProfileMocaNum            Integer32,
                hwGponDeviceOntProfileCatvAniNum         Integer32,
                hwGponDeviceOntProfileCatvUniNum         Integer32,
                hwGponDeviceOntProfileGemPortNum         Integer32,
                hwGponDeviceOntProfileGemPortMap         INTEGER,
                hwGponDeviceOntProfileTcontNum           Integer32,
                hwGponDeviceOntProfileTcont0PQNum        Integer32,
                hwGponDeviceOntProfileTcont1PQNum        Integer32,
                hwGponDeviceOntProfileTcont2PQNum        Integer32,
                hwGponDeviceOntProfileTcont3PQNum        Integer32,
                hwGponDeviceOntProfileTcont4PQNum        Integer32,
                hwGponDeviceOntProfileTcont5PQNum        Integer32,
                hwGponDeviceOntProfileTcont6PQNum        Integer32,
                hwGponDeviceOntProfileTcont7PQNum        Integer32,
                hwGponDeviceOntProfileRowStatus          RowStatus,
                hwGponDeviceOntProfileFCType             INTEGER,
                hwGponDeviceOntProfileEthNum             Integer32,
                hwGponDeviceOntProfileVdslPortNum        Integer32,
                hwGponDeviceOntProfileMaxNumOfAdapPotsPort Integer32,
                hwGponDeviceOntProfileMaxNumOfAdapEthPort  Integer32,
                hwGponDeviceOntProfileMaxNumOfAdapVdslPort Integer32,
                hwGponDeviceOntProfileMaxNumOfAdapCatvPort Integer32,
                hwGponDeviceOntProfileWifiPortNum        Integer32
    }

   hwGponDeviceOntProfileNameIndex OBJECT-TYPE
       SYNTAX     OCTET STRING (SIZE (1..63))
       MAX-ACCESS    not-accessible
       STATUS      current
       DESCRIPTION
           "The name of the ONT capability set profile."
       ::= { hwGponDeviceOntProfileControlEntry 1 }

   hwGponDeviceOntProfileRefNum OBJECT-TYPE
       SYNTAX     Integer32
       MAX-ACCESS    read-only
       STATUS      current
       DESCRIPTION
           "The binding times of the profile."
       ::= { hwGponDeviceOntProfileControlEntry 2 }

   hwGponDeviceOntProfilePonAniNum OBJECT-TYPE
       SYNTAX     Integer32
       MAX-ACCESS    read-write
       STATUS      current
       DESCRIPTION
           "The number of PON ports of online links."
       ::= { hwGponDeviceOntProfileControlEntry 3 }

   hwGponDeviceOntProfileUniConfig OBJECT-TYPE
       SYNTAX       INTEGER {
                  attention(1),
                  noattention(2)
       }
       MAX-ACCESS    read-write
       STATUS      current
       DESCRIPTION
           "The UNI configuration concerned option.
            Options:
            1. attention(1)   - attention the UNI configuration
            2. noattention(2) - noattention the UNI configuration
           "
       ::= { hwGponDeviceOntProfileControlEntry 4 }


   hwGponDeviceOntProfileMACBridge OBJECT-TYPE
       SYNTAX     INTEGER {
                   single(1),
                   multi(2)
                   }
       MAX-ACCESS    read-write
       STATUS      current
       DESCRIPTION
           "The MAC bridge type.
            Options:
            1. single(1) - The MAC bridge type is single
            2. multi(2)  - The MAC bridge type is multi
           "
       ::= { hwGponDeviceOntProfileControlEntry 5 }

   hwGponDeviceOntProfilePotsNum OBJECT-TYPE
       SYNTAX     Integer32
       MAX-ACCESS    read-write
       STATUS      current
       DESCRIPTION
           "The number of POTS ports.
            A special value of 0xFE (254) indicates the number of port is adaptive."
       ::= { hwGponDeviceOntProfileControlEntry 6 }

   hwGponDeviceOntProfileIPSupport OBJECT-TYPE
       SYNTAX     Integer32 (0..3)
       MAX-ACCESS    read-write
       STATUS      current
       DESCRIPTION
           "The IP config mode.
            0 - not support
            1 - support
            2 - dhcp
            3 - manual
           "
       ::= { hwGponDeviceOntProfileControlEntry 7 }

   hwGponDeviceOntProfileFeNum OBJECT-TYPE
       SYNTAX     Integer32
       MAX-ACCESS    read-write
       STATUS      current
       DESCRIPTION
               "The number of FE ports"
       ::= { hwGponDeviceOntProfileControlEntry 8 }

   hwGponDeviceOntProfileGeNum OBJECT-TYPE
       SYNTAX     Integer32
       MAX-ACCESS    read-write
       STATUS      current
       DESCRIPTION
           "The number of GE ports."
       ::= { hwGponDeviceOntProfileControlEntry 9 }

    hwGponDeviceOntTdmPortType OBJECT-TYPE
       SYNTAX     INTEGER {
              t1(13),
              e1(14),
              invalidValue(-1)
              }
       MAX-ACCESS    read-write
       STATUS      current
       DESCRIPTION
           "The TDM port type.
            Options:
            1. t1(13)           -The TDM port type is t1
            2. e1(14)           -The TDM port type is e1
            3. invalidValue(-1) -Invalid value
           "
       ::= { hwGponDeviceOntProfileControlEntry 10 }

   hwGponDeviceOntProfileE1T1TYPE OBJECT-TYPE
       SYNTAX     INTEGER {
                  tdmovergem(1),
                  cesop(2)
                  }
       MAX-ACCESS    read-write
       STATUS      current
       DESCRIPTION
           "The TDM service type.
            Options:
            1. tdmovergem(1) -The TDM service type is tdmovergem
            2. cesop(2)      -The TDM service type is cesop
           "
       ::= { hwGponDeviceOntProfileControlEntry 11 }

   hwGponDeviceOntProfileE1T1Num OBJECT-TYPE
       SYNTAX     Integer32
       MAX-ACCESS    read-write
       STATUS      current
       DESCRIPTION
           "The number of TDM ports."
       ::= { hwGponDeviceOntProfileControlEntry 12 }

   hwGponDeviceOntProfileMocaNum OBJECT-TYPE
       SYNTAX     Integer32
       MAX-ACCESS    read-write
       STATUS      current
       DESCRIPTION
           "The number of MOCA ports."
       ::= { hwGponDeviceOntProfileControlEntry 13 }

   hwGponDeviceOntProfileCatvAniNum OBJECT-TYPE
       SYNTAX     Integer32
       MAX-ACCESS    read-write
       STATUS      current
       DESCRIPTION
           "The number of CATV ANI ports."
       ::= { hwGponDeviceOntProfileControlEntry 14 }

     hwGponDeviceOntProfileCatvUniNum OBJECT-TYPE
       SYNTAX     Integer32
       MAX-ACCESS    read-write
       STATUS      current
       DESCRIPTION
           "The number of CATV UNI ports.
            A special value of 0xFE (254) indicates the number of port is adaptive."
       ::= { hwGponDeviceOntProfileControlEntry 15 }

     hwGponDeviceOntProfileGemPortNum OBJECT-TYPE
       SYNTAX     Integer32
       MAX-ACCESS    read-write
       STATUS      current
       DESCRIPTION
           "The number of GEM ports."
       ::= { hwGponDeviceOntProfileControlEntry 16 }

     hwGponDeviceOntProfileGemPortMap OBJECT-TYPE
       SYNTAX     INTEGER {
                  vlan(1),
                  pri8021p(2),
                  vlanpri(3),
                  port(4),
                  vlanport(5),
                  portpri(6),
                  vlanpriport(7),
                  e1t1port(8),
                  iptos(9),
                  vlaniptos(10)
                  }
       MAX-ACCESS    read-write
       STATUS      current
       DESCRIPTION
           "Mode of the mapping from the data service stream to GemPort.
            Options:
            1. vlan(1)          -Indicates the VLAN ID mapping
            2. pri8021p(2)      -Indicates the 802.1p priority mapping
            3. vlanpri(3)       -Indicates the VLAN ID and 802.1p priority mapping
            4. port(4)          -Indicates the port mapping
            5. vlanport(5)      -Indicates the VLAN ID and port mapping
            6. portpri(6)       -Indicates the 802.1p priority and port mapping
            7. vlanpriport(7)   -Indicates the VLAN ID and 802.1p priority and port mapping
            8. e1t1port(8)      -Indicates the E1T1 port mapping
            9. iptos(9)         -Indicates the IPTOS mapping
            10. vlaniptos(10)   -Indicates the IPTOS and VLAN ID mapping
           "
       ::= { hwGponDeviceOntProfileControlEntry 17 }

     hwGponDeviceOntProfileTcontNum OBJECT-TYPE
       SYNTAX     Integer32
       MAX-ACCESS    read-write
       STATUS      current
       DESCRIPTION
           "The number of T-CONTs."
       ::= { hwGponDeviceOntProfileControlEntry 18 }

     hwGponDeviceOntProfileTcont0PQNum OBJECT-TYPE
       SYNTAX     Integer32
       MAX-ACCESS    read-write
       STATUS      current
       DESCRIPTION
           "The number of PQs in T-CONT 0."
       ::= { hwGponDeviceOntProfileControlEntry 19 }

          hwGponDeviceOntProfileTcont1PQNum OBJECT-TYPE
       SYNTAX     Integer32
       MAX-ACCESS    read-write
       STATUS      current
       DESCRIPTION
           "The number of PQs in T-CONT 1."
       ::= { hwGponDeviceOntProfileControlEntry 20 }

           hwGponDeviceOntProfileTcont2PQNum OBJECT-TYPE
       SYNTAX     Integer32
       MAX-ACCESS    read-write
       STATUS      current
       DESCRIPTION
           "The number of PQs in T-CONT 2."
       ::= { hwGponDeviceOntProfileControlEntry 21 }

           hwGponDeviceOntProfileTcont3PQNum OBJECT-TYPE
       SYNTAX     Integer32
       MAX-ACCESS    read-write
       STATUS      current
       DESCRIPTION
           "The number of PQs in T-CONT 3."
       ::= { hwGponDeviceOntProfileControlEntry 22 }

           hwGponDeviceOntProfileTcont4PQNum OBJECT-TYPE
       SYNTAX     Integer32
       MAX-ACCESS    read-write
       STATUS      current
       DESCRIPTION
           "The number of PQs in T-CONT 4."
       ::= { hwGponDeviceOntProfileControlEntry 23 }


    hwGponDeviceOntProfileTcont5PQNum OBJECT-TYPE
       SYNTAX     Integer32
       MAX-ACCESS    read-write
       STATUS      current
       DESCRIPTION
           "The number of PQs in T-CONT 5."
       ::= { hwGponDeviceOntProfileControlEntry 24 }

     hwGponDeviceOntProfileTcont6PQNum OBJECT-TYPE
       SYNTAX     Integer32
       MAX-ACCESS    read-write
       STATUS      current
       DESCRIPTION
           "The number of PQs in T-CONT 6."
       ::= { hwGponDeviceOntProfileControlEntry 25 }

     hwGponDeviceOntProfileTcont7PQNum OBJECT-TYPE
       SYNTAX     Integer32
       MAX-ACCESS    read-write
       STATUS      current
       DESCRIPTION
           "The number of PQs in T-CONT 7."
       ::= { hwGponDeviceOntProfileControlEntry 26 }


     hwGponDeviceOntProfileRowStatus OBJECT-TYPE
       SYNTAX     RowStatus
       MAX-ACCESS    read-create
       STATUS      current
       DESCRIPTION
           "The row status, which is used to differentiate the creation, modification and deletion of a row.
            Options:
            1. createAndGo(4) -create a new instance of a conceptual row
            2. destroy(6)     -delete the instances associated with an existing conceptual row
           "
       ::= { hwGponDeviceOntProfileControlEntry 27 }


       hwGponDeviceOntProfileFCType OBJECT-TYPE
       SYNTAX     INTEGER {
                  pq(1),
                  gemportcar(2),
                  flowcar(3)
                  }
       MAX-ACCESS    read-write
       STATUS      current
       DESCRIPTION
           "The type of flow control.
            Options:
            1. pq(1)         - PQ
            2. gemportcar(2) - Gemport car
            3. flowcar(3)    - Flow car
           "
       ::= { hwGponDeviceOntProfileControlEntry 28 }

       hwGponDeviceOntProfileEthNum OBJECT-TYPE
       SYNTAX     Integer32
       MAX-ACCESS    read-write
       STATUS      current
       DESCRIPTION
           "The number of ETH ports.
            A special value of 0xFE (254) indicates the number of port is adaptive."
       ::= { hwGponDeviceOntProfileControlEntry 29 }

       hwGponDeviceOntProfileVdslPortNum OBJECT-TYPE
       SYNTAX     Integer32
       MAX-ACCESS    read-write
       STATUS      current
       DESCRIPTION
           "The number of VDSL ports.
            A special value of 0xFE (254) indicates the number of port is adaptive."
       ::= { hwGponDeviceOntProfileControlEntry 30 }

     hwGponDeviceOntProfileMaxNumOfAdapPotsPort OBJECT-TYPE
       SYNTAX     Integer32
       MAX-ACCESS    read-write
       STATUS      current
       DESCRIPTION
           "This object indicates the max number of adaptive pots ports.
            Range: 1-32. 32 is default value."
       ::= { hwGponDeviceOntProfileControlEntry 31 }

     hwGponDeviceOntProfileMaxNumOfAdapEthPort OBJECT-TYPE
       SYNTAX     Integer32
       MAX-ACCESS    read-write
       STATUS      current
       DESCRIPTION
           "This object indicates the max number of adaptive eth ports.
            Range: 1-24. 8 is default value."
       ::= { hwGponDeviceOntProfileControlEntry 32 }

     hwGponDeviceOntProfileMaxNumOfAdapVdslPort OBJECT-TYPE
       SYNTAX     Integer32
       MAX-ACCESS    read-write
       STATUS      current
       DESCRIPTION
           "This object indicates the max number of adaptive vdsl ports.
            Range: 1-8. 8 is default value."
       ::= { hwGponDeviceOntProfileControlEntry 33 }

     hwGponDeviceOntProfileMaxNumOfAdapCatvPort OBJECT-TYPE
       SYNTAX     Integer32
       MAX-ACCESS    read-write
       STATUS      current
       DESCRIPTION
           "This object indicates the max number of adaptive catv ports.
            Range: 1-8. 8 is default value."
       ::= { hwGponDeviceOntProfileControlEntry 34 }

     hwGponDeviceOntProfileWifiPortNum OBJECT-TYPE
       SYNTAX     Integer32
       MAX-ACCESS    read-write
       STATUS      current
       DESCRIPTION
           "The number of WiFi ports.
            Range: 0-4. 0 is default value."
       ::= { hwGponDeviceOntProfileControlEntry 35 }

    -- Table4 HwGponDeviceOntConfigTable
    hwGponDeviceOntConfigTable OBJECT-TYPE
        SYNTAX  SEQUENCE OF HwGponDeviceOntConfigEntry
        MAX-ACCESS not-accessible
        STATUS  current
        DESCRIPTION
           "This is the ONT configuration table.
            This table is used to create, modify, delete or query an ONT.
            The indexes of this table are ifIndex and hwGponDeviceOntObjectIndex.
           "
        ::= { hwGponDeviceControlObjects 5 }

    hwGponDeviceOntConfigEntry OBJECT-TYPE
        SYNTAX  HwGponDeviceOntConfigEntry
        MAX-ACCESS not-accessible
        STATUS  current
        DESCRIPTION
           "This is the ONT configuration table.
            This table is used to create, modify, delete or query an ONT.
            The indexes of this entry are ifIndex and hwGponDeviceOntObjectIndex.
           "
        INDEX { ifIndex, hwGponDeviceOntObjectIndex }
        ::= { hwGponDeviceOntConfigTable 1 }

    HwGponDeviceOntConfigEntry ::=
        SEQUENCE {
         hwGponDeviceOntObjectIndex                    Integer32,
         hwGponDeviceOntObjectCapabProfileName         OCTET STRING,
         hwGponDeviceOntObjectAuthMethod               INTEGER,
         hwGponDeviceOntObjectSn                       OCTET STRING,
         hwGponDeviceOntObjectPassword                 OCTET STRING,
         hwGponDeviceOntObjectRefAlarmProfileName      OCTET STRING,
         hwGponDeviceOntObjectDespt                    OCTET STRING,
         hwGponDeviceOntObjectDbaStatus                INTEGER,
         hwGponDeviceOntObjectVersion                  OCTET STRING,
         hwGponDeviceOntObjectVendorId                 Integer32,
         hwGponDeviceOntObjectProductId                Integer32,
         hwGponDeviceOntObjectEquipmentId              OCTET STRING,
         hwGponDeviceOntObjectMainSoftVer              OCTET STRING,
         hwGponDeviceOntObjectStandbySoftVer           OCTET STRING,
         hwGponDeviceOntObjectEntryStatus              RowStatus,
         hwGponDeviceOntObjectTimeOut                  Integer32,
         hwGponDeviceOntObjectLastUpTime               DateAndTime,
         hwGponDeviceOntObjectLastDownTime             DateAndTime,
         hwGponDeviceOntObjectLastDownCause            Integer32,
         hwGponDeviceOntObjectSnmpProfileName          OCTET STRING,
         hwGponDeviceOntObjectManageMode               INTEGER,
         hwGponDeviceOntObjectLastDyingGaspTime        DateAndTime,
         hwGponDeviceOntObjectProtectSide              INTEGER,
         hwGponDeviceOntCfgOpticAlarmProfileName       OCTET STRING,
         hwGponDeviceOntObjectProductDescription       OCTET STRING,
         hwGponDeviceOntObjectPGMemberRole             INTEGER,
         hwGponDeviceOntObjectLoid                     OCTET STRING,
         hwGponDeviceOntObjectCheckcode                OCTET STRING,
         hwGponDeviceOntObjectSoftWorkMode             INTEGER,
         hwGponDeviceOntObjectReregisterAuthMode       INTEGER,
         hwGponDeviceOntAuthEffectMode                 INTEGER,
         hwGponDeviceOntConfigCustomizedInfo           OCTET STRING,
         hwGponDeviceOntObjectNniType                  INTEGER,
         hwGponDeviceOntObjectHostName                 OCTET STRING,
         hwGponDeviceOntObjectEquipmentSn              OCTET STRING,
         hwGponDeviceOntObjectMac                      MacAddress
         }

    hwGponDeviceOntObjectIndex OBJECT-TYPE
        SYNTAX Integer32
        MAX-ACCESS  not-accessible
        STATUS  current
        DESCRIPTION
           "ONT ID."
        ::= { hwGponDeviceOntConfigEntry 1 }

    hwGponDeviceOntObjectCapabProfileName OBJECT-TYPE
       SYNTAX OCTET STRING (SIZE (1..63))
       MAX-ACCESS read-write
       STATUS current
       DESCRIPTION
           "The name of the ONT capability set profile."
       ::= { hwGponDeviceOntConfigEntry 26 }

    hwGponDeviceOntObjectAuthMethod OBJECT-TYPE
        SYNTAX INTEGER {
               sn (1),
               snpassword (2),
               alwayson (3),
               onceon (4),
               loidalwayson (5),
               loidonceon (6),
               loidcheckcodealwayson (7),
               loidcheckcodeonceon (8),
               snorpassword(9),
               invalid (-1)
        }
        MAX-ACCESS read-write
        STATUS  current
        DESCRIPTION
            "The authentication mode for the ONT.
             Options:
             1. sn(1)                        - SN
             2. snpassword(2)                - SN and password
             3. alwayson(3)                  - Password + always-on
             4. onceon(4)                    - Password + once-on
             5. loidalwayson (5)             - LOID + always-on
             6. loidonceon (6)               - LOID + once-on
             7. loidcheckcodealwayson (7)    - LOID + CHECKCODE + always-on
             8. loidcheckcodeonceon (8)      - LOID + CHECKCODE + once-on
             9. snorpassword(9)              - SN or password
             10.invalid(-1)                  - invalid value
            "
        DEFVAL { sn }
        ::= { hwGponDeviceOntConfigEntry 3 }

    hwGponDeviceOntObjectSn OBJECT-TYPE
        SYNTAX OCTET STRING (SIZE (8))
        MAX-ACCESS read-write
        STATUS  current
        DESCRIPTION
            "The configured ONT serial number."
        ::= { hwGponDeviceOntConfigEntry 4 }

    hwGponDeviceOntObjectPassword OBJECT-TYPE
        SYNTAX OCTET STRING
        MAX-ACCESS read-write
        STATUS  current
        DESCRIPTION
            "The ONT password.
             GPON password size (0..10)
             XG-PON password size (0..36)
            "
        ::= { hwGponDeviceOntConfigEntry 5 }

    hwGponDeviceOntObjectRefAlarmProfileName OBJECT-TYPE
        SYNTAX OCTET STRING (SIZE (0..33))
        MAX-ACCESS read-write
        STATUS current
        DESCRIPTION
            "The name of the ONT alarm profile. This object can only be set by single.
             Input no character means to un-bind the alarm profile with the ONT.
            "
        ::= { hwGponDeviceOntConfigEntry 8 }

   hwGponDeviceOntObjectDespt OBJECT-TYPE
       SYNTAX OCTET STRING (SIZE (1..128))
       MAX-ACCESS read-write
       STATUS current
       DESCRIPTION
           "The description of the ONT."
       ::= { hwGponDeviceOntConfigEntry 14 }

   hwGponDeviceOntObjectDbaStatus OBJECT-TYPE
       SYNTAX INTEGER {
              nsr (1),
              sr (2),
              invalid (-1)
       }
       MAX-ACCESS read-only
       STATUS current
       DESCRIPTION
           "The DBA report status.
            Options:
            1. nsr (1)      -The DBA report status is nsr
            2. sr (2)       -The DBA report status is sr
            3. invalid (-1) -The DBA report status is invalid
           "
       ::= { hwGponDeviceOntConfigEntry 15 }

    hwGponDeviceOntObjectVersion OBJECT-TYPE
       SYNTAX OCTET STRING (SIZE (0..14))
       MAX-ACCESS read-only
       STATUS current
       DESCRIPTION
               "The ONT version number"
       ::= { hwGponDeviceOntConfigEntry 16 }

     hwGponDeviceOntObjectVendorId OBJECT-TYPE
       SYNTAX Integer32
       MAX-ACCESS read-only
       STATUS current
       DESCRIPTION
           "ONT VendorID."
       ::= { hwGponDeviceOntConfigEntry 17 }

      hwGponDeviceOntObjectProductId OBJECT-TYPE
       SYNTAX Integer32
       MAX-ACCESS read-only
       STATUS current
       DESCRIPTION
           "Vendor product ID of the ONT."
       ::= { hwGponDeviceOntConfigEntry 18 }

      hwGponDeviceOntObjectEquipmentId OBJECT-TYPE
       SYNTAX OCTET STRING (SIZE (0..20))
       MAX-ACCESS read-only
       STATUS current
       DESCRIPTION
           "Device ID of the ONT."
       ::= { hwGponDeviceOntConfigEntry 19 }

       hwGponDeviceOntObjectMainSoftVer OBJECT-TYPE
       SYNTAX OCTET STRING (SIZE (0..14))
       MAX-ACCESS read-only
       STATUS current
       DESCRIPTION
           "The active software version of the ONT."
       ::= { hwGponDeviceOntConfigEntry 20 }

     hwGponDeviceOntObjectStandbySoftVer OBJECT-TYPE
       SYNTAX OCTET STRING (SIZE (0..14))
       MAX-ACCESS read-only
       STATUS current
       DESCRIPTION
           "The standby software version of the ONT."
       ::= { hwGponDeviceOntConfigEntry 21 }

   hwGponDeviceOntObjectEntryStatus OBJECT-TYPE
       SYNTAX RowStatus
       MAX-ACCESS  read-create
       STATUS current
       DESCRIPTION
           "The row status, which is used to differentiate the creation, modification and deletion of a row.
            Options:
            1. createAndGo(4) -create a new instance of a conceptual row
            2. destroy(6)     -delete the instances associated with an existing conceptual row
           "
       ::= { hwGponDeviceOntConfigEntry 25 }

   hwGponDeviceOntObjectTimeOut OBJECT-TYPE
       SYNTAX Integer32
       MAX-ACCESS  read-write
       STATUS current
       DESCRIPTION
           "This object indicates the registered working period of the ONT, ranging from 1 to 168 hours.
            The value (-1) indicates that there is no-aging time."
       DEFVAL { 1 }
       ::= { hwGponDeviceOntConfigEntry 27 }

   hwGponDeviceOntObjectLastUpTime OBJECT-TYPE
       SYNTAX DateAndTime
       MAX-ACCESS  read-only
       STATUS current
       DESCRIPTION
           "The time for ONT's last up."
       ::= { hwGponDeviceOntConfigEntry 28 }

   hwGponDeviceOntObjectLastDownTime OBJECT-TYPE
       SYNTAX DateAndTime
       MAX-ACCESS  read-only
       STATUS current
       DESCRIPTION
           "The time for ONT's last down."
       ::= { hwGponDeviceOntConfigEntry 29 }

   hwGponDeviceOntObjectLastDownCause OBJECT-TYPE
       SYNTAX Integer32
       MAX-ACCESS  read-only
       STATUS current
       DESCRIPTION
           "This object indicates the reason why the ONT last goes offline.
                 The value (1) indicates that the reason is LOS(Loss of signal),
                 The value (2) indicates that the reason is LOSi(Loss of signal for ONUi) or LOBi (Loss of burst for ONUi),
                 The value (3) indicates that the reason is LOFI(Loss of frame of ONUi),
                 The value (4) indicates that the reason is SFI(Signal fail of ONUi),
                 The value (5) indicates that the reason is LOAI(Loss of acknowledge with ONUi),
                 The value (6) indicates that the reason is LOAMI(Loss of PLOAM for ONUi),
                 The value (7) indicates that the reason is deactive ONT fails,
                 The value (8) indicates that the reason is deactive ONT success,
                 The value (9) indicates that the reason is reset ONT,
                 The value (10) indicates that the reason is re-register ONT,
                 The value (11) indicates that the reason is pop up fail,
                 The value (12) indicates that the reason is authentication fail,
                 The value (13) indicates that the reason is dying-gasp,
                 The value (14) reserved,
                 The value (15) indicates that the reason is LOKI(Loss of key synch with ONUi),
                 The value (18) indicates that the reason is deactived ONT due to the ring,
                 The value (30) indicates that the reason is shut down ONT optical module,
                 The value (31) indicates that the reason is reset ONT by ONT command,
                 The value (32) indicates that the reason is reset ONT by ONT reset button,
                 The value (33) indicates that the reason is reset ONT by ONT software,
                 The value (34) indicates that the reason is deactived ONT due to broadcast attack,
                 The value (35) indicates that the reason is operator check fail,
                 The value (37) indicates that the reason is a rogue ONT detected by itself,
                 The value (-1) indicates that the query fails.
                 "
       ::= { hwGponDeviceOntConfigEntry 30 }

   hwGponDeviceOntObjectSnmpProfileName OBJECT-TYPE
        SYNTAX OCTET STRING (SIZE (0..32))
        MAX-ACCESS read-write
        STATUS current
        DESCRIPTION
           "The name of ONT's SNMP profile."
        ::= { hwGponDeviceOntConfigEntry 31 }

    hwGponDeviceOntObjectManageMode OBJECT-TYPE
       SYNTAX INTEGER {
              omci (1),
              snmp (2),
              invalid (-1)
       }
       MAX-ACCESS read-write
       STATUS current
       DESCRIPTION
           "ONT management mode.
            Options:
            1. omci (1)     -ONT management mode is omci
            2. snmp (2)     -ONT management mode is snmp
            3. invalid (-1) -ONT management mode is invalid
           "
       DEFVAL { omci }
       ::= { hwGponDeviceOntConfigEntry 32 }

   hwGponDeviceOntObjectLastDyingGaspTime OBJECT-TYPE
       SYNTAX DateAndTime
       MAX-ACCESS  read-only
       STATUS current
       DESCRIPTION
           "The time for ONT's last Dying Gasp event happened."
       ::= { hwGponDeviceOntConfigEntry 33 }

   hwGponDeviceOntObjectProtectSide OBJECT-TYPE
        SYNTAX      INTEGER {
                protectside(1),
                work(2)
                    }
        MAX-ACCESS  read-write
        STATUS      current
        DESCRIPTION
            "The identify of ONT which is work or protect.
             Options:
             1. protectside(1) -The identify of ONT is protectside
             2. work(2)        -The identify of ONT is work
            "
        ::= { hwGponDeviceOntConfigEntry 34 }

   hwGponDeviceOntCfgOpticAlarmProfileName  OBJECT-TYPE
        SYNTAX     OCTET STRING (SIZE (0..32))
        MAX-ACCESS   read-write
        STATUS      current
        DESCRIPTION
            "The optical alarm profile name that ont bound."
        ::= { hwGponDeviceOntConfigEntry 35 }

   hwGponDeviceOntObjectProductDescription  OBJECT-TYPE
        SYNTAX     OCTET STRING (SIZE (0..256))
        MAX-ACCESS   read-only
        STATUS      current
        DESCRIPTION
            "The product description of the ONT."
        ::= { hwGponDeviceOntConfigEntry 36 }

   hwGponDeviceOntObjectPGMemberRole OBJECT-TYPE
       SYNTAX INTEGER {
              work (1),
              protect (2),
              unjoined (-1)
       }
       MAX-ACCESS read-only
       STATUS current
       DESCRIPTION
            "Indicate the role of the ont in the protect group, if not added to the protect group, the value is unjoined.
             Options:
             1. work (1)      -Indicate the role of the ont is a work member
             2. protect (2)   -Indicate the role of the ont is a protect member
             3. unjoined (-1) -Indicate the role of the ont is an unjoined member
            "
       ::= { hwGponDeviceOntConfigEntry 37 }

   hwGponDeviceOntObjectLoid OBJECT-TYPE
       SYNTAX     OCTET STRING (SIZE (0..24))
       MAX-ACCESS read-write
       STATUS current
       DESCRIPTION
            "This object indicates the ONT LOID.
            "
       ::= { hwGponDeviceOntConfigEntry 38 }

   hwGponDeviceOntObjectCheckcode OBJECT-TYPE
       SYNTAX     OCTET STRING (SIZE (0..12))
       MAX-ACCESS read-write
       STATUS current
       DESCRIPTION
            "This object indicates the ONT checkcode.
            "
       ::= { hwGponDeviceOntConfigEntry 39 }

   hwGponDeviceOntObjectSoftWorkMode OBJECT-TYPE
       SYNTAX  INTEGER {
               normal (1),
               survivalmode (2)
       }
       MAX-ACCESS read-only
       STATUS current
       DESCRIPTION
            "The object indicates the software working mode of the GPON ONT.
             Options:
             1. normal(1)             - Normal
             2. survivalmode(2)       - Survival mode
            "
       ::= { hwGponDeviceOntConfigEntry 40 }

   hwGponDeviceOntObjectReregisterAuthMode OBJECT-TYPE
       SYNTAX INTEGER {
              sn (1),
              snPassword (2),
              invalid (-1)
       }
       MAX-ACCESS read-write
       STATUS current
       DESCRIPTION
            "Indicate the type of the ont re-register type for onceon authentication mode, if the ont authentication mode is not onceon,
            the value is invalid. if the ont authentication mode is onceon, the default is sn-password.
             Options:
             1. sn (1)           -Indicate the re-register type of the ont is sn authentication type
             2. snPassword (2)  -Indicate the re-register type of the ont is sn-password authentication type
             3. invalid (-1)     -Indicate the re-register type of the ont is invalid
            "
       ::= { hwGponDeviceOntConfigEntry 41 }

    hwGponDeviceOntAuthEffectMode OBJECT-TYPE
       SYNTAX INTEGER {
              immediate (1),
              nextstartup (2),
              invalid (-1)
       }
       MAX-ACCESS read-write
       STATUS current
       DESCRIPTION
            "Indicates the effect taking mode after the ONT authentication mode is changed. The default effect taking mode is immediate.
             Options:
             1. immediate (1)    -Indicates that the change will take effect immediately.
             2. nextstartup (2)  -Indicates that the change will take effect when the ONT goes online next time.
             3. invalid (-1)     -Indicates that the effect taking mode is invalid.
            "
       ::= { hwGponDeviceOntConfigEntry 42 }

    hwGponDeviceOntConfigCustomizedInfo OBJECT-TYPE
       SYNTAX     OCTET STRING (SIZE (0..24))
       MAX-ACCESS read-write
       STATUS current
       DESCRIPTION
            "This object indicates the ONT customize information.
	    "
       ::= { hwGponDeviceOntConfigEntry 43 }

    hwGponDeviceOntObjectNniType OBJECT-TYPE
       SYNTAX INTEGER {
            rate2dot5G1dot25G (1),
            rate10G2dot5G (2),
            rate10G10G (3),
            auto (4),
            invalid (-1)
       }
       MAX-ACCESS read-write
       STATUS current
       DESCRIPTION
            "Indicates the effect taking mode after the ONT authentication mode is changed. The default effect taking mode is immediate.
             Options:
             1. rate2dot5G1dot25G (1) -Downstream rate 2.5Gbps, upstream rate 1.25Gbps.
             2. rate10G2dot5G (2)     -Downstream rate 10Gbps, upstream rate 2.5Gbps.
             3. rate10G10G (3)        -Downstream rate 10Gbps, upstream rate 10Gbps.
             4. auto(4)               -Indicates the actual ont nni type is automatically selected.
             5. invalid (-1)          -Indicates the invalid value.
            "
       ::= { hwGponDeviceOntConfigEntry 44 }

    hwGponDeviceOntObjectHostName OBJECT-TYPE
       SYNTAX OCTET STRING (SIZE (0..256))
       MAX-ACCESS read-only
       STATUS current
       DESCRIPTION
            "The host name of the ONT."
       ::= { hwGponDeviceOntConfigEntry 45 }

   hwGponDeviceOntObjectEquipmentSn OBJECT-TYPE
       SYNTAX   OCTET STRING   (SIZE (0..25))
       MAX-ACCESS  read-only
       STATUS   current
       DESCRIPTION
           "This object indicates the ONT Equipment Sn."
       ::= { hwGponDeviceOntConfigEntry 46 }

   hwGponDeviceOntObjectMac OBJECT-TYPE
       SYNTAX     MacAddress
       MAX-ACCESS  read-only
       STATUS   current
       DESCRIPTION
           "This object indicates the ONT MAC address."
       ::= { hwGponDeviceOntConfigEntry 47 }

   -- Table5 HwGponDeviceOntControlTable
   hwGponDeviceOntControlTable OBJECT-TYPE
       SYNTAX  SEQUENCE OF HwGponDeviceOntControlEntry
       MAX-ACCESS  not-accessible
       STATUS  current
       DESCRIPTION
           "This is the control table of the ONT.
            The indexes of this table are ifIndex
            and hwGponDeviceOntObjectIndex,
            which is ONT ID.
           "
       ::= { hwGponDeviceControlObjects 6 }


   hwGponDeviceOntControlEntry OBJECT-TYPE
       SYNTAX  HwGponDeviceOntControlEntry
       MAX-ACCESS  not-accessible
       STATUS  current
       DESCRIPTION
           "This is the control table of the ONT.
            The indexes of this entry are ifIndex
            and hwGponDeviceOntObjectIndex,
            which is ONT ID.
           "
       INDEX  { ifIndex, hwGponDeviceOntObjectIndex }
       ::= { hwGponDeviceOntControlTable 1 }

   HwGponDeviceOntControlEntry ::=
       SEQUENCE {
        hwGponDeviceOntObjectAction                       INTEGER,
        hwGponDeviceOntObjectReset                        INTEGER,
        hwGponDeviceOntObjectRunStatus                    INTEGER,
        hwGponDeviceOntObjectConfigStatus                 INTEGER,
        hwGponDeviceOntObjectReRegister                   INTEGER,
        hwGponDeviceOntObjectDiscoveryStatus              INTEGER,
        hwGponDeviceOntReDiscovery                        INTEGER,
        hwGponDeviceOntObjectMatchStatus                  INTEGER,
        hwGponDeviceOntRangingValue                       Integer32,
        hwGponDeviceOntBatteryCurStatus                   INTEGER,
        hwGponDeviceOntObjectIsolationState               INTEGER,
        hwGponDeviceOntObjectPrimaryStatus                INTEGER,
        hwGponDeviceOntObjectSecondaryStatus              BITS,
        hwGponDeviceOntObjectTcontNumCombined             Integer32,
        hwGponDeviceOntObjectMemoryOccupation             Integer32,
        hwGponDeviceOntObjectCpuOccupation                Integer32,
        hwGponDeviceOntObjectTemperature                  Integer32,
        hwGponDeviceOntLastRangingValue                   Integer32,
	hwGponDeviceOntObjectActualSn                     OCTET STRING
       }

   hwGponDeviceOntObjectAction OBJECT-TYPE
       SYNTAX  INTEGER {
               activate(1),
               deactivate(2)
       }
       MAX-ACCESS   read-write
       STATUS   current
       DESCRIPTION
           "This object is used to activate or deactivate an ONT.
            Options:
            1. activate(1)   -activate an ONT
            2. deactivate(2) -deactivate an ONT
           "
       DEFVAL { activate }
       ::= { hwGponDeviceOntControlEntry 1 }

   hwGponDeviceOntObjectReset OBJECT-TYPE
       SYNTAX  INTEGER {
               reset (1),
               invalidValue(-1)
       }
       MAX-ACCESS read-write
       STATUS  current
       DESCRIPTION
           "This object is used to reset an ONT.
            Options:
            1. reset (1)        -Reset an ONT
            2. invalidValue(-1) -Invalid value
           "
       ::= { hwGponDeviceOntControlEntry 2 }

   hwGponDeviceOntObjectRunStatus OBJECT-TYPE
       SYNTAX  INTEGER {
               up (1),
               down (2),
               invalidValue(-1)
       }
       MAX-ACCESS  read-only
       STATUS  current
       DESCRIPTION
           "The ONT running status.
            Options:
            1. up (1)           -The ONT running status is normal
            2. down (2)         -The ONT running status is fault
            3. invalidValue(-1) -The ONT running status is invalid
            Default: 1
           "
       ::= { hwGponDeviceOntControlEntry 4 }

   hwGponDeviceOntObjectConfigStatus OBJECT-TYPE
        SYNTAX  INTEGER {
                initialization (1),
                normal (2),
                failed (3),
                noresume (4),
                config (5),
                invalidValue(-1)
        }
        MAX-ACCESS  read-only
        STATUS  current
        DESCRIPTION
           "This is the ONT configuration resume status. If it is failed(3),
            the ONT is down and the service is interrupted.
            If the config status is noresume (4), set the resume policy as
            resume for the system and re-register the ONT.
            Options:
            1. initialization (1) -Indicates the initial status
            2. normal (2)         -Indicates the normal state
            3. failed (3)         -Indicates that the configuration fails
            4. noresume (4)       -Indicates that the configuration restoration is not performed
            5. config (5)         -Indicates that the configuration is being restored
            6. invalidValue(-1)   -Indicates that the configuration is invalid
            Default: 1
           "
        ::= { hwGponDeviceOntControlEntry 5 }


   hwGponDeviceOntObjectReRegister    OBJECT-TYPE
       SYNTAX  INTEGER {
               reRegister (1),
               invalidValue(-1)
       }
       MAX-ACCESS  read-write
       STATUS  current
       DESCRIPTION
           "This object is used to re-register an ONT.
            Options:
            1. reRegister (1)   - Re-register an ONT
            2. invalidValue(-1) - Invalid value
           "
       ::= { hwGponDeviceOntControlEntry 6 }

   hwGponDeviceOntObjectDiscoveryStatus OBJECT-TYPE
        SYNTAX  INTEGER {
                on (1),
                off (2),
                unKnownStatus (-1)
        }
        MAX-ACCESS  read-only
        STATUS  current
        DESCRIPTION
            "The ONT discovery status. This object is used to check whether the
             serial number can be changed by the password authentication ONTs.
             On (1) indicates that the SN can be changed. Off (2) indicates
             that the SN cannot be changed.
             However, this object will turn to off (2) when the authentication
             ONTs does not register to the OLT successfully in the specified time.
             In this situation, perform the rediscovery operation to reset the
             discovery status. The default value is on(1).
             Options:
             1. on (1)             -Indicates the SN can be changed
             2. off (2)            -Indicates the SN cannot be changed
             3. unKnownStatus (-1) -The SN is unKnown Status
            "
        ::= { hwGponDeviceOntControlEntry 7 }

   hwGponDeviceOntReDiscovery OBJECT-TYPE
        SYNTAX  INTEGER {
                rediscovery (1),
                invalidValue(-1)
                }
        MAX-ACCESS  read-write
        STATUS  current
        DESCRIPTION
            "This object is used to reset the discovery status of an ONT. If the
             authentication mode is once-on(4), after performing the rediscovery
             operation, the registered working period is re-timed.
             Options:
             1. rediscovery (1) -Reset the discovery status of an ONT
             2. invalidValue(-1)-The discovery status of an ONT is valid
            "
        ::= { hwGponDeviceOntControlEntry 8 }

   hwGponDeviceOntObjectMatchStatus OBJECT-TYPE
        SYNTAX  INTEGER {
                initialization (1),
                match (2),
                mismatch (3),
                invalidValue(-1)
                }
        MAX-ACCESS  read-only
        STATUS  current
        DESCRIPTION
               "The ONT match status DEFVAL { 1 }
                Options:
                1. initialization (1) -The ONT status is initialization
                2. match (2)          -The ONT status is match
                3. mismatch (3)       -The ONT status is mismatch
                4. invalidValue(-1)   -The ONT status is invalid
               "
        ::= { hwGponDeviceOntControlEntry 9 }

   hwGponDeviceOntRangingValue    OBJECT-TYPE
       SYNTAX  Integer32
       MAX-ACCESS  read-only
       STATUS  current
       DESCRIPTION
               "The result of the ONT ranging (m)"
       ::= { hwGponDeviceOntControlEntry 10 }

   hwGponDeviceOntBatteryCurStatus  OBJECT-TYPE
       SYNTAX  INTEGER{
                notSupport (0),
                charge (1),
                discharge (2),
                holding (3),
                supportButInvalid (4),
                unknownStatus (-1)
                }
       MAX-ACCESS  read-only
       STATUS  current
       DESCRIPTION
           "The ONT battery status.
            Options:
            1. notSupport(0)        - not support
            2. charge(1)            - charge state
            3. discharge(2)         - discharge state
            4. holding(3)           - holding state
            5. supportButInvalid(4) - provisioned and present but cannot recharge
            6. unknownStatus(-1)    - unknown status
           "
       ::= { hwGponDeviceOntControlEntry 11 }

   hwGponDeviceOntObjectIsolationState  OBJECT-TYPE
       SYNTAX  INTEGER{
                normal (0),
                isolated (1)
       }
       MAX-ACCESS  read-only
       STATUS  current
       DESCRIPTION
               "The ONT isolation status.
                Options:
                1. normal(0)   -The ONT isolation status is normal
                2. isolated(1) -The ONT isolation status is isolated
               "
       ::= { hwGponDeviceOntControlEntry 12 }

   hwGponDeviceOntObjectPrimaryStatus OBJECT-TYPE
      SYNTAX INTEGER
              {
              isNr(1),
              isAnr(2),
              isRst(3),
              isAnrst(4),
              oosAu(5),
              oosMa(6),
              oosAuma(7),
              oosAurst(8),
              oosMaanr(9)
              }
       MAX-ACCESS read-only
       STATUS current
       DESCRIPTION
           "The primary status of the Board.This parameter indicates the current overall
            service condition of an entity, i.e., whether it is in-service or out-of-service.
            Options:
            1. isNr(1)      - In Service, normal
            2. isAnr(2)     - In Service, abnormal
            3. isRst(3)     - In Service, restricted
            4. isAnrst(4)   - In Service, abnormal & restricted
            5. oosAu(5)     - Out of Service, autonomous
            6. oosMa(6)     - Out of Service, management
            7. oosAuma(7)   - Out of Service, autonomous & management
            8. oosAurst(8)  - Out of Service, autonomous & restricted
            9. oosMaanr(9)  - Out of Service, management & abnormal
           "
       ::= { hwGponDeviceOntControlEntry 13 }

   hwGponDeviceOntObjectSecondaryStatus OBJECT-TYPE
       SYNTAX BITS
              {
              sstAins(0),
                  sstFaf(1),
                  sstFlt(2),
                  sstLpbk(3),
                  sstMea(4),
                  sstSgeo(5),
                  sstStbyh(6),
                  sstTs(7),
                  sstUas(8),
                  sstUeq(9),
                  sstWrk(10),
                  sstPwr(11)
                  }
        MAX-ACCESS read-only
    STATUS current
    DESCRIPTION
            "This parameter indicates the secondary status of the board. The parameter provides additional
             information pertaining to PST and PSTQ. For example, it may indicate the type and/or reason of
             the external command, the event that occurred in the Network Element, etc. Multiple values may
             apply to an entity at a given moment. The highest bit of SST value indicates the sst-ains(0) status;
             the second highest bit of SST value indicates the sst-faf(1) status, and the rest can be deduced by analogy.
             This BITS structure can report the following status:
             1.  sstAins(0)  - this bit position positively reports that the status of the board is automatic inService
             2.  sstFaf(1)   - Facility Failure
             3.  sstFlt(2)   - Fault
             4.  sstLpbk(3)  - Loopback
             5.  sstMea(4)   - Mismatch of Equipment and Attributes
             6.  sstSgeo(5)  - Supporting Entity Outage
             7.  sstStbyh(6) - Standby-Hot
             8.  sstTs(7)    - Test
             9.  sstUas(8)   - Unassigned
             10. sstUeq(9)   - Unequipped
             11. sstWrk(10)  - Working
             12. sstPwr(11)  - Power
             "
    ::= { hwGponDeviceOntControlEntry 14 }

   hwGponDeviceOntObjectTcontNumCombined OBJECT-TYPE
       SYNTAX Integer32
       MAX-ACCESS read-only
       STATUS current
       DESCRIPTION
           "The number of the combined T-CONTs."
       ::= { hwGponDeviceOntControlEntry 15 }

   hwGponDeviceOntObjectMemoryOccupation OBJECT-TYPE
       SYNTAX Integer32
       MAX-ACCESS read-only
       STATUS current
       DESCRIPTION
           "The Memory occupation of the ONT, range: 0-100."
       ::= { hwGponDeviceOntControlEntry 16 }

   hwGponDeviceOntObjectCpuOccupation OBJECT-TYPE
       SYNTAX Integer32
       MAX-ACCESS read-only
       STATUS current
       DESCRIPTION
           "The CPU occupation of the ONT, range: 0-100."
       ::= { hwGponDeviceOntControlEntry 17 }

   hwGponDeviceOntObjectTemperature OBJECT-TYPE
       SYNTAX Integer32
       UNITS       "degree centigrade"
       MAX-ACCESS read-only
       STATUS current
       DESCRIPTION
           "The temperature of the ONT.
            Unit: degree centigrade."
       ::= { hwGponDeviceOntControlEntry 18 }

   hwGponDeviceOntLastRangingValue    OBJECT-TYPE
       SYNTAX  Integer32
       MAX-ACCESS  read-only
       STATUS  current
       DESCRIPTION
               "The result of the ONT last ranging (m)"
       ::= { hwGponDeviceOntControlEntry 19 }

   hwGponDeviceOntObjectActualSn OBJECT-TYPE
        SYNTAX OCTET STRING (SIZE (8))
        MAX-ACCESS read-only
        STATUS  current
        DESCRIPTION
            "The ONT's actual serial number."
        ::= { hwGponDeviceOntControlEntry 20 }

   -- Table6 HwGponDeviceOntRegInfoTable
   hwGponDeviceOntRegInfoTable OBJECT-TYPE
       SYNTAX   SEQUENCE OF HwGponDeviceOntRegInfoEntry
       MAX-ACCESS   not-accessible
       STATUS   current
       DESCRIPTION
           "This table is used to query the register information about the ONT,
            including the ONT SN, register time and register result.
            The indexes of this table are ifIndex and hwGponDeviceSerialNum.
           "
       ::= { hwGponDeviceStatObjects 1 }

   hwGponDeviceOntRegInfoEntry OBJECT-TYPE
       SYNTAX   HwGponDeviceOntRegInfoEntry
       MAX-ACCESS   not-accessible
       STATUS   current
       DESCRIPTION
           "This table is used to query the register information about the ONT,
            including the ONT SN, register time and register result.
            The indexes of this entry are ifIndex and hwGponDeviceSerialNum.
           "
       INDEX  { ifIndex, hwGponDeviceSerialNum }
       ::= { hwGponDeviceOntRegInfoTable 1 }

   HwGponDeviceOntRegInfoEntry ::=
       SEQUENCE {
                hwGponDeviceSerialNum                    Integer32,
                hwGponDeviceRegOntSn                     OCTET STRING,
                hwGponDeviceRegOntResult                 INTEGER,
                hwGponDeviceRegOntTime                   DateAndTime,
                hwGponDeviceRegConflictedIfindex         Integer32,
                hwGponDeviceRegConflictedOntIndex        Integer32,
                hwGponDeviceRegOntPassword               OCTET STRING,
                hwGponDeviceRegOntVendorId               Integer32,
                hwGponDeviceRegOntVersion                OCTET STRING,
                hwGponDeviceRegOntMainSoftVersion        OCTET STRING,
                hwGponDeviceRegOntEquipmentId            OCTET STRING,
                hwGponDeviceRegOntLoid                   OCTET STRING,
                hwGponDeviceRegOntCheckcode              OCTET STRING

                }

   hwGponDeviceSerialNum OBJECT-TYPE
       SYNTAX   Integer32
       MAX-ACCESS    not-accessible
       STATUS   current
       DESCRIPTION
           "The register number."
        ::= { hwGponDeviceOntRegInfoEntry 1 }

   hwGponDeviceRegOntSn OBJECT-TYPE
       SYNTAX   OCTET STRING (SIZE (1..8))
       MAX-ACCESS  read-only
       STATUS  current
       DESCRIPTION
           "The ONT serial number."
       ::= { hwGponDeviceOntRegInfoEntry 2 }

   hwGponDeviceRegOntResult OBJECT-TYPE
       SYNTAX  INTEGER {
               success(1),
               fail(2),
               snConflict(3),
               passwordConflict(4),
               loidConflict(5),
               passwordError(6),
               ccError(7),
               rangingOnuFail(8),
               unconfirmed(9),
               misMatch(10),
               loidError(11),
               invalidValue(-1)
       }
       MAX-ACCESS  read-only
       STATUS  current
       DESCRIPTION
           "The register result.
            Options:
            1. success(1)                    - The register result is success
            2. fail(2)                       - The register result is fail
            3. snConflict(3)                 - Indicates that the SN conflict
            4. passwordConflict(4)           - Indicates that the password conflict
            5. loidConflict(5)               - Indicates that the LOID conflict
            6. passwordError(6)              - Indicates that the password conflict
            7. ccError(7)                    - Indicates that the CC error
            8. rangingOnuFail(8)             - Indicates that the ranging ONU fail
            9. unconfirmed(9)                - Indicates that the ONU is unconfirmed
            10. misMatch(10)                 - Indicates that the ONU is mismatch
            11. loidError(11)                - Indicates that the LOID error
            12. invalidValue(-1)             - The register result is invalid
           "
       ::= { hwGponDeviceOntRegInfoEntry 3 }

   hwGponDeviceRegOntTime OBJECT-TYPE
       SYNTAX  DateAndTime
       MAX-ACCESS  read-only
       STATUS  current
       DESCRIPTION
           "The register time.
            -1 is the invalid value."
       ::= { hwGponDeviceOntRegInfoEntry 4 }

   hwGponDeviceRegConflictedIfindex OBJECT-TYPE
       SYNTAX  Integer32
       MAX-ACCESS   read-only
       STATUS  current
       DESCRIPTION
            "This object indicates the ifIndex of the conflicted ONT.
             -1 is the invalid value."
       ::= { hwGponDeviceOntRegInfoEntry 5 }

   hwGponDeviceRegConflictedOntIndex OBJECT-TYPE
       SYNTAX  Integer32
       MAX-ACCESS   read-only
       STATUS  current
       DESCRIPTION
            "This object indicates the index of the conflicted ONT.
             -1 is the invalid value."
       ::= { hwGponDeviceOntRegInfoEntry 6 }

   hwGponDeviceRegOntPassword OBJECT-TYPE
       SYNTAX   OCTET STRING
       MAX-ACCESS  read-only
       STATUS   current
       DESCRIPTION
           "This object indicates the ONT password.
            GPON password size (0..10)
            XG-PON password size (0..36)"
       ::= { hwGponDeviceOntRegInfoEntry 7 }

   hwGponDeviceRegOntVendorId OBJECT-TYPE
       SYNTAX   Integer32
       MAX-ACCESS  read-only
       STATUS   current
       DESCRIPTION
           "Vendor ID of the ONT."
       ::= { hwGponDeviceOntRegInfoEntry 8 }

    hwGponDeviceRegOntVersion OBJECT-TYPE
       SYNTAX   OCTET STRING    (SIZE (16))
       MAX-ACCESS  read-only
       STATUS   current
       DESCRIPTION
           "ONT hardware version."
       ::= { hwGponDeviceOntRegInfoEntry 9 }

   hwGponDeviceRegOntMainSoftVersion  OBJECT-TYPE
       SYNTAX   OCTET STRING   (SIZE (16))
       MAX-ACCESS  read-only
       STATUS   current
       DESCRIPTION
           "ONT software version."
       ::= { hwGponDeviceOntRegInfoEntry 10 }

   hwGponDeviceRegOntEquipmentId  OBJECT-TYPE
       SYNTAX   OCTET STRING   (SIZE (20))
       MAX-ACCESS  read-only
       STATUS   current
       DESCRIPTION
           "Device ID of the ONT."
       ::= { hwGponDeviceOntRegInfoEntry 11 }

    hwGponDeviceRegOntLoid  OBJECT-TYPE
       SYNTAX   OCTET STRING (SIZE (0..24))
       MAX-ACCESS  read-only
       STATUS   current
       DESCRIPTION
                "This object indicates the ONT LOID."
       ::= { hwGponDeviceOntRegInfoEntry 12 }

    hwGponDeviceRegOntCheckcode  OBJECT-TYPE
       SYNTAX   OCTET STRING (SIZE (0..12))
       MAX-ACCESS  read-only
       STATUS   current
       DESCRIPTION
                "This object indicates the ONT checkcode."
       ::= { hwGponDeviceOntRegInfoEntry 13 }

   -- Table7 HwGponDeviceAutoFindOntControlTable
   hwGponDeviceAutoFindOntControlTable OBJECT-TYPE
       SYNTAX  SEQUENCE OF HwGponDeviceAutoFindOntControlEntry
       MAX-ACCESS  not-accessible
       STATUS  current
       DESCRIPTION
           "This table is used to query the information about the auto-found ONTs
            in the system.
            The indexes of this table are ifIndex and hwGponDeviceAutoFindOntIndex.
           "
       ::= { hwGponDeviceControlObjects  9 }

   hwGponDeviceAutoFindOntControlEntry OBJECT-TYPE
       SYNTAX  HwGponDeviceAutoFindOntControlEntry
       MAX-ACCESS  not-accessible
       STATUS  current
       DESCRIPTION
           "This table is used to query the information about the auto-found ONTs
            in the system.
            The indexes of this entry are ifIndex and hwGponDeviceAutoFindOntIndex.
           "
       INDEX  { ifIndex, hwGponDeviceAutoFindOntIndex }
       ::= { hwGponDeviceAutoFindOntControlTable 1 }

   HwGponDeviceAutoFindOntControlEntry ::=
       SEQUENCE {
         hwGponDeviceAutoFindOntIndex                 Integer32,
         hwGponDeviceAutoFindOntSn                    OCTET STRING,
         hwGponDeviceAutoFindOntPassword              OCTET STRING,
         hwGponDeviceAutoFindOntVendorId              Integer32,
         hwGponDeviceAutoFindOntVer                   OCTET STRING,
         hwGponDeviceAutoFindOntMainSoftVer           OCTET STRING,
         hwGponDeviceAutoFindOntEquipmentId           OCTET STRING,
         hwGponDeviceAutoFindOntAutoFindTime          DateAndTime,
         hwGponDeviceAutoFindOntLoid                  OCTET STRING,
         hwGponDeviceAutoFindOntCheckcode             OCTET STRING,
         hwGponDeviceAutoFindOntCustomizedInfo        OCTET STRING,
         hwGponDeviceAutoFindOntNniType               INTEGER,
         hwGponDeviceAutoFindOntEquipmentSn           OCTET STRING,
         hwGponDeviceAutoFindOntMac                   MacAddress
       }

   hwGponDeviceAutoFindOntIndex OBJECT-TYPE
       SYNTAX   Integer32
       MAX-ACCESS  not-accessible
       STATUS   current
       DESCRIPTION
           "The index of the auto-found ONT."
       ::= { hwGponDeviceAutoFindOntControlEntry 1 }

   hwGponDeviceAutoFindOntSn OBJECT-TYPE
       SYNTAX   OCTET STRING (SIZE (8))
       MAX-ACCESS  read-only
       STATUS   current
       DESCRIPTION
           "ONT serial number."
       ::= { hwGponDeviceAutoFindOntControlEntry 2 }

   hwGponDeviceAutoFindOntPassword OBJECT-TYPE
       SYNTAX   OCTET STRING
       MAX-ACCESS  read-only
       STATUS   current
       DESCRIPTION
           "ONT password.
            GPON password size (0..10)
            XG-PON password size (0..36)
           "
       ::= { hwGponDeviceAutoFindOntControlEntry 3 }

   hwGponDeviceAutoFindOntVendorId OBJECT-TYPE
       SYNTAX   Integer32
       MAX-ACCESS  read-only
       STATUS   current
       DESCRIPTION
           "Vendor ID of the ONT."
       ::= { hwGponDeviceAutoFindOntControlEntry 4 }

    hwGponDeviceAutoFindOntVer OBJECT-TYPE
       SYNTAX   OCTET STRING    (SIZE (16))
       MAX-ACCESS  read-only
       STATUS   current
       DESCRIPTION
           "ONT hardware version."
       ::= { hwGponDeviceAutoFindOntControlEntry 5 }

   hwGponDeviceAutoFindOntMainSoftVer  OBJECT-TYPE
       SYNTAX   OCTET STRING   (SIZE (16))
       MAX-ACCESS  read-only
       STATUS   current
       DESCRIPTION
           "ONT software version."
       ::= { hwGponDeviceAutoFindOntControlEntry 6 }

   hwGponDeviceAutoFindOntEquipmentId  OBJECT-TYPE
       SYNTAX   OCTET STRING   (SIZE (20))
       MAX-ACCESS  read-only
       STATUS   current
       DESCRIPTION
           "Device ID of the ONT."
       ::= { hwGponDeviceAutoFindOntControlEntry 7 }

    hwGponDeviceAutoFindOntAutoFindTime OBJECT-TYPE
       SYNTAX   DateAndTime
       MAX-ACCESS  read-only
       STATUS   current
       DESCRIPTION
           "Time when the ONT is automatically found."
       ::= { hwGponDeviceAutoFindOntControlEntry 8 }

    hwGponDeviceAutoFindOntLoid  OBJECT-TYPE
       SYNTAX   OCTET STRING (SIZE (0..24))
       MAX-ACCESS  read-only
       STATUS   current
       DESCRIPTION
                "This object indicates the ONT LOID."
       ::= { hwGponDeviceAutoFindOntControlEntry 9 }

    hwGponDeviceAutoFindOntCheckcode  OBJECT-TYPE
       SYNTAX   OCTET STRING (SIZE (0..12))
       MAX-ACCESS  read-only
       STATUS   current
       DESCRIPTION
                "This object indicates the ONT checkcode."
       ::= { hwGponDeviceAutoFindOntControlEntry 10 }

    hwGponDeviceAutoFindOntCustomizedInfo  OBJECT-TYPE
       SYNTAX   OCTET STRING (SIZE (0..24))
       MAX-ACCESS  read-only
       STATUS   current
       DESCRIPTION
                "This object indicates the ONT customize information."
       ::= { hwGponDeviceAutoFindOntControlEntry 11 }

   hwGponDeviceAutoFindOntNniType OBJECT-TYPE
       SYNTAX INTEGER {
            rate2dot5G1dot25G (1),
            rate10G2dot5G (2),
            rate10G10G (3),
            invalid (-1)
       }
       MAX-ACCESS read-only
       STATUS current
       DESCRIPTION
            "This object indicates the ONT actual rate type.
             Options:
             1. rate2dot5G1dot25G(1)      - Downstream rate 2.5Gbps, upstream rate 1.25Gbps
             2. rate10G2dot5G(2)          - Downstream rate 10Gbps, upstream rate 2.5Gbps
             3. rate10G10G(3)             - Downstream rate 10Gbps, upstream rate 10Gbps
             4. invalid(-1)               - Indicates that the query fails or no information is detected
            "
       ::= { hwGponDeviceAutoFindOntControlEntry 12 }

    hwGponDeviceAutoFindOntEquipmentSn  OBJECT-TYPE
       SYNTAX   OCTET STRING (SIZE (0..25))
       MAX-ACCESS  read-only
       STATUS   current
       DESCRIPTION
                "This object indicates the ONT Equipment Sn."
       ::= { hwGponDeviceAutoFindOntControlEntry 13 }

    hwGponDeviceAutoFindOntMac  OBJECT-TYPE
       SYNTAX     MacAddress
       MAX-ACCESS  read-only
       STATUS   current
       DESCRIPTION
                "This object indicates the ONT MAC address."
       ::= { hwGponDeviceAutoFindOntControlEntry 14 }

      -- Table11 HwGponDeviceTcontProfileTable
   hwGponDeviceTcontProfileTable OBJECT-TYPE
       SYNTAX     SEQUENCE OF HwGponDeviceTcontProfileEntry
       MAX-ACCESS   not-accessible
       STATUS     current
       DESCRIPTION
           "This is the T-CONT(DBA) profile table. This table is
            used to create a T-CONT(DBA) profile,
            and is used to modify or delete a T-CONT(DBA) profile
            which is not bound.
            The index of this table is hwGponDeviceTcontNameIndex.
           "
       ::= { hwGponDeviceControlObjects  10 }

   hwGponDeviceTcontProfileEntry OBJECT-TYPE
       SYNTAX     HwGponDeviceTcontProfileEntry
       MAX-ACCESS not-accessible
       STATUS     current
       DESCRIPTION
           "This is the T-CONT(DBA) profile table. This table is
            used to create a T-CONT(DBA) profile,
            and is used to modify or delete a T-CONT(DBA) profile
            which is not bound.
            The index of this entry is hwGponDeviceTcontNameIndex.
           "
       INDEX       { IMPLIED hwGponDeviceTcontNameIndex }
       ::= { hwGponDeviceTcontProfileTable 1 }

   HwGponDeviceTcontProfileEntry ::=
       SEQUENCE {
                hwGponDeviceTcontNameIndex             OCTET STRING,
                hwGponDeviceTcontType                  Integer32,
                hwGponDeviceTcontFixedRate             Integer32,
                hwGponDeviceTcontAssuredRate           Integer32,
                hwGponDeviceTcontMaxRate               Integer32,
                hwGponDeviceTcontReferenceNum          Integer32,
                hwGponDeviceTconBandwithCompensate     INTEGER,
                hwGponDeviceTcontFixDelay              INTEGER,
                hwGponDeviceTcontAdditionalBandwidth   INTEGER,
                hwGponDeviceTcontPriority              Integer32,
                hwGponDeviceTcontWeight                Integer32,
                hwGponDeviceTcontEntryStatus           RowStatus,
                hwGponDeviceTcontOperateResult         Integer32,
                hwGponDeviceTcontAsynCommit	           INTEGER
                }

   hwGponDeviceTcontNameIndex OBJECT-TYPE
       SYNTAX    OCTET STRING  (SIZE (1..33))
       MAX-ACCESS    not-accessible
       STATUS    current
       DESCRIPTION
           "T-CONT(DBA) profile name."
       ::= { hwGponDeviceTcontProfileEntry 1 }

   hwGponDeviceTcontType OBJECT-TYPE
       SYNTAX   Integer32
       MAX-ACCESS    read-write
       STATUS    current
       DESCRIPTION
           "T-CONT(DBA) profile type.
           1  - the DBA profile type is type1
           2  - the DBA profile type is type2
           3  - the DBA profile type is type3
           4  - the DBA profile type is type4
           5  - the DBA profile type is type5"
       ::= { hwGponDeviceTcontProfileEntry 2 }

   hwGponDeviceTcontFixedRate OBJECT-TYPE
       SYNTAX   Integer32
       MAX-ACCESS    read-write
       STATUS    current
       DESCRIPTION
           "Fixed bandwidth of the profile."
       ::= { hwGponDeviceTcontProfileEntry 3 }

   hwGponDeviceTcontAssuredRate OBJECT-TYPE
       SYNTAX   Integer32
       MAX-ACCESS    read-write
       STATUS    current
       DESCRIPTION
           "Assured bandwidth of the profile."
       ::= { hwGponDeviceTcontProfileEntry 4 }

   hwGponDeviceTcontMaxRate OBJECT-TYPE
       SYNTAX   Integer32
       MAX-ACCESS    read-write
       STATUS    current
       DESCRIPTION
           "Max bandwidth of the profile."
       ::= { hwGponDeviceTcontProfileEntry 5 }

   hwGponDeviceTcontReferenceNum  OBJECT-TYPE
       SYNTAX   Integer32
       MAX-ACCESS    read-only
       STATUS    current
       DESCRIPTION
           "The binding times of the profile."
       ::= { hwGponDeviceTcontProfileEntry 6 }

   hwGponDeviceTconBandwithCompensate   OBJECT-TYPE
       SYNTAX   INTEGER{
                  enable(1),
                  disable(2)
       }
       MAX-ACCESS    read-write
       STATUS    current
       DESCRIPTION
           "Bandwidth compensation policy of the profile.
            Options:
            1. enable(1)  -Bandwidth compensation policy of the profile is enable
            2. disable(2) -Bandwidth compensation policy of the profile is disable
           "
       ::= { hwGponDeviceTcontProfileEntry 7 }

   hwGponDeviceTcontFixDelay   OBJECT-TYPE
       SYNTAX   INTEGER{
                  enable(1),
                  disable(2)
       }
       MAX-ACCESS    read-write
       STATUS    current
       DESCRIPTION
           "Fix delay switch of the profile.
            Options:
            1. enable(1)  -Fix delay switch of the profile is enable
            2. disable(2) -Fix delay switch of the profile is disable
           "
       ::= { hwGponDeviceTcontProfileEntry 8 }

   hwGponDeviceTcontAdditionalBandwidth   OBJECT-TYPE
       SYNTAX   INTEGER{
                  nonAssure(1),
                  bestEffort(2),
                  invalid(-1)
       }
       MAX-ACCESS    read-write
       STATUS    current
       DESCRIPTION
           "Additional bandwidth type of the profile.
            Options:
            1. nonAssure(1)  -Additional bandwidth type of the profile is non assure
            2. bestEffort(2) -Additional bandwidth type of the profile is best effort
            3. invalid(-1)    - Indicates that the query fails or no information is detected
           "
       ::= { hwGponDeviceTcontProfileEntry 9 }

   hwGponDeviceTcontPriority   OBJECT-TYPE
        SYNTAX Integer32
        MAX-ACCESS read-write
        STATUS current
        DESCRIPTION
            "This object is used to set best effort bandwidth assignment priority.
             Ranging from 0 to 7, 0 is the lowest priority.
             The default value is 0.
            "
       ::= { hwGponDeviceTcontProfileEntry 10 }

   hwGponDeviceTcontWeight   OBJECT-TYPE
        SYNTAX Integer32
        MAX-ACCESS read-write
        STATUS current
        DESCRIPTION
            "This object is used to set best effort bandwidth assignment weight.
             Ranging from 1 to 10000.
             The default value is 128.
            "
       ::= { hwGponDeviceTcontProfileEntry 11 }

   hwGponDeviceTcontEntryStatus OBJECT-TYPE
       SYNTAX   RowStatus
       MAX-ACCESS  read-create
       STATUS    current
       DESCRIPTION
           "Row status. This object is used to differentiate the
            creation, modification and deletion operations for an object.
            Options:
            1. createAndGo(4) -create a new instance of a conceptual row
            2. destroy(6)     -delete the instances associated with an existing conceptual row
           "
       ::= { hwGponDeviceTcontProfileEntry 15 }

   hwGponDeviceTcontOperateResult   OBJECT-TYPE
       SYNTAX   Integer32
       MAX-ACCESS  read-only
       STATUS    current
       DESCRIPTION
            "This object indicates the commit result of a DBA profile, the aging time of the result is 20s.
             Options:
             This node identifies the result of DBA profile commit:
                 Value 0 indicates the commit result is successfully.
                 Value 1~0xFFFFFFFF-2 indicates the commit result is fail and return error code.
                 Value 0xFFFFFFFD  indicates that the commit does not complete
                 Value 0xFFFFFFFE  indicates that no commit is being operated
                 Value 0xFFFFFFFF  indicates invalid
            "
       ::= { hwGponDeviceTcontProfileEntry 16 }

  hwGponDeviceTcontAsynCommit   OBJECT-TYPE
 		SYNTAX INTEGER {
           	asynMode(1),
          	invalid(-1)
        }
        MAX-ACCESS read-write
        STATUS current
        DESCRIPTION
              "This object indicates the mode of commit of a DBA profile
                Options:
                1. asynMode(1)   - Indicates that the commit mode is asynchronous
                2. invalid(-1)	 - Invalid value
             	The device will perform sync mode without the mib node.
	    	  "
       ::= { hwGponDeviceTcontProfileEntry 17 }

   -- Table9 HwGponDeviceTcontRefTable
   hwGponDeviceTcontRefTable OBJECT-TYPE
       SYNTAX      SEQUENCE OF HwGponDeviceTcontRefEntry
       MAX-ACCESS  not-accessible
       STATUS      current
       DESCRIPTION
           "This is the T-CONT configuration table. This table is used to
            bind, undo bind or modify the binding for the T-CONT and T-CONT (DBA)
            profiles. It is also used to query the bound profile of the T-CONT
            profile and the corresponding alloc-ID.
            The indexes of this table are ifIndex, hwGponDeviceOntObjectIndex and
            hwGponDeviceTcontRefIndex.
           "
       ::= { hwGponDeviceControlObjects 11 }

   hwGponDeviceTcontRefEntry OBJECT-TYPE
       SYNTAX    HwGponDeviceTcontRefEntry
       MAX-ACCESS  not-accessible
       STATUS      current
       DESCRIPTION
           "This is the T-CONT configuration table. This table is used to
            bind, undo bind or modify the binding for the T-CONT and T-CONT (DBA)
            profiles. It is also used to query the bound profile of the T-CONT
            profile and the corresponding alloc-ID.
            The indexes of this entry are ifIndex, hwGponDeviceOntObjectIndex and
            hwGponDeviceTcontRefIndex.
           "
       INDEX    { ifIndex, hwGponDeviceOntObjectIndex, hwGponDeviceTcontRefIndex }
       ::= { hwGponDeviceTcontRefTable 1 }

   HwGponDeviceTcontRefEntry ::=
       SEQUENCE {
                hwGponDeviceTcontRefIndex              Integer32,
                hwGponDeviceTcontName                  OCTET STRING,
                hwGponDeviceAllocId                    Integer32,
                hwGponDeviceTcontRefEntryStatus        RowStatus
                }

   hwGponDeviceTcontRefIndex OBJECT-TYPE
       SYNTAX   Integer32
       MAX-ACCESS  not-accessible
       STATUS      current
       DESCRIPTION
           "T-CONT ID."
       ::= { hwGponDeviceTcontRefEntry 1 }

   hwGponDeviceTcontName OBJECT-TYPE
       SYNTAX    OCTET STRING (SIZE (1..33))
       MAX-ACCESS  read-write
       STATUS      current
       DESCRIPTION
           "T-CONT(DBA) profile name."
       ::= { hwGponDeviceTcontRefEntry 2 }

   hwGponDeviceAllocId  OBJECT-TYPE
       SYNTAX   Integer32
       MAX-ACCESS  read-only
       STATUS      current
       DESCRIPTION
           "Alloc ID."
       ::= { hwGponDeviceTcontRefEntry 3 }

   hwGponDeviceTcontRefEntryStatus OBJECT-TYPE
       SYNTAX    RowStatus
       MAX-ACCESS  read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponDeviceTcontRefEntry 7 }

  -- Table13 HwGponDevicePortidControlTable
  hwGponDevicePortidControlTable OBJECT-TYPE
       SYNTAX      SEQUENCE OF HwGponDevicePortidControlEntry
       MAX-ACCESS  not-accessible
       STATUS      current
       DESCRIPTION
           "This is the GEM port configuration table. This table is used
            to create, delete, modify and query the GEM port. The GEM
            port ID can be specified or not when creating the GEM port.
            Input value -1 for the hwGponDevicePortidObjectIndex
            means the GEM port ID can be automatically allocated.
            The indexes of this table are ifIndex and
            hwGponDevicePortidObjectIndex, which is GEM port ID.
           "
       ::= { hwGponDeviceControlObjects 12 }

   hwGponDevicePortidControlEntry OBJECT-TYPE
       SYNTAX    HwGponDevicePortidControlEntry
       MAX-ACCESS  not-accessible
       STATUS      current
       DESCRIPTION
           "This is the GEM port configuration table. This table is used
            to create, delete, modify and query the GEM port. The GEM
            port ID can be specified or not when creating the GEM port.
            Input value -1 for the hwGponDevicePortidObjectIndex
            means the GEM port ID can be automatically allocated.
            The indexes of this entry are ifIndex and
            hwGponDevicePortidObjectIndex, which is GEM port ID.
           "
       INDEX    { ifIndex, hwGponDevicePortidObjectIndex }
       ::= { hwGponDevicePortidControlTable 1 }

   HwGponDevicePortidControlEntry ::=
   SEQUENCE {
             hwGponDevicePortidObjectIndex              Integer32,
             hwGponDevicePortidServiceType              INTEGER,
             hwGponDevicePortidObjectDnEncrypt          INTEGER,
             hwGponDevicePortidCascade                  INTEGER,
             hwGponDevicePortidEntryStatus              RowStatus,
             hwGponDevicePortidDescription              OCTET STRING,
             hwGponDevicePortidOltLoopback              INTEGER,
             hwGponDevicePortidOntLoopback              INTEGER
            }

   hwGponDevicePortidObjectIndex OBJECT-TYPE
       SYNTAX   Integer32
       MAX-ACCESS  not-accessible
       STATUS      current
       DESCRIPTION
           "GEM port ID."
       ::= { hwGponDevicePortidControlEntry 1 }

   hwGponDevicePortidCascade   OBJECT-TYPE
       SYNTAX   INTEGER{
                  on(1),
                  off(2)
        }
       MAX-ACCESS    read-write
       STATUS    current
       DESCRIPTION
           "The subtending attribute of a GEM port.
            Options:
            1. on(1)  -Open the subtending attribute of a GEM port
            2. off(2) -Close the subtending attribute of a GEM port
           "
       ::= { hwGponDevicePortidControlEntry 9 }

   hwGponDevicePortidServiceType   OBJECT-TYPE
       SYNTAX   INTEGER{
                  tdm(1),
                  omci(2),
                  eth(3)
       }
       MAX-ACCESS    read-write
       STATUS    current
       DESCRIPTION
           "The carried service type of the GEM port.
            Options:
            1. tdm(1)  -The carried service type of the GEM is tdm
            2. omci(2) -The carried service type of the GEM is omci
            3. eth(3)  -The carried service type of the GEM is eth
           "
       ::= { hwGponDevicePortidControlEntry 8 }

   hwGponDevicePortidObjectDnEncrypt   OBJECT-TYPE
       SYNTAX   INTEGER{
                  on(1),
                  off(2)
       }
       MAX-ACCESS    read-write
       STATUS    current
       DESCRIPTION
           "Downstream encryption switch.
            Options:
            1. on(1)  -Open the downstream encryption switch
            2. off(2) -Close the downstream encryption switch
           "
       ::= { hwGponDevicePortidControlEntry 6 }

   hwGponDevicePortidEntryStatus OBJECT-TYPE
       SYNTAX   RowStatus
       MAX-ACCESS  read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponDevicePortidControlEntry 7 }

   hwGponDevicePortidDescription OBJECT-TYPE
       SYNTAX    OCTET STRING (SIZE (1..64))
       MAX-ACCESS  read-write
       STATUS      current
       DESCRIPTION
           "The GEM port description."
       ::= { hwGponDevicePortidControlEntry 10 }

   hwGponDevicePortidOltLoopback   OBJECT-TYPE
       SYNTAX   INTEGER{
                  noLoopback(1),
                  oltRemoteInnerLoopback(2),
                  invalidValue(-1)
       }
       MAX-ACCESS    read-write
       STATUS    current
       DESCRIPTION
               "Set OLT GEM port loopback.
                Options:
                1.noLoopback(1)                - No loop back
                2.oltRemoteInnerLoopback(2)    - From OLT gemport to NNI
                3.invalidValue(-1)             - Failed in the loop back
               "
       DEFVAL { noLoopback }
       ::= { hwGponDevicePortidControlEntry 11 }

   hwGponDevicePortidOntLoopback   OBJECT-TYPE
       SYNTAX   INTEGER{
                  noloopback(1),
                  ontremoteinnerloopback(2),
                  notSupportQueryInCurrentMode(-1)
        }
       MAX-ACCESS    read-write
       STATUS    current
       DESCRIPTION
           "Set ONT GEM port loopback.
            Options:
            1. noloopback(1)                    - No loop back
            2. ontremoteinnerloopback(2)        - From ONT gemport to NNI
            3. notSupportQueryInCurrentMode(-1) - Indicates that the query fails or no information is detected
           "
       ::= { hwGponDevicePortidControlEntry 12 }


   -- Table11 hwGponDeviceOntPortidControlTable
   hwGponDeviceOntPortidControlTable OBJECT-TYPE
       SYNTAX     SEQUENCE OF HwGponDeviceOntPortidControlEntry
       MAX-ACCESS not-accessible
       STATUS     current
       DESCRIPTION
           "This is ONT GEM port configuration table. This table is used to
            configure the mapping relation between the T-CONT and GEM port of
            an ONT. The indexes of this table are ifIndex and
            hwGponDeviceOntPortidObjectIndex.
           "
       ::= { hwGponDeviceControlObjects 22 }

   hwGponDeviceOntPortidControlEntry OBJECT-TYPE
       SYNTAX     HwGponDeviceOntPortidControlEntry
       MAX-ACCESS not-accessible
       STATUS     current
       DESCRIPTION
           "This is ONT GEM port configuration table. This table is used to
            configure the mapping relation between the T-CONT and GEM port of
            an ONT. The indexes of this entry are ifIndex and
            hwGponDeviceOntPortidObjectIndex.
           "
       INDEX       { ifIndex, hwGponDeviceOntPortidObjectIndex }
       ::= { hwGponDeviceOntPortidControlTable 1 }

   HwGponDeviceOntPortidControlEntry ::=
       SEQUENCE {
             hwGponDeviceOntPortidObjectIndex              Integer32,
             hwGponDeviceOntPortidObjectOntId              Integer32,
             hwGponDeviceOntPortidObjectTcontId            Integer32,
             hwGponDeviceOntPortidObjectUpPQIndex          Integer32,
             hwGponDeviceOntPortidEntryStatus              RowStatus,
             hwGponDeviceOntPortidTcontAverBand            Integer32,
             hwGponDeviceOntPortidTcontMaxBand             Integer32,
             hwGponDeviceOntPortidTrafficTableId           Integer32,
             hwGponDeviceOntPortidObjectDownPQIndex        Integer32,
             hwGponDeviceOntPortidTrafficTableName         OCTET STRING
    }

  hwGponDeviceOntPortidObjectIndex OBJECT-TYPE
       SYNTAX   Integer32
       MAX-ACCESS  not-accessible
       STATUS      current
       DESCRIPTION
           "ONT GEM port ID."
       ::= { hwGponDeviceOntPortidControlEntry 1 }

   hwGponDeviceOntPortidObjectOntId OBJECT-TYPE
       SYNTAX   Integer32
       MAX-ACCESS  read-write
       STATUS      current
       DESCRIPTION
           "ONT-ID."
       ::= { hwGponDeviceOntPortidControlEntry 2 }

   hwGponDeviceOntPortidObjectTcontId OBJECT-TYPE
       SYNTAX   Integer32
       MAX-ACCESS  read-write
       STATUS      current
       DESCRIPTION
           "T-CONT ID."
       ::= { hwGponDeviceOntPortidControlEntry 3 }

   hwGponDeviceOntPortidObjectUpPQIndex OBJECT-TYPE
       SYNTAX   Integer32
       MAX-ACCESS   read-write
       STATUS       current
       DESCRIPTION
           "GEM port up stream PQ number."
       DEFVAL { 1 }
       ::= { hwGponDeviceOntPortidControlEntry 4 }

   hwGponDeviceOntPortidEntryStatus OBJECT-TYPE
       SYNTAX   RowStatus
       MAX-ACCESS  read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponDeviceOntPortidControlEntry 5 }

   hwGponDeviceOntPortidTcontAverBand OBJECT-TYPE
       SYNTAX   Integer32
       MAX-ACCESS  read-write
       STATUS      current
       DESCRIPTION
           "The average bandwidth of the GEM port."
       ::= { hwGponDeviceOntPortidControlEntry 6 }

   hwGponDeviceOntPortidTcontMaxBand OBJECT-TYPE
       SYNTAX   Integer32
       MAX-ACCESS  read-write
       STATUS      current
       DESCRIPTION
           "The maximum bandwidth of the GEM port."
       ::= { hwGponDeviceOntPortidControlEntry 7 }

   hwGponDeviceOntPortidTrafficTableId OBJECT-TYPE
       SYNTAX   Integer32 (-1 | 1..1024)
       MAX-ACCESS  read-write
       STATUS      current
       DESCRIPTION
               "The traffic table id of the GEM port. Range: 1~1024"
       ::= { hwGponDeviceOntPortidControlEntry 8 }

   hwGponDeviceOntPortidObjectDownPQIndex OBJECT-TYPE
       SYNTAX   Integer32 (-1 | 0..7 | 254)
       MAX-ACCESS   read-write
       STATUS       current
       DESCRIPTION
           "Gem port Down Stream PQ, Only effect on eth or veth uni port.
            0..7: Down Stream PQ,
            254 : Apaptive, Gemport Down Stream PQ is decided by ont.
            -1  : Default Value.Gemport Down Stream PQ is decided by olt."
       DEFVAL { -1 }
       ::= { hwGponDeviceOntPortidControlEntry 9 }

   hwGponDeviceOntPortidTrafficTableName OBJECT-TYPE
       SYNTAX       OCTET STRING  (SIZE (0..32))
       MAX-ACCESS   read-write
       STATUS       current
       DESCRIPTION
           "The traffic table name of the GEM port."
       ::= { hwGponDeviceOntPortidControlEntry 10 }

   -- Table12 hwGponDevicePortidMapControlTable
   hwGponDevicePortidMapControlTable OBJECT-TYPE
       SYNTAX     SEQUENCE OF HwGponDevicePortidMapControlEntry
       MAX-ACCESS not-accessible
       STATUS     current
       DESCRIPTION
           "This is the GEM port mapping configuration table. This table is
            used to create or delete the mapping between the GEM port and the
            traffic stream. One GEM port can map to 8 traffic streams that
            are differentiated by flow ID. The indexes of this table are the
            ifIndex, hwGponDevicePortidMapObjectIndex which is GEM portID,
            and hwGponDevicePortidFlowIndex which is flow index.
           "
       ::= { hwGponDeviceControlObjects 23 }

   hwGponDevicePortidMapControlEntry OBJECT-TYPE
       SYNTAX     HwGponDevicePortidMapControlEntry
       MAX-ACCESS not-accessible
       STATUS     current
       DESCRIPTION
           "This is the GEM port mapping configuration table. This table is
            used to create or delete the mapping between the GEM port and the
            traffic stream. One GEM port can map to 8 traffic streams that
            are differentiated by flow ID. The indexes of this entry are the
            ifIndex, hwGponDevicePortidMapObjectIndex which is GEM portID,
            and hwGponDevicePortidFlowIndex which is flow index.
           "
       INDEX       { ifIndex, hwGponDevicePortidMapObjectIndex, hwGponDevicePortidFlowIndex }
       ::= { hwGponDevicePortidMapControlTable 1 }

   HwGponDevicePortidMapControlEntry ::=
       SEQUENCE {
             hwGponDevicePortidMapObjectIndex              Integer32,
             hwGponDevicePortidFlowIndex                   Integer32,
             hwGponDevicePortidMapObjectVlanID             Integer32,
             hwGponDevicePortidMapObjectPir                Integer32,
             hwGponDevicePortidMapObjectPortType           INTEGER,
             hwGponDevicePortidMapObjectPortID             Integer32,
             hwGponDevicePortidMapEntryStatus              RowStatus,
             hwGponDevicePortidMapTcontAverBand            Integer32,
             hwGponDevicePortidMapTcontMaxBand             Integer32,
             hwGponDevicePortidMapTrafficTableId           Integer32,
             hwGponDevicePortidMapTransparent              INTEGER,
             hwGponDevicePortidMapTrafficTableName         OCTET STRING
    }

  hwGponDevicePortidMapObjectIndex OBJECT-TYPE
       SYNTAX   Integer32
       MAX-ACCESS  not-accessible
       STATUS      current
       DESCRIPTION
           "GEM portID."
       ::= { hwGponDevicePortidMapControlEntry 1 }

  hwGponDevicePortidFlowIndex OBJECT-TYPE
       SYNTAX   Integer32
       MAX-ACCESS  not-accessible
       STATUS      current
       DESCRIPTION
           "Flow number."
       ::= { hwGponDevicePortidMapControlEntry 2 }

   hwGponDevicePortidMapObjectVlanID OBJECT-TYPE
       SYNTAX   Integer32 (-1|0..4095|65533)
       MAX-ACCESS  read-write
       STATUS      current
       DESCRIPTION
           "VLAN ID of the traffic stream. The value -1 indicates invalid VLAN ID, and 65533 indicates untag traffic stream."
       ::= { hwGponDevicePortidMapControlEntry 4 }


   hwGponDevicePortidMapObjectPir OBJECT-TYPE
       SYNTAX   Integer32
       MAX-ACCESS   read-write
       STATUS       current
       DESCRIPTION
           "Priority of the traffic stream."
       ::= { hwGponDevicePortidMapControlEntry 5 }

    hwGponDevicePortidMapObjectPortType OBJECT-TYPE
       SYNTAX   INTEGER {
            t1 (13),
            e1 (14),
            fe (24),
            ge (34),
            vdsl (37),
            moca (46),
            eth (47),
            iphost (50),
            ippath (61),
            tdmvcl(253),
            ethBundle(254),
            invalidValue(-1)
       }
       MAX-ACCESS   read-write
       STATUS       current
       DESCRIPTION
           "Port type of the ONT.
            Options:
            1. t1 (13)        -the port type of the ONT is t1
            2. e1 (14)        -the port type of the ONT is e1
            3. fe (24)        -the port type of the ONT is fe
            4. ge (34)        -the port type of the ONT is ge
            5. vdsl (37)      -the port type of the ONT is vdsl
            6. moca (46)      -the port type of the ONT is moca
            7. eth (47)       -the port type of the ONT is eth
            8. iphost (50)    -the port type of the ONT is iphost
            9. ippath (61)    -the port type of the ONT is ippath
            10. tdmvcl(253)    - the port type of the ONT is tdmvcl
            11. ethBundle(254) -the port type of the ONT is ethBundle
            12.invalidValue(-1) - Indicates that the query fails or no information is detected
           "
       ::= { hwGponDevicePortidMapControlEntry 6 }

     hwGponDevicePortidMapObjectPortID OBJECT-TYPE
       SYNTAX   Integer32
       MAX-ACCESS   read-write
       STATUS       current
       DESCRIPTION
           "Port ID of the ONT, or the bundle-groupid when it is the eth-bundle port type."
       ::= { hwGponDevicePortidMapControlEntry 7 }

   hwGponDevicePortidMapEntryStatus OBJECT-TYPE
       SYNTAX   RowStatus
       MAX-ACCESS  read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponDevicePortidMapControlEntry 8 }

   hwGponDevicePortidMapTcontAverBand OBJECT-TYPE
       SYNTAX   Integer32
       MAX-ACCESS  read-write
       STATUS      current
       DESCRIPTION
           "Average band of the flow car."
       ::= { hwGponDevicePortidMapControlEntry 9 }

   hwGponDevicePortidMapTcontMaxBand OBJECT-TYPE
       SYNTAX   Integer32
       MAX-ACCESS  read-write
       STATUS      current
       DESCRIPTION
           "Max band of the flow car."
       ::= { hwGponDevicePortidMapControlEntry 10 }

   hwGponDevicePortidMapTrafficTableId OBJECT-TYPE
       SYNTAX   Integer32 (-1 | 1..1024)
       MAX-ACCESS  read-write
       STATUS      current
       DESCRIPTION
               "The traffic table id of the flow car. Range: 1~1024."
       ::= { hwGponDevicePortidMapControlEntry 11 }

    hwGponDevicePortidMapTransparent OBJECT-TYPE
       SYNTAX   INTEGER {
                         enable(1),
                         disable(2),
                         invalidValue(-1)
       }
       MAX-ACCESS   read-write
       STATUS       current
       DESCRIPTION
              "Flow transparent switch of the ONT.
               Options:
               1. enable(1)        -Flow transparent switch of the ONT is enable
               2. disable(2)       -Flow transparent switch of the ONT is disable
               3. invalidValue(-1) -Flow transparent switch of the ONT is invalid
              "
       ::= { hwGponDevicePortidMapControlEntry 12 }

    hwGponDevicePortidMapTrafficTableName OBJECT-TYPE
       SYNTAX       OCTET STRING  (SIZE (0..32))
       MAX-ACCESS   read-write
       STATUS       current
       DESCRIPTION
              "The traffic table name of the flow car."
       ::= { hwGponDevicePortidMapControlEntry 13 }

   -- Table13 HwGponOntVlanObjectTable
   hwGponOntVlanObjectTable OBJECT-TYPE
       SYNTAX     SEQUENCE OF HwGponOntVlanObjectEntry
       MAX-ACCESS not-accessible
       STATUS     current
       DESCRIPTION
           "This is the ONT port VLAN table. This table is used to add a port to a VLAN
            or to remove a port from a VLAN, the indexes are the ifIndex, ONT ID, VLAN ID and
            ONT port type. The indexes of this table are ifIndex, hwGponDeviceOntObjectIndex,
            hwGponOntVlanIndex, and hwGponOntVlanPortType.
           "
       ::= { hwGponDeviceControlObjects 13 }

   hwGponOntVlanObjectEntry OBJECT-TYPE
       SYNTAX     HwGponOntVlanObjectEntry
       MAX-ACCESS not-accessible
       STATUS     current
       DESCRIPTION
           "This is the ONT port VLAN table. This table is used to add a port to a VLAN
            or to remove a port from a VLAN, the indexes are the ifIndex, ONT ID, VLAN ID and
            ONT port type. The indexes of this entry are ifIndex, hwGponDeviceOntObjectIndex,
            hwGponOntVlanIndex, and hwGponOntVlanPortType.
           "
       INDEX       { ifIndex, hwGponDeviceOntObjectIndex, hwGponOntVlanIndex, hwGponOntVlanPortType }
       ::= { hwGponOntVlanObjectTable 1 }

   HwGponOntVlanObjectEntry ::=
       SEQUENCE {
                hwGponOntVlanIndex              VlanIndex,
                hwGponOntVlanPortType           INTEGER,
                hwGponOntVlanPorts              PortList,
                hwGponOntVlanRowStatus          RowStatus
                }

   hwGponOntVlanIndex OBJECT-TYPE
       SYNTAX     VlanIndex
       MAX-ACCESS    not-accessible
       STATUS      current
       DESCRIPTION
           "VLAN ID."
       ::= { hwGponOntVlanObjectEntry 1 }

   hwGponOntVlanPortType OBJECT-TYPE
       SYNTAX     INTEGER {
            fe (24),
            ge (34),
            vdsl (37),
            moca (46),
            eth (47),
            iphost (50)
          }
       MAX-ACCESS    not-accessible
       STATUS      current
       DESCRIPTION
           "ONT port type.
            Options:
            1. fe (24)     -ONT port type is fe
            2. ge (34)     -ONT port type is ge
            3. vdsl (37)   -ONT port type is vdsl
            4. moca (46)   -ONT port type is moca
            5. eth (47)    -ONT port type is eth
            6. iphost (50) -ONT port type is iphost
           "
       ::= { hwGponOntVlanObjectEntry 2 }

   hwGponOntVlanPorts OBJECT-TYPE
       SYNTAX     PortList
       MAX-ACCESS    read-write
       STATUS      current
       DESCRIPTION
           "The ONT port list."
       ::= { hwGponOntVlanObjectEntry 3 }

   hwGponOntVlanRowStatus OBJECT-TYPE
       SYNTAX     RowStatus
       MAX-ACCESS    read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponOntVlanObjectEntry 4 }

   -- Table15 HwGponOntifEthernetObjectTable
   hwGponOntifEthernetObjectTable OBJECT-TYPE
       SYNTAX     SEQUENCE OF HwGponOntifEthernetObjectEntry
       MAX-ACCESS not-accessible
       STATUS     current
       DESCRIPTION
           "This is the ONT ETH port table. This table is used to
            set or query the attribute of the ONT ETH port,
            including duplex, transmission rate and native VLAN and others.
            The indexes of this table are ifIndex, hwGponDeviceOntObjectIndex,
            hwGponOntifEthernetType, and hwGponOntifEthernetPort."
       ::= { hwGponDeviceControlObjects 14 }

   hwGponOntifEthernetObjectEntry OBJECT-TYPE
       SYNTAX     HwGponOntifEthernetObjectEntry
       MAX-ACCESS not-accessible
       STATUS     current
       DESCRIPTION
           "This is the ONT ETH port table. This table is used to
            set or query the attribute of the ONT ETH port,
            including duplex, transmission rate and native VLAN and others.
            The indexes of this entry are ifIndex, hwGponDeviceOntObjectIndex,
            hwGponOntifEthernetType, and hwGponOntifEthernetPort.
           "
       INDEX       { ifIndex, hwGponDeviceOntObjectIndex, hwGponOntifEthernetType, hwGponOntifEthernetPort }
       ::= { hwGponOntifEthernetObjectTable 1 }

   HwGponOntifEthernetObjectEntry ::=
       SEQUENCE {
                hwGponOntifEthernetType                    INTEGER,
                hwGponOntifEthernetPort                    Integer32,
                hwGponOntPortOperateStatus                 INTEGER,
                hwGponOntifEthernetDuplex                  INTEGER,
                hwGponOntifEthernetMTU                     Integer32,
                hwGponOntifEthernetSpeed                   INTEGER,
                hwGponOntifEthernetMdi                     Integer32,
                hwGponOntifEthernetMacAddressLearn         Integer32,
                hwGponOntifEthernetNegotiate               INTEGER,
                hwGponOntifEthernetVlanDefault             Integer32,
                hwGponOntifEthernetOnlineState             INTEGER,
                hwGponOntifEthernetPriority                Integer32,
                hwGponOntifEthernetFlowCtrlSwitch          INTEGER,
                hwGponOntifEthernetActualPortType          Integer32,
                hwGponOntifEthernetCancelPortCar           Integer32,
                hwGponOntifEthernetPortUpAverSpeedRate     Integer32,
                hwGponOntifEthernetPortDownAverSpeedRate   Integer32,
                hwGponOntifEthernetPortUpPeakSpeedRate     Integer32,
                hwGponOntifEthernetPortDownPeakSpeedRate   Integer32,
                hwGponOntifEthernetActualDuplex            INTEGER,
                hwGponOntifEthernetActualSpeed             INTEGER,
                hwGponOntifEthernetPortActualRingStatus    INTEGER,
                hwGponOntifEthernetMode                    INTEGER,
                hwGponOntifEthernetOpticalModuleStatus     INTEGER,
                hwGponOntifEthernetOnlineDuration          Gauge32
       }

   hwGponOntifEthernetType OBJECT-TYPE
       SYNTAX     INTEGER {
                  fe(24),
                  ge(34),
                  eth(47)
       }
       MAX-ACCESS    not-accessible
       STATUS      current
       DESCRIPTION
           "The ONT ETH port type.
            Options:
            1. fe(24)  -The ONT ETH port type is fe
            2. ge(34)  -The ONT ETH port type is ge
            3. eth(47) -The ONT ETH port type is eth
           "
       ::= { hwGponOntifEthernetObjectEntry 1 }

   hwGponOntifEthernetPort OBJECT-TYPE
       SYNTAX     Integer32
       MAX-ACCESS    not-accessible
       STATUS      current
       DESCRIPTION
           "The ONT ETH port ID."
       ::= { hwGponOntifEthernetObjectEntry 2 }

   hwGponOntifEthernetDuplex OBJECT-TYPE
       SYNTAX     INTEGER {
                  half (1),
                  full (2),
                  autoneg (3),
                  autohalf(4),
                  autofull(5),
                  invalidOrQueryFail (-1)
                  }
       MAX-ACCESS    read-write
       STATUS      current
       DESCRIPTION
           "The duplex type of the port.
            Options:
                 1. half(1)                    - Forced half duplex
                 2. full(2)                    - Forced full duplex
                 3. autoneg(3)                 - Auto negotiation
                 4. autohalf(4)                - Auto half duplex
                 5. autofull(5)                - Auto full duplex
                 6. invalidOrQueryFail (-1)    - Indicates that the query fails or no information is detected
           "
       ::= { hwGponOntifEthernetObjectEntry 3 }

   hwGponOntifEthernetMTU OBJECT-TYPE
       SYNTAX     Integer32
       MAX-ACCESS    read-write
       STATUS      current
       DESCRIPTION
           "Maximum transmission unit."
       ::= { hwGponOntifEthernetObjectEntry 4 }

      hwGponOntifEthernetSpeed OBJECT-TYPE
       SYNTAX     INTEGER {
                  speed10M (1),
                  speed100M (2),
                  speed1000M (3),
                  autoneg (4),
                  autospeed10M(5),
                  autospeed100M(6),
                  autospeed1000M(7),
                  speed10G(8),
                  autospeed10G(9),
                  speed2500M(10),
                  autospeed2500M(11),
                  invalid (-1)
                  }
       MAX-ACCESS    read-write
       STATUS      current
       DESCRIPTION
           "The transmission rate of the port.
            Options:
            1. speed10M(1)          - The forced transmission rate of the port is 10M
            2. speed100M(2)         - The forced transmission rate of the port is 100M
            3. speed1000M(3)        - The forced transmission rate of the port is 1000M
            4. autoneg(4)           - The transmission rate of the port is auto negotiation
            5. autospeed10M(5)      - The auto transmission rate of the port is 10M
            6. autospeed100M(6)     - The auto transmission rate of the port is 100M
            7. autospeed1000M(7)    - The auto transmission rate of the port is 1000M
            8. speed10G(8)          - The forced transmission rate of the port is 10G
            9. autospeed10G(9)      - The auto transmission rate of the port is 10G
            10. speed2500M(10)      - The forced transmission rate of the port is 2500M
            11. autospeed2500M(11)  - The auto transmission rate of the port is 2500M
            12. invalid(-1)         - Indicates that the query fails or no information is detected
           "
       ::= { hwGponOntifEthernetObjectEntry 5 }

    hwGponOntifEthernetMdi OBJECT-TYPE
       SYNTAX     Integer32
       MAX-ACCESS    read-write
       STATUS      current
       DESCRIPTION
           "The cross and direct connection auto sensing mode."
       ::= { hwGponOntifEthernetObjectEntry 6 }

   hwGponOntifEthernetMacAddressLearn   OBJECT-TYPE
       SYNTAX     Integer32
       MAX-ACCESS    read-only
       STATUS      current
       DESCRIPTION
           "The number of learned MAC addresses."
       ::= { hwGponOntifEthernetObjectEntry 7 }

   hwGponOntifEthernetNegotiate OBJECT-TYPE
       SYNTAX     INTEGER {
                  true(1),
                  false(2),
                  invalidValue(-1)
                  }
       MAX-ACCESS    read-write
       STATUS      current
       DESCRIPTION
           "The negotiation switch.
            Options:
            1. true(1)          -Enable the negotiation switch
            2. false(2)         -Disable the negotiation switch
            3. invalidValue(-1) -The negotiation switch is invalid
           "
       ::= { hwGponOntifEthernetObjectEntry 8 }

   hwGponOntifEthernetVlanDefault   OBJECT-TYPE
       SYNTAX     Integer32
       MAX-ACCESS    read-write
       STATUS      current
       DESCRIPTION
           "The native VLAN of the port."
       ::= { hwGponOntifEthernetObjectEntry 9 }

   hwGponOntifEthernetOnlineState OBJECT-TYPE
       SYNTAX     INTEGER{
                  true(1),
                  false(2),
                  invalidValue(-1)
                  }
       MAX-ACCESS    read-only
       STATUS      current
       DESCRIPTION
           "ONT ETH port status.
            Options:
            1. true(1)          -ONT ETH port is up
            2. false(2)         -ONT ETH port is down
            3. invalidValue(-1) -Invalid value
           "
       ::= { hwGponOntifEthernetObjectEntry 10 }

   hwGponOntifEthernetPriority OBJECT-TYPE
       SYNTAX     Integer32
       MAX-ACCESS    read-write
       STATUS      current
       DESCRIPTION
           "The default priority of the port."
       ::= { hwGponOntifEthernetObjectEntry 11 }

   hwGponOntPortOperateStatus OBJECT-TYPE
       SYNTAX     INTEGER {
                  enable(1),
                  disable(2),
                  invalidValue(-1)
                  }
       MAX-ACCESS    read-write
       STATUS      current
       DESCRIPTION
           "The operation enable switch of the port.
            Options:
            1. enable(1)        -Enable the operation switch of the port
            2. disable(2)       -Disable the operation switch of the port
            3. invalidValue(-1) -The operation switch of the port is invalid
           "
       ::= { hwGponOntifEthernetObjectEntry 12 }

   hwGponOntifEthernetFlowCtrlSwitch OBJECT-TYPE
       SYNTAX     INTEGER {
                  on(1),
                  off(2),
                  invalidValue(-1)
                  }
       MAX-ACCESS    read-write
       STATUS      current
       DESCRIPTION
           "Setting ONT port flow control switch.
            Options:
            1. on(1)            -Enable the ONT port flow control switch
            2. off(2)           -Disable the ONT port flow control switch
            3. invalidValue(-1) -The ONT port flow control switch is invalid
           "
       ::= { hwGponOntifEthernetObjectEntry 13 }

   hwGponOntifEthernetActualPortType  OBJECT-TYPE
       SYNTAX     Integer32
       MAX-ACCESS    read-only
       STATUS      current
       DESCRIPTION
           "The actual ETH port type of the ONT."
       ::= { hwGponOntifEthernetObjectEntry 14 }

   hwGponOntifEthernetCancelPortCar  OBJECT-TYPE
       SYNTAX     Integer32
       MAX-ACCESS    read-write
       STATUS      current
       DESCRIPTION
           "Cancel the car value."
       DEFVAL { 1 }
       ::= { hwGponOntifEthernetObjectEntry 15 }

   hwGponOntifEthernetPortUpAverSpeedRate  OBJECT-TYPE
       SYNTAX     Integer32
       MAX-ACCESS    read-write
       STATUS      current
       DESCRIPTION
           "The upstream average speed rate."
       ::= { hwGponOntifEthernetObjectEntry 16 }

   hwGponOntifEthernetPortDownAverSpeedRate  OBJECT-TYPE
       SYNTAX     Integer32
       MAX-ACCESS    read-write
       STATUS      current
       DESCRIPTION
           "The downstream average speed rate."
       ::= { hwGponOntifEthernetObjectEntry 17 }

   hwGponOntifEthernetPortUpPeakSpeedRate  OBJECT-TYPE
       SYNTAX     Integer32
       MAX-ACCESS    read-write
       STATUS      current
       DESCRIPTION
           "The upstream peak speed rate."
       ::= { hwGponOntifEthernetObjectEntry 18 }

   hwGponOntifEthernetPortDownPeakSpeedRate  OBJECT-TYPE
       SYNTAX     Integer32
       MAX-ACCESS    read-write
       STATUS      current
       DESCRIPTION
           "The downstream peak speed rate."
       ::= { hwGponOntifEthernetObjectEntry 19 }

    hwGponOntifEthernetActualDuplex OBJECT-TYPE
       SYNTAX     INTEGER {
                  half (1),
                  full (2),
                  invalid (-1)
                  }
       MAX-ACCESS    read-only
       STATUS      current
       DESCRIPTION
           "The duplex type of the port.
            Options:
            1. half(1)                    - Indicates that the actual status of the port is half duplex
            2. full(2)                    - Indicates that the actual status of the port is full duplex
            3. invalid (-1)               - Indicates that the query fails or no information is detected
           "
       ::= { hwGponOntifEthernetObjectEntry 20 }

     hwGponOntifEthernetActualSpeed OBJECT-TYPE
       SYNTAX     INTEGER {
                  speed10M (1),
                  speed100M (2),
                  speed1000M (3),
                  speed10G(4),
                  speed2500M(5),
                  invalid (-1)
                  }
       MAX-ACCESS    read-only
       STATUS      current
       DESCRIPTION
           "The transmission rate of the port.
            Options:
            1. speed10M(1)         - Indicates that the actual transmission rate of the port is 10M
            2. speed100M(2)        - Indicates that the actual transmission rate of the port is 100M
            3. speed1000M(3)       - Indicates that the actual transmission rate of the port is 1000M
            4. speed10G(4)         - Indicates that the actual transmission rate of the port is 10G
            5. speed2500M(5)       - Indicates that the actual transmission rate of the port is 2500M
            6. invalid(-1)         - Indicates that the query fails or no information is detected
           "
       ::= { hwGponOntifEthernetObjectEntry 21 }

     hwGponOntifEthernetPortActualRingStatus OBJECT-TYPE
       SYNTAX     INTEGER {
                  loop (1),
                  noloop (2),
                  invalid (-1)
                  }
       MAX-ACCESS    read-only
       STATUS      current
       DESCRIPTION
           "The ring status of ONT ETH port.
            Options:
            1. loop(1)         - Indicates that the ring status of ONT ETH port is loop
            2. noloop(2)       - Indicates that the ring status of ONT ETH port is no loop
            3. invalid(-1)     - Indicates that the query fails or no information is detected
           "
       ::= { hwGponOntifEthernetObjectEntry 22 }

     hwGponOntifEthernetMode OBJECT-TYPE
         SYNTAX     INTEGER {
                  electric (1),
                  optic (2),
                  invalid (-1)
                  }
         MAX-ACCESS    read-only
         STATUS      current
         DESCRIPTION
           "The mode of the ONT ethernet port.
            Options:
            1. electric(1)     - Indicates that the mode of ONT ETH port is electric
            2. optic(2)        - Indicates that the mode of ONT ETH port is optic
            3. invalid(-1)     - Indicates that the query fails or no information is detected
           "
       ::= { hwGponOntifEthernetObjectEntry 23 }

     hwGponOntifEthernetOpticalModuleStatus OBJECT-TYPE
         SYNTAX    INTEGER {
                  normal (1),
                  absence (2),
                  mismatch (3),
                  invalid (-1)
                  }
        MAX-ACCESS    read-only
        STATUS      current
        DESCRIPTION
           "Indicates the optical module status of the ONT ethernet port.
            Options:
            1. normal(1)       - Indicates that the optical module status of ONT ETH port is normal
            2. absence(2)      - Indicates that the optical module status of ONT ETH port is absence
            3. mismatch(3)     - Indicates that the optical module status of ONT ETH port is mismatch
            4. invalid(-1)     - Indicates that the query fails or no information is detected
           "
       ::= { hwGponOntifEthernetObjectEntry 24 }

     hwGponOntifEthernetOnlineDuration OBJECT-TYPE
            SYNTAX      Gauge32
            UNITS       "second"
            MAX-ACCESS  read-only
            STATUS      current
            DESCRIPTION
                "Indicates the online duration of the ONT ethernet port.
                 Unit: second
                "
            ::= { hwGponOntifEthernetObjectEntry 25 }

-- Table15 HwGponOntCatvPortCfgTable
   hwGponOntCatvPortCfgTable OBJECT-TYPE
       SYNTAX     SEQUENCE OF HwGponOntCatvPortCfgEntry
       MAX-ACCESS not-accessible
       STATUS     current
       DESCRIPTION
           "Attributes table of the ONT CATV port, which can be used to start up or shut down the ONT CATV port.
            The indexes of this table are ifIndex,
            hwGponDeviceOntObjectIndex, and hwGponOntCatvPortId.
           "
       ::= { hwGponDeviceControlObjects 25 }

   hwGponOntCatvPortCfgEntry OBJECT-TYPE
       SYNTAX     HwGponOntCatvPortCfgEntry
       MAX-ACCESS not-accessible
       STATUS     current
       DESCRIPTION
           "Attributes table of the ONT CATV port, which can be used to start up or shut down the ONT CATV port.
            The indexes of this entry are ifIndex,
            hwGponDeviceOntObjectIndex, and hwGponOntCatvPortId.
           "
       INDEX       { ifIndex, hwGponDeviceOntObjectIndex, hwGponOntCatvPortId }
       ::= { hwGponOntCatvPortCfgTable 1 }

   HwGponOntCatvPortCfgEntry ::=
       SEQUENCE {
                hwGponOntCatvPortId              Integer32,
                hwGponOntCatvOperateStatus       INTEGER,
                hwGponOntCatvSendOpticalPower    Integer32,
                hwGponOntCatvReciveOpticalPower  Integer32,
                hwGponOntCatvOnlineStatus        Integer32,
                hwGponOntCatvFrequency           INTEGER,
                hwGponOntCatvTxPower             Integer32
                }

   hwGponOntCatvPortId OBJECT-TYPE
       SYNTAX     Integer32
       MAX-ACCESS    not-accessible
       STATUS      current
       DESCRIPTION
           "ONT CATV port ID."
       ::= { hwGponOntCatvPortCfgEntry 1 }

   hwGponOntCatvOperateStatus OBJECT-TYPE
       SYNTAX     INTEGER {
                  enable(1),
                  disable(2),
                  invalidValue(-1)
                  }
       MAX-ACCESS    read-write
       STATUS      current
       DESCRIPTION
           "ONT CATV port laser switch.
            Options:
            1. enable(1)        -Enable the ONT CATV port laser switch
            2. disable(2)       -Disable the ONT CATV port laser switch
            3. invalidValue(-1) -The laser switch of ONT CATV port is invalid
           "
       ::= { hwGponOntCatvPortCfgEntry 2 }

   hwGponOntCatvSendOpticalPower OBJECT-TYPE
       SYNTAX    Integer32
       MAX-ACCESS   read-only
       STATUS     current
       DESCRIPTION
           "The send optical power of the port."
       ::= { hwGponOntCatvPortCfgEntry 3 }

   hwGponOntCatvReciveOpticalPower OBJECT-TYPE
       SYNTAX    Integer32
       MAX-ACCESS   read-only
       STATUS     current
       DESCRIPTION
           "The recive optical power of the port."
       ::= { hwGponOntCatvPortCfgEntry 4 }

   hwGponOntCatvOnlineStatus OBJECT-TYPE
       SYNTAX    Integer32
       MAX-ACCESS   read-only
       STATUS     current
       DESCRIPTION
               "The catv port link status 1:Online  2:Offline"
       ::= { hwGponOntCatvPortCfgEntry 5 }

   hwGponOntCatvFrequency OBJECT-TYPE
       SYNTAX     INTEGER {
                  allPass(1),
                  highPass(2),
                  lowPass(3),
                  invalid(-1)
                  }
       MAX-ACCESS    read-write
       STATUS      current
       DESCRIPTION
           "This object indicates the frequency of ONT CATV port.
            Options:
            1. allPass(1)         - Indicates that the frequency of ONT CATV port is highPass
            2. highPass(2)        - Indicates that the frequency of ONT CATV port is highPass
            3. lowPass(3)         - Indicates that the frequency  of ONT CATV port is lowPass
            4. invalid(-1)         - Indicates that the query fails or no information is detected
            "
       ::= { hwGponOntCatvPortCfgEntry 6 }

    hwGponOntCatvTxPower OBJECT-TYPE
        SYNTAX     Integer32
        UNITS      "0.001dBmV"
        MAX-ACCESS    read-only
        STATUS      current
        DESCRIPTION
            "This object indicates the Tx power of ONT CATV port.
             Unit: 0.001dBmV
             Options:
             1. invalid(0x7FFFFFFF)      - Indicates that the query fails or no information is detected
            "
        ::= { hwGponOntCatvPortCfgEntry 7 }

-- Table16 HwGponOntTDMPortCfgTable
   hwGponOntTDMPortCfgTable OBJECT-TYPE
       SYNTAX     SEQUENCE OF HwGponOntTDMPortCfgEntry
       MAX-ACCESS not-accessible
       STATUS     current
       DESCRIPTION
           "ONT TDM port config table.
            The indexes of this table are ifIndex,
            hwGponDeviceOntObjectIndex and
            hwGponOntTDMPortId.
           "
       ::= { hwGponDeviceControlObjects 26 }

   hwGponOntTDMPortCfgEntry OBJECT-TYPE
       SYNTAX     HwGponOntTDMPortCfgEntry
       MAX-ACCESS not-accessible
       STATUS     current
       DESCRIPTION
           "ONT TDM port config table.
            The indexes of this entry are ifIndex,
            hwGponDeviceOntObjectIndex and
            hwGponOntTDMPortId.
           "
       INDEX       { ifIndex, hwGponDeviceOntObjectIndex, hwGponOntTDMPortId }
       ::= { hwGponOntTDMPortCfgTable 1 }

   HwGponOntTDMPortCfgEntry ::=
       SEQUENCE {
                hwGponOntTDMPortId              Integer32,
                hwGponOntTDMPortOperateStatus   INTEGER,
                hwGponDeviceTDMPortCodeMode     INTEGER,
                hwGponDeviceOntTdmPortLoopback  INTEGER,
                hwGponOntTDMPortOnlineState     INTEGER,
                hwGponOntTDMPortTxClockMode     INTEGER
                }

   hwGponOntTDMPortId OBJECT-TYPE
       SYNTAX     Integer32
       MAX-ACCESS    not-accessible
       STATUS      current
       DESCRIPTION
           "ONT TDM port ID."
       ::= { hwGponOntTDMPortCfgEntry 1 }

   hwGponOntTDMPortOperateStatus OBJECT-TYPE
       SYNTAX     INTEGER {
                  enable(1),
                  disable(2),
                  invalid(-1)
                  }
       MAX-ACCESS    read-write
       STATUS      current
       DESCRIPTION
           "ONT TDM port enable switch.
            Options:
            1. enable(1)  -Enable the ONT TDM port switch
            2. disable(2) -Disable the ONT TDM port switch
            3. invalid(-1) -Indicates that the query fails or no information is detected
           "
       ::= { hwGponOntTDMPortCfgEntry 2 }

   hwGponDeviceTDMPortCodeMode OBJECT-TYPE
       SYNTAX    INTEGER{
                 ami(1),
                 hdb3(2),
                 invalid(-1)
                 }
       MAX-ACCESS  read-write
       STATUS      current
       DESCRIPTION
           "The code mode of the TDM port.
            Options:
            1. ami(1)  -The code mode of the TDM port is ami
            2. hdb3(2) -The code mode of the TDM port is hdb3
            3. invalid(-1) -Indicates that the query fails or no information is detected
           "
       ::= { hwGponOntTDMPortCfgEntry 3 }

   hwGponDeviceOntTdmPortLoopback OBJECT-TYPE
       SYNTAX    INTEGER{
                 noLoopback(1),
                 remoteInnerLoopback(2),
                 remoteOuterLoopback(4),
                 invalid(-1)
                 }
       MAX-ACCESS  read-write
       STATUS      current
       DESCRIPTION
           "The loopback mode of the ONT TDM port.
            Options:
            1. noLoopback(1)          - Indicates no loopback or that the loopback is canceled
            2. remoteInnerLoopback(2) - Indicates the remote inner loopback on the port
            3. remoteOuterLoopback(4) - Indicates the remote outer loopback on the port
            4. invalid(-1)            - Indicates that the query fails or no information is detected
           "
       DEFVAL { noLoopback }
       ::= { hwGponOntTDMPortCfgEntry 4 }

   hwGponOntTDMPortOnlineState OBJECT-TYPE
       SYNTAX    INTEGER{
                  true(1),
                  false(2),
                  invalid(-1)
                 }
       MAX-ACCESS  read-write
       STATUS      current
       DESCRIPTION
               "The link state of the ONT TDM port.
                Options:
                1. true(1)  -The link state of the ONT TDM port is true
                2. false(2) -The link state of the ONT TDM port is false
                3. invalid(-1) - Indicates that the query fails or no information is detected
               "
       DEFVAL { true }
       ::= { hwGponOntTDMPortCfgEntry 5 }

   hwGponOntTDMPortTxClockMode OBJECT-TYPE
       SYNTAX    INTEGER{
                  adapt(1),
                  system(2),
                  invalid(-1)
                 }
       MAX-ACCESS  read-write
       STATUS      current
       DESCRIPTION
               "This object indicates the tx-clock mode of ONT TDM port.
                Options:
                1. adapt(1)    - Indicates that the tx-clock mode of the ONT TDM port is adapt
                2. system(2)   - Indicates that the tx-clock mode of the ONT TDM port is system
                3. invalid(-1) - Indicates that the query fails or no information is detected
               "
       ::= { hwGponOntTDMPortCfgEntry 6 }

-- Table27 hwGponOntPortExtConfigTable
   hwGponOntPortExtConfigTable OBJECT-TYPE
       SYNTAX     SEQUENCE OF HwGponOntPortExtConfigEntry
       MAX-ACCESS not-accessible
       STATUS     current
       DESCRIPTION
           "Extended attributes table of the ONT port.
            The table is used to configure the ONT port attributes
            which are not necessary and set one leaf at one time.
            The indexes of this table are ifIndex, hwGponDeviceOntObjectIndex,
            hwGponOntPortType, and hwGponOntPortId.
           "
       ::= { hwGponDeviceControlObjects 27 }

   hwGponOntPortExtConfigEntry OBJECT-TYPE
       SYNTAX     HwGponOntPortExtConfigEntry
       MAX-ACCESS not-accessible
       STATUS     current
       DESCRIPTION
           "Extended attributes table of the ONT port.
            The table is used to configure the ONT port attributes
            which are not necessary and set one leaf at one time.
            The indexes of this entry are ifIndex, hwGponDeviceOntObjectIndex,
            hwGponOntPortType, and hwGponOntPortId.
           "
       INDEX       { ifIndex, hwGponDeviceOntObjectIndex, hwGponOntPortType, hwGponOntPortId }
       ::= { hwGponOntPortExtConfigTable 1 }

   HwGponOntPortExtConfigEntry ::=
       SEQUENCE {
                hwGponOntPortType                             INTEGER,
                hwGponOntPortId                               Integer32,
                hwGponOntEthPortLoopback                      INTEGER,
                hwGponOntPortQinqMode                         INTEGER,
                hwGponOntPortPriorityPolicy                   INTEGER,
                hwGponOntEthPortUpStreamCarTrafficTableId     Integer32,
                hwGponOntEthPortDownStreamCarTrafficTableId   Integer32,
                hwGponOntPortDscpProfileIndex                 Integer32,
                hwGponOntPortUpIgmpForwardMode                INTEGER,
                hwGponOntPortUpIgmpTransmitMode               INTEGER,
                hwGponOntPortUpIgmpMsgTranslationVlan         Integer32,
                hwGponOntPortUpIgmpMsgPriority                Integer32,
                hwGponOntPortMaxMacAddressNum                 Gauge32,
                hwGponOntEthPortDownstreamMode                INTEGER,
                hwGponOntEthPortUpStreamCarTrafficTableName   OCTET STRING,
                hwGponOntEthPortDownStreamCarTrafficTableName OCTET STRING,
                hwGponOntPortClassProfileIndex                Integer32,
                hwGponOntPortUnknownUnicastRate               Integer32,
                hwGponOntPortBroadcastRate                    Integer32,
                hwGponOntPortUnknownMulticastRate             Integer32
                }

   hwGponOntPortType OBJECT-TYPE
       SYNTAX     INTEGER {
                  fe(24),
                  ge(34),
                  vdsl(37),
                  wifi(40),
                  eth(47)
       }
       MAX-ACCESS    not-accessible
       STATUS      current
       DESCRIPTION
           "ONT port type.
            Options:
            1. fe(24)   - Indicates the FE port
            2. ge(34)   - Indicates the GE port
            3. vdsl(37) - Indicates the VDSL port
            4. wifi(40) - Indicates the WiFi port
            5. eth(47)  - Indicates the ETH port
           "
       ::= { hwGponOntPortExtConfigEntry 1 }

   hwGponOntPortId OBJECT-TYPE
       SYNTAX     Integer32
       MAX-ACCESS    not-accessible
       STATUS      current
       DESCRIPTION
           "ONT port ID."
       ::= { hwGponOntPortExtConfigEntry 2 }

   hwGponOntEthPortLoopback OBJECT-TYPE
       SYNTAX    INTEGER{
                 noloop(1),
                 remoteinner(2),
                 invalidValue(-1)
                 }
       MAX-ACCESS  read-write
       STATUS      current
       DESCRIPTION
           "The loopback mode of the ETH port.
            Options:
            1. noloop(1)        -The loopback mode of the ETH port is noloop
            2. remoteinner(2)   -The loopback mode of the ETH port is remoteinner
            3. invalidValue(-1) -The loopback mode of the ETH port is invalid
           "
       ::= { hwGponOntPortExtConfigEntry 3 }

   hwGponOntPortQinqMode OBJECT-TYPE
       SYNTAX    INTEGER{
                 disable(1),
                 enable(2),
                 unconcern(254)
                 }
       MAX-ACCESS  read-write
       STATUS      current
       DESCRIPTION
           "QinQ transparent transmission mode.
            Options:
            1. disable(1)     -Disable QinQ transparent transmission mode
            2. enable(2)      -Enable QinQ transparent transmission mode
            3. unconcern(254) -Unconcern QinQ transparent transmission mode
           "
       ::= { hwGponOntPortExtConfigEntry 4 }

   hwGponOntPortPriorityPolicy OBJECT-TYPE
       SYNTAX    INTEGER{
                 assigned(1),
                 copycos(2),
                 unconcern(254)
                 }
       MAX-ACCESS  read-write
       STATUS      current
       DESCRIPTION
           "The priority policy.
            Options:
            1. assigned(1)      -Assigned the priority policy
            2. copycos(2)       -The priority policy is copycos
            3. unconcern(254)   -Unconcern the priority policy
           "
       ::= { hwGponOntPortExtConfigEntry 5 }

   hwGponOntEthPortUpStreamCarTrafficTableId OBJECT-TYPE
       SYNTAX      Integer32
       MAX-ACCESS  read-write
       STATUS      current
       DESCRIPTION
           "The up stream car profile index of the ONT port, and range of 1~1024, and 0xfffe-unconcern."
       ::= { hwGponOntPortExtConfigEntry 6 }

   hwGponOntEthPortDownStreamCarTrafficTableId OBJECT-TYPE
       SYNTAX      Integer32
       MAX-ACCESS  read-write
       STATUS      current
       DESCRIPTION
           "The down stream car profile index of the ONT port, and range of 1~1024, and 0xfffe-unconcern."
       ::= { hwGponOntPortExtConfigEntry 7 }

  hwGponOntPortDscpProfileIndex OBJECT-TYPE
       SYNTAX      Integer32
       MAX-ACCESS  read-write
       STATUS      current
       DESCRIPTION
                   "The dscp profile index of the ONT eth port."
       ::= { hwGponOntPortExtConfigEntry 8 }

  hwGponOntPortUpIgmpForwardMode OBJECT-TYPE
       SYNTAX    INTEGER{
                 disable(1),
                 enable(2),
                 invalid(-1)
                 }
       MAX-ACCESS  read-write
       STATUS      current
       DESCRIPTION
           "The object is used to enable or disable the switch of ONT port IGMP forward mode.
            Options:
            1. disable(1)     - Disable the switch of ONT port IGMP forward mode
            2. enable(2)      - Enable the switch of ONT port IGMP forward mode
            3. invalid(-1)    - Indicates that the query fails or no information is detected
           "
       ::= { hwGponOntPortExtConfigEntry 9 }

   hwGponOntPortUpIgmpTransmitMode OBJECT-TYPE
       SYNTAX INTEGER {
                transparent(1),
                translation(2),
                default(3),
                disable(254),
                invalid(-1)
                }
       MAX-ACCESS read-write
       STATUS current
       DESCRIPTION
           "This object indicates the upstream igmp packets transmit mode of GPON ONT port.
            Options:
            1. transparent(1)    - Indicates that the GPON ONT port upstream igmp packets transmit mode is transparent
            2. translation(2)    - Indicates that the GPON ONT port upstream igmp packets transmit mode is translation
            3. default(3)        - Indicates that the GPON ONT port upstream igmp packets transmit mode is default
            4. disable(254)      - Indicates that the GPON ONT port upstream igmp packets transmit mode configured will be cancelled
            5. invalid(-1)       - Indicates that the query fails or no information is detected
           "
       ::= { hwGponOntPortExtConfigEntry 10 }

   hwGponOntPortUpIgmpMsgTranslationVlan OBJECT-TYPE
       SYNTAX Integer32 (-1|0..4095)
       MAX-ACCESS read-write
       STATUS current
       DESCRIPTION
           "The GPON ONT port upstream igmp packets will be translate to the translation vlan,
            if GPON ONT port upstream igmp packets forward mode is translation(2) or default(3).
           "
       ::= { hwGponOntPortExtConfigEntry 11 }

   hwGponOntPortUpIgmpMsgPriority OBJECT-TYPE
       SYNTAX Integer32 (-1|0..7)
       MAX-ACCESS read-write
       STATUS current
       DESCRIPTION
            "When GPON ONT port upstream igmp packets were added a vlan or
             translated to the translation vlan, priority was set.
            "
       ::= { hwGponOntPortExtConfigEntry 12 }

   hwGponOntPortMaxMacAddressNum OBJECT-TYPE
       SYNTAX Gauge32 (0..255 | 4294967295)
       MAX-ACCESS read-write
       STATUS current
       DESCRIPTION
            "This object indicates the maximum number of MAC addresses that can be learned on each ONT port.
             The number of MAC addresses learned on an ONT port should not greater than this number.
              range:0~255. 4294967295 is invalid value. 0 is default value, means unlimited.
            "
       ::= { hwGponOntPortExtConfigEntry 13 }

   hwGponOntEthPortDownstreamMode OBJECT-TYPE
       SYNTAX INTEGER {
                noOperation(1),
                operationAndDiscardMismatch(2),
                operationAndForwardMismatch(3),
                invalid(-1)
                }
       MAX-ACCESS read-write
       STATUS current
       DESCRIPTION
            "This object indicates the downstream mode of GPON ONT port.
             Options:
             1. noOperation(1)                 - Indicates not to process the VLAN tag of the downstram packets
             2. operationAndDiscardMismatch(2) - Indicates to process the VLAN tag of the downstream packets and discard the packets with mismatched VLAN tag
             3. operationAndForwardMismatch(3) - Indicates to process the VLAN tag of the downstream packets and forward the packets with mismatched VLAN tag
             4. invalid(-1)                    - Indicates that the query fails or no information is detected
            "
       ::= { hwGponOntPortExtConfigEntry 14 }

   hwGponOntEthPortUpStreamCarTrafficTableName OBJECT-TYPE
       SYNTAX OCTET STRING  (SIZE (0..32))
       MAX-ACCESS read-write
       STATUS current
       DESCRIPTION
            "The up stream car profile name of the ONT port."
       ::= { hwGponOntPortExtConfigEntry 15 }

   hwGponOntEthPortDownStreamCarTrafficTableName OBJECT-TYPE
       SYNTAX OCTET STRING  (SIZE (0..32))
       MAX-ACCESS read-write
       STATUS current
       DESCRIPTION
            "The down stream car profile name of the ONT port."
       ::= { hwGponOntPortExtConfigEntry 16 }

   hwGponOntPortClassProfileIndex OBJECT-TYPE
       SYNTAX Integer32
       MAX-ACCESS read-write
       STATUS current
       DESCRIPTION
            "Indicates the index of the traffic classification profile configured on the ONT port.
             The valid value range is 1~256.
             The value (65534) indicates that the traffic classification profile is not bound to the port.
             The value (-1) indicates that the query fails or no information is detected.
            "
       ::= { hwGponOntPortExtConfigEntry 17 }

   hwGponOntPortUnknownUnicastRate OBJECT-TYPE
       SYNTAX Integer32
       MAX-ACCESS read-write
       STATUS current
       DESCRIPTION
           "This object indicates the unknown unicast traffic suppression on the ONT port.
            The value (0~10000000) indicates the unknown unicast traffic maximum rate on the ONT port.
            The value (-3) indicates that the unknown unicast traffic rate on the ONT port is unlimited.
            The value (-2) indicates that the unknown unicast traffic suppression on the ONT port is not configured.
            The value (-1) indicates that the query fails or no information is detected.
            "
       ::= { hwGponOntPortExtConfigEntry 18 }

   hwGponOntPortBroadcastRate OBJECT-TYPE
       SYNTAX Integer32
       MAX-ACCESS read-write
       STATUS current
       DESCRIPTION
           "This object indicates the broadcast traffic suppression on the ONT port.
            The value (0~10000000) indicates the broadcast traffic maximum rate on the ONT port.
            The value (-3) indicates that the broadcast traffic rate on the ONT port is unlimited.
            The value (-2) indicates that the broadcast traffic suppression on the ONT port is not configured.
            The value (-1) indicates that the query fails or no information is detected.
            "
       ::= { hwGponOntPortExtConfigEntry 19 }

   hwGponOntPortUnknownMulticastRate OBJECT-TYPE
       SYNTAX Integer32
       MAX-ACCESS read-write
       STATUS current
       DESCRIPTION
           "This object indicates the unknown multicast traffic suppression on the ONT port.
            The value (0~10000000) indicates the unknown multicast traffic maximum rate on the ONT port.
            The value (-3) indicates that the unknown multicast traffic rate on the ONT port is unlimited.
            The value (-2) indicates that the unknown multicast traffic suppression on the ONT port is not configured.
            The value (-1) indicates that the query fails or no information is detected.
            "
       ::= { hwGponOntPortExtConfigEntry 20 }

-- Table28 hwGponOntPOTSPortCfgTable
   hwGponOntPOTSPortCfgTable OBJECT-TYPE
       SYNTAX     SEQUENCE OF HwGponOntPOTSPortCfgEntry
       MAX-ACCESS not-accessible
       STATUS     current
       DESCRIPTION
           "Attributes table of the ONT POTS port, currently used for setting the management status of the port and querying the actual status of the port.
            The indexes of this table are ifIndex, hwGponDeviceOntObjectIndex, and
            hwGponOntPOTSPortId.
           "
       ::= { hwGponDeviceControlObjects 28 }

   hwGponOntPOTSPortCfgEntry OBJECT-TYPE
       SYNTAX     HwGponOntPOTSPortCfgEntry
       MAX-ACCESS not-accessible
       STATUS     current
       DESCRIPTION
           "Attributes table of the ONT POTS port, currently used for setting the management status of the port and querying the actual status of the port.
            The indexes of this entry are ifIndex, hwGponDeviceOntObjectIndex, and
            hwGponOntPOTSPortId.
           "
       INDEX       { ifIndex, hwGponDeviceOntObjectIndex, hwGponOntPOTSPortId }
       ::= { hwGponOntPOTSPortCfgTable 1 }

   HwGponOntPOTSPortCfgEntry ::=
       SEQUENCE {
                hwGponOntPOTSPortId              Integer32,
                hwGponOntPOTSPortOperateStatus   INTEGER,
                hwGponOntPOTSPortOnlineState     INTEGER

                }

   hwGponOntPOTSPortId OBJECT-TYPE
       SYNTAX     Integer32
       MAX-ACCESS    not-accessible
       STATUS      current
       DESCRIPTION
           "ONT POTS port ID."
       ::= { hwGponOntPOTSPortCfgEntry 1 }

   hwGponOntPOTSPortOperateStatus OBJECT-TYPE
       SYNTAX     INTEGER {
                  enable(1),
                  disable(2)
                  }
       MAX-ACCESS    read-write
       STATUS      current
       DESCRIPTION
           "ONT POTS port enable switch.
            Options:
            1. enable(1)  -ONT POTS port enable switch
            2. disable(2) -ONT POTS port disable switch
           "
       ::= { hwGponOntPOTSPortCfgEntry 2 }

   hwGponOntPOTSPortOnlineState OBJECT-TYPE
       SYNTAX    INTEGER{
                  true(1),
                  false(2)
                 }
       MAX-ACCESS  read-write
       STATUS      current
       DESCRIPTION
           "The link state of the ONT POTS port.
            Options:
            1. true(1)  -Indicates that the ONT POTS port is online
            2. false(2) -Indicates that the ONT POTS port is offline
           "
       ::= { hwGponOntPOTSPortCfgEntry 3 }

-- Table17 HwGponOntMocaPortCfgTable
  hwGponOntMocaPortCfgTable OBJECT-TYPE
       SYNTAX     SEQUENCE OF HwGponOntMocaPortCfgEntry
       MAX-ACCESS not-accessible
       STATUS     current
       DESCRIPTION
           "The ONT MOCA port config table.
            The indexes of this table are ifIndex,
            hwGponDeviceOntObjectIndex and
            hwGponOnMocaPortId.
           "
       ::= { hwGponDeviceControlObjects 31 }

   hwGponOntMocaPortCfgEntry OBJECT-TYPE
       SYNTAX     HwGponOntMocaPortCfgEntry
       MAX-ACCESS not-accessible
       STATUS     current
       DESCRIPTION
           "The ONT MOCA port config table.
            The indexes of this entry are ifIndex,
            hwGponDeviceOntObjectIndex and
            hwGponOnMocaPortId.
           "
       INDEX       { ifIndex, hwGponDeviceOntObjectIndex, hwGponOnMocaPortId }
       ::= { hwGponOntMocaPortCfgTable 1 }

   HwGponOntMocaPortCfgEntry ::=
       SEQUENCE {
                hwGponOnMocaPortId                  Integer32,
                hwGponOntMocaPortVlanDefault        Integer32,
                hwGponOntMocaPortPri                Integer32,
                hwGponOntMocaPortDscpProfileIndex   Integer32
                }

    hwGponOnMocaPortId OBJECT-TYPE
       SYNTAX    Integer32
       MAX-ACCESS  not-accessible
       STATUS      current
       DESCRIPTION
           "ONT MOCA port ID."
       ::= { hwGponOntMocaPortCfgEntry 1 }

    hwGponOntMocaPortVlanDefault OBJECT-TYPE
       SYNTAX    Integer32
       MAX-ACCESS  read-write
       STATUS      current
       DESCRIPTION
           "Default VLAN of the port."
       ::= { hwGponOntMocaPortCfgEntry 2 }

    hwGponOntMocaPortPri OBJECT-TYPE
       SYNTAX    Integer32
       MAX-ACCESS  read-write
       STATUS      current
       DESCRIPTION
           "Default priority of the port."
       ::= { hwGponOntMocaPortCfgEntry 3 }

    hwGponOntMocaPortDscpProfileIndex OBJECT-TYPE
       SYNTAX    Integer32
       MAX-ACCESS  read-write
       STATUS      current
       DESCRIPTION
                   "The dscp profile index of the ONT moca port, the range is 1~50."
       ::= { hwGponOntMocaPortCfgEntry 4 }

  -- Table18 HwGponOntIpHostPortCfgTable
   hwGponOntIpHostPortCfgTable OBJECT-TYPE
       SYNTAX     SEQUENCE OF HwGponOntIpHostPortCfgEntry
       MAX-ACCESS not-accessible
       STATUS     current
       DESCRIPTION
           "The ONT IPHOST port config table.
            The indexes of this table are ifIndex,
            hwGponDeviceOntObjectIndex and
            hwGponOntIpHostPortId.
           "
       ::= { hwGponDeviceControlObjects 32 }

   hwGponOntIpHostPortCfgEntry OBJECT-TYPE
       SYNTAX     HwGponOntIpHostPortCfgEntry
       MAX-ACCESS not-accessible
       STATUS     current
       DESCRIPTION
           "The ONT IPHOST port config table.
            The indexes of this entry are ifIndex,
            hwGponDeviceOntObjectIndex and
            hwGponOntIpHostPortId.
           "
       INDEX       { ifIndex, hwGponDeviceOntObjectIndex, hwGponOntIpHostPortId }
       ::= { hwGponOntIpHostPortCfgTable 1 }

   HwGponOntIpHostPortCfgEntry ::=
       SEQUENCE {
                hwGponOntIpHostPortId          Integer32,
                hwGponOntIpHostPortVlanDefault Integer32,
                hwGponOntIpHostPortPri         Integer32,
                hwGponOntIpHostPortDscpProfileIndex Integer32
                }

    hwGponOntIpHostPortId OBJECT-TYPE
       SYNTAX    Integer32
       MAX-ACCESS  not-accessible
       STATUS      current
       DESCRIPTION
           "ONT IPHOST port ID."
       ::= { hwGponOntIpHostPortCfgEntry 1 }

    hwGponOntIpHostPortVlanDefault OBJECT-TYPE
       SYNTAX    Integer32
       MAX-ACCESS  read-write
       STATUS      current
       DESCRIPTION
           "The default VLAN of the port."
       ::= { hwGponOntIpHostPortCfgEntry 2 }

    hwGponOntIpHostPortPri OBJECT-TYPE
       SYNTAX    Integer32
       MAX-ACCESS  read-write
       STATUS      current
       DESCRIPTION
           "The default priority of the port."
       ::= { hwGponOntIpHostPortCfgEntry 3 }

     hwGponOntIpHostPortDscpProfileIndex OBJECT-TYPE
       SYNTAX      Integer32
       MAX-ACCESS  read-write
       STATUS      current
       DESCRIPTION
                   "The dscp profile index of the ONT iphost port, the range is 1~50."
       ::= { hwGponOntIpHostPortCfgEntry 4 }

   hwGponDeviceAlarmProfileTable OBJECT-TYPE
       SYNTAX     SEQUENCE OF HwGponDeviceAlarmProfileEntry
       MAX-ACCESS not-accessible
       STATUS     current
       DESCRIPTION
           "This table is used to create, delete or modify the GPON alarm profile.
            The index of this table is hwGponDeviceAlarmProfileNameIndex.
           "
       ::= { hwGponDeviceControlObjects 15 }

   hwGponDeviceAlarmProfileEntry OBJECT-TYPE
       SYNTAX     HwGponDeviceAlarmProfileEntry
       MAX-ACCESS not-accessible
       STATUS     current
       DESCRIPTION
           "This table is used to create, delete or modify the GPON alarm profile.
            The index of this entry is hwGponDeviceAlarmProfileNameIndex.
           "
       INDEX       { IMPLIED hwGponDeviceAlarmProfileNameIndex }
       ::= { hwGponDeviceAlarmProfileTable 1 }

   HwGponDeviceAlarmProfileEntry ::=
       SEQUENCE {
                 hwGponDeviceAlarmProfileNameIndex                     OCTET STRING,
                 hwGponDeviceAlarmProfileRefNum                        Integer32,
                 hwGponDeviceLostPacketsThreshold                      Integer32,
                 hwGponDeviceMisinsertedPacketsThreshold               Integer32,
                 hwGponDeviceImpairedBlocksThreshold                   Integer32,
                 hwGponDeviceFCSErrorsThreshold                        Integer32,
                 hwGponDeviceExcessiveCollisionCounterThreshold        Integer32,
                 hwGponDeviceLateCollisionCounterThreshold             Integer32,
                 hwGponDeviceFrameTooLongsThreshold                    Integer32,
                 hwGponDeviceBufferOverflowsonReceiveThreshold         Integer32,
                 hwGponDeviceBufferOverflowsonTransmitThreshold        Integer32,
                 hwGponDeviceSingleCollisionFrameCounterThreshold      Integer32,
                 hwGponDeviceMultipleCollisionsFrameCounterThreshold   Integer32,
                 hwGponDeviceSQECounterThreshold                       Integer32,
                 hwGponDeviceDeferredTransmissionCounterThreshold      Integer32,
                 hwGponDeviceInternalmactransmiterrorcounterThreshold  Integer32,
                 hwGponDeviceCarrierSenseErrorCounterThreshold         Integer32,
                 hwGponDeviceAlignmentErrorCounterThreshold            Integer32,
                 hwGponDeviceInternalMACReceiveErrorCounterThreshold   Integer32,
                 hwGponDevicePPPoEFilteredFrameCounterThreshold        Integer32,
                 hwGponDeviceDelayExceededDiscardThreshold             Integer32,
                 hwGponDeviceMTUExceededDiscardThreshold               Integer32,
                 hwGponDeviceReceivedAndDiscardedThreshold             Integer32,
                 hwGponDeviceCESErrorSecondsThreshold                  Integer32,
                 hwGponDeviceCESSeverelyErrorSecondsThreshold          Integer32,
                 hwGponDeviceCESBurstyErrorSecondsThreshold            Integer32,
                 hwGponDeviceCESUnavailableSecondsThreshold            Integer32,
                 hwGponDeviceCESControlledSlipSecondsThreshold         Integer32,
                 hwGponDeviceAlarmThresholdRowStatus                   RowStatus,
                 hwGponDeviceDropEventsThreshold                       Integer32,
                 hwGponDeviceUndersizepacketsThreshold                 Integer32,
                 hwGponDeviceFragmentsThreshold                        Integer32,
                 hwGponDeviceJabbersThreshold                          Integer32,
                 hwGponDeviceFailedSignalOfOnuThreshold                Integer32,
                 hwGponDeviceDegradedSignalOfOnuThreshold              Integer32,
                 hwGponDeviceFECUncorrectCodeWordsThreshold            Gauge32,
                 hwGponDeviceFECCorrectCodeWordsThreshold              Gauge32,
                 hwGponDeviceUpstreamPQDiscardedBytesThreshold         Integer32,
                 hwGponDeviceDownstreamPQDiscardedBytesThreshold       Integer32,
                 hwGponDeviceEncryptionKeyErrorsOfOnuThreshold         Integer32,
                 hwGponDeviceXgemKeyErrorsOfOnuThreshold               Integer32,
                 hwGponDeviceXgemHecErrorCountOfOnuThreshold           Integer32
    }

   hwGponDeviceAlarmProfileNameIndex OBJECT-TYPE
       SYNTAX     OCTET STRING (SIZE (1..33))
       MAX-ACCESS    not-accessible
       STATUS      current
       DESCRIPTION
           "The alarm profile name."
       ::= { hwGponDeviceAlarmProfileEntry 1 }

   hwGponDeviceAlarmProfileRefNum OBJECT-TYPE
       SYNTAX     Integer32
       MAX-ACCESS    read-only
       STATUS      current
       DESCRIPTION
           "The binding times of the profile."
       ::= { hwGponDeviceAlarmProfileEntry 2 }

   hwGponDeviceLostPacketsThreshold OBJECT-TYPE
       SYNTAX     Integer32
       MAX-ACCESS    read-write
       STATUS      current
       DESCRIPTION
           "The loss of frames threshold of GEM port."
       ::= { hwGponDeviceAlarmProfileEntry 3 }

   hwGponDeviceMisinsertedPacketsThreshold OBJECT-TYPE
       SYNTAX     Integer32
       MAX-ACCESS    read-write
       STATUS      current
       DESCRIPTION
           "The miss inserted frames threshold of GEM port."
       ::= { hwGponDeviceAlarmProfileEntry 4 }

   hwGponDeviceImpairedBlocksThreshold OBJECT-TYPE
       SYNTAX     Integer32
       MAX-ACCESS    read-write
       STATUS      current
       DESCRIPTION
           "The impaired blocks threshold of GEM port."
       ::= { hwGponDeviceAlarmProfileEntry 5 }

   hwGponDeviceFCSErrorsThreshold OBJECT-TYPE
       SYNTAX     Integer32
       MAX-ACCESS    read-write
       STATUS      current
       DESCRIPTION
           "Ethernet FCS errors threshold."
       ::= { hwGponDeviceAlarmProfileEntry 6 }

   hwGponDeviceExcessiveCollisionCounterThreshold OBJECT-TYPE
       SYNTAX     Integer32
       MAX-ACCESS    read-write
       STATUS      current
       DESCRIPTION
           "Ethernet excessive collision count threshold."
       ::= { hwGponDeviceAlarmProfileEntry 7 }

   hwGponDeviceLateCollisionCounterThreshold OBJECT-TYPE
       SYNTAX     Integer32
       MAX-ACCESS    read-write
       STATUS      current
       DESCRIPTION
           "Ethernet late collision count threshold."
       ::= { hwGponDeviceAlarmProfileEntry 8 }

   hwGponDeviceFrameTooLongsThreshold OBJECT-TYPE
       SYNTAX     Integer32
       MAX-ACCESS    read-write
       STATUS      current
       DESCRIPTION
           "This object indicates the too long Ethernet frames alarm threshold."
       ::= { hwGponDeviceAlarmProfileEntry 9 }

   hwGponDeviceBufferOverflowsonReceiveThreshold OBJECT-TYPE
       SYNTAX     Integer32
       MAX-ACCESS    read-write
       STATUS      current
       DESCRIPTION
           "Ethernet buffer received overflows threshold."
       ::= { hwGponDeviceAlarmProfileEntry 10 }

   hwGponDeviceBufferOverflowsonTransmitThreshold OBJECT-TYPE
       SYNTAX     Integer32
       MAX-ACCESS    read-write
       STATUS      current
       DESCRIPTION
           "Ethernet buffer transmission overflows threshold."
       ::= { hwGponDeviceAlarmProfileEntry 11 }

   hwGponDeviceSingleCollisionFrameCounterThreshold OBJECT-TYPE
       SYNTAX     Integer32
       MAX-ACCESS    read-write
       STATUS      current
       DESCRIPTION
           "Ethernet single collision frame count threshold."
       ::= { hwGponDeviceAlarmProfileEntry 12 }

   hwGponDeviceMultipleCollisionsFrameCounterThreshold OBJECT-TYPE
       SYNTAX     Integer32
       MAX-ACCESS    read-write
       STATUS      current
       DESCRIPTION
           "Ethernet multiple collisions frame count threshold."
       ::= { hwGponDeviceAlarmProfileEntry 13 }

   hwGponDeviceSQECounterThreshold OBJECT-TYPE
       SYNTAX     Integer32
       MAX-ACCESS    read-write
       STATUS      current
       DESCRIPTION
           "Alarm threshold of the number of SQE test error messages."
       ::= { hwGponDeviceAlarmProfileEntry 14 }

   hwGponDeviceDeferredTransmissionCounterThreshold OBJECT-TYPE
       SYNTAX     Integer32
       MAX-ACCESS    read-write
       STATUS      current
       DESCRIPTION
           "Ethernet deferred transmission count threshold."
       ::= { hwGponDeviceAlarmProfileEntry 15 }

   hwGponDeviceInternalmactransmiterrorcounterThreshold OBJECT-TYPE
       SYNTAX     Integer32
       MAX-ACCESS    read-write
       STATUS      current
       DESCRIPTION
           "Ethernet internal MAC transmission errors threshold."
       ::= { hwGponDeviceAlarmProfileEntry 16 }

   hwGponDeviceCarrierSenseErrorCounterThreshold OBJECT-TYPE
       SYNTAX     Integer32
       MAX-ACCESS    read-write
       STATUS      current
       DESCRIPTION
           "Alarm threshold of the number of loss errors during Ethernet carrier sense."
       ::= { hwGponDeviceAlarmProfileEntry 17 }

   hwGponDeviceAlignmentErrorCounterThreshold OBJECT-TYPE
       SYNTAX     Integer32
       MAX-ACCESS    read-write
       STATUS      current
       DESCRIPTION
           "Ethernet alignment errors threshold."
       ::= { hwGponDeviceAlarmProfileEntry 18 }

   hwGponDeviceInternalMACReceiveErrorCounterThreshold OBJECT-TYPE
       SYNTAX     Integer32
       MAX-ACCESS    read-write
       STATUS      current
       DESCRIPTION
           "Ethernet internal MAC receive errors threshold."
       ::= { hwGponDeviceAlarmProfileEntry 19 }

   hwGponDevicePPPoEFilteredFrameCounterThreshold OBJECT-TYPE
       SYNTAX     Integer32
       MAX-ACCESS    read-write
       STATUS      current
       DESCRIPTION
           "PPPOE filtered frames threshold."
       ::= { hwGponDeviceAlarmProfileEntry 20 }

   hwGponDeviceDelayExceededDiscardThreshold OBJECT-TYPE
       SYNTAX     Integer32
       MAX-ACCESS read-write
       STATUS  current
       DESCRIPTION
           "MAC bridge port discarded frames due to delay threshold."
       ::= { hwGponDeviceAlarmProfileEntry 21 }

   hwGponDeviceMTUExceededDiscardThreshold OBJECT-TYPE
       SYNTAX     Integer32
       MAX-ACCESS read-write
       STATUS  current
       DESCRIPTION
           "MAC bridge port MTU exceeded discard frames threshold."
       ::= { hwGponDeviceAlarmProfileEntry 22 }

   hwGponDeviceReceivedAndDiscardedThreshold OBJECT-TYPE
       SYNTAX     Integer32
       MAX-ACCESS read-write
       STATUS  current
       DESCRIPTION
           "MAC bridge port received incorrect frames threshold."
       ::= { hwGponDeviceAlarmProfileEntry 23 }

   hwGponDeviceCESErrorSecondsThreshold OBJECT-TYPE
       SYNTAX     Integer32
       MAX-ACCESS    read-write
       STATUS      current
       DESCRIPTION
           "CES error time threshold."
       ::= { hwGponDeviceAlarmProfileEntry 26 }

   hwGponDeviceCESSeverelyErrorSecondsThreshold OBJECT-TYPE
       SYNTAX     Integer32
       MAX-ACCESS    read-write
       STATUS      current
       DESCRIPTION
           "CES severely time threshold."
       ::= { hwGponDeviceAlarmProfileEntry 27 }

    hwGponDeviceCESBurstyErrorSecondsThreshold OBJECT-TYPE
       SYNTAX     Integer32
       MAX-ACCESS    read-write
       STATUS      current
       DESCRIPTION
           "CES burst time threshold."
       ::= { hwGponDeviceAlarmProfileEntry 28 }

     hwGponDeviceCESUnavailableSecondsThreshold OBJECT-TYPE
       SYNTAX     Integer32
       MAX-ACCESS    read-write
       STATUS      current
       DESCRIPTION
           "CES unavailable time threshold."
       ::= { hwGponDeviceAlarmProfileEntry 29 }

      hwGponDeviceCESControlledSlipSecondsThreshold OBJECT-TYPE
       SYNTAX     Integer32
       MAX-ACCESS    read-write
       STATUS      current
       DESCRIPTION
           "CES controlled slip time threshold."
       ::= { hwGponDeviceAlarmProfileEntry 30 }

   hwGponDeviceDropEventsThreshold OBJECT-TYPE
       SYNTAX     Integer32
       MAX-ACCESS    read-write
       STATUS      current
       DESCRIPTION
           "Drop events threshold."
       ::= { hwGponDeviceAlarmProfileEntry 31 }

   hwGponDeviceUndersizepacketsThreshold OBJECT-TYPE
       SYNTAX     Integer32
       MAX-ACCESS    read-write
       STATUS      current
       DESCRIPTION
           "Undersize frames threshold."
       ::= { hwGponDeviceAlarmProfileEntry 32 }

   hwGponDeviceFragmentsThreshold OBJECT-TYPE
       SYNTAX     Integer32
       MAX-ACCESS    read-write
       STATUS      current
       DESCRIPTION
           "Fragments threshold."
       ::= { hwGponDeviceAlarmProfileEntry 33 }

   hwGponDeviceJabbersThreshold OBJECT-TYPE
       SYNTAX     Integer32
       MAX-ACCESS    read-write
       STATUS      current
       DESCRIPTION
           "Jabbers threshold."
       ::= { hwGponDeviceAlarmProfileEntry 34 }

  hwGponDeviceFailedSignalOfOnuThreshold OBJECT-TYPE
       SYNTAX     Integer32
       MAX-ACCESS    read-write
       STATUS      current
       DESCRIPTION
               "Failed signal of ONU threshold(Format:1e-x),range:3~8,
                for example: if the value of the leaf is 3,the actual value is 0.001,
                if the value of the leaf is 8,the actual value is 0.00000001.
               "
       ::= { hwGponDeviceAlarmProfileEntry 35 }

  hwGponDeviceDegradedSignalOfOnuThreshold OBJECT-TYPE
       SYNTAX     Integer32
       MAX-ACCESS    read-write
       STATUS      current
       DESCRIPTION
               "Degraded signal of ONU threshold(Format:1e-x),range:4~9,
                for example: if the value of the leaf is 4,the actual value is 0.0001,
                if the value of the leaf is 9,the actual value is 0.000000001."
       ::= { hwGponDeviceAlarmProfileEntry 36 }

  hwGponDeviceFECUncorrectCodeWordsThreshold OBJECT-TYPE
       SYNTAX     Gauge32 (0..1101600000 | 4294967295)
       MAX-ACCESS    read-write
       STATUS      current
       DESCRIPTION
               "FEC uncorrectable code words threshold, range:0~1101600000. 4294967295 is invalid value"
       ::= { hwGponDeviceAlarmProfileEntry 37 }

  hwGponDeviceFECCorrectCodeWordsThreshold OBJECT-TYPE
       SYNTAX     Gauge32 (0..1101600000 | 4294967295)
       MAX-ACCESS    read-write
       STATUS      current
       DESCRIPTION
               "FEC correctable code words threshold, range:0~1101600000. 4294967295 is invalid value"
       ::= { hwGponDeviceAlarmProfileEntry 38 }

   hwGponDeviceUpstreamPQDiscardedBytesThreshold OBJECT-TYPE
       SYNTAX     Integer32
       MAX-ACCESS    read-write
       STATUS      current
       DESCRIPTION
           "Upstream PQ discarded byte alarm threshold, range:0~65535. If this parameter is set to an invalid value 0, the PQ alarm statistics function is disabled."
       ::= { hwGponDeviceAlarmProfileEntry 39 }

   hwGponDeviceDownstreamPQDiscardedBytesThreshold OBJECT-TYPE
       SYNTAX     Integer32
       MAX-ACCESS    read-write
       STATUS      current
       DESCRIPTION
           "Downstream PQ discarded byte alarm threshold, range:0~65535. If this parameter is set to an invalid value 0, the PQ alarm statistics function is disabled."
       ::= { hwGponDeviceAlarmProfileEntry 40 }

   hwGponDeviceAlarmThresholdRowStatus OBJECT-TYPE
       SYNTAX     RowStatus
       MAX-ACCESS    read-create
       STATUS      current
       DESCRIPTION
           "Row status. This object is used to differentiate the
            creation, modification and deletion operations for an object.
            Options:
            1. createAndGo(4) -create a new instance of a conceptual row
            2. destroy(6)     -delete the instances associated with an existing conceptual row
           "
       ::= { hwGponDeviceAlarmProfileEntry 50 }

   hwGponDeviceEncryptionKeyErrorsOfOnuThreshold OBJECT-TYPE
       SYNTAX     Integer32
       MAX-ACCESS    read-write
       STATUS      current
       DESCRIPTION
           "Encryption key errors Of Onu Threshold, range:0~100.
           "
       ::= { hwGponDeviceAlarmProfileEntry 51 }

   hwGponDeviceXgemKeyErrorsOfOnuThreshold OBJECT-TYPE
       SYNTAX     Integer32
       MAX-ACCESS    read-write
       STATUS      current
       DESCRIPTION
           "XGEM key errors Of Onu Threshold, range:0~100.
           "
       ::= { hwGponDeviceAlarmProfileEntry 52 }

   hwGponDeviceXgemHecErrorCountOfOnuThreshold OBJECT-TYPE
       SYNTAX     Integer32
       MAX-ACCESS    read-write
       STATUS      current
       DESCRIPTION
           "XGEM HEC error count Of Onu Threshold, range:0~100.
           "
       ::= { hwGponDeviceAlarmProfileEntry 53 }


   -- Table20 HwGponOntTrafficFlowStatsTable
   hwGponOntTrafficFlowStatsTable OBJECT-TYPE
       SYNTAX  SEQUENCE OF HwGponOntTrafficFlowStatsEntry
       MAX-ACCESS not-accessible
       STATUS current
       DESCRIPTION
           "The ONT traffic stream statistics table,
            Used for checking the number of LOFI alarms and number of upstream and downstream BIP errors on the ONT connected to a port.
            The indexes of this table are ifIndex and hwGponDeviceOntObjectIndex.
       "
       ::= { hwGponDeviceStatObjects 7 }

   hwGponOntTrafficFlowStatsEntry OBJECT-TYPE
       SYNTAX HwGponOntTrafficFlowStatsEntry
       MAX-ACCESS not-accessible
       STATUS current
       DESCRIPTION
           "The ONT traffic stream statistics table,
            Used for checking the number of LOFI alarms and number of upstream and downstream BIP errors on the ONT connected to a port.
            The indexes of this entry are ifIndex and hwGponDeviceOntObjectIndex.
       "
       INDEX { ifIndex, hwGponDeviceOntObjectIndex }
       ::= { hwGponOntTrafficFlowStatsTable 1 }

   HwGponOntTrafficFlowStatsEntry ::=
       SEQUENCE {
                    hwGponOntLofiAlarmStatsCnt                        Counter32,
                    hwGponOntUpFramesScapeErrCnt                      Counter32,
                    hwGponOntUpFrameBipErrCnt                         Counter32,
                    hwGponOntDnFramesBipErrCnt                        Counter32,
                    hwGponOntTrafficFlowStatsUpFecDecodCorrectCnt     Counter32,
                    hwGponOntTrafficFlowStatsUpFecDecodUnCorrectCnt   Counter32,
                    hwGponOntTrafficFlowStatsUpHecCheckErrCnt         Counter32,
                    hwGponOntTrafficFlowStatsDowiAlarmCnt             Counter32,
                    hwGponOntTrafficFlowStatsUpFecCodeDecodCorrectCnt Counter64,
                    hwGponOntTrafficFlowStatsUpFecCodeCnt             Counter64,
                    hwGponOntTrafficFlowStatsUpFcsErrorCnt            Counter64,
                    hwGponOntTrafficFlowStatsUpFrameBitErrorRatio     Counter64,
                    hwGponOntTrafficFlowStatsUpEthFrameErrorRatio     Counter64,
                    hwGponOntTrafficFlowStatsUpGemFrameErrorRatio     Counter64,
                    hwGponOntTrafficFlowStatsClear                    INTEGER
                }

   hwGponOntLofiAlarmStatsCnt OBJECT-TYPE
       SYNTAX Counter32
       MAX-ACCESS read-only
       STATUS current
       DESCRIPTION
           "The count of ONU loss of frame alarm."
       ::= { hwGponOntTrafficFlowStatsEntry 1 }

   hwGponOntUpFramesScapeErrCnt OBJECT-TYPE
       SYNTAX Counter32
       MAX-ACCESS read-only
       STATUS current
       DESCRIPTION
           "The count of ONU upstream frame scape error."
       ::= { hwGponOntTrafficFlowStatsEntry 2 }

   hwGponOntUpFrameBipErrCnt OBJECT-TYPE
       SYNTAX Counter32
       MAX-ACCESS read-only
       STATUS current
       DESCRIPTION
           "The count of ONU upstream frame BIP error."
       ::= { hwGponOntTrafficFlowStatsEntry 3 }

   hwGponOntDnFramesBipErrCnt OBJECT-TYPE
       SYNTAX Counter32
       MAX-ACCESS read-only
       STATUS current
       DESCRIPTION
           "The count of ONU downstream frame BIP error."
       ::= { hwGponOntTrafficFlowStatsEntry 4 }

   hwGponOntTrafficFlowStatsUpFecDecodCorrectCnt OBJECT-TYPE
       SYNTAX Counter32
       MAX-ACCESS read-only
       STATUS current
       DESCRIPTION
           "This object indicates the number of upstream FEC decoding corrected blocks."
       ::= { hwGponOntTrafficFlowStatsEntry 5 }

   hwGponOntTrafficFlowStatsUpFecDecodUnCorrectCnt OBJECT-TYPE
       SYNTAX Counter32
       MAX-ACCESS read-only
       STATUS current
       DESCRIPTION
           "This object indicates the number of upstream FEC decoding uncorrected blocks."
       ::= { hwGponOntTrafficFlowStatsEntry 6 }

   hwGponOntTrafficFlowStatsUpHecCheckErrCnt OBJECT-TYPE
       SYNTAX Counter32
       MAX-ACCESS read-only
       STATUS current
       DESCRIPTION
           "This object indicates the number of upstream HEC errors."
       ::= { hwGponOntTrafficFlowStatsEntry 7 }

   hwGponOntTrafficFlowStatsDowiAlarmCnt OBJECT-TYPE
       SYNTAX Counter32
       MAX-ACCESS read-only
       STATUS current
       DESCRIPTION
           "The count of ONU DOWi(Drift of Window) Alarm."
       ::= { hwGponOntTrafficFlowStatsEntry 8 }

   hwGponOntTrafficFlowStatsUpFecCodeDecodCorrectCnt OBJECT-TYPE
       SYNTAX Counter64
       MAX-ACCESS read-only
       STATUS current
       DESCRIPTION
           "This object indicates the number of upstream FEC code decoding corrected blocks."
       ::= { hwGponOntTrafficFlowStatsEntry 9 }

   hwGponOntTrafficFlowStatsUpFecCodeCnt OBJECT-TYPE
       SYNTAX Counter64
       MAX-ACCESS read-only
       STATUS current
       DESCRIPTION
           "This object indicates the number of upstream FEC code blocks."
       ::= { hwGponOntTrafficFlowStatsEntry 10 }

        hwGponOntTrafficFlowStatsUpFcsErrorCnt OBJECT-TYPE
       SYNTAX Counter64
       MAX-ACCESS read-only
       STATUS current
       DESCRIPTION
            "This object indicates the number of upstream FCS code errors in current 15 minutes.
             The value (-1) indicates that the query fails or no information is detected."
       ::= { hwGponOntTrafficFlowStatsEntry 11 }

    hwGponOntTrafficFlowStatsUpFrameBitErrorRatio OBJECT-TYPE
       SYNTAX Counter64
       MAX-ACCESS read-only
       STATUS current
       DESCRIPTION
            "This object indicates upstream frame bit error ratio in current 15 minutes.
             The value of this object indicates the absolute value of the exponente of the upstream frame bit error ratio with scientific notation.
             For example, if the upstream frame bit error ratio is calculated to be (0.0012), the scientific notation is 1.2E-3.
             The multiplicando (1.2) is ignored, and the value of this object is (3).
             The value (-1) indicates that the query fails or no information is detected.
             The value (0xFFFFFFE) indicates that the bit error ratio is (0).
             The value (0) indicates that the bit error ratio is (1)."
       ::= { hwGponOntTrafficFlowStatsEntry 12 }

    hwGponOntTrafficFlowStatsUpEthFrameErrorRatio OBJECT-TYPE
       SYNTAX Counter64
       MAX-ACCESS read-only
       STATUS current
       DESCRIPTION
             "This object indicates upstream ETH frame error ratio in current 15 minutes.
              The value of this object indicates the absolute value of the exponente of the upstream ETH frame error ratio with scientific notation.
              For example, if the upstream ETH frame bit error ratio is calculated to be (0.0012), the scientific notation is 1.2E-3.
              The multiplicando (1.2) is ignored, and the value of this object is (3).
              The value (-1) indicates that the query fails or no information is detected.
              The value (0xFFFFFFE) indicates that the bit error ratio is (0).
              The value (0) indicates that the bit error ratio is (1)."
       ::= { hwGponOntTrafficFlowStatsEntry 13 }

    hwGponOntTrafficFlowStatsUpGemFrameErrorRatio OBJECT-TYPE
       SYNTAX Counter64
       MAX-ACCESS read-only
       STATUS current
       DESCRIPTION
              "This object indicates upstream GEM frame error ratio in current 15 minutes.
               The value of this object indicates the absolute value of the exponente of the upstream GEM frame error ratio with scientific notation.
               For example, if the upstream GEM frame bit error ratio is calculated to be (0.0012), the scientific notation is 1.2E-3.
               The multiplicando (1.2) is ignored, and the value of this object is (3).
               The value (-1) indicates that the query fails or no information is detected.
               The value (0xFFFFFFE) indicates that the bit error ratio is (0).
               The value (0) indicates that the bit error ratio is (1)."
       ::= { hwGponOntTrafficFlowStatsEntry 14 }

   hwGponOntTrafficFlowStatsClear OBJECT-TYPE
       SYNTAX INTEGER{
           clear(1),
           invalid(-1)
       }
       MAX-ACCESS read-write
       STATUS current
       DESCRIPTION
           "This object is used to clear the statistics.
            Options:
            1. clear(1)                    - Indicates that clear the statistics
            2. invalid(-1)                 - Indicates that the query fails or no information is detected
           "
       ::= { hwGponOntTrafficFlowStatsEntry 20 }


   -- Table21 HwGponOntEtherStatsTable
   hwGponOntEtherStatsTable OBJECT-TYPE
       SYNTAX  SEQUENCE OF HwGponOntEtherStatsEntry
       MAX-ACCESS not-accessible
       STATUS current
       DESCRIPTION
           "ONT ETH port statistics table, used for querying and clearing the information about the ETH port.
            The indexes of this table are ifIndex,
            hwGponDeviceOntObjectIndex, hwGponOntifEthernetType and hwGponOntifEthernetPort.
           "
       ::= { hwGponDeviceStatObjects 6 }

   hwGponOntEtherStatsEntry OBJECT-TYPE
       SYNTAX HwGponOntEtherStatsEntry
       MAX-ACCESS not-accessible
       STATUS current
       DESCRIPTION
           "ONT ETH port statistics table, used for querying and clearing the information about the ETH port.
            The indexes of this entry are ifIndex,
            hwGponDeviceOntObjectIndex, hwGponOntifEthernetType and hwGponOntifEthernetPort.
           "
       INDEX { ifIndex, hwGponDeviceOntObjectIndex, hwGponOntifEthernetType, hwGponOntifEthernetPort }
       ::= { hwGponOntEtherStatsTable 1 }

   HwGponOntEtherStatsEntry ::=
       SEQUENCE {
        hwGponOntEtherStatsDataSource                OBJECT IDENTIFIER,
        hwGponOntEtherStatsDropEvents                Counter64,
        hwGponOntEtherStatsOctets                    Counter64,
        hwGponOntEtherStatsPkts                      Counter64,
        hwGponOntEtherStatsBroadcastPkts             Counter64,
        hwGponOntEtherStatsMulticastPkts             Counter64,
        hwGponOntEtherStatsCRCAlignErrors            Counter64,
        hwGponOntEtherStatsUndersizePkts             Counter64,
        hwGponOntEtherStatsOversizePkts              Counter64,
        hwGponOntEtherStatsFragments                 Counter64,
        hwGponOntEtherStatsJabbers                   Counter64,
        hwGponOntEtherStatsCollisions                Counter64,
        hwGponOntEtherStatsPkts64Octets              Counter64,
        hwGponOntEtherStatsPkts65to127Octets         Counter64,
        hwGponOntEtherStatsPkts128to255Octets        Counter64,
        hwGponOntEtherStatsPkts256to511Octets        Counter64,
        hwGponOntEtherStatsPkts512to1023Octets       Counter64,
        hwGponOntEtherStatsPkts1024to1518Octets      Counter64,
        hwGponOntFCSErrors                           Counter64,
        hwGponOntExcessiveCollisionCounter           Counter64,
        hwGponOntLateCollisionCounter                Counter64,
        hwGponOntFrameTooLongs                       Counter64,
        hwGponOntBufferOverflowsonReceive            Counter64,
        hwGponOntBufferOverflowsonTransmit           Counter64,
        hwGponOntSingleCollisionFrameCounter         Counter64,
        hwGponOntMultipleCollisionsFrameCounter      Counter64,
        hwGponOntSQECounter                          Counter64,
        hwGponOntDeferredTransmissionCounter         Counter64,
        hwGponOntInternalmacTransmitErrorcounter     Counter64,
        hwGponOntCarrierSenseErrorCounter            Counter64,
        hwGponOntAlignmentErrorCounter               Counter64,
        hwGponOntInternalMACReceiveErrorCounter      Counter64,
        hwGponOntPPPoEFilteredFrameCounter           Counter64,
        hwGponOntForwardedFrameCounter               Counter64,
        hwGponOntDelayExceededDiscardCounter         Counter64,
        hwGponOntEtherStatsReceiveUnicastPkts        Counter64,
        hwGponOntEtherStatsSendUnicastPkts           Counter64,
        hwGponOntEtherStatsSendBroadcastPkts         Counter64,
        hwGponOntEtherStatsSendMulticastPkts         Counter64,
        hwGponOntEtherStatsReceivePauseFlowCtrlFrame Counter64,
        hwGponOntEtherStatsSendPauseFlowCtrlFrame    Counter64,
        hwGponOntEtherStatsReceiveGoodPktsOctets       Counter64,
        hwGponOntEtherStatsSendGoodPktsOctets          Counter64,
        hwGponOntEtherStatsReceiveBadPktsOctets        Counter64,
        hwGponOntEtherStatsSendBadPktsOctets           Counter64,
        hwGponOntEtherStatsClear                       Integer32,
        hwGponOntEtherStatsSendOctets                  Counter64,
        hwGponOntEtherStatsForwardDropEvents           Counter64,
        hwGponOntEtherStatsSendPkts64Octets            Counter64,
        hwGponOntEtherStatsSendPkts65to127Octets       Counter64,
        hwGponOntEtherStatsSendPkts128to255Octets      Counter64,
        hwGponOntEtherStatsSendPkts256to511Octets      Counter64,
        hwGponOntEtherStatsSendPkts512to1023Octets    Counter64,
        hwGponOntEtherStatsSendPkts1024to1518Octets   Counter64,
        hwGponOntEtherStatsSendPktsOversize           Counter64,
        hwGponOntEtherStatsPkts1519toOversizeOctets   Counter64,
        hwGponOntEtherStatsStateChangeTimes           Integer32,
        hwGponOntEtherStatsDuration                   Gauge32
       }

    hwGponOntEtherStatsDataSource OBJECT-TYPE
       SYNTAX OBJECT IDENTIFIER
       MAX-ACCESS read-only
       STATUS current
       DESCRIPTION
           "ONT ETH statistics data source."
       ::= { hwGponOntEtherStatsEntry 1 }

   hwGponOntEtherStatsDropEvents OBJECT-TYPE
       SYNTAX Counter64
       UNITS "frames"
       MAX-ACCESS read-only
       STATUS current
       DESCRIPTION
           "Received and discarded frames count.
            Unit: frames
           "
       ::= { hwGponOntEtherStatsEntry 2 }

   hwGponOntEtherStatsOctets OBJECT-TYPE
       SYNTAX Counter64
       UNITS "frames"
       MAX-ACCESS read-only
       STATUS current
       DESCRIPTION
           "Received bytes.
            Unit: frames
           "
       ::= { hwGponOntEtherStatsEntry 3 }

   hwGponOntEtherStatsPkts OBJECT-TYPE
       SYNTAX Counter64
       UNITS "frames"
       MAX-ACCESS read-only
       STATUS current
       DESCRIPTION
           "Received frames.
            Unit: frames
           "
       ::= { hwGponOntEtherStatsEntry 4 }

   hwGponOntEtherStatsBroadcastPkts OBJECT-TYPE
       SYNTAX Counter64
       UNITS "frames"
       MAX-ACCESS read-only
       STATUS current
       DESCRIPTION
           "Received broadcast frames.
            Unit: frames
           "
       ::= { hwGponOntEtherStatsEntry 5 }

   hwGponOntEtherStatsMulticastPkts OBJECT-TYPE
       SYNTAX Counter64
       UNITS "frames"
       MAX-ACCESS read-only
       STATUS current
       DESCRIPTION
           "Received multicast frames.
            Unit: frames
           "
       ::= { hwGponOntEtherStatsEntry 6 }

   hwGponOntEtherStatsCRCAlignErrors OBJECT-TYPE
       SYNTAX Counter64
       UNITS "frames"
       MAX-ACCESS read-only
       STATUS current
       DESCRIPTION
           "Received CRC error frames.
            Unit: frames
           "
       ::= { hwGponOntEtherStatsEntry 7 }

   hwGponOntEtherStatsUndersizePkts OBJECT-TYPE
       SYNTAX Counter64
       UNITS "frames"
       MAX-ACCESS read-only
       STATUS current
       DESCRIPTION
           "Received undersize frames.
            Unit: frames
           "
       ::= { hwGponOntEtherStatsEntry 8 }

   hwGponOntEtherStatsOversizePkts OBJECT-TYPE
       SYNTAX Counter64
       UNITS "frames"
       MAX-ACCESS read-only
       STATUS current
       DESCRIPTION
           "Send MTU exceeded discard frames.
            Unit: frames
           "
       ::= { hwGponOntEtherStatsEntry 9 }

   hwGponOntEtherStatsFragments OBJECT-TYPE
       SYNTAX Counter64
       UNITS "frames"
       MAX-ACCESS read-only
       STATUS current
       DESCRIPTION
           "Received fragments.
            Unit: frames
           "
       ::= { hwGponOntEtherStatsEntry 10 }


   hwGponOntEtherStatsJabbers OBJECT-TYPE
       SYNTAX Counter64
       UNITS "frames"
       MAX-ACCESS read-only
       STATUS current
       DESCRIPTION
           "Received Jabber error frames.
            Unit: frames
           "
       ::= { hwGponOntEtherStatsEntry 11 }

   hwGponOntEtherStatsCollisions OBJECT-TYPE
       SYNTAX Counter64
       UNITS "frames"
       MAX-ACCESS read-only
       STATUS current
       DESCRIPTION
           "Count of collisions.
            Unit: frames
           "
       ::= { hwGponOntEtherStatsEntry 12 }

   hwGponOntEtherStatsPkts64Octets OBJECT-TYPE
       SYNTAX Counter64
       UNITS "frames"
       MAX-ACCESS read-only
       STATUS current
       DESCRIPTION
           "Received 64-octet frames.
            Unit: frames
           "
       ::= { hwGponOntEtherStatsEntry 13 }

   hwGponOntEtherStatsPkts65to127Octets OBJECT-TYPE
       SYNTAX Counter64
       UNITS "frames"
       MAX-ACCESS read-only
       STATUS current
       DESCRIPTION
           "Received 65~127-octet frames.
            Unit: frames
           "
       ::= { hwGponOntEtherStatsEntry 14 }

   hwGponOntEtherStatsPkts128to255Octets OBJECT-TYPE
       SYNTAX Counter64
       UNITS "frames"
       MAX-ACCESS read-only
       STATUS current
       DESCRIPTION
           "Received 128~255-octet frames.
            Unit: frames
           "
       ::= { hwGponOntEtherStatsEntry 15 }

   hwGponOntEtherStatsPkts256to511Octets OBJECT-TYPE
       SYNTAX Counter64
       UNITS "frames"
       MAX-ACCESS read-only
       STATUS current
       DESCRIPTION
           "Received 256~511-octet frames.
            Unit: frames
           "
       ::= { hwGponOntEtherStatsEntry 16 }

   hwGponOntEtherStatsPkts512to1023Octets OBJECT-TYPE
       SYNTAX Counter64
       UNITS "frames"
       MAX-ACCESS read-only
       STATUS current
       DESCRIPTION
           "Received 512~1023-octet frames.
            Unit: frames
           "
       ::= { hwGponOntEtherStatsEntry 17 }

   hwGponOntEtherStatsPkts1024to1518Octets OBJECT-TYPE
       SYNTAX Counter64
       UNITS "frames"
       MAX-ACCESS read-only
       STATUS current
       DESCRIPTION
           "Received 1024~1518-octet frames.
            Unit: frames
           "
       ::= { hwGponOntEtherStatsEntry 18 }

   hwGponOntFCSErrors  OBJECT-TYPE
       SYNTAX Counter64
       UNITS "frames"
       MAX-ACCESS read-only
       STATUS current
       DESCRIPTION
           "Received FCS error frames.
            Unit: frames
           "
       ::= { hwGponOntEtherStatsEntry 19 }

   hwGponOntExcessiveCollisionCounter  OBJECT-TYPE
       SYNTAX Counter64
       UNITS "frames"
       MAX-ACCESS read-only
       STATUS current
       DESCRIPTION
           "Sent excessive collision frames.
            Unit: frames
           "
       ::= { hwGponOntEtherStatsEntry 20 }

   hwGponOntLateCollisionCounter  OBJECT-TYPE
       SYNTAX Counter64
       UNITS "frames"
       MAX-ACCESS read-only
       STATUS current
       DESCRIPTION
           "Number of collisions occurring later than 512 bit-times.
            Unit: frames
           "
       ::= { hwGponOntEtherStatsEntry 21 }

   hwGponOntFrameTooLongs  OBJECT-TYPE
       SYNTAX Counter64
       UNITS "frames"
       MAX-ACCESS read-only
       STATUS current
       DESCRIPTION
           "Received oversize frames.
            Unit: frames
           "
       ::= { hwGponOntEtherStatsEntry 22 }

   hwGponOntBufferOverflowsonReceive  OBJECT-TYPE
       SYNTAX Counter64
       UNITS "frames"
       MAX-ACCESS read-only
       STATUS current
       DESCRIPTION
           "Number of receive buffer overflows.
            Unit: frames
           "
       ::= { hwGponOntEtherStatsEntry 23 }

   hwGponOntBufferOverflowsonTransmit  OBJECT-TYPE
       SYNTAX Counter64
       UNITS "frames"
       MAX-ACCESS read-only
       STATUS current
       DESCRIPTION
           "Number of send buffer overflows.
            Unit: frames
           "
       ::= { hwGponOntEtherStatsEntry 24 }

   hwGponOntSingleCollisionFrameCounter  OBJECT-TYPE
       SYNTAX Counter64
       UNITS "frames"
       MAX-ACCESS read-only
       STATUS current
       DESCRIPTION
           "Number of deferred sent frames due to single collision.
            Unit: frames
           "
       ::= { hwGponOntEtherStatsEntry 25 }

    hwGponOntMultipleCollisionsFrameCounter  OBJECT-TYPE
        SYNTAX Counter64
        UNITS "frames"
        MAX-ACCESS read-only
        STATUS current
        DESCRIPTION
            "Number of deferred sent frames due to multiple collisions.
             Unit: frames
            "
        ::= { hwGponOntEtherStatsEntry 26 }

    hwGponOntSQECounter  OBJECT-TYPE
        SYNTAX Counter64
        UNITS "frames"
        MAX-ACCESS read-only
        STATUS current
        DESCRIPTION
            "Number of SQE test error messages.
             Unit: frames
            "
        ::= { hwGponOntEtherStatsEntry 27 }

    hwGponOntDeferredTransmissionCounter  OBJECT-TYPE
        SYNTAX Counter64
        UNITS "frames"
        MAX-ACCESS read-only
        STATUS current
        DESCRIPTION
            "Sent deferred frames.
             Unit: frames
            "
        ::= { hwGponOntEtherStatsEntry 28 }

    hwGponOntInternalmacTransmitErrorcounter  OBJECT-TYPE
        SYNTAX Counter64
        UNITS "frames"
        MAX-ACCESS read-only
        STATUS current
        DESCRIPTION
            "Sent error frames at the MAC sublayer.
             Unit: frames
            "
        ::= { hwGponOntEtherStatsEntry 29 }

    hwGponOntCarrierSenseErrorCounter  OBJECT-TYPE
        SYNTAX Counter64
        UNITS "frames"
        MAX-ACCESS read-only
        STATUS current
        DESCRIPTION
            "Number of frame loss errors during carrier sense.
             Unit: frames
            "
        ::= { hwGponOntEtherStatsEntry 30 }

    hwGponOntAlignmentErrorCounter  OBJECT-TYPE
        SYNTAX Counter64
        UNITS "frames"
        MAX-ACCESS read-only
        STATUS current
        DESCRIPTION
            "Received alignment error frames.
             Unit: frames
            "
        ::= { hwGponOntEtherStatsEntry 31 }

    hwGponOntInternalMACReceiveErrorCounter  OBJECT-TYPE
        SYNTAX Counter64
        UNITS "frames"
        MAX-ACCESS read-only
        STATUS current
        DESCRIPTION
            "Received error frames at the MAC sublayer.
             Unit: frames
            "
        ::= { hwGponOntEtherStatsEntry 32 }

    hwGponOntPPPoEFilteredFrameCounter  OBJECT-TYPE
        SYNTAX Counter64
        UNITS "frames"
        MAX-ACCESS read-only
        STATUS current
        DESCRIPTION
            "Received PPPoE filtered frames.
             Unit: frames
            "
        ::= { hwGponOntEtherStatsEntry 33 }

    hwGponOntForwardedFrameCounter  OBJECT-TYPE
        SYNTAX Counter64
        UNITS "frames"
        MAX-ACCESS read-only
        STATUS current
        DESCRIPTION
            "Number of sent frames.
             Unit: frames
            "
        ::= { hwGponOntEtherStatsEntry 34 }

    hwGponOntDelayExceededDiscardCounter  OBJECT-TYPE
        SYNTAX Counter64
        UNITS "frames"
        MAX-ACCESS read-only
        STATUS current
        DESCRIPTION
            "Discarded frames due to delay.
             Unit: frames
            "
        ::= { hwGponOntEtherStatsEntry 35 }

    hwGponOntEtherStatsReceiveUnicastPkts  OBJECT-TYPE
        SYNTAX Counter64
        UNITS "frames"
        MAX-ACCESS read-only
        STATUS current
        DESCRIPTION
            "Number of received unicast frames.
             Unit: frames
            "
        ::= { hwGponOntEtherStatsEntry 36 }

    hwGponOntEtherStatsSendUnicastPkts  OBJECT-TYPE
        SYNTAX Counter64
        UNITS "frames"
        MAX-ACCESS read-only
        STATUS current
        DESCRIPTION
            "Number of sent unicast frames.
             Unit: frames
            "
        ::= { hwGponOntEtherStatsEntry 37 }

    hwGponOntEtherStatsSendBroadcastPkts  OBJECT-TYPE
        SYNTAX Counter64
        UNITS "frames"
        MAX-ACCESS read-only
        STATUS current
        DESCRIPTION
            "Sent broadcast frames.
             Unit: frames
            "
        ::= { hwGponOntEtherStatsEntry 38 }

    hwGponOntEtherStatsSendMulticastPkts  OBJECT-TYPE
        SYNTAX Counter64
        UNITS "frames"
        MAX-ACCESS read-only
        STATUS current
        DESCRIPTION
            "Sent multicast frames.
             Unit: frames
            "
        ::= { hwGponOntEtherStatsEntry 39 }

    hwGponOntEtherStatsReceivePauseFlowCtrlFrame  OBJECT-TYPE
        SYNTAX Counter64
        UNITS "frames"
        MAX-ACCESS read-only
        STATUS current
        DESCRIPTION
            "Received pause flow control frames.
             Unit: frames
            "
        ::= { hwGponOntEtherStatsEntry 40 }

    hwGponOntEtherStatsSendPauseFlowCtrlFrame  OBJECT-TYPE
        SYNTAX Counter64
        UNITS "frames"
        MAX-ACCESS read-only
        STATUS current
        DESCRIPTION
            "Sent pause flow control frames.
             Unit: frames
            "
        ::= { hwGponOntEtherStatsEntry 41 }

    hwGponOntEtherStatsReceiveGoodPktsOctets  OBJECT-TYPE
        SYNTAX Counter64
        UNITS "frames"
        MAX-ACCESS read-only
        STATUS current
        DESCRIPTION
            "Received good frames octets.
             Unit: frames
            "
        ::= { hwGponOntEtherStatsEntry 42 }

    hwGponOntEtherStatsSendGoodPktsOctets  OBJECT-TYPE
        SYNTAX Counter64
        UNITS "frames"
        MAX-ACCESS read-only
        STATUS current
        DESCRIPTION
            "Sent good frames octets.
             Unit: frames
            "
        ::= { hwGponOntEtherStatsEntry 43 }

    hwGponOntEtherStatsReceiveBadPktsOctets  OBJECT-TYPE
        SYNTAX Counter64
        UNITS "frames"
        MAX-ACCESS read-only
        STATUS current
        DESCRIPTION
            "Received error frames octets.
             Unit: frames
            "
        ::= { hwGponOntEtherStatsEntry 44 }

    hwGponOntEtherStatsSendBadPktsOctets  OBJECT-TYPE
        SYNTAX Counter64
        UNITS "frames"
        MAX-ACCESS read-only
        STATUS current
        DESCRIPTION
            "Sent error frames octets.
             Unit: frames
            "
        ::= { hwGponOntEtherStatsEntry 45 }

      hwGponOntEtherStatsClear  OBJECT-TYPE
        SYNTAX Integer32
        MAX-ACCESS read-write
        STATUS current
        DESCRIPTION
            "Clear the statistics."
        ::= { hwGponOntEtherStatsEntry 46 }

      hwGponOntEtherStatsSendOctets   OBJECT-TYPE
            SYNTAX Counter64
            MAX-ACCESS read-only
            STATUS current
            DESCRIPTION
                "This object indicates the sent octets"
            ::= { hwGponOntEtherStatsEntry 47 }

        hwGponOntEtherStatsForwardDropEvents OBJECT-TYPE
            SYNTAX Counter64
            MAX-ACCESS read-only
            STATUS current
            DESCRIPTION
                "This object indicates the sent drop events"
            ::= { hwGponOntEtherStatsEntry 48 }


        hwGponOntEtherStatsSendPkts64Octets OBJECT-TYPE
            SYNTAX Counter64
            MAX-ACCESS read-only
            STATUS current
            DESCRIPTION
                "This object indicates the sent 64-octet frames"
            ::= { hwGponOntEtherStatsEntry 49 }

        hwGponOntEtherStatsSendPkts65to127Octets OBJECT-TYPE
            SYNTAX Counter64
            MAX-ACCESS read-only
            STATUS current
            DESCRIPTION
                "This object indicates the sent 65~127-octet frames"
            ::= { hwGponOntEtherStatsEntry 50 }

        hwGponOntEtherStatsSendPkts128to255Octets OBJECT-TYPE
            SYNTAX Counter64
            MAX-ACCESS read-only
            STATUS current
            DESCRIPTION
                "This object indicates the sent 128~255-octet frames"
            ::= { hwGponOntEtherStatsEntry 51 }

        hwGponOntEtherStatsSendPkts256to511Octets OBJECT-TYPE
            SYNTAX Counter64
            MAX-ACCESS read-only
            STATUS current
            DESCRIPTION
                "This object indicates the sent 256~511-octet frames."
            ::= { hwGponOntEtherStatsEntry 52 }

        hwGponOntEtherStatsSendPkts512to1023Octets OBJECT-TYPE
            SYNTAX Counter64
            MAX-ACCESS read-only
            STATUS current
            DESCRIPTION
                "This object indicates the sent 512~1023-octet frames."
            ::= { hwGponOntEtherStatsEntry 53}

         hwGponOntEtherStatsSendPkts1024to1518Octets OBJECT-TYPE
            SYNTAX Counter64
            MAX-ACCESS read-only
            STATUS current
            DESCRIPTION
                "This object indicates the sent 1024~1518-octet frames."
            ::= { hwGponOntEtherStatsEntry 54 }

        hwGponOntEtherStatsSendPktsOversize  OBJECT-TYPE
            SYNTAX Counter64
            MAX-ACCESS read-only
            STATUS current
            DESCRIPTION
                "This object indicates the sent oversize frames."
            ::= { hwGponOntEtherStatsEntry 55 }

       hwGponOntEtherStatsPkts1519toOversizeOctets  OBJECT-TYPE
            SYNTAX Counter64
            MAX-ACCESS read-only
            STATUS current
            DESCRIPTION
                "This object indicates the received 1519~oversize-octet frames."
            ::= { hwGponOntEtherStatsEntry 56 }

       hwGponOntEtherStatsStateChangeTimes  OBJECT-TYPE
            SYNTAX Integer32
            MAX-ACCESS read-only
            STATUS current
            DESCRIPTION
                "This object indicates the ONT ethernet port state changed times."
            ::= { hwGponOntEtherStatsEntry 57 }

       hwGponOntEtherStatsDuration OBJECT-TYPE
            SYNTAX      Gauge32
            UNITS       "second"
            MAX-ACCESS  read-only
            STATUS      current
            DESCRIPTION
                "Indicates the statistic duration of the GPON ONT ethernet port.
                 Unit: second
                "
            ::= { hwGponOntEtherStatsEntry 58 }

      -- Table22 HwGponOntGemPortStatsTable
   hwGponOntGemPortStatsTable OBJECT-TYPE
       SYNTAX  SEQUENCE OF HwGponOntGemPortStatsEntry
       MAX-ACCESS not-accessible
       STATUS current
       DESCRIPTION
           "ONT GEM port statistics table, used for querying and clearing the information about the GEM port.
            The indexes of this table are ifIndex,
            hwGponDeviceOntObjectIndex and hwGponDevicePortidObjectIndex.
       "
       ::= { hwGponDeviceStatObjects 8 }

   hwGponOntGemPortStatsEntry OBJECT-TYPE
       SYNTAX HwGponOntGemPortStatsEntry
       MAX-ACCESS not-accessible
       STATUS current
       DESCRIPTION
           "ONT GEM port statistics table, used for querying and clearing the information about the GEM port.
            The indexes of this entry are ifIndex,
            hwGponDeviceOntObjectIndex and hwGponDevicePortidObjectIndex.
       "
       INDEX { ifIndex, hwGponDeviceOntObjectIndex, hwGponDevicePortidObjectIndex }
       ::= { hwGponOntGemPortStatsTable 1 }

   HwGponOntGemPortStatsEntry ::=
       SEQUENCE {
       hwGponOntGemPortLostPackets                       Counter64,
       hwGponOntGemPortMisinsertedPackets                Counter64,
       hwGponOntGemPortReceivedPackets                   Counter64,
       hwGponOntGemPortReceivedBlocks                    Counter64,
       hwGponOntGemPortTransmittedBlocks                 Counter64,
       hwGponOntGemPortImpairedBlocks                    Counter64,
       hwGponOntGemPortClear                             Integer32,
       hwGponOntGemPortTransmittedGemFrames              Counter64
       }

   hwGponOntGemPortLostPackets OBJECT-TYPE
       SYNTAX Counter64
       MAX-ACCESS read-only
       STATUS current
       DESCRIPTION
           "Loss of frames."
       ::= { hwGponOntGemPortStatsEntry 1 }

   hwGponOntGemPortMisinsertedPackets OBJECT-TYPE
       SYNTAX Counter64
       MAX-ACCESS read-only
       STATUS current
       DESCRIPTION
           "Number of frames sent incorrectly."
       ::= { hwGponOntGemPortStatsEntry 2 }

   hwGponOntGemPortReceivedPackets OBJECT-TYPE
       SYNTAX Counter64
       MAX-ACCESS read-only
       STATUS current
       DESCRIPTION
           "Received frames."
       ::= { hwGponOntGemPortStatsEntry 3 }

   hwGponOntGemPortReceivedBlocks OBJECT-TYPE
       SYNTAX Counter64
       MAX-ACCESS read-only
       STATUS current
       DESCRIPTION
           "Received blocks."
       ::= { hwGponOntGemPortStatsEntry 4 }

   hwGponOntGemPortTransmittedBlocks OBJECT-TYPE
       SYNTAX Counter64
       MAX-ACCESS read-only
       STATUS current
       DESCRIPTION
           "Sent blocks."
       ::= { hwGponOntGemPortStatsEntry 5 }

   hwGponOntGemPortImpairedBlocks OBJECT-TYPE
       SYNTAX Counter64
       MAX-ACCESS read-only
       STATUS current
       DESCRIPTION
           "Number of received severely errored blocks."
       ::= { hwGponOntGemPortStatsEntry 6 }

   hwGponOntGemPortClear OBJECT-TYPE
       SYNTAX Integer32
       MAX-ACCESS read-write
       STATUS current
       DESCRIPTION
           "Clear the statistics."
       ::= { hwGponOntGemPortStatsEntry 7 }

   hwGponOntGemPortTransmittedGemFrames OBJECT-TYPE
       SYNTAX Counter64
       MAX-ACCESS read-only
       STATUS current
       DESCRIPTION
           "Number of transmitted GEM frames."
       ::= { hwGponOntGemPortStatsEntry 8 }

-- Table28 HwGponDeviceOntIpConfigTable
   hwGponDeviceOntIpConfigTable OBJECT-TYPE
       SYNTAX     SEQUENCE OF HwGponDeviceOntIpConfigEntry
       MAX-ACCESS not-accessible
       STATUS     current
       DESCRIPTION
           "This is the ONT IP configuration table.
            This table is used to configure and query
            the IP configuration mode and IP address of an ONT.
            The indexes of this table are ifIndex,
            hwGponDeviceOntObjectIndex and hwGponOntIpIndex.
           "
       ::= { hwGponDeviceControlObjects 30 }

   hwGponDeviceOntIpConfigEntry OBJECT-TYPE
       SYNTAX     HwGponDeviceOntIpConfigEntry
       MAX-ACCESS not-accessible
       STATUS     current
       DESCRIPTION
           "This is the ONT IP configuration table.
            This table is used to configure and query
            the IP configuration mode and IP address of an ONT.
            The indexes of this entry are ifIndex,
            hwGponDeviceOntObjectIndex and hwGponOntIpIndex.
           "
       INDEX       { ifIndex, hwGponDeviceOntObjectIndex, hwGponOntIpIndex }
       ::= { hwGponDeviceOntIpConfigTable 1 }

   HwGponDeviceOntIpConfigEntry ::=
       SEQUENCE {
               hwGponOntIpConfigMode                 INTEGER,
               hwGponOntIpAddress                    IpAddress,
               hwGponOntNetMask                      IpAddress,
               hwGponOntPhyAddress                   MacAddress,
               hwGponOntNetGateway                   IpAddress,
               hwGponOntMasterDNS                    IpAddress,
               hwGponOntSlandbyeDNS                  IpAddress,
               hwGponOntIpConfigVlan                 Integer32,
               hwGponOntIpConfigPriority             Integer32,
               hwGponOntIpIndex                      Integer32,
               hwGponOntIpconfigDscpDefaultPriority  Integer32,
               hwGponOntIpconfigDscpProfIndex        Integer32,
               hwGponOntIpconfigDhcpReset            INTEGER
               }

    hwGponOntIpConfigMode  OBJECT-TYPE
        SYNTAX     INTEGER{
                   dhcp(1),
                   manual(2),
                   configurationFile(3)
                   }
        MAX-ACCESS   read-write
        STATUS      current
        DESCRIPTION
            "IP configuration mode.
             Options:
             1. dhcp(1)              -Indicates the dynamic allocation mode
             2. manual(2)            -Indicates the static allocation mode
             3. configurationFile(3) -Indicates the configuration file mode
            "
       ::= { hwGponDeviceOntIpConfigEntry 1 }

    hwGponOntIpAddress  OBJECT-TYPE
        SYNTAX     IpAddress
        MAX-ACCESS   read-write
        STATUS      current
        DESCRIPTION
            "ONT ip address."
        ::= { hwGponDeviceOntIpConfigEntry 2 }

    hwGponOntNetMask  OBJECT-TYPE
        SYNTAX     IpAddress
        MAX-ACCESS   read-write
        STATUS      current
        DESCRIPTION
            "Subnet mask."
        ::= { hwGponDeviceOntIpConfigEntry 3 }


    hwGponOntPhyAddress  OBJECT-TYPE
        SYNTAX     MacAddress
        MAX-ACCESS   read-only
        STATUS      current
        DESCRIPTION
            "ONT MAC address."
        ::= { hwGponDeviceOntIpConfigEntry 4 }

    hwGponOntNetGateway  OBJECT-TYPE
        SYNTAX     IpAddress
        MAX-ACCESS   read-write
        STATUS      current
        DESCRIPTION
            "The default network gateway."
        ::= { hwGponDeviceOntIpConfigEntry 5 }


    hwGponOntMasterDNS  OBJECT-TYPE
        SYNTAX     IpAddress
        MAX-ACCESS   read-write
        STATUS      current
        DESCRIPTION
            "The active DNS address."
        ::= { hwGponDeviceOntIpConfigEntry 6 }


    hwGponOntSlandbyeDNS  OBJECT-TYPE
        SYNTAX     IpAddress
        MAX-ACCESS   read-write
        STATUS      current
        DESCRIPTION
            "The standby DNS address."
        ::= { hwGponDeviceOntIpConfigEntry 7 }

   hwGponOntIpConfigVlan  OBJECT-TYPE
       SYNTAX     Integer32
       MAX-ACCESS   read-write
       STATUS      current
       DESCRIPTION
               "The management VLAN of ONT.
                range: 0-4095"
       ::= { hwGponDeviceOntIpConfigEntry 8 }

   hwGponOntIpConfigPriority  OBJECT-TYPE
       SYNTAX     Integer32
       MAX-ACCESS   read-write
       STATUS      current
       DESCRIPTION
           "The management priority of ONT. range: 0-7, 0xfe: dscp-mapping."
       DEFVAL { 0 }
       ::= { hwGponDeviceOntIpConfigEntry 9 }

   hwGponOntIpIndex  OBJECT-TYPE
       SYNTAX     Integer32
       MAX-ACCESS  not-accessible
       STATUS      current
       DESCRIPTION
           "The IP index of the ont IP host."
       ::= { hwGponDeviceOntIpConfigEntry 10 }

   hwGponOntIpconfigDscpDefaultPriority OBJECT-TYPE
       SYNTAX      Integer32
       MAX-ACCESS  read-write
       STATUS      current
       DESCRIPTION
           "The default priority for dscp-mapping policy."
       ::= { hwGponDeviceOntIpConfigEntry 11 }

   hwGponOntIpconfigDscpProfIndex OBJECT-TYPE
       SYNTAX      Integer32
       MAX-ACCESS  read-write
       STATUS      current
       DESCRIPTION
               "The dscp profile index of the ONT ip host, and the range is 1~50"
       ::= { hwGponDeviceOntIpConfigEntry 12 }

   hwGponOntIpconfigDhcpReset OBJECT-TYPE
      SYNTAX      INTEGER
      {
        reset(1),
        invalid (-1)
      }
      MAX-ACCESS   read-write
        STATUS      current
        DESCRIPTION
            "This object is used for resetting the ip host in the DHCP mode.
            Options:
            1. reset(1)            - DHCP reset in the DHCP mode
            2. invalid (-1)        - Invalid
            "
       ::= { hwGponDeviceOntIpConfigEntry 13 }

-- Table29 hwGponDeviceOntExtConfigTable
   hwGponDeviceOntExtConfigTable OBJECT-TYPE
       SYNTAX     SEQUENCE OF HwGponDeviceOntExtConfigEntry
       MAX-ACCESS not-accessible
       STATUS     current
       DESCRIPTION
           "This configuration table is used to set and query the multicast packet
            forwarding mode and transparent transmission attributes of the ONT.
            In addition, it is used to enable and disable the MAC address learning function of the ONT.
            When the multicast packet forwarding mode is tag switching,
            the configuration table can be also used to set and query the VLAN ID
            and the multicast snooping mode of the ONT, set the upstream IGMP packet forwarding mode,
            and disable the upstream forward error correction (FEC) function on the ONT.
            The indexes of this table are ifIndex and hwGponDeviceOntObjectIndex.
           "
       ::= { hwGponDeviceControlObjects 47 }

   hwGponDeviceOntExtConfigEntry OBJECT-TYPE
       SYNTAX     HwGponDeviceOntExtConfigEntry
       MAX-ACCESS not-accessible
       STATUS     current
       DESCRIPTION
           "This configuration table is used to set and query the multicast packet
            forwarding mode and transparent transmission attributes of the ONT.
            In addition, it is used to enable and disable the MAC address learning function of the ONT.
            When the multicast packet forwarding mode is tag switching,
            the configuration table can be also used to set and query the VLAN ID
            and the multicast snooping mode of the ONT, set the upstream IGMP packet forwarding mode,
            and disable the upstream forward error correction (FEC) function on the ONT.
            The indexes of this entry are ifIndex and hwGponDeviceOntObjectIndex.
           "
       INDEX       { ifIndex, hwGponDeviceOntObjectIndex }
       ::= { hwGponDeviceOntExtConfigTable 1 }

   HwGponDeviceOntExtConfigEntry ::=
       SEQUENCE {
               hwGponDeviceOntObjectIgmpMode              INTEGER,
               hwGponDeviceOntObjectIgmpSwitchVlan        Integer32,
               hwGponDeviceOntTransparent                 INTEGER,
               hwGponDeviceOntObjectMacCount              Integer32,
               hwGponDeviceOntTdmLocalInnerLoopback       INTEGER,
               hwGponDeviceOntTdmLocalOuterLoopback       INTEGER,
               hwGponDeviceOntMacAddressSwitch            INTEGER,
               hwGponDeviceOntUpIgmpMsgProcMode           INTEGER,
               hwGponDeviceOntIgmpForwardTranslationVlan  Integer32,
               hwGponDeviceOntMulticastCtrlMode           INTEGER,
               hwGponDeviceOntUpFEC                       INTEGER,
               hwGponDeviceOntObjectOMCCEncrypt           INTEGER,
               hwGponDeviceOntIgmpForwardPriority         Integer32,
               hwGponDeviceOntNativeVlanOption            INTEGER,
               hwGponDeviceOntTr069Management             INTEGER,
               hwGponDeviceOntUpPqColorPolicy             INTEGER,
               hwGponDeviceOntDownPqColorPolicy           INTEGER,
               hwGponDeviceOntMulticastMode               INTEGER,
               hwGponDeviceOntTr069ManagementIpIndex      Integer32,
               hwGponDeviceOntRingCheckSwitch             INTEGER,
               hwGponDeviceOntRingCheckAutoShutdownSwitch INTEGER,
               hwGponDeviceOntRingCheckDetectingFrequency Integer32,
               hwGponDeviceOntRingCheckResumeInterval     Integer32,
               hwGponDeviceOntMonitorLinkSwitch           INTEGER,
               hwGponDeviceOntMTU                         Integer32
               }

   hwGponDeviceOntObjectIgmpMode  OBJECT-TYPE
       SYNTAX     INTEGER{
                  untag(1),
                  tagSwitch(2),
                  tagPermeate(3),
                  unconcern(254),
                  invalid (-1)
                  }
       MAX-ACCESS   read-write
       STATUS      current
       DESCRIPTION
           "ONT multicast forwarding mode. After the downstream multicast traffic
            passes the ONT, if the multicast forwarding mode is tag-switch,
            the multicast VLAN is switched to the configured user VLAN.
            If the multicast forwarding mode is tag-permeate, the multicast VLAN
            is reserved. In untag (1) mode, the 802.1q tag is skipped.
            Options:
            1. untag(1)        -ONT multicast forwarding mode is untag
            2. tagSwitch(2)    -ONT multicast forwarding mode is tagSwitch
            3. tagPermeate(3)  -ONT multicast forwarding mode is tagPermeate
            4. unconcern(254)  -ONT multicast forwarding mode is unconcern
            5. invalid (-1)    -ONT multicast forwarding mode is invalid
           "
       ::= { hwGponDeviceOntExtConfigEntry 1 }

   hwGponDeviceOntObjectIgmpSwitchVlan  OBJECT-TYPE
       SYNTAX     Integer32 (-1 | 1..4095 | 4096)
       MAX-ACCESS   read-write
       STATUS      current
       DESCRIPTION
           "The user VLAN, that can be set only in tag-switch mode.
           the value (4096) indicates IGMP-user-VLAN is used for multicast VLAN.
           the value (-1) indicates has not config the VLAN."
       ::= { hwGponDeviceOntExtConfigEntry 2 }

   hwGponDeviceOntTransparent  OBJECT-TYPE
       SYNTAX     INTEGER{
                  enable(1),
                  disable(2),
                  invalid (-1)
                  }
       MAX-ACCESS   read-write
       STATUS      current
       DESCRIPTION
           "The ONT transparent mode.
            Options:
            1. enable(1)    -Enable the ONT transparent mode
            2. disable(2)   -Disable the ONT transparent mode
            3. invalid (-1) -The ONT transparent mode is invalid
           "
       ::= { hwGponDeviceOntExtConfigEntry 3 }

   hwGponDeviceOntObjectMacCount    OBJECT-TYPE
       SYNTAX  Integer32
       MAX-ACCESS  read-only
       STATUS  current
       DESCRIPTION
           "The MAC address count that ONT learned."
       ::= { hwGponDeviceOntExtConfigEntry 4 }

   hwGponDeviceOntTdmLocalInnerLoopback  OBJECT-TYPE
       SYNTAX     INTEGER{
                  noLoopback(1),
                  localInnerLoopback(2),
                  unkonwn(-1)
                  }
       MAX-ACCESS   read-write
       STATUS      current
       DESCRIPTION
           "Local inner loopback of the E1 service of the ONT.
            Options:
            1. noLoopback(1)         -Local inner loopback of the E1 service of the ONT is noLoopback
            2. localInnerLoopback(2) -Local inner loopback of the E1 service of the ONT is localInnerLoopback
            3. unkonwn(-1)           -Local inner loopback of the E1 service of the ONT is unkonwn
           "
       ::= { hwGponDeviceOntExtConfigEntry 5 }

   hwGponDeviceOntTdmLocalOuterLoopback  OBJECT-TYPE
       SYNTAX     INTEGER{
                  noLoopback(1),
                  localOuterLoopback(2),
                  unkonwn(-1)
                  }
       MAX-ACCESS   read-write
       STATUS      current
       DESCRIPTION
           "Local outer loopback of the E1 service of the ONT.
            Options:
            1. noLoopback(1)          -Local outer loopback of the E1 service of the ONT is noLoopback
            2. localOuterLoopback(2)  -Local outer loopback of the E1 service of the ONT is localOuterLoopback
            3. unkonwn(-1)            -Local outer loopback of the E1 service of the ONT is unkonwn
           "
       DEFVAL { noLoopback }
       ::= { hwGponDeviceOntExtConfigEntry 6 }

    hwGponDeviceOntMacAddressSwitch  OBJECT-TYPE
        SYNTAX     INTEGER{
                   enable(1),
                   disable(2),
                   invalid (-1)
                   }
        MAX-ACCESS   read-write
        STATUS      current
        DESCRIPTION
            "The switch of the ONT MAC address learning function.
             Options:
             1. enable(1)    -Enable the switch of the ONT MAC address learning function
             2. disable(2)   -Disable the switch of the ONT MAC address learning function
             3. invalid (-1) -The switch of the ONT MAC address learning function is invalid
            "
        DEFVAL { enable }
        ::= { hwGponDeviceOntExtConfigEntry 7 }

   hwGponDeviceOntUpIgmpMsgProcMode  OBJECT-TYPE
       SYNTAX     INTEGER{
                   transparent(1),
                   translation(2),
                   default(3),
                   unconcern(254),
                   invalid (-1)
                   }
        MAX-ACCESS   read-write
        STATUS       current
        DESCRIPTION
            "In Upstream the ONT forwards the IGMP packets to the OLT, the VLAN translation mode.
             Options:
             1. transparent(1) -The VLAN translation mode is transparent
             2. translation(2) -The VLAN translation mode is translation
             3. default(3)     -The VLAN translation mode is default
             4. unconcern(254) -The VLAN translation mode is unconcern
             5. invalid (-1)   -The VLAN translation mode is invalid
            "
        ::= { hwGponDeviceOntExtConfigEntry 8 }

   hwGponDeviceOntIgmpForwardTranslationVlan  OBJECT-TYPE
       SYNTAX      Integer32   (-1..4095)
       MAX-ACCESS  read-write
       STATUS      current
       DESCRIPTION
           "The translation VLAN, that can be set only in translation mode.
            the value (-1) indicates has not config the VLAN."
       ::= { hwGponDeviceOntExtConfigEntry 9 }

   hwGponDeviceOntMulticastCtrlMode  OBJECT-TYPE
       SYNTAX     INTEGER{
                  snooping(1),
                  spr(2),
                  unsupported(-1)
                  }
       MAX-ACCESS  read-write
       STATUS      current
       DESCRIPTION
           "The ont multicast control mode.
            Options:
            1. snooping(1)               - Snooping mode
            2. spr(2)                    - Snooping with proxy reporting mode
            3. unsupported(-1)           - Indicates that the query fails or no information is detected
           "
       ::= { hwGponDeviceOntExtConfigEntry 10 }

    hwGponDeviceOntUpFEC           OBJECT-TYPE
    SYNTAX INTEGER{
            enable(1),
            disable(2),
            invalidValue(-1)
    }
    MAX-ACCESS read-write
    STATUS current
    DESCRIPTION
            "Gpon ont upstream FEC.
             Options:
             1. enable(1)        - Enable Gpon ont upstream FEC
             2. disable(2)       - Disable Gpon ont upstream FEC
             3. invalidValue(-1) - Invalid value
            "
        ::= { hwGponDeviceOntExtConfigEntry 11 }

    hwGponDeviceOntObjectOMCCEncrypt OBJECT-TYPE
    SYNTAX INTEGER{
            on(1),
            off(2),
            invalidValue(-1)
    }
    MAX-ACCESS read-write
    STATUS current
    DESCRIPTION
            "Gpon ont OMCC downstream encrypt status.
             Options:
             1. on(1)            - Gpon ont OMCC downstream encrypt status is open
             2. off(2)           - Gpon ont OMCC downstream encrypt status is close
             3. invalidValue(-1) - Gpon ont OMCC downstream encrypt status is invalid
            "
        ::= { hwGponDeviceOntExtConfigEntry 12 }

    hwGponDeviceOntIgmpForwardPriority OBJECT-TYPE
    SYNTAX      Integer32   (-1 | 0..7)
    MAX-ACCESS read-write
    STATUS current
    DESCRIPTION
            "When upstream igmp packets were added a vlan or translated to the translation vlan,
             priority was set.
            "
        ::= { hwGponDeviceOntExtConfigEntry 13 }

    hwGponDeviceOntNativeVlanOption OBJECT-TYPE
    SYNTAX   INTEGER
                 {
                     concern(1),
                     unconcern(2),
                     invalidValue(-1)
            }
    MAX-ACCESS read-write
    STATUS current
    DESCRIPTION
        "ONT native VLAN.
         Options:
         1. concern(1)       -Indicates that it is concerned
         2. unconcern(2)     -Indicates that it is not concerned
         3. invalidValue(-1) -Invalid value
            "
        ::= { hwGponDeviceOntExtConfigEntry 14 }

    hwGponDeviceOntTr069Management OBJECT-TYPE
    SYNTAX INTEGER{
            enable(1),
            disable(2)
    }
    MAX-ACCESS read-write
    STATUS current
    DESCRIPTION
            "Gpon ont tr069 management status.
             Options:
             1. enable(1)  -Enable the Gpon ont tr069 management status
             2. disable(2) -Disable the Gpon ont tr069 management status
            "
        ::= { hwGponDeviceOntExtConfigEntry 15 }

    hwGponDeviceOntUpPqColorPolicy OBJECT-TYPE
    SYNTAX INTEGER{
            noMarking(0),
            dei(2),
            invalid(-1)
    }
    MAX-ACCESS read-write
    STATUS current
    DESCRIPTION
            "This object indicates the ONT upstream priority-queue color policy.
             Options:
             1. noMarking(0)        - Indicates that the upstream priority-queue color policy is no marking
             2. dei(2)               - Indicates that the upstream priority-queue color policy is DEI
             3. invalid(-1)          - Indicates that the upstream priority-queue color policy is invalid
            "
        ::= { hwGponDeviceOntExtConfigEntry 17 }

    hwGponDeviceOntDownPqColorPolicy OBJECT-TYPE
    SYNTAX INTEGER{
            noMarking(0),
            dei(2),
            invalid(-1)
    }
    MAX-ACCESS read-write
    STATUS current
    DESCRIPTION
            "This object indicates the ONT downstream priority-queue color policy.
             Options:
             1. noMarking(0)        - Indicates that the upstream priority-queue color policy is no marking
             2. dei(2)               - Indicates that the upstream priority-queue color policy is DEI
             3. invalid(-1)          - Indicates that the upstream priority-queue color policy is invalid
            "
        ::= { hwGponDeviceOntExtConfigEntry 18 }

    hwGponDeviceOntMulticastMode OBJECT-TYPE
    SYNTAX INTEGER{
            oltcontrol(1),
            igmpsnooping(2),
            unconcern(254),
            invalid(-1)
    }
    MAX-ACCESS read-write
    STATUS current
    DESCRIPTION
            "This object indicates the ONT multicast mode.
             Options:
             1. oltcontrol(1)        - Indicates that the ont multicast mode is olt controled
             2. igmpsnooping(2)      - Indicates that the ont multicast mode is igmp snooping
             3. unconcern(254)       - Indicates that the ont multicast mode is not concerned
             4. invalid(-1)          - Indicates that the ont multicast mode is invalid
	     "
      ::= { hwGponDeviceOntExtConfigEntry 19 }

    hwGponDeviceOntTr069ManagementIpIndex OBJECT-TYPE
    SYNTAX     Integer32
    MAX-ACCESS read-write
    STATUS current
    DESCRIPTION
            "The index of IP host which used by TR069.
            "
      ::= { hwGponDeviceOntExtConfigEntry 20 }

    hwGponDeviceOntRingCheckSwitch OBJECT-TYPE
    SYNTAX INTEGER{
            enable(1),
            disable(2),
            invalid(-1)
    }
    MAX-ACCESS read-write
    STATUS current
    DESCRIPTION
            "This object indicates the ONT ring check switch.
             Options:
             1. enable(1)   - Enable the Gpon ont ring check
             2. disable(2)  - Disable the Gpon ont ring check
             3. invalid(-1) - Invalid value

            "
      ::= { hwGponDeviceOntExtConfigEntry 21 }

    hwGponDeviceOntRingCheckAutoShutdownSwitch OBJECT-TYPE
    SYNTAX INTEGER{
            enable(1),
            disable(2),
            invalid(-1)
    }
    MAX-ACCESS read-write
    STATUS current
    DESCRIPTION
            "This object indicates the ONT ring check auto shutdown switch.
             Options:
             1. enable(1)   - Enable the Gpon ont ring check auto shutdown
             2. disable(2)  - Disable the Gpon ont ring check auto shutdown
             3. invalid(-1) - Invalid value
            "
      ::= { hwGponDeviceOntExtConfigEntry 22 }

    hwGponDeviceOntRingCheckDetectingFrequency OBJECT-TYPE
    SYNTAX     Integer32   (-1..20)
    MAX-ACCESS read-write
    STATUS current
    DESCRIPTION
            "The fequency of ring check detecting.
            "
      ::= { hwGponDeviceOntExtConfigEntry 23 }

    hwGponDeviceOntRingCheckResumeInterval OBJECT-TYPE
    SYNTAX     Integer32   (-1 | 60..3600)
    MAX-ACCESS read-write
    STATUS current
    DESCRIPTION
            "The interval of ring check resume.
            "
      ::= { hwGponDeviceOntExtConfigEntry 24 }

    hwGponDeviceOntMonitorLinkSwitch  OBJECT-TYPE
    SYNTAX     INTEGER{
                   enable(1),
                   disable(2),
                   unconcern (254),
                   invalid(-1)
                   }
    MAX-ACCESS   read-write
    STATUS      current
    DESCRIPTION
            "The switch of the ONT Monitor Link function.
             Options:
             1. enable(1)       -Enable the the ONT Monitor Link function.
             2. disable(2)      -Disable the the ONT Monitor Link function.
             3. unconcern (254) -The ONT Monitor Link function is unconcern and dependS on ONT Configuration.The default value is unconcern.
             4. invalid(-1)     -Indicates that the query fails or no information is detected.
             "
      ::= { hwGponDeviceOntExtConfigEntry 25 }

    hwGponDeviceOntMTU OBJECT-TYPE
    SYNTAX Integer32 (-1|0|1519..9280)
    UNITS  "byte"
    MAX-ACCESS read-write
    STATUS current
    DESCRIPTION
       "This object indicates the ONT MTU value. Unit:byte.
        The value (0) indicates that the MTU value is decided by ONT.
        The value (-1) indicates that the query fails or no information is detected.
        The default value is unconcern(0).
       "
      ::= { hwGponDeviceOntExtConfigEntry 26}

-- Table30 hwGponDevicePortidQueryTable
   hwGponDevicePortidQueryTable OBJECT-TYPE
       SYNTAX     SEQUENCE OF HwGponDevicePortidQueryEntry
       MAX-ACCESS not-accessible
       STATUS     current
       DESCRIPTION
           "This is the GEM port query table. This table is used to query the GEM port
            that is configured with the flow mapping. The index contians the traffic stream
            parameters such as VLAN ID, priority, port type and others.
            The indexes of this table are ifIndex, hwGponDeviceOntObjectIndex,
            hwGponDevicePortidMapTypeIndex, hwGponDevicePortidMapObjectVlanIndex,
            hwGponDevicePortidMapObjectPriIndex, hwGponDevicePortidMapObjectPortTypeIndex
            and hwGponDevicePortidMapObjectPortIDIndex."
       ::= { hwGponDeviceControlObjects 48 }

   hwGponDevicePortidQueryEntry OBJECT-TYPE
       SYNTAX     HwGponDevicePortidQueryEntry
       MAX-ACCESS not-accessible
       STATUS     current
       DESCRIPTION
           "This is the GEM port query table. This table is used to query the GEM port
            that is configured with the flow mapping. The index contians the traffic stream
            parameters such as VLAN ID, priority, port type and others.
            The indexes of this entry are ifIndex, hwGponDeviceOntObjectIndex,
            hwGponDevicePortidMapTypeIndex, hwGponDevicePortidMapObjectVlanIndex,
            hwGponDevicePortidMapObjectPriIndex, hwGponDevicePortidMapObjectPortTypeIndex
            and hwGponDevicePortidMapObjectPortIDIndex.
           "
       INDEX       { ifIndex, hwGponDeviceOntObjectIndex, hwGponDevicePortidMapTypeIndex,
       hwGponDevicePortidMapObjectVlanIndex, hwGponDevicePortidMapObjectPriIndex,
       hwGponDevicePortidMapObjectPortTypeIndex, hwGponDevicePortidMapObjectPortIDIndex }
       ::= { hwGponDevicePortidQueryTable 1 }

   HwGponDevicePortidQueryEntry ::=
        SEQUENCE {
                hwGponDevicePortidMapTypeIndex            Integer32,
                hwGponDevicePortidMapObjectVlanIndex      Integer32,
                hwGponDevicePortidMapObjectPriIndex       Integer32,
                hwGponDevicePortidMapObjectPortTypeIndex  INTEGER,
                hwGponDevicePortidMapObjectPortIDIndex    Integer32,
                hwGponDeviceMappedPortid                  Integer32
                }

   hwGponDevicePortidMapTypeIndex  OBJECT-TYPE
       SYNTAX     Integer32
       MAX-ACCESS   not-accessible
       STATUS      current
       DESCRIPTION
           "GEM port mapping type."
       ::= { hwGponDevicePortidQueryEntry 1 }

   hwGponDevicePortidMapObjectVlanIndex  OBJECT-TYPE
       SYNTAX     Integer32
       MAX-ACCESS   not-accessible
       STATUS      current
       DESCRIPTION
           " VLAN ID of stream mapping."
       ::= { hwGponDevicePortidQueryEntry 2 }

   hwGponDevicePortidMapObjectPriIndex  OBJECT-TYPE
       SYNTAX     Integer32
       MAX-ACCESS   not-accessible
       STATUS      current
       DESCRIPTION
           "Priority of stream mapping."
       ::= { hwGponDevicePortidQueryEntry 3 }

   hwGponDevicePortidMapObjectPortTypeIndex  OBJECT-TYPE
       SYNTAX     INTEGER {
            t1 (13),
            e1 (14),
            fe (24),
            ge (34),
            vdsl (37),
            moca (46),
            eth (47),
            iphost (50),
            tdmvcl (253),
            invalidValue(-1)
            }
       MAX-ACCESS   not-accessible
       STATUS      current
       DESCRIPTION
           "Port type.
            Options:
            1. t1(13)      -Port type is t1
            2. e1(14)      -Port type is e1
            3. fe(24)      -Port type is fe
            4. ge(34)      -Port type is ge
            5. vdsl(37)    -Port type is vdsl
            6. moca(46)    -Port type is moca
            7. eth(47)     -Port type is eth
            8. iphost(50)  -Port type is iphost
            9. tdmvcl(253) -Port type is tdmvcl
	    10.invalidValue(-1) -Indicates that the query fails or no information is detected
           "
       ::= { hwGponDevicePortidQueryEntry 4 }

   hwGponDevicePortidMapObjectPortIDIndex  OBJECT-TYPE
       SYNTAX     Integer32
       MAX-ACCESS   not-accessible
       STATUS      current
       DESCRIPTION
           "Port ID."
       ::= { hwGponDevicePortidQueryEntry 5 }

   hwGponDeviceMappedPortid  OBJECT-TYPE
       SYNTAX     Integer32
       MAX-ACCESS   read-only
       STATUS      current
       DESCRIPTION
           "GEM port ID."

       ::= { hwGponDevicePortidQueryEntry 6 }

-- Table31 hwGponOltEtherStatisticTable
   hwGponOltEtherStatisticTable OBJECT-TYPE
       SYNTAX     SEQUENCE OF HwGponOltEtherStatisticEntry
       MAX-ACCESS not-accessible
       STATUS     current
       DESCRIPTION
           "This table is used to query the number of frames corresponding to
            the received, sent, and discarded Ethernet packets on the GPON port.
            The index of this table is ifIndex.
           "
       ::= { hwGponDeviceStatObjects 9 }

   hwGponOltEtherStatisticEntry OBJECT-TYPE
       SYNTAX     HwGponOltEtherStatisticEntry
       MAX-ACCESS not-accessible
       STATUS     current
       DESCRIPTION
           "This table is used to query the number of frames corresponding to
            the received, sent, and discarded Ethernet packets on the GPON port.
            The index of this entry is ifIndex.
           "
       INDEX       { ifIndex }
       ::= { hwGponOltEtherStatisticTable 1 }

   HwGponOltEtherStatisticEntry ::=
       SEQUENCE {
               hwGponOltEtherStatisticReceivedPakts                  Counter64,
               hwGponOltEtherStatisticSendPakts                      Counter64,
               hwGponOltEtherStatisticDropPakts                      Counter64,
               hwGponOltEtherStatisticReceivedTotalPakts             Counter64,
               hwGponOltEtherStatisticReceivedBroadcastPakts         Counter64,
               hwGponOltEtherStatisticReceivedMulticastPakts         Counter64,
               hwGponOltEtherStatisticReceivedUnicastPakts           Counter64,
               hwGponOltEtherStatisticReceivedLen64Bytes             Counter64,
               hwGponOltEtherStatisticReceivedLen65To127Bytes        Counter64,
               hwGponOltEtherStatisticReceivedLen128To255Bytes       Counter64,
               hwGponOltEtherStatisticReceivedLen256To511Bytes       Counter64,
               hwGponOltEtherStatisticReceivedLen512To1023Bytes      Counter64,
               hwGponOltEtherStatisticReceivedLen1024To1518Bytes     Counter64,
               hwGponOltEtherStatisticReceivedLenMore1518Bytes       Counter64,
               hwGponOltEtherStatisticReceivedBytes                  Counter64,
               hwGponOltEtherStatisticReceivedTooLongPakts           Counter64,
               hwGponOltEtherStatisticReceivedTooShortPakts          Counter64,
               hwGponOltEtherStatisticReceivedCRCErrPakts            Counter64,
               hwGponOltEtherStatisticSendTotalPakts                 Counter64,
               hwGponOltEtherStatisticSendBroadcastPakts             Counter64,
               hwGponOltEtherStatisticSendMulticastPakts             Counter64,
               hwGponOltEtherStatisticSendUnicastPakts               Counter64,
               hwGponOltEtherStatisticSendLen64Bytes                 Counter64,
               hwGponOltEtherStatisticSendLen65To127Bytes            Counter64,
               hwGponOltEtherStatisticSendLen128To255Bytes           Counter64,
               hwGponOltEtherStatisticSendLen256To511Bytes           Counter64,
               hwGponOltEtherStatisticSendLen512To1023Bytes          Counter64,
               hwGponOltEtherStatisticSendLen1024To1518Bytes         Counter64,
               hwGponOltEtherStatisticSendLenMore1518Bytes           Counter64,
               hwGponOltEtherStatisticSendBytes                      Counter64,
               hwGponOltEtherStatisticClear                          Integer32,
               hwGponOltEtherStatisticSendMulticastBytes             Counter64,
               hwGponOltEthernetStatisticSendBufferOverflowDropPakts Counter64
               }

   hwGponOltEtherStatisticReceivedPakts  OBJECT-TYPE
       SYNTAX     Counter64
       MAX-ACCESS   read-only
       STATUS      current
       DESCRIPTION
           "Received frames."
       ::= { hwGponOltEtherStatisticEntry 1 }

   hwGponOltEtherStatisticSendPakts  OBJECT-TYPE
       SYNTAX     Counter64
       MAX-ACCESS   read-only
       STATUS      current
       DESCRIPTION
           "Sent frames."
       ::= { hwGponOltEtherStatisticEntry 2 }

   hwGponOltEtherStatisticDropPakts  OBJECT-TYPE
       SYNTAX     Counter64
       MAX-ACCESS   read-only
       STATUS      current
       DESCRIPTION
           "Received discarded frames(over-size, under size or CRC error)."
       ::= { hwGponOltEtherStatisticEntry 3 }

   hwGponOltEtherStatisticReceivedTotalPakts  OBJECT-TYPE
       SYNTAX     Counter64
       MAX-ACCESS   read-only
       STATUS      current
       DESCRIPTION
           "Received GEM frames."
       ::= { hwGponOltEtherStatisticEntry 4 }

   hwGponOltEtherStatisticReceivedBroadcastPakts  OBJECT-TYPE
       SYNTAX     Counter64
       MAX-ACCESS   read-only
       STATUS      current
       DESCRIPTION
           "Received broadcast frames."
       ::= { hwGponOltEtherStatisticEntry 5 }

   hwGponOltEtherStatisticReceivedMulticastPakts  OBJECT-TYPE
       SYNTAX     Counter64
       MAX-ACCESS   read-only
       STATUS      current
       DESCRIPTION
           "Received multicast frames."
       ::= { hwGponOltEtherStatisticEntry 6 }

   hwGponOltEtherStatisticReceivedUnicastPakts  OBJECT-TYPE
       SYNTAX     Counter64
       MAX-ACCESS   read-only
       STATUS      current
       DESCRIPTION
           "Received unicast frames."
       ::= { hwGponOltEtherStatisticEntry 7 }

   hwGponOltEtherStatisticReceivedLen64Bytes    OBJECT-TYPE
       SYNTAX     Counter64
       MAX-ACCESS   read-only
       STATUS      current
       DESCRIPTION
           "Received 64-octet frames."
       ::= { hwGponOltEtherStatisticEntry 8 }

   hwGponOltEtherStatisticReceivedLen65To127Bytes    OBJECT-TYPE
       SYNTAX     Counter64
       MAX-ACCESS   read-only
       STATUS      current
       DESCRIPTION
           "Received 65~127-octet frames."
       ::= { hwGponOltEtherStatisticEntry 9 }

   hwGponOltEtherStatisticReceivedLen128To255Bytes    OBJECT-TYPE
       SYNTAX     Counter64
       MAX-ACCESS   read-only
       STATUS      current
       DESCRIPTION
           "Received 128~255-octet frames."
       ::= { hwGponOltEtherStatisticEntry 10 }

   hwGponOltEtherStatisticReceivedLen256To511Bytes    OBJECT-TYPE
       SYNTAX     Counter64
       MAX-ACCESS   read-only
       STATUS      current
       DESCRIPTION
           "Received 256~511-octet frames."
       ::= { hwGponOltEtherStatisticEntry 11 }

   hwGponOltEtherStatisticReceivedLen512To1023Bytes    OBJECT-TYPE
       SYNTAX     Counter64
       MAX-ACCESS   read-only
       STATUS      current
       DESCRIPTION
           "Received 512~1023-octet frames."
       ::= { hwGponOltEtherStatisticEntry 12 }

   hwGponOltEtherStatisticReceivedLen1024To1518Bytes    OBJECT-TYPE
       SYNTAX     Counter64
       MAX-ACCESS   read-only
       STATUS      current
       DESCRIPTION
           "Received 1024~1518-octet frames."
       ::= { hwGponOltEtherStatisticEntry 13 }

   hwGponOltEtherStatisticReceivedLenMore1518Bytes    OBJECT-TYPE
       SYNTAX     Counter64
       MAX-ACCESS   read-only
       STATUS      current
       DESCRIPTION
           "Received over 1518-octet frames."
       ::= { hwGponOltEtherStatisticEntry 14 }

   hwGponOltEtherStatisticReceivedBytes    OBJECT-TYPE
       SYNTAX     Counter64
       MAX-ACCESS   read-only
       STATUS      current
       DESCRIPTION
           "Received octets."
       ::= { hwGponOltEtherStatisticEntry 15 }

   hwGponOltEtherStatisticReceivedTooLongPakts    OBJECT-TYPE
       SYNTAX     Counter64
       MAX-ACCESS   read-only
       STATUS      current
       DESCRIPTION
           "Received oversize frames."
       ::= { hwGponOltEtherStatisticEntry 16 }

   hwGponOltEtherStatisticReceivedTooShortPakts    OBJECT-TYPE
       SYNTAX     Counter64
       MAX-ACCESS   read-only
       STATUS      current
       DESCRIPTION
           "Received undersize frames."
       ::= { hwGponOltEtherStatisticEntry 17 }

   hwGponOltEtherStatisticReceivedCRCErrPakts    OBJECT-TYPE
       SYNTAX     Counter64
       MAX-ACCESS   read-only
       STATUS      current
       DESCRIPTION
           "Received CRC error frames."
       ::= { hwGponOltEtherStatisticEntry 18 }

   hwGponOltEtherStatisticSendTotalPakts    OBJECT-TYPE
       SYNTAX     Counter64
       MAX-ACCESS   read-only
       STATUS      current
       DESCRIPTION
           "Send GEM frames."
       ::= { hwGponOltEtherStatisticEntry 19 }

   hwGponOltEtherStatisticSendBroadcastPakts    OBJECT-TYPE
       SYNTAX     Counter64
       MAX-ACCESS   read-only
       STATUS      current
       DESCRIPTION
           "Send broadcast frames."
       ::= { hwGponOltEtherStatisticEntry 20 }

   hwGponOltEtherStatisticSendMulticastPakts    OBJECT-TYPE
       SYNTAX     Counter64
       MAX-ACCESS   read-only
       STATUS      current
       DESCRIPTION
           "Send multicast frames."
       ::= { hwGponOltEtherStatisticEntry 21 }

   hwGponOltEtherStatisticSendUnicastPakts    OBJECT-TYPE
       SYNTAX     Counter64
       MAX-ACCESS   read-only
       STATUS      current
       DESCRIPTION
           "Number of sent Ethernet unicast frames."
       ::= { hwGponOltEtherStatisticEntry 22 }

   hwGponOltEtherStatisticSendLen64Bytes    OBJECT-TYPE
       SYNTAX     Counter64
       MAX-ACCESS   read-only
       STATUS      current
       DESCRIPTION
           "Sent 64-octet frames."
       ::= { hwGponOltEtherStatisticEntry 23 }

   hwGponOltEtherStatisticSendLen65To127Bytes    OBJECT-TYPE
       SYNTAX     Counter64
       MAX-ACCESS   read-only
       STATUS      current
       DESCRIPTION
           "Sent 65~127-octet frames."
       ::= { hwGponOltEtherStatisticEntry 24 }


   hwGponOltEtherStatisticSendLen128To255Bytes    OBJECT-TYPE
       SYNTAX     Counter64
       MAX-ACCESS   read-only
       STATUS      current
       DESCRIPTION
           "Sent 128~255-octet frames."
       ::= { hwGponOltEtherStatisticEntry 25 }

   hwGponOltEtherStatisticSendLen256To511Bytes    OBJECT-TYPE
       SYNTAX     Counter64
       MAX-ACCESS   read-only
       STATUS      current
       DESCRIPTION
           "Sent 256~511-octet frames."
       ::= { hwGponOltEtherStatisticEntry 26 }

   hwGponOltEtherStatisticSendLen512To1023Bytes    OBJECT-TYPE
       SYNTAX     Counter64
       MAX-ACCESS   read-only
       STATUS      current
       DESCRIPTION
           "Sent 512~1023-octet frames."
       ::= { hwGponOltEtherStatisticEntry 27 }

   hwGponOltEtherStatisticSendLen1024To1518Bytes    OBJECT-TYPE
       SYNTAX     Counter64
       MAX-ACCESS   read-only
       STATUS      current
       DESCRIPTION
           "Sent 1024~1518-octet frames."
       ::= { hwGponOltEtherStatisticEntry 28 }

   hwGponOltEtherStatisticSendLenMore1518Bytes    OBJECT-TYPE
       SYNTAX     Counter64
       MAX-ACCESS   read-only
       STATUS      current
       DESCRIPTION
           "Sent over 1518-octet frames."
       ::= { hwGponOltEtherStatisticEntry 29 }

   hwGponOltEtherStatisticSendBytes    OBJECT-TYPE
       SYNTAX     Counter64
       MAX-ACCESS   read-only
       STATUS      current
       DESCRIPTION
           "Sent octets."
       ::= { hwGponOltEtherStatisticEntry 30 }

   hwGponOltEtherStatisticClear       OBJECT-TYPE
       SYNTAX     Integer32
       MAX-ACCESS   read-write
       STATUS      current
       DESCRIPTION
           "Clear the statistics."
       ::= { hwGponOltEtherStatisticEntry 31 }

   hwGponOltEtherStatisticSendMulticastBytes    OBJECT-TYPE
       SYNTAX     Counter64
       MAX-ACCESS   read-only
       STATUS      current
       DESCRIPTION
           "Sent multicast bytes."
       ::= { hwGponOltEtherStatisticEntry 32 }

   hwGponOltEthernetStatisticSendBufferOverflowDropPakts    OBJECT-TYPE
       SYNTAX     Counter64
       MAX-ACCESS   read-only
       STATUS      current
       DESCRIPTION
           "This object indicates the sent overflow drop frames."
       ::= { hwGponOltEtherStatisticEntry 33 }

-- Table32 hwGponGtcStatisticTable
   hwGponGtcStatisticTable OBJECT-TYPE
       SYNTAX     SEQUENCE OF HwGponGtcStatisticEntry
       MAX-ACCESS not-accessible
       STATUS     current
       DESCRIPTION
           "GPON port GTC statistics table,
            used to query the number of received and sent GTC frames on the GPON port.
            The index of this table is ifIndex."
       ::= { hwGponDeviceStatObjects 10 }

   hwGponGtcStatisticEntry OBJECT-TYPE
       SYNTAX     HwGponGtcStatisticEntry
       MAX-ACCESS not-accessible
       STATUS     current
       DESCRIPTION
           "GPON port GTC statistics table,
            used to query the number of received and sent GTC frames on the GPON port.
            The index of this entry is ifIndex."
       INDEX       { ifIndex }
       ::= { hwGponGtcStatisticTable 1 }

   HwGponGtcStatisticEntry ::=
       SEQUENCE {
               hwGponOltGtcStatisticReceivedFrames           Counter64,
               hwGponOltGtcStatisticReceivedOMCIPackts       Counter64,
               hwGponOltGtcStatisticReceivedPLOAMPackts      Counter64,
               hwGponOltGtcStatisticReceivedIdlePackts       Counter64,
               hwGponOltGtcStatisticSendFrames               Counter64,
               hwGponOltGtcStatisticSendOMCIPackts           Counter64,
               hwGponOltGtcStatisticSendPLOAMPackts          Counter64,
               hwGponOltGtcStatisticSendIdlePackts           Counter64,
               hwGponOltGtcStatisticsClear                   Integer32
               }

   hwGponOltGtcStatisticReceivedFrames  OBJECT-TYPE
       SYNTAX     Counter64
       MAX-ACCESS   read-only
       STATUS      current
       DESCRIPTION
           "Received GEM frames."
       ::= { hwGponGtcStatisticEntry 1 }

   hwGponOltGtcStatisticReceivedOMCIPackts  OBJECT-TYPE
       SYNTAX     Counter64
       MAX-ACCESS   read-only
       STATUS      current
       DESCRIPTION
           "Received OMCI frames."
       ::= { hwGponGtcStatisticEntry 2 }

   hwGponOltGtcStatisticReceivedPLOAMPackts  OBJECT-TYPE
       SYNTAX     Counter64
       MAX-ACCESS   read-only
       STATUS      current
       DESCRIPTION
           "Received PLOAM frames."
       ::= { hwGponGtcStatisticEntry 3 }

   hwGponOltGtcStatisticReceivedIdlePackts  OBJECT-TYPE
       SYNTAX     Counter64
       MAX-ACCESS   read-only
       STATUS      current
       DESCRIPTION
           "Received IDLE frames."
       ::= { hwGponGtcStatisticEntry 4 }

   hwGponOltGtcStatisticSendFrames  OBJECT-TYPE
       SYNTAX     Counter64
       MAX-ACCESS   read-only
       STATUS      current
       DESCRIPTION
           "Sent GEM frames."
       ::= { hwGponGtcStatisticEntry 5 }

   hwGponOltGtcStatisticSendOMCIPackts  OBJECT-TYPE
       SYNTAX     Counter64
       MAX-ACCESS   read-only
       STATUS      current
       DESCRIPTION
           "Sent OMCI frames."
       ::= { hwGponGtcStatisticEntry 6 }

   hwGponOltGtcStatisticSendPLOAMPackts  OBJECT-TYPE
       SYNTAX     Counter64
       MAX-ACCESS   read-only
       STATUS      current
       DESCRIPTION
           "Sent PLOAM frames."
       ::= { hwGponGtcStatisticEntry 7 }

   hwGponOltGtcStatisticSendIdlePackts    OBJECT-TYPE
       SYNTAX     Counter64
       MAX-ACCESS   read-only
       STATUS      current
       DESCRIPTION
           "Sent IDLE frames."
       ::= { hwGponGtcStatisticEntry 8 }

   hwGponOltGtcStatisticsClear           OBJECT-TYPE
       SYNTAX     Integer32
       MAX-ACCESS   read-write
       STATUS      current
       DESCRIPTION
           "Clear the statistics."
       ::= { hwGponGtcStatisticEntry 9 }

-- Table33 hwGponOntStatisticsTable
   hwGponOntStatisticsTable OBJECT-TYPE
       SYNTAX     SEQUENCE OF HwGponOntStatisticsEntry
       MAX-ACCESS not-accessible
       STATUS     current
       DESCRIPTION
           "ONT performance statistics table, used for querying the number of upstream and downstream frames,
            bytes, and dropped packets of the ONT.This table is used in xpon distributing mode.
            The indexes of this table are ifIndex and hwGponDeviceOntObjectIndex.
           "
       ::= { hwGponDeviceStatObjects 11 }

   hwGponOntStatisticsEntry OBJECT-TYPE
       SYNTAX     HwGponOntStatisticsEntry
       MAX-ACCESS not-accessible
       STATUS     current
       DESCRIPTION
           "ONT performance statistics table, used for querying the number of upstream and downstream frames,
            bytes, and dropped packets of the ONT.This table is used in xpon distributing mode.
            The indexes of this entry are ifIndex and hwGponDeviceOntObjectIndex.
           "
       INDEX       { ifIndex, hwGponDeviceOntObjectIndex }
       ::= { hwGponOntStatisticsTable 1 }

   HwGponOntStatisticsEntry ::=
       SEQUENCE {
               hwGponOntStatisticsUpPackts             Counter64,
               hwGponOntStatisticsDownPackts           Counter64,
               hwGponOntStatisticsUpBytes              Counter64,
               hwGponOntStatisticsDownBytes            Counter64,
               hwGponOntStatisticsUpDropPackts         Counter64,
               hwGponOntStatisticsDownDropPackts       Counter64,
               hwGponOntStatisticsClear                Integer32
               }

   hwGponOntStatisticsUpPackts  OBJECT-TYPE
       SYNTAX     Counter64
       MAX-ACCESS   read-only
       STATUS      current
       DESCRIPTION
           "Upstream frames."
       ::= { hwGponOntStatisticsEntry 1 }

   hwGponOntStatisticsDownPackts  OBJECT-TYPE
       SYNTAX     Counter64
       MAX-ACCESS   read-only
       STATUS      current
       DESCRIPTION
           "Downstream frames."
       ::= { hwGponOntStatisticsEntry 2 }

   hwGponOntStatisticsUpBytes  OBJECT-TYPE
       SYNTAX     Counter64
       MAX-ACCESS   read-only
       STATUS      current
       DESCRIPTION
           "Upstream bytes."
       ::= { hwGponOntStatisticsEntry 3 }

   hwGponOntStatisticsDownBytes  OBJECT-TYPE
       SYNTAX     Counter64
       MAX-ACCESS   read-only
       STATUS      current
       DESCRIPTION
           "Downstream bytes."
       ::= { hwGponOntStatisticsEntry 4 }

   hwGponOntStatisticsUpDropPackts   OBJECT-TYPE
       SYNTAX     Counter64
       MAX-ACCESS   read-only
       STATUS      current
       DESCRIPTION
           "Upstream discarded frames."
       ::= { hwGponOntStatisticsEntry 5 }

   hwGponOntStatisticsDownDropPackts  OBJECT-TYPE
       SYNTAX     Counter64
       MAX-ACCESS   read-only
       STATUS      current
       DESCRIPTION
           "Downstream discarded frames."
       ::= { hwGponOntStatisticsEntry 6 }

   hwGponOntStatisticsClear  OBJECT-TYPE
       SYNTAX     Integer32
       MAX-ACCESS   read-write
       STATUS      current
       DESCRIPTION
           "Clear the statistics."
       ::= { hwGponOntStatisticsEntry 7 }

-- Table34 hwGponGemportStatisticsTable
   hwGponGemportStatisticsTable OBJECT-TYPE
       SYNTAX     SEQUENCE OF HwGponGemportStatisticsEntry
       MAX-ACCESS not-accessible
       STATUS     current
       DESCRIPTION
           "GEM port performance statistics table, used to query the number of upstream and downstream frames,
            bytes, and dropped packets of the GEM port.
            The indexes of this table are ifIndex and hwGponDevicePortidObjectIndex."
       ::= { hwGponDeviceStatObjects 12 }

   hwGponGemportStatisticsEntry OBJECT-TYPE
       SYNTAX     HwGponGemportStatisticsEntry
       MAX-ACCESS not-accessible
       STATUS     current
       DESCRIPTION
           "GEM port performance statistics table, used to query the number of upstream and downstream frames,
            bytes, and dropped packets of the GEM port.
            The indexes of this entry are ifIndex and hwGponDevicePortidObjectIndex."
       INDEX       { ifIndex, hwGponDevicePortidObjectIndex }
       ::= { hwGponGemportStatisticsTable 1 }

   HwGponGemportStatisticsEntry ::=
        SEQUENCE {
                hwGponGemportStatisUpPackts             Counter64,
                hwGponGemportStatisDownPackts           Counter64,
                hwGponGemportStatisUpBytes              Counter64,
                hwGponGemportStatisDownBytes            Counter64,
                hwGponGemportStatisUpDropPackts         Counter64,
                hwGponGemportStatisDownDropPackts       Counter64,
                hwGponGemportStatisticsClear            Integer32
                 }

   hwGponGemportStatisUpPackts  OBJECT-TYPE
       SYNTAX     Counter64
       MAX-ACCESS   read-only
       STATUS      current
       DESCRIPTION
           "Upstream frames."
       ::= { hwGponGemportStatisticsEntry 1 }

   hwGponGemportStatisDownPackts  OBJECT-TYPE
       SYNTAX     Counter64
       MAX-ACCESS   read-only
       STATUS      current
       DESCRIPTION
           "Downstream frames."
       ::= { hwGponGemportStatisticsEntry 2 }

   hwGponGemportStatisUpBytes  OBJECT-TYPE
       SYNTAX     Counter64
       MAX-ACCESS   read-only
       STATUS      current
       DESCRIPTION
           "Upstream bytes."
       ::= { hwGponGemportStatisticsEntry 3 }

   hwGponGemportStatisDownBytes  OBJECT-TYPE
       SYNTAX     Counter64
       MAX-ACCESS   read-only
       STATUS      current
       DESCRIPTION
           "Downstream bytes."
       ::= { hwGponGemportStatisticsEntry 4 }

   hwGponGemportStatisUpDropPackts   OBJECT-TYPE
       SYNTAX     Counter64
       MAX-ACCESS   read-only
       STATUS      current
       DESCRIPTION
           "Upstream discarded frames."
       ::= { hwGponGemportStatisticsEntry 5 }

   hwGponGemportStatisDownDropPackts  OBJECT-TYPE
       SYNTAX     Counter64
       MAX-ACCESS   read-only
       STATUS      current
       DESCRIPTION
           "Downstream discarded frames."
       ::= { hwGponGemportStatisticsEntry 6 }

   hwGponGemportStatisticsClear  OBJECT-TYPE
       SYNTAX     Integer32
       MAX-ACCESS   read-write
       STATUS      current
       DESCRIPTION
           "Clear the statistics."
       ::= { hwGponGemportStatisticsEntry 7 }

    -- Table 33 : HwEponDeviceOltConfigTable

    hwEponDeviceOltConfigTable OBJECT-TYPE
        SYNTAX     SEQUENCE OF HwEponDeviceOltConfigEntry
        MAX-ACCESS not-accessible
        STATUS     current
        DESCRIPTION
            "PON port attribute table, used to set various attributes of the PON port..
             The index of this table is ifIndex.
            "
        ::= { hwGponDeviceControlObjects 33 }

    hwEponDeviceOltConfigEntry OBJECT-TYPE
        SYNTAX     HwEponDeviceOltConfigEntry
        MAX-ACCESS not-accessible
        STATUS     current
        DESCRIPTION
            "PON port attribute table, used to set various attributes of the PON port..
             The index of this entry is ifIndex.
            "
        INDEX       { ifIndex }
        ::= { hwEponDeviceOltConfigTable 1 }

    HwEponDeviceOltConfigEntry ::=
        SEQUENCE {
                hwEponDeviceOltObjectfarthest                 Integer32,
                hwEponDeviceOltObjectAutofindOntEnable        Integer32,
                hwEponDeviceOltObjectDespt                    OCTET STRING
                }

    hwEponDeviceOltObjectfarthest  OBJECT-TYPE
        SYNTAX     Integer32
        MAX-ACCESS   read-write
        STATUS      current
        DESCRIPTION
            "Maximum distance of the ONT connected to the PON port."
        ::= { hwEponDeviceOltConfigEntry 1 }

    hwEponDeviceOltObjectAutofindOntEnable  OBJECT-TYPE
        SYNTAX     Integer32
        MAX-ACCESS   read-write
        STATUS      current
        DESCRIPTION
            "The ONT auto-find function of the PON port is enabled."
        ::= { hwEponDeviceOltConfigEntry 2 }

    hwEponDeviceOltObjectDespt  OBJECT-TYPE
        SYNTAX     OCTET STRING (SIZE (0..32))
        MAX-ACCESS   read-write
        STATUS      current
        DESCRIPTION
            "PON port description."
        ::= { hwEponDeviceOltConfigEntry 3}

    --Table 34 : HwEponDeviceOltControlTable

    hwEponDeviceOltControlTable OBJECT-TYPE
        SYNTAX     SEQUENCE OF HwEponDeviceOltControlEntry
        MAX-ACCESS not-accessible
        STATUS     current
        DESCRIPTION
            "This table implements the control of the PON port.
             The index of this table is ifIndex.
            "
        ::= { hwGponDeviceControlObjects 34 }

    hwEponDeviceOltControlEntry OBJECT-TYPE
        SYNTAX     HwEponDeviceOltControlEntry
        MAX-ACCESS not-accessible
        STATUS     current
        DESCRIPTION
            "This table implements the control of the PON port.
             The index of this entry is ifIndex.
            "
        INDEX       { ifIndex }
        ::= { hwEponDeviceOltControlTable 1 }

    HwEponDeviceOltControlEntry ::=
        SEQUENCE {
                hwEponDeviceOltObjectLaserSwitch              Integer32,
                hwEponDeviceOltObjectStatus                   Integer32
                }

    hwEponDeviceOltObjectLaserSwitch  OBJECT-TYPE
        SYNTAX     Integer32
        MAX-ACCESS   read-write
        STATUS      current
        DESCRIPTION
            "Laser switch of the PON port."
        ::= { hwEponDeviceOltControlEntry 1 }

    hwEponDeviceOltObjectStatus  OBJECT-TYPE
        SYNTAX     Integer32
        MAX-ACCESS   read-only
        STATUS      current
        DESCRIPTION
            "Status of the port on the OLT."
        ::= { hwEponDeviceOltControlEntry 2 }

    --Table 35 : HwEponDeviceOntProfileControlTable

    hwEponDeviceOntProfileControlTable OBJECT-TYPE
        SYNTAX     SEQUENCE OF HwEponDeviceOntProfileControlEntry
        MAX-ACCESS not-accessible
        STATUS     current
        DESCRIPTION
            "ONT capability set profile table, used to query, add or delete the ONT capability set profile.
             The index of this table is hwEponDeviceOntProfileNameIndex.
            "
        ::= { hwGponDeviceControlObjects 35 }

    hwEponDeviceOntProfileControlEntry OBJECT-TYPE
        SYNTAX     HwEponDeviceOntProfileControlEntry
        MAX-ACCESS not-accessible
        STATUS     current
        DESCRIPTION
            "ONT capability set profile table, used to query, add or delete the ONT capability set profile.
             The index of this entry is hwEponDeviceOntProfileNameIndex.
            "
        INDEX       { IMPLIED hwEponDeviceOntProfileNameIndex }
        ::= { hwEponDeviceOntProfileControlTable 1 }

    HwEponDeviceOntProfileControlEntry ::=
        SEQUENCE {
                hwEponDeviceOntProfileNameIndex               OCTET STRING,
                hwEponDeviceOntProfileRefNum                  Integer32,
                hwEponDeviceOntProfileUniConfig               Integer32,
                hwEponDeviceOntProfilePotsNum                 Integer32,
                hwEponDeviceOntTdmPortType                    Integer32,
                hwEponDeviceOntProfileE1T1Num                 Integer32,
                hwEponDeviceOntProfileRowStatus               RowStatus,
                hwEponDeviceOntGEMap                          PortList,
                hwEponDeviceOntFEMap                          PortList,
                hwEponDeviceOntMode                           INTEGER
                }

    hwEponDeviceOntProfileNameIndex  OBJECT-TYPE
        SYNTAX     OCTET STRING (SIZE (1..63))
        MAX-ACCESS  not-accessible
        STATUS      current
        DESCRIPTION
            "Name of the ONT capability set profile."
        ::= { hwEponDeviceOntProfileControlEntry 1 }

    hwEponDeviceOntProfileRefNum  OBJECT-TYPE
        SYNTAX     Integer32
        MAX-ACCESS  read-only
        STATUS      current
        DESCRIPTION
            "Number of references to the ONT capability set profile."
        ::= { hwEponDeviceOntProfileControlEntry 2 }

    hwEponDeviceOntProfileUniConfig  OBJECT-TYPE
        SYNTAX     Integer32
        MAX-ACCESS  read-write
        STATUS      current
        DESCRIPTION
            "Configuration of the UNI interface."
        ::= { hwEponDeviceOntProfileControlEntry 3 }

    hwEponDeviceOntProfilePotsNum  OBJECT-TYPE
        SYNTAX     Integer32
        MAX-ACCESS  read-write
        STATUS      current
        DESCRIPTION
            "Number of POTS ports."
        ::= { hwEponDeviceOntProfileControlEntry 4 }

    hwEponDeviceOntTdmPortType  OBJECT-TYPE
        SYNTAX     Integer32
        MAX-ACCESS  read-write
        STATUS      current
        DESCRIPTION
            "Type of the TDM port."
        ::= { hwEponDeviceOntProfileControlEntry 5 }

    hwEponDeviceOntProfileE1T1Num  OBJECT-TYPE
        SYNTAX     Integer32
        MAX-ACCESS  read-write
        STATUS      current
        DESCRIPTION
            "Number of TDM ports."
        ::= { hwEponDeviceOntProfileControlEntry 6 }

    hwEponDeviceOntProfileRowStatus  OBJECT-TYPE
        SYNTAX     RowStatus
        MAX-ACCESS  read-create
        STATUS      current
        DESCRIPTION
            "Row status. This object is used to differentiate the
             creation, modification and deletion operations for an object.
             Options:
             1. createAndGo(4) -create a new instance of a conceptual row
             2. destroy(6)     -delete the instances associated with an existing conceptual row
            "
        ::= { hwEponDeviceOntProfileControlEntry 7 }

    hwEponDeviceOntGEMap  OBJECT-TYPE
        SYNTAX     PortList
        MAX-ACCESS  read-write
        STATUS      current
        DESCRIPTION
            "GE port bit map of the ONT. The bit map is numbered from 1; the value of the bit map plus the number of FE ports must not exceed 64."
        ::= { hwEponDeviceOntProfileControlEntry 8 }

    hwEponDeviceOntFEMap  OBJECT-TYPE
        SYNTAX     PortList
        MAX-ACCESS  read-write
        STATUS      current
        DESCRIPTION
            "FE port bit map of the ONT. The bit map is numbered from 1; the value of the bit map plus the number of GE ports must not exceed 64."
        ::= { hwEponDeviceOntProfileControlEntry 9 }


    hwEponDeviceOntMode  OBJECT-TYPE
        SYNTAX     INTEGER {
            singalUser (1),
            multiUser (2),
            uplinkUser (3)
        }
        MAX-ACCESS  read-write
        STATUS      current
        DESCRIPTION
            "ONT user mode.
             Options:
             1. singalUser (1) -Indicates a single user
             2. multiUser (2)  -Indicates multiple users
             3. uplinkUser (3) -Indicates the subtending user
            "
        ::= { hwEponDeviceOntProfileControlEntry 10 }

    -- Table 36 : HwEponDeviceOntConfigTable

    hwEponDeviceOntConfigTable OBJECT-TYPE
        SYNTAX     SEQUENCE OF HwEponDeviceOntConfigEntry
        MAX-ACCESS not-accessible
        STATUS     current
        DESCRIPTION
            "ONT configuration table, used for adding, confirming, deleting, and modifying an ONT,
             and also used for modifying and querying other attributes of the ONT.
             The indexes of this table are ifIndex and hwEponDeviceOntObjectIndex.
            "
        ::= { hwGponDeviceControlObjects 36 }

    hwEponDeviceOntConfigEntry OBJECT-TYPE
        SYNTAX     HwEponDeviceOntConfigEntry
        MAX-ACCESS not-accessible
        STATUS     current
        DESCRIPTION
            "ONT configuration table, used for adding, confirming, deleting, and modifying an ONT,
             and also used for modifying and querying other attributes of the ONT.
             The indexes of this entry are ifIndex and hwEponDeviceOntObjectIndex.
            "
        INDEX       { ifIndex, hwEponDeviceOntObjectIndex }
        ::= { hwEponDeviceOntConfigTable 1 }

   HwEponDeviceOntConfigEntry ::=
       SEQUENCE {
               hwEponDeviceOntObjectIndex                    Integer32,
               hwEponDeviceOntObjectCapabProfileName         OCTET STRING,
               hwEponDeviceOntObjectDespt                    OCTET STRING,
               hwEponDeviceOntObjectEntryStatus              RowStatus,
               hwEponDeviceOntObjectMacAddress               MacAddress,
               hwEponDeviceOntObjectVendorId                 OCTET STRING,
               hwEponDeviceOntObjectModel                    Integer32,
               hwEponDeviceOntObjectOntId                    OCTET STRING,
               hwEponDeviceOntObjectHardwareVersion          OCTET STRING,
               hwEponDeviceOntObjectSoftwareVersion          OCTET STRING,
               hwEponDeviceOntObjectOntChipVendorID          OCTET STRING,
               hwEponDeviceOntObjectOntChipModel             Integer32,
               hwEponDeviceOntObjectOntChipVersion           Integer32,
               hwEponDeviceOntObjectOntChipDesignDate        OCTET STRING,
               hwEponDeviceOntObjectOntFirmwareVersion       Integer32,
               hwEponDeviceOntObjectOntChipRevision          Integer32,
               hwEponDeviceOntObjectDownTrafficCirValue      Integer32,
               hwEponDeviceOntObjectUpDbaProfileName         DisplayString,
               hwEponDeviceOntObjectFecEnableFlag            Integer32,
               hwEponDeviceOntObjectEncryptionEnableFlag     Integer32
               }

    hwEponDeviceOntObjectIndex  OBJECT-TYPE
        SYNTAX     Integer32
        MAX-ACCESS   not-accessible
        STATUS      current
        DESCRIPTION
            "ONT-ID."
        ::= { hwEponDeviceOntConfigEntry 1 }

    hwEponDeviceOntObjectCapabProfileName  OBJECT-TYPE
        SYNTAX     OCTET STRING (SIZE (1..63))
        MAX-ACCESS   read-write
        STATUS      current
        DESCRIPTION
            "Name of the capability set profile bound to the ONT."
        ::= { hwEponDeviceOntConfigEntry 2 }

    hwEponDeviceOntObjectDespt  OBJECT-TYPE
        SYNTAX     OCTET STRING (SIZE (1..80))
        MAX-ACCESS   read-write
        STATUS      current
        DESCRIPTION
            "Description of the ONT."
        ::= { hwEponDeviceOntConfigEntry 3 }

    hwEponDeviceOntObjectEntryStatus  OBJECT-TYPE
        SYNTAX     RowStatus
        MAX-ACCESS  read-create
        STATUS      current
        DESCRIPTION
            "Row status. This object is used to differentiate the
             creation, modification and deletion operations for an object.
             Options:
             1. createAndGo(4) -create a new instance of a conceptual row
             2. destroy(6)     -delete the instances associated with an existing conceptual row
            "
        ::= { hwEponDeviceOntConfigEntry 4 }

    hwEponDeviceOntObjectMacAddress   OBJECT-TYPE
        SYNTAX     MacAddress
        MAX-ACCESS  read-write
        STATUS      current
        DESCRIPTION
            "MAC address of the ONT."
        ::= { hwEponDeviceOntConfigEntry 5 }

    hwEponDeviceOntObjectVendorId   OBJECT-TYPE
        SYNTAX     OCTET STRING   (SIZE (1..4))
        MAX-ACCESS  read-only
        STATUS      current
        DESCRIPTION
            "Vendor ID of the ONT."
        ::= { hwEponDeviceOntConfigEntry 6 }

    hwEponDeviceOntObjectModel   OBJECT-TYPE
        SYNTAX     Integer32
        MAX-ACCESS  read-only
        STATUS      current
        DESCRIPTION
            "ONT model."
        ::= { hwEponDeviceOntConfigEntry 7 }

    hwEponDeviceOntObjectOntId   OBJECT-TYPE
        SYNTAX     OCTET STRING   (SIZE (1..6))
        MAX-ACCESS  read-only
        STATUS      current
        DESCRIPTION
            "ONT ID."
        ::= { hwEponDeviceOntConfigEntry 8 }


    hwEponDeviceOntObjectHardwareVersion   OBJECT-TYPE
        SYNTAX     OCTET STRING   (SIZE (1..8))
        MAX-ACCESS  read-only
        STATUS      current
        DESCRIPTION
            "ONT hardware version."
        ::= { hwEponDeviceOntConfigEntry 9 }

    hwEponDeviceOntObjectSoftwareVersion   OBJECT-TYPE
        SYNTAX     OCTET STRING   (SIZE (1..16))
        MAX-ACCESS  read-only
        STATUS      current
        DESCRIPTION
            "ONT software version."
        ::= { hwEponDeviceOntConfigEntry 10 }

    hwEponDeviceOntObjectOntChipVendorID   OBJECT-TYPE
        SYNTAX     OCTET STRING   (SIZE (1..2))
        MAX-ACCESS  read-only
        STATUS      current
        DESCRIPTION
            "Vendor ID of the ONT chip."
        ::= { hwEponDeviceOntConfigEntry 11 }

    hwEponDeviceOntObjectOntChipModel   OBJECT-TYPE
        SYNTAX     Integer32
        MAX-ACCESS  read-only
        STATUS      current
        DESCRIPTION
            "ONT chip model."
        ::= { hwEponDeviceOntConfigEntry 12 }

    hwEponDeviceOntObjectOntChipVersion   OBJECT-TYPE
        SYNTAX     Integer32
        MAX-ACCESS  read-only
        STATUS      current
        DESCRIPTION
            "The verion of the ONT's chip."
        ::= { hwEponDeviceOntConfigEntry 13 }

    hwEponDeviceOntObjectOntChipDesignDate   OBJECT-TYPE
       SYNTAX     OCTET STRING (SIZE (1..3))
       MAX-ACCESS  read-only
       STATUS      current
       DESCRIPTION
           "The design data of the ONT's chip."
       ::= { hwEponDeviceOntConfigEntry 14 }

    hwEponDeviceOntObjectOntFirmwareVersion   OBJECT-TYPE
       SYNTAX     Integer32
       MAX-ACCESS  read-only
       STATUS      current
       DESCRIPTION
           "The firmware version of the ONT's chip."
       ::= { hwEponDeviceOntConfigEntry 15 }

    hwEponDeviceOntObjectOntChipRevision   OBJECT-TYPE
       SYNTAX     Integer32
       MAX-ACCESS  read-only
       STATUS      current
       DESCRIPTION
           "The firmware reversion of the ONT's chip."
       ::= { hwEponDeviceOntConfigEntry 16 }

    hwEponDeviceOntObjectDownTrafficCirValue  OBJECT-TYPE
       SYNTAX     Integer32
       MAX-ACCESS  read-write
       STATUS      current
       DESCRIPTION
           "Index of the downstream CAR table."
       ::= { hwEponDeviceOntConfigEntry 17 }

    hwEponDeviceOntObjectUpDbaProfileName   OBJECT-TYPE
       SYNTAX     DisplayString
       MAX-ACCESS  read-write
       STATUS      current
       DESCRIPTION
           "Index of the DBA profile."
       ::= { hwEponDeviceOntConfigEntry 18 }

    hwEponDeviceOntObjectFecEnableFlag   OBJECT-TYPE
       SYNTAX     Integer32
       MAX-ACCESS  read-write
       STATUS      current
       DESCRIPTION
           "FEC enable flag of the ONT."
       ::= { hwEponDeviceOntConfigEntry 19 }

    hwEponDeviceOntObjectEncryptionEnableFlag   OBJECT-TYPE
       SYNTAX     Integer32
       MAX-ACCESS  read-write
       STATUS      current
       DESCRIPTION
           "Encryption enable flag of the ONT."
       ::= { hwEponDeviceOntConfigEntry 20 }

    --Table 37 :  HwEponDeviceOntControlTable

    hwEponDeviceOntControlTable OBJECT-TYPE
       SYNTAX     SEQUENCE OF HwEponDeviceOntControlEntry
       MAX-ACCESS not-accessible
       STATUS     current
       DESCRIPTION
           "Operation and maintenance table of the ONT, used for activating, deactivating, resetting, and re-registering the ONT, or querying the status of the ONT.
            The indexes of this table are ifIndex and hwEponDeviceOntObjectIndex.
           "
       ::= { hwGponDeviceControlObjects 37 }

    hwEponDeviceOntControlEntry OBJECT-TYPE
       SYNTAX     HwEponDeviceOntControlEntry
       MAX-ACCESS not-accessible
       STATUS     current
       DESCRIPTION
           "Operation and maintenance table of the ONT, used for activating, deactivating, resetting, and re-registering the ONT, or querying the status of the ONT.
            The indexes of this entry are ifIndex and hwEponDeviceOntObjectIndex.
           "
       INDEX       { ifIndex, hwEponDeviceOntObjectIndex }
       ::= { hwEponDeviceOntControlTable 1 }

    HwEponDeviceOntControlEntry ::=
        SEQUENCE {
                hwEponDeviceOntObjectAction                   Integer32,
                hwEponDeviceOntObjectReset                    Integer32,
                hwEponDeviceOntObjectRunStatus                Integer32,
                hwEponDeviceOntObjectConfigStatus             Integer32,
                hwEponDeviceOntObjectReRegister               Integer32,
                hwEponDeviceOntObjectLoopBack                 Integer32,
                hwEponDeviceOntObjectProfileMatchStatus       Integer32,
                hwEponDeviceOntObjectRtt                      Integer32,
                hwEponDeviceOntObjectDistance                 Integer32
                }

    hwEponDeviceOntObjectAction  OBJECT-TYPE
       SYNTAX     Integer32
       MAX-ACCESS   read-write
       STATUS      current
       DESCRIPTION
           "Activation and deactivation of the ONT."
       ::= { hwEponDeviceOntControlEntry 1 }

    hwEponDeviceOntObjectReset  OBJECT-TYPE
       SYNTAX     Integer32
       MAX-ACCESS   read-write
       STATUS      current
       DESCRIPTION
           "Resetting of the ONT."
       ::= { hwEponDeviceOntControlEntry 2 }

    hwEponDeviceOntObjectRunStatus  OBJECT-TYPE
       SYNTAX     Integer32
       MAX-ACCESS   read-write
       STATUS      current
       DESCRIPTION
           "Running status of the ONT."
       ::= { hwEponDeviceOntControlEntry 3 }

   hwEponDeviceOntObjectConfigStatus  OBJECT-TYPE
       SYNTAX     Integer32
       MAX-ACCESS   read-only
       STATUS      current
       DESCRIPTION
           "Configuration status of the ONT."
       ::= { hwEponDeviceOntControlEntry 4 }

   hwEponDeviceOntObjectReRegister  OBJECT-TYPE
       SYNTAX     Integer32
       MAX-ACCESS   read-write
       STATUS      current
       DESCRIPTION
           "Re-registration of the ONT."
       ::= { hwEponDeviceOntControlEntry 5 }

   hwEponDeviceOntObjectLoopBack  OBJECT-TYPE
       SYNTAX     Integer32
       MAX-ACCESS   read-write
       STATUS      current
       DESCRIPTION
           "Configuration of the ONT loopback function."
       ::= { hwEponDeviceOntControlEntry 6 }

   hwEponDeviceOntObjectProfileMatchStatus  OBJECT-TYPE
       SYNTAX     Integer32
       MAX-ACCESS   read-only
       STATUS      current
       DESCRIPTION
           "Profile match status of the ONT."
       ::= { hwEponDeviceOntControlEntry 7 }

   hwEponDeviceOntObjectRtt  OBJECT-TYPE
       SYNTAX     Integer32
       MAX-ACCESS   read-only
       STATUS      current
       DESCRIPTION
           "Rtt value of the ONT."
       ::= { hwEponDeviceOntControlEntry 8 }

    hwEponDeviceOntObjectDistance  OBJECT-TYPE
       SYNTAX     Integer32
       MAX-ACCESS   read-only
       STATUS      current
       DESCRIPTION
           "Actual distance of the ONT."
       ::= { hwEponDeviceOntControlEntry 9 }

    --Table 38 : HwEponDeviceAutoFindOntControlTable

    hwEponDeviceAutoFindOntControlTable OBJECT-TYPE
       SYNTAX     SEQUENCE OF HwEponDeviceAutoFindOntControlEntry
       MAX-ACCESS not-accessible
       STATUS     current
       DESCRIPTION
           "ONT auto-find table, used to query the information about all the ONTs that are automatically found.
            The indexes of this table are ifIndex and hwEponDeviceAutoFindOntIndex.
           "
       ::= { hwGponDeviceControlObjects 38 }

    hwEponDeviceAutoFindOntControlEntry OBJECT-TYPE
       SYNTAX     HwEponDeviceAutoFindOntControlEntry
       MAX-ACCESS not-accessible
       STATUS     current
       DESCRIPTION
           "ONT auto-find table, used to query the information about all the ONTs that are automatically found.
            The indexes of this entry are ifIndex and hwEponDeviceAutoFindOntIndex.
           "
       INDEX       { ifIndex, hwEponDeviceAutoFindOntIndex }
       ::= { hwEponDeviceAutoFindOntControlTable 1 }

    HwEponDeviceAutoFindOntControlEntry ::=
        SEQUENCE {
                hwEponDeviceAutoFindOntIndex                  Integer32,
                hwEponDeviceAutoFindOntMacAddress             MacAddress
                }

    hwEponDeviceAutoFindOntIndex  OBJECT-TYPE
       SYNTAX     Integer32
       MAX-ACCESS   not-accessible
       STATUS      current
       DESCRIPTION
           "Internal serial number in the buffer of the auto-found ONT."
       ::= { hwEponDeviceAutoFindOntControlEntry 1 }

    hwEponDeviceAutoFindOntMacAddress  OBJECT-TYPE
       SYNTAX     MacAddress
       MAX-ACCESS   read-only
       STATUS      current
       DESCRIPTION
           "MAC address of the ONT."
       ::= { hwEponDeviceAutoFindOntControlEntry 2 }

    --Table 39 : HwEponOntVlanObjectTable

    hwEponOntVlanObjectTable OBJECT-TYPE
       SYNTAX     SEQUENCE OF HwEponOntVlanObjectEntry
       MAX-ACCESS not-accessible
       STATUS     current
       DESCRIPTION
           "VLAN management table of the ONT physical port.
            The indexes of this table are ifIndex, hwEponDeviceOntObjectIndex,
            hwEponOntVlanIndex and hwEponOntVlanPortType.
           "
       ::= { hwGponDeviceControlObjects 39 }

    hwEponOntVlanObjectEntry OBJECT-TYPE
       SYNTAX     HwEponOntVlanObjectEntry
       MAX-ACCESS not-accessible
       STATUS     current
       DESCRIPTION
           "VLAN management table of the ONT physical port.
            The indexes of this entry are ifIndex, hwEponDeviceOntObjectIndex,
            hwEponOntVlanIndex and hwEponOntVlanPortType.
           "
       INDEX       { ifIndex, hwEponDeviceOntObjectIndex,
                     hwEponOntVlanIndex, hwEponOntVlanPortType }
       ::= { hwEponOntVlanObjectTable 1 }

    HwEponOntVlanObjectEntry ::=
        SEQUENCE {
                hwEponOntVlanIndex                            VlanIndex,
                hwEponOntVlanPortType                         Integer32,
                hwEponOntVlanRowStatus                        RowStatus,
                hwEponOntVlanPorts                            PortList
                }

    hwEponOntVlanIndex  OBJECT-TYPE
       SYNTAX     VlanIndex
       MAX-ACCESS   not-accessible
       STATUS      current
       DESCRIPTION
           "VLAN index."
       ::= { hwEponOntVlanObjectEntry 1 }

    hwEponOntVlanPortType  OBJECT-TYPE
       SYNTAX     Integer32
       MAX-ACCESS   not-accessible
       STATUS      current
       DESCRIPTION
           "Type of the ONT port."
       ::= { hwEponOntVlanObjectEntry 2 }

    hwEponOntVlanRowStatus  OBJECT-TYPE
       SYNTAX     RowStatus
       MAX-ACCESS   read-create
       STATUS      current
       DESCRIPTION
           "The row status, which is used to differentiate the creation, modification and deletion of a row.
            Options:
            1. createAndGo(4) -create a new instance of a conceptual row
            2. destroy(6)     -delete the instances associated with an existing conceptual row
           "
       ::= { hwEponOntVlanObjectEntry 3 }

    hwEponOntVlanPorts  OBJECT-TYPE
       SYNTAX     PortList
       MAX-ACCESS   read-write
       STATUS      current
       DESCRIPTION
           "Table of physical ports on the ONT added to a VLAN. This table is an 8-byte bit table,
            with totally 64 bits, representing ports 1-63. You can perform operations on only one port at a time.
           "
       ::= { hwEponOntVlanObjectEntry 4 }

    -- Table 40 :  HwEponOntifEthernetObjectTable

    hwEponOntifEthernetObjectTable OBJECT-TYPE
       SYNTAX     SEQUENCE OF HwEponOntifEthernetObjectEntry
       MAX-ACCESS not-accessible
       STATUS     current
       DESCRIPTION
           "ONT physical port management table, used for setting the priority, native VLAN, and other attributes of the port.
            The indexes of this table are ifIndex, hwEponDeviceOntObjectIndex,
            hwEponOntifEthernetType and hwEponOntifEthernetPort.
           "
       ::= { hwGponDeviceControlObjects 40 }

    hwEponOntifEthernetObjectEntry OBJECT-TYPE
       SYNTAX     HwEponOntifEthernetObjectEntry
       MAX-ACCESS not-accessible
       STATUS     current
       DESCRIPTION
           "ONT physical port management table, used for setting the priority, native VLAN, and other attributes of the port.
            The indexes of this entry are ifIndex, hwEponDeviceOntObjectIndex,
            hwEponOntifEthernetType and hwEponOntifEthernetPort.
           "
       INDEX       { ifIndex, hwEponDeviceOntObjectIndex, hwEponOntifEthernetType,
                     hwEponOntifEthernetPort }
       ::= { hwEponOntifEthernetObjectTable 1 }

    HwEponOntifEthernetObjectEntry ::=
        SEQUENCE {
                hwEponOntifEthernetType                       Integer32,
                hwEponOntifEthernetPort                       Integer32,
                hwEponOntPortOperateStatus                    Integer32,
                hwEponOntifEthernetNegotiate                  Integer32,
                hwEponOntifEthernetVlanDefault                Integer32,
                hwEponOntifEthernetOnlineState                Integer32,
                hwEponOntifEthernetPortBckPessureFlag         Integer32,
                hwEponOntifEthernetPortPolicingCIRinKbps      Integer32,
                hwEponOntifEthernetPortPolicingCBSinBytes     Integer32,
                hwEponOntifEthernetPortPolicingEBSinBytes     Integer32,
                hwEponOntifEthernetPortMulticastStripFlag     Integer32
                }

    hwEponOntifEthernetType  OBJECT-TYPE
       SYNTAX     Integer32
       MAX-ACCESS   not-accessible
       STATUS      current
       DESCRIPTION
           "Index of the port type."
       ::= { hwEponOntifEthernetObjectEntry 1 }

    hwEponOntifEthernetPort  OBJECT-TYPE
       SYNTAX     Integer32
       MAX-ACCESS   not-accessible
       STATUS      current
       DESCRIPTION
           "Index of the port ID."
       ::= { hwEponOntifEthernetObjectEntry 2 }

    hwEponOntPortOperateStatus  OBJECT-TYPE
       SYNTAX     Integer32
       MAX-ACCESS   read-write
       STATUS      current
       DESCRIPTION
           "Operation status of the port."
       ::= { hwEponOntifEthernetObjectEntry 3 }

    hwEponOntifEthernetNegotiate  OBJECT-TYPE
       SYNTAX     Integer32
       MAX-ACCESS   read-write
       STATUS      current
       DESCRIPTION
           "Auto-negotiation switch."
       ::= { hwEponOntifEthernetObjectEntry 4 }


   hwEponOntifEthernetVlanDefault  OBJECT-TYPE
       SYNTAX     Integer32
       MAX-ACCESS   read-write
       STATUS      current
       DESCRIPTION
           "Native VLANs for the ONT ports."
       ::= { hwEponOntifEthernetObjectEntry 5 }


   hwEponOntifEthernetOnlineState  OBJECT-TYPE
       SYNTAX     Integer32
       MAX-ACCESS   read-only
       STATUS      current
       DESCRIPTION
           "ONT ETH port status."
       ::= { hwEponOntifEthernetObjectEntry 6 }

   hwEponOntifEthernetPortBckPessureFlag  OBJECT-TYPE
       SYNTAX     Integer32
       MAX-ACCESS   read-write
       STATUS      current
       DESCRIPTION
           "Back pressure flag."
       ::= { hwEponOntifEthernetObjectEntry 8 }

    hwEponOntifEthernetPortPolicingCIRinKbps   OBJECT-TYPE
       SYNTAX     Integer32
       MAX-ACCESS   read-write
       STATUS      current
       DESCRIPTION
           "Committed rate of the port."
       ::= { hwEponOntifEthernetObjectEntry 9 }


   hwEponOntifEthernetPortPolicingCBSinBytes  OBJECT-TYPE
       SYNTAX     Integer32
       MAX-ACCESS   read-write
       STATUS      current
       DESCRIPTION
           "Burst size of the port."
       ::= { hwEponOntifEthernetObjectEntry 10 }

   hwEponOntifEthernetPortPolicingEBSinBytes  OBJECT-TYPE
       SYNTAX     Integer32
       MAX-ACCESS   read-write
       STATUS      current
       DESCRIPTION
           "Excess burst size of the packets with the high priority."
       ::= { hwEponOntifEthernetObjectEntry 11 }

    hwEponOntifEthernetPortMulticastStripFlag  OBJECT-TYPE
       SYNTAX     Integer32
       MAX-ACCESS   read-write
       STATUS      current
       DESCRIPTION
           "Flag for whether the multicast VLAN tag on the ONT is stripped."
       ::= { hwEponOntifEthernetObjectEntry 12 }


   --Table 41 :  HwEponOntE1PortCfgTable

    hwEponOntE1PortCfgTable OBJECT-TYPE
       SYNTAX     SEQUENCE OF HwEponOntE1PortCfgEntry
       MAX-ACCESS not-accessible
       STATUS     current
       DESCRIPTION
           "E1 port attribute table.
            The indexes of this table are ifIndex, hwGponDeviceOntObjectIndex,
            and hwEponOntE1PortId.
           "
       ::= { hwGponDeviceControlObjects 41 }

    hwEponOntE1PortCfgEntry OBJECT-TYPE
       SYNTAX     HwEponOntE1PortCfgEntry
       MAX-ACCESS not-accessible
       STATUS     current
       DESCRIPTION
           "E1 port attribute table.
            The indexes of this entry are ifIndex, hwGponDeviceOntObjectIndex,
            and hwEponOntE1PortId.
           "
       INDEX       { ifIndex, hwGponDeviceOntObjectIndex, hwEponOntE1PortId }
       ::= { hwEponOntE1PortCfgTable 1 }

    HwEponOntE1PortCfgEntry ::=
        SEQUENCE {
                hwEponOntE1PortId                             Integer32,
                hwEponOntE1PortOperateStatus                  Integer32
                }

    hwEponOntE1PortId  OBJECT-TYPE
       SYNTAX     Integer32
       MAX-ACCESS   not-accessible
       STATUS      current
       DESCRIPTION
           "ID of the E1 port."
       ::= { hwEponOntE1PortCfgEntry 1 }

    hwEponOntE1PortOperateStatus  OBJECT-TYPE
       SYNTAX     Integer32
       MAX-ACCESS   read-write
       STATUS      current
       DESCRIPTION
           "Operation status of the port."
       ::= { hwEponOntE1PortCfgEntry 2 }

    -- Table 42 :  HwEponOntELPortStatsTable

    hwEponOntELPortStatsTable OBJECT-TYPE
       SYNTAX     SEQUENCE OF HwEponOntELPortStatsEntry
       MAX-ACCESS not-accessible
       STATUS     current
       DESCRIPTION
           "EL port statistics table.
            The indexes of this table are ifIndex
            and hwEponDeviceOntObjectIndex.
           "
       ::= { hwGponDeviceControlObjects 42 }

    hwEponOntELPortStatsEntry OBJECT-TYPE
       SYNTAX     HwEponOntELPortStatsEntry
       MAX-ACCESS not-accessible
       STATUS     current
       DESCRIPTION
           "EL port statistics table.
            The indexes of this entry are ifIndex
            and hwEponDeviceOntObjectIndex.
           "
       INDEX       { ifIndex, hwEponDeviceOntObjectIndex }
       ::= { hwEponOntELPortStatsTable 1 }

    HwEponOntELPortStatsEntry ::=
        SEQUENCE {
                hwEponELportOltUpPqFrameNum                   Counter32,
                hwEponELportOltUpPqByteNum                    Counter32,
                hwEponELportOltDownPqFrameNum                 Counter32,
                hwEponELportOltDownPqByteNum                  Counter32,
                hwEponELportOltRecFrameLittMinNum             Counter32,
                hwEponELportOltRecFrameBiggerMaxNum           Counter32,
                hwEponELportRecErrFCSNum                      Counter32,
                hwEponELportRecErrByteNum                     Counter32,
                hwEponELportRecByteUsefulNum                  Counter64,
                hwEponELportRecSumByteNum                     Counter64,
                hwEponELportRecErrFrameNum                    Counter32,
                hwEponELportRecRightFrameNum                  Counter32,
                hwEponOntRecErrFCSNum                         Counter32,
                hwEponOntRecRightPacketNum                    Counter32,
                hwEponOntTranRightPacketNum                   Counter32,
                hwEponOntSysRecErrFCSPacketNum                Counter32,
                hwEponOntSysRecRightPacketNum                 Counter32,
                hwEponOntSysTranRightPacketNum                Counter32,
                hwEponOntRecErrByteNum                        Counter64,
                hwEponOntRecRightByteNum                      Counter64,
                hwEponOntTranRightByteNum                     Counter64,
                hwEponOntSysRecErrByteNum                     Counter64,
                hwEponOntSysRecRightByteNum                   Counter64,
                hwEponOntSysTranRightByteNum                  Counter64,
                hwEponOntRecErrHECFrameNum                    Counter32,
                hwEponOntRecNotSupportMPCPFrameNum            Counter32,
                hwEponOntRecSuccOAMFrameNum                   Counter32,
                hwEponOntTranSuccOAMFrameNum                  Counter32,
                hwEponOntRecNotSupportOAMFrameNum             Counter32,
                hwEponOntTransFramesNumWithPri0               Counter32,
                hwEponOntTransFramesNumWithPri1               Counter32,
                hwEponOntTransFramesNumWithPri2               Counter32,
                hwEponOntTransFramesNumWithPri3               Counter32,
                hwEponOntTransFramesNumWithPri4               Counter32,
                hwEponOntTransFramesNumWithPri5               Counter32,
                hwEponOntTransFramesNumWithPri6               Counter32,
                hwEponOntTransFramesNumWithPri7               Counter32,
                hwEponOntELPortStatsClear                     INTEGER
                }

    hwEponELportOltUpPqFrameNum  OBJECT-TYPE
       SYNTAX     Counter32
       MAX-ACCESS   read-only
       STATUS      current
       DESCRIPTION
           "Number of forwarded frames on the upstream PQ on the OLT side."
       ::= { hwEponOntELPortStatsEntry 1 }

    hwEponELportOltUpPqByteNum  OBJECT-TYPE
       SYNTAX     Counter32
       MAX-ACCESS   read-only
       STATUS      current
       DESCRIPTION
           "Number of forwarded bytes on the upstream PQ on the OLT side."
       ::= { hwEponOntELPortStatsEntry 2 }

    hwEponELportOltDownPqFrameNum  OBJECT-TYPE
       SYNTAX     Counter32
       MAX-ACCESS   read-only
       STATUS      current
       DESCRIPTION
           "Number of forwarded frames on the downstream PQ on the OLT side."
       ::= { hwEponOntELPortStatsEntry 3 }

    hwEponELportOltDownPqByteNum  OBJECT-TYPE
       SYNTAX     Counter32
       MAX-ACCESS   read-only
       STATUS      current
       DESCRIPTION
           "Number of forwarded bytes on the downstream PQ on the OLT side."
       ::= { hwEponOntELPortStatsEntry 4 }

    hwEponELportOltRecFrameLittMinNum  OBJECT-TYPE
       SYNTAX     Counter32
       MAX-ACCESS   read-only
       STATUS      current
       DESCRIPTION
           "Number of frames received by the OLT that are shorter than the minimum frame length."
       ::= { hwEponOntELPortStatsEntry 5 }

    hwEponELportOltRecFrameBiggerMaxNum  OBJECT-TYPE
       SYNTAX     Counter32
       MAX-ACCESS   read-only
       STATUS      current
       DESCRIPTION
           "Number of frames received by the OLT that are longer than the maximum frame length."
       ::= { hwEponOntELPortStatsEntry 6 }
    hwEponELportRecErrFCSNum   OBJECT-TYPE
       SYNTAX     Counter32
       MAX-ACCESS   read-only
       STATUS      current
       DESCRIPTION
           "Number of frames with FCS errors."
       ::= { hwEponOntELPortStatsEntry 7 }

    hwEponELportRecErrByteNum  OBJECT-TYPE
       SYNTAX     Counter32
       MAX-ACCESS   read-only
       STATUS      current
       DESCRIPTION
           "Number of received error bytes."
       ::= { hwEponOntELPortStatsEntry 8 }

    hwEponELportRecByteUsefulNum  OBJECT-TYPE
       SYNTAX     Counter64
       MAX-ACCESS   read-only
       STATUS      current
       DESCRIPTION
           "Number of received available bytes."
       ::= { hwEponOntELPortStatsEntry 9 }

    hwEponELportRecSumByteNum  OBJECT-TYPE
       SYNTAX     Counter64
       MAX-ACCESS   read-only
       STATUS      current
       DESCRIPTION
           "Total number of received correct bytes."
       ::= { hwEponOntELPortStatsEntry 10 }

    hwEponELportRecErrFrameNum  OBJECT-TYPE
       SYNTAX     Counter32
       MAX-ACCESS   read-only
       STATUS      current
       DESCRIPTION
           "Number of received error frames."
       ::= { hwEponOntELPortStatsEntry 11 }

    hwEponELportRecRightFrameNum  OBJECT-TYPE
       SYNTAX     Counter32
       MAX-ACCESS   read-only
       STATUS      current
       DESCRIPTION
           "Number of received correct frames."
       ::= { hwEponOntELPortStatsEntry 12 }

    hwEponOntRecErrFCSNum  OBJECT-TYPE
       SYNTAX     Counter32
       MAX-ACCESS   read-only
       STATUS      current
       DESCRIPTION
           "Number of FCS error packets received by the ONT PON port."
       ::= { hwEponOntELPortStatsEntry 13 }

    hwEponOntRecRightPacketNum  OBJECT-TYPE
       SYNTAX     Counter32
       MAX-ACCESS   read-only
       STATUS      current
       DESCRIPTION
           "Number of correct packets received by the ONT PON port."
       ::= { hwEponOntELPortStatsEntry 14 }

    hwEponOntTranRightPacketNum  OBJECT-TYPE
       SYNTAX     Counter32
       MAX-ACCESS   read-only
       STATUS      current
       DESCRIPTION
           "Number of packets transmitted by the ONT PON port."
       ::= { hwEponOntELPortStatsEntry 15 }

    hwEponOntSysRecErrFCSPacketNum  OBJECT-TYPE
       SYNTAX     Counter32
       MAX-ACCESS   read-only
       STATUS      current
       DESCRIPTION
           "Number of packets with FCS errors received by the ONT system."
       ::= { hwEponOntELPortStatsEntry 16 }

    hwEponOntSysRecRightPacketNum  OBJECT-TYPE
       SYNTAX     Counter32
       MAX-ACCESS   read-only
       STATUS      current
       DESCRIPTION
           "Number of correct packets received by the ONT system."
       ::= { hwEponOntELPortStatsEntry 17 }

    hwEponOntSysTranRightPacketNum  OBJECT-TYPE
       SYNTAX     Counter32
       MAX-ACCESS   read-only
       STATUS      current
       DESCRIPTION
           "Number of packets transmitted by the ONT system."
       ::= { hwEponOntELPortStatsEntry 18 }

    hwEponOntRecErrByteNum  OBJECT-TYPE
       SYNTAX     Counter64
       MAX-ACCESS   read-only
       STATUS      current
       DESCRIPTION
           "Number of bytes of the error packets received by the ONT PON port."
       ::= { hwEponOntELPortStatsEntry 19 }

    hwEponOntRecRightByteNum  OBJECT-TYPE
       SYNTAX     Counter64
       MAX-ACCESS   read-only
       STATUS      current
       DESCRIPTION
           "Number of bytes of the correct packets received by the ONT PON port."
       ::= { hwEponOntELPortStatsEntry 20 }

    hwEponOntTranRightByteNum  OBJECT-TYPE
       SYNTAX     Counter64
       MAX-ACCESS   read-only
       STATUS      current
       DESCRIPTION
           "Number of bytes of the packets transmitted by the ONT PON port."
       ::= { hwEponOntELPortStatsEntry 21 }

    hwEponOntSysRecErrByteNum  OBJECT-TYPE
       SYNTAX     Counter64
       MAX-ACCESS   read-only
       STATUS      current
       DESCRIPTION
           "Number of bytes of the error packets received by the ONT system."
       ::= { hwEponOntELPortStatsEntry 22 }

    hwEponOntSysRecRightByteNum  OBJECT-TYPE
       SYNTAX     Counter64
       MAX-ACCESS   read-only
       STATUS      current
       DESCRIPTION
           "Number of bytes of the correct packets received by the ONT system."
       ::= { hwEponOntELPortStatsEntry 23 }

    hwEponOntSysTranRightByteNum  OBJECT-TYPE
       SYNTAX     Counter64
       MAX-ACCESS   read-only
       STATUS      current
       DESCRIPTION
           "Number of bytes of the packets transmitted by the ONT system."
       ::= { hwEponOntELPortStatsEntry 24 }

   hwEponOntRecErrHECFrameNum  OBJECT-TYPE
       SYNTAX     Counter32
       MAX-ACCESS   read-only
       STATUS      current
       DESCRIPTION
           "Number of received frames with the HEC errors."
       ::= { hwEponOntELPortStatsEntry 25 }

    hwEponOntRecNotSupportMPCPFrameNum  OBJECT-TYPE
       SYNTAX     Counter32
       MAX-ACCESS   read-only
       STATUS      current
       DESCRIPTION
           "Number of received unsupported MPCP frames."
       ::= { hwEponOntELPortStatsEntry 26 }

    hwEponOntRecSuccOAMFrameNum  OBJECT-TYPE
       SYNTAX     Counter32
       MAX-ACCESS   read-only
       STATUS      current
       DESCRIPTION
           "Number of received OAM frames."
       ::= { hwEponOntELPortStatsEntry 27 }

   hwEponOntTranSuccOAMFrameNum  OBJECT-TYPE
       SYNTAX     Counter32
       MAX-ACCESS   read-only
       STATUS      current
       DESCRIPTION
           "Number of sent OAM frames."
       ::= { hwEponOntELPortStatsEntry 28 }

    hwEponOntRecNotSupportOAMFrameNum  OBJECT-TYPE
       SYNTAX     Counter32
       MAX-ACCESS   read-only
       STATUS      current
       DESCRIPTION
           "Number of received unsupported OAM frames."
       ::= { hwEponOntELPortStatsEntry 29 }

    hwEponOntTransFramesNumWithPri0  OBJECT-TYPE
       SYNTAX     Counter32
       MAX-ACCESS   read-only
       STATUS      current
       DESCRIPTION
           "Number of frames with priority 0 sent by the PON port."
       ::= { hwEponOntELPortStatsEntry 30 }

   hwEponOntTransFramesNumWithPri1  OBJECT-TYPE
       SYNTAX     Counter32
       MAX-ACCESS   read-only
       STATUS      current
       DESCRIPTION
           "Number of frames with priority 1 sent by the PON port."
       ::= { hwEponOntELPortStatsEntry 31 }

    hwEponOntTransFramesNumWithPri2  OBJECT-TYPE
       SYNTAX     Counter32
       MAX-ACCESS   read-only
       STATUS      current
       DESCRIPTION
           "Number of frames with priority 2 sent by the PON port."
       ::= { hwEponOntELPortStatsEntry 32 }

    hwEponOntTransFramesNumWithPri3  OBJECT-TYPE
       SYNTAX     Counter32
       MAX-ACCESS   read-only
       STATUS      current
       DESCRIPTION
           "Number of frames with priority 3 sent by the PON port."
       ::= { hwEponOntELPortStatsEntry 33 }

   hwEponOntTransFramesNumWithPri4  OBJECT-TYPE
       SYNTAX     Counter32
       MAX-ACCESS   read-only
       STATUS      current
       DESCRIPTION
           "Number of frames with priority 4 sent by the PON port."
       ::= { hwEponOntELPortStatsEntry 34 }

    hwEponOntTransFramesNumWithPri5   OBJECT-TYPE
       SYNTAX     Counter32
       MAX-ACCESS   read-only
       STATUS      current
       DESCRIPTION
           "Number of frames with priority 5 sent by the PON port."
       ::= { hwEponOntELPortStatsEntry 35 }

    hwEponOntTransFramesNumWithPri6  OBJECT-TYPE
       SYNTAX     Counter32
       MAX-ACCESS   read-only
       STATUS      current
       DESCRIPTION
           "Number of frames with priority 6 sent by the PON port."
       ::= { hwEponOntELPortStatsEntry 36 }

   hwEponOntTransFramesNumWithPri7  OBJECT-TYPE
       SYNTAX     Counter32
       MAX-ACCESS   read-only
       STATUS      current
       DESCRIPTION
           "Number of frames with priority 7 sent by the PON port."
       ::= { hwEponOntELPortStatsEntry 37 }


    hwEponOntELPortStatsClear  OBJECT-TYPE
       SYNTAX   INTEGER {
           clear(1)
           }
       MAX-ACCESS   read-write
       STATUS      current
       DESCRIPTION
           "Clearing of the performance statistics.
            Options:
            1. clear(1) - Clearing of the performance statistics
           "
       ::= { hwEponOntELPortStatsEntry 38 }


    -- Table 43 : HwEponOltStatsTable

    hwEponOltStatsTable OBJECT-TYPE
       SYNTAX     SEQUENCE OF HwEponOltStatsEntry
       MAX-ACCESS not-accessible
       STATUS     current
       DESCRIPTION
           "PON port traffic statistics table.
            The index of this table is ifIndex.
           "
       ::= { hwGponDeviceControlObjects 43 }

    hwEponOltStatsEntry OBJECT-TYPE
       SYNTAX     HwEponOltStatsEntry
       MAX-ACCESS not-accessible
       STATUS     current
       DESCRIPTION
           "PON port traffic statistics table.
            The index of this entry is ifIndex.
           "
       INDEX       { ifIndex  }
       ::= { hwEponOltStatsTable 1 }

    HwEponOltStatsEntry ::=
        SEQUENCE {
                hwEponOltRecvRightPackNumh                    Counter32,
                hwEponOltRecvRightPackNuml                    Counter32,
                hwEponOltRecvErrPackNumh                      Counter32,
                hwEponOltRecvErrPackNuml                      Counter32,
                hwEponOltTranRightPackNumh                    Counter32,
                hwEponOltTranRightPackNuml                    Counter32,
                hwEponOltRecvRightByteNum                     Counter64,
                hwEponOltRecvErrByteNum                       Counter64,
                hwEponOltTranRightByteNum                     Counter64,
                hwEponOltSysRecvRightPackNumh                 Counter32,
                hwEponOltSysRecvRightPackNuml                 Counter32,
                hwEponOltSysRecvErrPackNumh                   Counter32,
                hwEponOltSysRecvErrPackNuml                   Counter32,
                hwEponOltSysTranRightPackNumh                 Counter32,
                hwEponOltSysTranRightPackNuml                 Counter32,
                hwEponOltSysRecvRightByteNum                  Counter64,
                hwEponOltSysRecvErrByteNum                    Counter64,
                hwEponOltSysTranRightByteNum                  Counter64,
                hwEponOltRevcFramLenLittMinNum                Counter32,
                hwEponOltSysRevcFramLenLittMinNum             Counter32,
                hwEponOltRevcFramLenBiggerMaxNum              Counter32,
                hwEponOltSysRevcFramLenBiggerMaxNum           Counter32,
                hwEponOltRevcErrHecFrameNum                   Counter32,
                hwEponOltDownStreamDropRightFrameNum          Counter32,
                hwEponOltUpStreamDropRightFrameNum            Counter32,
                hwEponOltDownStreamDropRightByteNumh          Counter32,
                hwEponOltDownStreamDropRightByteNuml          Counter32,
                hwEponOltUpStreamDropRightFrameNumh           Counter32,
                hwEponOltUpStreamDropRightFrameNuml           Counter32,
                hwEponOltTranFramesNumWithPri0                Counter32,
                hwEponOltTranFramesNumWithPri1                Counter32,
                hwEponOltTranFramesNumWithPri2                Counter32,
                hwEponOltTranFramesNumWithPri3                Counter32,
                hwEponOltTranFramesNumWithPri4                Counter32,
                hwEponOltTranFramesNumWithPri5                Counter32,
                hwEponOltTranFramesNumWithPri6                Counter32,
                hwEponOltTranFramesNumWithPri7                Counter32,
                hwEponOltRecvFramesNumWithPri0                Counter32,
                hwEponOltRecvFramesNumWithPri1                Counter32,
                hwEponOltRecvFramesNumWithPri2                Counter32,
                hwEponOltRecvFramesNumWithPri3                Counter32,
                hwEponOltRecvFramesNumWithPri4                Counter32,
                hwEponOltRecvFramesNumWithPri5                Counter32,
                hwEponOltRecvFramesNumWithPri6                Counter32,
                hwEponOltRecvFramesNumWithPri7                Counter32,
                hwEponOltTranBytesNumWithPri0                 Counter32,
                hwEponOltTranBytesNumWithPri1                 Counter32,
                hwEponOltTranBytesNumWithPri2                 Counter32,
                hwEponOltTranBytesNumWithPri3                 Counter32,
                hwEponOltTranBytesNumWithPri4                 Counter32,
                hwEponOltTranBytesNumWithPri5                 Counter32,
                hwEponOltTranBytesNumWithPri6                 Counter32,
                hwEponOltTranBytesNumWithPri7                 Counter32,
                hwEponOltRecvBytesNumWithPri0                 Counter32,
                hwEponOltRecvBytesNumWithPri1                 Counter32,
                hwEponOltRecvBytesNumWithPri2                 Counter32,
                hwEponOltRecvBytesNumWithPri3                 Counter32,
                hwEponOltRecvBytesNumWithPri4                 Counter32,
                hwEponOltRecvBytesNumWithPri5                 Counter32,
                hwEponOltRecvBytesNumWithPri6                 Counter32,
                hwEponOltRecvBytesNumWithPri7                 Counter32,
                hwEponOltStatsClear                           INTEGER
                }

    hwEponOltRecvRightPackNumh  OBJECT-TYPE
       SYNTAX     Counter32
       MAX-ACCESS   read-only
       STATUS      current
       DESCRIPTION
           "Number (higher four bytes) of correct packets received by the PON port."
       ::= { hwEponOltStatsEntry 1 }

    hwEponOltRecvRightPackNuml  OBJECT-TYPE
       SYNTAX     Counter32
       MAX-ACCESS   read-only
       STATUS      current
       DESCRIPTION
           "Number (lower four bytes) of correct packets received by the PON port."
       ::= { hwEponOltStatsEntry 2 }

   hwEponOltRecvErrPackNumh  OBJECT-TYPE
       SYNTAX     Counter32
       MAX-ACCESS   read-only
       STATUS      current
       DESCRIPTION
           "Number (higher four bytes) of error packets received by the PON port."
       ::= { hwEponOltStatsEntry 3 }

   hwEponOltRecvErrPackNuml  OBJECT-TYPE
       SYNTAX     Counter32
       MAX-ACCESS   read-only
       STATUS      current
       DESCRIPTION
           "Number (lower four bytes) of error packets received by the PON port."
       ::= { hwEponOltStatsEntry 4 }

   hwEponOltTranRightPackNumh   OBJECT-TYPE
       SYNTAX     Counter32
       MAX-ACCESS   read-only
       STATUS      current
       DESCRIPTION
           "Number (higher four bytes) of correct packets sent by the PON port."
       ::= { hwEponOltStatsEntry 5 }

   hwEponOltTranRightPackNuml   OBJECT-TYPE
       SYNTAX     Counter32
       MAX-ACCESS   read-only
       STATUS      current
       DESCRIPTION
           "Number (lower four bytes) of correct packets sent by the PON port."
       ::= { hwEponOltStatsEntry 6 }

    hwEponOltRecvRightByteNum  OBJECT-TYPE
       SYNTAX     Counter64
       MAX-ACCESS   read-only
       STATUS      current
       DESCRIPTION
           "Number of bytes of the correct packets received by the PON port."
       ::= { hwEponOltStatsEntry 7 }

    hwEponOltRecvErrByteNum   OBJECT-TYPE
       SYNTAX     Counter64
       MAX-ACCESS   read-only
       STATUS      current
       DESCRIPTION
           "Number of bytes of the error packets received by the PON port."
       ::= { hwEponOltStatsEntry 8 }

   hwEponOltTranRightByteNum  OBJECT-TYPE
       SYNTAX     Counter64
       MAX-ACCESS   read-only
       STATUS      current
       DESCRIPTION
           "Number of bytes of the correct packets sent by the PON port."
       ::= { hwEponOltStatsEntry 9 }

   hwEponOltSysRecvRightPackNumh  OBJECT-TYPE
       SYNTAX     Counter32
       MAX-ACCESS   read-only
       STATUS      current
       DESCRIPTION
           "Number (higher four bytes) of correct packets received by the system."
       ::= { hwEponOltStatsEntry 10 }

   hwEponOltSysRecvRightPackNuml  OBJECT-TYPE
       SYNTAX     Counter32
       MAX-ACCESS   read-only
       STATUS      current
       DESCRIPTION
           "Number (lower four bytes) of correct packets received by the system."
       ::= { hwEponOltStatsEntry 11 }

   hwEponOltSysRecvErrPackNumh   OBJECT-TYPE
       SYNTAX     Counter32
       MAX-ACCESS   read-only
       STATUS      current
       DESCRIPTION
           "Number (higher four bytes) of error packets received by the system."
       ::= { hwEponOltStatsEntry 12 }

    hwEponOltSysRecvErrPackNuml  OBJECT-TYPE
       SYNTAX     Counter32
       MAX-ACCESS   read-only
       STATUS      current
       DESCRIPTION
           "Number (lower four bytes) of error packets received by the system."
       ::= { hwEponOltStatsEntry 13 }

    hwEponOltSysTranRightPackNumh  OBJECT-TYPE
       SYNTAX     Counter32
       MAX-ACCESS   read-only
       STATUS      current
       DESCRIPTION
           "Number (higher four bytes) of correct packets sent by the system."
       ::= { hwEponOltStatsEntry 14 }

   hwEponOltSysTranRightPackNuml  OBJECT-TYPE
       SYNTAX     Counter32
       MAX-ACCESS   read-only
       STATUS      current
       DESCRIPTION
           "Number (lower four bytes) of correct packets sent by the system."
       ::= { hwEponOltStatsEntry 15 }

   hwEponOltSysRecvRightByteNum   OBJECT-TYPE
       SYNTAX     Counter64
       MAX-ACCESS   read-only
       STATUS      current
       DESCRIPTION
           "Number of bytes of the correct packets received by the system."
       ::= { hwEponOltStatsEntry 16 }

   hwEponOltSysRecvErrByteNum  OBJECT-TYPE
       SYNTAX     Counter64
       MAX-ACCESS   read-only
       STATUS      current
       DESCRIPTION
           "Number of bytes of the error packets received by the system."
       ::= { hwEponOltStatsEntry 17 }

   hwEponOltSysTranRightByteNum  OBJECT-TYPE
       SYNTAX     Counter64
       MAX-ACCESS   read-only
       STATUS      current
       DESCRIPTION
           "Number of bytes of the correct packets sent by the system."
       ::= { hwEponOltStatsEntry 18 }

    hwEponOltRevcFramLenLittMinNum  OBJECT-TYPE
       SYNTAX     Counter32
       MAX-ACCESS   read-only
       STATUS      current
       DESCRIPTION
           "Number of frames received by the PON port that are shorter than the minimum frame length."
       ::= { hwEponOltStatsEntry 19 }

    hwEponOltSysRevcFramLenLittMinNum  OBJECT-TYPE
       SYNTAX     Counter32
       MAX-ACCESS   read-only
       STATUS      current
       DESCRIPTION
           "Number of frames received by the system that are shorter than the minimum frame length."
       ::= { hwEponOltStatsEntry 20 }

   hwEponOltRevcFramLenBiggerMaxNum  OBJECT-TYPE
       SYNTAX     Counter32
       MAX-ACCESS   read-only
       STATUS      current
       DESCRIPTION
           "Number of frames received by the PON port that are longer than the maximum frame length."
       ::= { hwEponOltStatsEntry 21 }

   hwEponOltSysRevcFramLenBiggerMaxNum  OBJECT-TYPE
       SYNTAX     Counter32
       MAX-ACCESS   read-only
       STATUS      current
       DESCRIPTION
           "Number of frames received by the system that are longer than the maximum frame length."
       ::= { hwEponOltStatsEntry 22 }

   hwEponOltRevcErrHecFrameNum  OBJECT-TYPE
       SYNTAX     Counter32
       MAX-ACCESS   read-only
       STATUS      current
       DESCRIPTION
           "Number of frames with the HEC errors received by the PON port."
       ::= { hwEponOltStatsEntry 23 }

   hwEponOltDownStreamDropRightFrameNum  OBJECT-TYPE
       SYNTAX     Counter32
       MAX-ACCESS   read-only
       STATUS      current
       DESCRIPTION
           "Number of discarded frames of the downstream correct packets."
       ::= { hwEponOltStatsEntry 24 }

    hwEponOltUpStreamDropRightFrameNum  OBJECT-TYPE
       SYNTAX     Counter32
       MAX-ACCESS   read-only
       STATUS      current
       DESCRIPTION
           "Number of discarded frames of the upstream correct packets."
       ::= { hwEponOltStatsEntry 25 }

    hwEponOltDownStreamDropRightByteNumh  OBJECT-TYPE
       SYNTAX     Counter32
       MAX-ACCESS   read-only
       STATUS      current
       DESCRIPTION
           "Number (higher four bytes) of discarded bytes of the downstream correct packet."
       ::= { hwEponOltStatsEntry 26 }

   hwEponOltDownStreamDropRightByteNuml  OBJECT-TYPE
       SYNTAX     Counter32
       MAX-ACCESS   read-only
       STATUS      current
       DESCRIPTION
           "Number (lower four bytes) of discarded bytes of the downstream correct packet."
       ::= { hwEponOltStatsEntry 27 }

   hwEponOltUpStreamDropRightFrameNumh  OBJECT-TYPE
       SYNTAX     Counter32
       MAX-ACCESS   read-only
       STATUS      current
       DESCRIPTION
           "Number (higher four bytes) of discarded bytes of the upstream correct packets."
       ::= { hwEponOltStatsEntry 28 }

   hwEponOltUpStreamDropRightFrameNuml  OBJECT-TYPE
       SYNTAX     Counter32
       MAX-ACCESS   read-only
       STATUS      current
       DESCRIPTION
           "Number (lower four bytes) of discarded bytes of the upstream correct packets."
       ::= { hwEponOltStatsEntry 29 }

   hwEponOltTranFramesNumWithPri0  OBJECT-TYPE
       SYNTAX     Counter32
       MAX-ACCESS   read-only
       STATUS      current
       DESCRIPTION
           "Number of frames with priority 0 sent by the PON port."
       ::= { hwEponOltStatsEntry 30 }

    hwEponOltTranFramesNumWithPri1  OBJECT-TYPE
       SYNTAX     Counter32
       MAX-ACCESS   read-only
       STATUS      current
       DESCRIPTION
           "Number of frames with priority 1 sent by the PON port."
       ::= { hwEponOltStatsEntry 31 }

    hwEponOltTranFramesNumWithPri2   OBJECT-TYPE
       SYNTAX     Counter32
       MAX-ACCESS   read-only
       STATUS      current
       DESCRIPTION
           "Number of frames with priority 2 sent by the PON port."
       ::= { hwEponOltStatsEntry 32 }

   hwEponOltTranFramesNumWithPri3  OBJECT-TYPE
       SYNTAX     Counter32
       MAX-ACCESS   read-only
       STATUS      current
       DESCRIPTION
           "Number of frames with priority 3 sent by the PON port."
       ::= { hwEponOltStatsEntry 33 }

   hwEponOltTranFramesNumWithPri4   OBJECT-TYPE
       SYNTAX     Counter32
       MAX-ACCESS   read-only
       STATUS      current
       DESCRIPTION
           "Number of frames with priority 4 sent by the PON port."
       ::= { hwEponOltStatsEntry 34 }

   hwEponOltTranFramesNumWithPri5  OBJECT-TYPE
       SYNTAX     Counter32
       MAX-ACCESS   read-only
       STATUS      current
       DESCRIPTION
           "Number of frames with priority 5 sent by the PON port."
       ::= { hwEponOltStatsEntry 35 }

   hwEponOltTranFramesNumWithPri6  OBJECT-TYPE
       SYNTAX     Counter32
       MAX-ACCESS   read-only
       STATUS      current
       DESCRIPTION
           "Number of frames with priority 6 sent by the PON port."
       ::= { hwEponOltStatsEntry 36 }

    hwEponOltTranFramesNumWithPri7  OBJECT-TYPE
       SYNTAX     Counter32
       MAX-ACCESS   read-only
       STATUS      current
       DESCRIPTION
           "Number of frames with priority 7 sent by the PON port."
       ::= { hwEponOltStatsEntry 37 }

    hwEponOltRecvFramesNumWithPri0  OBJECT-TYPE
       SYNTAX     Counter32
       MAX-ACCESS   read-only
       STATUS      current
       DESCRIPTION
           "Number of frames with priority 0 received by the PON port."
       ::= { hwEponOltStatsEntry 38 }

   hwEponOltRecvFramesNumWithPri1  OBJECT-TYPE
       SYNTAX     Counter32
       MAX-ACCESS   read-only
       STATUS      current
       DESCRIPTION
           "Number of frames with priority 1 received by the PON port."
       ::= { hwEponOltStatsEntry 39 }

   hwEponOltRecvFramesNumWithPri2  OBJECT-TYPE
       SYNTAX     Counter32
       MAX-ACCESS   read-only
       STATUS      current
       DESCRIPTION
           "Number of frames with priority 2 received by the PON port."
       ::= { hwEponOltStatsEntry 40 }

   hwEponOltRecvFramesNumWithPri3   OBJECT-TYPE
       SYNTAX     Counter32
       MAX-ACCESS   read-only
       STATUS      current
       DESCRIPTION
           "Number of frames with priority 3 received by the PON port."
       ::= { hwEponOltStatsEntry 41 }

   hwEponOltRecvFramesNumWithPri4  OBJECT-TYPE
       SYNTAX     Counter32
       MAX-ACCESS   read-only
       STATUS      current
       DESCRIPTION
           "Number of frames with priority 4 received by the PON port."
       ::= { hwEponOltStatsEntry 42 }

    hwEponOltRecvFramesNumWithPri5  OBJECT-TYPE
       SYNTAX     Counter32
       MAX-ACCESS   read-only
       STATUS      current
       DESCRIPTION
           "Number of frames with priority 5 received by the PON port."
       ::= { hwEponOltStatsEntry 43 }

    hwEponOltRecvFramesNumWithPri6  OBJECT-TYPE
       SYNTAX     Counter32
       MAX-ACCESS   read-only
       STATUS      current
       DESCRIPTION
           "Number of frames with priority 6 received by the PON port."
       ::= { hwEponOltStatsEntry 44 }

   hwEponOltRecvFramesNumWithPri7  OBJECT-TYPE
       SYNTAX     Counter32
       MAX-ACCESS   read-only
       STATUS      current
       DESCRIPTION
           "Number of frames with priority 7 received by the PON port."
       ::= { hwEponOltStatsEntry 45 }

   hwEponOltTranBytesNumWithPri0  OBJECT-TYPE
       SYNTAX     Counter32
       MAX-ACCESS   read-only
       STATUS      current
       DESCRIPTION
           "Number of bytes with priority 0 sent by the PON port."
       ::= { hwEponOltStatsEntry 46 }

   hwEponOltTranBytesNumWithPri1  OBJECT-TYPE
       SYNTAX     Counter32
       MAX-ACCESS   read-only
       STATUS      current
       DESCRIPTION
           "Number of bytes with priority 1 sent by the PON port."
       ::= { hwEponOltStatsEntry 47 }

   hwEponOltTranBytesNumWithPri2  OBJECT-TYPE
       SYNTAX     Counter32
       MAX-ACCESS   read-only
       STATUS      current
       DESCRIPTION
           "Number of bytes with priority 2 sent by the PON port."
       ::= { hwEponOltStatsEntry 48 }

    hwEponOltTranBytesNumWithPri3  OBJECT-TYPE
       SYNTAX     Counter32
       MAX-ACCESS   read-only
       STATUS      current
       DESCRIPTION
           "Number of bytes with priority 3 sent by the PON port."
       ::= { hwEponOltStatsEntry 49 }

    hwEponOltTranBytesNumWithPri4  OBJECT-TYPE
       SYNTAX     Counter32
       MAX-ACCESS   read-only
       STATUS      current
       DESCRIPTION
           "Number of bytes with priority 4 sent by the PON port."
       ::= { hwEponOltStatsEntry 50 }

   hwEponOltTranBytesNumWithPri5  OBJECT-TYPE
       SYNTAX     Counter32
       MAX-ACCESS   read-only
       STATUS      current
       DESCRIPTION
           "Number of bytes with priority 5 sent by the PON port."
       ::= { hwEponOltStatsEntry 51 }

   hwEponOltTranBytesNumWithPri6  OBJECT-TYPE
       SYNTAX     Counter32
       MAX-ACCESS   read-only
       STATUS      current
       DESCRIPTION
           "Number of bytes with priority 6 sent by the PON port."
       ::= { hwEponOltStatsEntry 52 }

   hwEponOltTranBytesNumWithPri7  OBJECT-TYPE
       SYNTAX     Counter32
       MAX-ACCESS   read-only
       STATUS      current
       DESCRIPTION
           "Number of bytes with priority 7 sent by the PON port."
       ::= { hwEponOltStatsEntry 53 }

   hwEponOltRecvBytesNumWithPri0  OBJECT-TYPE
       SYNTAX     Counter32
       MAX-ACCESS   read-only
       STATUS      current
       DESCRIPTION
           "Number of bytes with priority 0 received by the PON port."
       ::= { hwEponOltStatsEntry 54 }

    hwEponOltRecvBytesNumWithPri1  OBJECT-TYPE
       SYNTAX     Counter32
       MAX-ACCESS   read-only
       STATUS      current
       DESCRIPTION
           "Number of bytes with priority 1 received by the PON port."
       ::= { hwEponOltStatsEntry 55 }

    hwEponOltRecvBytesNumWithPri2  OBJECT-TYPE
       SYNTAX     Counter32
       MAX-ACCESS   read-only
       STATUS      current
       DESCRIPTION
           "Number of bytes with priority 2 received by the PON port."
       ::= { hwEponOltStatsEntry 56 }

   hwEponOltRecvBytesNumWithPri3   OBJECT-TYPE
       SYNTAX     Counter32
       MAX-ACCESS   read-only
       STATUS      current
       DESCRIPTION
           "Number of bytes with priority 3 received by the PON port."
       ::= { hwEponOltStatsEntry 57 }

   hwEponOltRecvBytesNumWithPri4  OBJECT-TYPE
       SYNTAX     Counter32
       MAX-ACCESS   read-only
       STATUS      current
       DESCRIPTION
           "Number of bytes with priority 4 received by the PON port."
       ::= { hwEponOltStatsEntry 58 }

   hwEponOltRecvBytesNumWithPri5  OBJECT-TYPE
       SYNTAX     Counter32
       MAX-ACCESS   read-only
       STATUS      current
       DESCRIPTION
           "Number of bytes with priority 5 received by the PON port."
       ::= { hwEponOltStatsEntry 59 }

   hwEponOltRecvBytesNumWithPri6  OBJECT-TYPE
       SYNTAX     Counter32
       MAX-ACCESS   read-only
       STATUS      current
       DESCRIPTION
           "Number of bytes with priority 6 received by the PON port."
       ::= { hwEponOltStatsEntry 60 }

    hwEponOltRecvBytesNumWithPri7  OBJECT-TYPE
       SYNTAX     Counter32
       MAX-ACCESS   read-only
       STATUS      current
       DESCRIPTION
           "Number of bytes with priority 7 received by the PON port."
       ::= { hwEponOltStatsEntry 61 }

    hwEponOltStatsClear  OBJECT-TYPE
       SYNTAX   INTEGER {
           clear(1)
           }
       MAX-ACCESS   read-write
       STATUS      current
       DESCRIPTION
           "Clearing of the performance statistics.
            Options:
            1. clear(1) -Clearing of the performance statistics
           "
       ::= { hwEponOltStatsEntry 62 }

   -- Table 44 :  2.17  HwEponOntCapabilityTable (13 node)

    hwEponOntCapabilityTable OBJECT-TYPE
       SYNTAX     SEQUENCE OF HwEponOntCapabilityEntry
       MAX-ACCESS not-accessible
       STATUS     current
       DESCRIPTION
           "ONT capability set table, used only for the query operation.
            The indexes of this table are ifIndex and
            hwEponDeviceOntObjectIndex.
           "
       ::= { hwGponDeviceControlObjects 44 }

    hwEponOntCapabilityEntry OBJECT-TYPE
       SYNTAX     HwEponOntCapabilityEntry
       MAX-ACCESS not-accessible
       STATUS     current
       DESCRIPTION
           "ONT capability set table, used only for the query operation.
            The indexes of this entry are ifIndex and
            hwEponDeviceOntObjectIndex.
           "
       INDEX       { ifIndex, hwEponDeviceOntObjectIndex }
       ::= { hwEponOntCapabilityTable 1 }

    HwEponOntCapabilityEntry ::=
        SEQUENCE {
                hwEponOntPOTSPortNum                       Integer32,
                hwEponOntFEPortsNum                        Integer32,
                hwEponOntGEPortsNum                        Integer32,
                hwEponOntTDMPortsNum                       Integer32,
                hwEponOntFECSupport                    Integer32,
                hwEponOntSupportbackupbattery              Integer32,
                hwEponOntUpQueueAllocationIncre            Integer32,
                hwEponOntUpQueueNum                        Integer32,
                hwEponOntUpQueueNumPerPort                 Integer32,
                hwEponOntDownQueueNum                      Integer32,
                hwEponOntDownQueueNumPerPort               Integer32,
                hwEponOntFePortList                        PortList,
                hwEponOntGePortList                        PortList
                }

    hwEponOntPOTSPortNum  OBJECT-TYPE
       SYNTAX     Integer32
       MAX-ACCESS   read-only
       STATUS      current
       DESCRIPTION
           "Number of ONT POTS ports."
       ::= { hwEponOntCapabilityEntry 1 }

    hwEponOntFEPortsNum  OBJECT-TYPE
       SYNTAX     Integer32
       MAX-ACCESS   read-only
       STATUS      current
       DESCRIPTION
           "Number of ONT FE ports."
       ::= { hwEponOntCapabilityEntry 2 }

    hwEponOntGEPortsNum  OBJECT-TYPE
       SYNTAX     Integer32
       MAX-ACCESS   read-only
       STATUS      current
       DESCRIPTION
           "Number of ONT GE ports."
       ::= { hwEponOntCapabilityEntry 3 }

    hwEponOntTDMPortsNum  OBJECT-TYPE
       SYNTAX     Integer32
       MAX-ACCESS   read-only
       STATUS      current
       DESCRIPTION
           "Number of ONT TDM ports."
       ::= { hwEponOntCapabilityEntry 4 }

    hwEponOntFECSupport  OBJECT-TYPE
       SYNTAX     Integer32
       MAX-ACCESS   read-only
       STATUS      current
       DESCRIPTION
           "Flag of whether the ONT supports FEC."
       ::= { hwEponOntCapabilityEntry 5 }

    hwEponOntSupportbackupbattery  OBJECT-TYPE
       SYNTAX     Integer32
       MAX-ACCESS   read-only
       STATUS      current
       DESCRIPTION
           "Flag of whether the ONT supports the backup battery."
       ::= { hwEponOntCapabilityEntry 6 }

    hwEponOntUpQueueAllocationIncre  OBJECT-TYPE
       SYNTAX     Integer32
       MAX-ACCESS   read-only
       STATUS      current
       DESCRIPTION
           "Increment of the allocated bandwidth of the upstream queue."
       ::= { hwEponOntCapabilityEntry 7 }


    hwEponOntUpQueueNum  OBJECT-TYPE
       SYNTAX     Integer32
       MAX-ACCESS   read-only
       STATUS      current
       DESCRIPTION
           "Number of upstream queues."
       ::= { hwEponOntCapabilityEntry 8 }

    hwEponOntUpQueueNumPerPort  OBJECT-TYPE
       SYNTAX     Integer32
       MAX-ACCESS   read-only
       STATUS      current
       DESCRIPTION
           "Maximum number of queues of the uplink port."
       ::= { hwEponOntCapabilityEntry 9 }

    hwEponOntDownQueueNum  OBJECT-TYPE
       SYNTAX     Integer32
       MAX-ACCESS   read-only
       STATUS      current
       DESCRIPTION
           "Number of downstream queues."
       ::= { hwEponOntCapabilityEntry 10}

    hwEponOntDownQueueNumPerPort  OBJECT-TYPE
       SYNTAX     Integer32
       MAX-ACCESS   read-only
       STATUS      current
       DESCRIPTION
           "Maximum number of queues of the downlink port."
       ::= { hwEponOntCapabilityEntry 11}

    hwEponOntFePortList  OBJECT-TYPE
       SYNTAX     PortList
       MAX-ACCESS   read-only
       STATUS      current
       DESCRIPTION
           "Bitmap of the FE port, a string of characters."
       ::= { hwEponOntCapabilityEntry 12}

    hwEponOntGePortList  OBJECT-TYPE
       SYNTAX     PortList
       MAX-ACCESS   read-only
       STATUS      current
       DESCRIPTION
           "Bitmap of the GE port, a string of characters."
       ::= { hwEponOntCapabilityEntry 13}

      -- Table 45 : hwEponDeviceCtcRemoteOntMulticastCtrItemTable

    hwEponDeviceCtcRemoteOntMulticastCtrItemTable OBJECT-TYPE
       SYNTAX     SEQUENCE OF HwEponDeviceCtcRemoteOntMulticastCtrItemEntry
       MAX-ACCESS not-accessible
       STATUS     current
       DESCRIPTION
           "ONT multicast control items table, used for the real-time query and available only when hwEponDeviceCtcOntMulticastControlCtcType in the ONT global configuration is CTC.
            The indexes of this table are ifIndex, hwEponDeviceOntObjectIndex,
            and hwEponDeviceOntMulticastCtrItemIndex.
           "
       ::= { hwGponDeviceControlObjects 45 }

    hwEponDeviceCtcRemoteOntMulticastCtrItemEntry OBJECT-TYPE
       SYNTAX     HwEponDeviceCtcRemoteOntMulticastCtrItemEntry
       MAX-ACCESS not-accessible
       STATUS     current
       DESCRIPTION
           "ONT multicast control items table, used for the real-time query and available only when hwEponDeviceCtcOntMulticastControlCtcType in the ONT global configuration is CTC.
            The indexes of this entry are ifIndex, hwEponDeviceOntObjectIndex,
            and hwEponDeviceOntMulticastCtrItemIndex.
           "
       INDEX       { ifIndex, hwEponDeviceOntObjectIndex, hwEponDeviceOntMulticastCtrItemIndex }
       ::= { hwEponDeviceCtcRemoteOntMulticastCtrItemTable 1 }


    HwEponDeviceCtcRemoteOntMulticastCtrItemEntry ::=
        SEQUENCE {
                   hwEponDeviceOntMulticastCtrItemIndex                      Integer32,
                   hwEponDeviceCtcOntMulticastCtrlType                       INTEGER,
                   hwEponDeviceCtcOntMulticastCtrlUsrID                      Integer32,
                   hwEponDeviceCtcOntMulticastCtrlGDA                        OCTET STRING,
                   hwEponDeviceCtcOntMulticastCtrlVlanIDorSA                 OCTET STRING
                }

    hwEponDeviceOntMulticastCtrItemIndex  OBJECT-TYPE
       SYNTAX     Integer32
       MAX-ACCESS   not-accessible
       STATUS      current
       DESCRIPTION
           "Index of the multicast control item."
       ::= { hwEponDeviceCtcRemoteOntMulticastCtrItemEntry 1 }

    hwEponDeviceCtcOntMulticastCtrlType  OBJECT-TYPE
       SYNTAX     INTEGER {
                           gDA(0),
                           gDAVLAN(1),
                           gDASA(2)
                          }
       MAX-ACCESS   read-only
       STATUS      current
       DESCRIPTION
           "Multicast control type.
            Options:
            1. gDA(0)     -Multicast control type is gDA
            2. gDAVLAN(1) -Multicast control type is gDAVLAN
            3. gDASA(2)   -Multicast control type is gDASA
           "
       ::= { hwEponDeviceCtcRemoteOntMulticastCtrItemEntry 2 }


    hwEponDeviceCtcOntMulticastCtrlUsrID  OBJECT-TYPE
       SYNTAX     Integer32
       MAX-ACCESS   read-only
       STATUS      current
       DESCRIPTION
           "User ID."
       ::= { hwEponDeviceCtcRemoteOntMulticastCtrItemEntry 3 }

    hwEponDeviceCtcOntMulticastCtrlGDA  OBJECT-TYPE
       SYNTAX     OCTET STRING  ( SIZE (1..6) )
       MAX-ACCESS   read-only
       STATUS      current
       DESCRIPTION
           "Multicast destination MAC address."
       ::= { hwEponDeviceCtcRemoteOntMulticastCtrItemEntry 4 }

   hwEponDeviceCtcOntMulticastCtrlVlanIDorSA  OBJECT-TYPE
       SYNTAX     OCTET STRING  ( SIZE (1..6) )
       MAX-ACCESS   read-only
       STATUS      current
       DESCRIPTION
           "VLAN ID or multicast source MAC address."
       ::= { hwEponDeviceCtcRemoteOntMulticastCtrItemEntry 5 }

    -- Table 46 : hwEponDeviceCtcRemoteOntPortVLANConfigurationTable

    hwEponDeviceCtcRemoteOntPortVLANConfigurationTable OBJECT-TYPE
       SYNTAX     SEQUENCE OF HwEponDeviceCtcRemoteOntPortVLANConfigurationEntry
       MAX-ACCESS not-accessible
       STATUS     current
       DESCRIPTION
           "This table is used for querying the VLAN mode and the default VLAN configuration of the ONT FE/GE port in real time.
            The indexes of this table are ifIndex, hwEponDeviceOntObjectIndex,
            hwEponOntifEthernetType, and hwEponOntifEthernetPort.
           "
       ::= { hwGponDeviceControlObjects 46 }

    hwEponDeviceCtcRemoteOntPortVLANConfigurationEntry OBJECT-TYPE
       SYNTAX     HwEponDeviceCtcRemoteOntPortVLANConfigurationEntry
       MAX-ACCESS not-accessible
       STATUS     current
       DESCRIPTION
           "This table is used for querying the VLAN mode and the default VLAN configuration of the ONT FE/GE port in real time.
            The indexes of this entry are ifIndex, hwEponDeviceOntObjectIndex,
            hwEponOntifEthernetType, and hwEponOntifEthernetPort.
           "
       INDEX       { ifIndex, hwEponDeviceOntObjectIndex, hwEponOntifEthernetType, hwEponOntifEthernetPort }
       ::= { hwEponDeviceCtcRemoteOntPortVLANConfigurationTable 1 }

    HwEponDeviceCtcRemoteOntPortVLANConfigurationEntry ::=
        SEQUENCE {
                   hwEponDeviceCtcOntPortVLANMode                 INTEGER,
                   hwEponDeviceCtcOntPortDefaultTagTPID           Integer32,
                   hwEponDeviceCtcOntPortDefaultTagCFI            Integer32,
                   hwEponDeviceCtcOntPortDefaultTagPri            Integer32,
                   hwEponDeviceCtcOntPortDefaultTagVID            Integer32
                }

    hwEponDeviceCtcOntPortVLANMode  OBJECT-TYPE
       SYNTAX     INTEGER {
                           transparent(0),
                           tag(1),
                           translation(2)
                          }
       MAX-ACCESS   read-only
       STATUS      current
       DESCRIPTION
           "VLAN mode.
           Options:
           1. transparent(0) -VLAN mode is transparent
           2. tag(1)         -VLAN mode is tag
           3. translation(2) -VLAN mode is translation
           "
       ::= { hwEponDeviceCtcRemoteOntPortVLANConfigurationEntry 1 }

    hwEponDeviceCtcOntPortDefaultTagTPID  OBJECT-TYPE
       SYNTAX     Integer32
       MAX-ACCESS   read-only
       STATUS      current
       DESCRIPTION
           "TPID of the default tag of the ONT port."
       ::= { hwEponDeviceCtcRemoteOntPortVLANConfigurationEntry 2 }

   hwEponDeviceCtcOntPortDefaultTagCFI  OBJECT-TYPE
       SYNTAX     Integer32
       MAX-ACCESS   read-only
       STATUS      current
       DESCRIPTION
           "CFI of the default tag of the ONT port."
       ::= { hwEponDeviceCtcRemoteOntPortVLANConfigurationEntry 3 }

   hwEponDeviceCtcOntPortDefaultTagPri  OBJECT-TYPE
       SYNTAX     Integer32
       MAX-ACCESS   read-only
       STATUS      current
       DESCRIPTION
           "Pri of the default tag of the ONT port."
       ::= { hwEponDeviceCtcRemoteOntPortVLANConfigurationEntry 4 }

   hwEponDeviceCtcOntPortDefaultTagVID  OBJECT-TYPE
       SYNTAX     Integer32
       MAX-ACCESS   read-only
       STATUS      current
       DESCRIPTION
           "VID (VLAN ID) of the default tag of the ONT port."
       ::= { hwEponDeviceCtcRemoteOntPortVLANConfigurationEntry 5 }

    -- Table 49 : hwEponDeviceCtcRemoteOntPortVLANTranslationTable

    hwEponDeviceCtcRemoteOntPortVLANTranslationTable OBJECT-TYPE
       SYNTAX     SEQUENCE OF HwEponDeviceCtcRemoteOntPortVLANTranslationEntry
       MAX-ACCESS not-accessible
       STATUS     current
       DESCRIPTION
           "This table is used for querying the VLAN switching pair configuration of the ONT FE/GE port.
            The indexes of this table are ifIndex, hwEponDeviceOntObjectIndex,
            hwEponOntifEthernetType, hwEponOntifEthernetPort, and hwEponOntifEthernetPortVlanTransIndex.
           "
       ::= { hwGponDeviceControlObjects 49 }

    hwEponDeviceCtcRemoteOntPortVLANTranslationEntry OBJECT-TYPE
       SYNTAX     HwEponDeviceCtcRemoteOntPortVLANTranslationEntry
       MAX-ACCESS not-accessible
       STATUS     current
       DESCRIPTION
           "This table is used for querying the VLAN switching pair configuration of the ONT FE/GE port.
            The indexes of this entry are ifIndex, hwEponDeviceOntObjectIndex,
            hwEponOntifEthernetType, hwEponOntifEthernetPort, and hwEponOntifEthernetPortVlanTransIndex.
           "
       INDEX       { ifIndex, hwEponDeviceOntObjectIndex, hwEponOntifEthernetType, hwEponOntifEthernetPort, hwEponOntifEthernetPortVlanTransIndex }
       ::= { hwEponDeviceCtcRemoteOntPortVLANTranslationTable 1 }

    HwEponDeviceCtcRemoteOntPortVLANTranslationEntry ::=
        SEQUENCE {
                   hwEponOntifEthernetPortVlanTransIndex                     Integer32,
           hwEponDeviceCtcOntPortVlanTranslationOldTagVID            Integer32,
                   hwEponDeviceCtcOntPortVlanTranslationOldTagPri            Integer32,
                   hwEponDeviceCtcOntPortVlanTranslationOldTagTPID           Integer32,
                   hwEponDeviceCtcOntPortVlanTranslationOldTagCFI            Integer32,
                   hwEponDeviceCtcOntPortVlanTranslationNewTagVID            Integer32,
                   hwEponDeviceCtcOntPortVlanTranslationNewTagTPID           Integer32,
                   hwEponDeviceCtcOntPortVlanTranslationNewTagCFI            Integer32,
                   hwEponDeviceCtcOntPortVlanTranslationNewTagPri            Integer32
                  }

    hwEponOntifEthernetPortVlanTransIndex  OBJECT-TYPE
       SYNTAX     Integer32
       MAX-ACCESS   not-accessible
       STATUS      current
       DESCRIPTION
           "Internal number of the VLAN switching item of the ONT port in the VLAN translation mode."
       ::= { hwEponDeviceCtcRemoteOntPortVLANTranslationEntry 1 }

    hwEponDeviceCtcOntPortVlanTranslationOldTagVID  OBJECT-TYPE
       SYNTAX     Integer32
       MAX-ACCESS   read-only
       STATUS      current
       DESCRIPTION
           "VID (VLAN ID) of the old tag of the ONT port in the VLAN translation mode."
       ::= { hwEponDeviceCtcRemoteOntPortVLANTranslationEntry 2 }

   hwEponDeviceCtcOntPortVlanTranslationOldTagPri  OBJECT-TYPE
       SYNTAX     Integer32
       MAX-ACCESS   read-only
       STATUS      current
       DESCRIPTION
           "Pri of the old tag of the ONT port in the VLAN translation mode."
       ::= { hwEponDeviceCtcRemoteOntPortVLANTranslationEntry 3 }

   hwEponDeviceCtcOntPortVlanTranslationOldTagTPID  OBJECT-TYPE
       SYNTAX     Integer32
       MAX-ACCESS   read-only
       STATUS      current
       DESCRIPTION
           "TPID of the old tag of the ONT port in the VLAN translation mode."
       ::= { hwEponDeviceCtcRemoteOntPortVLANTranslationEntry 4 }

   hwEponDeviceCtcOntPortVlanTranslationOldTagCFI  OBJECT-TYPE
       SYNTAX     Integer32
       MAX-ACCESS   read-only
       STATUS      current
       DESCRIPTION
           "CFI of the old tag of the ONT port in the VLAN translation mode."
       ::= { hwEponDeviceCtcRemoteOntPortVLANTranslationEntry 5 }

   hwEponDeviceCtcOntPortVlanTranslationNewTagVID  OBJECT-TYPE
       SYNTAX     Integer32
       MAX-ACCESS   read-only
       STATUS      current
       DESCRIPTION
           "VID of the new tag of the ONT port in the VLAN translation mode."
       ::= { hwEponDeviceCtcRemoteOntPortVLANTranslationEntry 6 }

   hwEponDeviceCtcOntPortVlanTranslationNewTagTPID  OBJECT-TYPE
       SYNTAX     Integer32
       MAX-ACCESS   read-only
       STATUS      current
       DESCRIPTION
           "TPID of the new tag of the ONT port in the VLAN translation mode."
       ::= { hwEponDeviceCtcRemoteOntPortVLANTranslationEntry 7 }

   hwEponDeviceCtcOntPortVlanTranslationNewTagCFI  OBJECT-TYPE
       SYNTAX     Integer32
       MAX-ACCESS   read-only
       STATUS      current
       DESCRIPTION
           "CFI of the new tag of the ONT port in the VLAN translation mode."
       ::= { hwEponDeviceCtcRemoteOntPortVLANTranslationEntry 8 }

   hwEponDeviceCtcOntPortVlanTranslationNewTagPri  OBJECT-TYPE
       SYNTAX     Integer32
       MAX-ACCESS   read-only
       STATUS      current
       DESCRIPTION
           "Pri of the new tag of the ONT port in the VLAN translation mode."
       ::= { hwEponDeviceCtcRemoteOntPortVLANTranslationEntry 9 }

-- Table 50 : hwGponOltOpticsModuleInformationTable

    hwGponOltOpticsModuleInformationTable OBJECT-TYPE
        SYNTAX     SEQUENCE OF HwGponOltOpticsModuleInformationEntry
        MAX-ACCESS not-accessible
        STATUS     current
        DESCRIPTION
            "Show the optics module information.
             The index of this table is ifIndex.
            "
        ::= { hwGponDeviceControlObjects 50 }

    hwGponOltOpticsModuleInformationEntry OBJECT-TYPE
        SYNTAX     HwGponOltOpticsModuleInformationEntry
        MAX-ACCESS not-accessible
        STATUS     current
        DESCRIPTION
            "Show the optics module information.
             The index of this entry is ifIndex.
            "
        INDEX       { ifIndex }
        ::= { hwGponOltOpticsModuleInformationTable 1 }

    HwGponOltOpticsModuleInformationEntry ::=
        SEQUENCE {
                   hwGponOpticsMDIdentifier
            INTEGER,
           hwGponOpticsMDExtID
            INTEGER,
           hwGponOpticsMDConnector
            INTEGER,
           hwGponOpticsMDEncoding
            INTEGER,
           hwGponOpticsMDBrNominal
            Integer32,
           hwGponOpticsMDLength9Micronkm
            Integer32,
           hwGponOpticsMDLength9Micron
            Integer32,
           hwGponOpticsMDLength50Micron
            Integer32,
           hwGponOpticsMDLength62Micron5
            Integer32,
           hwGponOpticsMDLengthCopper
            Integer32,
           hwGponOpticsMDVendorName
            OCTET STRING,
           hwGponOpticsMDVendorOUI
            OCTET STRING,
           hwGponOpticsMDVendorPN
            OCTET STRING,
           hwGponOpticsMDVendorRev
            OCTET STRING,
           hwGponOpticsMDWaveLength
            Integer32,
           hwGponOpticsMDCcBase
            Integer32,
           hwGponOpticsMDOptions
            Integer32,
           hwGponOpticsMDBrMax
            Integer32,
           hwGponOpticsMDBrMin
            Integer32,
           hwGponOpticsMDVendorSN
            OCTET STRING,
           hwGponOpticsMDDateCode
            OCTET STRING,
           hwGponOpticsMDDiagnosticMonitoringType
            Integer32,
           hwGponOpticsMDEnhancedOptions
            Integer32,
           hwGponOpticsMDSFF8472Compliance
            INTEGER,
           hwGponOpticsMDCcExt
            Integer32,
           hwGponOpticsMDVendorSpecific
            OCTET STRING,
           hwGponOpticsModuleXponType
            INTEGER,
           hwGponOpticsModuleXponSubType
            INTEGER,
           hwGponOpticsModuleXponUsedType
            INTEGER,
           hwGponOpticsModuleXponEncapsulationType
            INTEGER,
           hwGponOpticsMDPartNum
            OCTET STRING
                }

       hwGponOpticsMDIdentifier OBJECT-TYPE
           SYNTAX INTEGER
            {
            unknown(1),
            gbic(2),
            solderedToMotherboard(3),
            sfp(4),
            invalidValue(-1)
            }
           MAX-ACCESS read-only
           STATUS current
           DESCRIPTION
           "This object indicates the type of serial transceiver.
                Options:
                1. unknown(1)                      - Unknown or unspecified
                2. gbic(2)                         - GBIC
                3. solderedToMotherboard(3)        - Module soldered to motherboard
                4. sfp(4)                          - SFP or SFP Plus
                5. invalidValue(-1)                - Invalid value
           "
       ::= { hwGponOltOpticsModuleInformationEntry 1 }

    hwGponOpticsMDExtID OBJECT-TYPE
    SYNTAX INTEGER
            {
            notSpecifiedOrNotCompliant(1),
            moddef1(2),
            moddef2(3),
            moddef3(4),
            byTwowireOnly(5),
            moddef5(6),
            moddef6(7),
            moddef7(8),
            invalidValue(-1)
            }
    MAX-ACCESS read-only
    STATUS current
    DESCRIPTION
            "This object indicates the extended identifier of type of serial transceiver.
             Options:
             1. notSpecifiedOrNotCompliant(1)   - Not specified or not compliant with a defined MOD_DEF
             2. moddef1(2)                      - GBIC is compliant with MOD_DEF 1
             3. moddef2(3)                      - GBIC is compliant with MOD_DEF 2
             4. moddef3(4)                      - GBIC is compliant with MOD_DEF 3
             5. byTwowireOnly(5)                - GBIC/SFP function is defined by two-wire interface ID only
             6. moddef5(6)                      - GBIC is compliant with MOD_DEF 5
             7. moddef6(7)                      - GBIC is compliant with MOD_DEF 6
             8. moddef7(8)                      - GBIC is compliant with MOD_DEF 7
             9. invalidValue(-1)                - Invalid value
            "
    ::= { hwGponOltOpticsModuleInformationEntry 2 }

    hwGponOpticsMDConnector OBJECT-TYPE
    SYNTAX INTEGER
           {
            unknown(1),
            sc(2),
            copperConnector1(3),
            copperConnector2(4),
            bnctnc(5),
            coaxialHeaders(6),
            fiberJack(7),
            lc(8),
            mtrj(9),
            mu(10),
            sg(11),
            opticalPigtail(12),
            hssdcII(13),
            copperPigtail(14),
            mpoParallelOptic(15),
            rj45(16),
            invalidValue(-1)
           }
    MAX-ACCESS read-only
    STATUS current
    DESCRIPTION
        "This object indicates the code for connector type.
             Options:
             1.  unknown(1)              - Unknown
             2.  sc(2)                   - SC
             3.  copperConnector1(3)     - Fibre Channel Style 1 copper connector
             4.  copperConnector2(4)     - Fibre Channel Style 2 copper connector
             5.  bnctnc(5)               - BNC/TNC
             6.  coaxialHeaders(6)       - Fibre Channel coaxial headers
             7.  fiberJack(7)            - FiberJack
             8.  lc(8)                   - LC
             9.  mtrj(9)                 - MT-RJ
             10. mu(10)                  - MU
             11. sg(11)                  - SG
             12. opticalPigtail(12)      - Optical pigtail
             13. hssdcII(13)             - HSSDC II
             14. copperPigtail(14)       - Copper Pigtail
             15. mpoParallelOptic(15)    - MPO Parallel Optic
             16. rj45(16)                - RJ45
             17. invalidValue(-1)        - Invalid value
            "
    ::= { hwGponOltOpticsModuleInformationEntry 3 }

    hwGponOpticsMDEncoding OBJECT-TYPE
        SYNTAX INTEGER
            {
            unspecified(1),
            encodingMethod8B10B(2),
            encodingMethod4B5B(3),
            nrz(4),
            manchester(5),
            sonetScrambled(6),
            encodingMethod64B66B (7),
            invalidValue(-1)
            }
        MAX-ACCESS read-only
        STATUS current
        DESCRIPTION
            "This object indicates the code for serial encoding algorithm.
             Options:
             1.  unspecified(1)            - Unspecified
             2.  encodingMethod8B10B(2)    - 8B10B
             3.  encodingMethod4B5B(3)     - 4B5B
             4.  nrz(4)                    - NRZ
             5.  manchester(5)             - Manchester
             6.  sonetScrambled(6)         - SONET Scrambled
             7. encodingMethod64B66B(7)    - 64B66B
             8. invalidValue(-1)           - Invalid value
            "
        ::= { hwGponOltOpticsModuleInformationEntry 4 }

    hwGponOpticsMDBrNominal OBJECT-TYPE
    SYNTAX Integer32
    MAX-ACCESS read-only
    STATUS current
    DESCRIPTION
            "Nominal bit rate, units of 100 MBits/sec."
    ::= { hwGponOltOpticsModuleInformationEntry 5 }

    hwGponOpticsMDLength9Micronkm OBJECT-TYPE
    SYNTAX Integer32
    MAX-ACCESS read-only
    STATUS current
    DESCRIPTION
            "Link length supported for 9/125 um fiber, units of km."
    ::= { hwGponOltOpticsModuleInformationEntry 6 }

    hwGponOpticsMDLength9Micron OBJECT-TYPE
    SYNTAX Integer32
    MAX-ACCESS read-only
    STATUS current
    DESCRIPTION
            "Link length supported for 9/125 um fiber, units of 100 m."
    ::= { hwGponOltOpticsModuleInformationEntry 7 }

    hwGponOpticsMDLength50Micron OBJECT-TYPE
    SYNTAX Integer32
    MAX-ACCESS read-only
    STATUS current
    DESCRIPTION
            "Link length supported for 50/125 um fiber, units of 10 m."
    ::= { hwGponOltOpticsModuleInformationEntry 8 }

    hwGponOpticsMDLength62Micron5 OBJECT-TYPE
    SYNTAX Integer32
    MAX-ACCESS read-only
    STATUS current
    DESCRIPTION
            "Link length supported for 62.5/125 um fiber, units of 10 m."
    ::= { hwGponOltOpticsModuleInformationEntry 9 }

    hwGponOpticsMDLengthCopper OBJECT-TYPE
    SYNTAX Integer32
    MAX-ACCESS read-only
    STATUS current
    DESCRIPTION
            "Link length supported for copper, units of meters."
    ::= { hwGponOltOpticsModuleInformationEntry 10 }

    hwGponOpticsMDVendorName OBJECT-TYPE
    SYNTAX OCTET STRING (SIZE (0..17))
    MAX-ACCESS read-only
    STATUS current
    DESCRIPTION
            "SFP vendor name (ASCII)."
    ::= { hwGponOltOpticsModuleInformationEntry 11 }

    hwGponOpticsMDVendorOUI OBJECT-TYPE
    SYNTAX OCTET STRING (SIZE (0..9))
    MAX-ACCESS read-only
    STATUS current
    DESCRIPTION
            "SFP vendor IEEE company ID."
    ::= { hwGponOltOpticsModuleInformationEntry 12 }

    hwGponOpticsMDVendorPN OBJECT-TYPE
    SYNTAX OCTET STRING (SIZE (0..17))
    MAX-ACCESS read-only
    STATUS current
    DESCRIPTION
            "Part number provided by SFP vendor (ASCII)."
    ::= { hwGponOltOpticsModuleInformationEntry 13 }

    hwGponOpticsMDVendorRev OBJECT-TYPE
    SYNTAX OCTET STRING (SIZE (0..5))
    MAX-ACCESS read-only
    STATUS current
    DESCRIPTION
            "Revision level for part number provided by vendor (ASCII)."
    ::= { hwGponOltOpticsModuleInformationEntry 14 }

    hwGponOpticsMDWaveLength OBJECT-TYPE
    SYNTAX Integer32
    MAX-ACCESS read-only
    STATUS current
    DESCRIPTION
            "Laser wavelength,units of nm."
    ::= { hwGponOltOpticsModuleInformationEntry 15 }

    hwGponOpticsMDCcBase OBJECT-TYPE
    SYNTAX Integer32
    MAX-ACCESS read-only
    STATUS current
    DESCRIPTION
            "Check code for Base ID Fields (one byte)."
    ::= { hwGponOltOpticsModuleInformationEntry 16 }

    hwGponOpticsMDOptions OBJECT-TYPE
    SYNTAX Integer32
    MAX-ACCESS read-only
    STATUS current
    DESCRIPTION
        "Indicates which optional transceiver signals are implemented.
              bit                 Description of option
               10                 Cooled laser transmitter
               9                  Power Level 2 requirement
               8                  Linear Receiver Output
              7-6                 Reserved
               5                  RATE_SELECT
               4                  TX_DISABLE
               3                  TX_FAULT
               2                  LOS (signal inverted from standard definition)
               1                  LOS (signal as defined in SFP MSA)
               0                  Reserved
             "
    ::= { hwGponOltOpticsModuleInformationEntry 17 }

    hwGponOpticsMDBrMax OBJECT-TYPE
    SYNTAX Integer32
    MAX-ACCESS read-only
    STATUS current
    DESCRIPTION
            "Upper bit rate margin, units of 0.01."
    ::= { hwGponOltOpticsModuleInformationEntry 18 }

    hwGponOpticsMDBrMin OBJECT-TYPE
    SYNTAX Integer32
    MAX-ACCESS read-only
    STATUS current
    DESCRIPTION
            "Lower bit rate margin, units of 0.01."
    ::= { hwGponOltOpticsModuleInformationEntry 19 }

    hwGponOpticsMDVendorSN OBJECT-TYPE
    SYNTAX OCTET STRING (SIZE (0..17))
    MAX-ACCESS read-only
    STATUS current
    DESCRIPTION
            "Serial number provided by vendor (ASCII)."
    ::= { hwGponOltOpticsModuleInformationEntry 20 }

    hwGponOpticsMDDateCode OBJECT-TYPE
    SYNTAX OCTET STRING (SIZE (0..9))
    MAX-ACCESS read-only
    STATUS current
    DESCRIPTION
            "The optics module of date code."
    ::= { hwGponOltOpticsModuleInformationEntry 21 }

    hwGponOpticsMDDiagnosticMonitoringType OBJECT-TYPE
    SYNTAX Integer32
    MAX-ACCESS read-only
    STATUS current
    DESCRIPTION
        "Indicates which type of diagnostic monitoring is implemented.
              bit                 Description of Diagnostic Monitoring Type
               7                  Reserved
               6                  Digital diagnostic monitoring
               5                  Intemally Calibrated
               4                  Extemally Calibrated
               3                  Received power measurement type:(0 = OMA, 1 = Average)
               2                  Address change required
               1-0                Reserved
        "
    ::= { hwGponOltOpticsModuleInformationEntry 22 }

    hwGponOpticsMDEnhancedOptions OBJECT-TYPE
    SYNTAX Integer32
    MAX-ACCESS read-only
    STATUS current
    DESCRIPTION
        "Indicates which optional enhanced features are implemented.
             bit                 Description of Enhanced Options
              7                  Alarm/warning flags
              6                  TX_DISABLE control and monitoring
              5                  TX_FAULT monitoring
              4                  RX_LOS monitoring
              3                  RATE_SELECT control and monitoring
              2                  Application Select control
              1                  Rate Select control
              0                  Reserved
             "
    ::= { hwGponOltOpticsModuleInformationEntry 23 }

    hwGponOpticsMDSFF8472Compliance OBJECT-TYPE
    SYNTAX INTEGER
            {
            undefined(1),
            includesRev93SFF8472(2),
            includesRev95SFF8472(3),
            includesRev102SFF8472(4),
            includesRev104SFF8472(5),
            includesRev110SFF8472(6),
            invalidValue(-1)
            }
    MAX-ACCESS read-only
    STATUS current
    DESCRIPTION
            "Indicates which revision of SFF-8472 the transceiver complies
             Options:
             1. undefined(1)               - Not included or undefined
             2. includesRev93SFF8472(2)    - Includes functionality described in Rev 9.3
             3. includesRev95SFF8472(3)    - Includes functionality described in Rev 9.5
             4. includesRev102SFF8472(4)   - Includes functionality described in Rev 10.2
             5. includesRev104SFF8472(5)   - Includes functionality described in Rev 10.4
             6. includesRev110SFF8472(6)   - Includes functionality described in Rev 11.0
             7. invalidValue(-1)           - Invalid value
            "
    ::= { hwGponOltOpticsModuleInformationEntry 24 }

    hwGponOpticsMDCcExt OBJECT-TYPE
    SYNTAX Integer32
    MAX-ACCESS read-only
    STATUS current
    DESCRIPTION
            "Check code for the Extended ID Fields (one byte)."
    ::= { hwGponOltOpticsModuleInformationEntry 25 }

    hwGponOpticsMDVendorSpecific OBJECT-TYPE
    SYNTAX OCTET STRING (SIZE (0..33))
    MAX-ACCESS read-only
    STATUS current
    DESCRIPTION
        "Vendor Specific."
    ::= { hwGponOltOpticsModuleInformationEntry 26 }

    hwGponOpticsModuleXponType OBJECT-TYPE
    SYNTAX INTEGER
        {
        unknown(1),
        gpon(2),
        epon(3),
        epon10g(4),
        gpon10g(5),
        wdmpon(6),
        hybridpon(7),
        gponepon(8),
        xgspon(9),
        gponandxgpon(10),
        gponandxgspon(11),
        twdmpon(15),
        invalidValue(-1)
        }
        MAX-ACCESS read-only
    STATUS current
    DESCRIPTION
            "Options:
             1. unknown(1)         - Unknown
             2. gpon(2)            - GPON
             3. epon(3)            - EPON
             4. epon10g(4)         - 10G EPON
             5. gpon10g(5)         - 10G GPON
             6. wdmpon(6)          - WDM PON
             7. hybridpon(7)       - Hybrid PON
             8. gponepon(8)        - GPON/EPON
             9. xgspon(9)          - XGS-PON
             10.gponandxgpon(10)   - GPON+XG-PON
             11.gponandxgspon(11)  - GPON+XGS-PON
             12.twdmpon(15)        - TWDM-PON
             13.invalidValue(-1)   - Invalid value
        "
    ::= { hwGponOltOpticsModuleInformationEntry 27 }

    hwGponOpticsModuleXponSubType OBJECT-TYPE
    SYNTAX INTEGER
        {
        unknown(1),
        classbplus(101),
        classcplus(102),
        classb(103),
        classcplusplus(104),
        classd(105),
        px20(201),
        px20plus(202),
        px20plusplus(203),
        pr30(301),
        pr20(302),
        prx30(303),
        prx20(304),
        prx40(305),
        pr40(306),
        prx30e(307),
        prx40e(308),
        pr30plus(309),
        n2a(405),
        n2b(406),
        n1(407),
        e1(408),
        e2a(409),
        e2b(410),
        d1(411),
        d2(412),
        n2(413),
        e2(414),
        classbPlusAndPx20Plus(501),
        classbAndPx20(502),
        invalidValue(-1)
        }
    MAX-ACCESS read-only
    STATUS current
    DESCRIPTION
        "Options:
             1. unknown(1)                 - Unknown
             2. classbplus(101)            - CLASS B+
             3. classcplus(102)            - CLASS C+
             4. classb(103)                - CLASS B
             5. classcplusplus(104)        - CLASS C++
             6. classd(105)                - CLASS D
             7. px20(201)                  - PX20
             8. px20plus(202)              - PX20+
             9. px20plusplus(203)          - PX20++
             10. pr30(301)                  - PR30
             11.pr20(302)                  - PR20
             12.prx30(303)                 - PRX30
             13.prx20(304)                 - PRX20
             14.prx40(305)                 - PRX40
             15.pr40(306)                  - PR40
             16.prx30e(307)                - PRX30-E
             17.prx40e(308)                - PRX40-E
             18.pr30plus(309)              - PR30+
             19.n2a(405)                   - N2a
             20.n2b(406)                   - N2b
             21.n1(407)                    - N1
             22.e1(408)                    - E1
             23.e2a(409)                   - E2a
             24.e2b(410)                   - E2b
             25.d1(411)                    - D1
             26.d2(412)                    - D2
             27.n2(413)                    - N2
             28.e2(414)                    - E2
             29.classbPlusAndPx20Plus(501) - GPON CLASS B+/EPON PX20+
             30.classbAndPx20(502)         - GPON CLASS B/EPON PX20
             31.invalidValue(-1)           - Invalid value
        "
    ::= { hwGponOltOpticsModuleInformationEntry 28 }

    hwGponOpticsModuleXponUsedType OBJECT-TYPE
    SYNTAX INTEGER
    {
        unknown(1),
        olt(2),
        ont(3),
        onu(4),
        catvtriplex(5),
        invalidValue(-1)
    }
    MAX-ACCESS read-only
    STATUS current
    DESCRIPTION
        "The used scene.
         Options:
         1. unknown(1)       - Unknown
         2. olt(2)           - OLT
         3. ont(3)           - ONT
         4. onu(4)           - ONU
         5. catvtriplex(5)   - CATV TriPlex
         6. invalidValue(-1) - Invalid value
        "
    ::= { hwGponOltOpticsModuleInformationEntry 29 }

    hwGponOpticsModuleXponEncapsulationType OBJECT-TYPE
    SYNTAX INTEGER
    {
        unknown(1),
        sff2x5(2),
        sff2x10(3),
        sfp(4),
        xfp(5),
        lxfp(6),
        bosaonboard(7),
        sfpplus(8),
        invalidValue(-1)
    }
    MAX-ACCESS read-only
    STATUS current
    DESCRIPTION
            "Options:
             1. unknown(1)              - Unknown
             2. sff2x5(2)               - SFF 2x5
             3. sff2x10(3)              - SFF 2x10
             4. sfp(4)                  - SFP
             5. xfp(5)                  - XFP
             6. lxfp(6)                 - LXFP
             7. bosaonboard(7)          - BOSA ON BOARD
             8. sfpplus(8)              - SFP+
             9. invalidValue(-1)        - Invalid value
        "
    ::= { hwGponOltOpticsModuleInformationEntry 30 }

      hwGponOpticsMDPartNum OBJECT-TYPE
        SYNTAX OCTET STRING (SIZE (0..16))
        MAX-ACCESS read-only
        STATUS current
        DESCRIPTION
           "Indicate the part number of a optical module provided by Huawei."
      ::= { hwGponOltOpticsModuleInformationEntry 31 }

-- Table 51 : hwGponOltOpticsDdmInformationTable

    hwGponOltOpticsDdmInformationTable OBJECT-TYPE
        SYNTAX     SEQUENCE OF HwGponOltOpticsDdmInformationEntry
        MAX-ACCESS not-accessible
        STATUS     current
        DESCRIPTION
            "This table is used for querying the information about the optical transceiver of the PON port.
             The index of this table is ifIndex.
            "
        ::= { hwGponDeviceControlObjects 51 }

    hwGponOltOpticsDdmInformationEntry OBJECT-TYPE
        SYNTAX     HwGponOltOpticsDdmInformationEntry
        MAX-ACCESS not-accessible
        STATUS     current
        DESCRIPTION
            "This table is used for querying the information about the optical transceiver of the PON port.
             The index of this entry is ifIndex.
            "
        INDEX       { ifIndex }
        ::= { hwGponOltOpticsDdmInformationTable 1 }

    HwGponOltOpticsDdmInformationEntry ::=
        SEQUENCE {
                 hwGponOpticsTemperature
            Integer32,
         hwGponOpticsSupplyVoltage
            Integer32,
         hwGponOpticsTxBiasCurrent
            Integer32,
         hwGponOpticsTxPower
            Integer32,
         hwGponOpticsRxPower
            Integer32
         }

    hwGponOpticsTemperature OBJECT-TYPE
        SYNTAX Integer32
        MAX-ACCESS read-only
        STATUS current
        DESCRIPTION
            "Optics temperature,units of C(centigrade)."
        ::= { hwGponOltOpticsDdmInformationEntry 1 }

    hwGponOpticsSupplyVoltage OBJECT-TYPE
        SYNTAX Integer32
        MAX-ACCESS read-only
        STATUS current
        DESCRIPTION
            "Supply voltage,units of 0.01V."
        ::= { hwGponOltOpticsDdmInformationEntry 2 }

    hwGponOpticsTxBiasCurrent OBJECT-TYPE
        SYNTAX Integer32
        MAX-ACCESS read-only
        STATUS current
        DESCRIPTION
            "Optics current,units of mA."
        ::= { hwGponOltOpticsDdmInformationEntry 3 }

    hwGponOpticsTxPower OBJECT-TYPE
        SYNTAX Integer32
        MAX-ACCESS read-only
        STATUS current
        DESCRIPTION
            "Optics send power,units of 0.01dBm."
        ::= { hwGponOltOpticsDdmInformationEntry 4 }

    hwGponOpticsRxPower OBJECT-TYPE
        SYNTAX Integer32
        MAX-ACCESS read-only
        STATUS current
        DESCRIPTION
            "Optics receive power,units of 0.01dBm."
        ::= { hwGponOltOpticsDdmInformationEntry 5 }


-- Table 52:HwGponDeviceOntAlarmStateTable
    hwGponDeviceOntAlarmStateTable OBJECT-TYPE
        SYNTAX     SEQUENCE OF HwGponDeviceOntAlarmStateEntry
        MAX-ACCESS not-accessible
        STATUS     current
        DESCRIPTION
            "The table is used to query the state of the ONT alarms,
             The alarms include SDi, SFi, DOWi, and LOSi alarms.
             The indexes of this table are ifIndex and
             hwGponDeviceOntObjectIndex.
            "
        ::= { hwGponDeviceControlObjects 52 }

    hwGponDeviceOntAlarmStateEntry OBJECT-TYPE
        SYNTAX     HwGponDeviceOntAlarmStateEntry
        MAX-ACCESS not-accessible
        STATUS     current
        DESCRIPTION
            "The table is used to query the state of the ONT alarms,
             The alarms include SDi, SFi, DOWi, and LOSi alarms.
             The indexes of this entry are ifIndex and
             hwGponDeviceOntObjectIndex.
            "
        INDEX       { ifIndex, hwGponDeviceOntObjectIndex }
        ::= { hwGponDeviceOntAlarmStateTable 1 }

    HwGponDeviceOntAlarmStateEntry ::=
        SEQUENCE {
                    hwGponDeviceOntAlarmStateSDi                Integer32,
                    hwGponDeviceOntAlarmStateSFi                Integer32,
            hwGponDeviceOntAlarmStateDOWi               Integer32,
                hwGponDeviceOntAlarmStateLOSi               Integer32,
            hwGponDeviceOntAlarmStateRDIi               Integer32
         }

    hwGponDeviceOntAlarmStateSDi OBJECT-TYPE
        SYNTAX Integer32
        MAX-ACCESS read-only
        STATUS current
        DESCRIPTION
            "ONU signal deterioration alarm."
        ::= { hwGponDeviceOntAlarmStateEntry 1 }

    hwGponDeviceOntAlarmStateSFi OBJECT-TYPE
        SYNTAX Integer32
        MAX-ACCESS read-only
        STATUS current
        DESCRIPTION
            "ONU signal failure alarm."
        ::= { hwGponDeviceOntAlarmStateEntry 2 }

    hwGponDeviceOntAlarmStateDOWi OBJECT-TYPE
        SYNTAX Integer32
        MAX-ACCESS read-only
        STATUS current
        DESCRIPTION
            "ONU window drift alarm."
        ::= { hwGponDeviceOntAlarmStateEntry 3 }

    hwGponDeviceOntAlarmStateLOSi OBJECT-TYPE
        SYNTAX Integer32
        MAX-ACCESS read-only
        STATUS current
        DESCRIPTION
            "ONU signal loss alarm."
        ::= { hwGponDeviceOntAlarmStateEntry 4 }

    hwGponDeviceOntAlarmStateRDIi  OBJECT-TYPE
        SYNTAX Integer32
        MAX-ACCESS read-only
        STATUS current
        DESCRIPTION
            "ONT remote bit error alarm."
        ::= { hwGponDeviceOntAlarmStateEntry 5 }

-- Table 53:HwGponDeviceOntOpticsDdmInfoTable
    hwGponDeviceOntOpticsDdmInfoTable OBJECT-TYPE
        SYNTAX     SEQUENCE OF HwGponDeviceOntOpticsDdmInfoEntry
        MAX-ACCESS not-accessible
        STATUS     current
        DESCRIPTION
            "This table is used to query the information about the ONT optical transceiver, including the Rx optical power,
         Tx optical power, bias current, temperature, and optical power.
             The indexes of this table are ifIndex and hwGponDeviceOntObjectIndex.
            "
        ::= { hwGponDeviceControlObjects 53 }

    hwGponDeviceOntOpticsDdmInfoEntry OBJECT-TYPE
        SYNTAX     HwGponDeviceOntOpticsDdmInfoEntry
        MAX-ACCESS not-accessible
        STATUS     current
        DESCRIPTION
            "This table is used to query the information about the ONT optical transceiver, including the Rx optical power,
         Tx optical power, bias current, temperature, and optical power.
             The indexes of this entry are ifIndex and hwGponDeviceOntObjectIndex.
        "
        INDEX       { ifIndex, hwGponDeviceOntObjectIndex }
        ::= { hwGponDeviceOntOpticsDdmInfoTable 1 }

    HwGponDeviceOntOpticsDdmInfoEntry ::=
        SEQUENCE {
                    hwGponOntOpticsTemperature                Integer32,
            hwGponOntOpticsBiasCurrent                Integer32,
            hwGponOntOpticsTxPower                    Integer32,
            hwGponOntOpticsRxPower                    Integer32,
            hwGponOntOpticsVoltage                    Integer32,
            hwGponOntOpticsOltRxOntPower              Integer32,
            hwGponOntOpticsDdmAniCATVRxPower          Integer32
         }

    hwGponOntOpticsTemperature OBJECT-TYPE
        SYNTAX Integer32
        MAX-ACCESS read-only
        STATUS current
        DESCRIPTION
            "The temperature of the optical module."
        ::= { hwGponDeviceOntOpticsDdmInfoEntry 1 }

    hwGponOntOpticsBiasCurrent OBJECT-TYPE
        SYNTAX Integer32
        MAX-ACCESS read-only
        STATUS current
        DESCRIPTION
            "The Bias Current of the optical module."
        ::= { hwGponDeviceOntOpticsDdmInfoEntry 2 }

    hwGponOntOpticsTxPower OBJECT-TYPE
        SYNTAX Integer32
        MAX-ACCESS read-only
        STATUS current
        DESCRIPTION
            "The transmitting power of the optical module."
        ::= { hwGponDeviceOntOpticsDdmInfoEntry 3 }

    hwGponOntOpticsRxPower OBJECT-TYPE
        SYNTAX Integer32
        MAX-ACCESS read-only
        STATUS current
        DESCRIPTION
            "The receiving power of the optical module."
        ::= { hwGponDeviceOntOpticsDdmInfoEntry 4 }

    hwGponOntOpticsVoltage OBJECT-TYPE
        SYNTAX Integer32
        MAX-ACCESS read-only
        STATUS current
        DESCRIPTION
            "Voltage of the ONT optical transceiver."
        ::= { hwGponDeviceOntOpticsDdmInfoEntry 5 }

    hwGponOntOpticsOltRxOntPower OBJECT-TYPE
        SYNTAX Integer32
        MAX-ACCESS read-only
        STATUS current
        DESCRIPTION
            "The ONT optical power received on the OLT, unit dBm.
             The relationship between the actual value and the value get from this leaf node is as follows,
             Actual value = ((Node value - 10000) / 100)
            "
        ::= { hwGponDeviceOntOpticsDdmInfoEntry 6 }

    hwGponOntOpticsDdmAniCATVRxPower OBJECT-TYPE
        SYNTAX Integer32
        MAX-ACCESS read-only
        STATUS current
        DESCRIPTION
            "Indicates the CATV receiving optical power of the optical module,unit dBm."
        ::= { hwGponDeviceOntOpticsDdmInfoEntry 7 }

-- Table hwXponDeviceOntSnmpProfileTable
    -- 1.3.6.1.4.1.2011.5.100.1.1.1.54
    hwXponDeviceOntSnmpProfileTable OBJECT-TYPE
        SYNTAX SEQUENCE OF HwXponDeviceOntSnmpProfileEntry
        MAX-ACCESS not-accessible
        STATUS current
        DESCRIPTION
            "XPON MDU SNMP Agent config information.
             This table supports operations, such as adding, modifying, querying and deleting only when the ONT is in the SNMP management mode.
             The index of this table is hwXponDeviceOntSnmpProfileNameIndex.
            "
        ::= { hwGponDeviceControlObjects 54 }

    -- 1.3.6.1.4.1.2011.5.100.1.1.1.54.1
    hwXponDeviceOntSnmpProfileEntry OBJECT-TYPE
        SYNTAX HwXponDeviceOntSnmpProfileEntry
        MAX-ACCESS not-accessible
        STATUS current
        DESCRIPTION
            "XPON MDU SNMP Agent config information.
             This table supports operations, such as adding, modifying, querying and deleting only when the ONT is in the SNMP management mode.
             The index of this entry is hwXponDeviceOntSnmpProfileNameIndex.
            "
        INDEX { IMPLIED hwXponDeviceOntSnmpProfileNameIndex }
        ::= { hwXponDeviceOntSnmpProfileTable 1 }

    HwXponDeviceOntSnmpProfileEntry ::=
        SEQUENCE {
                  hwXponDeviceOntSnmpProfileNameIndex
                    OCTET STRING,
                  hwXponDeviceOntSnmpVersion
                    INTEGER,
                  hwXponDeviceOntSnmpReadCommunityName
                    OCTET STRING,
                  hwXponDeviceOntSnmpWriteCommunityName
                    OCTET STRING,
                  hwXponDeviceOntSnmpTrapHostIP
                    IpAddress,
                  hwXponDeviceOntSnmpTrapHostSrcUDPPort
                    Integer32,
                  hwXponDeviceOntSnmpSecurityName
                    OCTET STRING,
                  hwXponDeviceOntSnmpRowStatus
                    RowStatus,
                  hwXponDeviceOntSnmpUsmUsername
                    OCTET STRING,
                  hwXponDeviceOntSnmpAuthenticationMode
                    INTEGER,
                  hwXponDeviceOntSnmpAuthenticationPassword
                    OCTET STRING,
                  hwXponDeviceOntSnmpPrivacyMode
                    INTEGER,
                  hwXponDeviceOntSnmpPrivacyPassword
                    OCTET STRING,
                  hwXponDeviceOntSnmpSecurityLevel
                    INTEGER
                 }

    -- 1.3.6.1.4.1.2011.5.100.1.1.1.54.1.1
    hwXponDeviceOntSnmpProfileNameIndex OBJECT-TYPE
        SYNTAX OCTET STRING (SIZE (1..63))
        MAX-ACCESS not-accessible
        STATUS current
        DESCRIPTION
            "ONT SNMP profile name."
        ::= { hwXponDeviceOntSnmpProfileEntry 1 }

    -- 1.3.6.1.4.1.2011.5.100.1.1.1.54.1.2
    hwXponDeviceOntSnmpVersion OBJECT-TYPE
        SYNTAX INTEGER {
                         v1(1),
                         v2c(2),
                         v3(3)
                       }
        MAX-ACCESS read-write
        STATUS current
        DESCRIPTION
            "Snmp Version.
             Options:
             1. v1(1)  -v1
             2. v2c(2) -v2c
             3. v3(3)  -v3
            "
        DEFVAL { v1 }
        ::= { hwXponDeviceOntSnmpProfileEntry 2 }

    -- 1.3.6.1.4.1.2011.5.100.1.1.1.54.1.3
    hwXponDeviceOntSnmpReadCommunityName OBJECT-TYPE
        SYNTAX OCTET STRING (SIZE (0..32))
        MAX-ACCESS read-write
        STATUS current
        DESCRIPTION
            "Name of a read community."
        ::= { hwXponDeviceOntSnmpProfileEntry 3 }

    -- 1.3.6.1.4.1.2011.5.100.1.1.1.54.1.4
    hwXponDeviceOntSnmpWriteCommunityName OBJECT-TYPE
        SYNTAX OCTET STRING (SIZE (0..32))
        MAX-ACCESS read-write
        STATUS current
        DESCRIPTION
            "Name of a write community."
        ::= { hwXponDeviceOntSnmpProfileEntry 4 }

    -- 1.3.6.1.4.1.2011.5.100.1.1.1.54.1.5
    hwXponDeviceOntSnmpTrapHostIP OBJECT-TYPE
        SYNTAX IpAddress
        MAX-ACCESS read-write
        STATUS current
        DESCRIPTION
            "The target host address of sending trap message."
        ::= { hwXponDeviceOntSnmpProfileEntry 5 }

    -- 1.3.6.1.4.1.2011.5.100.1.1.1.54.1.6
    hwXponDeviceOntSnmpTrapHostSrcUDPPort OBJECT-TYPE
        SYNTAX Integer32
        MAX-ACCESS read-write
        STATUS current
        DESCRIPTION
            "UDP source port for sending traps.
             Range: 1-65535
            "
        ::= { hwXponDeviceOntSnmpProfileEntry 6 }

    -- 1.3.6.1.4.1.2011.5.100.1.1.1.54.1.7
    hwXponDeviceOntSnmpSecurityName OBJECT-TYPE
        SYNTAX OCTET STRING (SIZE (1..32))
        MAX-ACCESS read-write
        STATUS current
        DESCRIPTION
            "The security name of SNMP message."
        ::= { hwXponDeviceOntSnmpProfileEntry 7 }

    -- 1.3.6.1.4.1.2011.5.100.1.1.1.54.1.8
    hwXponDeviceOntSnmpRowStatus OBJECT-TYPE
        SYNTAX RowStatus
        MAX-ACCESS read-create
        STATUS current
        DESCRIPTION
            "The row status, which is used to differentiate the creation,
             modification and deletion of a row.
             Options:
             1. createAndGo(4) -create a new instance of a conceptual row
             2. destroy(6)     -delete the instances associated with an existing conceptual row
            "
        ::= { hwXponDeviceOntSnmpProfileEntry 8 }

    -- 1.3.6.1.4.1.2011.5.100.1.1.1.54.1.9
    hwXponDeviceOntSnmpUsmUsername OBJECT-TYPE
        SYNTAX OCTET STRING (SIZE (0..32))
        MAX-ACCESS read-write
        STATUS current
        DESCRIPTION
            "The name of the SNMPv3 user."
        ::= { hwXponDeviceOntSnmpProfileEntry 9 }

    -- 1.3.6.1.4.1.2011.5.100.1.1.1.54.1.10
    hwXponDeviceOntSnmpAuthenticationMode OBJECT-TYPE
        SYNTAX INTEGER{
            none(1),
            hmacMd5(2),
            hmacSha(3),
            invalid(255)
        }
        MAX-ACCESS read-write
        STATUS current
        DESCRIPTION
            "This object indicates the user authentication mode.
             When the version of the SNMP profile is v1 or v2c, the invalid value will be returned.
             Options:
             1. none(1)        - No authentication mode
             2. hmacMd5(2)     - Hmac-md5 authentication mode
             3. hmacSha(3)     - Hmac-sha authentication mode
             4. invalid(255)   - Invalid value
            "
        ::= { hwXponDeviceOntSnmpProfileEntry 10 }

    -- 1.3.6.1.4.1.2011.5.100.1.1.1.54.1.11
    hwXponDeviceOntSnmpAuthenticationPassword OBJECT-TYPE
        SYNTAX OCTET STRING (SIZE (0..0 | 8..64))
        MAX-ACCESS read-write
        STATUS current
        DESCRIPTION
            "The authentication password."
        ::= { hwXponDeviceOntSnmpProfileEntry 11 }

    -- 1.3.6.1.4.1.2011.5.100.1.1.1.54.1.12
    hwXponDeviceOntSnmpPrivacyMode OBJECT-TYPE
        SYNTAX INTEGER{
            none(1),
            des56(2),
            tripleDes(3),
            aes128(4),
            aes192(20),
            aes256(21),
            invalid(255)
        }
        MAX-ACCESS read-write
        STATUS current
        DESCRIPTION
            "This object indicates the user encryption mode.
             When the version of the SNMP profile is v1 or v2c, the invalid value will be returned.
             Options:
             1. none(1)        - No encryption mode
             2. des56(2)       - 56-bit DES encryption mode
             3. tripleDes(3)   - 3DES encryption mode
             4. aes128(4)      - 128-bit AES encryption mode
             5. aes192(20)      - 192-bit AES encryption mode
             6. aes256(21)      - 256-bit AES encryption mode
             7. invalid(255)   - Invalid value
            "
        ::= { hwXponDeviceOntSnmpProfileEntry 12 }

    -- 1.3.6.1.4.1.2011.5.100.1.1.1.54.1.13
    hwXponDeviceOntSnmpPrivacyPassword OBJECT-TYPE
        SYNTAX OCTET STRING (SIZE (0..0 | 8..64))
        MAX-ACCESS read-write
        STATUS current
        DESCRIPTION
            "The encryption password."
        ::= { hwXponDeviceOntSnmpProfileEntry 13 }

    -- 1.3.6.1.4.1.2011.5.100.1.1.1.54.1.14
    hwXponDeviceOntSnmpSecurityLevel OBJECT-TYPE
        SYNTAX INTEGER{
            privacy(1),
            authentication(2),
            noauthnopriv(3),
            invalid(255)
        }
        MAX-ACCESS read-write
        STATUS current
        DESCRIPTION
            "This object indicates the trap security level.
             When the version of the SNMP profile is v1 or v2c, the invalid value will be returned.
             Options:
             1. privacy(1)         - Authenticate and encrypt the SNMPv3 trap packet
             2. authentication(2)  - Authenticate but not encrypt the SNMPv3 trap packet
             3. noauthnopriv(3)    - Not authenticate nor encrypt the SNMPv3 trap packet
             4. invalid(255)       - Invalid value
            "
        ::= { hwXponDeviceOntSnmpProfileEntry 14 }

    -- Table 55: hwGponOntPortVlanTranslationTable
    hwGponOntPortVlanTranslationTable OBJECT-TYPE
        SYNTAX     SEQUENCE OF HwGponOntPortVlanTranslationEntry
        MAX-ACCESS not-accessible
        STATUS     current
        DESCRIPTION
            "VLAN and priority switching configuration table of the GPON ONT port, supporting configuration only when the ONT port type is Ethernet.
             The indexes of this table are ifIndex,
             hwGponDeviceOntObjectIndex, hwGponOntifEthernetPort,
             and hwGponOntPortVlanTranslationInnerIndex.
            "
        ::= { hwGponDeviceControlObjects 55 }

    hwGponOntPortVlanTranslationEntry OBJECT-TYPE
        SYNTAX     HwGponOntPortVlanTranslationEntry
        MAX-ACCESS not-accessible
        STATUS     current
        DESCRIPTION
            "VLAN and priority switching configuration table of the GPON ONT port, supporting configuration only when the ONT port type is Ethernet.
             The indexes of this entry are ifIndex,
             hwGponDeviceOntObjectIndex, hwGponOntifEthernetPort,
             and hwGponOntPortVlanTranslationInnerIndex.
            "
        INDEX       { ifIndex, hwGponDeviceOntObjectIndex,
                       hwGponOntifEthernetPort, hwGponOntPortVlanTranslationInnerIndex }
        ::= { hwGponOntPortVlanTranslationTable 1 }

    HwGponOntPortVlanTranslationEntry ::=
        SEQUENCE {
                hwGponOntPortVlanTranslationInnerIndex      Integer32,
                hwGponOntPortVlanTranslationCVlan           Integer32,
                hwGponOntPortVlanTranslationType            INTEGER,
                hwGponOntPortVlanTranslationSVlan           Integer32,
                hwGponOntPortVlanTranslationPri             Integer32,
                hwGponOntPortVlanTranslationRowStatus       RowStatus
                }

    hwGponOntPortVlanTranslationInnerIndex  OBJECT-TYPE
        SYNTAX     Integer32
        MAX-ACCESS   not-accessible
        STATUS      current
        DESCRIPTION
            "The inner index of vlan translation of ONT port, it is used to identify the maximum
             8 different vlan translation of one ONT port.
             Range: 0-7
            "
        ::= { hwGponOntPortVlanTranslationEntry 1 }

    hwGponOntPortVlanTranslationCVlan  OBJECT-TYPE
        SYNTAX     Integer32
        MAX-ACCESS   read-write
        STATUS      current
        DESCRIPTION
            "The user vlan which will be translated to the service vlan and priority,
             when datagram is transmitted from the ONT port.
             Range: 0-4095
            "
        ::= { hwGponOntPortVlanTranslationEntry 2 }

    hwGponOntPortVlanTranslationType  OBJECT-TYPE
        SYNTAX     INTEGER
            {
             vlan (1),
             vlanAndPri (2)
            }
        MAX-ACCESS   read-write
        STATUS      current
        DESCRIPTION
            "The vlan translation type of ONT port.
             Options:
             1. vlan (1)       -Vlan translation
             2. vlanAndPri (2) -Vlan and priority translation
            "
        ::= { hwGponOntPortVlanTranslationEntry 3 }

    hwGponOntPortVlanTranslationSVlan  OBJECT-TYPE
        SYNTAX     Integer32
        MAX-ACCESS   read-write
        STATUS      current
        DESCRIPTION
            "The service vlan which the user vlan will be translated to, when datagram
             is transmitted from the ONT port.
             Range: 0-4095
            "
        ::= { hwGponOntPortVlanTranslationEntry 4 }

    hwGponOntPortVlanTranslationPri  OBJECT-TYPE
        SYNTAX     Integer32
        MAX-ACCESS   read-write
        STATUS      current
        DESCRIPTION
            "The priority after the user vlan translation, when datagram
             is transmitted from the ONT port.
             Range: 0-7
            "
        DEFVAL { 0 }
        ::= { hwGponOntPortVlanTranslationEntry 5 }

    hwGponOntPortVlanTranslationRowStatus OBJECT-TYPE
        SYNTAX     RowStatus
        MAX-ACCESS    read-create
        STATUS      current
        DESCRIPTION
            "Row status. This object is used to differentiate the
             creation, modification and deletion operations for an object.
             Options:
             1. createAndGo(4) -create a new instance of a conceptual row
             2. destroy(6)     -delete the instances associated with an existing conceptual row
            "
        ::= { hwGponOntPortVlanTranslationEntry 6 }

-- Table:HwOntLoadSelectTable 56
    -- 1.3.6.1.4.1.2011.5.100.1.1.1.56
    hwOntLoadSelectTable OBJECT-TYPE
        SYNTAX     SEQUENCE OF HwOntLoadSelectEntry
        MAX-ACCESS not-accessible
        STATUS     current
        DESCRIPTION
            "It is used to add ont to loading list and query the loading state for ont.
             The indexes of this table are ifIndex and hwGponDeviceOntObjectIndex.
            "
        ::= { hwGponDeviceControlObjects 56 }

    hwOntLoadSelectEntry OBJECT-TYPE
        SYNTAX     HwOntLoadSelectEntry
        MAX-ACCESS not-accessible
        STATUS     current
        DESCRIPTION
            "It is used to add ont to loading list and query the loading state for ont.
             The indexes of this entry are ifIndex and hwGponDeviceOntObjectIndex.
            "
        INDEX       { ifIndex, hwGponDeviceOntObjectIndex }
        ::= { hwOntLoadSelectTable 1 }

    HwOntLoadSelectEntry ::=
        SEQUENCE
            {
            hwOntLoadSelectState                  INTEGER,
            hwOntLoadSelectProgress               Integer32,
            hwOntLoadSelectRowStatus              RowStatus,
            hwOntLoadSelectPriority               Integer32,
            hwOntLoadSelectActiveMode             INTEGER
            }

    hwOntLoadSelectState OBJECT-TYPE
        SYNTAX INTEGER
            {
            ready(1),
            loading(2),
            success(3),
            fail(4),
            invalidValue(-1)
            }
        MAX-ACCESS read-only
        STATUS current
        DESCRIPTION
            "The loading state of the ont.
             Options:
             1. ready(1)         -The loading state of the ont is ready
             2. loading(2)       -The loading state of the ont is loading
             3. success(3)       -The loading state of the ont is success
             4. fail(4)          -The loading state of the ont is fail
             5. invalidValue(-1) -The loading state of the ont is invalid
            "
        ::= { hwOntLoadSelectEntry 1 }

    hwOntLoadSelectProgress OBJECT-TYPE
        SYNTAX Integer32
        MAX-ACCESS read-only
        STATUS current
        DESCRIPTION
            "The loading progress of the ont."
        ::= { hwOntLoadSelectEntry 2 }

    hwOntLoadSelectRowStatus OBJECT-TYPE
        SYNTAX     RowStatus
        MAX-ACCESS    read-create
        STATUS current
        DESCRIPTION
            "Row status. This object is used to differentiate the
             creation and deletion operations for an object.
             Options:
             1. createAndGo(4) -create a new instance of a conceptual row
             2. destroy(6)     -delete the instances associated with an existing conceptual row
            "
        ::= { hwOntLoadSelectEntry 3 }

        hwOntLoadSelectPriority OBJECT-TYPE
            SYNTAX Integer32
            MAX-ACCESS    read-write
            STATUS current
            DESCRIPTION
                "This object is used to set the priority of an ONT loading task.
                 A smaller value represents a higher priority.
                "
            ::= { hwOntLoadSelectEntry 4 }

        hwOntLoadSelectActiveMode OBJECT-TYPE
            SYNTAX INTEGER {
                nextstartup(1),
                immediate(2),
                graceful(3),
                invalid(-1)
            }
            MAX-ACCESS    read-write
            STATUS current
            DESCRIPTION
                "This object is used to configure the effect mode of an loaded ONT.
                 Options:
                 1. nextstartup(1)         - Indicates that the ONT takes effect after next startup
                 2. immediate(2)           - Indicates that the ONT takes effect immediately
                 3. graceful(3)            - Indicates that the ONT takes effect gracefully
                 4. invalid(-1)            - Indicates that the query fails or no information is detected
                "
            ::= { hwOntLoadSelectEntry 5 }

-- Table:HwOntLoadCtrlTable 57
    -- 1.3.6.1.4.1.2011.5.100.1.1.1.57
    hwOntLoadCtrlTable OBJECT IDENTIFIER
        ::= { hwGponDeviceControlObjects 57}

    hwOntLoadFileType OBJECT-TYPE
        SYNTAX INTEGER
            {
            app(1),
            cfg(2),
            invalid(255)
            }
        MAX-ACCESS read-write
        STATUS current
        DESCRIPTION
            "ONT file type.
             Options:
             1. app(1)          - Indicates that the ONT file type is application.
             2. cfg(2)          - Indicates that the ONT file type is configuration.
             3. invalid(255)    - Indicates that the ONT file type is invalid.
            "
        ::= { hwOntLoadCtrlTable 1 }

    hwOntLoadServerIpAddr OBJECT-TYPE
        SYNTAX     IpAddress
        MAX-ACCESS    read-write
        STATUS current
        DESCRIPTION
            "Server IP address."
        ::= { hwOntLoadCtrlTable 2 }

    hwOntLoadProtocol OBJECT-TYPE
        SYNTAX     INTEGER{
                             tftp(1),
                             ftp(2),
                             sftp(3),
                             invalid(255)
                               }
        MAX-ACCESS    read-write
        STATUS current
        DESCRIPTION
            "Transfer Protocol.
             Options:
             1. tftp(1)         - Indicates that the ONT loading protocol is tftp.
             2. ftp(2)          - Indicates that the ONT loading protocol is ftp.
             3. sftp(3)         - Indicates that the ONT loading protocol is sftp..
             4. invalid(255)    - Indicates that the ONT loading protocol is invalid.
            "
        ::= { hwOntLoadCtrlTable 3 }

    hwOntLoadFileName OBJECT-TYPE
    SYNTAX OCTET STRING (SIZE (0..80))
        MAX-ACCESS    read-write
        STATUS current
        DESCRIPTION
            "File name."
        ::= { hwOntLoadCtrlTable 4 }

    hwOntLoadUserName OBJECT-TYPE
        SYNTAX OCTET STRING (SIZE (0..16))
        MAX-ACCESS    read-write
        STATUS current
        DESCRIPTION
            "User name."
        ::= { hwOntLoadCtrlTable 5 }

    hwOntLoadPassword OBJECT-TYPE
        SYNTAX OCTET STRING (SIZE (0..16))
        MAX-ACCESS    read-write
        STATUS current
        DESCRIPTION
            "Password."
        ::= { hwOntLoadCtrlTable 6 }

    hwOntLoadAdminStatus OBJECT-TYPE
        SYNTAX     INTEGER
            {
            start(1),
            stop(2)
            }
        MAX-ACCESS    read-write
        STATUS current
        DESCRIPTION
            "ONT loading management status.
             Options:
             1. start(1)        - Indicates that the ONT loading management status is start.
             2. stop(2)         - Indicates that the ONT loading management status is stop.
            "
        ::= { hwOntLoadCtrlTable 7 }


    hwOntLoadXmlIndex OBJECT-TYPE
        SYNTAX Integer32
        MAX-ACCESS    read-write
        STATUS current
        DESCRIPTION
            "F/S/P of ONT loading xml file. Reading this object will result in implementation-specific results."
        ::= { hwOntLoadCtrlTable 8 }

    hwOntLoadXmlOntObjectIndex OBJECT-TYPE
        SYNTAX     Integer32
        MAX-ACCESS   read-write
        STATUS current
        DESCRIPTION
            "ONT ID of loading xml file. Reading this object will result in implementation-specific results."
        ::= { hwOntLoadCtrlTable 9 }

    hwOntLoadImageActiveMode OBJECT-TYPE
        SYNTAX     INTEGER
            {
            nextstartup(1),
            immediate(2),
            graceful(3),
            invalid(-1)
            }
        MAX-ACCESS    read-write
        STATUS current
        DESCRIPTION
            "Active mode of ont loading.
             Default: 1
             Options:
             1. nextstartup(1)         - Indicates that the ONT takes effect after next startup
             2. immediate(2)           - Indicates that the ONT takes effect immediately
             3. graceful(3)            - Indicates that the ONT takes effect gracefully
             4. invalid(-1)            - Indicates that the query fails or no information is detected
            "
        ::= { hwOntLoadCtrlTable 10 }

    hwOntLoadXmlAES128Key OBJECT-TYPE
        SYNTAX OCTET STRING (SIZE (0..16))
        MAX-ACCESS    read-write
        STATUS current
        DESCRIPTION
            "This object indicates the AES-128 cryptographic key for the ont xml file.
             This AES-128 key is 128bits(16 Bytes).
            "
        ::= { hwOntLoadCtrlTable 11 }

    hwOntLoadServerPort OBJECT-TYPE
            SYNTAX     Integer32 ( 0..65535)
            MAX-ACCESS   read-write
            STATUS current
            DESCRIPTION
                "This object indicates the port of server for ont loading.
                 The TFTP port default value is 69.
		 The FTP port default value is 21.
                 The SFTP port default value is 22.
                "
            ::= { hwOntLoadCtrlTable 12 }

-- Table58 hwGponDeviceOntSnmpStaticRouteTable
    -- 1.3.6.1.4.1.2011.5.100.1.1.1.58
    hwGponDeviceOntSnmpStaticRouteTable OBJECT-TYPE
        SYNTAX     SEQUENCE OF HwGponDeviceOntSnmpStaticRouteEntry
        MAX-ACCESS not-accessible
        STATUS     current
        DESCRIPTION
            "This is the ONT SNMP static route configuration table.
             This table is used to configure and query the SNMP route configuration of an ONT.
             The indexes of this table are ifIndex, hwGponDeviceOntObjectIndex and hwGponOntSnmpStaticRouteIndex.
            "
        ::= { hwGponDeviceControlObjects 58 }

    hwGponDeviceOntSnmpStaticRouteEntry OBJECT-TYPE
        SYNTAX     HwGponDeviceOntSnmpStaticRouteEntry
        MAX-ACCESS not-accessible
        STATUS     current
        DESCRIPTION
            "This is the ONT SNMP static route configuration table.
             This table is used to configure and query the SNMP route configuration of an ONT.
             The indexes of this entry are ifIndex, hwGponDeviceOntObjectIndex and hwGponOntSnmpStaticRouteIndex."
        INDEX       { ifIndex, hwGponDeviceOntObjectIndex, hwGponOntSnmpStaticRouteIndex }
        ::= { hwGponDeviceOntSnmpStaticRouteTable 1 }

    HwGponDeviceOntSnmpStaticRouteEntry ::=
       SEQUENCE {
              hwGponOntSnmpStaticRouteIndex                        Integer32,
              hwGponOntSnmpStaticRouteIpAddress                    IpAddress,
              hwGponOntSnmpStaticRouteNetMask                      IpAddress,
              hwGponOntSnmpStaticRouteNextHop                      IpAddress,
              hwGponOntSnmpStaticRouteRowStatus                    RowStatus
              }

    hwGponOntSnmpStaticRouteIndex  OBJECT-TYPE
        SYNTAX     Integer32
        MAX-ACCESS   not-accessible
        STATUS      current
        DESCRIPTION
            "ONT SNMP static route table index."
        ::= { hwGponDeviceOntSnmpStaticRouteEntry 1 }

    hwGponOntSnmpStaticRouteIpAddress  OBJECT-TYPE
        SYNTAX     IpAddress
        MAX-ACCESS   read-write
        STATUS      current
        DESCRIPTION
            "IP address."
        ::= { hwGponDeviceOntSnmpStaticRouteEntry 2 }

    hwGponOntSnmpStaticRouteNetMask  OBJECT-TYPE
        SYNTAX     IpAddress
        MAX-ACCESS   read-write
        STATUS      current
        DESCRIPTION
            "Subnet mask."
        ::= { hwGponDeviceOntSnmpStaticRouteEntry 3 }


    hwGponOntSnmpStaticRouteNextHop  OBJECT-TYPE
        SYNTAX     IpAddress
        MAX-ACCESS   read-write
        STATUS      current
        DESCRIPTION
            "Next hop."
        ::= { hwGponDeviceOntSnmpStaticRouteEntry 4 }

    hwGponOntSnmpStaticRouteRowStatus OBJECT-TYPE
        SYNTAX       RowStatus
        MAX-ACCESS   read-create
        STATUS      current
        DESCRIPTION
            "Row status. This object is used to differentiate the creation,
             modification and deletion operations for an object.
             Options:
             1. createAndGo(4) -create a new instance of a conceptual row
             2. destroy(6)     -delete the instances associated with an existing conceptual row
            "
        ::= { hwGponDeviceOntSnmpStaticRouteEntry 5 }

-- Table1 hwGponDeviceGemLineTestTable
    -- 1.3.6.1.4.1.2011.5.100.1.1.16.1
    hwGponDeviceGemPortLineTestTable OBJECT-TYPE
        SYNTAX     SEQUENCE OF HwGponDeviceGemPortLineTestEntry
        MAX-ACCESS not-accessible
        STATUS     current
        DESCRIPTION
            "This is the GEM port line test table.
             This table is used to do line testing from OLT to ONT GEM port.
             The indexes of this table are ifIndex and hwGponDevicePortidObjectIndex.
            "
        ::= { hwGponDeviceLineTestObjects 1 }

    hwGponDeviceGemPortLineTestEntry OBJECT-TYPE
        SYNTAX     HwGponDeviceGemPortLineTestEntry
        MAX-ACCESS not-accessible
        STATUS     current
        DESCRIPTION
            "This is the GEM port line test table.
             This table is used to do line testing from OLT to ONT GEM port.
             The indexes of this entry are ifIndex and hwGponDevicePortidObjectIndex.
            "
        INDEX       { ifIndex, hwGponDevicePortidObjectIndex }
        ::= { hwGponDeviceGemPortLineTestTable 1 }

    HwGponDeviceGemPortLineTestEntry ::=
        SEQUENCE {
            hwGponGemPortLineTestFrameLength                Integer32,
            hwGponGemPortLineTestFramesTxNum                Integer32,
            hwGponGemPortLineTestFramesRxNum                Integer32
        }

    hwGponGemPortLineTestFrameLength   OBJECT-TYPE
        SYNTAX  Integer32
        MAX-ACCESS    read-write
        STATUS    current
        DESCRIPTION
            "Frame length of GEM port line test.
             Reading this object will result in implementation-specific results.
             Range: 64-1518
             Default: 64
            "

        ::= { hwGponDeviceGemPortLineTestEntry 1 }

    hwGponGemPortLineTestFramesTxNum   OBJECT-TYPE
        SYNTAX  Integer32
        MAX-ACCESS    read-write
        STATUS    current
        DESCRIPTION
            "Number of GEM port line test frames sending.
             Reading this object will result in implementation-specific results.
             Range: 5-100
             Default: 5
            "

        ::= { hwGponDeviceGemPortLineTestEntry 2 }

    hwGponGemPortLineTestFramesRxNum   OBJECT-TYPE
        SYNTAX  Integer32
        MAX-ACCESS    read-only
        STATUS    current
        DESCRIPTION
            "Number of GEM port line test frames receiving."
        ::= { hwGponDeviceGemPortLineTestEntry 3 }


-- Table2 hwGponDeviceOntUniLineTestTable
    -- 1.3.6.1.4.1.2011.5.100.1.1.16.2
    hwGponDeviceOntUniLineTestTable OBJECT-TYPE
        SYNTAX     SEQUENCE OF HwGponDeviceOntUniLineTestEntry
        MAX-ACCESS not-accessible
        STATUS     current
        DESCRIPTION
            "This is the ONT UNI line test table.
             This table is used to do line testing from OLT to ONT UNI.
             The indexes of this table are ifIndex, hwGponDeviceOntObjectIndex,
             hwGponOntUniPhyType, and hwGponOntUniPhyIndex.
            "
        ::= { hwGponDeviceLineTestObjects 2 }

    hwGponDeviceOntUniLineTestEntry OBJECT-TYPE
        SYNTAX     HwGponDeviceOntUniLineTestEntry
        MAX-ACCESS not-accessible
        STATUS     current
        DESCRIPTION
            "This is the ONT UNI line test table.
             This table is used to do line testing from OLT to ONT UNI.
             The indexes of this entry are ifIndex, hwGponDeviceOntObjectIndex,
             hwGponOntUniPhyType, and hwGponOntUniPhyIndex.
            "
        INDEX       { ifIndex, hwGponDeviceOntObjectIndex, hwGponOntUniPhyType, hwGponOntUniPhyIndex }
        ::= { hwGponDeviceOntUniLineTestTable 1 }

    HwGponDeviceOntUniLineTestEntry ::=
        SEQUENCE {
            hwGponOntUniPhyType                            INTEGER,
            hwGponOntUniPhyIndex                           Integer32,
            hwGponOntUniLineTestFrameLength                Integer32,
            hwGponOntUniLineTestFramesTxNum                Integer32,
            hwGponOntUniLineTestSrvFlowIndex               Integer32,
            hwGponOntUniLineTestFramesRxNum                Integer32
        }

    hwGponOntUniPhyType   OBJECT-TYPE
        SYNTAX  INTEGER {
                    t1(13),
                e1(14),
                fe(24),
                ge(34),
                moca(46),
                eth(47),
                iphost(50)
                        }
        MAX-ACCESS not-accessible
        STATUS    current
        DESCRIPTION
            "Physical type of ONT UNI.
            Options:
            1. t1(13)     -Physical type of ONT UNI is t1
            2. e1(14)     -Physical type of ONT UNI is e1
            3. fe(24)     -Physical type of ONT UNI is fe
            4. ge(34)     -Physical type of ONT UNI is ge
            5. moca(46)   -Physical type of ONT UNI is moca
            6. eth(47)    -Physical type of ONT UNI is eth
            7. iphost(50) -Physical type of ONT UNI is iphost
            "
        ::= { hwGponDeviceOntUniLineTestEntry 1 }

    hwGponOntUniPhyIndex   OBJECT-TYPE
        SYNTAX  Integer32
        MAX-ACCESS not-accessible
        STATUS    current
        DESCRIPTION
            "Physical index of ONT UNI.
            "
        ::= { hwGponDeviceOntUniLineTestEntry 2 }

    hwGponOntUniLineTestFrameLength   OBJECT-TYPE
        SYNTAX  Integer32
        MAX-ACCESS    read-write
        STATUS    current
        DESCRIPTION
            "Frame length of ONT UNI line test.
             Reading this object will result in implementation-specific results.
             Range: 64-1518
             Default: 64
            "

        ::= { hwGponDeviceOntUniLineTestEntry 3 }

    hwGponOntUniLineTestFramesTxNum   OBJECT-TYPE
        SYNTAX  Integer32
        MAX-ACCESS    read-write
        STATUS    current
        DESCRIPTION
            "Number of ONT UNI line test frames sending.
             Reading this object will result in implementation-specific results.
             Range: 5-100
             Default: 5
            "

       ::= { hwGponDeviceOntUniLineTestEntry 4 }

    hwGponOntUniLineTestSrvFlowIndex   OBJECT-TYPE
        SYNTAX  Integer32
        MAX-ACCESS    read-write
        STATUS    current
        DESCRIPTION
            "Service-port index of ONT UNI line test flow.
             Reading this object will result in implementation-specific results.
             Range: 1-16384
            "
        ::= { hwGponDeviceOntUniLineTestEntry 5 }

    hwGponOntUniLineTestFramesRxNum   OBJECT-TYPE
        SYNTAX  Integer32
        MAX-ACCESS    read-only
        STATUS    current
        DESCRIPTION
            "Number of ONT UNI line test frames receiving."
        ::= { hwGponDeviceOntUniLineTestEntry 6 }

    hwGponOntPortVlanCfgTable OBJECT-TYPE
        SYNTAX     SEQUENCE OF HwGponOntPortVlanCfgEntry
        MAX-ACCESS not-accessible
        STATUS     current
        DESCRIPTION
            "This is the ONT port vlan configuration table.This table
             is used to set, modify and query the vlan configuration of ONT port.
             The indexes of this table are ifIndex, hwGponDeviceOntObjectIndex,
             hwGponOntPortVlanCfgOntPhyType, hwGponOntPortVlanCfgOntPhyIndex,
             hwGponOntPortVlanCfgCVlan, hwGponOntPortVlanCfgCPri, and hwGponOntPortVlanCfgEtherType.
            "
        ::= { hwGponDeviceControlObjects 60 }

    hwGponOntPortVlanCfgEntry OBJECT-TYPE
        SYNTAX     HwGponOntPortVlanCfgEntry
        MAX-ACCESS not-accessible
        STATUS     current
        DESCRIPTION
            "This is the ONT port vlan configuration table.This table
             is used to set, modify and query the vlan configuration of ONT port.
             The indexes of this entry are ifIndex, hwGponDeviceOntObjectIndex,
             hwGponOntPortVlanCfgOntPhyType, hwGponOntPortVlanCfgOntPhyIndex,
             hwGponOntPortVlanCfgCVlan, hwGponOntPortVlanCfgCPri, and hwGponOntPortVlanCfgEtherType.
            "
        INDEX       { ifIndex, hwGponDeviceOntObjectIndex,
                      hwGponOntPortVlanCfgOntPhyType, hwGponOntPortVlanCfgOntPhyIndex,
                      hwGponOntPortVlanCfgCVlan,
                      hwGponOntPortVlanCfgCPri,
                      hwGponOntPortVlanCfgEtherType}
        ::= { hwGponOntPortVlanCfgTable 1 }

    HwGponOntPortVlanCfgEntry ::=
        SEQUENCE {
                hwGponOntPortVlanCfgOntPhyType              INTEGER,
                hwGponOntPortVlanCfgOntPhyIndex             Integer32,
                hwGponOntPortVlanCfgCVlan                   Integer32,
                hwGponOntPortVlanCfgSVlan                   Integer32,
                hwGponOntPortVlanCfgSPri                    Integer32,
                hwGponOntPortVlanCfgRowStatus               RowStatus,
                hwGponOntPortVlanCfgType                    INTEGER,
                hwGponOntPortVlanCfgCPri                    Integer32,
                hwGponOntPortVlanCfgEtherType               Integer32,
                hwGponOntPortVlanCfgSPriPolicy              INTEGER,
                hwGponOntPortVlanCfgDscpDefaultPriority     Integer32,
                hwGponOntPortVlanCfgTlsSwitch               INTEGER
                }

    hwGponOntPortVlanCfgOntPhyType OBJECT-TYPE
        SYNTAX INTEGER
            {
            vdsl(37),
            wifi(40),
            moca(46),
            eth(47),
            iphost(50)
            }
        MAX-ACCESS not-accessible
        STATUS current
        DESCRIPTION
            "Port type of the ONT.
             Options:
             1. vdsl(37)   -Port type of the ONT is vdsl
             2. wifi(40)   -Port type of the ONT is wifi
             3. moca(46)   -Port type of the ONT is moca
             4. eth(47)    -Port type of the ONT is eth
             5. iphost(50) -Port type of the ONT is iphost
            "
    ::= { hwGponOntPortVlanCfgEntry 1 }

    hwGponOntPortVlanCfgOntPhyIndex OBJECT-TYPE
        SYNTAX Integer32
        MAX-ACCESS not-accessible
        STATUS current
        DESCRIPTION
            "Port index of the ONT.
            "
        ::= { hwGponOntPortVlanCfgEntry 2 }

    hwGponOntPortVlanCfgCVlan  OBJECT-TYPE
        SYNTAX     Integer32
        MAX-ACCESS   not-accessible
        STATUS      current
        DESCRIPTION
            "The customer VLAN which is used as the index of the table.
             If configure standard vlan of the ont port, you can set S-VLAN same as C-VLAN,
             or don't set leaves hwGponOntPortVlanCfgSVlan and hwGponOntPortVlanCfgSPri.
             Range: 0-4095
            "
        ::= { hwGponOntPortVlanCfgEntry 3 }

    hwGponOntPortVlanCfgSVlan  OBJECT-TYPE
        SYNTAX     Integer32
        MAX-ACCESS   read-write
        STATUS      current
        DESCRIPTION
            "The Ont port service vlan. It is standard vlan of the ont port when the S-VLAN is same as the C-VLAN.
             Range: 0-4095
            "
        ::= { hwGponOntPortVlanCfgEntry 4 }

    hwGponOntPortVlanCfgSPri  OBJECT-TYPE
        SYNTAX     Integer32
        MAX-ACCESS   read-write
        STATUS      current
        DESCRIPTION
            "The service priority after the customer vlan translation or qinq.
             set Range: 0-7
             -1 indicates has not set the S-VLAN priority.
            "
        DEFVAL { 0 }
        ::= { hwGponOntPortVlanCfgEntry 5 }

    hwGponOntPortVlanCfgRowStatus OBJECT-TYPE
        SYNTAX     RowStatus
        MAX-ACCESS    read-create
        STATUS      current
        DESCRIPTION
            "Row status. This object is used to differentiate the
             creation, modification and deletion operations for an object.
             Options:
             1. createAndGo(4) -create a new instance of a conceptual row
             2. destroy(6)     -delete the instances associated with an existing conceptual row
            "
        ::= { hwGponOntPortVlanCfgEntry 6 }

    hwGponOntPortVlanCfgType  OBJECT-TYPE
        SYNTAX     INTEGER
            {
            translation(2),
            qinq(3)
            }
        MAX-ACCESS   read-write
        STATUS      current
        DESCRIPTION
            "The VLAN configuraton type of Eth port: 2-translation or 3-qinq.
             Options:
             1. translation(2) -The VLAN configuraton type of Eth port is translation
             2. qinq(3)        -The VLAN configuraton type of Eth port is qinq
            "
        ::= { hwGponOntPortVlanCfgEntry 7 }

    hwGponOntPortVlanCfgCPri  OBJECT-TYPE
       SYNTAX      Integer32
       MAX-ACCESS  not-accessible
       STATUS      current
       DESCRIPTION
           "The customer priority after the customer vlan translation or qinq.
            When the priority may not be specified, should input -1.
            Range: 0-7
           "
       ::= { hwGponOntPortVlanCfgEntry 8 }

    hwGponOntPortVlanCfgEtherType  OBJECT-TYPE
        SYNTAX      Integer32
        MAX-ACCESS   not-accessible
        STATUS      current
        DESCRIPTION
            "The customer service encapsulation type: IPv4-IPoE(1-default) or PPPoE(2) or IPv6-IPoE(4).
             Options:
             1. ipv4-ipoe(1)  -The customer service encapsulation type is ipv4 ipoe
             2. pppoe(2)      -The customer service encapsulation type is pppoe
             3. ipv6-ipoe(4)  -The customer service encapsulation type is ipv6 ipoe
             4. invalid(-1)   -Has not set the customer service encapsulation type
             5. 0x600-0xffff  -The customer service encapsulation type is user-defined
            "
        ::= { hwGponOntPortVlanCfgEntry 9 }

       hwGponOntPortVlanCfgSPriPolicy  OBJECT-TYPE
       SYNTAX      INTEGER
           {
           specify(1),
           userCos(2),
           dscpMapping(3),
           invalid (-1)
           }
       MAX-ACCESS  read-write
       STATUS      current
       DESCRIPTION
           "S-vlan priority policy.
            Options:
            1. specify(1)      - S-vlan priority policy is specify
            2. userCos(2)     - S-vlan priority policy is user-cos
            3. dscpMapping(3) - S-vlan priority policy is dscp-mapping
            4. invalid(-1)    - Indicates that the query fails or no information is detected
           "
       ::= { hwGponOntPortVlanCfgEntry 10 }

       hwGponOntPortVlanCfgDscpDefaultPriority  OBJECT-TYPE
       SYNTAX      Integer32
       MAX-ACCESS  read-write
       STATUS      current
       DESCRIPTION
           "The default priority for dscp-mapping policy."
       ::= { hwGponOntPortVlanCfgEntry 11 }

       hwGponOntPortVlanCfgTlsSwitch  OBJECT-TYPE
       SYNTAX      INTEGER
           {
           off(1),
           on(2),
           invalidValue(-1)
           }
       MAX-ACCESS  read-write
       STATUS      current
       DESCRIPTION
           "The switch used to config the attribute of vlan translation.
            Options:
            1. off(1)           - Disable the switch
            2. on(2)            - Enable the switch
            3. invalidValue(-1) - Invalid value
           "
       ::= { hwGponOntPortVlanCfgEntry 12 }

--  Table hwGponDeviceOpticsDdmAlarmProfileInfoTable
    hwGponDeviceOpticsDdmAlarmProfileInfoTable OBJECT-TYPE
        SYNTAX SEQUENCE OF HwGponDeviceOpticsDdmAlarmProfileInfoEntry
        MAX-ACCESS not-accessible
        STATUS current
        DESCRIPTION
            "This is the Gpon optical alarm profile infomation table.
             The index of this table is hwGponDeviceOpticsModuleAlarmProfileInfoNameIndex.
            "
        ::= { hwGponDeviceControlObjects 61 }

    hwGponDeviceOpticsDdmAlarmProfileInfoEntry OBJECT-TYPE
        SYNTAX HwGponDeviceOpticsDdmAlarmProfileInfoEntry
        MAX-ACCESS not-accessible
        STATUS current
        DESCRIPTION
            "This is the Gpon optical alarm profile infomation table.
             The index of this entry is hwGponDeviceOpticsModuleAlarmProfileInfoNameIndex.
            "
        INDEX { IMPLIED hwGponDeviceOpticsModuleAlarmProfileInfoNameIndex}
        ::= { hwGponDeviceOpticsDdmAlarmProfileInfoTable 1 }

    HwGponDeviceOpticsDdmAlarmProfileInfoEntry ::=
        SEQUENCE {
            hwGponDeviceOpticsModuleAlarmProfileInfoNameIndex
                OCTET STRING,
            hwGponDeviceOpticsDdmAlarmProfileBindNum
                Integer32,
            hwGponDeviceOpticsDdmAlarmProfileInfoRowStatus
                RowStatus,
            hwGponDeviceOpticsDdmAlarmProfileTxOpticAlarmUpper
                Integer32,
            hwGponDeviceOpticsDdmAlarmProfileTxOpticAlarmLower
                Integer32,
            hwGponDeviceOpticsDdmAlarmProfileTxOpticWarnUpper
                Integer32,
            hwGponDeviceOpticsDdmAlarmProfileTxOpticWarnLower
                Integer32,
            hwGponDeviceOpticsDdmAlarmProfileRxOpticAlarmUpper
                Integer32,
            hwGponDeviceOpticsDdmAlarmProfileRxOpticAlarmLower
                Integer32,
            hwGponDeviceOpticsDdmAlarmProfileRxOpticWarnUpper
                Integer32,
            hwGponDeviceOpticsDdmAlarmProfileRxOpticWarnLower
                Integer32,
            hwGponDeviceOpticsDdmAlarmProfileBiasCurrentAlarmUpper
                Integer32,
            hwGponDeviceOpticsDdmAlarmProfileBiasCurrentAlarmLower
                Integer32,
            hwGponDeviceOpticsDdmAlarmProfileBiasCurrentWarnUpper
                Integer32,
            hwGponDeviceOpticsDdmAlarmProfileBiasCurrentWarnLower
                Integer32,
            hwGponDeviceOpticsDdmAlarmProfileSupplyVoltageAlarmUpper
                Integer32,
            hwGponDeviceOpticsDdmAlarmProfileSupplyVoltageAlarmLower
                Integer32,
            hwGponDeviceOpticsDdmAlarmProfileSupplyVoltageWarnUpper
                Integer32,
            hwGponDeviceOpticsDdmAlarmProfileSupplyVoltageWarnLower
                Integer32,
            hwGponDeviceOpticsDdmAlarmProfileTemperatureAlarmUpper
                Integer32,
            hwGponDeviceOpticsDdmAlarmProfileTemperatureAlarmLower
                Integer32,
            hwGponDeviceOpticsDdmAlarmProfileTemperatureWarnUpper
                Integer32,
            hwGponDeviceOpticsDdmAlarmProfileTemperatureWarnLower
                Integer32,
            hwGponDeviceOpticsDdmAlarmProfileOntCatvRxOpticAlarmUpper
                Integer32,
            hwGponDeviceOpticsDdmAlarmProfileOntCatvRxOpticAlarmLower
                Integer32
        }

    hwGponDeviceOpticsModuleAlarmProfileInfoNameIndex OBJECT-TYPE
        SYNTAX OCTET STRING (SIZE(1..32))
        MAX-ACCESS not-accessible
        STATUS current
        DESCRIPTION
            "GPON optical alarm profile name index."
        ::= { hwGponDeviceOpticsDdmAlarmProfileInfoEntry 1 }

    hwGponDeviceOpticsDdmAlarmProfileBindNum OBJECT-TYPE
        SYNTAX Integer32
        MAX-ACCESS read-only
        STATUS current
        DESCRIPTION
            "GPON optical alarm profile binding times."
        ::= { hwGponDeviceOpticsDdmAlarmProfileInfoEntry 2 }

    hwGponDeviceOpticsDdmAlarmProfileInfoRowStatus OBJECT-TYPE
        SYNTAX RowStatus
        MAX-ACCESS read-create
        STATUS current
        DESCRIPTION
            "Row status. This object is used to differentiate the
             creation and deletion operations for an object.
             Options:
             1. createAndGo(4) -create a new instance of a conceptual row
             2. destroy(6)     -delete the instances associated with an existing conceptual row
            "
        ::= { hwGponDeviceOpticsDdmAlarmProfileInfoEntry 3 }


    hwGponDeviceOpticsDdmAlarmProfileTxOpticAlarmUpper OBJECT-TYPE
        SYNTAX Integer32
        MAX-ACCESS read-write
        STATUS current
        DESCRIPTION
            "Tx optical power alarm upper threshold."
        ::= { hwGponDeviceOpticsDdmAlarmProfileInfoEntry 4 }

    hwGponDeviceOpticsDdmAlarmProfileTxOpticAlarmLower OBJECT-TYPE
        SYNTAX Integer32
        MAX-ACCESS read-write
        STATUS current
        DESCRIPTION
            "Tx optical power alarm lower threshold."
        ::= { hwGponDeviceOpticsDdmAlarmProfileInfoEntry 5 }

    hwGponDeviceOpticsDdmAlarmProfileTxOpticWarnUpper OBJECT-TYPE
        SYNTAX Integer32
        MAX-ACCESS read-write
        STATUS current
        DESCRIPTION
            "Tx optical power warning upper threshold."
        ::= { hwGponDeviceOpticsDdmAlarmProfileInfoEntry 6 }

    hwGponDeviceOpticsDdmAlarmProfileTxOpticWarnLower OBJECT-TYPE
        SYNTAX Integer32
        MAX-ACCESS read-write
        STATUS current
        DESCRIPTION
            "Tx optical power warning lower threshold."
        ::= { hwGponDeviceOpticsDdmAlarmProfileInfoEntry 7 }

    hwGponDeviceOpticsDdmAlarmProfileRxOpticAlarmUpper OBJECT-TYPE
        SYNTAX Integer32
        MAX-ACCESS read-write
        STATUS current
        DESCRIPTION
            "Rx optical power alarm upper threshold."
        ::= { hwGponDeviceOpticsDdmAlarmProfileInfoEntry 8 }

    hwGponDeviceOpticsDdmAlarmProfileRxOpticAlarmLower OBJECT-TYPE
        SYNTAX Integer32
        MAX-ACCESS read-write
        STATUS current
        DESCRIPTION
            "Rx optical power alarm lower threshold."
        ::= { hwGponDeviceOpticsDdmAlarmProfileInfoEntry 9 }

    hwGponDeviceOpticsDdmAlarmProfileRxOpticWarnUpper OBJECT-TYPE
        SYNTAX Integer32
        MAX-ACCESS read-write
        STATUS current
        DESCRIPTION
            "Rx optical power warning upper threshold."
        ::= { hwGponDeviceOpticsDdmAlarmProfileInfoEntry 10 }

    hwGponDeviceOpticsDdmAlarmProfileRxOpticWarnLower OBJECT-TYPE
        SYNTAX Integer32
        MAX-ACCESS read-write
        STATUS current
        DESCRIPTION
            "Rx optical power warning lower threshold."
        ::= { hwGponDeviceOpticsDdmAlarmProfileInfoEntry 11 }

    hwGponDeviceOpticsDdmAlarmProfileBiasCurrentAlarmUpper OBJECT-TYPE
        SYNTAX Integer32
        MAX-ACCESS read-write
        STATUS current
        DESCRIPTION
            "Bias current alarm upper threshold."
        ::= { hwGponDeviceOpticsDdmAlarmProfileInfoEntry 12 }

    hwGponDeviceOpticsDdmAlarmProfileBiasCurrentAlarmLower OBJECT-TYPE
        SYNTAX Integer32
        MAX-ACCESS read-write
        STATUS current
        DESCRIPTION
            "Bias current alarm lower threshold."
        ::= { hwGponDeviceOpticsDdmAlarmProfileInfoEntry 13 }

    hwGponDeviceOpticsDdmAlarmProfileBiasCurrentWarnUpper OBJECT-TYPE
        SYNTAX Integer32
        MAX-ACCESS read-write
        STATUS current
        DESCRIPTION
            "Bias current warning upper threshold."
        ::= { hwGponDeviceOpticsDdmAlarmProfileInfoEntry 14 }

    hwGponDeviceOpticsDdmAlarmProfileBiasCurrentWarnLower OBJECT-TYPE
        SYNTAX Integer32
        MAX-ACCESS read-write
        STATUS current
        DESCRIPTION
            "Bias current warning lower threshold."
        ::= { hwGponDeviceOpticsDdmAlarmProfileInfoEntry 15 }

    hwGponDeviceOpticsDdmAlarmProfileSupplyVoltageAlarmUpper OBJECT-TYPE
        SYNTAX Integer32
        MAX-ACCESS read-write
        STATUS current
        DESCRIPTION
            "Supply Voltage power alarm upper threshold."
        ::= { hwGponDeviceOpticsDdmAlarmProfileInfoEntry 16 }

    hwGponDeviceOpticsDdmAlarmProfileSupplyVoltageAlarmLower OBJECT-TYPE
        SYNTAX Integer32
        MAX-ACCESS read-write
        STATUS current
        DESCRIPTION
            "Supply Voltage power alarm lower threshold."
        ::= { hwGponDeviceOpticsDdmAlarmProfileInfoEntry 17 }

    hwGponDeviceOpticsDdmAlarmProfileSupplyVoltageWarnUpper OBJECT-TYPE
        SYNTAX Integer32
        MAX-ACCESS read-write
        STATUS current
        DESCRIPTION
            "Supply Voltage power warning upper threshold."
        ::= { hwGponDeviceOpticsDdmAlarmProfileInfoEntry 18 }

    hwGponDeviceOpticsDdmAlarmProfileSupplyVoltageWarnLower OBJECT-TYPE
        SYNTAX Integer32
        MAX-ACCESS read-write
        STATUS current
        DESCRIPTION
            "Supply Voltage power warning lower threshold."
        ::= { hwGponDeviceOpticsDdmAlarmProfileInfoEntry 19 }

    hwGponDeviceOpticsDdmAlarmProfileTemperatureAlarmUpper OBJECT-TYPE
        SYNTAX Integer32
        MAX-ACCESS read-write
        STATUS current
        DESCRIPTION
            "Temperature alarm upper threshold."
        ::= { hwGponDeviceOpticsDdmAlarmProfileInfoEntry 20 }

    hwGponDeviceOpticsDdmAlarmProfileTemperatureAlarmLower OBJECT-TYPE
        SYNTAX Integer32
        MAX-ACCESS read-write
        STATUS current
        DESCRIPTION
            "Temperature alarm lower threshold."
        ::= { hwGponDeviceOpticsDdmAlarmProfileInfoEntry 21 }

    hwGponDeviceOpticsDdmAlarmProfileTemperatureWarnUpper OBJECT-TYPE
        SYNTAX Integer32
        MAX-ACCESS read-write
        STATUS current
        DESCRIPTION
            "Temperature warning upper threshold."
        ::= { hwGponDeviceOpticsDdmAlarmProfileInfoEntry 22 }

    hwGponDeviceOpticsDdmAlarmProfileTemperatureWarnLower OBJECT-TYPE
        SYNTAX Integer32
        MAX-ACCESS read-write
        STATUS current
        DESCRIPTION
            "Temperature warning lower threshold."
        ::= { hwGponDeviceOpticsDdmAlarmProfileInfoEntry 23 }

    hwGponDeviceOpticsDdmAlarmProfileOntCatvRxOpticAlarmUpper OBJECT-TYPE
        SYNTAX Integer32
        MAX-ACCESS read-write
        STATUS current
        DESCRIPTION
            "ONT CATV rx optical power alarm upper threshold."
        ::= { hwGponDeviceOpticsDdmAlarmProfileInfoEntry 24 }

    hwGponDeviceOpticsDdmAlarmProfileOntCatvRxOpticAlarmLower OBJECT-TYPE
        SYNTAX Integer32
        MAX-ACCESS read-write
        STATUS current
        DESCRIPTION
            "ONT CATV rx optical power alarm lower threshold."
        ::= { hwGponDeviceOpticsDdmAlarmProfileInfoEntry 25 }


--  hwGponDeviceEthPortBundleCfgTable
    hwGponDeviceEthPortBundleCfgTable OBJECT-TYPE
        SYNTAX     SEQUENCE OF HwGponDeviceEthPortBundleCfgEntry
        MAX-ACCESS not-accessible
        STATUS     current
        DESCRIPTION
            "This is the ONT port-bundle configuration table.
             The indexes of this table are ifIndex,
             hwGponDeviceEthPortBundleOntObjectIndex, and
             hwGponDeviceEthPortBundleCfgIndex.
            "
        ::= { hwGponDeviceControlObjects 62 }

    hwGponDeviceEthPortBundleCfgEntry OBJECT-TYPE
        SYNTAX     HwGponDeviceEthPortBundleCfgEntry
        MAX-ACCESS not-accessible
        STATUS     current
        DESCRIPTION
            "This is the ONT port-bundle configuration table.
             The indexes of this entry are ifIndex,
             hwGponDeviceEthPortBundleOntObjectIndex, and
             hwGponDeviceEthPortBundleCfgIndex.
            "
        INDEX       { ifIndex, hwGponDeviceEthPortBundleOntObjectIndex, hwGponDeviceEthPortBundleCfgIndex }
        ::= { hwGponDeviceEthPortBundleCfgTable 1 }

    HwGponDeviceEthPortBundleCfgEntry ::=
        SEQUENCE {
                  hwGponDeviceEthPortBundleOntObjectIndex       Integer32,
                  hwGponDeviceEthPortBundleCfgIndex             Integer32,
                  hwGponDeviceEthPortBundleCfgPortBitMap        Integer32,
                  hwGponDeviceEthPortBundleCfgRowStatus         RowStatus
                 }

    hwGponDeviceEthPortBundleOntObjectIndex OBJECT-TYPE
         SYNTAX   Integer32
         MAX-ACCESS  not-accessible
         STATUS      current
         DESCRIPTION
             "ONT ID."
         ::= { hwGponDeviceEthPortBundleCfgEntry 1 }

    hwGponDeviceEthPortBundleCfgIndex OBJECT-TYPE
         SYNTAX   Integer32 (1..8)
         MAX-ACCESS  not-accessible
         STATUS      current
         DESCRIPTION
             "Bundle group index."
         ::= { hwGponDeviceEthPortBundleCfgEntry 2 }

    hwGponDeviceEthPortBundleCfgPortBitMap OBJECT-TYPE
        SYNTAX   Integer32
        MAX-ACCESS  read-write
        STATUS      current
        DESCRIPTION
            "The bundle port bitmap."
        ::= { hwGponDeviceEthPortBundleCfgEntry 3 }

    hwGponDeviceEthPortBundleCfgRowStatus OBJECT-TYPE
       SYNTAX   RowStatus
       MAX-ACCESS  read-create
       STATUS      current
       DESCRIPTION
           "Row status. This object is used to differentiate the creation, modification and deletion operations for an object.
            Options:
            1. createAndGo(4) -create a new instance of a conceptual row
            2. destroy(6)     -delete the instances associated with an existing conceptual row
           "
       ::= { hwGponDeviceEthPortBundleCfgEntry 4 }

--end add by h00114109

--Table hwGponDynamicMacQueryTable
    HwGponDynamicMacQueryPara ::= TEXTUAL-CONVENTION
        STATUS       current
        DESCRIPTION
            "Reserved parameter."
        SYNTAX       Integer32

    HwGponDynamicMacQueryType ::= TEXTUAL-CONVENTION
        STATUS       current
        DESCRIPTION  "Query type."
            --"the value is quering index; if no index, th value is -1."
            -- for example, if the value is gponOntPortInSpecVlan(1), the value of ifIndex, hwGponDynamicMacVlanId, hwGponDynamicMacIndex,
            -- hwGponDynamicMacQueryPara0, hwGponDynamicMacQueryPara1, hwGponDynamicMacQueryPara2 is valid,
            -- and the value of hwGponDynamicMacQueryPara3 is invalid, -1"
        SYNTAX       INTEGER {
                           -- learnt mac(s) of XPON ONT port in the specified vlan;
                           -- hwGponDynamicMacQueryPara0 : ONT ID
                           -- hwGponDynamicMacQueryPara1 : ONT Port type
                           -- hwGponDynamicMacQueryPara2 : ONT Port ID
                           -- hwGponDynamicMacVlanId: The VLAN ID
                              gponOntPortInSpecVlan(1),

                           -- learnt mac(s) of XPON ONT int the specified port;
                           -- hwGponDynamicMacQueryPara0 : ONT ID
                           -- hwGponDynamicMacQueryPara1 : ONT Port type
                           -- hwGponDynamicMacQueryPara2 : ONT Port ID
                           -- hwGponDynamicMacVlanId: The value is -1
                              gponOntInSpecPort(2),

                           -- learnt mac(s) of the specified XPON ONT;
                           -- hwGponDynamicMacQueryPara0 : ONT ID
                           -- hwGponDynamicMacQueryPara1 : The value is -1
                           -- hwGponDynamicMacQueryPara2 : The value is -1
                           -- hwGponDynamicMacVlanId: The value is -1
                              gponOntInSpecOnt(3),

                           -- learnt mac(s) of the WLAN of specified ONT;
                           -- hwGponDynamicMacQueryPara0 : ONT ID
                           -- hwGponDynamicMacQueryPara1 : The value is -1
                           -- hwGponDynamicMacQueryPara2 : The value is -1
                           -- hwGponDynamicMacVlanId: The value is -1
                              gponOntInSpecWlan(4)
                             }

    hwGponDynamicMacQueryTable OBJECT-TYPE
        SYNTAX SEQUENCE OF HwGponDynamicMacQueryEntry
        MAX-ACCESS not-accessible
        STATUS current
        DESCRIPTION
            "Query Dynamic MAC address table.
             The indexes of this table are ifIndex, hwGponDynamicMacVlanId,
             hwGponDynamicMacIndex, hwGponDynamicMacQueryType, hwGponDynamicMacQueryPara0,
             hwGponDynamicMacQueryPara1, hwGponDynamicMacQueryPara2, and hwGponDynamicMacQueryPara3.
            "
        ::= { hwGponDeviceControlObjects 63 }

    hwGponDynamicMacQueryEntry OBJECT-TYPE
        SYNTAX HwGponDynamicMacQueryEntry
        MAX-ACCESS not-accessible
        STATUS current
        DESCRIPTION
            "Query Dynamic MAC address table.
             The indexes of this entry are ifIndex, hwGponDynamicMacVlanId,
             hwGponDynamicMacIndex, hwGponDynamicMacQueryType, hwGponDynamicMacQueryPara0,
             hwGponDynamicMacQueryPara1, hwGponDynamicMacQueryPara2, and hwGponDynamicMacQueryPara3.
            "
        INDEX { ifIndex,
                hwGponDynamicMacVlanId,
                hwGponDynamicMacIndex,
                hwGponDynamicMacQueryType,
                hwGponDynamicMacQueryPara0,
                hwGponDynamicMacQueryPara1,
                hwGponDynamicMacQueryPara2,
                hwGponDynamicMacQueryPara3
              }
        ::= { hwGponDynamicMacQueryTable 1 }

    HwGponDynamicMacQueryEntry ::=
        SEQUENCE {
                  hwGponDynamicMacVlanId      Integer32,
                  hwGponDynamicMacIndex       Integer32,
                  hwGponDynamicMacQueryType   HwGponDynamicMacQueryType,
                  hwGponDynamicMacQueryPara0  HwGponDynamicMacQueryPara,
                  hwGponDynamicMacQueryPara1  HwGponDynamicMacQueryPara,
                  hwGponDynamicMacQueryPara2  HwGponDynamicMacQueryPara,
                  hwGponDynamicMacQueryPara3  HwGponDynamicMacQueryPara,
                  hwGponDynamicMacAddr        OCTET STRING
                 }

    hwGponDynamicMacVlanId   OBJECT-TYPE
        SYNTAX Integer32(1..4094)
        MAX-ACCESS not-accessible
        STATUS current
        DESCRIPTION
            "The VLAN ID."
        ::= { hwGponDynamicMacQueryEntry 1 }

    hwGponDynamicMacIndex   OBJECT-TYPE
        SYNTAX Integer32
        MAX-ACCESS not-accessible
        STATUS current
        DESCRIPTION
            "The dynamic MAC address index."
        ::= { hwGponDynamicMacQueryEntry 2 }

    hwGponDynamicMacQueryType   OBJECT-TYPE
        SYNTAX HwGponDynamicMacQueryType
        MAX-ACCESS not-accessible
        STATUS current
        DESCRIPTION
            "This object indicates the query type.
             Options:
             1. gponOntPortInSpecVlan(1)  - The ONT port is in the specified vlan
             2. gponOntInSpecPort(2)      - The specified ONT port
             3. gponOntInSpecOnt(3)       - The specified ONT
             4. gponOntInSpecWlan(4)      - The WLAN of specified ONT
            "
        ::= { hwGponDynamicMacQueryEntry 3 }

    hwGponDynamicMacQueryPara0   OBJECT-TYPE
        SYNTAX HwGponDynamicMacQueryPara
        MAX-ACCESS not-accessible
        STATUS current
        DESCRIPTION
            "The First reserved Parameter of HwGponDynamicMacQueryEntry."
        ::= { hwGponDynamicMacQueryEntry 4 }

    hwGponDynamicMacQueryPara1   OBJECT-TYPE
        SYNTAX HwGponDynamicMacQueryPara
        MAX-ACCESS not-accessible
        STATUS current
        DESCRIPTION
            "The Second reserved Parameter of HwGponDynamicMacQueryEntry."
        ::= { hwGponDynamicMacQueryEntry 5 }

    hwGponDynamicMacQueryPara2   OBJECT-TYPE
        SYNTAX HwGponDynamicMacQueryPara
        MAX-ACCESS not-accessible
        STATUS current
        DESCRIPTION
            "The Third reserved Parameter of HwGponDynamicMacQueryEntry. Range: 1~8."
        ::= { hwGponDynamicMacQueryEntry 6 }

    hwGponDynamicMacQueryPara3   OBJECT-TYPE
        SYNTAX HwGponDynamicMacQueryPara
        MAX-ACCESS not-accessible
        STATUS current
        DESCRIPTION
            "The Fourth reserved Parameter of HwGponDynamicMacQueryEntry."
        ::= { hwGponDynamicMacQueryEntry 7 }

    hwGponDynamicMacAddr   OBJECT-TYPE
        SYNTAX OCTET STRING (SIZE (0..1280))
        MAX-ACCESS read-only
        STATUS current
        DESCRIPTION
           "MAC address.
            When hwGponDynamicMacQueryType is 1 ,the MAC addresses which can include 5 MAC addresses at most, and its format is (XX.XX.XX.XX.XX.XX).
            When hwGponDynamicMacQueryType is 2 or 3 or 4, the query result contains MAC address entries with a length of 0-1280 bytes.
            A maximum of 128 MAC addresses can be queried, each entry containing 10 bytes.
            The queried entry is in a format of port type (1 byte)+port ID (1 byte)+VLAN ID (2 bytes)+MAC address (6 bytes),
            where the blank field can be represented by 0, for example, 3401400000E0FC000001.
            Range: 0-1280.
           "
        ::= { hwGponDynamicMacQueryEntry 8 }

--  Table hwGponOltDualparentTable
    hwGponOltDualparentTable OBJECT-TYPE
        SYNTAX     SEQUENCE OF HwGponOltDualparentEntry
        MAX-ACCESS not-accessible
        STATUS     current
        DESCRIPTION
            "Type-B dual parent protect group config table.
             The index of this table is ifIndex.
            "
        ::= { hwGponDeviceControlObjects 64 }

    hwGponOltDualparentEntry OBJECT-TYPE
        SYNTAX     HwGponOltDualparentEntry
        MAX-ACCESS not-accessible
        STATUS     current
        DESCRIPTION
            "Type-B dual parent protect group config table.
             The index of this entry is ifIndex.
            "
        INDEX       { ifIndex }
        ::= { hwGponOltDualparentTable 1 }

    HwGponOltDualparentEntry ::=
        SEQUENCE {
                  hwGponOltDualparentJoin          INTEGER,
                  hwGponOltDualparentFreeze        INTEGER,
                  hwGponOltDualparentForceSwitch   INTEGER,
                  hwGponOltDualparentWorkState     INTEGER,
                  hwGponOltDualparentDetectDuration Integer32,
                  hwGponOltDualparentDesc          OCTET STRING
                 }

    hwGponOltDualparentJoin     OBJECT-TYPE
        SYNTAX    INTEGER
            {
            joinwork(1),
            joinprotect(2),
            undojoin(3)
            }
        MAX-ACCESS  read-write
        STATUS      current
        DESCRIPTION
            "Indicating the port whether or not join in the TYPE-B dual parent protect group.
             Options:
             1. joinwork(1)    - The port join in the TYPE-B dual parent protect group as a work member
             2. joinprotect(2) - The port join in the TYPE-B dual parent protect group as a protect member
             3. undojoin(3)    - the port doesn't join in the TYPE-B dual parent protect group
            "
        ::= { hwGponOltDualparentEntry 1 }

    hwGponOltDualparentFreeze     OBJECT-TYPE
        SYNTAX      INTEGER
            {
            freeze(1),
            undofreeze(2)
            }
        MAX-ACCESS  read-write
        STATUS      current
        DESCRIPTION
            "Indicating the protect status of the port whether or not be frozen.
             Options:
             1. freeze(1)     - Indicate the protect status of the port is frozen
             2. undofreeze(2) - Indicate the protect status of the port isn't frozen
            "
        ::= { hwGponOltDualparentEntry 2 }

    hwGponOltDualparentForceSwitch  OBJECT-TYPE
        SYNTAX      INTEGER
            {
            force(1),
            autoDetect(2)
            }
        MAX-ACCESS  read-write
        STATUS      current
        DESCRIPTION
            "Indicating the work mode of the port : force or auto-detect.
             Options:
             1. force(1)       - Indicate the work mode of the port is force
             2. autoDetect(2) - Indicate the work mode of the port is auto-detect
            "
        ::= { hwGponOltDualparentEntry 3 }

    hwGponOltDualparentWorkState     OBJECT-TYPE
        SYNTAX      INTEGER
            {
            active(1),
            standby(2),
            fault(3),
            detect(4)
            }
        MAX-ACCESS  read-write
        STATUS      current
        DESCRIPTION
            "Set or show the port protect status.
             Options:
             1. active(1)  - The port protect status is active
             2. standby(2) - The port protect status is standby
             3. fault(3)   - The port protect status is fault
             4. detect(4)  - The port protect status is detect
            "
        ::= { hwGponOltDualparentEntry 4 }

    hwGponOltDualparentDetectDuration      OBJECT-TYPE
        SYNTAX      Integer32
        UNITS       "seconds"
        MAX-ACCESS  read-only
        STATUS      current
        DESCRIPTION
            "The duration of the port in detecting status.
             Unit: seconds"
        ::= { hwGponOltDualparentEntry 5 }


    hwGponOltDualparentDesc OBJECT-TYPE
        SYNTAX OCTET STRING (SIZE(1..32))
        MAX-ACCESS read-write
        STATUS current
        DESCRIPTION
            "The description of TYPE-B dual parent member port."
        ::= { hwGponOltDualparentEntry 6 }

-- Table hwGponOntRegisterExInfoTable
    hwGponOntRegisterExInfoTable OBJECT-TYPE
        SYNTAX     SEQUENCE OF HwGponOntRegisterExInfoEntry
        MAX-ACCESS not-accessible
        STATUS     current
        DESCRIPTION
            "This table is used to save the ont's register info,less than 10 times.
             The indexes of this table are ifIndex, hwGponDeviceOntObjectIndex,
             and hwGponOntRegisterInfoIndex.
            "
        ::= { hwGponDeviceControlObjects 65 }

    hwGponOntRegisterExInfoEntry OBJECT-TYPE
        SYNTAX     HwGponOntRegisterExInfoEntry
        MAX-ACCESS not-accessible
        STATUS     current
        DESCRIPTION
            "This table is used to save the ont's register info,less than 10 times.
             The indexes of this entry are ifIndex, hwGponDeviceOntObjectIndex,
             and hwGponOntRegisterInfoIndex.
            "
        INDEX       { ifIndex, hwGponDeviceOntObjectIndex, hwGponOntRegisterInfoIndex }
        ::= { hwGponOntRegisterExInfoTable 1 }

    HwGponOntRegisterExInfoEntry ::=
        SEQUENCE {
                 hwGponOntRegisterInfoIndex                     Integer32,
                 hwGponOntRegisterInfoAuthMethod                INTEGER,
                 hwGponOntRegisterInfoSN                        OCTET STRING,
                 hwGponOntRegisterInfoPassword                  OCTET STRING,
                 hwGponOntRegisterInfoType                      OCTET STRING,
                 hwGponOntRegisterInfoUpTime                    OCTET STRING,
                 hwGponOntRegisterInfoDownTime                  OCTET STRING,
                 hwGponOntRegisterInfoDownCause                 INTEGER,
                 hwGponOntRegisterInfoLoid                      OCTET STRING,
                 hwGponOntRegisterInfoCheckcode                 OCTET STRING
                 }

    hwGponOntRegisterInfoIndex  OBJECT-TYPE
        SYNTAX      Integer32(0..9)
        MAX-ACCESS  not-accessible
        STATUS      current
        DESCRIPTION
            "The ONT register information index."
        ::= { hwGponOntRegisterExInfoEntry 1 }

    hwGponOntRegisterInfoAuthMethod  OBJECT-TYPE
        SYNTAX      INTEGER
        {
            sn(1),
            snandpassword(2),
            alwayson(3),
            onceon(4),
            loidalwayson (5),
            loidonceon (6),
            loidcheckcodealwayson (7),
            loidcheckcodeonceon (8),
            invalidValue(-1)
        }
        MAX-ACCESS  read-only
        STATUS      current
        DESCRIPTION
            "The authentication mode for the ONT.
             Options:
             1. sn(1)            - The authentication mode for the ONT is sn
             2. snandpassword(2) - The authentication mode for the ONT is sn and password
             3. alwayson(3)      - The authentication mode for the ONT is always on
             4. onceon(4)        - The authentication mode for the ONT is once on
             5. loidalwayson (5)             - The authentication mode for the ONT is loid + always-on
             6. loidonceon (6)               - The authentication mode for the ONT is loid + once-on
             7. loidcheckcodealwayson (7)    - The authentication mode for the ONT is loid + checkcode + always-on
             8. loidcheckcodeonceon (8)      - The authentication mode for the ONT is loid + checkcode + once-on
             9. invalidValue(-1)             - The authentication mode for the ONT is invalid
             "
        ::= { hwGponOntRegisterExInfoEntry 2 }

    hwGponOntRegisterInfoSN  OBJECT-TYPE
        SYNTAX      OCTET STRING (SIZE (16))
        MAX-ACCESS  read-only
        STATUS      current
        DESCRIPTION
            "The ONT serial number."
        ::= { hwGponOntRegisterExInfoEntry 3 }

    hwGponOntRegisterInfoPassword  OBJECT-TYPE
        SYNTAX      OCTET STRING
        MAX-ACCESS  read-only
        STATUS      current
        DESCRIPTION
            "The ONT password.
             GPON password size (0..10)
             XG-PON password size (0..36)
            "
        ::= { hwGponOntRegisterExInfoEntry 4 }

    hwGponOntRegisterInfoType OBJECT-TYPE
        SYNTAX       OCTET STRING (SIZE (0..20))
        MAX-ACCESS   read-only
        STATUS       current
        DESCRIPTION
            "The ONT type."
        ::= { hwGponOntRegisterExInfoEntry 5 }

    hwGponOntRegisterInfoUpTime  OBJECT-TYPE
        SYNTAX      OCTET STRING (SIZE (0..30))
        MAX-ACCESS  read-only
        STATUS      current
        DESCRIPTION
            "The time for ONT's up."
        ::= { hwGponOntRegisterExInfoEntry 6 }

    hwGponOntRegisterInfoDownTime  OBJECT-TYPE
        SYNTAX      OCTET STRING (SIZE (0..30))
        MAX-ACCESS  read-only
        STATUS      current
        DESCRIPTION
            "The time for ONT's down."
        ::= { hwGponOntRegisterExInfoEntry 7 }

    hwGponOntRegisterInfoDownCause  OBJECT-TYPE
        SYNTAX      INTEGER
            {
            ontdeleted(0),
            linkeddown(1),
            losi(2),
            lofi(3),
            sfi(4),
            loai(5),
            loami(6),
            disablefail(7),
            deactived(8),
            reset(9),
            reRegister(10),
            popupfail(11),
            authfail(12),
            dyinggasp(13),
            reserved(14),
            loki(15),
            ringDeactivated(18),
	    turnOffOptic(30),
            cmdReboot(31),
            ontResetkeyReboot(32),
            ontSoftwareReset(33),
            broadcastAttackDeactivated(34),
            operatorCheckFail(35),
            ontOltIncompatible(36),
            rogueOntselfDetected(37),
            autoIsolateReset(38),
            autoIsolateDeact(39),
            ontNotInWhiteList(40),
            noerror(255),
            invalid(-1)
            }
        MAX-ACCESS  read-only
        STATUS      current
        DESCRIPTION
            "The cause of ONT's down.
             Options:
             1. ontdeleted(0)                     - The cause of ONT's down is that the ont is deleted
             2. linkeddown(1)                     - The cause of ONT's down is that the ont is link down
             3. losi(2)                           - The cause of ONT's down is LOSi(Loss of signal for ONUi) or LOBi (Loss of burst for ONUi)
             4. lofi(3)                           - The cause of ONT's down is that the ont is lofi
             5. sfi(4)                            - The cause of ONT's down is that the ont is sfi
             6. loai(5)                           - The cause of ONT's down is that the ont is loai
             7. loami(6)                          - The cause of ONT's down is that the ont is loami
             8. disablefail(7)                    - The cause of ONT's down is that the ont is disablefail
             9. deactived(8)                      - The cause of ONT's down is that the ont is deactived
             10. reset(9)                         - The cause of ONT's down is that the ont is reseted
             11. reRegister(10)                   - The cause of ONT's down is that the ont is re-register
             12. popupfail(11)                    - The cause of ONT's down is that the ont popup test fails
             13. authfail(12)                     - The cause of ONT's down is that the ont is authfail
             14. dyinggasp(13)                    - The cause of ONT's down is that the ont is dyinggasp
             15. reserved(14)                     - Reserved
             16. loki(15)                         - The cause of ONT's down is that the ont is loki
             17. ringDeactivated(18)              - The cause of ONT's down is that the ont is deactivated due to the ring
             18. turnOffOptic(30)                 - The cause of ONT's down is that the ont optical module is shut down
             19. cmdReboot(31)                    - The cause of ONT's down is that the ont is reset by ont command
             20. ontResetkeyReboot(32)            - The cause of ONT's down is that the ont is reset by ont reset button
             21. ontSoftwareReset(33)             - The cause of ONT's down is that the ont is reset by ont software
             22. broadcastAttackDeactivated(34)   - The cause of ONT's down is that the ont is deactivated due to broadcast attack
             23. operatorCheckFail(35)            - The cause of ONT's down is that operator check fail
             24. ontOltIncompatible(36)           - The cause of ONT's down is that the ont is incompatible with the OLT
             25. rogueOntselfDetected(37)         - The cause of ONT's down is that the rogue ont detected by itself
             26. autoIsolateReset(38)             - The cause of ONT's down is that the ont resets to prevent rogue ont attacks
             27. autoIsolateDeact(39)             - The cause of ONT's down is that the ont is deactivated to prevent rogue ont attacks
             28. ontNotInWhiteList(40)            - The cause of ONT's down is that the ont is not in the white list
             29. noerror(255)                     - The cause of ONT's down is that the ont is noerror
             30. invalid(-1)                      - Indicates that the query fails or no information is detected
            "
        ::= { hwGponOntRegisterExInfoEntry 8 }

        hwGponOntRegisterInfoLoid  OBJECT-TYPE
            SYNTAX   OCTET STRING (SIZE (0..24))
            MAX-ACCESS  read-only
            STATUS   current
            DESCRIPTION
                "This object indicates the ONT LOID."
            ::= { hwGponOntRegisterExInfoEntry 9 }

        hwGponOntRegisterInfoCheckcode  OBJECT-TYPE
            SYNTAX   OCTET STRING (SIZE (0..12))
            MAX-ACCESS  read-only
            STATUS   current
            DESCRIPTION
                "This object indicates the ONT checkcode."
            ::= { hwGponOntRegisterExInfoEntry 10 }

-- Table hwGponDeviceRogueOntTable
    hwGponDeviceRogueOntTable OBJECT-TYPE
        SYNTAX     SEQUENCE OF HwGponDeviceRogueOntEntry
        MAX-ACCESS not-accessible
        STATUS     current
        DESCRIPTION
            "This is the rogue ONT list table.
             The index of this table is ifIndex.
            "
        ::= { hwGponDeviceControlObjects 66 }

    hwGponDeviceRogueOntEntry OBJECT-TYPE
        SYNTAX     HwGponDeviceRogueOntEntry
        MAX-ACCESS not-accessible
        STATUS     current
        DESCRIPTION
            "This is the rogue ONT list table.
             The index of this entry is ifIndex.
            "
        INDEX       { ifIndex }
        ::= { hwGponDeviceRogueOntTable 1 }

    HwGponDeviceRogueOntEntry ::=
        SEQUENCE {
            hwGponDeviceRogueOnt        OntList
        }

    hwGponDeviceRogueOnt  OBJECT-TYPE
        SYNTAX     OntList
        MAX-ACCESS   read-only
        STATUS      current
        DESCRIPTION
           "Rogue ont list."
        ::= { hwGponDeviceRogueOntEntry 1 }

-- Table hwGponDeviceOntMulticastPortIdControlTable
    hwGponDeviceOntMulticastPortIdControlTable OBJECT-TYPE
        SYNTAX     SEQUENCE OF HwGponDeviceOntMulticastPortIdControlEntry
        MAX-ACCESS not-accessible
        STATUS     current
        DESCRIPTION
            "This is the ONT multicast gemport configuration table.
             The indexes of this table are ifIndex, hwGponDeviceOntObjectIndex.
            "
        ::= { hwGponDeviceControlObjects 67 }

    hwGponDeviceOntMulticastPortIdControlEntry OBJECT-TYPE
        SYNTAX     HwGponDeviceOntMulticastPortIdControlEntry
        MAX-ACCESS not-accessible
        STATUS     current
        DESCRIPTION
            "This is the ONT multicast gemport configuration table.
             The indexes of this entry are ifIndex, hwGponDeviceOntObjectIndex.
            "
        INDEX       { ifIndex, hwGponDeviceOntObjectIndex }
        ::= { hwGponDeviceOntMulticastPortIdControlTable 1 }

    HwGponDeviceOntMulticastPortIdControlEntry ::=
        SEQUENCE {
                 hwGponDeviceMulticastPortIdObjectTcontId       Integer32,
                 hwGponDeviceMulticastPortidObjectPortType      INTEGER,
                 hwGponDeviceMulticastPortidObjectPortID        Integer32
                 }

    hwGponDeviceMulticastPortIdObjectTcontId  OBJECT-TYPE
        SYNTAX      Integer32
        MAX-ACCESS  read-write
        STATUS      current
        DESCRIPTION
            "T-CONT ID. The issued value (-1) of T-CONT ID indicates that the multicast gemport is not specified to any T-CONT."
        ::= { hwGponDeviceOntMulticastPortIdControlEntry 1 }

    hwGponDeviceMulticastPortidObjectPortType  OBJECT-TYPE
        SYNTAX  INTEGER{
             eth(47),
             ethBundle(254),
             invalid(-1)
            }
        MAX-ACCESS  read-write
        STATUS      current
        DESCRIPTION
            "This object indicates the port type of the ONT.
             Options:
                 1. eth(47)            - ETH
                 2. ethBundle(254)     - EthBundle
                 3. invalid(-1)        - Indicates that the query fails or no information is detected
            "
        ::= { hwGponDeviceOntMulticastPortIdControlEntry 2 }

    hwGponDeviceMulticastPortidObjectPortID  OBJECT-TYPE
        SYNTAX      Integer32
        MAX-ACCESS  read-write
        STATUS      current
        DESCRIPTION
            "This object indicates the port index of the ONT,
             or the bundle-groupid when it is the eth-bundle port type.
             "
        ::= { hwGponDeviceOntMulticastPortIdControlEntry 3 }

-- hwGponDeviceOntUpIgmpMsgConfigTable
   hwGponDeviceOntUpIgmpMsgConfigTable OBJECT-TYPE
       SYNTAX     SEQUENCE OF HwGponDeviceOntUpIgmpMsgConfigEntry
       MAX-ACCESS not-accessible
       STATUS     current
       DESCRIPTION
           "This table is used to set and query the user-VLAN-based IGMP packet forwarding mode of ONT.
            The indexes of this table are ifIndex, hwGponDeviceOntObjectIndex and hwGponDeviceOntUpIgmpMsgForwardUserVlan.
           "
       ::= { hwGponDeviceControlObjects 68 }

   hwGponDeviceOntUpIgmpMsgConfigEntry OBJECT-TYPE
       SYNTAX     HwGponDeviceOntUpIgmpMsgConfigEntry
       MAX-ACCESS not-accessible
       STATUS     current
       DESCRIPTION
           "This table is used to set and query the user-VLAN-based IGMP packet forwarding mode of ONT.
            The indexes of this entry are ifIndex, hwGponDeviceOntObjectIndex and hwGponDeviceOntUpIgmpMsgForwardUserVlan.
           "
       INDEX       { ifIndex, hwGponDeviceOntObjectIndex, hwGponDeviceOntUpIgmpMsgForwardUserVlan}
       ::= { hwGponDeviceOntUpIgmpMsgConfigTable 1 }

   HwGponDeviceOntUpIgmpMsgConfigEntry ::=
       SEQUENCE {
               hwGponDeviceOntUpIgmpMsgForwardUserVlan        Integer32,
               hwGponDeviceOntUpIgmpMsgForwardMode            INTEGER,
               hwGponDeviceOntUpIgmpMsgForwardTranslationVlan Integer32,
               hwGponDeviceOntUpIgmpMsgForwardPriority        Integer32,
               hwGponDeviceOntUpIgmpMsgForwardRowStatus       RowStatus
               }

   hwGponDeviceOntUpIgmpMsgForwardUserVlan OBJECT-TYPE
            SYNTAX Integer32
            MAX-ACCESS not-accessible
            STATUS current
            DESCRIPTION
                "This object indicates the user VLAN of upstream IGMP packets.
                 0..4095 indicates the user VLAN."
            ::= { hwGponDeviceOntUpIgmpMsgConfigEntry 1 }

   hwGponDeviceOntUpIgmpMsgForwardMode OBJECT-TYPE
            SYNTAX INTEGER {
                transparent(1),
                translation(2),
                default(3),
                invalid(-1)
            }
            MAX-ACCESS read-write
            STATUS current
            DESCRIPTION
                "This object indicates the IGMP packet forwarding mode.
                 Only the value transparent(1) is supported currently.
                 Options:
                 1. transparent(1) - Indicates that the IGMP upstream packets forward mode is transparent
                 2. translation(2) - Indicates that the IGMP upstream packets forward mode is translation
                 3. default(3)     - Indicates that the IGMP upstream packets forward mode is add VLAN tag
                 4. invalid(-1)    - Indicates that the query fails or no information is detected.
                "
            ::= { hwGponDeviceOntUpIgmpMsgConfigEntry 2 }

        hwGponDeviceOntUpIgmpMsgForwardTranslationVlan OBJECT-TYPE
            SYNTAX Integer32 (-1|0..4095)
            MAX-ACCESS read-write
            STATUS current
            DESCRIPTION
                "This object indicates the ont upstream IGMP packets will be translate to the translation vlan.
                "
            ::= { hwGponDeviceOntUpIgmpMsgConfigEntry 3 }

        hwGponDeviceOntUpIgmpMsgForwardPriority OBJECT-TYPE
            SYNTAX Integer32 (-1|0..7)
            MAX-ACCESS read-write
            STATUS current
            DESCRIPTION
                "When upstream IGMP packets were added a vlan or translated to the translation vlan, priority was set.
                "
            ::= { hwGponDeviceOntUpIgmpMsgConfigEntry 4 }

        hwGponDeviceOntUpIgmpMsgForwardRowStatus OBJECT-TYPE
            SYNTAX     RowStatus
            MAX-ACCESS    read-create
            STATUS      current
            DESCRIPTION
                "Row status. This object is used to differentiate the
                 creation, modification and deletion operations for an object.
                 Options:
                 1. createAndGo(4) -create a new instance of a conceptual row
                 2. destroy(6)     -delete the instances associated with an existing conceptual row
                "
            ::= { hwGponDeviceOntUpIgmpMsgConfigEntry 5 }

-- hwGponDeviceOntPortClassInfoTable
   hwGponDeviceOntPortClassInfoTable OBJECT-TYPE
       SYNTAX     SEQUENCE OF HwGponDeviceOntPortClassInfoEntry
       MAX-ACCESS not-accessible
       STATUS     current
       DESCRIPTION
           "This table is used to set and query the GPON classification.
            The indexes of this table are hwGponDeviceOntPortClassInfoProfileIdIndex, hwGponDeviceOntPortClassInfoPrecedenceIndex and hwGponDeviceOntPortClassInfoConditionIndex.
           "
       ::= { hwGponDeviceControlObjects 69 }

   hwGponDeviceOntPortClassInfoEntry OBJECT-TYPE
       SYNTAX     HwGponDeviceOntPortClassInfoEntry
       MAX-ACCESS not-accessible
       STATUS     current
       DESCRIPTION
           "This table is used to set and query the GPON classification.
            The indexes of this entry are hwGponDeviceOntPortClassInfoProfileIdIndex, hwGponDeviceOntPortClassInfoPrecedenceIndex and hwGponDeviceOntPortClassInfoConditionIndex.
           "
       INDEX       { hwGponDeviceOntPortClassInfoProfileIdIndex, hwGponDeviceOntPortClassInfoPrecedenceIndex, hwGponDeviceOntPortClassInfoConditionIndex}
       ::= { hwGponDeviceOntPortClassInfoTable 1 }

   HwGponDeviceOntPortClassInfoEntry ::=
       SEQUENCE {
               hwGponDeviceOntPortClassInfoProfileIdIndex        Integer32,
               hwGponDeviceOntPortClassInfoPrecedenceIndex       Integer32,
               hwGponDeviceOntPortClassInfoConditionIndex        Integer32,
               hwGponDeviceOntPortClassInfoProfileRefNum         Integer32,
               hwGponDeviceOntPortClassInfoProfileName           OCTET STRING,
               hwGponDeviceOntPortClassInfoProfileQueuemapped    Integer32,
               hwGponDeviceOntPortClassInfoProfilePriMark        Integer32,
               hwGponDeviceOntPortClassInfoProfileFieldselect    Integer32,
               hwGponDeviceOntPortClassInfoProfileOperator       Integer32,
               hwGponDeviceOntPortClassInfoProfileMatchValue     OCTET STRING,
               hwGponDeviceOntPortClassInfoProfileRowStatus      RowStatus
               }

    hwGponDeviceOntPortClassInfoProfileIdIndex OBJECT-TYPE
        SYNTAX Integer32
        MAX-ACCESS  not-accessible
        STATUS  current
        DESCRIPTION
           "This object indicates the profile index."
        ::= { hwGponDeviceOntPortClassInfoEntry 1 }

    hwGponDeviceOntPortClassInfoPrecedenceIndex OBJECT-TYPE
        SYNTAX Integer32
        MAX-ACCESS  not-accessible
        STATUS  current
        DESCRIPTION
           "This object indicates the precedence-rule."
        ::= { hwGponDeviceOntPortClassInfoEntry 2 }

    hwGponDeviceOntPortClassInfoConditionIndex OBJECT-TYPE
        SYNTAX Integer32
        MAX-ACCESS  not-accessible
        STATUS  current
        DESCRIPTION
           "This object indicates the conditionindex-condition."
        ::= { hwGponDeviceOntPortClassInfoEntry 3 }

     hwGponDeviceOntPortClassInfoProfileRefNum OBJECT-TYPE
         SYNTAX Integer32
         MAX-ACCESS read-only
         STATUS current
         DESCRIPTION
            " This object indicates the profile binding times."
         ::= { hwGponDeviceOntPortClassInfoEntry 4 }

     hwGponDeviceOntPortClassInfoProfileName OBJECT-TYPE
         SYNTAX   OCTET STRING (SIZE (1..32))
         MAX-ACCESS read-write
         STATUS      current
         DESCRIPTION
            "This object indicates the profile name."
         ::= { hwGponDeviceOntPortClassInfoEntry 5}

     hwGponDeviceOntPortClassInfoProfileQueuemapped OBJECT-TYPE
         SYNTAX   Integer32
         MAX-ACCESS read-write
         STATUS      current
         DESCRIPTION
            "This object indicates the mapping queue.
             The valid value range is 0~255.
	     The value (-1) indicates that the query fails or no information is detected.
	     "
         ::= { hwGponDeviceOntPortClassInfoEntry 6}

     hwGponDeviceOntPortClassInfoProfilePriMark OBJECT-TYPE
          SYNTAX   Integer32
          MAX-ACCESS read-write
          STATUS      current
          DESCRIPTION
             "This object indicates the priority mark.
              The valid value range is 0~7,255.
	      The value (-1) indicates that the query fails or no information is detected.
	      "
         ::= { hwGponDeviceOntPortClassInfoEntry 7}

     hwGponDeviceOntPortClassInfoProfileFieldselect OBJECT-TYPE
           SYNTAX  Integer32
           MAX-ACCESS read-write
           STATUS current
           DESCRIPTION
                "This object indicates the field selected corresponding the condition.
                 The value (0) indicates that the field is classified by destination MAC.
                 The value (1) indicates that the field is classified by source MAC.
                 The value (2) indicates that the field is classified by ethernet user priority.
                 The value (3) indicates that the field is classified by VLAN ID.
                 The value (4) indicates that the field is classified by ETH type.
                 The value (5) indicates that the field is classified by destination IPv4 address.
                 The value (6) indicates that the field is classified by source IPv4 address.
                 The value (7) indicates that the field is classified by IP protocol type.
                 The value (8) indicates that the field is classified by IPv4 DSCP.
                 The value (9) indicates that the field is classified by IPv6 DSCP.
                 The value (10) indicates that the field is classified by source port of layer 4 protocol.
                 The value (11) indicates that the field is classified by destination port of layer 4 protocol.
                 The value (12) indicates that the field is classified by IP version.
                 The value (13) indicates that the field is classified by IPv6 flow label.
                 The value (14) indicates that the field is classified by destination IPv6 address.
                 The value (15) indicates that the field is classified by source IPv6 address.
                 The value (16) indicates that the field is classified by prefix of destination IPv6 address.
                 The value (17) indicates that the field is classified by prefix of source IPv6 address.
                 The value (18) indicates that the field is classified by IPv6 next header.
		 The value (-1) indicates that the query fails or no information is detected.
                "
         ::= { hwGponDeviceOntPortClassInfoEntry 8}

      hwGponDeviceOntPortClassInfoProfileOperator OBJECT-TYPE
            SYNTAX  Integer32
            MAX-ACCESS  read-write
            STATUS  current
            DESCRIPTION
                "This object indicates the operator flag.
             	 The value (0) indicates that the operator flag is never match.
	 	 The value (1) indicates that the operator flag is equal.
		 The value (2) indicates that the operator flag is not equal.
		 The value (3) indicates that the operator flag is less than or equal.
		 The value (4) indicates that the operator flag is greater or equal.
		 The value (5) indicates that the operator flag is true if field exists.
	 	 The value (6) indicates that the operator flag is true if field not exist.
		 The value (7) indicates that the operator flag is always match.
		 The value (-1) indicates that the query fails or no information is detected
                "
         ::= { hwGponDeviceOntPortClassInfoEntry 9}

     hwGponDeviceOntPortClassInfoProfileMatchValue OBJECT-TYPE
          SYNTAX    OCTET STRING (SIZE (1..64))
          MAX-ACCESS read-write
          STATUS      current
          DESCRIPTION
             "This object indicates the match values."
         ::= { hwGponDeviceOntPortClassInfoEntry 10}

     hwGponDeviceOntPortClassInfoProfileRowStatus OBJECT-TYPE
         SYNTAX     RowStatus
         MAX-ACCESS    read-create
         STATUS      current
         DESCRIPTION
             "The hwGponDeviceOntPortClassProfileRowStatus is used to create a new row
	      or to modify or delete an existing row in this table.
		Options:
                1. createAndGo(4) -create a new instance of a conceptual row.
                2. destroy(6)     -delete the instances associated with an existing conceptual row.
             "
         ::= { hwGponDeviceOntPortClassInfoEntry 11 }

-- hwGponDeviceGemBundleTable
    hwGponDeviceGemBundleTable OBJECT-TYPE
        SYNTAX     SEQUENCE OF HwGponDeviceGemBundleEntry
        MAX-ACCESS not-accessible
        STATUS     current
        DESCRIPTION
            "This table is used to configure the GPON GEM port bundle.
             The indexes of this table are ifIndex and hwGponDevicePortidObjectIndex
             which is the master GEM port of bundle.
           "
        ::= { hwGponDeviceControlObjects 70 }

    hwGponDeviceGemBundleEntry OBJECT-TYPE
        SYNTAX      HwGponDeviceGemBundleEntry
        MAX-ACCESS  not-accessible
        STATUS      current
        DESCRIPTION
            "This table is used to configure the GPON GEM port bundle.
             The indexes of this entry are ifIndex and hwGponDevicePortidObjectIndex
             which is the Master GEM port of bundle.
            "
        INDEX    { ifIndex, hwGponDevicePortidObjectIndex }
        ::= { hwGponDeviceGemBundleTable 1 }

    HwGponDeviceGemBundleEntry ::=
        SEQUENCE {
            hwGponDeviceGemBundleSlaveList OCTET STRING
        }

    hwGponDeviceGemBundleSlaveList OBJECT-TYPE
        SYNTAX      OCTET STRING (SIZE (0..255))
        MAX-ACCESS  read-write
        STATUS      current
        DESCRIPTION
            "Indicates the slave GEM ports of bundle.
             The value of slave GEM ports of bundle:
             number(1byte)             :Indicates the number of slave GEM ports. The maximum number is 7.
             gemportid(2byte * number) :Indicates a slave GEM port ID.
            "
        ::= { hwGponDeviceGemBundleEntry 1 }
END
