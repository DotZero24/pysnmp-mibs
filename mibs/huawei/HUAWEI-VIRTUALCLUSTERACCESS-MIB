-- ===================================================================
-- Copyright (C) 2014 by HUAWEI TECHNOLOGIES. All rights reserved.
-- Description: This MIB contains private managed object and notification
--              trap definitions for virtual cluster access.
-- Reference:
-- Version: V1.00
-- ===================================================================


    HUAWEI-VIRTUALCLUSTERACCESS-MIB DEFINITIONS ::= BEGIN

        IMPORTS
            hwDatacomm
                FROM HUAWEI-MIB
            ifIndex, ifName, InterfaceIndex
                FROM IF-MIB
            SnmpAdminString
                FROM SNMP-FRAMEWORK-MIB
            MODULE-COMPLIANCE, OBJECT-GROUP, NOTIFICATION-GROUP
                FROM SNMPv2-CONF
            Integer32, Unsigned32, Counter32, IpAddress, BITS, OBJECT-TYPE,
            MODULE-IDENTITY, NOTIFICATION-TYPE
                FROM SNMPv2-SMI
            InetAddressType, InetAddress
                FROM INET-ADDRESS-MIB;


        hwVirtualClusterAccessMib MODULE-IDENTITY
            LAST-UPDATED "201403031311Z"
            ORGANIZATION
                "Huawei Technologies Co.,Ltd."
            CONTACT-INFO
                "Huawei Industrial Base
                 Bantian, Longgang
                 Shenzhen 518129
                 People's Republic of China
                 Website: http://www.huawei.com
                 Email: support@huawei.com"
            DESCRIPTION
        "This MIB contains private managed object and notification trap definitions for virtual cluster access."
--
-- Revision history
--
        REVISION    "201403031311Z"
        DESCRIPTION "V1.00, initial version."

            ::= { hwDatacomm 318 }

--
-- Node definitions
--

        hwVirtualClusterAccessInfo OBJECT IDENTIFIER ::= { hwVirtualClusterAccessMib 1 }

        hwVirtualClusterAccessGlobalInfo OBJECT IDENTIFIER ::= { hwVirtualClusterAccessInfo 1 }

        hwVirtualClusterAccessWorkMode OBJECT-TYPE
            SYNTAX INTEGER
                {
                master(1),
                slave(2)
                }
            MAX-ACCESS read-only
            STATUS current
            DESCRIPTION
                "The work mode of virtual cluster access system.
                Options:
                1. master(1)       -indicates work mode of Master.
                2. slave(2)        -indicates work mode of Slave."
            ::= { hwVirtualClusterAccessGlobalInfo 1 }

        hwVirtualClusterAccessAdminIP OBJECT-TYPE
            SYNTAX  InetAddress
            MAX-ACCESS read-only
            STATUS current
            DESCRIPTION
                "The value of this object identifies the administrative IP address of master/slave."
            ::= { hwVirtualClusterAccessGlobalInfo 2 }

        hwVirtualClusterAccessVPNInstanceName OBJECT-TYPE
            SYNTAX OCTET STRING
            MAX-ACCESS read-only
            STATUS current
            DESCRIPTION
                "The VPN instance name of virtual cluster access system."
            ::= { hwVirtualClusterAccessGlobalInfo 3 }

        hwVirtualClusterAccessAdminIPDiscoveryMode OBJECT-TYPE
            SYNTAX INTEGER
                {
                config(1),
                auto(2)
                }
            MAX-ACCESS read-only
            STATUS current
            DESCRIPTION
                "In slave work mode, the mode of discovery administrative IP address.
                Options:
                1. config(1)      -configuration in virtual cluster access system.
                2. auto(2)        -auto discovery by virtual cluster access system."
            ::= { hwVirtualClusterAccessGlobalInfo 4 }

        hwVirtualClusterAccessMasterDiscoveryMode OBJECT-TYPE
            SYNTAX INTEGER
                {
                config(1),
                auto(2)
                }
            MAX-ACCESS read-only
            STATUS current
            DESCRIPTION
                "In slave work mode, the mode of discovery master infomation.
                Options:
                1. config(1)      -configuration in virtual cluster access system.
                2. auto(2)        -auto discovery by virtual cluster access system."
            ::= { hwVirtualClusterAccessGlobalInfo 5 }

        hwVirtualClusterAccessPathComputeMasterId OBJECT-TYPE
            SYNTAX  InetAddress
            MAX-ACCESS read-only
            STATUS current
            DESCRIPTION
                "The ID of path compute master"
            ::= { hwVirtualClusterAccessGlobalInfo 6 }

        hwVirtualClusterAccessTableInfo OBJECT IDENTIFIER ::= { hwVirtualClusterAccessInfo 2 }

        hwVirtualClusterAccessVpTable OBJECT-TYPE
            SYNTAX SEQUENCE OF HwVirtualClusterAccessVpEntry
            MAX-ACCESS not-accessible
            STATUS current
            DESCRIPTION
                "Basic information about virtual cluster access VP.
                 The index of this table is hwVirtualClusterAccessVpSourceNodeId, hwVirtualClusterAccessVpDestNodeId, hwVirtualClusterAccessVpGroupIdentity, hwVirtualClusterAccessVpType.
                "
            ::= { hwVirtualClusterAccessTableInfo 1 }

        hwVirtualClusterAccessVpEntry OBJECT-TYPE
            SYNTAX HwVirtualClusterAccessVpEntry
            MAX-ACCESS not-accessible
            STATUS current
            DESCRIPTION
                "Basic information about virtual cluster access VP.
                 The index of this entry is hwVirtualClusterAccessVpSourceNodeId, hwVirtualClusterAccessVpDestNodeId, hwVirtualClusterAccessVpGroupIdentity, hwVirtualClusterAccessVpType.
                "
            INDEX { hwVirtualClusterAccessVpSourceNodeId, hwVirtualClusterAccessVpDestNodeId, hwVirtualClusterAccessVpGroupIdentity, hwVirtualClusterAccessVpType }
            ::= { hwVirtualClusterAccessVpTable 1 }

        HwVirtualClusterAccessVpEntry ::=
            SEQUENCE {
                hwVirtualClusterAccessVpSourceNodeId
                    IpAddress,
                hwVirtualClusterAccessVpDestNodeId
                    IpAddress,
                hwVirtualClusterAccessVpGroupIdentity
                    Integer32,
                hwVirtualClusterAccessVpType
                    INTEGER,
                hwVirtualClusterAccessVpApId
                    IpAddress,
                hwVirtualClusterAccessVpIfIndex
                    InterfaceIndex,
                hwVirtualClusterAccessVpIfName
                    SnmpAdminString,
                hwVirtualClusterAccessVpOperState
                    INTEGER,
                hwVirtualClusterAccessVpReason
                    Integer32,
                hwVirtualClusterAccessVpId
                    Integer32
             }

        hwVirtualClusterAccessVpSourceNodeId  OBJECT-TYPE
            SYNTAX IpAddress
            MAX-ACCESS not-accessible
            STATUS current
            DESCRIPTION
                "Indicates the administrative IP address of source node."
            ::= { hwVirtualClusterAccessVpEntry 1 }

        hwVirtualClusterAccessVpDestNodeId  OBJECT-TYPE
            SYNTAX IpAddress
            MAX-ACCESS not-accessible
            STATUS current
            DESCRIPTION
                "Indicates the administrative IP address of destination node."
            ::= { hwVirtualClusterAccessVpEntry 2 }

        hwVirtualClusterAccessVpGroupIdentity OBJECT-TYPE
            SYNTAX Integer32(1..65535)
            MAX-ACCESS not-accessible
            STATUS current
            DESCRIPTION
                "Indicates the VP group ID."
            ::= { hwVirtualClusterAccessVpEntry 3 }

        hwVirtualClusterAccessVpType OBJECT-TYPE
			      SYNTAX INTEGER
            {
                primary(1),
                hotstandby(2)
            }
            MAX-ACCESS not-accessible
            STATUS current
            DESCRIPTION
                "Indicates type of VP.
                Options:
                1. primary(1)          -indicates VP type is primary.
                2. hotstandby(2)       -indicates VP type is hotstandby."
            ::= { hwVirtualClusterAccessVpEntry 4 }

        hwVirtualClusterAccessVpApId OBJECT-TYPE
            SYNTAX IpAddress
            MAX-ACCESS read-only
            STATUS current
            DESCRIPTION
                "Indicates the AP ID of failure AP."
            ::= { hwVirtualClusterAccessVpEntry 5 }

        hwVirtualClusterAccessVpIfIndex OBJECT-TYPE
            SYNTAX InterfaceIndex
            MAX-ACCESS read-only
            STATUS current
            DESCRIPTION
                "Indicates the index of failure AP interface."
            ::= { hwVirtualClusterAccessVpEntry 6 }

        hwVirtualClusterAccessVpIfName OBJECT-TYPE
            SYNTAX SnmpAdminString
            MAX-ACCESS read-only
            STATUS current
            DESCRIPTION
                "Indicates the name of failure AP interface."
            ::= { hwVirtualClusterAccessVpEntry 7 }

        hwVirtualClusterAccessVpOperState OBJECT-TYPE
            SYNTAX INTEGER
            {
                up(1),
                down(2)
            }
            MAX-ACCESS read-only
            STATUS current
            DESCRIPTION
                "Indicates VP operate state.
                Options:
                1. up(1)          -indicates VP operate state is up.
                2. down(2)        -indicates VP operate state is down."
            ::= { hwVirtualClusterAccessVpEntry 8 }

        hwVirtualClusterAccessVpReason OBJECT-TYPE
            SYNTAX Integer32
            MAX-ACCESS read-only
            STATUS current
            DESCRIPTION
                "This object indicates the cause that the VP becomes down.
                 Options:
                 1. VpUp(1)            --indicates VP was up.
                 2. VpDelete(2)        --indicates VP was deleted.
                 3. BfdDown(3)         --indicates BFD was down.
                 4. ApDown(4)          --indicates AP down.
                 5. ApInterfaceDown(5) --indicates AP interface was down.
                 6. other(6)           --indicates other reason.
				 "
            ::= { hwVirtualClusterAccessVpEntry 9 }

        hwVirtualClusterAccessVpId OBJECT-TYPE
            SYNTAX Integer32(1..65535)
            MAX-ACCESS read-only
            STATUS current
            DESCRIPTION
                "Indicates the VP ID."
            ::= { hwVirtualClusterAccessVpEntry 10 }

        hwVirtualClusterAccessVpGroupTable OBJECT-TYPE
            SYNTAX SEQUENCE OF HwVirtualClusterAccessVpGroupEntry
            MAX-ACCESS not-accessible
            STATUS current
            DESCRIPTION
                "Basic information about virtual cluster access VP group.
                 The index of this table is hwVirtualClusterAccessVpGroupSourceNodeId, hwVirtualClusterAccessVpGroupDestNodeId, hwVirtualClusterAccessVpGroupId.
                "
            ::= { hwVirtualClusterAccessTableInfo 2 }

        hwVirtualClusterAccessVpGroupEntry OBJECT-TYPE
            SYNTAX HwVirtualClusterAccessVpGroupEntry
            MAX-ACCESS not-accessible
            STATUS current
            DESCRIPTION
                "Basic information about virtual cluster access VP group.
                 The index of this entry is hwVirtualClusterAccessVpGroupSourceNodeId, hwVirtualClusterAccessVpGroupDestNodeId, hwVirtualClusterAccessVpGroupId.
                "
            INDEX { hwVirtualClusterAccessVpGroupSourceNodeId, hwVirtualClusterAccessVpGroupDestNodeId, hwVirtualClusterAccessVpGroupId }
            ::= { hwVirtualClusterAccessVpGroupTable 1 }

        HwVirtualClusterAccessVpGroupEntry ::=
            SEQUENCE {
                hwVirtualClusterAccessVpGroupSourceNodeId
                    IpAddress,
                hwVirtualClusterAccessVpGroupDestNodeId
                    IpAddress,
                hwVirtualClusterAccessVpGroupId
                    Integer32,
                hwVirtualClusterAccessVpGroupVpId
                    Integer32,
                hwVirtualClusterAccessVpGroupOperState
                    INTEGER,
                hwVirtualClusterAccessVpGroupReason
                    Integer32,
                hwVirtualClusterAccessVpGroupPrimaryVpId
                    Integer32,
                hwVirtualClusterAccessVpGroupStandbyVpId
                    Integer32,
                hwVirtualClusterAccessVpGroupSwitchDirection
                    INTEGER
             }

        hwVirtualClusterAccessVpGroupSourceNodeId  OBJECT-TYPE
            SYNTAX IpAddress
            MAX-ACCESS not-accessible
            STATUS current
            DESCRIPTION
                "Indicates the source node administrative IP address of VP group."
            ::= { hwVirtualClusterAccessVpGroupEntry 1 }

        hwVirtualClusterAccessVpGroupDestNodeId  OBJECT-TYPE
            SYNTAX IpAddress
            MAX-ACCESS not-accessible
            STATUS current
            DESCRIPTION
                "Indicates the destination node administrative IP address of VP group."
            ::= { hwVirtualClusterAccessVpGroupEntry 2 }

        hwVirtualClusterAccessVpGroupId OBJECT-TYPE
            SYNTAX Integer32(1..65535)
            MAX-ACCESS not-accessible
            STATUS current
            DESCRIPTION
                "Indicates the group ID of VP group."
            ::= { hwVirtualClusterAccessVpGroupEntry 3 }

        hwVirtualClusterAccessVpGroupVpId OBJECT-TYPE
            SYNTAX Integer32
            MAX-ACCESS read-only
            STATUS current
            DESCRIPTION
                "Indicates  the last down VP ID for hwVpGroupDown, or the frist up VP ID for hwVpGroupDownClear."
            ::= { hwVirtualClusterAccessVpGroupEntry 4 }


        hwVirtualClusterAccessVpGroupOperState OBJECT-TYPE
            SYNTAX INTEGER
            {
                up(1),
                down(2)
            }
            MAX-ACCESS read-only
            STATUS current
            DESCRIPTION
                "Indicates VP group operate state.
                Options:
                1. up(1)          -indicates VP group operate state is up.
                2. down(2)        -indicates VP group operate state is down."
            ::= { hwVirtualClusterAccessVpGroupEntry 5 }

	    hwVirtualClusterAccessVpGroupReason OBJECT-TYPE
            SYNTAX Integer32
            MAX-ACCESS read-only
            STATUS current
            DESCRIPTION
                 "This object indicates the cause that the VP group becomes down.
                 Options:
                 1. VpGroupUp(1)            --indicates VP Group was up.
                 2. VpGroupDelete(2)        --indicates VP Group was deleted.
                 3. BfdDown(3)         --indicates BFD was down.
                 4. ApDown(4)          --indicates AP down.
                 5. ApInterfaceDown(5) --indicates AP interface was down.
                 6. other(6)           --indicates other reason.
				 "
            ::= { hwVirtualClusterAccessVpGroupEntry 6 }

            hwVirtualClusterAccessVpGroupPrimaryVpId OBJECT-TYPE
            SYNTAX Integer32
            MAX-ACCESS read-only
            STATUS current
            DESCRIPTION
                "Indicates the primary VP ID of VP group."
            ::= { hwVirtualClusterAccessVpGroupEntry 7 }

            hwVirtualClusterAccessVpGroupStandbyVpId OBJECT-TYPE
            SYNTAX Integer32
            MAX-ACCESS read-only
            STATUS current
            DESCRIPTION
                "Indicates the standby VP ID of VP group."
            ::= { hwVirtualClusterAccessVpGroupEntry 8 }

            hwVirtualClusterAccessVpGroupSwitchDirection OBJECT-TYPE
            SYNTAX INTEGER
            {
                primarytohotstandby (1),
                hotstandbytoprimary(2)
            }
            MAX-ACCESS read-only
            STATUS current
            DESCRIPTION
                "Indicates the switch direction of VP group.
                Options:
                1. primarytohotstandby(1)          -indicates switch direction is  primary to hotstandby.
                2. hotstandbytoprimary(2)        -indicates switch direction is hotstandby to primary."
            ::= { hwVirtualClusterAccessVpGroupEntry 9 }

        hwVirtualClusterAccessVcTable OBJECT-TYPE
            SYNTAX SEQUENCE OF HwVirtualClusterAccessVcEntry
            MAX-ACCESS not-accessible
            STATUS current
            DESCRIPTION
                "Basic information about virtual cluster access VC.
                 The index of this table is hwVirtualClusterAccessVcMasterId, hwVirtualClusterAccessVcApId, hwVirtualClusterAccessVcIfIndex, hwVirtualClusterAccessVcAcIfIndex.
                "
            ::= { hwVirtualClusterAccessTableInfo 3 }

        hwVirtualClusterAccessVcEntry OBJECT-TYPE
            SYNTAX HwVirtualClusterAccessVcEntry
            MAX-ACCESS not-accessible
            STATUS current
            DESCRIPTION
                "Basic information about virtual cluster access VC.
                 The index of this entry is hwVirtualClusterAccessVcMasterId, hwVirtualClusterAccessVcApId, hwVirtualClusterAccessVcIfIndex, hwVirtualClusterAccessVcAcIfIndex.
                "
            INDEX { hwVirtualClusterAccessVcMasterId, hwVirtualClusterAccessVcApId, hwVirtualClusterAccessVcIfIndex, hwVirtualClusterAccessVcAcIfIndex }
            ::= { hwVirtualClusterAccessVcTable 1 }

        HwVirtualClusterAccessVcEntry ::=
            SEQUENCE {
                hwVirtualClusterAccessVcMasterId
                    IpAddress,
                hwVirtualClusterAccessVcApId
                    IpAddress,
                hwVirtualClusterAccessVcIfIndex
                    InterfaceIndex,
                hwVirtualClusterAccessVcAcIfIndex
                   InterfaceIndex,
                hwVirtualClusterAccessVcRemoteApIfName
                    SnmpAdminString,
                hwVirtualClusterAccessVcAcIfName
                    SnmpAdminString,
                hwVirtualClusterAccessVcVpSourceNodeId
                    IpAddress,
                hwVirtualClusterAccessVcVpDestNodeId
                    IpAddress,
                hwVirtualClusterAccessVcVpGroupId
                    Integer32,
                hwVirtualClusterAccessVcId
                    Integer32,
                hwVirtualClusterAccessVcType
                    Integer32,
                hwVirtualClusterAccessVcPeerIpAddr
                    IpAddress,
                hwVirtualClusterAccessVcOperState
                    INTEGER,
                hwVirtualClusterAccessVcReason
                    Integer32
             }

        hwVirtualClusterAccessVcMasterId OBJECT-TYPE
            SYNTAX IpAddress
            MAX-ACCESS not-accessible
            STATUS current
            DESCRIPTION
                "Indicates the master ID of VC."
            ::= { hwVirtualClusterAccessVcEntry 1 }

        hwVirtualClusterAccessVcApId OBJECT-TYPE
            SYNTAX IpAddress
            MAX-ACCESS not-accessible
            STATUS current
            DESCRIPTION
                "Indicates the AP ID of VC."
            ::= { hwVirtualClusterAccessVcEntry 2 }

        hwVirtualClusterAccessVcIfIndex OBJECT-TYPE
            SYNTAX InterfaceIndex
            MAX-ACCESS not-accessible
            STATUS current
            DESCRIPTION
                "Indicates the remote interface index of VC."
            ::= { hwVirtualClusterAccessVcEntry 3 }

	    hwVirtualClusterAccessVcAcIfIndex OBJECT-TYPE
            SYNTAX InterfaceIndex
            MAX-ACCESS not-accessible
            STATUS current
            DESCRIPTION
                "Indicates the AP interface index of VC."
            ::= { hwVirtualClusterAccessVcEntry 4 }

        hwVirtualClusterAccessVcRemoteApIfName OBJECT-TYPE
            SYNTAX SnmpAdminString
            MAX-ACCESS read-only
            STATUS current
            DESCRIPTION
                "Indicates the remote AP interface name of VC."
            ::= { hwVirtualClusterAccessVcEntry 5 }

         hwVirtualClusterAccessVcAcIfName OBJECT-TYPE
            SYNTAX SnmpAdminString
            MAX-ACCESS read-only
            STATUS current
            DESCRIPTION
                "Indicates the AP interface name of VC."
            ::= { hwVirtualClusterAccessVcEntry 6 }

        hwVirtualClusterAccessVcVpSourceNodeId  OBJECT-TYPE
            SYNTAX IpAddress
            MAX-ACCESS read-only
            STATUS current
            DESCRIPTION
                "Indicates the source node administrative IP address of failure VP group."
            ::= { hwVirtualClusterAccessVcEntry 7 }

        hwVirtualClusterAccessVcVpDestNodeId  OBJECT-TYPE
            SYNTAX IpAddress
            MAX-ACCESS read-only
            STATUS current
            DESCRIPTION
                "Indicates the destination node administrative IP address of failure VP group."
            ::= { hwVirtualClusterAccessVcEntry 8 }

        hwVirtualClusterAccessVcVpGroupId OBJECT-TYPE
            SYNTAX Integer32
            MAX-ACCESS read-only
            STATUS current
            DESCRIPTION
                "Indicates the group ID of failure VP group."
            ::= { hwVirtualClusterAccessVcEntry 9 }

          hwVirtualClusterAccessVcId OBJECT-TYPE
            SYNTAX Integer32
            MAX-ACCESS read-only
            STATUS current
            DESCRIPTION
                "Indicates the ID of failure VC."
            ::= { hwVirtualClusterAccessVcEntry 10 }

          hwVirtualClusterAccessVcType OBJECT-TYPE
            SYNTAX Integer32
            MAX-ACCESS read-only
            STATUS current
            DESCRIPTION
                "Indicates the type of failure VC."
            ::= { hwVirtualClusterAccessVcEntry 11 }

           hwVirtualClusterAccessVcPeerIpAddr OBJECT-TYPE
            SYNTAX IpAddress
            MAX-ACCESS read-only
            STATUS current
            DESCRIPTION
                "Indicates the peer ip of failure VC."
            ::= { hwVirtualClusterAccessVcEntry 12 }

         hwVirtualClusterAccessVcOperState OBJECT-TYPE
            SYNTAX INTEGER
            {
                up(1),
                down(2)
            }
            MAX-ACCESS read-only
            STATUS current
            DESCRIPTION
                "Indicates VC operate state.
                Options:
                1. up(1)          -indicates VC operate state is up.
                2. down(2)        -indicates VC operate state is down."
            ::= { hwVirtualClusterAccessVcEntry 13 }

        hwVirtualClusterAccessVcReason OBJECT-TYPE
            SYNTAX Integer32
            MAX-ACCESS read-only
            STATUS current
            DESCRIPTION
                 "This object indicates the cause that the VC becomes down.
                 Options:
                 1. BfdDown(1)            --indicates BFD was down.
                 2. physicDown(2)        --indicates physic was down.
                 3. ApDownOrApOffLine(3)    --indicates AP was down or off line.
                 4. outPwDown(4)          --indicates out PW was down.
                 5. VpGroupDown(5) --indicates VP group was down.
                 6. other(6)           --indicates other reason.
                 7. VcDelete   -- indicates VC was deleted.
                 8. VcUp       -- indicates VC was up.
                  "
            ::= { hwVirtualClusterAccessVcEntry 14 }

        hwVirtualClusterAccessRemoteApIfTable OBJECT-TYPE
            SYNTAX SEQUENCE OF HwVirtualClusterAccessRemoteApIfEntry
            MAX-ACCESS not-accessible
            STATUS current
            DESCRIPTION
                "Basic information about virtual cluster access remote AP interface.
                 The index of this table is hwVirtualClusterAccessRemoteApIfMasterId, hwVirtualClusterAccessRemoteApIfIndex.
                "
            ::= { hwVirtualClusterAccessTableInfo 4 }

        hwVirtualClusterAccessRemoteApIfEntry OBJECT-TYPE
            SYNTAX HwVirtualClusterAccessRemoteApIfEntry
            MAX-ACCESS not-accessible
            STATUS current
            DESCRIPTION
                "Basic information about virtual cluster access remote AP interface.
                 The index of this entry is hwVirtualClusterAccessRemoteApIfMasterId, hwVirtualClusterAccessRemoteApIfIndex.
                "
            INDEX { hwVirtualClusterAccessRemoteApIfMasterId, hwVirtualClusterAccessRemoteApIfIndex }
            ::= { hwVirtualClusterAccessRemoteApIfTable 1 }

        HwVirtualClusterAccessRemoteApIfEntry ::=
            SEQUENCE {
                hwVirtualClusterAccessRemoteApIfMasterId
                    IpAddress,
                hwVirtualClusterAccessRemoteApIfIndex
                    InterfaceIndex,
                hwVirtualClusterAccessRemoteApIfName
                    SnmpAdminString,
                hwVirtualClusterAccessRemoteApIfOperState
                    INTEGER,
                hwVirtualClusterAccessRemoteApIfReason
                    Integer32
             }

        hwVirtualClusterAccessRemoteApIfMasterId OBJECT-TYPE
            SYNTAX IpAddress
            MAX-ACCESS not-accessible
            STATUS current
            DESCRIPTION
                "Indicates the master ID of remote AP interface."
            ::= { hwVirtualClusterAccessRemoteApIfEntry 1 }

        hwVirtualClusterAccessRemoteApIfIndex OBJECT-TYPE
            SYNTAX InterfaceIndex
            MAX-ACCESS not-accessible
            STATUS current
            DESCRIPTION
                "Indicates the index of remote AP interface."
            ::= { hwVirtualClusterAccessRemoteApIfEntry 2 }

        hwVirtualClusterAccessRemoteApIfName OBJECT-TYPE
            SYNTAX SnmpAdminString
            MAX-ACCESS read-only
            STATUS current
            DESCRIPTION
                "Indicates the name of remote AP interface."
            ::= { hwVirtualClusterAccessRemoteApIfEntry 3 }

        hwVirtualClusterAccessRemoteApIfOperState OBJECT-TYPE
            SYNTAX INTEGER
            {
                up(1),
                down(2)
            }
            MAX-ACCESS read-only
            STATUS current
            DESCRIPTION
                "Indicates the interface operate state.
                Options:
                1. up(1)          -indicates interface operate state is up.
                2. down(2)        -indicates interface operate state is down."
            ::= { hwVirtualClusterAccessRemoteApIfEntry 4 }

        hwVirtualClusterAccessRemoteApIfReason OBJECT-TYPE
            SYNTAX Integer32
            MAX-ACCESS read-only
            STATUS current
            DESCRIPTION
                 "This object indicates the cause that the remote AP interface becomes down.
                 Options:
                 1. ConfigError(1)            --indicates configuration was error.
                 2. VcDown(2)        --indicates VC was down.
                 3. ApDownOrApOutline(3)    --indicates AP was down or outline.
                 4. other(4)          --indicates other reason.
                 5. remoteApDelete(5) --indicates remote AP was deleted.
				 "
            ::= { hwVirtualClusterAccessRemoteApIfEntry 5 }

        hwVirtualClusterAccessApTable OBJECT-TYPE
            SYNTAX SEQUENCE OF HwVirtualClusterAccessApEntry
            MAX-ACCESS not-accessible
            STATUS current
            DESCRIPTION
                "Basic information about virtual cluster access AP.
                 The index of this table is hwVirtualClusterAccessApId, hwVirtualClusterAccessApMasterId.
                "
            ::= { hwVirtualClusterAccessTableInfo 5 }

        hwVirtualClusterAccessApEntry OBJECT-TYPE
            SYNTAX HwVirtualClusterAccessApEntry
            MAX-ACCESS not-accessible
            STATUS current
            DESCRIPTION
                "Basic information about virtual cluster access AP.
                 The index of this entry is hwVirtualClusterAccessApId, hwVirtualClusterAccessApMasterId.
                "
            INDEX { hwVirtualClusterAccessApId, hwVirtualClusterAccessApMasterId }
            ::= { hwVirtualClusterAccessApTable 1 }

        HwVirtualClusterAccessApEntry ::=
            SEQUENCE {
                hwVirtualClusterAccessApId
                    IpAddress,
                hwVirtualClusterAccessApMasterId
                    IpAddress,
                hwVirtualClusterAccessApOperState
                    INTEGER,
                hwVirtualClusterAccessApReason
                    Integer32
             }

        hwVirtualClusterAccessApId OBJECT-TYPE
            SYNTAX IpAddress
            MAX-ACCESS not-accessible
            STATUS current
            DESCRIPTION
                "Indicates the AP ID of failure AP."
            ::= { hwVirtualClusterAccessApEntry 1 }

        hwVirtualClusterAccessApMasterId OBJECT-TYPE
            SYNTAX IpAddress
            MAX-ACCESS not-accessible
            STATUS current
            DESCRIPTION
                "Indicates the master ID of failure AP."
            ::= { hwVirtualClusterAccessApEntry 2 }

        hwVirtualClusterAccessApOperState OBJECT-TYPE
            SYNTAX INTEGER
            {
                up(1),
                down(2)
            }
            MAX-ACCESS read-only
            STATUS current
            DESCRIPTION
                "Indicates AP operate state.
                Options:
                1. up(1)          -indicates AP operate state is up.
                2. down(2)        -indicates AP operate state is down."
            ::= { hwVirtualClusterAccessApEntry 3 }

        hwVirtualClusterAccessApReason OBJECT-TYPE
            SYNTAX Integer32
            MAX-ACCESS read-only
            STATUS current
            DESCRIPTION
            "This object indicates the cause that the AP becomes down.
              Options:
                 1. ConfigCancel(1)    --indicates configuration was canceled.
                 2. MscpSessionDown(2) --indicates MSCP session was down.
                 3. other(3)           --indicates other reason.
                 4. ApDelete(4)        --indicates AP was deleted.
                 5. ApUp(5)            --indicates AP was up.
				 "
            ::= { hwVirtualClusterAccessApEntry 4 }

        hwVirtualClusterAccessMasterPeerDownTable OBJECT-TYPE
            SYNTAX SEQUENCE OF HwVirtualClusterAccessMasterPeerDownEntry
            MAX-ACCESS not-accessible
            STATUS current
            DESCRIPTION
                "Basic information about virtual cluster access master.
                 The index of this table is hwVirtualClusterAccessMasterPeerDownMasterId, hwVirtualClusterAccessMasterPeerDownPeerMasterId.
                "
            ::= { hwVirtualClusterAccessTableInfo 6 }

        hwVirtualClusterAccessMasterPeerDownEntry OBJECT-TYPE
            SYNTAX HwVirtualClusterAccessMasterPeerDownEntry
            MAX-ACCESS not-accessible
            STATUS current
            DESCRIPTION
                "Basic information about virtual cluster access master.
                 The index of this entry is hwVirtualClusterAccessMasterPeerDownMasterId, hwVirtualClusterAccessMasterPeerDownPeerMasterId.
                "
            INDEX { hwVirtualClusterAccessMasterPeerDownMasterId, hwVirtualClusterAccessMasterPeerDownPeerMasterId }
            ::= { hwVirtualClusterAccessMasterPeerDownTable 1 }

        HwVirtualClusterAccessMasterPeerDownEntry ::=
            SEQUENCE {
                hwVirtualClusterAccessMasterPeerDownMasterId
                    IpAddress,
                hwVirtualClusterAccessMasterPeerDownPeerMasterId
                    IpAddress,
                hwVirtualClusterAccessMasterPeerDownOperState
                    INTEGER,
                hwVirtualClusterAccessMasterPeerDownReason
                    Integer32
             }

        hwVirtualClusterAccessMasterPeerDownMasterId OBJECT-TYPE
            SYNTAX IpAddress
            MAX-ACCESS not-accessible
            STATUS current
            DESCRIPTION
                "Indicates the master administrative IP address of failure connection."
            ::= { hwVirtualClusterAccessMasterPeerDownEntry 1 }

        hwVirtualClusterAccessMasterPeerDownPeerMasterId OBJECT-TYPE
            SYNTAX IpAddress
            MAX-ACCESS not-accessible
            STATUS current
            DESCRIPTION
                "Indicates the peer master administrative IP address of failure connection."
            ::= { hwVirtualClusterAccessMasterPeerDownEntry 2 }

        hwVirtualClusterAccessMasterPeerDownOperState OBJECT-TYPE
            SYNTAX INTEGER
            {
                up(1),
                down(2)
            }
            MAX-ACCESS read-only
            STATUS current
            DESCRIPTION
                "Indicates peer master operate state.
                Options:
                1. up(1)          -indicates peer master operate state is up.
                2. down(2)        -indicates peer master operate state is down."
            ::= { hwVirtualClusterAccessMasterPeerDownEntry 3 }

        hwVirtualClusterAccessMasterPeerDownReason OBJECT-TYPE
            SYNTAX Integer32
            MAX-ACCESS read-only
            STATUS current
            DESCRIPTION
            "This object indicates the cause that the peer master becomes down.
             Options:
                 1. MscpSessionDown(1) --indicates MSCP session was down.
                 2. masterQuitVirtualclusteraccess(2) --indicates master quit virtual cluster access.
                 3. peerMasterRequestDisconnect(3)   --indicates peer master request disconnect.
                 4. other(4)        --indicates other reason.
                 5. peerMasterDelete(5) --indicates peer master was deleted.
                 6. ApUp(6)            --indicates AP was up.
				 "
            ::= { hwVirtualClusterAccessMasterPeerDownEntry 4 }

        hwVirtualClusterAccessLinkDownTable OBJECT-TYPE
            SYNTAX SEQUENCE OF HwVirtualClusterAccessLinkDownEntry
            MAX-ACCESS not-accessible
            STATUS current
            DESCRIPTION
                "Basic information about virtual cluster access link down.
                 The index of this table is hwVirtualClusterAccessLinkDownApId, hwVirtualClusterAccessLinkDownIfIndex.
                "
            ::= { hwVirtualClusterAccessTableInfo 7 }

        hwVirtualClusterAccessLinkDownEntry OBJECT-TYPE
            SYNTAX HwVirtualClusterAccessLinkDownEntry
            MAX-ACCESS not-accessible
            STATUS current
            DESCRIPTION
                "Basic information about virtual cluster access link down.
                 The index of this entry is hwVirtualClusterAccessLinkDownApId, hwVirtualClusterAccessLinkDownIfIndex.
                "
            INDEX { hwVirtualClusterAccessLinkDownApId, hwVirtualClusterAccessLinkDownIfIndex }
            ::= { hwVirtualClusterAccessLinkDownTable 1 }

        HwVirtualClusterAccessLinkDownEntry ::=
            SEQUENCE {
                hwVirtualClusterAccessLinkDownApId
                    IpAddress,
                hwVirtualClusterAccessLinkDownIfIndex
                    Integer32,
                hwVirtualClusterAccessLinkDownIfAdminStatus
                    INTEGER,
                hwVirtualClusterAccessLinkDownIfOperStatus
                    INTEGER,
                hwVirtualClusterAccessLinkDownIfName
                    SnmpAdminString,
               hwVirtualClusterAccessLinkDownReason
                    Integer32
             }

        hwVirtualClusterAccessLinkDownApId OBJECT-TYPE
            SYNTAX IpAddress
            MAX-ACCESS not-accessible
            STATUS current
            DESCRIPTION
                "Indicates the AP administrative IP address of failure node."
            ::= { hwVirtualClusterAccessLinkDownEntry 1 }

        hwVirtualClusterAccessLinkDownIfIndex OBJECT-TYPE
            SYNTAX Integer32(1..65535)
            MAX-ACCESS not-accessible
            STATUS current
            DESCRIPTION
                "Indicates the index of failure interface."
            ::= { hwVirtualClusterAccessLinkDownEntry 2 }

        hwVirtualClusterAccessLinkDownIfAdminStatus OBJECT-TYPE
            SYNTAX INTEGER
            {
                up(1),
                down(2)
            }
            MAX-ACCESS read-only
            STATUS current
            DESCRIPTION
                "Indicates the interface administrative operate state.
                Options:
                1. up(1)          -indicates interface administrative state is up.
                2. down(2)        -indicates interface administrative state is down."
            ::= { hwVirtualClusterAccessLinkDownEntry 3 }

        hwVirtualClusterAccessLinkDownIfOperStatus OBJECT-TYPE
            SYNTAX INTEGER
            {
                up(1),
                down(2)
            }
            MAX-ACCESS read-only
            STATUS current
            DESCRIPTION
                "Indicates link operate state.
                Options:
                1. up(1)          -indicates link operate state is up.
                2. down(2)        -indicates link operate state is down."
            ::= { hwVirtualClusterAccessLinkDownEntry 4 }

        hwVirtualClusterAccessLinkDownIfName OBJECT-TYPE
            SYNTAX SnmpAdminString
            MAX-ACCESS read-only
            STATUS current
            DESCRIPTION
                "Indicates the name of failure interface."
            ::= { hwVirtualClusterAccessLinkDownEntry 5 }

        hwVirtualClusterAccessLinkDownReason OBJECT-TYPE
            SYNTAX Integer32(1..65535)
            MAX-ACCESS read-only
            STATUS current
            DESCRIPTION
                 "This object indicates the cause that the Link becomes down.
                 Options:
                 1. ifPhysicalLinkDown(1)     --indicates interface physical link was down.
                 2. interfaceDelete(2)        --indicates interface was deleted.
                 3. ifPhysicalLinkUp(3)       --indicates interface physical link was up.
				 "
            ::= { hwVirtualClusterAccessLinkDownEntry 6 }

        hwVirtualClusterAccessMasterInfoTable OBJECT-TYPE
            SYNTAX SEQUENCE OF HwVirtualClusterAccessMasterInfoEntry
            MAX-ACCESS not-accessible
            STATUS current
            DESCRIPTION
                "In slave work mode, basic information about virtual cluster access master information.
                 The index of this table is hwVirtualClusterAccessMasterInfoId.
                "
            ::= { hwVirtualClusterAccessTableInfo 8 }

        hwVirtualClusterAccessMasterInfoEntry OBJECT-TYPE
            SYNTAX HwVirtualClusterAccessMasterInfoEntry
            MAX-ACCESS not-accessible
            STATUS current
            DESCRIPTION
                "In slave work mode, basic information about virtual cluster access master information.
                 The index of this entry is hwVirtualClusterAccessMasterInfoId.
                "
            INDEX { hwVirtualClusterAccessMasterInfoId }
            ::= { hwVirtualClusterAccessMasterInfoTable 1 }

        HwVirtualClusterAccessMasterInfoEntry ::=
            SEQUENCE {
                hwVirtualClusterAccessMasterInfoId
                    InetAddress,
                hwVirtualClusterAccessMasterInfoRole
                    INTEGER,
                hwVirtualClusterAccessMasterInfoState
                    INTEGER,
                hwVirtualClusterAccessMasterInfoGrState
                    INTEGER,
                hwVirtualClusterAccessMasterInfoUpTime
                    SnmpAdminString,
                hwVirtualClusterAccessMasterInfoLabelSpaceBaseValue
                    Integer32,
                hwVirtualClusterAccessMasterInfoLabelSpaceSize
                    Integer32
             }

        hwVirtualClusterAccessMasterInfoId OBJECT-TYPE
            SYNTAX InetAddress
            MAX-ACCESS not-accessible
            STATUS current
            DESCRIPTION
                "Indicates the administrative IP address of master."
            ::= { hwVirtualClusterAccessMasterInfoEntry 1 }

        hwVirtualClusterAccessMasterInfoRole OBJECT-TYPE
            SYNTAX INTEGER
                {
                primary(1),
                secondary(2)
                }
            MAX-ACCESS read-only
            STATUS current
            DESCRIPTION
                "Indicates the bandwidth type used by this tunnel.
                Options:
                1. primary(1)          -indicates this is primary master.
                2. secondary(2)        -indicates this is secondary master.
                "
            ::= { hwVirtualClusterAccessMasterInfoEntry 2 }

        hwVirtualClusterAccessMasterInfoState OBJECT-TYPE
            SYNTAX INTEGER
                {
                init(1),
                setup(2),
                preregistering(3),
                registering(4),
                running(5)
                }
            MAX-ACCESS read-only
            STATUS current
            DESCRIPTION
                "Indicates the bandwidth type used by this tunnel.
                Options:
                1. init(1)             -indicates connection is not connected yet.
                2. setup(2)            -indicates connection is up.
                3. preregistering(3)   -indicates AP have sent preregister message and wait response from master.
                4. registering(4)      -indicates AP have sent register message and wait response from master.
                5. running(5)          -indicates connection is connected and registered successfully.
                "
            ::= { hwVirtualClusterAccessMasterInfoEntry 3 }

        hwVirtualClusterAccessMasterInfoGrState OBJECT-TYPE
            SYNTAX INTEGER
                {
                idle(1),
                reconnect(2),
                recovery(3),
                aging(4)
                }
            MAX-ACCESS read-only
            STATUS current
            DESCRIPTION
                "Indicates the bandwidth type used by this tunnel.
                Options:
                1. idle(1)          -indicates GR is not running.
                2. reconnect(2)     -indicates GR is waiting for connection UP.
                3. recovery(3)      -indicates connection is UP and update datas.
                4. aging(4)         -indicates aging un-update datas.
                "
            ::= { hwVirtualClusterAccessMasterInfoEntry 4 }

        hwVirtualClusterAccessMasterInfoUpTime OBJECT-TYPE
            SYNTAX SnmpAdminString
            MAX-ACCESS read-only
            STATUS current
            DESCRIPTION
                "Indicates the up time of connection."
            ::= { hwVirtualClusterAccessMasterInfoEntry 5 }

        hwVirtualClusterAccessMasterInfoLabelSpaceBaseValue OBJECT-TYPE
            SYNTAX Integer32
            MAX-ACCESS read-only
            STATUS current
            DESCRIPTION
                "Indicates the base value of labelspace."
            ::= { hwVirtualClusterAccessMasterInfoEntry 6 }

        hwVirtualClusterAccessMasterInfoLabelSpaceSize OBJECT-TYPE
            SYNTAX Integer32
            MAX-ACCESS read-only
            STATUS current
            DESCRIPTION
                "Indicates the labelspace size."
            ::= { hwVirtualClusterAccessMasterInfoEntry 7 }

        hwVirtualClusterAccessTrap OBJECT IDENTIFIER ::= { hwVirtualClusterAccessMib 2 }

        hwVpTrap OBJECT IDENTIFIER ::= { hwVirtualClusterAccessTrap 1 }

        hwVpDown NOTIFICATION-TYPE
            OBJECTS { hwVirtualClusterAccessVpId, hwVirtualClusterAccessVpApId, hwVirtualClusterAccessVpIfIndex, hwVirtualClusterAccessVpIfName, hwVirtualClusterAccessVpOperState, hwVirtualClusterAccessVpReason }
            STATUS current
            DESCRIPTION
                "This notification indicates that VP changes to down."
            ::= { hwVpTrap 1 }

        hwVpDownClear NOTIFICATION-TYPE
            OBJECTS { hwVirtualClusterAccessVpId, hwVirtualClusterAccessVpApId, hwVirtualClusterAccessVpIfIndex, hwVirtualClusterAccessVpIfName, hwVirtualClusterAccessVpOperState, hwVirtualClusterAccessVpReason }
            STATUS current
            DESCRIPTION
                "This notification indicates that VP changes to up."
            ::= { hwVpTrap 2 }

        hwVpGroupTrap OBJECT IDENTIFIER ::= { hwVirtualClusterAccessTrap 2 }

        hwVpGroupDown NOTIFICATION-TYPE
            OBJECTS { hwVirtualClusterAccessVpGroupVpId, hwVirtualClusterAccessVpGroupOperState, hwVirtualClusterAccessVpGroupReason }
            STATUS current
            DESCRIPTION
                "This notification indicates that VP group changes to down."
            ::= { hwVpGroupTrap 1 }

        hwVpGroupDownClear NOTIFICATION-TYPE
            OBJECTS { hwVirtualClusterAccessVpGroupVpId, hwVirtualClusterAccessVpGroupOperState, hwVirtualClusterAccessVpGroupReason }
            STATUS current
            DESCRIPTION
                "This notification indicates that VP group changes to up."
            ::= { hwVpGroupTrap 2 }

        hwVpGroupSwitch NOTIFICATION-TYPE
            OBJECTS { hwVirtualClusterAccessVpGroupPrimaryVpId, hwVirtualClusterAccessVpGroupStandbyVpId, hwVirtualClusterAccessVpGroupSwitchDirection, hwVirtualClusterAccessVpGroupReason }
            STATUS current
            DESCRIPTION
                "This notification indicates that traffic switch occurred in VP group."
            ::= { hwVpGroupTrap 3 }

        hwVcTrap OBJECT IDENTIFIER ::= { hwVirtualClusterAccessTrap 3 }

        hwVcDown NOTIFICATION-TYPE
            OBJECTS { hwVirtualClusterAccessVcRemoteApIfName, hwVirtualClusterAccessVcAcIfName, hwVirtualClusterAccessVcVpSourceNodeId , hwVirtualClusterAccessVcVpDestNodeId ,
			          hwVirtualClusterAccessVcVpGroupId, hwVirtualClusterAccessVcId, hwVirtualClusterAccessVcType, hwVirtualClusterAccessVcPeerIpAddr, hwVirtualClusterAccessVcOperState, hwVirtualClusterAccessVcReason }
            STATUS current
            DESCRIPTION
                "This notification indicates that VC changes to down."
            ::= { hwVcTrap 1 }

        hwVcDownClear NOTIFICATION-TYPE
            OBJECTS { hwVirtualClusterAccessVcRemoteApIfName, hwVirtualClusterAccessVcAcIfName, hwVirtualClusterAccessVcVpSourceNodeId , hwVirtualClusterAccessVcVpDestNodeId ,
			          hwVirtualClusterAccessVcVpGroupId, hwVirtualClusterAccessVcId, hwVirtualClusterAccessVcType, hwVirtualClusterAccessVcPeerIpAddr, hwVirtualClusterAccessVcOperState, hwVirtualClusterAccessVcReason }
            STATUS current
            DESCRIPTION
                "This notification indicates that VC changes to up."
            ::= { hwVcTrap 2 }

        hwRemoteApIfTrap OBJECT IDENTIFIER ::= { hwVirtualClusterAccessTrap 4 }

        hwRemoteApIfDown NOTIFICATION-TYPE
            OBJECTS { hwVirtualClusterAccessRemoteApIfName, hwVirtualClusterAccessRemoteApIfOperState, hwVirtualClusterAccessRemoteApIfReason }
            STATUS current
            DESCRIPTION
                "This notification indicates that remote AP interface changes to down."
            ::= { hwRemoteApIfTrap 1 }

        hwRemoteApIfDownClear NOTIFICATION-TYPE
            OBJECTS { hwVirtualClusterAccessRemoteApIfName, hwVirtualClusterAccessRemoteApIfOperState, hwVirtualClusterAccessRemoteApIfReason }
            STATUS current
            DESCRIPTION
                "This notification indicates that remote AP interface changes to up."
            ::= { hwRemoteApIfTrap 2 }

        hwApTrap OBJECT IDENTIFIER ::= { hwVirtualClusterAccessTrap 5 }

        hwApDown NOTIFICATION-TYPE
            OBJECTS { hwVirtualClusterAccessApOperState, hwVirtualClusterAccessApReason }
            STATUS current
            DESCRIPTION
                "This notification indicates that AP changes to down."
            ::= { hwApTrap 1 }

        hwApDownClear NOTIFICATION-TYPE
            OBJECTS { hwVirtualClusterAccessApOperState, hwVirtualClusterAccessApReason }
            STATUS current
            DESCRIPTION
                "This notification indicates that AP changes to up."
            ::= { hwApTrap 2 }

        hwApLogin NOTIFICATION-TYPE
		    OBJECTS { hwVirtualClusterAccessApOperState }
            STATUS current
            DESCRIPTION
                "This notification indicates that AP changes to up."
            ::= { hwApTrap 3 }

        hwMasterTrap OBJECT IDENTIFIER ::= { hwVirtualClusterAccessTrap 6 }

        hwMasterPeerDown NOTIFICATION-TYPE
            OBJECTS { hwVirtualClusterAccessMasterPeerDownOperState, hwVirtualClusterAccessMasterPeerDownReason }
            STATUS current
            DESCRIPTION
                "This notification indicates that peer master was lost."
            ::= { hwMasterTrap 1 }

        hwMasterPeerDownClear NOTIFICATION-TYPE
            OBJECTS { hwVirtualClusterAccessMasterPeerDownOperState, hwVirtualClusterAccessMasterPeerDownReason }
            STATUS current
            DESCRIPTION
                "This notification indicates that peer master lost resumed."
            ::= { hwMasterTrap 2 }


       hwVirtualClusterAccessLinkDownTrap OBJECT IDENTIFIER ::= { hwVirtualClusterAccessTrap 7 }

       hwVirtualClusterAccessLinkDown NOTIFICATION-TYPE
            OBJECTS { hwVirtualClusterAccessLinkDownIfName, hwVirtualClusterAccessLinkDownIfAdminStatus, hwVirtualClusterAccessLinkDownIfOperStatus, hwVirtualClusterAccessLinkDownReason}
            STATUS current
            DESCRIPTION
                "This notification indicates that interface changes to down."
            ::= { hwVirtualClusterAccessLinkDownTrap 1 }

       hwVirtualClusterAccessLinkDownClear NOTIFICATION-TYPE
            OBJECTS { hwVirtualClusterAccessLinkDownIfName, hwVirtualClusterAccessLinkDownIfAdminStatus, hwVirtualClusterAccessLinkDownIfOperStatus,  hwVirtualClusterAccessLinkDownReason}
            STATUS current
            DESCRIPTION
                "This notification indicates that interface changes to up."
            ::= { hwVirtualClusterAccessLinkDownTrap 2 }


       hwVirtualClusterAccessConformance OBJECT IDENTIFIER ::= { hwVirtualClusterAccessMib 3 }

       hwVirtualClusterAccessGroups OBJECT IDENTIFIER ::= { hwVirtualClusterAccessConformance 1 }

       hwVirtualClusterAccessVpGroup OBJECT-GROUP
	     OBJECTS {  hwVirtualClusterAccessVpApId, hwVirtualClusterAccessVpIfIndex, hwVirtualClusterAccessVpIfName, hwVirtualClusterAccessVpOperState, hwVirtualClusterAccessVpReason, hwVirtualClusterAccessVpId }
	     STATUS current
	     DESCRIPTION
	        "Basic information about virtual cluster access VP."
	     ::= { hwVirtualClusterAccessGroups 1 }

       hwVirtualClusterAccessVpGroupGroup OBJECT-GROUP
	     OBJECTS { hwVirtualClusterAccessVpGroupVpId, hwVirtualClusterAccessVpGroupOperState, hwVirtualClusterAccessVpGroupReason, hwVirtualClusterAccessVpGroupPrimaryVpId, hwVirtualClusterAccessVpGroupStandbyVpId, hwVirtualClusterAccessVpGroupSwitchDirection}
	     STATUS current
	     DESCRIPTION
	        "Basic information about virtual cluster access VP group."
	     ::= { hwVirtualClusterAccessGroups 2 }

       hwVirtualClusterAccessVcGroup OBJECT-GROUP
	     OBJECTS { hwVirtualClusterAccessVcRemoteApIfName, hwVirtualClusterAccessVcAcIfName, hwVirtualClusterAccessVcVpSourceNodeId , hwVirtualClusterAccessVcVpDestNodeId ,
	              hwVirtualClusterAccessVcVpGroupId, hwVirtualClusterAccessVcId, hwVirtualClusterAccessVcType, hwVirtualClusterAccessVcPeerIpAddr, hwVirtualClusterAccessVcOperState, hwVirtualClusterAccessVcReason }
	     STATUS current
	     DESCRIPTION
	        "Basic information about virtual cluster access VC."
	     ::= { hwVirtualClusterAccessGroups 3 }

       hwVirtualClusterAccessRemoteApIfGroup OBJECT-GROUP
	     OBJECTS { hwVirtualClusterAccessRemoteApIfName, hwVirtualClusterAccessRemoteApIfOperState, hwVirtualClusterAccessRemoteApIfReason }
	     STATUS current
	     DESCRIPTION
	        "Basic information about virtual cluster access remote AP interface."
	     ::= { hwVirtualClusterAccessGroups 4 }

       hwVirtualClusterAccessApGroup OBJECT-GROUP
	     OBJECTS { hwVirtualClusterAccessApOperState, hwVirtualClusterAccessApReason }
	     STATUS current
	     DESCRIPTION
	        "Basic information about virtual cluster access AP."
	     ::= { hwVirtualClusterAccessGroups 5 }

       hwVirtualClusterAccessMasterPeerGroup OBJECT-GROUP
	     OBJECTS { hwVirtualClusterAccessMasterPeerDownOperState, hwVirtualClusterAccessMasterPeerDownReason }
	     STATUS current
	     DESCRIPTION
	        "Basic information about virtual cluster access master."
	     ::= { hwVirtualClusterAccessGroups 6 }

	     hwVCNotificationGroup NOTIFICATION-GROUP
	          NOTIFICATIONS {
	              hwVpDown,
	              hwVpDownClear,
	              hwVpGroupDown,
	              hwVpGroupDownClear,
	              hwVpGroupSwitch,
	              hwVcDown,
	              hwVcDownClear,
	              hwRemoteApIfDown,
	              hwRemoteApIfDownClear,
	              hwApDown,
	              hwApDownClear,
	              hwApLogin,
	              hwMasterPeerDown,
	              hwMasterPeerDownClear,
	              hwVirtualClusterAccessLinkDown,
	              hwVirtualClusterAccessLinkDownClear
	              }
            STATUS current
            DESCRIPTION
                "The virtual cluster access Notification information."
            ::= { hwVirtualClusterAccessGroups 7 }

       hwVirtualClusterAccessLinkDownGroup OBJECT-GROUP
	     OBJECTS { hwVirtualClusterAccessLinkDownIfName, hwVirtualClusterAccessLinkDownIfAdminStatus, hwVirtualClusterAccessLinkDownIfOperStatus, hwVirtualClusterAccessLinkDownReason }
	     STATUS current
	     DESCRIPTION
	        "Basic information about virtual cluster access link down."
	     ::= { hwVirtualClusterAccessGroups 8 }

       hwVirtualClusterAccessGlobalGroup OBJECT-GROUP
	    OBJECTS { hwVirtualClusterAccessWorkMode, hwVirtualClusterAccessAdminIP, hwVirtualClusterAccessVPNInstanceName, hwVirtualClusterAccessAdminIPDiscoveryMode, hwVirtualClusterAccessMasterDiscoveryMode,hwVirtualClusterAccessPathComputeMasterId }
	    STATUS current
	    DESCRIPTION
	        "Basic information about virtual cluster access global information."
	    ::= { hwVirtualClusterAccessGroups 9 }


      hwVirtualClusterAccessMasterInfoGroup OBJECT-GROUP
	    OBJECTS { hwVirtualClusterAccessMasterInfoRole, hwVirtualClusterAccessMasterInfoState, hwVirtualClusterAccessMasterInfoGrState, hwVirtualClusterAccessMasterInfoUpTime, hwVirtualClusterAccessMasterInfoLabelSpaceBaseValue, hwVirtualClusterAccessMasterInfoLabelSpaceSize }
	    STATUS current
	    DESCRIPTION
	        "In slave work mode, basic information about virtual cluster access master information."
	    ::= { hwVirtualClusterAccessGroups 10 }

      hwVirtualClusterAccessCompliances OBJECT IDENTIFIER ::= { hwVirtualClusterAccessConformance 2 }

      hwVirtualClusterAccessCompliance MODULE-COMPLIANCE
            STATUS current
            DESCRIPTION
                "The virtual cluster access information."
            MODULE HUAWEI-VIRTUALCLUSTERACCESS-MIB
            MANDATORY-GROUPS { hwVirtualClusterAccessVpGroup, hwVirtualClusterAccessVpGroupGroup, hwVirtualClusterAccessVcGroup,
                               hwVirtualClusterAccessRemoteApIfGroup, hwVirtualClusterAccessApGroup, hwVirtualClusterAccessMasterPeerGroup,
                               hwVCNotificationGroup, hwVirtualClusterAccessLinkDownGroup, hwVirtualClusterAccessGlobalGroup, hwVirtualClusterAccessMasterInfoGroup
                               }
            ::= { hwVirtualClusterAccessCompliances 1 }

    END

--
-- HUAWEI-VIRTUALCLUSTERACCESS-MIB.mib
--
