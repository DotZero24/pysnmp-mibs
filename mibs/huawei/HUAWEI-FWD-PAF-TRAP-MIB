--
-- HUAWEI-FWD-PAF-TRAP-MIB.mib
-- Copyright (C) 2006 by HUAWEI TECHNOLOGIES. All rights reserved
-- Friday, May 27, 2011 at 20:05:42
--

	HUAWEI-FWD-PAF-TRAP-MIB DEFINITIONS ::= BEGIN

		IMPORTS
			entPhysicalName
				FROM ENTITY-MIB
			hwDatacomm
				FROM HUAWEI-MIB
			OBJECT-GROUP, NOTIFICATION-GROUP, MODULE-COMPLIANCE
				FROM SNMPv2-CONF
			Unsigned32, OBJECT-TYPE, MODULE-IDENTITY, NOTIFICATION-TYPE
				FROM SNMPv2-SMI;


		hwFwdPafTrapMIB MODULE-IDENTITY
			LAST-UPDATED "201105261134Z"		-- May 26, 2011 at 11:34 GMT
			ORGANIZATION
        "Huawei Technologies Co.,Ltd."
			CONTACT-INFO
        "Huawei Industrial Base
        Bantian, Longgang
        Shenzhen 518129
        People's Republic of China
        Website: http://www.huawei.com
        Email: support@huawei.com
        "
			DESCRIPTION
				"The private mib file includes the alarm
				information of FEI reported."
			REVISION "201105261135Z"		-- May 26, 2011 at 11:35 GMT
			DESCRIPTION
				"ver 1.0"
			::= { hwDatacomm 288 }



--
-- Node definitions
--

		-- 1.3.6.1.4.1.2011.5.25.288.1
		hwFwdPafTrapObject OBJECT IDENTIFIER ::= { hwFwdPafTrapMIB 1 }

		-- 1.3.6.1.4.1.2011.5.25.288.1.1
		hwFwdPafChassisId OBJECT-TYPE
			SYNTAX Unsigned32
			MAX-ACCESS accessible-for-notify
			STATUS current
			DESCRIPTION
				"The index for the chassis."
			::= { hwFwdPafTrapObject 1 }

		-- 1.3.6.1.4.1.2011.5.25.288.1.2
		hwFwdPafSlotId OBJECT-TYPE
			SYNTAX Unsigned32
			MAX-ACCESS accessible-for-notify
			STATUS current
			DESCRIPTION
				"The index for the slot."
			::= { hwFwdPafTrapObject 2 }

		-- 1.3.6.1.4.1.2011.5.25.288.1.3
		hwFwdPhysicalindex OBJECT-TYPE
			SYNTAX Unsigned32
			MAX-ACCESS accessible-for-notify
			STATUS current
			DESCRIPTION
				"The index for this entry."
			::= { hwFwdPafTrapObject 3 }

		-- 1.3.6.1.4.1.2011.5.25.288.2
		hwFwdPafTraps OBJECT IDENTIFIER ::= { hwFwdPafTrapMIB 2 }

		-- 1.3.6.1.4.1.2011.5.25.288.2.1
		hwFwdPafTrap OBJECT IDENTIFIER ::= { hwFwdPafTraps 1 }

		-- 1.3.6.1.4.1.2011.5.25.288.2.1.1
		hwLCFwdPafNonSupport NOTIFICATION-TYPE
			OBJECTS { hwFwdPhysicalindex, entPhysicalName, hwFwdPafChassisId, hwFwdPafSlotId }
			STATUS current
			DESCRIPTION
				"Description."
			::= { hwFwdPafTrap 1 }

		-- 1.3.6.1.4.1.2011.5.25.288.2.1.2
		hwLCFwdPafNonSupportResume NOTIFICATION-TYPE
			OBJECTS { hwFwdPhysicalindex, entPhysicalName, hwFwdPafChassisId, hwFwdPafSlotId }
			STATUS current
			DESCRIPTION
				"Description."
			::= { hwFwdPafTrap 2 }

		-- 1.3.6.1.4.1.2011.5.25.288.3
		hwFwdPafTrapConformance OBJECT IDENTIFIER ::= { hwFwdPafTrapMIB 3 }

		-- 1.3.6.1.4.1.2011.5.25.288.3.1
		hwFwdPafTrapGroups OBJECT IDENTIFIER ::= { hwFwdPafTrapConformance 1 }

		-- 1.3.6.1.4.1.2011.5.25.288.3.1.1
		hwFwdPafObjectGroup OBJECT-GROUP
			OBJECTS { hwFwdPafChassisId, hwFwdPafSlotId, hwFwdPhysicalindex }
			STATUS current
			DESCRIPTION
				"Description."
			::= { hwFwdPafTrapGroups 1 }

		-- 1.3.6.1.4.1.2011.5.25.288.3.1.2
		hwFwdPafTrapGroup NOTIFICATION-GROUP
			NOTIFICATIONS { hwLCFwdPafNonSupport, hwLCFwdPafNonSupportResume }
			STATUS current
			DESCRIPTION
				"Description."
			::= { hwFwdPafTrapGroups 2 }

		hwFwdPafTrapCompliance MODULE-COMPLIANCE
		    STATUS current
			DESCRIPTION
			   "Description"
			MODULE -- this module
			MANDATORY-GROUPS { hwFwdPafTrapGroup }
			::= { hwFwdPafTrapGroups 3 }


	END

--
-- HUAWEI-FWD-PAF-TRAP-MIB.mib
--
