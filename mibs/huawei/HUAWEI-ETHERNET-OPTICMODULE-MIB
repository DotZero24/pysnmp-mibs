-- ============================================================================
-- Copyright (C) 2019 by HUAWEI TECHNOLOGIES. All rights reserved.
-- Description: This mib is used for managing Ethernet optics module.
-- Reference:
-- Version: V1.38
-- ============================================================================

  HUAWEI-ETHERNET-OPTICMODULE-MIB DEFINITIONS ::= BEGIN

    IMPORTS
      hwFrameIndex, hwSlotIndex, hwFrameIndex, hwSlotIndex, hwPortIndex, hwPortDesc
        FROM HUAWEI-DEVICE-MIB
      huaweiMgmt
        FROM HUAWEI-MIB
      ifIndex, InterfaceIndex
        FROM IF-MIB
      TimeTicks,OBJECT-TYPE,Integer32,Unsigned32,MODULE-IDENTITY,NOTIFICATION-TYPE
        FROM SNMPv2-SMI
      TruthValue, MacAddress, RowStatus, TEXTUAL-CONVENTION
        FROM SNMPv2-TC;

    hwEthernetPort MODULE-IDENTITY
      LAST-UPDATED "201906110000Z"
      ORGANIZATION "Huawei Technologies Co.,Ltd."
      CONTACT-INFO
                   "Huawei Industrial Base
                    Bantian, Longgang
                    Shenzhen 518129
                    People's Republic of China
                    Website: http://www.huawei.com
                    Email: support@huawei.com
                   "
      DESCRIPTION
        "This mib is used for managing Ethernet optics module."

--  Revision history
      REVISION     "201906110000Z"
      DESCRIPTION  "V1.38
	               Modify leaf hwOpticsSmartSFPIILoopOpticloss description;
				   Modify leaf hwOpticsPowerThresholdSwitch deafultValueInEnum;
				   Modify leaf hwOpticsTemperatureThresholdSwitch deafultValueInEnum;
				   Modify leaf hwOpticsVoltageThresholdSwitch deafultValueInEnum;
				   Modify leaf hwOpticsCurrentThresholdSwitch deafultValueInEnum;
				   Modify leaf hwOpticsLaserTemperatureThresholdSwitch deafultValueInEnum;
				   Modify leaf hwOpticsWaveLengthThresholdSwitch deafultValueInEnum;
				   Modify leaf hwOpticsTecCurrentThresholdSwitch deafultValueInEnum.
				   "

      REVISION     "201808270000Z"
      DESCRIPTION  "V1.37, Add leaf hwOpticsTransceiverNormalAlarmTrap into hwOpticsAlarmTraps."

      REVISION     "201807060000Z"
      DESCRIPTION  "V1.36
                    Add leaf hwOpticsMDSFF8636Compliance into hwOpticsModuleInformationTable;
                    Add enumerated qSfpPlus(14) and qSfp28(18) in hwOpticsMDIdentifier leaf node;
                    Add enumerated powerClass1(9), powerClass2(10), powerClass3(11), powerClass4(12),
                    powerClass5(13), powerClass6(14), and powerClass7(15) in hwOpticsMDExtID leaf node;
      			    Add enumerated mpo2ParallelOptic(18) in hwOpticsMDConnector leaf node;
      			    Modify the scope of hwOpticsModuleUserEeprom;
                    Add enumerated en100GBASESR4(16), en100GBASELR4(17), en100GBASEER4(18),
                    and en100GBASESR10(19) in hwOpticsMDGEComplianceCodes leaf node;
                    Add enumerated multiMode50mOM3(8) in hwOpticsMDTransmissionMedia leaf node;
                    Add enumerated speedExtended(8) in hwOpticsMDSpeed leaf node;
                    Add table hwOpticsChannelDdmInformationTable;
                    Add the following leaves into hwOpticsChannelDdmInformationTable:
                     hwOpticsModuleChannelIndex
                     hwOpticsModuleChannleTxBiasCurrent
                     hwOpticsModuleChannleTxPower
                     hwOpticsModuleChannleRxPower.
                   "

      REVISION     "201711070000Z"
      DESCRIPTION  "V1.35, leaf hwOpticsMDGEComplianceCodes add enum."

      REVISION     "201708070000Z"
      DESCRIPTION  "V1.34
       			    Modify the scope of hwOpticsPowerTxLowerThresholdValue;
      			    Modify the scope of hwOpticsPowerTxUpperThresholdValue;
      			    Modify the scope of hwOpticsPowerRxUpperThresholdValue;
      			    Modify the scope of hwOpticsPowerRxLowerThresholdValue;
      			    Modify the scope of hwOpticsTemperatureLowerThresholdValue;
      			    Modify the scope of hwOpticsTemperatureUpperThresholdValue;
      			    Modify the scope of hwOpticsVoltageLowerThresholdValue;
      			    Modify the scope of hwOpticsVoltageUpperThresholdValue;
      			    Modify the scope of hwOpticsCurrentLowerThresholdValue;
      			    Modify the scope of hwOpticsCurrentUpperThresholdValue;
      			    Modify the scope of hwOpticsLaserTemperatureLowerThresholdValue;
      			    Modify the scope of hwOpticsLaserTemperatureUpperThresholdValue;
      			    Modify the scope of hwOpticsWaveLengthLowerThresholdValue;
      			    Modify the scope of hwOpticsWaveLengthUpperThresholdValue;
      			    Modify the scope of hwOpticsTecCurrentLowerThresholdValue;
      			    Modify the scope of hwOpticsTecCurrentUpperThresholdValue;"

      REVISION     "201704050000Z"
      DESCRIPTION  "V1.33
      			    Modify the scope of hwOpticsModuleThresholdTxLower;
      			    Modify the scope of hwOpticsModuleThresholdTxUpper;
      			    Modify the scope of hwOpticsModuleThresholdRxUpper;
      			    Modify the scope of hwOpticsModuleThresholdRxLower;
      			    Modify the scope of hwOpticsModuleThresholdTempLower;
      			    Modify the scope of hwOpticsModuleThresholdTempUpper;
      			    Modify the scope of hwOpticsModuleThresholdVoltageLower;
      			    Modify the scope of hwOpticsModuleThresholdVoltageUpper;
      			    Modify the scope of hwOpticsModuleThresholdCurrentLower;
      			    Modify the scope of hwOpticsModuleThresholdCurrentUpper;
      			    Modify the scope of hwOpticsModuleThresholdLaserTempLower;
      			    Modify the scope of hwOpticsModuleThresholdLaserTempUpper;
      			    Modify the scope of hwOpticsModuleThresholdWaveLengthLower;
      			    Modify the scope of hwOpticsModuleThresholdWaveLengthUpper;
      			    Modify the scope of hwOpticsModuleThresholdTecCurrentLower;
      			    Modify the scope of hwOpticsModuleThresholdTecCurrentUpper;"

      REVISION     "201702150000Z"
      DESCRIPTION  "V1.32
      			    Modify the scope of hwOpticsMDSpeed;
      			    Modify the scope of hwOpticsMDSFPRateId;
      			    Modify the scope of hwOpticsMDOptions;
      			    Modify the scope of hwOpticsMDSFF8472Compliance;
					"

      REVISION     "201702070000Z"
      DESCRIPTION  "V1.31
      			    Modify the description of hwOpticsMDSFF8472Compliance
      			    Modify the scope of hwOpticsMDSFF8472Compliance;
      			    Modify the scope of hwOpticsMDIdentifier;
      			    Modify the scope of hwOpticsMDExtID;
      			    Modify the scope of hwOpticsMDConnector;
      			    Modify the scope of hwOpticsMDEncoding;
      			    Modify the scope of hwOpticsMDGEComplianceCodes;
      			    Modify the scope of hwOpticsMDSFPRateId;
      			    Modify the scope of hwOpticsMDOptions;
      			    Modify the scope of hw10GEOpticsMDIdentifier;
      			    Modify the scope of hw10GEOpticsMDExtCLEICode;
      			    Modify the scope of hw10GEOpticsMDExtTXRefClock;
      			    Modify the scope of hw10GEOpticsMDExtCDRFunc;
      			    Modify the scope of hw10GEOpticsMDExtPowerLevel;
      			    Modify the scope of hw10GEOpticsMDConnector;
      			    Modify the scope of hw10GEOpticsMDTransmitterSupport;
      			    Modify the scope of hw10GEOpticsMDDetector;
      			    Modify the scope of hw10GEOpticsMDCooledTransmitterDevice;
      			    Modify the scope of hw10GEOpticsMDWavelengthControl;
      			    Modify the scope of hw10GEOpticsMDTransmitterTechnologySupport;
      			    Modify the scope of hw10GEOpticsMDSupportXFIMode;
      			    Modify the scope of hw10GEOpticsMDSupportLinesideMode;
      			    Modify the scope of hw10GEOpticsMDEnhancedOptions;
      			    Modify the scope of hw10GEOpticsMDAuxInputOne;
      			    Modify the scope of hw10GEOpticsMDAuxInputTwo;
					"

      REVISION     "201607180000Z"
      DESCRIPTION  "V1.30
      				1. Add the default value and Modify the description of the following leaves
      				   in table hwOpticsPowerThresholdTable:
                       Add the default value of hwOpticsPowerTxLowerThresholdValue
                       Add the default value of hwOpticsPowerTxUpperThresholdValue
                       Add the default value of hwOpticsPowerRxUpperThresholdValue
                       Add the default value of hwOpticsPowerRxLowerThresholdValue
                       Add the default value of hwOpticsTemperatureLowerThresholdValue
                       Add the default value of hwOpticsTemperatureUpperThresholdValue
                       Add the default value of hwOpticsVoltageLowerThresholdValue
                       Add the default value of hwOpticsVoltageUpperThresholdValue
                       Add the default value of hwOpticsCurrentLowerThresholdValue
                       Add the default value of hwOpticsCurrentUpperThresholdValue
                       Add the default value of hwOpticsLaserTemperatureLowerThresholdValue
                       Add the default value of hwOpticsLaserTemperatureUpperThresholdValue
                       Add the default value of hwOpticsWaveLengthLowerThresholdValue
                       Add the default value of hwOpticsWaveLengthUpperThresholdValue
                       Add the default value of hwOpticsTecCurrentLowerThresholdValue
                       Add the default value of hwOpticsTecCurrentUpperThresholdValue.
                    2. Add table hwOpticsModuleThresholdTable.
                    3. Add the following leaves into hwOpticsModuleThresholdTable:
                       hwOpticsModuleThresholdTxLower
                       hwOpticsModuleThresholdTxUpper
                       hwOpticsModuleThresholdRxUpper
                       hwOpticsModuleThresholdRxLower
                       hwOpticsModuleThresholdTempLower
                       hwOpticsModuleThresholdTempUpper
                       hwOpticsModuleThresholdVoltageLower
                       hwOpticsModuleThresholdVoltageUpper
                       hwOpticsModuleThresholdCurrentLower
                       hwOpticsModuleThresholdCurrentUpper
                       hwOpticsModuleThresholdLaserTempLower
                       hwOpticsModuleThresholdLaserTempUpper
                       hwOpticsModuleThresholdWaveLengthLower
                       hwOpticsModuleThresholdWaveLengthUpper
                       hwOpticsModuleThresholdTecCurrentLower
                       hwOpticsModuleThresholdTecCurrentUpper."

      REVISION     "201512040000Z"
      DESCRIPTION  "V1.29, Modify the Units of hwOpticsTxBiasCurrent"

      REVISION     "201410250000Z"
      DESCRIPTION  "V1.28, Modify the scope of hwOpticsMDGEComplianceCodes"

      REVISION     "201409020000Z"
      DESCRIPTION  "V1.27
                    Add the following leave into hwOpticsModuleInformationTable:
                    hwOpticsModuleUserEeprom"

      REVISION     "201407220000Z"
      DESCRIPTION  "V1.26
                    1. Add the following leaves into hwOpticsModuleInformationTable:
                       hwOpticsDwdmClass
                       hwOpticsDwdmPower
                       hwOpticsDwdmMaxTemperature
                       hwOpticsDwdmMinTemperature
                       hwOpticsDwdmMaxSupplyCurrent
                       hwOpticsDwdmChannelSpacing
                       hwOpticsDwdmNumberOfChannels
                       hwOpticsDwdmWaveLength
                    2. Add the following leaves into hwOpticsDdmInformationTable:
                       hwOpticsLaserTemperature
                       hwOpticsWaveLength
                       hwOpticsTecCurrent
                    3. Add the following leaves into hwOpticsPowerThresholdTable:
                       hwOpticsLaserTemperatureLowerThresholdValue
                       hwOpticsLaserTemperatureUpperThresholdValue
                       hwOpticsLaserTemperatureThresholdSwitch
                       hwOpticsWaveLengthLowerThresholdValue
                       hwOpticsWaveLengthUpperThresholdValue
                       hwOpticsWaveLengthThresholdSwitch
                       hwOpticsTecCurrentLowerThresholdValue
                       hwOpticsTecCurrentUpperThresholdValue
                       hwOpticsTecCurrentThresholdSwitch"

      REVISION     "201406290000Z"
      DESCRIPTION  "V1.25, Modify hwEthernet to hwEthernetPort because the HUAWEI-MIB changed
                    and modify the following not normative nodes to satisfy for the new OMSYS tool.
                    hwOpticsModuleInformation
		    hwOpticsSmartSFPProtocolVersion
		    hwOpticsSmartSFPSSFPEnhancedOption
		    hwOpticsSmartSFPLoopbackdeviceloss
		    hwOpticsSmartSFPRoundtripfiberloss
		    hwOpticsSmartSFPIILoopOpticloss."

      REVISION     "201404170000Z"
      DESCRIPTION  "V1.24, Add leaf hwOpticsMDHuaweiPartNumber into hwOpticsModuleTransceiverTable."

      REVISION     "201204200000Z"
      DESCRIPTION  "V1.23, Modify the description of mib:
                    Modify the unit of hwOpticsMDWaveLength."

      REVISION     "201112270000Z"
      DESCRIPTION  "V1.22, Modify the description of mib:
                    Modify the scope and unit of hwOpticsTemperatureLowerThresholdValue
                    Modify the scope and unit of hwOpticsTemperatureUpperThresholdValue
                    Modify the scope and unit of hwOpticsVoltageLowerThresholdValue
                    Modify the scope and unit of hwOpticsVoltageUpperThresholdValue
                    Modify the scope and unit of hwOpticsCurrentLowerThresholdValue
                    Modify the scope and unit of hwOpticsCurrentUpperThresholdValue."

      REVISION     "201112060000Z"
      DESCRIPTION  "V1.21, Add the following leaves into hwOpticsModuleInformationTable:
      		        hwOpticsMDSFPPulsCableTech,
      		        hwOpticsMDSFPRateId,
      		        hwOpticsMDLength50MicronOM3.
      		        Modify the scope of hwOpticsMDIdentifier;
      		        Modify the scope of hwOpticsMDConnector;
      		        Modify the scope of hwOpticsMDSFF8472Compliance;
      		        Modify the scope of hwOpticsMDGEComplianceCodes;
      		        Modify the scope of hwOpticsMDLinkLength;
      		        Modify the scope of hwOpticsMDSpeed.
      		        Modify the description of mib:
      		        hwOpticsMDLength9Micron,
      		        hwOpticsMDSFF8472Compliance,
      		        hwOpticsMDLength9Micronkm."


      REVISION     "201110050000Z"
      DESCRIPTION  "V1.20, Modify the name of hwOpticsPowerThresholdValue.
      		    Modify the description of mib:
                    Add the invalid value description of hwOpticsTemperature
                    Add the invalid value description of hwOpticsSupplyVoltage
                    Add the invalid value description of hwOpticsTxBiasCurrent
                    Add the invalid value description of hwOpticsTxPower
                    Add the invalid value description of hwOpticsRxPower
                    Add the invalid value description of hwOpticsPowerTxLowerThresholdValue
                    Add the invalid value description of hwOpticsPowerTxUpperThresholdValue
                    Add the invalid value description of hwOpticsPowerRxUpperThresholdValue
                    Add the invalid value description of hwOpticsPowerRxLowerThresholdValue
                    Add the invalid value description of hwOpticsTemperatureLowerThresholdValue
                    Add the invalid value description of hwOpticsTemperatureUpperThresholdValue
                    Add the invalid value description of hwOpticsVoltageLowerThresholdValue
                    Add the invalid value description of hwOpticsVoltageUpperThresholdValue
                    Add the invalid value description of hwOpticsCurrentLowerThresholdValue
                    Add the invalid value description of hwOpticsCurrentUpperThresholdValue."

      REVISION     "201107260000Z"
      DESCRIPTION  "V1.19, Modify the description of mib.
                    Modify the scope of hwOpticsTemperatureLowerThresholdValue
                    Modify the scope of hwOpticsTemperatureUpperThresholdValue."

      REVISION     "201107050000Z"
      DESCRIPTION  "V1.18, Add the following leaves into hwOpticsPowerThresholdTable:
                    hwOpticsTemperatureLowerThresholdValue,
                    hwOpticsTemperatureUpperThresholdValue,
                    hwOpticsTemperatureThresholdSwitch,
                    hwOpticsVoltageLowerThresholdValue,
                    hwOpticsVoltageUpperThresholdValue,
                    hwOpticsVoltageThresholdSwitch,
                    hwOpticsCurrentLowerThresholdValue,
                    hwOpticsCurrentUpperThresholdValue,
                    hwOpticsCurrentThresholdSwitch."

      REVISION     "201101210000Z"
      DESCRIPTION  "V1.17, Add leaf hwOpticsMDInfoRemote into hwOpticsModuleInformationTable.
                    Add leaf hwOpticsMDTransceiverRemote into hwOpticsModuleTransceiverTable.
                    Add leaf hwOpticsMDDdmInfoRemote into hwOpticsDdmInformationTable.
                    Add hwOpticsSmartSFPExtModuleInformationTable.
                    Add following leaves into hwOpticsSmartSFPExtModuleInformationTable:
                     hwOpticsSmartSFPIdentifier,
                     hwOpticsSmartSFPProtocolVersion,
                     hwOpticsSmartSFPSSFPEnhancedOption,
                     hwOpticsSmartSFPPassword,
                     hwOpticsSmartSFPRemoteControllable,
                     hwOpticsSmartSFPSubCarrierControl,
                     hwOpticsSmartSFPSubCarrierlinkStatus,
                     hwOpticsSmartSFPLocalLoopback,
                     hwOpticsSmartSFPRemoteLoopback,
                     hwOpticsSmartSFPDyingGaspStatus,
                     hwOpticsSmartSFPLocalRXOutputControl,
                     hwOpticsSmartSFPPilottoneControl,
                     hwOpticsSmartSFPPilottoneStatus,
                     hwOpticsSmartSFPLoopbackdeviceloss,
                     hwOpticsSmartSFPRoundtripfiberloss,
                     hwOpticsSmartSFPExtModuleInfoRemote.
                    Add hwOpticsSmartSFPConfigTable.
                    Add leaf hwOpticsSmartSFPIILoopOpticloss into hwOpticsSmartSFPConfigTable.
                    Modify the description of mib."

      REVISION     "201010100000Z"
      DESCRIPTION  "V1.16, Modify the description of hwOpticsPowerThresholdSwitch.
                    Add an enumerate invalid(-1) of hw10GEOpticsMDFibreCompliance."

      REVISION     "201007100000Z"
      DESCRIPTION  "V1.15, Modify the description of mib.
                    Add following leaves into hwOpticsPowerThresholdTable:
                     hwOpticsPowerTxUpperThresholdValue,
                     hwOpticsPowerRxUpperThresholdValue,
                     hwOpticsPowerRxLowerThresholdValue.
                    Modify the scope of hwOpticsPowerThresholdValue.
                    Modify the module name HUAWEI-ETHERNET-OPTICSMODULE-MIB to HUAWEI-ETHERNET-OPTICMODULE-MIB
                    Delete parameter hwPortDesc of hwOpticsTransceiverFaultyAlarmTrap."


      REVISION     "201005120000Z"
      DESCRIPTION  "V1.14, leaf hwOpticsMDGEComplianceCodes add enum. "

      REVISION     "201004200000Z"
      DESCRIPTION  "V1.13, Modify the name of HUAWEI-ETHERNET-OPTICSMODULE-MIB "

      REVISION     "201004120000Z"
      DESCRIPTION  "V1.12, leaf hw10GEOpticsMDLowerSpeedLink add enum,
                    leaf hw10GEOpticsMDMaxBitRateSupportedByCDR add enum,
                    table hwOpticsModuleInformationTable add description ,
                    table hwOpticsModuleTransceiverTable add description ,
                    table hw10GEOpticsModuleInformationTable add description ,
                    table hwOpticsDdmInformationTable add description ,
                    table hwOpticsPowerThresholdTable add description."

      REVISION     "201004010000Z"
      DESCRIPTION  "V1.11, Modify the syntax error."

      REVISION     "201001120000Z"
      DESCRIPTION  "V1.10, add the definition of the trap node."

      REVISION     "200909290000Z"
      DESCRIPTION  "V1.09, leaf hwOpticsMDIdentifier add enum,
                   leaf hwOpticsMDEncoding add enum,
                   leaf hwOpticsMDSFF8472Compliance add enum ,
                   leaf hwOpticsMDGEComplianceCodes add enum."

      REVISION     "200703230000Z"
      DESCRIPTION  "V1.02, add hwOpticsDdmInformationTable."

      REVISION     "200611240000Z"
      DESCRIPTION  "V1.01, add hw10GEOpticsModuleInformationTable."

      REVISION     "200611240000Z"
      DESCRIPTION  "V1.00, Initial version."

      ::= { huaweiMgmt 14 }

      PortList ::= TEXTUAL-CONVENTION
      STATUS      current
      DESCRIPTION
        "Each octet within this value specifies a set of eight
         ports, with the first octet specifying ports 1 through
         8, the second octet specifying ports 9 through 16, etc.
         Within each octet, the most significant bit represents
         the lowest numbered port, and the least significant bit
         represents the highest numbered port.  Thus, each port
         of the bridge is represented by a single bit within the
         value of this object.  If that bit has a value of '1'
         then that port is included in the set of ports; the port
         is not included if its bit has a value of '0'.
         "
      SYNTAX      OCTET STRING

    hwOpticsModuleInformation OBJECT IDENTIFIER ::= { hwEthernetPort 6 }

    hwOpticsModuleInformationTable OBJECT-TYPE
      SYNTAX SEQUENCE OF HwOpticsModuleInformationEntry
      MAX-ACCESS not-accessible
      STATUS current
      DESCRIPTION
        "Indicates the optical module table of an Ethernet port. It is used for querying
         the information about the optical module of an Ethernet port.
         The index of this table is ifIndex.
         "
      ::= { hwOpticsModuleInformation 1 }

    hwOpticsModuleInformationEntry OBJECT-TYPE
      SYNTAX HwOpticsModuleInformationEntry
      MAX-ACCESS not-accessible
      STATUS current
      DESCRIPTION
        "Indicates the optical module table of an Ethernet port. It is used for querying
         the information about the optical module of an Ethernet port.
         The index of this entry is ifIndex.
         "
      INDEX { ifIndex }
      ::= { hwOpticsModuleInformationTable 1 }

    HwOpticsModuleInformationEntry ::=
      SEQUENCE {
        hwOpticsMDIdentifier
          INTEGER,
        hwOpticsMDExtID
          INTEGER,
        hwOpticsMDConnector
          INTEGER,
        hwOpticsMDEncoding
          INTEGER,
        hwOpticsMDBrNominal
          Integer32,
        hwOpticsMDLength9Micronkm
          Integer32,
        hwOpticsMDLength9Micron
          Integer32,
        hwOpticsMDLength50Micron
          Integer32,
        hwOpticsMDLength62Micron5
          Integer32,
        hwOpticsMDLengthCopper
          Integer32,
        hwOpticsMDVendorName
          OCTET STRING,
        hwOpticsMDVendorOUI
          Integer32,
        hwOpticsMDVendorPN
          OCTET STRING,
        hwOpticsMDVendorRev
          OCTET STRING,
        hwOpticsMDWaveLength
          Integer32,
        hwOpticsMDCcBase
          Integer32,
        hwOpticsMDOptions
          INTEGER,
        hwOpticsMDBrMax
          Integer32,
        hwOpticsMDBrMin
          Integer32,
        hwOpticsMDVendorSN
          OCTET STRING,
        hwOpticsMDDateCode
          OCTET STRING,
        hwOpticsMDDiagnosticMonitoringType
          INTEGER,
        hwOpticsMDEnhancedOptions
          INTEGER,
        hwOpticsMDSFF8472Compliance
          INTEGER,
        hwOpticsMDCcExt
          Integer32,
        hwOpticsMDVendorSpecific
          OCTET STRING,
        hwOpticsMDCLEICode
          OCTET STRING,
        hwOpticsMDInfoRemote
          INTEGER,
        hwOpticsMDSFPPulsCableTech
          INTEGER,
        hwOpticsMDSFPRateId
          INTEGER,
        hwOpticsMDLength50MicronOM3
          Integer32,
        hwOpticsDwdmClass
          INTEGER,
        hwOpticsDwdmPower
          INTEGER,
        hwOpticsDwdmMaxTemperature
          Integer32,
        hwOpticsDwdmMinTemperature
          Integer32,
        hwOpticsDwdmMaxSupplyCurrent
          Integer32,
        hwOpticsDwdmChannelSpacing
          INTEGER,
        hwOpticsDwdmNumberOfChannels
          Integer32,
        hwOpticsDwdmWaveLength
          Integer32,
        hwOpticsModuleUserEeprom
          OCTET STRING,
        hwOpticsMDSFF8636Compliance
          INTEGER
       }

    hwOpticsMDIdentifier OBJECT-TYPE
      SYNTAX INTEGER
        {
        unknown(1),
        gbic(2),
        solderedToMotherboard(3),
        sfp(4),
        pin300XBI(5),
        xenpak(6),
        xfp(7),
        xff(8),
        xfpe(9),
        xpak(10),
        x2(11),
        dwdmSfp(12),
        qSfp(13),
        qSfpPlus(14),
        qSfp28(18),
        invalid(255)
        }
      MAX-ACCESS read-only
      STATUS current
      DESCRIPTION
        "Indicate the identifier of optical module.
         Options:
         1. unknown(1)                 -unknown the identifier of optical module
         2. gbic(2)                    -the identifier of optical module is gbic
         3. solderedToMotherboard(3)   -the identifier of optical module is solderedToMotherboard
         4. sfp(4)                     -the identifier of optical module is sfp
         5. pin300XBI(5)               -the identifier of optical module is pin300XBI
         6. xenpak(6)                  -the identifier of optical module is xenpak
         7. xfp(7)                     -the identifier of optical module is xfp
         8. xff(8)                     -the identifier of optical module is xff
         9. xfpe(9)                    -the identifier of optical module is xfpe
         10. xpak(10)                  -the identifier of optical module is xpak
         11. x2(11)                    -the identifier of optical module is x2
         12. dwdmSfp(12)               -the identifier of optical module is DWDM-SFP
         13. qSfp(13)                  -the identifier of optical module is QSFP
         14. qSfpPlus(14)              -the identifier of optical module is QSFP+
         15. qSfp28(18)                -the identifier of optical module is QSFP28
         16. invalid(255)              -invalid value
        "
      ::= { hwOpticsModuleInformationEntry 1 }

    hwOpticsMDExtID OBJECT-TYPE
      SYNTAX INTEGER
        {
        notSpecifiedOrNotCompliant(1),
        moddef1(2),
        moddef2(3),
        moddef3(4),
        bySerialIDOnly(5),
        moddef5(6),
        moddef6(7),
        moddef7(8),
        powerClass1(9),
        powerClass2(10),
        powerClass3(11),
        powerClass4(12),
        powerClass5(13),
        powerClass6(14),
        powerClass7(15),
        invalid(255)
        }
      MAX-ACCESS read-only
      STATUS current
      DESCRIPTION
        "Indicate the extended type of optical module.
         Options:
         1. notSpecifiedOrNotCompliant(1)   -the extended type of optical module is notSpecifiedOrNotCompliant
         2. moddef1(2)                      -the extended type of optical module is moddef1
         3. moddef2(3)                      -the extended type of optical module is moddef2
         4. moddef3(4)                      -the extended type of optical module is moddef3
         5. bySerialIDOnly(5)               -the extended type of optical module is bySerialIDOnly
         6. moddef5(6)                      -the extended type of optical module is moddef5
         7. moddef6(7)                      -the extended type of optical module is moddef6
         8. moddef7(8)                      -the extended type of optical module is moddef7
         9. powerClass1(9)                  -the extended type of optical module is Power Class 1 (1.5 W max.)
         10. powerClass2(10)                -the extended type of optical module is Power Class 2 (2.0 W max.)
         11. powerClass3(11)                -the extended type of optical module is Power Class 3 (2.5 W max.)
         12. powerClass4(12)                -the extended type of optical module is Power Class 4 (3.5 W max.)
         13. powerClass5(13)                -the extended type of optical module is Power Class 5 (4.0 W max.)
         14. powerClass6(14)                -the extended type of optical module is Power Class 6 (4.5 W max.)
         15. powerClass7(15)                -the extended type of optical module is Power Class 7 (5.0 W max.)
         16. invalid(255)                   -invalid value
        "
      ::= { hwOpticsModuleInformationEntry 2 }

    hwOpticsMDConnector OBJECT-TYPE
      SYNTAX INTEGER
        {
        unknown(1),
        sc(2),
        copperConnector1(3),
        copperConnector2(4),
        bnctnc(5),
        coaxialHeaders(6),
        fiberJack(7),
        lc(8),
        mtrj(9),
        mu(10),
        sg(11),
        opticalPigtail(12),
        hssdcii(13),
        copperPigtail(14),
        vendorSpecific(15),
        mpoParallelOptic(16),
        rj45(17),
        invalid(255)
        }
      MAX-ACCESS read-only
      STATUS current
      DESCRIPTION
        "Indicate the type of optical module connector.
         Options:
         1. unknown(1)            -unknown the type of optical module connector
         2. sc(2)                 -the type of optical module connector is sc
         3. copperConnector1(3)   -the type of optical module connector is copperConnector1
         4. copperConnector2(4)   -the type of optical module connector is copperConnector2
         5. bnctnc(5)             -the type of optical module connector is bnctnc
         6. coaxialHeaders(6)     -the type of optical module connector is coaxialHeaders
         7. fiberJack(7)          -the type of optical module connector is fiberJack
         8. lc(8)                 -the type of optical module connector is lc
         9. mtrj(9)               -the type of optical module connector is mtrj
         10. mu(10)               -the type of optical module connector is mu
         11. sg(11)               -the type of optical module connector is sg
         12. opticalPigtail(12)   -the type of optical module connector is opticalPigtail
         13. hssdcii(13)          -the type of optical module connector is hssdcii
         14. copperPigtail(14)    -the type of optical module connector is copperPigtail
         15. vendorSpecific(15)   -the type of optical module connector is vendorSpecific
         16. mpoParallelOptic     -the type of optical module connector is mpo parallel optic
         17. rj45                 -the type of optical module connector is RJ45
         18. mpo2ParallelOptic    -the type of optical module connector is mpo2 parallel optic
         19. invalid(255)         -invalid value
        "
      ::= { hwOpticsModuleInformationEntry 3 }

    hwOpticsMDEncoding OBJECT-TYPE
      SYNTAX INTEGER
        {
        unspecified(1),
        encodingMethod8B10B(2),
        encodingMethod4B5B(3),
        nrz(4),
        manchester(5),
        sONETScrambled(6),
        encodingMethod64B66B(7),
        invalid(255)
        }
      MAX-ACCESS read-only
      STATUS current
      DESCRIPTION
        "Indicate the encoding mechanism.
         Options:
         1. unspecified(1)            -the encoding mechanism is unspecified
         2. encodingMethod8B10B(2)    -the encoding mechanism is encodingMethod8B10B
         3. encodingMethod4B5B(3)     -the encoding mechanism is encodingMethod4B5B
         4. nrz(4)                    -the encoding mechanism is nrz
         5. manchester(5)             -the encoding mechanism is manchester
         6. sONETScrambled(6)         -the encoding mechanism is sONETScrambled
         7. encodingMethod64B66B(7)   -the encoding mechanism is encodingMethod64B66B
         8. invalid(255)			  -invalid value
         "
      ::= { hwOpticsModuleInformationEntry 4 }

    hwOpticsMDBrNominal OBJECT-TYPE
      SYNTAX Integer32
      MAX-ACCESS read-only
      STATUS current
      DESCRIPTION
        "Nominal bit rate.
         Unit: 100 MBits/sec
         "
      ::= { hwOpticsModuleInformationEntry 5 }

    hwOpticsMDLength9Micronkm OBJECT-TYPE
      SYNTAX Integer32
      MAX-ACCESS read-only
      STATUS current
      DESCRIPTION
        "Indicate the link length that is supported by the transceiver while operating in
         compliance with the applicable standards using 9 micron Single-mode Fiber.
         The maximum value is 255, which means that the transceiver supports a link length
         greater than 254 km.
         Unit: km
         "
      ::= { hwOpticsModuleInformationEntry 6 }

    hwOpticsMDLength9Micron OBJECT-TYPE
      SYNTAX Integer32
      MAX-ACCESS read-only
      STATUS current
      DESCRIPTION
        "Indicate the link length that is supported by the transceiver while operating in
         compliance with the applicable standards using 9 micron Single-mode Fiber.
         The maximum value is 255, which means that the transceiver supports a link length
         greater than 25.4 km.
         Unit: 100m
         "
      ::= { hwOpticsModuleInformationEntry 7 }

    hwOpticsMDLength50Micron OBJECT-TYPE
      SYNTAX Integer32
      MAX-ACCESS read-only
      STATUS current
      DESCRIPTION
        "Indicate link length that is supported by the transceiver while operating in
         compliance with applicable standards using 50 micron multi-mode OM2 [500MHz*km]
         fiber.
         The maximum value is 255, which means that the transceiver supports a link
         length greater than 2.54 km.
         Unit: 10m
         "
      ::= { hwOpticsModuleInformationEntry 8 }

    hwOpticsMDLength62Micron5 OBJECT-TYPE
      SYNTAX Integer32
      MAX-ACCESS read-only
      STATUS current
      DESCRIPTION
        "Indicate link length that is supported by the transceiver while operating in
         compliance with applicable standards using 62.5 micron multi-mode OM1 [200 MHz*km]
         fiber.
         The maximum value is 255, which means that the transceiver supports a link length
         greater than 2.54 km.
         Unit: 10m"
      ::= { hwOpticsModuleInformationEntry 9 }

    hwOpticsMDLengthCopper OBJECT-TYPE
      SYNTAX Integer32
      MAX-ACCESS read-only
      STATUS current
      DESCRIPTION
        "Indicate Link length supported for copper.
         Unit: 1m"
      ::= { hwOpticsModuleInformationEntry 10 }

    hwOpticsMDVendorName OBJECT-TYPE
      SYNTAX OCTET STRING (SIZE (0..17))
      MAX-ACCESS read-only
      STATUS current
      DESCRIPTION
        "Indicate the vendor name of a optical module.
        "
      ::= { hwOpticsModuleInformationEntry 11 }

    hwOpticsMDVendorOUI OBJECT-TYPE
      SYNTAX Integer32
      MAX-ACCESS read-only
      STATUS current
      DESCRIPTION
        "Indicate the vendor IEEE company ID of a optical module."
      ::= { hwOpticsModuleInformationEntry 12 }

    hwOpticsMDVendorPN OBJECT-TYPE
      SYNTAX OCTET STRING (SIZE (0..17))
      MAX-ACCESS read-only
      STATUS current
      DESCRIPTION
        "Indicate the part number of a optical module provided by vendor.
         "
      ::= { hwOpticsModuleInformationEntry 13 }

    hwOpticsMDVendorRev OBJECT-TYPE
      SYNTAX OCTET STRING (SIZE (0..5))
      MAX-ACCESS read-only
      STATUS current
      DESCRIPTION
        "Indicate the revision level for part number provided by vendor.
         "
      ::= { hwOpticsModuleInformationEntry 14 }

    hwOpticsMDWaveLength OBJECT-TYPE
      SYNTAX Integer32
      MAX-ACCESS read-only
      STATUS current
      DESCRIPTION
        "The laser wavelength.
        Unit: 1nm
        "
      ::= { hwOpticsModuleInformationEntry 15 }

    hwOpticsMDCcBase OBJECT-TYPE
      SYNTAX Integer32
      MAX-ACCESS read-only
      STATUS current
      DESCRIPTION
        "The check code for base ID fields(one byte)."
      ::= { hwOpticsModuleInformationEntry 16 }

    hwOpticsMDOptions OBJECT-TYPE
      SYNTAX INTEGER
        {
         rateSelect(1),
         txDisableAndTheSerialOutputDisabled(2),
         txFault(3),
         signalLossAndInvertedFromStandard(4),
         signalLossAndAsDefined(5),
         tunabletransmittertechnology(6),
         rdt(7),
         invalid(65535)
        }
      MAX-ACCESS read-only
      STATUS current
      DESCRIPTION
        "Options:
         1. rateSelect(1)                          -RATE_SELECT is implemented
         2. txDisableAndTheSerialOutputDisabled(2) -TX_DISABLE is implemented and disables the serial output.
         3. txFault(3)                             -TX_FAULT signal implemented.
         4. signalLossAndInvertedFromStandard(4)   -Loss of Signal implemented, signal inverted from standard definition in SFP MSA.
         5. signalLossAndAsDefined(5)              -Loss of Signal implemented, signal as defined in SFP MSA
         6. tunabletransmittertechnology(6),       -Tunable transmitter technology.A value of 1 indicates that the transmitter wavelength/frequency is tunable in accordance with SFF-8690.
         7. rdt(7),                                -Receiver decision threshold implemented.A value of 1 indicates that RDT is implemented.
         8. invalid(65535)						   -invalid value
        "
      ::= { hwOpticsModuleInformationEntry 17 }

    hwOpticsMDBrMax OBJECT-TYPE
      SYNTAX Integer32
      MAX-ACCESS read-only
      STATUS current
      DESCRIPTION
        "The upper bit rate margin."
      ::= { hwOpticsModuleInformationEntry 18 }

    hwOpticsMDBrMin OBJECT-TYPE
      SYNTAX Integer32
      MAX-ACCESS read-only
      STATUS current
      DESCRIPTION
        "The lower bit rate margin."
      ::= { hwOpticsModuleInformationEntry 19 }

    hwOpticsMDVendorSN OBJECT-TYPE
      SYNTAX OCTET STRING (SIZE (0..17))
      MAX-ACCESS read-only
      STATUS current
      DESCRIPTION
        "The serial number of a optical module provided by vendor.
         "
      ::= { hwOpticsModuleInformationEntry 20 }

    hwOpticsMDDateCode OBJECT-TYPE
      SYNTAX OCTET STRING (SIZE (0..9))
      MAX-ACCESS read-only
      STATUS current
      DESCRIPTION
        "The date code of a optical module."
      ::= { hwOpticsModuleInformationEntry 21 }

    hwOpticsMDDiagnosticMonitoringType OBJECT-TYPE
      SYNTAX INTEGER
        {
         internallyCalibrated(1),
         externallyCalibrated(2),
         invalid(-1)
        }
      MAX-ACCESS read-only
      STATUS current
      DESCRIPTION
        "Indicate the diagnostic monitoring type.
         Options:
         1. internallyCalibrated(1)   -the diagnostic monitoring type is internallyCalibrated
         2. externallyCalibrated(2)   -the diagnostic monitoring type is externallyCalibrated
         3. invalid(-1)               -invalid value
         "
      ::= { hwOpticsModuleInformationEntry 22 }

    hwOpticsMDEnhancedOptions OBJECT-TYPE
      SYNTAX INTEGER
        {
         forAllMonitoredQuantities(1),
         txDisable(2),
         txFault(3),
         rxLOS(4),
         rateSelect(5),
         invalid(-1)
        }
      MAX-ACCESS read-only
      STATUS current
      DESCRIPTION
        "Indicate enhanced Options.
         Options:
         1. forAllMonitoredQuantities(1) -optional Alarm/warning flags implemented for all monitored quantities
         2. txDisable(2)                 -optional Soft TX_DISABLE control and monitoring implemented
         3. txFault(3)                   -optional Soft TX_FAULT monitoring implemented
         4. rxLOS(4)                     -optional Soft RX_LOS monitoring implemented
         5. rateSelect(5)                -optional Soft RATE_SELECT control and monitoring implemented
         6. invalid(-1)                  -invalid value
        "
      ::= { hwOpticsModuleInformationEntry 23 }

    hwOpticsMDSFF8472Compliance OBJECT-TYPE
      SYNTAX INTEGER
        {
         undefined(1),
         includesSFF8472V93(2),
         includesSFF8472V95(3),
         includesSFF8472V102(4),
         includesSFF8472V104(5),
         includesSFF8472V110(6),
         tbd(7),
         includesSFF8472V113(8),
         includesSFF8472V114(9),
         includesSFF8472V120(10),
         invalid(255)
        }
      MAX-ACCESS read-only
      STATUS current
      DESCRIPTION
        "Indicate the SFF-8472 standard.
         Options:
         1. undefined(1)             -not included or undefined.
         2. includesSFF8472V93(2)    -includes functionality described in SFF-8472 Rev 9.3.
         3. includesSFF8472V95(3)    -includes functionality described in SFF-8472 Rev 9.5.
         4. includesSFF8472V102(4)   -includes functionality described in SFF-8472 Rev 10.2.
         5. includesSFF8472V104(5)   -includes functionality described in SFF-8472 Rev 10.4.
         6. includesSFF8472V110(6)   -includes functionality described in SFF-8472 Rev 11.0.
         7. tbd(7)                   -to be determined.
         8. includesSFF8472V113(8)   -includes functionality described in SFF-8472 Rev 11.3.
         9. includesSFF8472V114(9)   -includes functionality described in SFF-8472 Rev 11.4.
         10. includesSFF8472V120(10) -includes functionality described in SFF-8472 Rev 12.0.
         11. invalid(255)            -invalid value.
       "
      ::= { hwOpticsModuleInformationEntry 24 }

    hwOpticsMDCcExt OBJECT-TYPE
      SYNTAX Integer32
      MAX-ACCESS read-only
      STATUS current
      DESCRIPTION
        "Check code for the Extended ID Fields."
      ::= { hwOpticsModuleInformationEntry 25 }

    hwOpticsMDVendorSpecific OBJECT-TYPE
      SYNTAX OCTET STRING (SIZE (0..96))
      MAX-ACCESS read-only
      STATUS current
      DESCRIPTION
        "Vendor of Optical module specific information."
      ::= { hwOpticsModuleInformationEntry 26 }

    hwOpticsMDCLEICode OBJECT-TYPE
      SYNTAX OCTET STRING (SIZE (0..10))
      MAX-ACCESS read-only
      STATUS current
      DESCRIPTION
        "CLEI code supported by eSFP. Length is 10 bytes."
      ::= { hwOpticsModuleInformationEntry 27 }

    hwOpticsMDInfoRemote OBJECT-TYPE
      SYNTAX INTEGER
        {
        remote(1),
        invalid(-1)
        }
      MAX-ACCESS read-only
      STATUS current
      DESCRIPTION
        "Indicates the operation is performed on a remote optical module.
         Options:
         1. remote(1)        -the operation is performed on a remote optical module
         2. invalid(-1)      -invalid value
         "
      ::= { hwOpticsModuleInformationEntry 28 }

    hwOpticsMDSFPPulsCableTech OBJECT-TYPE
      SYNTAX INTEGER
        {
        passiveCable(1),
        activeCable(2),
        invalid(-1)
        }
      MAX-ACCESS read-only
      STATUS current
      DESCRIPTION
        "Indicates the cable specification compliance.
         Options:
         1. passiveCable(1)        -Passive Cable
         2. activeCable(2)         -Active Cable
         2. invalid(-1)            -invalid value
         "
      ::= { hwOpticsModuleInformationEntry 29 }

    hwOpticsMDSFPRateId OBJECT-TYPE
      SYNTAX INTEGER
        {
        sff8079(1),
        sff8431RX(2),
        sff8431TX(3),
        sff8431RXTX(4),
        pcpi5RX(5),
        fcpi5RXTX(6),
        fcpi6RXTX(7),
        rate10G8GRXTX(8),
        invalid(-1),
        invalid1(255)
        }
      MAX-ACCESS read-only
      STATUS current
      DESCRIPTION
        "Indicates the cable specification compliance.
         Options:
         1. sff8079(1)        -Defined for SFF-8079 (4/2/1G Rate_Select & AS0/AS1)
         2. sff8431RX(2)      -Defined for SFF-8431 (8/4/2G Rx Rate_Select only)
         3. sff8431TX(3)      -Defined for SFF-8431 (8/4/2G Tx Rate_Select only)
         4. sff8431RXTX(4)    -Defined for SFF-8431 (8/4/2G Independent Rx & Tx Rate_select)
         5. fcpi5RX(5)        -Defined for FC-PI-5 (16/8/4G Rx Rate_select only) High=16G only, Low=8G/4G
         6. fcpi5RXTX(6)      -Defined for FC-PI-5 (16/8/4G Independent Rx, Tx Rate_select) High=16G only, Low=8G/4G
         7. fcpi6RXTX(7)      -Defined for FC-PI-6 (32/16/8G Independent Rx, Tx Rate_Select) High=32G only, Low = 16G/8G
         8. rate10G8GRXTX(8)  -Defined for 10/8G Rx and Tx Rate_Select controlling the operation or locking modes of the internal signal conditioner, retimer or CDR,
                               High Bit Rate (10G) =9.95-11.3 Gb/s; Low Bit Rate (8G) = 8.5 Gb/s.
         9. invalid(-1)       -invalid value
         10. invalid1(255)	  -invalid value
         "
      ::= { hwOpticsModuleInformationEntry 30 }

    hwOpticsMDLength50MicronOM3 OBJECT-TYPE
      SYNTAX Integer32
      MAX-ACCESS read-only
      STATUS current
      DESCRIPTION
        "Indicate link length that is supported by the transceiver while operating in
         compliance with applicable standards using 50 micron multi-mode OM2 [2000MHz*km]
         fiber.
         The maximum value is 255, which means that the transceiver supports a link
         length greater than 2.54 km. A value of zero means that the transceiver does not support 50
         micron multimode fiber or that the length information must be determined from the transceiver
         technology.
         Unit: 10m
         "
      ::= { hwOpticsModuleInformationEntry 31 }

    hwOpticsDwdmClass OBJECT-TYPE
      SYNTAX INTEGER
        {
        noWdm(1),
        cwdm(2),
        dwdm(3),
        invalid(-1)
        }
      MAX-ACCESS read-only
      STATUS current
      DESCRIPTION
        "Extended identifier: WDM class.
         Options:
         1. noWdm(1)          -no WDM
         2. cwdm(2)           -CWDM
         3. dwdm(3)           -DWDM
         4. invalid(-1)       -invalid value
         "
      ::= { hwOpticsModuleInformationEntry 32 }

    hwOpticsDwdmPower OBJECT-TYPE
      SYNTAX INTEGER
        {
          dwdmPowerLevel1(1),
          dwdmPowerLevel2(2),
          dwdmPowerLevel3(3),
          invalid(-1)
        }
      MAX-ACCESS read-only
      STATUS current
      DESCRIPTION
        "Extended identifier: Power level.
         Options:
         1. dwdmPowerLevel1(1)  -The power is lower than 1W.
         2. dwdmPowerLevel2(2)  -The power is between 1W and 1.5W.
         3. dwdmPowerLevel3(3)  -The power is higher than 1.5W.
         4. invalid(-1)         -invalid value
         "
      ::= { hwOpticsModuleInformationEntry 33 }

     hwOpticsDwdmMaxTemperature OBJECT-TYPE
      SYNTAX Integer32
      UNITS "0.000001C"
      MAX-ACCESS read-only
      STATUS current
      DESCRIPTION
        "Max temperature.
         Invalid value: 2147483647, returned if the optical module is unavailable or not supported.
         Unit: 0.000001C
         "
      ::= { hwOpticsModuleInformationEntry 34 }

     hwOpticsDwdmMinTemperature OBJECT-TYPE
      SYNTAX Integer32
      UNITS "0.000001C"
      MAX-ACCESS read-only
      STATUS current
      DESCRIPTION
        "Min temperature.
         Invalid value: 2147483647, returned if the optical module is unavailable or not supported.
         Unit: 0.000001C
         "
      ::= { hwOpticsModuleInformationEntry 35 }

     hwOpticsDwdmMaxSupplyCurrent OBJECT-TYPE
      SYNTAX Integer32
      UNITS "0.000001A"
      MAX-ACCESS read-only
      STATUS current
      DESCRIPTION
        "Max supply current.
         Invalid value: 2147483647, returned if the optical module is unavailable or not supported.
         Unit: 0.000001A
         "
      ::= { hwOpticsModuleInformationEntry 36 }

     hwOpticsDwdmChannelSpacing OBJECT-TYPE
      SYNTAX INTEGER
        {
          channelSpacing200G(1),
          channelSpacing100G(2),
          channelSpacing50G(3),
          invalid(-1)
        }
      MAX-ACCESS read-only
      STATUS current
      DESCRIPTION
        "Fibre channel spacing.
         Options:
         1. channelSpacing200G(1)           -The fibre channel spacing is 200GHz.
         2. channelSpacing100G(2)           -The fibre channel spacing is 100GHZ.
         3. channelSpacing50G(3)            -The fibre channel spacing is 50GHZ.
         4. invalid(-1)                     -invalid value
         "
      ::= { hwOpticsModuleInformationEntry 37 }

     hwOpticsDwdmNumberOfChannels OBJECT-TYPE
      SYNTAX Integer32
      MAX-ACCESS read-only
      STATUS current
      DESCRIPTION
        "Number of channels.
         Invalid value: -1, returned if the optical module is unavailable or not supported.
         "
      ::= { hwOpticsModuleInformationEntry 38 }

     hwOpticsDwdmWaveLength OBJECT-TYPE
      SYNTAX Integer32
      UNITS "0.01nm"
      MAX-ACCESS read-only
      STATUS current
      DESCRIPTION
        "Laser wavelength.
         Invalid value: -1, returned if the optical module is unavailable or not supported.
         Unit: 0.01nm
         "
      ::= { hwOpticsModuleInformationEntry 39 }

     hwOpticsModuleUserEeprom OBJECT-TYPE
      SYNTAX OCTET STRING (SIZE (0..384))
      MAX-ACCESS read-only
      STATUS current
      DESCRIPTION
        "Optics module user EEPROM information."
      ::= { hwOpticsModuleInformationEntry 40 }

    hwOpticsMDSFF8636Compliance OBJECT-TYPE
      SYNTAX INTEGER
        {
         undefined(1),
         includesSFF8436V48OrEarlier(2),
         includesSFF8436V48OrEarlierEX(3),
         includesSFF8636V13OrEarlier(4),
         includesSFF8636V14(5),
         includesSFF8636V15(6),
         includesSFF8636V20(7),
         includesSFF8636V25To27(8),
         includesSFF8636V28OrLater(9),
         invalid(255)
        }
      MAX-ACCESS read-only
      STATUS current
      DESCRIPTION
        "Indicate the SFF-8636 standard.
         Options:
         1. undefined(1)                        -not included or undefined.
         2. includesSFF8436V48OrEarlier(2)      -includes functionality described in SFF-8436 Rev 4.8 or earlier.
         3. includesSFF8436V48OrEarlierEX(3)    -includes functionality described in SFF-8436 Rev 4.8 or earlier with exception.
         4. includesSFF8636V13OrEarlier(4)      -includes functionality described in SFF-8636 Rev 1.3 or earlier.
         5. includesSFF8636V14(5)               -includes functionality described in SFF-8636 Rev 1.4.
         6. includesSFF8636V15(6)               -includes functionality described in SFF-8636 Rev 1.5.
         7. includesSFF8636V20(7)               -includes functionality described in SFF-8636 Rev 2.0.
         8. includesSFF8636V25To27(8)           -includes functionality described in SFF-8636 Rev 2.5, 2.6 and 2.7.
         9. includesSFF8636V28OrLater(9)        -includes functionality described in SFF-8636 Rev 2.8 or later.
         10. invalid(255)                       -invalid value.
       "
      ::= { hwOpticsModuleInformationEntry 41 }

    hwOpticsModuleTransceiverTable OBJECT-TYPE
      SYNTAX SEQUENCE OF HwOpticsModuleTransceiverEntry
      MAX-ACCESS not-accessible
      STATUS current
      DESCRIPTION
        "This table used for querying the information about the optical transceiver of an Ethernet port.
         The index of this table is ifindex.
         "
      ::= { hwOpticsModuleInformation 2 }

    hwOpticsModuleTransceiverEntry OBJECT-TYPE
      SYNTAX HwOpticsModuleTransceiverEntry
      MAX-ACCESS not-accessible
      STATUS current
      DESCRIPTION
        "This table used for querying the information about the optical transceiver of an Ethernet port.
         The index of this entry is ifindex.
         "
      INDEX { ifIndex }
      ::= { hwOpticsModuleTransceiverTable 1 }

    HwOpticsModuleTransceiverEntry ::=
      SEQUENCE {
        hwOpticsMDInfinibandComplianceCodes
          INTEGER,
        hwOpticsMDSONETcomplianceCodes
          INTEGER,
        hwOpticsMDGEComplianceCodes
          INTEGER,
        hwOpticsMDLinkLength
          INTEGER,
        hwOpticsMDTransmitterTechnology
          INTEGER,
        hwOpticsMDTransmissionMedia
          INTEGER,
        hwOpticsMDSpeed
          INTEGER,
        hwOpticsMDTransceiverRemote
          INTEGER,
        hwOpticsMDHuaweiPartNumber
          OCTET STRING
       }

    hwOpticsMDInfinibandComplianceCodes OBJECT-TYPE
      SYNTAX INTEGER
        {
        sx(1),
        lx(2),
        copperActive(3),
        copperPassive(4),
        invalid(-1)
        }
      MAX-ACCESS read-only
      STATUS current
      DESCRIPTION
        "Infiniband transceiver type.
         Options:
         1. sx(1)            -infiniband transceiver type is sx
         2. lx(2)            -infiniband transceiver type is lx
         3. copperActive(3)  -infiniband transceiver type is copperActive
         4. copperPassive(4) -infiniband transceiver type is copperPassive
         5. invalid(-1)      -invalid value
        "
      ::= { hwOpticsModuleTransceiverEntry 1 }

    hwOpticsMDSONETcomplianceCodes OBJECT-TYPE
      SYNTAX INTEGER
        {
        oC48LongReach(1),
        oC48IntermediateReach(2),
        oC48ShortReach(3),
        oC12SingleModeLongReach(4),
        oC12SingleModeIntermediateReach(5),
        oC12MultiModeShortReach(6),
        oC3SingleModeLongReach(7),
        oC3SingleModeIntermediateReach(8),
        oC3MultiModeShortReach(9),
        invalid(-1)
        }
      MAX-ACCESS read-only
      STATUS current
      DESCRIPTION
        "SONET transceiver type.
         Options:
         1. oC48LongReach(1)                   -SONET transceiver type is oC48LongReach
         2. oC48IntermediateReach(2)           -SONET transceiver type is oC48IntermediateReach
         3. oC48ShortReach(3)                  -SONET transceiver type is oC48ShortReach
         4. oC12SingleModeLongReach(4)         -SONET transceiver type is oC12SingleModeLongReach
         5. oC12SingleModeIntermediateReach(5) -SONET transceiver type is oC12SingleModeIntermediateReach
         6. oC12MultiModeShortReach(6)         -SONET transceiver type is oC12MultiModeShortReach
         7. oC3SingleModeLongReach(7)          -SONET transceiver type is oC3SingleModeLongReach
         8. oC3SingleModeIntermediateReach(8)  -SONET transceiver type is oC3SingleModeIntermediateReach
         9. oC3MultiModeShortReach(9)          -SONET transceiver type is oC3MultiModeShortReach
         10. invalid(-1)                       -invalid value
        "
      ::= { hwOpticsModuleTransceiverEntry 2 }

    hwOpticsMDGEComplianceCodes OBJECT-TYPE
      SYNTAX INTEGER
        {
        en1000BASET(1),
        en1000BASECX(2),
        en1000BASELX(3),
        en1000BASESX(4),
        enMULTILX(5),
        en100BASELX(6),
        en100BASEFX(7),
        en1000BASEBX(8),
        en1000BASEPX(9),
        en10GBASELRM(10),
        en10GBASELR(11),
        en10GBASESR(12),
        en100BASEBX(13),
        en10GBASEER(14),
        en1000BASEZX(15),
        en100GBASESR4(16),
        en100GBASELR4(17),
        en100GBASEER4(18),
        en100GBASESR10(19),
        invalid(-1),
        invalid1(255)
        }
      MAX-ACCESS read-only
      STATUS current
      DESCRIPTION
        "Ethernet transceiver type.
         Options:
         1. en1000BASET(1)              -Ethernet transceiver type is 1000BASE-T
         2. en1000BASECX(2)             -Ethernet transceiver type is 1000BASE-CX
         3. en1000BASELX(3)             -Ethernet transceiver type is 1000BASE-LX
         4. en1000BASESX(4)             -Ethernet transceiver type is 1000BASE-SX
         5. enMULTILX(5)                -Ethernet transceiver type is 100BASE-LX&1000BASE-LX
         6. en100BASELX(6)              -Ethernet transceiver type is 100BASE-LX
         7. en100BASEFX(7)              -Ethernet transceiver type is 100BASE-FX
         8. en1000BASEBX(8)             -Ethernet transceiver type is 1000BASE-BX
         9. en1000BASEPX(9)             -Ethernet transceiver type is 1000BASE-PX
         10. en10GBASELRM(10)           -Ethernet transceiver type is 10GBASE-LRM
         11. en10GBASELR(11)            -Ethernet transceiver type is 10GBASE-LR
         12. en10GBASESR(12)            -Ethernet transceiver type is 10GBASE-SR
         13. en100BASEBX(13)            -Ethernet transceiver type is 100BASE-BX
         14. en10GBASEER(14)            -Ethernet transceiver type is 10G BASE-ER
         15. en1000BASEZX(15)           -Ethernet transceiver type is 1000BASE-ZX
         16. en100GBASESR4(16)          -Ethernet transceiver type is 100GBASE-SR4
         17. en100GBASELR4(17)          -Ethernet transceiver type is 100GBASE-LR4
         18. en100GBASEER4(18)          -Ethernet transceiver type is 100GBASE-ER4
         19. en100GBASESR10(19)         -Ethernet transceiver type is 100GBASE-SR10
         20. invalid(-1)                -invalid value
         21. invalid1(255)               -invalid value
         "
      ::= { hwOpticsModuleTransceiverEntry 3 }

    hwOpticsMDLinkLength OBJECT-TYPE
      SYNTAX INTEGER
        {
        veryLongDistance(1),
        shortDistance(2),
        intermediateDistance(3),
        longDistance(4),
        mediumDistance(5),
        invalid(-1)
        }
      MAX-ACCESS read-only
      STATUS current
      DESCRIPTION
        "Fibre Channel link length.
         Options:
         1. veryLongDistance(1)      -fibre channel link length is veryLongDistance
         2. shortDistance(2)         -fibre channel link length is shortDistance
         3. intermediateDistance(3)  -fibre channel link length is intermediateDistance
         4. longDistance(4)          -fibre channel link length is longDistance
         5. mediumDistance           -fibre channel link length is MediumDistance
         6. invalid(-1)              -invalid value
         "
      ::= { hwOpticsModuleTransceiverEntry 4 }

    hwOpticsMDTransmitterTechnology OBJECT-TYPE
      SYNTAX INTEGER
        {
        longwaveLaser(1),
        electricalInterenclosure(2),
        shortwaveLaser(3),
        invalid(-1)
        }
      MAX-ACCESS read-only
      STATUS current
      DESCRIPTION
        "Fibre Channel transmitter technology.
         Options:
         1. longwaveLaser(1)              -fibre channel transmitter technology is longwaveLaser
         2. electricalInterenclosure(2)   -fibre channel transmitter technology is electricalInterenclosure
         3. shortwaveLaser(3)             -fibre channel transmitter technology is shortwaveLaser
         4. invalid(-1)                   -invalid value
         "
      ::= { hwOpticsModuleTransceiverEntry 5 }

    hwOpticsMDTransmissionMedia OBJECT-TYPE
      SYNTAX INTEGER
        {
        twinAxialPair(1),
        shieldedTwistedPair(2),
        miniatureCoax(3),
        videoCoax(4),
        multiMode62m5(5),
        multiMode50m(6),
        singleMode(7),
        multiMode50mOM3(8),
        invalid(-1)
        }
      MAX-ACCESS read-only
      STATUS current
      DESCRIPTION
        "Fibre Channel transmission media.
         Options:
         1. twinAxialPair(1)         -fibre channel transmission media is twinAxialPair
         2. shieldedTwistedPair(2)   -fibre channel transmission media is shieldedTwistedPair
         3. miniatureCoax(3)         -fibre channel transmission media is miniatureCoax
         4. videoCoax(4)             -fibre channel transmission media is videoCoax
         5. multiMode62m5(5)         -fibre channel transmission media is multiMode62m5
         6. multiMode50m(6)          -fibre channel transmission media is multiMode50m
         7. singleMode(7)            -fibre channel transmission media is singleMode
         8. multiMode50mOM3(8)       -fibre channel transmission media is multiMode50mOM3
         9. invalid(-1)              -invalid value
        "
      ::= { hwOpticsModuleTransceiverEntry 6 }

    hwOpticsMDSpeed OBJECT-TYPE
      SYNTAX INTEGER
        {
        speed400MBytesPerSec(1),
        speed200MBytesPerSec(2),
        speed100MBytesPerSec(3),
        speed800MBytesPerSec(4),
        speed1200MBytesPerSec(5),
        speed1600MBytesPerSec(6),
        speed3200MBytesPerSec(7),
        speedExtended(8),
        invalid(-1)
        }
      MAX-ACCESS read-only
      STATUS current
      DESCRIPTION
        "Fibre Channel speed.
         Options:
         1. speed400MBytesPerSec(1)    -fibre channel speed is 400 MBits/s
         2. speed200MBytesPerSec(2)    -fibre channel speed is 200 MBits/s
         3. speed100MBytesPerSec(3)    -fibre channel speed is 100 MBits/s
         4. speed800MBytesPerSec(4)    -fibre channel speed is 800 MBits/s
         5. speed1200MBytesPerSec(5)   -fibre channel speed is 1200 MBits/s
         6. speed1600MBytesPerSec(6)   -fibre channel speed is 1600 MBits/s
         7. speed3200MBytesPerSec(7)   -fibre channel speed is 3200 MBits/s
         8. speedExtended(8)           -fibre channel speed is extended specification
         9. invalid(-1)                -invalid value
        "
      ::= { hwOpticsModuleTransceiverEntry 7 }

    hwOpticsMDTransceiverRemote OBJECT-TYPE
      SYNTAX INTEGER
        {
        remote(1),
        invalid(-1)
        }
      MAX-ACCESS read-only
      STATUS current
      DESCRIPTION
        "Indicates the operation is performed on a remote optical module.
         Options:
         1. remote(1)        -the operation is performed on a remote optical module
         2. invalid(-1)      -invalid value
        "
      ::= { hwOpticsModuleTransceiverEntry 8 }

    hwOpticsMDHuaweiPartNumber OBJECT-TYPE
      SYNTAX OCTET STRING (SIZE (0..17))
      MAX-ACCESS read-only
      STATUS current
      DESCRIPTION
        "Indicate the part number of a optical module provided by Huawei.
        "
      ::= { hwOpticsModuleTransceiverEntry 9 }

    hw10GEOpticsModuleInformationTable OBJECT-TYPE
      SYNTAX SEQUENCE OF Hw10GEOpticsModuleInformationEntry
      MAX-ACCESS not-accessible
      STATUS current
      DESCRIPTION
        "Indicates the 10GE optical module information table of an Ethernet port.
         It is used for querying the information about the 10GE optical module of
         an Ethernet port.
         The index of this table is ifindex.
         "
      ::= { hwOpticsModuleInformation 3 }

    hw10GEOpticsModuleInformationEntry OBJECT-TYPE
      SYNTAX Hw10GEOpticsModuleInformationEntry
      MAX-ACCESS not-accessible
      STATUS current
      DESCRIPTION
        "Indicates the 10GE optical module information table of an Ethernet port.
         It is used for querying the information about the 10GE optical module of
         an Ethernet port.
         The index of this entry is ifindex.
         "
      INDEX { ifIndex }
      ::= { hw10GEOpticsModuleInformationTable 1 }

    Hw10GEOpticsModuleInformationEntry ::=
      SEQUENCE
      {
        hw10GEOpticsMDIdentifier
              INTEGER,
        hw10GEOpticsMDExtCLEICode
              INTEGER,
        hw10GEOpticsMDExtTXRefClock
              INTEGER,
        hw10GEOpticsMDExtCDRFunc
              INTEGER,
        hw10GEOpticsMDExtPowerLevel
              INTEGER,
        hw10GEOpticsMDConnector
              INTEGER,
        hw10GEOpticsMDEthComplianceBaseEW
              INTEGER,
        hw10GEOpticsMDEthComplianceBaseLW
              INTEGER,
        hw10GEOpticsMDEthComplianceBaseSW
              INTEGER,
        hw10GEOpticsMDEthComplianceBaseLRM
              INTEGER,
        hw10GEOpticsMDEthComplianceBaseER
              INTEGER,
        hw10GEOpticsMDEthComplianceBaseLR
              INTEGER,
        hw10GEOpticsMDEthComplianceBaseSR
              INTEGER,
        hw10GEOpticsMDFibreCompliance
              INTEGER,
        hw10GEOpticsMDLowerSpeedLink
              INTEGER,
        hw10GEOpticsMDSONETSDHCodesI64point5
              INTEGER,
        hw10GEOpticsMDSONETSDHCodesI64point3
              INTEGER,
        hw10GEOpticsMDSONETSDHCodesI64point2
              INTEGER,
        hw10GEOpticsMDSONETSDHCodesI64point2r
              INTEGER,
        hw10GEOpticsMDSONETSDHCodesI64point1
              INTEGER,
        hw10GEOpticsMDSONETSDHCodesI64point1r
              INTEGER,
        hw10GEOpticsMDSONETSDHCodesS64point5b
              INTEGER,
        hw10GEOpticsMDSONETSDHCodesS64point5a
              INTEGER,
        hw10GEOpticsMDSONETSDHCodesS64point3b
              INTEGER,
        hw10GEOpticsMDSONETSDHCodesS64point3a
              INTEGER,
        hw10GEOpticsMDSONETSDHCodesS64point2b
              INTEGER,
        hw10GEOpticsMDSONETSDHCodesS64point2a
              INTEGER,
        hw10GEOpticsMDSONETSDHCodesS64point1
              INTEGER,
        hw10GEOpticsMDSONETSDHCodesG959P1L1
              INTEGER,
        hw10GEOpticsMDSONETSDHCodesL64point3
              INTEGER,
        hw10GEOpticsMDSONETSDHCodesL64point2c
              INTEGER,
        hw10GEOpticsMDSONETSDHCodesL64point2b
              INTEGER,
        hw10GEOpticsMDSONETSDHCodesL64point2a
              INTEGER,
        hw10GEOpticsMDSONETSDHCodesL64point1
              INTEGER,
        hw10GEOpticsMDSONETSDHCodesV64point3
              INTEGER,
        hw10GEOpticsMDSONETSDHCodesV64point2b
              INTEGER,
        hw10GEOpticsMDSONETSDHCodesV64point2a
              INTEGER,
        hw10GEOpticsMDEncodingRZ
              INTEGER,
        hw10GEOpticsMDEncodingNRZ
              INTEGER,
        hw10GEOpticsMDEncodingSONET
              INTEGER,
        hw10GEOpticsMDEncoding8B10B
              INTEGER,
        hw10GEOpticsMDEncoding64B
              INTEGER,
        hw10GEOpticsMDBrMin
              Integer32,
        hw10GEOpticsMDBrMax
              Integer32,
        hw10GEOpticsMDSupportLenSMF
              Integer32,
        hw10GEOpticsMDSupportLenE50um
              Integer32,
        hw10GEOpticsMDSupportLen50um
              Integer32,
        hw10GEOpticsMDSupportLen62p5um
              Integer32,
        hw10GEOpticsMDSupportLenCopper
              Integer32,
        hw10GEOpticsMDTransmitterSupport
              INTEGER,
        hw10GEOpticsMDDetector
              INTEGER,
        hw10GEOpticsMDCooledTransmitterDevice
              INTEGER,
        hw10GEOpticsMDWavelengthControl
              INTEGER,
        hw10GEOpticsMDTransmitterTechnologySupport
              INTEGER,
        hw10GEOpticsMDVendorName
              OCTET STRING,
        hw10GEOpticsMDSupportXFIMode
              INTEGER,
        hw10GEOpticsMDSupportLinesideMode
              INTEGER,
        hw10GEOpticsMDMaxBitRateSupportedByCDR
              INTEGER,
        hw10GEOpticsMDVendorOUI
              Integer32,
        hw10GEOpticsMDVendorPN
              OCTET STRING,
        hw10GEOpticsMDVendorRev
              OCTET STRING,
        hw10GEOpticsMDWavelength
              Integer32,
        hw10GEOpticsMDWaveTolerance
              Integer32,
        hw10GEOpticsMDMaxCaseTemperature
              Integer32,
        hw10GEOpticsMDMaxDissipation
              Integer32,
        hw10GEOpticsMDCcbase
              Integer32,
        hw10GEOpticsMDMaxDissipationPowerDownMode
              Integer32,
        hw10GEOpticsMDMaximum5P0VSupply
            Integer32,
        hw10GEOpticsMDMaximum3P3VSupply
              Integer32,
        hw10GEOpticsMDMaximum1P8VSupply
              Integer32,
        hw10GEOpticsMDMaximum5P2VSupply
              Integer32,
        hw10GEOpticsMDVendorSN
              OCTET STRING,
        hw10GEOpticsMDDateCode
              OCTET STRING,
        hw10GEOpticsMDDiagnoMonitorPowerMeasure
              INTEGER,
        hw10GEOpticsMDDiagnoMonitorTypeFECBER
              INTEGER,
        hw10GEOpticsMDEnhancedOptions
              INTEGER,
        hw10GEOpticsMDAuxInputOne
              INTEGER,
        hw10GEOpticsMDAuxInputTwo
              INTEGER,
        hw10GEOpticsMDCCEXT
              Integer32,
        hw10GEOpticsMDVendorSpecific
              OCTET STRING
       }

    hw10GEOpticsMDIdentifier OBJECT-TYPE
      SYNTAX INTEGER
        {
          unknown(0),
          gbic(1),
          solderedToMotherBoard(2),
          sfp(3),
          pin300XBI(4),
          xenpak(5),
          xfp(6),
          xff(7),
          xfep(8),
          xpak(9),
          x2(10),
          invalid(-1)
        }
      MAX-ACCESS read-only
      STATUS current
      DESCRIPTION
        "Indicate the identifier of 10GE optical module.
         Options:
         1. unknown(0)                  -unknown identifier of 10GE optical module
         2. gbic(1)                     -the identifier of 10GE optical module is gbic
         3. solderedToMotherBoard(2)    -the identifier of 10GE optical module is solderedToMotherBoard
         4. sfp(3)                      -the identifier of 10GE optical module is sfp
         5. pin300XBI(4)                -the identifier of 10GE optical module is pin300XBI
         6. xenpak(5)                   -the identifier of 10GE optical module is xenpak
         7. xfp(6)                      -the identifier of 10GE optical module is xfp
         8. xff(7)                      -the identifier of 10GE optical module is xff
         9. xfep(8)                     -the identifier of 10GE optical module is xfep
         10. xpak(9)                    -the identifier of 10GE optical module is xpak
         11. x2(10)                     -the identifier of 10GE optical module is x2
         12. invalid(-1)				-invalid value
        "
      ::= { hw10GEOpticsModuleInformationEntry 1 }

    hw10GEOpticsMDExtCLEICode OBJECT-TYPE
      SYNTAX INTEGER
        {
          nonExtCLEICode(0),
          extCLEICode(1),
          invalid(-1)
        }
      MAX-ACCESS read-only
      STATUS current
      DESCRIPTION
        "Extended identifier: CLEI
         Options:
         1. nonExtCLEICode(0)  -no CLEI code present in Table 02h
         2. extCLEICode(1)     -CLEI code present in Table 02h
         3. invalid(-1)		   -invalid value
        "
      ::= { hw10GEOpticsModuleInformationEntry 2 }

    hw10GEOpticsMDExtTXRefClock OBJECT-TYPE
      SYNTAX INTEGER
        {
          nonExtTXRefClock(0),
          extTXRefClock(1),
          invalid(-1)
        }
      MAX-ACCESS read-only
      STATUS current
      DESCRIPTION
        "Extended identifier: TX Ref Clock
         Options:
         1. nonExtTXRefClock(0) -tx Ref Clock Input Not Required
         2. extTXRefClock(1)    -tx Ref Clock Input Required
         3. invalid(-1)			-invalid value
        "
      ::= { hw10GEOpticsModuleInformationEntry 3 }

    hw10GEOpticsMDExtCDRFunc OBJECT-TYPE
      SYNTAX INTEGER
        {
          nonExtCDRFunc(0),
          extCDRFunc(1),
          invalid(-1)
        }
      MAX-ACCESS read-only
      STATUS current
      DESCRIPTION
        "Extended identifier: CDR function
         Options:
         1. nonExtCDRFunc(0) -no CDR version of XFP
         2. extCDRFunc(1)    -module with CDR function
         3. invalid(-1)		 -invalid value
        "
      ::= { hw10GEOpticsModuleInformationEntry 4 }

    hw10GEOpticsMDExtPowerLevel OBJECT-TYPE
      SYNTAX INTEGER
        {
          extPowerLevel1(0),
          extPowerLevel2(1),
          extPowerLevel3(2),
          extPowerLevel4(3),
          invalid(-1)
        }
      MAX-ACCESS read-only
      STATUS current
      DESCRIPTION
        "Extended identifier: Power Level
         Options:
         1. extPowerLevel1(0)  -power Level 1 Module (1.5 W max. power dissipation.)
         2. extPowerLevel2(1)  -power Level 2 Module (2.5W Max)
         3. extPowerLevel3(2)  -power Level 3 Module (3.5W max. power dissipation.)
         4. extPowerLevel4(3)  -power Level 4 Module (>3.5W max. power dissipation.)
         5. invalid(-1)		   -invalid value
        "
      ::= { hw10GEOpticsModuleInformationEntry 5 }

    hw10GEOpticsMDConnector OBJECT-TYPE
      SYNTAX INTEGER
        {
          unknown(0),
          sc(1),
          style1Connector(2),
          style2Connector(3),
          bnctnc(4),
          channelCoaxial(5),
          fiberJack(6),
          lc(7),
          mtrj(8),
          mu(9),
          sg(10),
          opticalPigtail(11),
          hssdc(20),
          copperPigtail(21),
          invalid(-1)
        }
      MAX-ACCESS read-only
      STATUS current
      DESCRIPTION
        "Indicate the type of 10GE optical module connector.
         Options:
         1. unknown(0)             -unknown the type of 10GE optical module connector
         2. sc(1)                  -the type of 10GE optical module connector is sc
         3. style1Connector(2)     -the type of 10GE optical module connector is style1Connector
         4. style2Connector(3)     -the type of 10GE optical module connector is style2Connector
         5. bnctnc(4)              -the type of 10GE optical module connector is bnctnc
         6. channelCoaxial(5)      -the type of 10GE optical module connector is channelCoaxial
         7. fiberJack(6)           -the type of 10GE optical module connector is fiberJack
         8. lc(7)                  -the type of 10GE optical module connector is lc
         9. mtrj(8)                -the type of 10GE optical module connector is mtrj
         10. mu(9)                 -the type of 10GE optical module connector is mu
         11. sg(10)                -the type of 10GE optical module connector is sg
         12. opticalPigtail(11)    -the type of 10GE optical module connector is opticalPigtail
         13. hssdc(20)             -the type of 10GE optical module connector is hssdc
         14. copperPigtail(21)     -the type of 10GE optical module connector is copperPigtail
         15. invalid(-1)		   -invalid value
        "
      ::= { hw10GEOpticsModuleInformationEntry 6 }

    hw10GEOpticsMDEthComplianceBaseEW OBJECT-TYPE
      SYNTAX INTEGER
        {
          nonEthComplianceBaseEW(0),
          ethComplianceBaseEW(1)
        }
      MAX-ACCESS read-only
      STATUS current
      DESCRIPTION
        "Indicate 10GBASE-EW support or not.
         Options:
         1. nonEthComplianceBaseEW(0) -not support 10GBASE-EW
         2. ethComplianceBaseEW(1)    -support 10GBASE-EW
        "
      ::= { hw10GEOpticsModuleInformationEntry 7 }

    hw10GEOpticsMDEthComplianceBaseLW OBJECT-TYPE
      SYNTAX INTEGER
        {
          nonEthComplianceBaseLW(0),
          ethComplianceBaseLW(1)
        }
      MAX-ACCESS read-only
      STATUS current
      DESCRIPTION
        "Indicate 10GBASE-LW support or not.
         Options:
         1. nonEthComplianceBaseLW(0) -not support 10GBASE-LW
         2. ethComplianceBaseLW(1)    -support 10GBASE-LW
         "
      ::= { hw10GEOpticsModuleInformationEntry 8 }

    hw10GEOpticsMDEthComplianceBaseSW OBJECT-TYPE
      SYNTAX INTEGER
        {
          nonEthComplianceBaseSW(0),
          ethComplianceBaseSW(1)
        }
      MAX-ACCESS read-only
      STATUS current
      DESCRIPTION
        "Indicate 10GBASE-SW support or not.
         Options:
         1. nonEthComplianceBaseSW(0) -not support 10GBASE-SW
         2. ethComplianceBaseSW(1)    -support 10GBASE-SW
        "
      ::= { hw10GEOpticsModuleInformationEntry 9 }

    hw10GEOpticsMDEthComplianceBaseLRM OBJECT-TYPE
      SYNTAX INTEGER
        {
          nonEthComplianceBaseLRM(0),
          ethComplianceBaseLRM(1)
        }
      MAX-ACCESS read-only
      STATUS current
      DESCRIPTION
        "Indicate 10GBASE-LRM support or not.
         Options:
         1. nonEthComplianceBaseLRM(0) -not support 10GBASE-LRM
         2. ethComplianceBaseLRM(1)    -support 10GBASE-LRM
        "
      ::= { hw10GEOpticsModuleInformationEntry 10 }

    hw10GEOpticsMDEthComplianceBaseER OBJECT-TYPE
      SYNTAX INTEGER
        {
          nonEthComplianceBaseER(0),
          ethComplianceBaseER(1)
        }
      MAX-ACCESS read-only
      STATUS current
      DESCRIPTION
        "Indicate 10GBASE-ER support or not.
         Options:
         1. nonEthComplianceBaseER(0) -not support 10GBASE-ER
         2. ethComplianceBaseER(1)    -support 10GBASE-ER
        "
      ::= { hw10GEOpticsModuleInformationEntry 11 }

    hw10GEOpticsMDEthComplianceBaseLR OBJECT-TYPE
      SYNTAX INTEGER
        {
          nonEthComplianceBaseLR(0),
          ethComplianceBaseLR(1)
        }
      MAX-ACCESS read-only
      STATUS current
      DESCRIPTION
        "Indicate 10GBASE-LR support or not.
         Options:
         1. nonEthComplianceBaseLR(0) -not support 10GBASE-LR
         2. ethComplianceBaseLR(1)    -support 10GBASE-LR
        "
      ::= { hw10GEOpticsModuleInformationEntry 12 }

    hw10GEOpticsMDEthComplianceBaseSR OBJECT-TYPE
      SYNTAX INTEGER
        {
          nonEthComplianceBaseSR(0),
          ethComplianceBaseSR(1)
        }
      MAX-ACCESS read-only
      STATUS current
      DESCRIPTION
        "Indicate 10GBASE-SR support or not.
         Options:
         1. nonEthComplianceBaseSR(0) -not support 10GBASE-SR
         2. ethComplianceBaseSR(1)    -support 10GBASE-SR
        "
      ::= { hw10GEOpticsModuleInformationEntry 13 }

    hw10GEOpticsMDFibreCompliance OBJECT-TYPE
      SYNTAX INTEGER
        {
          fibreComplianceInter1300FP(16),
          fibreComplianceExtended1550(32),
          fibreComplianceSM1200(64),
          fibreComplianceMX1200(128),
          invalid(-1)
        }
      MAX-ACCESS read-only
      STATUS current
      DESCRIPTION
        "Indicate 10 Gigabit Fibre Channel Compliance type.
         Options:
         1. fibreComplianceInter1300FP(16)  -intermediate Reach 1300 nm FP
         2. fibreComplianceExtended1550(32) -extended reach 1550 nm
         3. fibreComplianceSM1200(64)       -1200-SM-LL-L
         4. fibreComplianceMX1200(128)      -1200-MX-SN-I
         5. invalid(-1)                     -invalid value
        "
      ::= { hw10GEOpticsModuleInformationEntry 14 }

    hw10GEOpticsMDLowerSpeedLink OBJECT-TYPE
      SYNTAX INTEGER
        {
          lowerSpeedLinkOC48LR(2),
          lowerSpeedLinkOC48IR(4),
          lowerSpeedLinkOC48SR(8),
          lowerSpeedLinkFCSMF(16),
          lowerSpeedLinkFCMMF(32),
          lowerSpeedLinkLXSMF(64),
          lowerSpeedLinkSXMMF(128),
          invalid(-1)
        }
      MAX-ACCESS read-only
      STATUS current
      DESCRIPTION
        "Indicate Lower Speed Links type.
         Options:
         1. lowerSpeedLinkOC48LR(2)   -lower speed links type is OC48LR
         2. lowerSpeedLinkOC48IR(4)   -lower speed links type is OC48IR
         3. lowerSpeedLinkOC48SR(8)   -lower speed links type is OC48SR
         4. lowerSpeedLinkFCSMF(16)   -lower speed links type is FCSMF
         5. lowerSpeedLinkFCMMF(32)   -lower speed links type is FCMMF
         6. lowerSpeedLinkLXSMF(64)   -lower speed links type is LXSMF
         7. lowerSpeedLinkSXMMF(128)  -lower speed links type is SXMMF
         8. invalid(-1)               -invalid value
        "
      ::= { hw10GEOpticsModuleInformationEntry 15 }

    hw10GEOpticsMDSONETSDHCodesI64point5 OBJECT-TYPE
      SYNTAX INTEGER
        {
          notSupport(0),
          support(1)
        }
      MAX-ACCESS read-only
      STATUS current
      DESCRIPTION
        "Indicate SONET/SDH Codes I-64.5 support or not.
         Options:
         1. notSupport(0) -not Support I-64.5
         2. support(1)    -support I-64.5
        "
      ::= { hw10GEOpticsModuleInformationEntry 16 }

    hw10GEOpticsMDSONETSDHCodesI64point3 OBJECT-TYPE
      SYNTAX INTEGER
        {
          notSupport(0),
          support(1)
        }
      MAX-ACCESS read-only
      STATUS current
      DESCRIPTION
        "Indicate SONET/SDH Codes I-64.3 support or not.
         Options:
         1. notSupport(0) -not Support I-64.3
         2. support(1)    -support I-64.3
        "
      ::= { hw10GEOpticsModuleInformationEntry 17 }

    hw10GEOpticsMDSONETSDHCodesI64point2 OBJECT-TYPE
      SYNTAX INTEGER
        {
          notSupport(0),
          support(1)
        }
      MAX-ACCESS read-only
      STATUS current
      DESCRIPTION
        "Indicate SONET/SDH Codes I-64.2 support or not.
         Options:
         1. notSupport(0) -not Support I-64.2
         2. support(1)    -support I-64.2
        "
      ::= { hw10GEOpticsModuleInformationEntry 18 }

    hw10GEOpticsMDSONETSDHCodesI64point2r OBJECT-TYPE
      SYNTAX INTEGER
        {
          notSupport(0),
          support(1)
        }
      MAX-ACCESS read-only
      STATUS current
      DESCRIPTION
        "Indicate SONET/SDH Codes I-64.2r support or not.
         Options:
         1. notSupport(0) -not support I-64.2r
         2. support(1)    -support I-64.2r
        "
      ::= { hw10GEOpticsModuleInformationEntry 19 }

    hw10GEOpticsMDSONETSDHCodesI64point1 OBJECT-TYPE
      SYNTAX INTEGER
        {
          notSupport(0),
          support(1)
        }
      MAX-ACCESS read-only
      STATUS current
      DESCRIPTION
        "Indicate SONET/SDH Codes I-64.1 support or not.
         Options:
         1. notSupport(0) -not support I-64.1
         2. support(1)    -support I-64.1
        "
      ::= { hw10GEOpticsModuleInformationEntry 20 }

    hw10GEOpticsMDSONETSDHCodesI64point1r OBJECT-TYPE
      SYNTAX INTEGER
        {
          notSupport(0),
          support(1)
        }
      MAX-ACCESS read-only
      STATUS current
      DESCRIPTION
        "Indicate SONET/SDH Codes I-64.1r support or not.
         Options:
         1. notSupport(0) -not support I-64.1r
         2. support(1)    -support I-64.1r
        "
      ::= { hw10GEOpticsModuleInformationEntry 21 }

    hw10GEOpticsMDSONETSDHCodesS64point5b OBJECT-TYPE
      SYNTAX INTEGER
        {
          notSupport(0),
          support(1)
        }
      MAX-ACCESS read-only
      STATUS current
      DESCRIPTION
        "Indicate SONET/SDH Codes S-64.5b support or not.
         Options:
         1. notSupport(0) -not support S-64.5b
         2. support(1)    -support S-64.5b
        "
      ::= { hw10GEOpticsModuleInformationEntry 22 }

    hw10GEOpticsMDSONETSDHCodesS64point5a OBJECT-TYPE
      SYNTAX INTEGER
        {
          notSupport(0),
          support(1)
        }
      MAX-ACCESS read-only
      STATUS current
      DESCRIPTION
        "Indicate SONET/SDH Codes S-64.5a support or not.
         Options:
         1. notSupport(0) -not support S-64.5a
         2. support(1)    -support S-64.5a
        "
      ::= { hw10GEOpticsModuleInformationEntry 23 }

    hw10GEOpticsMDSONETSDHCodesS64point3b OBJECT-TYPE
      SYNTAX INTEGER
        {
          notSupport(0),
          support(1)
        }
      MAX-ACCESS read-only
      STATUS current
      DESCRIPTION
        "Indicate SONET/SDH Codes S-64.3b support or not.
         Options:
         1. notSupport(0) -not support S-64.3b
         2. support(1)    -support S-64.3b
        "
      ::= { hw10GEOpticsModuleInformationEntry 24 }

    hw10GEOpticsMDSONETSDHCodesS64point3a OBJECT-TYPE
      SYNTAX INTEGER
        {
          notSupport(0),
          support(1)
        }
      MAX-ACCESS read-only
      STATUS current
      DESCRIPTION
        "Indicate SONET/SDH Codes S-64.3a support or not.
         Options:
         1. notSupport(0) -not support S-64.3a
         2. support(1)    -support S-64.3a
        "
      ::= { hw10GEOpticsModuleInformationEntry 25 }

    hw10GEOpticsMDSONETSDHCodesS64point2b OBJECT-TYPE
      SYNTAX INTEGER
        {
          notSupport(0),
          support(1)
        }
      MAX-ACCESS read-only
      STATUS current
      DESCRIPTION
        "Indicate SONET/SDH Codes S-64.2b support or not.
         Options:
         1. notSupport(0) -not support S-64.2b
         2. support(1)    -support S-64.2b
        "
      ::= { hw10GEOpticsModuleInformationEntry 26 }

    hw10GEOpticsMDSONETSDHCodesS64point2a OBJECT-TYPE
      SYNTAX INTEGER
        {
          notSupport(0),
          support(1)
        }
      MAX-ACCESS read-only
      STATUS current
      DESCRIPTION
        "Indicate SONET/SDH Codes S-64.2a support or not.
         Options:
         1. notSupport(0) -not support S-64.2a
         2. support(1)    -support S-64.2a
        "
      ::= { hw10GEOpticsModuleInformationEntry 27 }

    hw10GEOpticsMDSONETSDHCodesS64point1 OBJECT-TYPE
      SYNTAX INTEGER
        {
          notSupport(0),
          support(1)
        }
      MAX-ACCESS read-only
      STATUS current
      DESCRIPTION
        "Indicate SONET/SDH Codes S-64.1 support or not.
         Options:
         1. notSupport(0) -not support S-64.1
         2. support(1)    -support S-64.1
        "
      ::= { hw10GEOpticsModuleInformationEntry 28 }

    hw10GEOpticsMDSONETSDHCodesG959P1L1 OBJECT-TYPE
      SYNTAX INTEGER
        {
          notSupport(0),
          support(1)
        }
      MAX-ACCESS read-only
      STATUS current
      DESCRIPTION
        "Indicate SONET/SDH Codes G.959.1 P1L1-2D2 support or not.
         Options:
         1. notSupport(0) -not support G.959.1 P1L1-2D2
         2. support(1)    -support G.959.1 P1L1-2D2
        "
      ::= { hw10GEOpticsModuleInformationEntry 29 }

    hw10GEOpticsMDSONETSDHCodesL64point3 OBJECT-TYPE
      SYNTAX INTEGER
        {
          notSupport(0),
          support(1)
        }
      MAX-ACCESS read-only
      STATUS current
      DESCRIPTION
        "Indicate SONET/SDH Codes L-64.3 support or not.
         Options:
         1. notSupport(0) -not support L-64.3
         2. support(1)    -support L-64.3
        "
      ::= { hw10GEOpticsModuleInformationEntry 30 }

    hw10GEOpticsMDSONETSDHCodesL64point2c OBJECT-TYPE
      SYNTAX INTEGER
        {
          notSupport(0),
          support(1)
        }
      MAX-ACCESS read-only
      STATUS current
      DESCRIPTION
        "Indicate SONET/SDH Codes L-64.2c support or not.
         Options:
         1. notSupport(0) -not support L-64.2c
         2. support(1)    -support L-64.2c
        "
      ::= { hw10GEOpticsModuleInformationEntry 31 }

    hw10GEOpticsMDSONETSDHCodesL64point2b OBJECT-TYPE
      SYNTAX INTEGER
        {
          notSupport(0),
          support(1)
        }
      MAX-ACCESS read-only
      STATUS current
      DESCRIPTION
        "Indicate SONET/SDH Codes L-64.2b support or not.
         Options:
         1. notSupport(0) -not support L-64.2b
         2. support(1)    -support L-64.2b
        "
      ::= { hw10GEOpticsModuleInformationEntry 32 }

    hw10GEOpticsMDSONETSDHCodesL64point2a OBJECT-TYPE
      SYNTAX INTEGER
        {
          notSupport(0),
          support(1)
        }
      MAX-ACCESS read-only
      STATUS current
      DESCRIPTION
        "Indicate SONET/SDH Codes L-64.2a support or not.
         Options:
         1. notSupport(0) -not support L-64.2a
         2. support(1)    -support L-64.2a
        "
      ::= { hw10GEOpticsModuleInformationEntry 33 }

    hw10GEOpticsMDSONETSDHCodesL64point1 OBJECT-TYPE
      SYNTAX INTEGER
        {
          notSupport(0),
          support(1)
        }
      MAX-ACCESS read-only
      STATUS current
      DESCRIPTION
        "Indicate SONET/SDH Codes L-64.1 support or not.
         Options:
         1. notSupport(0) -not support L-64.1
         2. support(1)    -support L-64.1
        "
      ::= { hw10GEOpticsModuleInformationEntry 34 }

    hw10GEOpticsMDSONETSDHCodesV64point3 OBJECT-TYPE
      SYNTAX INTEGER
        {
          notSupport(0),
          support(1)
        }
      MAX-ACCESS read-only
      STATUS current
      DESCRIPTION
        "Indicate SONET/SDH Codes V-64.3 support or not.
         Options:
         1. notSupport(0) -not support V-64.3
         2. support(1)    -support V-64.3
        "
      ::= { hw10GEOpticsModuleInformationEntry 35 }

    hw10GEOpticsMDSONETSDHCodesV64point2b OBJECT-TYPE
      SYNTAX INTEGER
        {
          notSupport(0),
          support(1)
        }
      MAX-ACCESS read-only
      STATUS current
      DESCRIPTION
        "Indicate SONET/SDH Codes V-64.2b support or not.
         Options:
         1. notSupport(0) -not support V-64.2b
         2. support(1)    -support V-64.2b
        "
      ::= { hw10GEOpticsModuleInformationEntry 36 }

    hw10GEOpticsMDSONETSDHCodesV64point2a OBJECT-TYPE
      SYNTAX INTEGER
        {
          notSupport(0),
          support(1)
        }
      MAX-ACCESS read-only
      STATUS current
      DESCRIPTION
        "Indicate SONET/SDH Codes V-64.2a support or not.
         Options:
         1. notSupport(0) -not support V-64.2a
         2. support(1)    -support V-64.2a
        "
      ::= { hw10GEOpticsModuleInformationEntry 37 }

    hw10GEOpticsMDEncodingRZ OBJECT-TYPE
      SYNTAX INTEGER
        {
          nonEncodingRZ(0),
          encodingRZ(1)
        }
      MAX-ACCESS read-only
      STATUS current
      DESCRIPTION
        "Indicate encoding mechanism RZ support or not.
         Options:
         1. nonEncodingRZ(0) -not support RZ
         2. encodingRZ(1)    -support RZ
        "
      ::= { hw10GEOpticsModuleInformationEntry 38 }

    hw10GEOpticsMDEncodingNRZ OBJECT-TYPE
      SYNTAX INTEGER
        {
          nonEncodingNRZ(0),
          encodingNRZ(1)
        }
      MAX-ACCESS read-only
      STATUS current
      DESCRIPTION
        "Indicate encoding mechanism NRZ support or not.
         Options:
         1. nonEncodingNRZ(0) -not support NRZ
         2. encodingNRZ(1)    -support NRZ
        "
      ::= { hw10GEOpticsModuleInformationEntry 39 }

    hw10GEOpticsMDEncodingSONET OBJECT-TYPE
      SYNTAX INTEGER
        {
          nonEncodingSONET(0),
          encodingSONET(1)
        }
      MAX-ACCESS read-only
      STATUS current
      DESCRIPTION
        "Indicate encoding mechanism SONET support or not.
         Options:
         1. nonEncodingSONET(0)  -not support SONET
         2. encodingSONET(1)     -support SONET
        "
      ::= { hw10GEOpticsModuleInformationEntry 40 }

    hw10GEOpticsMDEncoding8B10B OBJECT-TYPE
      SYNTAX INTEGER
        {
          nonEncoding8B10B(0),
          encoding8B10B(1)
        }
      MAX-ACCESS read-only
      STATUS current
      DESCRIPTION
        "Indicate encoding mechanism 8B10B support or not.
         Options:
         1. nonEncoding8B10B(0) -not support 8B10B
         2. encoding8B10B(1)    -support 8B10B
        "
      ::= { hw10GEOpticsModuleInformationEntry 41 }

    hw10GEOpticsMDEncoding64B OBJECT-TYPE
      SYNTAX INTEGER
        {
          nonEncoding64B(0),
          encoding64B(1)
        }
      MAX-ACCESS read-only
      STATUS current
      DESCRIPTION
        "Indicate encoding mechanism 64B/66B support or not.
         Options:
         1. nonEncoding64B(0) -not support 64B/66B
         2. encoding64B(1)    -support 64B/66B
        "
      ::= { hw10GEOpticsModuleInformationEntry 42 }

    hw10GEOpticsMDBrMin OBJECT-TYPE
      SYNTAX Integer32
      MAX-ACCESS read-only
      STATUS current
      DESCRIPTION
        "Minimum bit rate.
         Unit: 100 MBits/s
         "
      ::= { hw10GEOpticsModuleInformationEntry 43 }

    hw10GEOpticsMDBrMax OBJECT-TYPE
      SYNTAX Integer32
      MAX-ACCESS read-only
      STATUS current
      DESCRIPTION
        "Maximum bit rate.
         Unit: 100 MBits/s
         "
      ::= { hw10GEOpticsModuleInformationEntry 44 }

    hw10GEOpticsMDSupportLenSMF OBJECT-TYPE
      SYNTAX Integer32
      MAX-ACCESS read-only
      STATUS current
      DESCRIPTION
        "Indicate the link length that is supported by the transceiver with the applicable standards
         using Single-mode Fiber.
         "
      ::= { hw10GEOpticsModuleInformationEntry 45 }

    hw10GEOpticsMDSupportLenE50um OBJECT-TYPE
      SYNTAX Integer32
      MAX-ACCESS read-only
      STATUS current
      DESCRIPTION
        "Indicate the link length that is supported by the transceiver with the applicable standards
         using 2000MHz*km (850nm) extended bandwidth 50 micron core multimode fiber.
         Unit: 2m
        "
      ::= { hw10GEOpticsModuleInformationEntry 46 }

    hw10GEOpticsMDSupportLen50um OBJECT-TYPE
      SYNTAX Integer32
      MAX-ACCESS read-only
      STATUS current
      DESCRIPTION
        "This value specifies the link length that is supported by the transceiver with the applicable
         standards using 500MHz*km (850 and 1310nm) 50 micron core multimode fiber.
         Unit: 1m
         "
      ::= { hw10GEOpticsModuleInformationEntry 47 }

    hw10GEOpticsMDSupportLen62p5um OBJECT-TYPE
      SYNTAX Integer32
      MAX-ACCESS read-only
      STATUS current
      DESCRIPTION
        "This value specifies the link length that is supported by the transceiver with the applicable
         standards using 200MHz*km (850 nm)/500 MHz*km (1310 nm) 62.5 micron core multimode fiber.
         Unit: 1m
         "
      ::= { hw10GEOpticsModuleInformationEntry 48 }

    hw10GEOpticsMDSupportLenCopper OBJECT-TYPE
      SYNTAX Integer32
      MAX-ACCESS read-only
      STATUS current
      DESCRIPTION
        "Indicate the minimum link length that is supported by the transceiver with copper cable.
         Unit: 1m
         "
      ::= { hw10GEOpticsModuleInformationEntry 49 }

    hw10GEOpticsMDTransmitterSupport OBJECT-TYPE
      SYNTAX INTEGER
        {
          nonTunable(0),
          tunable(1),
          invalid(-1)
        }
      MAX-ACCESS read-only
      STATUS current
      DESCRIPTION
        "Indicate the transmitter support tunable or not.
         Options:
         1. nonTunable(0) -transmitter not support tunable
         2. tunable(1)    -transmitter support tunable
         3. invalid(-1)	  -invalid value
        "
      ::= { hw10GEOpticsModuleInformationEntry 50 }

    hw10GEOpticsMDDetector OBJECT-TYPE
      SYNTAX INTEGER
        {
          nonDetector(0),
          detector(1),
          invalid(-1)
        }
      MAX-ACCESS read-only
      STATUS current
      DESCRIPTION
        "Indicate the Detector is enable or not.
         Options:
         1. nonDetector(0) -detector is disable
         2. detector(1)    -detector is enable
         3. invalid(-1)	   -invalid value
        "
      ::= { hw10GEOpticsModuleInformationEntry 51 }

    hw10GEOpticsMDCooledTransmitterDevice OBJECT-TYPE
      SYNTAX INTEGER
        {
          nonSupport(0),
          support(1),
          invalid(-1)
        }
      MAX-ACCESS read-only
      STATUS current
      DESCRIPTION
        "Indicate the Cooled transmitter is enable or not.
         Options:
         1. nonSupport(0) -cooled transmitter is disable
         2. support(1)    -cooled transmitter is enable
         3. invalid(-1)	  -invalid value
        "
      ::= { hw10GEOpticsModuleInformationEntry 52 }

    hw10GEOpticsMDWavelengthControl OBJECT-TYPE
      SYNTAX INTEGER
        {
          nonSupport(0),
          support(1),
          invalid(-1)
        }
      MAX-ACCESS read-only
      STATUS current
      DESCRIPTION
        "Indicate the wavelength control support or not.
         Options:
         1. nonSupport(0) -wavelength control not support
         2. support(1)    -wavelength control support
         3. invalid(-1)	  -invalid value
        "
      ::= { hw10GEOpticsModuleInformationEntry 53 }

    hw10GEOpticsMDTransmitterTechnologySupport OBJECT-TYPE
      SYNTAX INTEGER
        {
          vCSEL850(0),
          vCSEL1310(1),
          vCSEL1550(2),
          fP1310(3),
          dFB1310(4),
          dFB1550(5),
          eML1310(6),
          eML1550(7),
          cOPPER(8),
          invalid(-1)
        }
      MAX-ACCESS read-only
      STATUS current
      DESCRIPTION
        "Indicate the transmitter technology type.
         Options:
         1. vCSEL850(0)     -the transmitter technology type is vCSEL850
         2. vCSEL1310(1)    -the transmitter technology type is vCSEL1310
         3. vCSEL1550(2)    -the transmitter technology type is vCSEL1550
         4. fP1310(3)       -the transmitter technology type is fP1310
         5. dFB1310(4)      -the transmitter technology type is dFB1310
         6. dFB1550(5)      -the transmitter technology type is dFB1550
         7. eML1310(6)      -the transmitter technology type is eML1310
         8. eML1550(7)      -the transmitter technology type is eML1550
         9. cOPPER(8)       -the transmitter technology type is cOPPER
         10. invalid(-1)	-invalid value
        "
      ::= { hw10GEOpticsModuleInformationEntry 54 }

    hw10GEOpticsMDVendorName OBJECT-TYPE
      SYNTAX OCTET STRING (SIZE (0..40))
      MAX-ACCESS read-only
      STATUS current
      DESCRIPTION
        "Indicate the vendor name of a 10GE optical module.
        "
      ::= { hw10GEOpticsModuleInformationEntry 55 }

    hw10GEOpticsMDSupportXFIMode OBJECT-TYPE
      SYNTAX INTEGER
        {
          nonSupportXFIMode(0),
          supportXFIMode(1),
          invalid(-1)
        }
      MAX-ACCESS read-only
      STATUS current
      DESCRIPTION
        "Indicate the XFI loopback mode support or not.
         Options:
         1. nonSupportXFIMode(0) -the XFI loopback mode not support
         2. supportXFIMode(1)    -the XFI loopback mode support
         3. invalid(-1)			 -invalid value
        "
      ::= { hw10GEOpticsModuleInformationEntry 56 }

    hw10GEOpticsMDSupportLinesideMode OBJECT-TYPE
      SYNTAX INTEGER
        {
          nonSupportLinesideMode(0),
          supportLinesideMode(1),
          invalid(-1)
        }
      MAX-ACCESS read-only
      STATUS current
      DESCRIPTION
        "Indicate the Lineside loopback mode support or not.
         Options:
         1. nonSupportLinesideMode(0) -lineside loopback mode not support
         2. supportLinesideMode(1)    -lineside loopback mode support
         3. invalid(-1)				  -invalid value
        "
      ::= { hw10GEOpticsModuleInformationEntry 57 }

    hw10GEOpticsMDMaxBitRateSupportedByCDR  OBJECT-TYPE
      SYNTAX INTEGER
        {
          maxBitRateSupportedByCDR11p1(1),
          maxBitRateSupportedByCDR10p7(3),
          maxBitRateSupportedByCDR10p5(7),
          maxBitRateSupportedByCDR10p3(15),
          maxBitRateSupportedByCDR9p95(31),
          invalid(-1)
        }
      MAX-ACCESS read-only
      STATUS current
      DESCRIPTION
        "Indicate which rate is supported by the CDR.
         Options:
         1. maxBitRateSupportedByCDR11p1(1)  -CDR support for 11.1 Gb/s
         2. maxBitRateSupportedByCDR10p7(3)  -CDR support for 10.7 Gb/s
         3. maxBitRateSupportedByCDR10p5(7)  -CDR support for 10.5 Gb/s
         4. maxBitRateSupportedByCDR10p3(15) -CDR support for 10.3 Gb/s
         5. maxBitRateSupportedByCDR9p95(31) -CDR support for 9.95 Gb/s
         6. invalid(-1)                      -invalid value
        "
      ::= { hw10GEOpticsModuleInformationEntry 58 }

    hw10GEOpticsMDVendorOUI OBJECT-TYPE
      SYNTAX Integer32
      MAX-ACCESS read-only
      STATUS current
      DESCRIPTION
        "Indicate the vendor IEEE company ID of a 10GE optical module."
      ::= { hw10GEOpticsModuleInformationEntry 59 }

    hw10GEOpticsMDVendorPN OBJECT-TYPE
      SYNTAX OCTET STRING (SIZE (0..40))
      MAX-ACCESS read-only
      STATUS current
      DESCRIPTION
        "Indicate the part number of a 10GE optical module provided by vendor."
      ::= { hw10GEOpticsModuleInformationEntry 60 }

    hw10GEOpticsMDVendorRev OBJECT-TYPE
      SYNTAX OCTET STRING (SIZE (0..40))
      MAX-ACCESS read-only
      STATUS current
      DESCRIPTION
        "Indicate the revision level for part number provided by vendor."
      ::= { hw10GEOpticsModuleInformationEntry 61 }

    hw10GEOpticsMDWavelength OBJECT-TYPE
      SYNTAX Integer32
      MAX-ACCESS read-only
      STATUS current
      DESCRIPTION
        "The laser wavelength."
      ::= { hw10GEOpticsModuleInformationEntry 62 }

    hw10GEOpticsMDWaveTolerance OBJECT-TYPE
      SYNTAX Integer32
      MAX-ACCESS read-only
      STATUS current
      DESCRIPTION
        "The guaranteed +/- range of transmitter output wavelength under all normal operating conditions.
        "
      ::= { hw10GEOpticsModuleInformationEntry 63 }

    hw10GEOpticsMDMaxCaseTemperature OBJECT-TYPE
      SYNTAX Integer32
      MAX-ACCESS read-only
      STATUS current
      DESCRIPTION
        "Maximum Case Temperature in Degrees C."
      ::= { hw10GEOpticsModuleInformationEntry 64 }

    hw10GEOpticsMDCcbase OBJECT-TYPE
      SYNTAX Integer32
      MAX-ACCESS read-only
      STATUS current
      DESCRIPTION
        "Cc_base. "
      ::= { hw10GEOpticsModuleInformationEntry 65 }

    hw10GEOpticsMDMaxDissipation OBJECT-TYPE
      SYNTAX Integer32
      MAX-ACCESS read-only
      STATUS current
      DESCRIPTION
        "Maximum Power Dissipation.
         Max power is 8 bit value * 20 mW.
        "
      ::= { hw10GEOpticsModuleInformationEntry 66 }

    hw10GEOpticsMDMaxDissipationPowerDownMode OBJECT-TYPE
      SYNTAX Integer32
      MAX-ACCESS read-only
      STATUS current
      DESCRIPTION
        "Maximum Total Power Dissipation in Power Down Mode.
         Max Power is 8 bit value * 10 mW.
        "
      ::= { hw10GEOpticsModuleInformationEntry 67 }

    hw10GEOpticsMDMaximum5P0VSupply OBJECT-TYPE
      SYNTAX Integer32
      MAX-ACCESS read-only
      STATUS current
      DESCRIPTION
        "Maximum current required by +5V Supply."
      ::= { hw10GEOpticsModuleInformationEntry 68 }

    hw10GEOpticsMDMaximum3P3VSupply OBJECT-TYPE
      SYNTAX Integer32
      MAX-ACCESS read-only
      STATUS current
      DESCRIPTION
        "Maximum current required by +3.3V Supply."
      ::= { hw10GEOpticsModuleInformationEntry 69 }

    hw10GEOpticsMDMaximum1P8VSupply OBJECT-TYPE
      SYNTAX Integer32
      MAX-ACCESS read-only
      STATUS current
      DESCRIPTION
        "Maximum current required by +1.8V Supply."
      ::= { hw10GEOpticsModuleInformationEntry 70 }

    hw10GEOpticsMDMaximum5P2VSupply OBJECT-TYPE
      SYNTAX Integer32
      MAX-ACCESS read-only
      STATUS current
      DESCRIPTION
        "Maximum current required by -5.2V Supply."
      ::= { hw10GEOpticsModuleInformationEntry 71 }

    hw10GEOpticsMDVendorSN OBJECT-TYPE
      SYNTAX OCTET STRING (SIZE (0..140))
      MAX-ACCESS read-only
      STATUS current
      DESCRIPTION
        "The serial number of a 10GE optical module provided by vendor."
      ::= { hw10GEOpticsModuleInformationEntry 72 }

    hw10GEOpticsMDDateCode OBJECT-TYPE
      SYNTAX OCTET STRING (SIZE (0..40))
      MAX-ACCESS read-only
      STATUS current
      DESCRIPTION
        "The date code of a 10GE optical module."
      ::= { hw10GEOpticsModuleInformationEntry 73 }

    hw10GEOpticsMDDiagnoMonitorPowerMeasure OBJECT-TYPE
      SYNTAX INTEGER
        {
          supportOMA(0),
          supportAveragePower(1)
        }
      MAX-ACCESS read-only
      STATUS current
      DESCRIPTION
        "Received power measurement type.
         Options:
         1. supportOMA(0)          -OMA
         2. supportAveragePower(1) -AveragePower
        "
      ::= { hw10GEOpticsModuleInformationEntry 74 }

    hw10GEOpticsMDDiagnoMonitorTypeFECBER OBJECT-TYPE
      SYNTAX INTEGER
        {
          nonSupportBER(0),
          supportBER(1)
        }
      MAX-ACCESS read-only
      STATUS current
      DESCRIPTION
        "Module Respond to FEC BER.
         Options:
         1. nonSupportBER(0) -no BER Support
         2. supportBER(1)    -BER Support
        "
      ::= { hw10GEOpticsModuleInformationEntry 75 }

    hw10GEOpticsMDEnhancedOptions OBJECT-TYPE
      SYNTAX INTEGER
        {
          cmu(0),
          rateSelect(2),
          fec(4),
          vpsby(8),
          rxLOS(16),
          txFault(32),
          txDisable(64),
          alarmFLGIM(128),
          invalid(-1)
        }
      MAX-ACCESS read-only
      STATUS current
      DESCRIPTION
        "Indicate enhanced Options.
         Options:
         1. cmu(0)            -enhanced options is cmu
         2. rateSelect(2)     -enhanced options is rateSelect
         3. fec(4)            -enhanced options is fec
         4. vpsby(8)          -enhanced options is vpsby
         5. rxLOS(16)         -enhanced options is rxLOS
         6. txFault(32)       -enhanced options is txFault
         7. txDisable(64)     -enhanced options is txDisable
         8. alarmFLGIM(128)   -enhanced options is alarmFLGIM
         9. invalid(-1)		  -invalid value
         "
      ::= { hw10GEOpticsModuleInformationEntry 76 }

    hw10GEOpticsMDAuxInputOne OBJECT-TYPE
      SYNTAX INTEGER
        {
          auxInputType1(0),
          auxInputType2(1),
          auxInputType4(3),
          auxInputType5(4),
          auxInputType6(5),
          auxInputType7(6),
          auxInputType8(7),
          auxInputType9(8),
          auxInputType10(9),
          auxInputType11(10),
          auxInputType14(13),
          auxInputType15(14),
          auxInputType16(15),
          invalid(-1)
        }
      MAX-ACCESS read-only
      STATUS current
      DESCRIPTION
        "Indicate which quantity is monitored by each auxiliary A/D channel one.
         Options:
         1. auxInputType1(0)    -Auxiliary monitoring not implemented
         2. auxInputType2(1)    -APD Bias Voltage
         3. auxInputType4(3)    -TEC Current (mA)
         4. auxInputType5(4)    -Laser Temperature
         5. auxInputType6(5)    -Laser Wavelength
         6. auxInputType7(6)    -+5V Supply Voltage
         7. auxInputType8(7)    -+3.3V Supply Voltage
         8. auxInputType9(8)    -+1.8V Supply Voltage
         9. auxInputType10(9)   --5.2V Supply Voltage
         10. auxInputType11(10) -+5V Supply Current
         11. auxInputType14(13) -+3.3V Supply Current
         12. auxInputType15(14) -+1.8V Supply Current
         13. auxInputType16(15) --5.2V Supply Current
         14. invalid(-1)		-invalid value
        "
      ::= { hw10GEOpticsModuleInformationEntry 77 }

    hw10GEOpticsMDAuxInputTwo OBJECT-TYPE
      SYNTAX INTEGER
        {
          auxInputType1(0),
          auxInputType2(1),
          auxInputType4(3),
          auxInputType5(4),
          auxInputType6(5),
          auxInputType7(6),
          auxInputType8(7),
          auxInputType9(8),
          auxInputType10(9),
          auxInputType11(10),
          auxInputType14(13),
          auxInputType15(14),
          auxInputType16(15),
          invalid(-1)
        }
      MAX-ACCESS read-only
      STATUS current
      DESCRIPTION
        "Indicate which quantity is monitored by each auxiliary A/D channel two.
         Options:
         1. auxInputType1(0)    -Auxiliary monitoring not implemented
         2. auxInputType2(1)    -APD Bias Voltage
         3. auxInputType4(3)    -TEC Current (mA)
         4. auxInputType5(4)    -Laser Temperature
         5. auxInputType6(5)    -Laser Wavelength
         6. auxInputType7(6)    -+5V Supply Voltage
         7. auxInputType8(7)    -+3.3V Supply Voltage
         8. auxInputType9(8)    -+1.8V Supply Voltage
         9. auxInputType10(9)   --5.2V Supply Voltage
         10. auxInputType11(10) -+5V Supply Current
         11. auxInputType14(13) -+3.3V Supply Current
         12. auxInputType15(14) -+1.8V Supply Current
         13. auxInputType16(15) --5.2V Supply Current
         14. invalid(-1)		-invalid value
        "
      ::= { hw10GEOpticsModuleInformationEntry 78 }

    hw10GEOpticsMDCCEXT OBJECT-TYPE
      SYNTAX Integer32
      MAX-ACCESS read-only
      STATUS current
      DESCRIPTION
        " CC_EXT "
      ::= { hw10GEOpticsModuleInformationEntry 79 }

    hw10GEOpticsMDVendorSpecific OBJECT-TYPE
      SYNTAX OCTET STRING (SIZE (0..140))
      MAX-ACCESS read-only
      STATUS current
      DESCRIPTION
        "Vendor of 10GE Optical module specific information."
      ::= { hw10GEOpticsModuleInformationEntry 80 }


    hwOpticsDdmInformationTable OBJECT-TYPE
      SYNTAX SEQUENCE OF HwOpticsDdmInformationEntry
      MAX-ACCESS not-accessible
      STATUS current
      DESCRIPTION
        "Indicates the optical module diagnose information table of an Ethernet port.
         It is used for querying the diagnose information about the optical module of
         an Ethernet port.
         The index of this table is ifindex.
         "
      ::= { hwOpticsModuleInformation 4 }

    hwOpticsDdmInformationEntry OBJECT-TYPE
      SYNTAX HwOpticsDdmInformationEntry
      MAX-ACCESS not-accessible
      STATUS current
      DESCRIPTION
        "Indicates the optical module diagnose information table of an Ethernet port.
         It is used for querying the diagnose information about the optical module of
         an Ethernet port.
         The index of this entry is ifindex.
         "
      INDEX { ifIndex }
      ::= { hwOpticsDdmInformationTable 1 }

    HwOpticsDdmInformationEntry ::=
      SEQUENCE {
        hwOpticsTemperature
          Integer32,
        hwOpticsSupplyVoltage
          Integer32,
        hwOpticsTxBiasCurrent
          Integer32,
        hwOpticsTxPower
          Integer32,
        hwOpticsRxPower
          Integer32,
        hwOpticsMDDdmInfoRemote
          INTEGER,
        hwOpticsLaserTemperature
          Integer32,
        hwOpticsWaveLength
          Integer32,
        hwOpticsTecCurrent
          Integer32
       }

     hwOpticsTemperature OBJECT-TYPE
      SYNTAX Integer32
      UNITS "0.000001C"
      MAX-ACCESS read-only
      STATUS current
      DESCRIPTION
        "Temperature.
         Invalid value: 2147483647, an invalid value is returned if the optical module is unavailable or is not supported.
         Unit: 0.000001C
        "
      ::= { hwOpticsDdmInformationEntry 1 }

    hwOpticsSupplyVoltage OBJECT-TYPE
      SYNTAX Integer32
      UNITS "0.000001V"
      MAX-ACCESS read-only
      STATUS current
      DESCRIPTION
        "Supply voltage.
         Invalid value: 2147483647, an invalid value is returned if the optical module is unavailable or is not supported.
         Unit: 0.000001V
        "
      ::= { hwOpticsDdmInformationEntry 2 }

    hwOpticsTxBiasCurrent OBJECT-TYPE
      SYNTAX Integer32
      UNITS "0.000001mA"
      MAX-ACCESS read-only
      STATUS current
      DESCRIPTION
        "Transmitted bias current.
         Invalid value: 2147483647, an invalid value is returned if the optical module is unavailable or is not supported.
         Unit: 0.000001mA
        "
      ::= { hwOpticsDdmInformationEntry 3 }

    hwOpticsTxPower OBJECT-TYPE
      SYNTAX Integer32
      UNITS "0.000001dBm"
      MAX-ACCESS read-only
      STATUS current
      DESCRIPTION
        "Transmitted power.
         Invalid value: 2147483647, an invalid value is returned if the optical module is unavailable or is not supported.
         Unit: 0.000001dBm
        "
      ::= { hwOpticsDdmInformationEntry 4 }

    hwOpticsRxPower OBJECT-TYPE
      SYNTAX Integer32
      UNITS "0.000001dBm"
      MAX-ACCESS read-only
      STATUS current
      DESCRIPTION
        "Received power.
         Invalid value: 2147483647, an invalid value is returned if the optical module is unavailable or is not supported.
         Unit: 0.000001dBm
        "
      ::= { hwOpticsDdmInformationEntry 5 }

    hwOpticsMDDdmInfoRemote OBJECT-TYPE
      SYNTAX INTEGER
        {
        remote(1),
        invalid(-1)
        }
      MAX-ACCESS read-only
      STATUS current
      DESCRIPTION
        "Indicates the operation is performed on a remote optical module.
         Options:
         1. remote(1)        -the operation is performed on a remote optical module
         2. invalid(-1)      -invalid value
        "
      ::= { hwOpticsDdmInformationEntry 6 }

    hwOpticsLaserTemperature OBJECT-TYPE
      SYNTAX Integer32
      UNITS "0.000001C"
      MAX-ACCESS read-only
      STATUS current
      DESCRIPTION
        "Temperature of the optical laser.
         Invalid value: 2147483647, returned if the optical module is unavailable or not supported.
         Unit: 0.000001C
        "
      ::= { hwOpticsDdmInformationEntry 7 }

    hwOpticsWaveLength OBJECT-TYPE
      SYNTAX Integer32
      UNITS "0.01nm"
      MAX-ACCESS read-only
      STATUS current
      DESCRIPTION
        "Wavelength of the optical laser.
         Invalid value: 2147483647, returned if the optical module is unavailable or not supported.
         Unit: 0.01nm
        "
      ::= { hwOpticsDdmInformationEntry 8 }

    hwOpticsTecCurrent OBJECT-TYPE
      SYNTAX Integer32
      UNITS "0.000001A"
      MAX-ACCESS read-only
      STATUS current
      DESCRIPTION
        "Current of the thermoelectric cooler on the optical module.
         Invalid value: 2147483647, returned if the optical module is unavailable or not supported.
         Unit: 0.000001A
        "
      ::= { hwOpticsDdmInformationEntry 9 }

    hwOpticsPowerThresholdTable OBJECT-TYPE
      SYNTAX SEQUENCE OF HwOpticsPowerThresholdEntry
      MAX-ACCESS not-accessible
      STATUS current
      DESCRIPTION
        "Indicates the optical power threshold table of an Ethernet port.
         It is used for querying, setting, and clearing the optical power threshold of an Ethernet port.
         After the power threshold is set, the power threshold alarming function of the optical port is enabled.
         When the optical power is lower than the lower threshold or higher than the upper threshold, an alarm is reported.
         The index of this table is ifindex.
         "
      ::= { hwOpticsModuleInformation 5 }

    hwOpticsPowerThresholdEntry OBJECT-TYPE
      SYNTAX HwOpticsPowerThresholdEntry
      MAX-ACCESS not-accessible
      STATUS current
      DESCRIPTION
        "Indicates the optical power threshold table of an Ethernet port.
         It is used for querying, setting, and clearing the optical power threshold of an Ethernet port.
         After the power threshold is set, the power threshold alarming function of the optical port is enabled.
         When the optical power is lower than the lower threshold or higher than the upper threshold, an alarm is reported.
         The index of this entry is ifindex.
         "
      INDEX { ifIndex }
      ::= { hwOpticsPowerThresholdTable 1 }

    HwOpticsPowerThresholdEntry ::=
      SEQUENCE {
        hwOpticsPowerTxLowerThresholdValue
          Integer32,
        hwOpticsPowerThresholdSwitch
          INTEGER,
        hwOpticsPowerTxUpperThresholdValue
          Integer32,
        hwOpticsPowerRxUpperThresholdValue
          Integer32,
        hwOpticsPowerRxLowerThresholdValue
          Integer32,
        hwOpticsTemperatureLowerThresholdValue
          Integer32,
        hwOpticsTemperatureUpperThresholdValue
          Integer32,
        hwOpticsTemperatureThresholdSwitch
          INTEGER,
        hwOpticsVoltageLowerThresholdValue
          Integer32,
        hwOpticsVoltageUpperThresholdValue
          Integer32,
        hwOpticsVoltageThresholdSwitch
          INTEGER,
        hwOpticsCurrentLowerThresholdValue
          Integer32,
        hwOpticsCurrentUpperThresholdValue
          Integer32,
        hwOpticsCurrentThresholdSwitch
          INTEGER,
        hwOpticsLaserTemperatureLowerThresholdValue
          Integer32,
        hwOpticsLaserTemperatureUpperThresholdValue
          Integer32,
        hwOpticsLaserTemperatureThresholdSwitch
          INTEGER,
        hwOpticsWaveLengthLowerThresholdValue
          Integer32,
        hwOpticsWaveLengthUpperThresholdValue
          Integer32,
        hwOpticsWaveLengthThresholdSwitch
          INTEGER,
        hwOpticsTecCurrentLowerThresholdValue
          Integer32,
        hwOpticsTecCurrentUpperThresholdValue
          Integer32,
        hwOpticsTecCurrentThresholdSwitch
          INTEGER
       }

    hwOpticsPowerTxLowerThresholdValue OBJECT-TYPE
      SYNTAX Integer32 (-99000000..100000000 | 2147483646 | 2147483647)
      UNITS "0.000001dBm"
      MAX-ACCESS read-write
      STATUS current
      DESCRIPTION
        "TX optical power lower limit threshold value.
         Options:
         1. -99000000..100000000 -valid range of optical power lower limit threshold value.
         2. 2147483646           -indication the optical module built-in alarm detection threshold.
         3. 2147483647           -invalid value, an invalid value is returned if the threshold is not configured.
         Unit: 0.000001dBm
        "
      ::= { hwOpticsPowerThresholdEntry 1 }

    hwOpticsPowerThresholdSwitch OBJECT-TYPE
      SYNTAX INTEGER
        {
        on(1),
        off(2),
        invalid(-1)
        }
      MAX-ACCESS read-write
      STATUS current
      DESCRIPTION
        "Optical power threshold value Switch.
         Options:
         1. on(1)       -set optical power threshold value
         2. off(2)      -clear optical power threshold value
         3. invalid(-1) -invalid value
         Default: off(2)
        "
      DEFVAL { off }
      ::= { hwOpticsPowerThresholdEntry 2 }

    hwOpticsPowerTxUpperThresholdValue OBJECT-TYPE
      SYNTAX Integer32 (-99000000..100000000 | 2147483646 | 2147483647)
      UNITS "0.000001dBm"
      MAX-ACCESS read-write
      STATUS current
      DESCRIPTION
        "TX optical power upper limit threshold value.
         1. -99000000..100000000 -valid range of optical power upper limit threshold value.
         2. 2147483646           -indication the optical module built-in alarm detection threshold.
         3. 2147483647           -invalid value, an invalid value is returned if the threshold is not configured.
         Unit: 0.000001dBm
        "
      ::= { hwOpticsPowerThresholdEntry 3 }

    hwOpticsPowerRxUpperThresholdValue OBJECT-TYPE
      SYNTAX Integer32 (-99000000..100000000 | 2147483646 | 2147483647)
      UNITS "0.000001dBm"
      MAX-ACCESS read-write
      STATUS current
      DESCRIPTION
        "RX optical power upper limit threshold value.
         1. -99000000..100000000 -valid range of optical power upper limit threshold value.
         2. 2147483646           -indication the optical module built-in alarm detection threshold.
         3. 2147483647           -invalid value, an invalid value is returned if the threshold is not configured.
         Unit: 0.000001dBm
        "
      ::= { hwOpticsPowerThresholdEntry 4 }

    hwOpticsPowerRxLowerThresholdValue OBJECT-TYPE
      SYNTAX Integer32 (-99000000..100000000 | 2147483646 | 2147483647)
      UNITS "0.000001dBm"
      MAX-ACCESS read-write
      STATUS current
      DESCRIPTION
        "RX optical power lower limit threshold value.
         1. -99000000..100000000 -valid range of optical power lower limit threshold value.
         2. 2147483646           -indication the optical module built-in alarm detection threshold.
         3. 2147483647           -invalid value, an invalid value is returned if the threshold is not configured.
         Unit: 0.000001dBm
        "
      ::= { hwOpticsPowerThresholdEntry 5 }

    hwOpticsTemperatureLowerThresholdValue OBJECT-TYPE
      SYNTAX Integer32 (-99000000..300000000 | 2147483646 | 2147483647)
      UNITS "0.000001C"
      MAX-ACCESS read-write
      STATUS current
      DESCRIPTION
        "Optical temperature lower limit threshold value.
         1. -99000000..300000000 -valid range of optical temperature lower limit threshold value.
         2. 2147483646           -indication the optical module built-in alarm detection threshold.
         3. 2147483647           -invalid value, an invalid value is returned if the threshold is not configured.
         Unit: 0.000001C
        "
      ::= { hwOpticsPowerThresholdEntry 6 }

    hwOpticsTemperatureUpperThresholdValue OBJECT-TYPE
      SYNTAX Integer32 (-99000000..300000000 | 2147483646 | 2147483647)
      UNITS "0.000001C"
      MAX-ACCESS read-write
      STATUS current
      DESCRIPTION
        "Optical temperature upper limit threshold value.
         1. -99000000..300000000 -valid range of optical temperature upper limit threshold value.
         2. 2147483646           -indication the optical module built-in alarm detection threshold.
         3. 2147483647           -invalid value, an invalid value is returned if the threshold is not configured.
         Unit: 0.000001C
        "
      ::= { hwOpticsPowerThresholdEntry 7 }

    hwOpticsTemperatureThresholdSwitch OBJECT-TYPE
      SYNTAX INTEGER
        {
        on(1),
        off(2),
        invalid(-1)
        }
      MAX-ACCESS read-write
      STATUS current
      DESCRIPTION
        "Optical temperature threshold value Switch.
         Options:
         1. on(1)       -set optical temparature threshold value
         2. off(2)      -clear optical temperature threshold value
         3. invalid(-1) -invalid value
         Default: off(2)
        "
      DEFVAL { off }
      ::= { hwOpticsPowerThresholdEntry 8 }


    hwOpticsVoltageLowerThresholdValue OBJECT-TYPE
      SYNTAX Integer32 (0..100000000 | 2147483646 | 2147483647)
      UNITS "0.000001V"
      MAX-ACCESS read-write
      STATUS current
      DESCRIPTION
        "Optical voltage lower limit threshold value.
         1. 0..100000000         -valid range of optical voltage lower limit threshold value.
         2. 2147483646           -indication the optical module built-in alarm detection threshold.
         3. 2147483647           -invalid value, an invalid value is returned if the threshold is not configured.
         Unit: 0.000001V
        "
      ::= { hwOpticsPowerThresholdEntry 9 }

    hwOpticsVoltageUpperThresholdValue OBJECT-TYPE
      SYNTAX Integer32 (0..100000000 | 2147483646 | 2147483647)
      UNITS "0.000001V"
      MAX-ACCESS read-write
      STATUS current
      DESCRIPTION
        "Optical voltage upper limit threshold value.
         1. 0..100000000         -valid range of optical voltage upper limit threshold value.
         2. 2147483646           -indication the optical module built-in alarm detection threshold.
         3. 2147483647           -invalid value, an invalid value is returned if the threshold is not configured.
         Unit: 0.000001V
        "
      ::= { hwOpticsPowerThresholdEntry 10 }

    hwOpticsVoltageThresholdSwitch OBJECT-TYPE
      SYNTAX INTEGER
        {
        on(1),
        off(2),
        invalid(-1)
        }
      MAX-ACCESS read-write
      STATUS current
      DESCRIPTION
        "Optical voltage threshold value Switch.
         Options:
         1. on(1)       -set optical voltage threshold value
         2. off(2)      -clear optical voltage threshold value
         3. invalid(-1) -invalid value
         Default: off(2)
        "
      DEFVAL { off }
      ::= { hwOpticsPowerThresholdEntry 11 }

    hwOpticsCurrentLowerThresholdValue OBJECT-TYPE
      SYNTAX Integer32 (0..10000000 | 2147483646 | 2147483647)
      UNITS "0.000001A"
      MAX-ACCESS read-write
      STATUS current
      DESCRIPTION
        "Optical current lower limit threshold value.
         1. 0..10000000          -valid range of optical current lower limit threshold value.
         2. 2147483646           -indication the optical module built-in alarm detection threshold.
         3. 2147483647           -invalid value, an invalid value is returned if the threshold is not configured.
         Unit: 0.000001A
        "
      ::= { hwOpticsPowerThresholdEntry 12 }

    hwOpticsCurrentUpperThresholdValue OBJECT-TYPE
      SYNTAX Integer32 (0..10000000 | 2147483646 | 2147483647)
      UNITS "0.000001A"
      MAX-ACCESS read-write
      STATUS current
      DESCRIPTION
        "Optical current upper limit threshold value.
         1. 0..10000000          -valid range of optical current upper limit threshold value.
         2. 2147483646           -indication the optical module built-in alarm detection threshold.
         3. 2147483647           -invalid value, an invalid value is returned if the threshold is not configured.
         Unit: 0.000001A
        "
      ::= { hwOpticsPowerThresholdEntry 13 }

    hwOpticsCurrentThresholdSwitch OBJECT-TYPE
      SYNTAX INTEGER
        {
        on(1),
        off(2),
        invalid(-1)
        }
      MAX-ACCESS read-write
      STATUS current
      DESCRIPTION
        "Optical current threshold value Switch.
         Options:
         1. on(1)       -set optical current threshold value
         2. off(2)      -clear optical current threshold value
         3. invalid(-1) -invalid value
         Default: off(2)
        "
      DEFVAL { off }
      ::= { hwOpticsPowerThresholdEntry 14 }

    hwOpticsLaserTemperatureLowerThresholdValue OBJECT-TYPE
      SYNTAX Integer32 (-99000000..300000000 | 2147483646 | 2147483647)
      UNITS "0.000001C"
      MAX-ACCESS read-write
      STATUS current
      DESCRIPTION
        "Lower optical laser temperature threshold.
         1. -99000000..300000000 -valid range of the lower optical laser temperature threshold.
         2. 2147483646           -indication the optical module built-in alarm detection threshold.
         3. 2147483647           -invalid value, returned if the threshold is not configured.
         Unit: 0.000001C
        "
      ::= { hwOpticsPowerThresholdEntry 15 }

    hwOpticsLaserTemperatureUpperThresholdValue OBJECT-TYPE
      SYNTAX Integer32 (-99000000..300000000 | 2147483646 | 2147483647)
      UNITS "0.000001C"
      MAX-ACCESS read-write
      STATUS current
      DESCRIPTION
        "Upper optical laser temperature threshold.
         1. -99000000..300000000 -valid range of the upper optical laser temperature threshold.
         2. 2147483646           -indication the optical module built-in alarm detection threshold.
         3. 2147483647           -invalid value, returned if the threshold is not configured.
         Unit: 0.000001C
        "
      ::= { hwOpticsPowerThresholdEntry 16 }

    hwOpticsLaserTemperatureThresholdSwitch OBJECT-TYPE
      SYNTAX INTEGER
        {
        on(1),
        off(2),
        invalid(-1)
        }
      MAX-ACCESS read-write
      STATUS current
      DESCRIPTION
        "Switch of optical laser temperature thresholds.
         Options:
         1. on(1)       -Set optical laser temperature thresholds.
         2. off(2)      -Clear optical laser temperature thresholds.
         3. invalid(-1) -invalid value
         Default: off(2)
        "
      DEFVAL { off }
      ::= { hwOpticsPowerThresholdEntry 17 }

    hwOpticsWaveLengthLowerThresholdValue OBJECT-TYPE
      SYNTAX Integer32 (100000..165600 | 2147483646 | 2147483647)
      UNITS "0.01nm"
      MAX-ACCESS read-write
      STATUS current
      DESCRIPTION
        "Lower optical laser wavelength threshold.
         1. 100000..165600 -valid range of the lower optical laser wavelength threshold.
         2. 2147483646     -indication the optical module built-in alarm detection threshold.
         3. 2147483647     -invalid value, returned if the threshold is not configured.
         Unit: 0.01nm
        "
      ::= { hwOpticsPowerThresholdEntry 18 }

    hwOpticsWaveLengthUpperThresholdValue OBJECT-TYPE
      SYNTAX Integer32 (100000..165600 | 2147483646 | 2147483647)
      UNITS "0.01nm"
      MAX-ACCESS read-write
      STATUS current
      DESCRIPTION
        "Upper optical laser wavelength threshold.
         1. 100000..165600 -valid range of the upper optical laser wavelength threshold.
         2. 2147483646     -indication the optical module built-in alarm detection threshold.
         3. 2147483647     -invalid value, returned if the threshold is not configured.
         Unit: 0.01nm
        "
      ::= { hwOpticsPowerThresholdEntry 19 }

    hwOpticsWaveLengthThresholdSwitch OBJECT-TYPE
      SYNTAX INTEGER
        {
        on(1),
        off(2),
        invalid(-1)
        }
      MAX-ACCESS read-write
      STATUS current
      DESCRIPTION
        "Switch of optical laser wavelength thresholds.
         Options:
         1. on(1)       -Set optical laser wavelength thresholds.
         2. off(2)      -Clear optical laser wavelength thresholds.
         3. invalid(-1) -invalid value
         Default: off(2)
        "
      DEFVAL { off }
      ::= { hwOpticsPowerThresholdEntry 20 }

    hwOpticsTecCurrentLowerThresholdValue OBJECT-TYPE
      SYNTAX Integer32 (-10000000..10000000 | 2147483646 | 2147483647)
      UNITS "0.000001A"
      MAX-ACCESS read-write
      STATUS current
      DESCRIPTION
        "Lower threshold for the thermoelectric cooler current.
         1. -10000000-10000000 -valid range of the lower threshold for the thermoelectric cooler current.
         2. 2147483646         -indication the optical module built-in alarm detection threshold.
         3. 2147483647         -invalid value, returned if the threshold is not configured.
         Unit: 0.000001A
        "
      ::= { hwOpticsPowerThresholdEntry 21 }

    hwOpticsTecCurrentUpperThresholdValue OBJECT-TYPE
      SYNTAX Integer32 (-10000000..10000000 | 2147483646 | 2147483647)
      UNITS "0.000001A"
      MAX-ACCESS read-write
      STATUS current
      DESCRIPTION
        "Upper threshold for the thermoelectric cooler current.
         1. -10000000-10000000 -valid range of the upper threshold for the thermoelectric cooler current.
         2. 2147483646         -indication the optical module built-in alarm detection threshold.
         3. 2147483647         -invalid value, returned if the threshold is not configured.
         Unit: 0.000001A
        "
      ::= { hwOpticsPowerThresholdEntry 22 }

    hwOpticsTecCurrentThresholdSwitch OBJECT-TYPE
      SYNTAX INTEGER
        {
        on(1),
        off(2),
        invalid(-1)
        }
      MAX-ACCESS read-write
      STATUS current
      DESCRIPTION
        "Switch of thermoelectric cooler current thresholds.
         Options:
         1. on(1)       -Set thermoelectric cooler current thresholds.
         2. off(2)      -Clear thermoelectric cooler current thresholds.
         3. invalid(-1) -invalid value
         Default: off(2)
        "
      DEFVAL { off }
      ::= { hwOpticsPowerThresholdEntry 23 }

    hwOpticsModuleTraps OBJECT IDENTIFIER ::= { hwOpticsModuleInformation 6 }

    hwOpticsCommonTraps OBJECT IDENTIFIER ::= { hwOpticsModuleTraps 1 }
    hwOpticsCommonTrapsPrefix OBJECT IDENTIFIER ::= { hwOpticsCommonTraps 0 }

    hwOpticsAlarmTraps  OBJECT IDENTIFIER ::= { hwOpticsModuleTraps 2 }
    hwOpticsAlarmTrapsPrefix  OBJECT IDENTIFIER ::= { hwOpticsAlarmTraps 0 }

    hwOpticsTransceiverFaultyAlarmTrap NOTIFICATION-TYPE
      OBJECTS
        {
        hwFrameIndex,
        hwSlotIndex,
        hwPortIndex
        }
      STATUS current
      DESCRIPTION
        "This trap will send when the optical transceiver is faulty."
      ::= { hwOpticsAlarmTraps 0 1 }

    hwOpticsPowerOutOfRangeAlarmTrap NOTIFICATION-TYPE
      OBJECTS
        {
        hwFrameIndex,
        hwSlotIndex,
        hwPortIndex,
        hwOpticsTxPower
        }
      STATUS current
      DESCRIPTION
         "This trap will send when the Tx power of the Ethernet optical port is out of the range."
      ::= { hwOpticsAlarmTraps 0 2 }

    hwOpticsPortTemperatureHighAlarmTrap NOTIFICATION-TYPE
      OBJECTS
        {
        hwFrameIndex,
        hwSlotIndex,
        hwPortIndex,
        hwOpticsTemperature
        }
      STATUS current
      DESCRIPTION
        "This trap will send when the temperature of the Ethernet optical port is too high."
      ::= { hwOpticsAlarmTraps 0 3 }

    hwOpticsTransceiverNormalAlarmTrap NOTIFICATION-TYPE
      OBJECTS
        {
        hwFrameIndex,
        hwSlotIndex,
        hwPortIndex
        }
      STATUS current
      DESCRIPTION
        "This trap will send when the optical transceiver is normal."
      ::= { hwOpticsAlarmTraps 0 4 }

    hwOpticsSmartSFPExtModuleInformationTable OBJECT-TYPE
      SYNTAX SEQUENCE OF HwOpticsSmartSFPExtModuleInformationEntry
      MAX-ACCESS not-accessible
      STATUS current
      DESCRIPTION
        "Indicates the extended information table of a smart SFP optical module.
         It is used for querying the extend information about a smart SFP optical module and setting loopback of a smart SFP optical module.
         This operation can be performed on both local and remote optical modules.
         When this operation is performed on a remote optical module, the hwOpticsSmartSFPExtModuleInfoRemote leaf is required.
         The index of this table is ifIndex.
         "
      ::= { hwOpticsModuleInformation 7 }

    hwOpticsSmartSFPExtModuleInformationEntry OBJECT-TYPE
      SYNTAX HwOpticsSmartSFPExtModuleInformationEntry
      MAX-ACCESS not-accessible
      STATUS current
      DESCRIPTION
        "Indicates the extended information table of a smart SFP optical module.
         It is used for querying the extend information about a smart SFP optical module and setting loopback of a smart SFP optical module.
         This operation can be performed on both local and remote optical modules.
         When this operation is performed on a remote optical module, the hwOpticsSmartSFPExtModuleInfoRemote leaf is required.
         The index of this entry is ifIndex.
         "
      INDEX { ifIndex }
      ::= { hwOpticsSmartSFPExtModuleInformationTable 1 }

    HwOpticsSmartSFPExtModuleInformationEntry ::=
      SEQUENCE {
        hwOpticsSmartSFPIdentifier
          INTEGER,
        hwOpticsSmartSFPProtocolVersion
          Integer32,
        hwOpticsSmartSFPSSFPEnhancedOption
          Integer32,
        hwOpticsSmartSFPPassword
          Unsigned32,
        hwOpticsSmartSFPRemoteControllable
          INTEGER,
        hwOpticsSmartSFPSubCarrierControl
          INTEGER,
        hwOpticsSmartSFPSubCarrierlinkStatus
          INTEGER,
        hwOpticsSmartSFPLocalLoopback
          INTEGER,
        hwOpticsSmartSFPRemoteLoopback
          INTEGER,
        hwOpticsSmartSFPDyingGaspStatus
          INTEGER,
        hwOpticsSmartSFPLocalRXOutputControl
          INTEGER,
        hwOpticsSmartSFPPilottoneControl
          INTEGER,
        hwOpticsSmartSFPPilottoneStatus
          INTEGER,
        hwOpticsSmartSFPLoopbackdeviceloss
          Integer32,
        hwOpticsSmartSFPRoundtripfiberloss
          Integer32,
        hwOpticsSmartSFPExtModuleInfoRemote
          INTEGER
       }

    hwOpticsSmartSFPIdentifier OBJECT-TYPE
      SYNTAX INTEGER
        {
        smartSFPI(1),
        smartSFPII(2),
        unknowType(3)
        }
      MAX-ACCESS read-only
      STATUS current
      DESCRIPTION
        "Indicates the type of a smart SFP optical module.
         Options:
         1. smartSFPI(1)             -The optical module is a smart SFP I optical module
         2. smartSFPII(2)            -The optical module is a smart SFP II optical module
         3. unknowType(3)            -Unknown or unspecified type
        "
      ::= { hwOpticsSmartSFPExtModuleInformationEntry 1 }

    hwOpticsSmartSFPProtocolVersion OBJECT-TYPE
      SYNTAX Integer32 (-1 | 0..255)
      MAX-ACCESS read-only
      STATUS current
      DESCRIPTION
        "Indicates the protocol version of a smart SFP optical module.
         Range: -1, 0-255.
         -1 is the invalid value.
        "
      ::= { hwOpticsSmartSFPExtModuleInformationEntry 2 }

    hwOpticsSmartSFPSSFPEnhancedOption OBJECT-TYPE
      SYNTAX Integer32 (-1 | 0..65535)
      MAX-ACCESS read-only
      STATUS current
      DESCRIPTION
        "Indicates the enhanced options of a smart SFP optical module.
         Range: -1, 0-65535.
         -1 is the invalid value.
        "
      ::= { hwOpticsSmartSFPExtModuleInformationEntry 3 }

    hwOpticsSmartSFPPassword OBJECT-TYPE
      SYNTAX Unsigned32
      MAX-ACCESS read-only
      STATUS current
      DESCRIPTION
        "Indicates the password of a smart SFP optical module.
        "
      ::= { hwOpticsSmartSFPExtModuleInformationEntry 4 }

    hwOpticsSmartSFPRemoteControllable OBJECT-TYPE
      SYNTAX INTEGER
        {
        disable(1),
        enable(2),
        invalid(-1)
        }
      MAX-ACCESS read-only
      STATUS current
      DESCRIPTION
        "Indicates whether the remote smart SFP optical module can control the local optical module.
         Options:
         1. disable(1)       -disable, control command from remote optical module will be ignored
         2. enable(2)        -enable
         3. invalid(-1)      -invalid value
        "
      ::= { hwOpticsSmartSFPExtModuleInformationEntry 5 }

    hwOpticsSmartSFPSubCarrierControl OBJECT-TYPE
      SYNTAX INTEGER
        {
        disable(1),
        enable(2),
        invalid(-1)
        }
      MAX-ACCESS read-only
      STATUS current
      DESCRIPTION
        "Indicates sub-carrier control of a smart SFP optical module, that is,
         whether the local smart SFP optical module can send signals to the remote optical module.
         Options:
         1. disable(1)       -disable
         2. enable(2)        -enable
         3. invalid(-1)      -invalid value
        "
      ::= { hwOpticsSmartSFPExtModuleInformationEntry 6 }

    hwOpticsSmartSFPSubCarrierlinkStatus OBJECT-TYPE
      SYNTAX INTEGER
        {
        down(1),
        rxUp(2),
        up(3),
        invalid(-1)
        }
      MAX-ACCESS read-only
      STATUS current
      DESCRIPTION
        "Indicates the sub-carrier status of a smart SFP optical module.
         Options:
         1. down(1)        -linked down
         2. rxUp(2)        -linked up in RX only
         3. up(3)          -linked up in both RX and TX direction
         4. invalid(-1)    -invalid value
        "
      ::= { hwOpticsSmartSFPExtModuleInformationEntry 7 }

    hwOpticsSmartSFPLocalLoopback OBJECT-TYPE
      SYNTAX INTEGER
        {
        noloop(1),
        remote(2),
        local(3),
        invalid(-1)
        }
      MAX-ACCESS read-write
      STATUS current
      DESCRIPTION
        "Indicates the loopback control of a local smart SFP optical module.
         Options:
         1. noloop(1)      -no loop
         2. remote(2)      -local outward loop back
         3. local(3)       -local inward loop back
         4. invalid(-1)    -invalid value
        "
      ::= { hwOpticsSmartSFPExtModuleInformationEntry 8 }

    hwOpticsSmartSFPRemoteLoopback OBJECT-TYPE
      SYNTAX INTEGER
        {
        noloop(1),
        remote(2),
        invalid(-1)
        }
      MAX-ACCESS read-write
      STATUS current
      DESCRIPTION
        "Indicates the loopback control of a remote smart SFP optical module.
         Options:
         1. noloop(1)      -no loop
         2. remote(2)      -remote outward loop back
         3. invalid(-1)    -invalid value
        "
      ::= { hwOpticsSmartSFPExtModuleInformationEntry 9 }

    hwOpticsSmartSFPDyingGaspStatus OBJECT-TYPE
      SYNTAX INTEGER
        {
        poweron(1),
        poweroff(2),
        invalid(-1)
        }
      MAX-ACCESS read-write
      STATUS current
      DESCRIPTION
        "Indicates the dying-gasp status of a remote smart SFP optical module.
         Options:
         1. poweron(1)     -remote normal power
         2. poweroff(2)    -remote Dying-Gasp asserted
         3. invalid(-1)    -invalid value
        "
      ::= { hwOpticsSmartSFPExtModuleInformationEntry 10 }

    hwOpticsSmartSFPLocalRXOutputControl OBJECT-TYPE
      SYNTAX INTEGER
        {
        disable(1),
        enable(2),
        disableRxLos(3),
        invalid(-1)
        }
      MAX-ACCESS read-write
      STATUS current
      DESCRIPTION
        "Indicates the local output control of a smart SFP optical module.
         Options:
         1. disable(1)        -disable
         2. enable(2)         -enable
         3. disableRxLos(3)   -disable when LOS asserted
         4. invalid(-1)       -invalid value
        "
      ::= { hwOpticsSmartSFPExtModuleInformationEntry 11 }

    hwOpticsSmartSFPPilottoneControl OBJECT-TYPE
      SYNTAX INTEGER
        {
        disable(1),
        enable(2),
        invalid(-1)
        }
      MAX-ACCESS read-write
      STATUS current
      DESCRIPTION
        "Indicates control of outputting attenuation signals by a smart SFP optical module.
         Options:
         1. disable(1)        -disable
         2. enable(2)         -enable
         3. invalid(-1)       -invalid value
        "
      ::= { hwOpticsSmartSFPExtModuleInformationEntry 12 }

    hwOpticsSmartSFPPilottoneStatus OBJECT-TYPE
      SYNTAX INTEGER
        {
        noSignal(1),
        toneDetected(2),
        invalid(-1)
        }
      MAX-ACCESS read-write
      STATUS current
      DESCRIPTION
        "Indicates the carrier loopback detection status of a smart SFP optical module.
         Options:
         1. noSignal(1)         -no signal
         2. toneDetected(2)     -tone detected
         3. invalid(-1)         -invalid value
        "
      ::= { hwOpticsSmartSFPExtModuleInformationEntry 13 }

    hwOpticsSmartSFPLoopbackdeviceloss OBJECT-TYPE
      SYNTAX Integer32 (-1 | 0..25500)
      UNITS "0.01db"
      MAX-ACCESS read-only
      STATUS current
      DESCRIPTION
        "Indicates the optical attenuation of a remote loopback device.
         Range: -1, 0-25500.
         -1 is the invalid value.
         Unit: 0.01db
        "
      ::= { hwOpticsSmartSFPExtModuleInformationEntry 14 }

    hwOpticsSmartSFPRoundtripfiberloss OBJECT-TYPE
      SYNTAX Integer32 (-1 | 0..25500)
      UNITS "0.01db"
      MAX-ACCESS read-only
      STATUS current
      DESCRIPTION
        "Indicates the optical attenuation of an optical path.
         Range: -1, 0-25500.
         -1 is the invalid value.
         Unit: 0.01db
        "
      ::= { hwOpticsSmartSFPExtModuleInformationEntry 15 }

    hwOpticsSmartSFPExtModuleInfoRemote OBJECT-TYPE
      SYNTAX INTEGER
        {
        remote(1),
        invalid(-1)
        }
      MAX-ACCESS read-only
      STATUS current
      DESCRIPTION
        "Indicates the operation is performed on a remote optical module.
         Options:
         1. remote(1)        -the operation is performed on a remote optical module
         2. invalid(-1)      -invalid value
        "
      ::= { hwOpticsSmartSFPExtModuleInformationEntry 16 }

    hwOpticsSmartSFPConfigTable OBJECT-TYPE
      SYNTAX SEQUENCE OF HwOpticsSmartSFPConfigEntry
      MAX-ACCESS not-accessible
      STATUS current
      DESCRIPTION
        "Indicates the configured parameter table of a smart SFP optical module.
         It is used for querying and setting the configured parameters of a smart SFP optical module.
         This table supports only the smart SFP 2 optical module.
         The index of this table is ifIndex.
         "
      ::= { hwOpticsModuleInformation 8 }

    hwOpticsSmartSFPConfigEntry OBJECT-TYPE
      SYNTAX HwOpticsSmartSFPConfigEntry
      MAX-ACCESS not-accessible
      STATUS current
      DESCRIPTION
        "Indicates the configured parameter table of a smart SFP optical module.
         It is used for querying and setting the configured parameters of a smart SFP optical module.
         This table supports only the smart SFP 2 optical module.
         The index of this entry is ifIndex.
         "
      INDEX { ifIndex }
      ::= { hwOpticsSmartSFPConfigTable 1 }

    HwOpticsSmartSFPConfigEntry ::=
      SEQUENCE {
        hwOpticsSmartSFPIILoopOpticloss
          Integer32
       }

    hwOpticsSmartSFPIILoopOpticloss OBJECT-TYPE
      SYNTAX Integer32 (-1 | 0..25500)
      UNITS "0.01db"
      MAX-ACCESS read-write
      STATUS current
      DESCRIPTION
        "Indicates the optical attenuation of a remote loopback device.
         Unit: 0.01db.
         Range: -1, 0-25500.
         -1 is the invalid value.
         Default: 1400.
        "
      ::= { hwOpticsSmartSFPConfigEntry 1 }

    hwOpticsModuleThresholdTable OBJECT-TYPE
      SYNTAX SEQUENCE OF HwOpticsModuleThresholdEntry
      MAX-ACCESS not-accessible
      STATUS current
      DESCRIPTION
        "It is used for querying the default value of optical power and parameter
         threshold of an Ethernet port.
         The index of this table is ifindex."
      ::= { hwOpticsModuleInformation 9 }

    hwOpticsModuleThresholdEntry OBJECT-TYPE
      SYNTAX HwOpticsModuleThresholdEntry
      MAX-ACCESS not-accessible
      STATUS current
      DESCRIPTION
        "It is used for querying the default value of optical power and parameter
         threshold of an Ethernet port.
         The index of this entry is ifindex."
      INDEX { ifIndex }
      ::= { hwOpticsModuleThresholdTable 1 }

    HwOpticsModuleThresholdEntry ::=
      SEQUENCE {
        hwOpticsModuleThresholdTxLower
          Integer32,
        hwOpticsModuleThresholdTxUpper
          Integer32,
        hwOpticsModuleThresholdRxUpper
          Integer32,
        hwOpticsModuleThresholdRxLower
          Integer32,
        hwOpticsModuleThresholdTempLower
          Integer32,
        hwOpticsModuleThresholdTempUpper
          Integer32,
        hwOpticsModuleThresholdVoltageLower
          Integer32,
        hwOpticsModuleThresholdVoltageUpper
          Integer32,
        hwOpticsModuleThresholdCurrentLower
          Integer32,
        hwOpticsModuleThresholdCurrentUpper
          Integer32,
        hwOpticsModuleThresholdLaserTempLower
          Integer32,
        hwOpticsModuleThresholdLaserTempUpper
          Integer32,
        hwOpticsModuleThresholdWaveLengthLower
          Integer32,
        hwOpticsModuleThresholdWaveLengthUpper
          Integer32,
        hwOpticsModuleThresholdTecCurrentLower
          Integer32,
        hwOpticsModuleThresholdTecCurrentUpper
          Integer32
       }

    hwOpticsModuleThresholdTxLower OBJECT-TYPE
      SYNTAX Integer32
      UNITS "0.000001dBm"
      MAX-ACCESS read-only
      STATUS current
      DESCRIPTION
        "TX optical power lower limit threshold value.
         1. 2147483647           -invalid value, an invalid value is returned if the threshold is not exist.
         Unit: 0.000001dBm
         "
      ::= { hwOpticsModuleThresholdEntry 1 }

    hwOpticsModuleThresholdTxUpper OBJECT-TYPE
      SYNTAX Integer32
      UNITS "0.000001dBm"
      MAX-ACCESS read-only
      STATUS current
      DESCRIPTION
        "TX optical power upper limit threshold value.
         1. 2147483647           -invalid value, an invalid value is returned if the threshold is not exist.
         Unit: 0.000001dBm
         "
      ::= { hwOpticsModuleThresholdEntry 2 }

    hwOpticsModuleThresholdRxUpper OBJECT-TYPE
      SYNTAX Integer32
      UNITS "0.000001dBm"
      MAX-ACCESS read-only
      STATUS current
      DESCRIPTION
        "RX optical power upper limit threshold value.
         1. 2147483647           -invalid value, an invalid value is returned if the threshold is not exist.
         Unit: 0.000001dBm
         "
      ::= { hwOpticsModuleThresholdEntry 3 }

    hwOpticsModuleThresholdRxLower OBJECT-TYPE
      SYNTAX Integer32
      UNITS "0.000001dBm"
      MAX-ACCESS read-only
      STATUS current
      DESCRIPTION
        "RX optical power lower limit threshold value.
         1. 2147483647           -invalid value, an invalid value is returned if the threshold is not exist.
         Unit: 0.000001dBm
         "
      ::= { hwOpticsModuleThresholdEntry 4 }

    hwOpticsModuleThresholdTempLower OBJECT-TYPE
      SYNTAX Integer32
      UNITS "0.000001C"
      MAX-ACCESS read-only
      STATUS current
      DESCRIPTION
        "Optical temperature lower limit threshold value.
         1. 2147483647           -invalid value, an invalid value is returned if the threshold is not exist.
         Unit: 0.000001C
         "
      ::= { hwOpticsModuleThresholdEntry 5 }

    hwOpticsModuleThresholdTempUpper OBJECT-TYPE
      SYNTAX Integer32
      UNITS "0.000001C"
      MAX-ACCESS read-only
      STATUS current
      DESCRIPTION
        "Optical temperature upper limit threshold value.
         1. 2147483647           -invalid value, an invalid value is returned if the threshold is not exist.
         Unit: 0.000001C
         "
      ::= { hwOpticsModuleThresholdEntry 6 }

    hwOpticsModuleThresholdVoltageLower OBJECT-TYPE
      SYNTAX Integer32
      UNITS "0.000001V"
      MAX-ACCESS read-only
      STATUS current
      DESCRIPTION
        "Optical voltage lower limit threshold value.
         1. 2147483647           -invalid value, an invalid value is returned if the threshold is not exist.
         Unit: 0.000001V
         "
      ::= { hwOpticsModuleThresholdEntry 7 }

    hwOpticsModuleThresholdVoltageUpper OBJECT-TYPE
      SYNTAX Integer32
      UNITS "0.000001V"
      MAX-ACCESS read-only
      STATUS current
      DESCRIPTION
        "Optical voltage upper limit threshold value.
         1. 2147483647           -invalid value, an invalid value is returned if the threshold is not exist.
         Unit: 0.000001V
         "
      ::= { hwOpticsModuleThresholdEntry 8 }

    hwOpticsModuleThresholdCurrentLower OBJECT-TYPE
      SYNTAX Integer32
      UNITS "0.000001A"
      MAX-ACCESS read-only
      STATUS current
      DESCRIPTION
        "Optical current lower limit threshold value.
         1. 2147483647           -invalid value, an invalid value is returned if the threshold is not exist.
         Unit: 0.000001A
         "
      ::= { hwOpticsModuleThresholdEntry 9 }

    hwOpticsModuleThresholdCurrentUpper OBJECT-TYPE
      SYNTAX Integer32
      UNITS "0.000001A"
      MAX-ACCESS read-only
      STATUS current
      DESCRIPTION
        "Optical current upper limit threshold value.
         1. 2147483647           -invalid value, an invalid value is returned if the threshold is not exist.
         Unit: 0.000001A
         "
      ::= { hwOpticsModuleThresholdEntry 10 }

    hwOpticsModuleThresholdLaserTempLower OBJECT-TYPE
      SYNTAX Integer32
      UNITS "0.000001C"
      MAX-ACCESS read-only
      STATUS current
      DESCRIPTION
        "Lower optical laser temperature threshold.
         1. 2147483647           -invalid value, an invalid value is returned if the threshold is not exist.
         Unit: 0.000001C
         "
      ::= { hwOpticsModuleThresholdEntry 11 }

    hwOpticsModuleThresholdLaserTempUpper OBJECT-TYPE
      SYNTAX Integer32
      UNITS "0.000001C"
      MAX-ACCESS read-only
      STATUS current
      DESCRIPTION
        "Upper optical laser temperature threshold.
         1. 2147483647           -invalid value, an invalid value is returned if the threshold is not exist.
         Unit: 0.000001C
         "
      ::= { hwOpticsModuleThresholdEntry 12 }

    hwOpticsModuleThresholdWaveLengthLower OBJECT-TYPE
      SYNTAX Integer32
      UNITS "0.01nm"
      MAX-ACCESS read-only
      STATUS current
      DESCRIPTION
        "Lower optical laser wavelength threshold.
         1. 2147483647           -invalid value, an invalid value is returned if the threshold is not exist.
         Unit: 0.01nm
         "
      ::= { hwOpticsModuleThresholdEntry 13 }

    hwOpticsModuleThresholdWaveLengthUpper OBJECT-TYPE
      SYNTAX Integer32
      UNITS "0.01nm"
      MAX-ACCESS read-only
      STATUS current
      DESCRIPTION
        "Upper optical laser wavelength threshold.
         1. 2147483647           -invalid value, an invalid value is returned if the threshold is not exist.
         Unit: 0.01nm
         "
      ::= { hwOpticsModuleThresholdEntry 14 }

    hwOpticsModuleThresholdTecCurrentLower OBJECT-TYPE
      SYNTAX Integer32
      UNITS "0.000001A"
      MAX-ACCESS read-only
      STATUS current
      DESCRIPTION
        "Lower threshold for the thermoelectric cooler current.
         1. 2147483647           -invalid value, an invalid value is returned if the threshold is not exist.
         Unit: 0.000001A
         "
      ::= { hwOpticsModuleThresholdEntry 15 }

    hwOpticsModuleThresholdTecCurrentUpper OBJECT-TYPE
      SYNTAX Integer32
      UNITS "0.000001A"
      MAX-ACCESS read-only
      STATUS current
      DESCRIPTION
        "Upper threshold for the thermoelectric cooler current.
         1. 2147483647           -invalid value, an invalid value is returned if the threshold is not exist.
         Unit: 0.000001A
         "
      ::= { hwOpticsModuleThresholdEntry 16 }

    hwOpticsChannelDdmInformationTable OBJECT-TYPE
      SYNTAX SEQUENCE OF HwOpticsChannelDdmInformationEntry
      MAX-ACCESS not-accessible
      STATUS current
      DESCRIPTION
        "It is used for querying the optical module channel Ddm Information of an Ethernet port.
         The index of this table are ifIndex and hwOpticsModuleChannelIndex."

      ::= { hwOpticsModuleInformation 10 }

    hwOpticsChannelDdmInformationEntry OBJECT-TYPE
      SYNTAX HwOpticsChannelDdmInformationEntry
      MAX-ACCESS not-accessible
      STATUS current
      DESCRIPTION
        "It is used for querying the optical module channel Ddm Information of an Ethernet port.
         The index of this table are ifindex and hwOpticsModuleChannelIndex."
      INDEX { ifIndex, hwOpticsModuleChannelIndex }
      ::= { hwOpticsChannelDdmInformationTable 1 }

    HwOpticsChannelDdmInformationEntry ::=
      SEQUENCE {
        hwOpticsModuleChannelIndex
          Integer32,
        hwOpticsModuleChannleTxBiasCurrent
          Integer32,
        hwOpticsModuleChannleTxPower
          Integer32,
        hwOpticsModuleChannleRxPower
          Integer32
       }

    hwOpticsModuleChannelIndex OBJECT-TYPE
      SYNTAX Integer32
      MAX-ACCESS not-accessible
      STATUS current
      DESCRIPTION
        "Optical module channel Index. 1~4 for 100G optical module.
        "
      ::= { hwOpticsChannelDdmInformationEntry 1 }

    hwOpticsModuleChannleTxBiasCurrent OBJECT-TYPE
      SYNTAX Integer32
      UNITS "0.000001mA"
      MAX-ACCESS read-only
      STATUS current
      DESCRIPTION
        "Transmitted bias current.
         Invalid value: 2147483647, an invalid value is returned if the optical module is unavailable or is not supported.
         Unit: 0.000001mA
        "
      ::= { hwOpticsChannelDdmInformationEntry 2 }

    hwOpticsModuleChannleTxPower OBJECT-TYPE
      SYNTAX Integer32
      UNITS "0.000001dBm"
      MAX-ACCESS read-only
      STATUS current
      DESCRIPTION
        "Transmitted power.
         Invalid value: 2147483647, an invalid value is returned if the optical module is unavailable or is not supported.
         Unit: 0.000001dBm
        "
      ::= { hwOpticsChannelDdmInformationEntry 3 }

    hwOpticsModuleChannleRxPower OBJECT-TYPE
      SYNTAX Integer32
      UNITS "0.000001dBm"
      MAX-ACCESS read-only
      STATUS current
      DESCRIPTION
        "Received power.
         Invalid value: 2147483647, an invalid value is returned if the optical module is unavailable or is not supported.
         Unit: 0.000001dBm
        "
      ::= { hwOpticsChannelDdmInformationEntry 4 }

  END
