DATAPOWER-CONFIG-MIB DEFINITIONS ::= BEGIN


-- Programmatically Generated; do not edit

-- Licensed Materials - Property of IBM
-- IBM WebSphere DataPower Appliances
-- Copyright IBM Corporation 2007,2017. All Rights Reserved.
-- US Government Users Restricted Rights - Use, duplication or disclosure
-- restricted by GSA ADP Schedule Contract with IBM Corp.

IMPORTS
    enterprises, MODULE-IDENTITY, OBJECT-TYPE,
    Unsigned32
        FROM SNMPv2-SMI
    TEXTUAL-CONVENTION, DisplayString
        FROM SNMPv2-TC;

dpConfigMIB MODULE-IDENTITY
    LAST-UPDATED "200701110000Z"
    ORGANIZATION "IBM Corporation"
    CONTACT-INFO "IBM Corporation, Application Integration and Middleware, DataPower SOA Appliances. Web:
    http://www-306.ibm.com/software/integration/datapower/support/ Email: csupport@us.ibm.com"
    DESCRIPTION "The MIB module for configuration of a DataPower XML device."
    REVISION "200701110000Z"
    DESCRIPTION "Updated"

    ::= { dpModules 2 }

datapower OBJECT IDENTIFIER ::= { enterprises 14685 }

dpModules OBJECT IDENTIFIER ::= { datapower 2 }

dpManagement OBJECT IDENTIFIER ::= { datapower 3 }

dpConfig OBJECT IDENTIFIER ::= { dpManagement 2 }

--

dpConfigDNSNameServiceTable OBJECT-TYPE
    SYNTAX      SEQUENCE OF DPConfigDNSNameServiceEntry
    MAX-ACCESS  not-accessible
    STATUS      current
    DESCRIPTION
        "Configure the DNS name resolution service"

    ::= { dpConfig 1 }

dpConfigDNSNameServiceEntry OBJECT-TYPE
    SYNTAX      DPConfigDNSNameServiceEntry
    MAX-ACCESS  not-accessible
    STATUS      current
    DESCRIPTION "Table row."
    INDEX { dpConfigDNSNameServiceIndex, IMPLIED dpConfigDNSNameServicename }

    ::= { dpConfigDNSNameServiceTable 1 }

DPConfigDNSNameServiceEntry ::= SEQUENCE {
    dpConfigDNSNameServiceIndex    Unsigned32,
    dpConfigDNSNameServicename    DisplayString
}

dpConfigDNSNameServiceIndex OBJECT-TYPE
    SYNTAX      Unsigned32
    MAX-ACCESS  read-only
    STATUS      current
    DESCRIPTION "No description yet."

    ::= { dpConfigDNSNameServiceEntry 1 }

dpConfigDNSNameServicename OBJECT-TYPE
    SYNTAX      DisplayString
    MAX-ACCESS  read-only
    STATUS      current
    DESCRIPTION "No description yet."

    ::= { dpConfigDNSNameServiceEntry 2 }

--

dpConfigEthernetInterfaceTable OBJECT-TYPE
    SYNTAX      SEQUENCE OF DPConfigEthernetInterfaceEntry
    MAX-ACCESS  not-accessible
    STATUS      current
    DESCRIPTION
        "Configure and manage Ethernet interfaces."

    ::= { dpConfig 2 }

dpConfigEthernetInterfaceEntry OBJECT-TYPE
    SYNTAX      DPConfigEthernetInterfaceEntry
    MAX-ACCESS  not-accessible
    STATUS      current
    DESCRIPTION "Table row."
    INDEX { dpConfigEthernetInterfaceIndex, IMPLIED dpConfigEthernetInterfacename }

    ::= { dpConfigEthernetInterfaceTable 1 }

DPConfigEthernetInterfaceEntry ::= SEQUENCE {
    dpConfigEthernetInterfaceIndex    Unsigned32,
    dpConfigEthernetInterfacename    DisplayString
}

dpConfigEthernetInterfaceIndex OBJECT-TYPE
    SYNTAX      Unsigned32
    MAX-ACCESS  read-only
    STATUS      current
    DESCRIPTION "No description yet."

    ::= { dpConfigEthernetInterfaceEntry 1 }

dpConfigEthernetInterfacename OBJECT-TYPE
    SYNTAX      DisplayString
    MAX-ACCESS  read-only
    STATUS      current
    DESCRIPTION "No description yet."

    ::= { dpConfigEthernetInterfaceEntry 2 }

--

dpConfigCRLFetchTable OBJECT-TYPE
    SYNTAX      SEQUENCE OF DPConfigCRLFetchEntry
    MAX-ACCESS  not-accessible
    STATUS      current
    DESCRIPTION "Table."

    ::= { dpConfig 3 }

dpConfigCRLFetchEntry OBJECT-TYPE
    SYNTAX      DPConfigCRLFetchEntry
    MAX-ACCESS  not-accessible
    STATUS      current
    DESCRIPTION "Table row."
    INDEX { dpConfigCRLFetchIndex, IMPLIED dpConfigCRLFetchname }

    ::= { dpConfigCRLFetchTable 1 }

DPConfigCRLFetchEntry ::= SEQUENCE {
    dpConfigCRLFetchIndex    Unsigned32,
    dpConfigCRLFetchname    DisplayString
}

dpConfigCRLFetchIndex OBJECT-TYPE
    SYNTAX      Unsigned32
    MAX-ACCESS  read-only
    STATUS      current
    DESCRIPTION "No description yet."

    ::= { dpConfigCRLFetchEntry 1 }

dpConfigCRLFetchname OBJECT-TYPE
    SYNTAX      DisplayString
    MAX-ACCESS  read-only
    STATUS      current
    DESCRIPTION "No description yet."

    ::= { dpConfigCRLFetchEntry 2 }

--

dpConfigHTTPServiceTable OBJECT-TYPE
    SYNTAX      SEQUENCE OF DPConfigHTTPServiceEntry
    MAX-ACCESS  not-accessible
    STATUS      current
    DESCRIPTION
        "Creates an HTTP server. This server delivers documents stored on the local
        system."

    ::= { dpConfig 4 }

dpConfigHTTPServiceEntry OBJECT-TYPE
    SYNTAX      DPConfigHTTPServiceEntry
    MAX-ACCESS  not-accessible
    STATUS      current
    DESCRIPTION "Table row."
    INDEX { dpConfigHTTPServiceIndex, IMPLIED dpConfigHTTPServicename }

    ::= { dpConfigHTTPServiceTable 1 }

DPConfigHTTPServiceEntry ::= SEQUENCE {
    dpConfigHTTPServiceIndex    Unsigned32,
    dpConfigHTTPServicename    DisplayString
}

dpConfigHTTPServiceIndex OBJECT-TYPE
    SYNTAX      Unsigned32
    MAX-ACCESS  read-only
    STATUS      current
    DESCRIPTION "No description yet."

    ::= { dpConfigHTTPServiceEntry 1 }

dpConfigHTTPServicename OBJECT-TYPE
    SYNTAX      DisplayString
    MAX-ACCESS  read-only
    STATUS      current
    DESCRIPTION "No description yet."

    ::= { dpConfigHTTPServiceEntry 2 }

--

dpConfigStatisticsTable OBJECT-TYPE
    SYNTAX      SEQUENCE OF DPConfigStatisticsEntry
    MAX-ACCESS  not-accessible
    STATUS      current
    DESCRIPTION
        "Use this page to establish Statistics settings. Statistics must be enabled
        for some of the monitors to work correctly."

    ::= { dpConfig 5 }

dpConfigStatisticsEntry OBJECT-TYPE
    SYNTAX      DPConfigStatisticsEntry
    MAX-ACCESS  not-accessible
    STATUS      current
    DESCRIPTION "Table row."
    INDEX { dpConfigStatisticsIndex, IMPLIED dpConfigStatisticsname }

    ::= { dpConfigStatisticsTable 1 }

DPConfigStatisticsEntry ::= SEQUENCE {
    dpConfigStatisticsIndex    Unsigned32,
    dpConfigStatisticsname    DisplayString
}

dpConfigStatisticsIndex OBJECT-TYPE
    SYNTAX      Unsigned32
    MAX-ACCESS  read-only
    STATUS      current
    DESCRIPTION "No description yet."

    ::= { dpConfigStatisticsEntry 1 }

dpConfigStatisticsname OBJECT-TYPE
    SYNTAX      DisplayString
    MAX-ACCESS  read-only
    STATUS      current
    DESCRIPTION "No description yet."

    ::= { dpConfigStatisticsEntry 2 }

--

dpConfigTraceTargetTable OBJECT-TYPE
    SYNTAX      SEQUENCE OF DPConfigTraceTargetEntry
    MAX-ACCESS  not-accessible
    STATUS      current
    DESCRIPTION
        "Allows the configuration of a trace target."

    ::= { dpConfig 6 }

dpConfigTraceTargetEntry OBJECT-TYPE
    SYNTAX      DPConfigTraceTargetEntry
    MAX-ACCESS  not-accessible
    STATUS      current
    DESCRIPTION "Table row."
    INDEX { dpConfigTraceTargetIndex, IMPLIED dpConfigTraceTargetname }

    ::= { dpConfigTraceTargetTable 1 }

DPConfigTraceTargetEntry ::= SEQUENCE {
    dpConfigTraceTargetIndex    Unsigned32,
    dpConfigTraceTargetname    DisplayString
}

dpConfigTraceTargetIndex OBJECT-TYPE
    SYNTAX      Unsigned32
    MAX-ACCESS  read-only
    STATUS      current
    DESCRIPTION "No description yet."

    ::= { dpConfigTraceTargetEntry 1 }

dpConfigTraceTargetname OBJECT-TYPE
    SYNTAX      DisplayString
    MAX-ACCESS  read-only
    STATUS      current
    DESCRIPTION "No description yet."

    ::= { dpConfigTraceTargetEntry 2 }

--

dpConfigNTPServiceTable OBJECT-TYPE
    SYNTAX      SEQUENCE OF DPConfigNTPServiceEntry
    MAX-ACCESS  not-accessible
    STATUS      current
    DESCRIPTION
        "Configure remote NTP (Network Time Protocol) server. This allows the
        automatic synchronization of the system clock."

    ::= { dpConfig 7 }

dpConfigNTPServiceEntry OBJECT-TYPE
    SYNTAX      DPConfigNTPServiceEntry
    MAX-ACCESS  not-accessible
    STATUS      current
    DESCRIPTION "Table row."
    INDEX { dpConfigNTPServiceIndex, IMPLIED dpConfigNTPServicename }

    ::= { dpConfigNTPServiceTable 1 }

DPConfigNTPServiceEntry ::= SEQUENCE {
    dpConfigNTPServiceIndex    Unsigned32,
    dpConfigNTPServicename    DisplayString
}

dpConfigNTPServiceIndex OBJECT-TYPE
    SYNTAX      Unsigned32
    MAX-ACCESS  read-only
    STATUS      current
    DESCRIPTION "No description yet."

    ::= { dpConfigNTPServiceEntry 1 }

dpConfigNTPServicename OBJECT-TYPE
    SYNTAX      DisplayString
    MAX-ACCESS  read-only
    STATUS      current
    DESCRIPTION "No description yet."

    ::= { dpConfigNTPServiceEntry 2 }

--

dpConfigThrottlerTable OBJECT-TYPE
    SYNTAX      SEQUENCE OF DPConfigThrottlerEntry
    MAX-ACCESS  not-accessible
    STATUS      current
    DESCRIPTION
        "This setting throttles, or disallows, traffic when the total memory
        available to the system reaches the thresholds established here."

    ::= { dpConfig 8 }

dpConfigThrottlerEntry OBJECT-TYPE
    SYNTAX      DPConfigThrottlerEntry
    MAX-ACCESS  not-accessible
    STATUS      current
    DESCRIPTION "Table row."
    INDEX { dpConfigThrottlerIndex, IMPLIED dpConfigThrottlername }

    ::= { dpConfigThrottlerTable 1 }

DPConfigThrottlerEntry ::= SEQUENCE {
    dpConfigThrottlerIndex    Unsigned32,
    dpConfigThrottlername    DisplayString
}

dpConfigThrottlerIndex OBJECT-TYPE
    SYNTAX      Unsigned32
    MAX-ACCESS  read-only
    STATUS      current
    DESCRIPTION "No description yet."

    ::= { dpConfigThrottlerEntry 1 }

dpConfigThrottlername OBJECT-TYPE
    SYNTAX      DisplayString
    MAX-ACCESS  read-only
    STATUS      current
    DESCRIPTION "No description yet."

    ::= { dpConfigThrottlerEntry 2 }

--

dpConfigStylePolicyTable OBJECT-TYPE
    SYNTAX      SEQUENCE OF DPConfigStylePolicyEntry
    MAX-ACCESS  not-accessible
    STATUS      current
    DESCRIPTION
        "Create, Edit or Delete a Processing Policy. A policy consists of one or
        more Processing Rules. Rules execute depending upon the direction of the
        message and on whether or not a corresponding matching rule selects the
        document for processing. A service may have only one policy active at a
        time. Click Services in the left-hand navigation menu and then click the
        appropriate policy link to use the graphical interface to create and edit
        policies."

    ::= { dpConfig 9 }

dpConfigStylePolicyEntry OBJECT-TYPE
    SYNTAX      DPConfigStylePolicyEntry
    MAX-ACCESS  not-accessible
    STATUS      current
    DESCRIPTION "Table row."
    INDEX { dpConfigStylePolicyIndex, IMPLIED dpConfigStylePolicyname }

    ::= { dpConfigStylePolicyTable 1 }

DPConfigStylePolicyEntry ::= SEQUENCE {
    dpConfigStylePolicyIndex    Unsigned32,
    dpConfigStylePolicyname    DisplayString
}

dpConfigStylePolicyIndex OBJECT-TYPE
    SYNTAX      Unsigned32
    MAX-ACCESS  read-only
    STATUS      current
    DESCRIPTION "No description yet."

    ::= { dpConfigStylePolicyEntry 1 }

dpConfigStylePolicyname OBJECT-TYPE
    SYNTAX      DisplayString
    MAX-ACCESS  read-only
    STATUS      current
    DESCRIPTION "No description yet."

    ::= { dpConfigStylePolicyEntry 2 }

--

dpConfigHTTPUserAgentTable OBJECT-TYPE
    SYNTAX      SEQUENCE OF DPConfigHTTPUserAgentEntry
    MAX-ACCESS  not-accessible
    STATUS      current
    DESCRIPTION
        "Use this page to configure a User Agent, which the device uses to retrieve
        resources (for example, stylesheets or XML documents) from remote servers.
        A User Agent can also affect the messages emitted by a Multi-Protocol
        Gateway"

    ::= { dpConfig 10 }

dpConfigHTTPUserAgentEntry OBJECT-TYPE
    SYNTAX      DPConfigHTTPUserAgentEntry
    MAX-ACCESS  not-accessible
    STATUS      current
    DESCRIPTION "Table row."
    INDEX { dpConfigHTTPUserAgentIndex, IMPLIED dpConfigHTTPUserAgentname }

    ::= { dpConfigHTTPUserAgentTable 1 }

DPConfigHTTPUserAgentEntry ::= SEQUENCE {
    dpConfigHTTPUserAgentIndex    Unsigned32,
    dpConfigHTTPUserAgentname    DisplayString
}

dpConfigHTTPUserAgentIndex OBJECT-TYPE
    SYNTAX      Unsigned32
    MAX-ACCESS  read-only
    STATUS      current
    DESCRIPTION "No description yet."

    ::= { dpConfigHTTPUserAgentEntry 1 }

dpConfigHTTPUserAgentname OBJECT-TYPE
    SYNTAX      DisplayString
    MAX-ACCESS  read-only
    STATUS      current
    DESCRIPTION "No description yet."

    ::= { dpConfigHTTPUserAgentEntry 2 }

--

dpConfigTCPProxyServiceTable OBJECT-TYPE
    SYNTAX      SEQUENCE OF DPConfigTCPProxyServiceEntry
    MAX-ACCESS  not-accessible
    STATUS      current
    DESCRIPTION
        "Creates a TCP Proxy service."

    ::= { dpConfig 12 }

dpConfigTCPProxyServiceEntry OBJECT-TYPE
    SYNTAX      DPConfigTCPProxyServiceEntry
    MAX-ACCESS  not-accessible
    STATUS      current
    DESCRIPTION "Table row."
    INDEX { dpConfigTCPProxyServiceIndex, IMPLIED dpConfigTCPProxyServicename }

    ::= { dpConfigTCPProxyServiceTable 1 }

DPConfigTCPProxyServiceEntry ::= SEQUENCE {
    dpConfigTCPProxyServiceIndex    Unsigned32,
    dpConfigTCPProxyServicename    DisplayString
}

dpConfigTCPProxyServiceIndex OBJECT-TYPE
    SYNTAX      Unsigned32
    MAX-ACCESS  read-only
    STATUS      current
    DESCRIPTION "No description yet."

    ::= { dpConfigTCPProxyServiceEntry 1 }

dpConfigTCPProxyServicename OBJECT-TYPE
    SYNTAX      DisplayString
    MAX-ACCESS  read-only
    STATUS      current
    DESCRIPTION "No description yet."

    ::= { dpConfigTCPProxyServiceEntry 2 }

--

dpConfigURLMapTable OBJECT-TYPE
    SYNTAX      SEQUENCE OF DPConfigURLMapEntry
    MAX-ACCESS  not-accessible
    STATUS      current
    DESCRIPTION
        "Configure/Edit URL maps. URL Maps are used by Processing Actions and by
        XML Manager Compile Options Policies."

    ::= { dpConfig 13 }

dpConfigURLMapEntry OBJECT-TYPE
    SYNTAX      DPConfigURLMapEntry
    MAX-ACCESS  not-accessible
    STATUS      current
    DESCRIPTION "Table row."
    INDEX { dpConfigURLMapIndex, IMPLIED dpConfigURLMapname }

    ::= { dpConfigURLMapTable 1 }

DPConfigURLMapEntry ::= SEQUENCE {
    dpConfigURLMapIndex    Unsigned32,
    dpConfigURLMapname    DisplayString
}

dpConfigURLMapIndex OBJECT-TYPE
    SYNTAX      Unsigned32
    MAX-ACCESS  read-only
    STATUS      current
    DESCRIPTION "No description yet."

    ::= { dpConfigURLMapEntry 1 }

dpConfigURLMapname OBJECT-TYPE
    SYNTAX      DisplayString
    MAX-ACCESS  read-only
    STATUS      current
    DESCRIPTION "No description yet."

    ::= { dpConfigURLMapEntry 2 }

--

dpConfigURLRefreshPolicyTable OBJECT-TYPE
    SYNTAX      SEQUENCE OF DPConfigURLRefreshPolicyEntry
    MAX-ACCESS  not-accessible
    STATUS      current
    DESCRIPTION
        "Configure/Edit URL Refresh Policies"

    ::= { dpConfig 14 }

dpConfigURLRefreshPolicyEntry OBJECT-TYPE
    SYNTAX      DPConfigURLRefreshPolicyEntry
    MAX-ACCESS  not-accessible
    STATUS      current
    DESCRIPTION "Table row."
    INDEX { dpConfigURLRefreshPolicyIndex, IMPLIED dpConfigURLRefreshPolicyname }

    ::= { dpConfigURLRefreshPolicyTable 1 }

DPConfigURLRefreshPolicyEntry ::= SEQUENCE {
    dpConfigURLRefreshPolicyIndex    Unsigned32,
    dpConfigURLRefreshPolicyname    DisplayString
}

dpConfigURLRefreshPolicyIndex OBJECT-TYPE
    SYNTAX      Unsigned32
    MAX-ACCESS  read-only
    STATUS      current
    DESCRIPTION "No description yet."

    ::= { dpConfigURLRefreshPolicyEntry 1 }

dpConfigURLRefreshPolicyname OBJECT-TYPE
    SYNTAX      DisplayString
    MAX-ACCESS  read-only
    STATUS      current
    DESCRIPTION "No description yet."

    ::= { dpConfigURLRefreshPolicyEntry 2 }

--

dpConfigUserTable OBJECT-TYPE
    SYNTAX      SEQUENCE OF DPConfigUserEntry
    MAX-ACCESS  not-accessible
    STATUS      current
    DESCRIPTION
        "Create or edit a local user account. When you modify a local user account,
        the changes do not affect remote user accounts in a role-based management
        XML information file. An administrator can change the password for the
        account. An administrator can force the account owner to change the
        password during the next log in attempt."

    ::= { dpConfig 15 }

dpConfigUserEntry OBJECT-TYPE
    SYNTAX      DPConfigUserEntry
    MAX-ACCESS  not-accessible
    STATUS      current
    DESCRIPTION "Table row."
    INDEX { dpConfigUserIndex, IMPLIED dpConfigUsername }

    ::= { dpConfigUserTable 1 }

DPConfigUserEntry ::= SEQUENCE {
    dpConfigUserIndex    Unsigned32,
    dpConfigUsername    DisplayString
}

dpConfigUserIndex OBJECT-TYPE
    SYNTAX      Unsigned32
    MAX-ACCESS  read-only
    STATUS      current
    DESCRIPTION "No description yet."

    ::= { dpConfigUserEntry 1 }

dpConfigUsername OBJECT-TYPE
    SYNTAX      DisplayString
    MAX-ACCESS  read-only
    STATUS      current
    DESCRIPTION "No description yet."

    ::= { dpConfigUserEntry 2 }

--

dpConfigNetworkSettingsTable OBJECT-TYPE
    SYNTAX      SEQUENCE OF DPConfigNetworkSettingsEntry
    MAX-ACCESS  not-accessible
    STATUS      current
    DESCRIPTION
        "Configure appliance-wide network settings."

    ::= { dpConfig 16 }

dpConfigNetworkSettingsEntry OBJECT-TYPE
    SYNTAX      DPConfigNetworkSettingsEntry
    MAX-ACCESS  not-accessible
    STATUS      current
    DESCRIPTION "Table row."
    INDEX { dpConfigNetworkSettingsIndex, IMPLIED dpConfigNetworkSettingsname }

    ::= { dpConfigNetworkSettingsTable 1 }

DPConfigNetworkSettingsEntry ::= SEQUENCE {
    dpConfigNetworkSettingsIndex    Unsigned32,
    dpConfigNetworkSettingsname    DisplayString
}

dpConfigNetworkSettingsIndex OBJECT-TYPE
    SYNTAX      Unsigned32
    MAX-ACCESS  read-only
    STATUS      current
    DESCRIPTION "No description yet."

    ::= { dpConfigNetworkSettingsEntry 1 }

dpConfigNetworkSettingsname OBJECT-TYPE
    SYNTAX      DisplayString
    MAX-ACCESS  read-only
    STATUS      current
    DESCRIPTION "No description yet."

    ::= { dpConfigNetworkSettingsEntry 2 }

--

dpConfigXMLManagerTable OBJECT-TYPE
    SYNTAX      SEQUENCE OF DPConfigXMLManagerEntry
    MAX-ACCESS  not-accessible
    STATUS      current
    DESCRIPTION
        "An XML Manager manages the compilation and caching of stylesheets, the
        caching of documents, and provides configuration constraints on the size
        and parsing depth of documents. You can enable streaming operation by
        configuring an XML Manager to use a Streaming Compile Option Policy. More
        than one firewall may use the same XML Manager."

    ::= { dpConfig 17 }

dpConfigXMLManagerEntry OBJECT-TYPE
    SYNTAX      DPConfigXMLManagerEntry
    MAX-ACCESS  not-accessible
    STATUS      current
    DESCRIPTION "Table row."
    INDEX { dpConfigXMLManagerIndex, IMPLIED dpConfigXMLManagername }

    ::= { dpConfigXMLManagerTable 1 }

DPConfigXMLManagerEntry ::= SEQUENCE {
    dpConfigXMLManagerIndex    Unsigned32,
    dpConfigXMLManagername    DisplayString
}

dpConfigXMLManagerIndex OBJECT-TYPE
    SYNTAX      Unsigned32
    MAX-ACCESS  read-only
    STATUS      current
    DESCRIPTION "No description yet."

    ::= { dpConfigXMLManagerEntry 1 }

dpConfigXMLManagername OBJECT-TYPE
    SYNTAX      DisplayString
    MAX-ACCESS  read-only
    STATUS      current
    DESCRIPTION "No description yet."

    ::= { dpConfigXMLManagerEntry 2 }

--

dpConfigMQQMTable OBJECT-TYPE
    SYNTAX      SEQUENCE OF DPConfigMQQMEntry
    MAX-ACCESS  not-accessible
    STATUS      current
    DESCRIPTION
        "In IBM MQ, distributed send and receive queues are managed by a component
        called a queue manager. The queue manager provides messaging services for
        communicating applications by periodically monitoring/polling queues, by
        ensuring that sent messages are directed to the correct receive queue, or
        that messages are routed to another queue manager. This Queue Manager
        object on the device corresponds to a Queue Manager running on another
        host on the network. The properties set here enable communication between
        the device and the Queue Manager."

    ::= { dpConfig 18 }

dpConfigMQQMEntry OBJECT-TYPE
    SYNTAX      DPConfigMQQMEntry
    MAX-ACCESS  not-accessible
    STATUS      current
    DESCRIPTION "Table row."
    INDEX { dpConfigMQQMIndex, IMPLIED dpConfigMQQMname }

    ::= { dpConfigMQQMTable 1 }

DPConfigMQQMEntry ::= SEQUENCE {
    dpConfigMQQMIndex    Unsigned32,
    dpConfigMQQMname    DisplayString
}

dpConfigMQQMIndex OBJECT-TYPE
    SYNTAX      Unsigned32
    MAX-ACCESS  read-only
    STATUS      current
    DESCRIPTION "No description yet."

    ::= { dpConfigMQQMEntry 1 }

dpConfigMQQMname OBJECT-TYPE
    SYNTAX      DisplayString
    MAX-ACCESS  read-only
    STATUS      current
    DESCRIPTION "No description yet."

    ::= { dpConfigMQQMEntry 2 }

--

dpConfigXSLProxyServiceTable OBJECT-TYPE
    SYNTAX      SEQUENCE OF DPConfigXSLProxyServiceEntry
    MAX-ACCESS  not-accessible
    STATUS      current
    DESCRIPTION
        "The XSL Proxy service is deprecated. Creates an XSL Proxy on local IP/port
        for server on remote IP/port. A loopback proxy does not require a remote
        IP and port. The Proxy applies the selected XSL proxy processing policy to
        messages flowing through the proxy (as requests, responses or both
        directions). The proxy may apply the selected URL rewrite policy to client
        requests. If needed, the proxy may communicate with either the back end
        server or the requesting client using the SSL profiles selected."

    ::= { dpConfig 19 }

dpConfigXSLProxyServiceEntry OBJECT-TYPE
    SYNTAX      DPConfigXSLProxyServiceEntry
    MAX-ACCESS  not-accessible
    STATUS      current
    DESCRIPTION "Table row."
    INDEX { dpConfigXSLProxyServiceIndex, IMPLIED dpConfigXSLProxyServicename }

    ::= { dpConfigXSLProxyServiceTable 1 }

DPConfigXSLProxyServiceEntry ::= SEQUENCE {
    dpConfigXSLProxyServiceIndex    Unsigned32,
    dpConfigXSLProxyServicename    DisplayString
}

dpConfigXSLProxyServiceIndex OBJECT-TYPE
    SYNTAX      Unsigned32
    MAX-ACCESS  read-only
    STATUS      current
    DESCRIPTION "No description yet."

    ::= { dpConfigXSLProxyServiceEntry 1 }

dpConfigXSLProxyServicename OBJECT-TYPE
    SYNTAX      DisplayString
    MAX-ACCESS  read-only
    STATUS      current
    DESCRIPTION "No description yet."

    ::= { dpConfigXSLProxyServiceEntry 2 }

--

dpConfigMQGWTable OBJECT-TYPE
    SYNTAX      SEQUENCE OF DPConfigMQGWEntry
    MAX-ACCESS  not-accessible
    STATUS      current
    DESCRIPTION "Table."

    ::= { dpConfig 20 }

dpConfigMQGWEntry OBJECT-TYPE
    SYNTAX      DPConfigMQGWEntry
    MAX-ACCESS  not-accessible
    STATUS      current
    DESCRIPTION "Table row."
    INDEX { dpConfigMQGWIndex, IMPLIED dpConfigMQGWname }

    ::= { dpConfigMQGWTable 1 }

DPConfigMQGWEntry ::= SEQUENCE {
    dpConfigMQGWIndex    Unsigned32,
    dpConfigMQGWname    DisplayString
}

dpConfigMQGWIndex OBJECT-TYPE
    SYNTAX      Unsigned32
    MAX-ACCESS  read-only
    STATUS      current
    DESCRIPTION "No description yet."

    ::= { dpConfigMQGWEntry 1 }

dpConfigMQGWname OBJECT-TYPE
    SYNTAX      DisplayString
    MAX-ACCESS  read-only
    STATUS      current
    DESCRIPTION "No description yet."

    ::= { dpConfigMQGWEntry 2 }

--

dpConfigSSLProxyServiceTable OBJECT-TYPE
    SYNTAX      SEQUENCE OF DPConfigSSLProxyServiceEntry
    MAX-ACCESS  not-accessible
    STATUS      current
    DESCRIPTION
        "Creates an SSL Proxy service. This service can be used to wrap or unwrap a
        TCP stream in SSL. This service requires SSL profiles to secure the
        connections. When the appliance is an SSL client, use a forward SSL proxy
        profile or an SSL client profile to secure connections between the clients
        and its targets. When the appliance is an SSL server, use a reverse SSL
        proxy profile or an SSL server profile to secure connections between
        clients and the appliance. When the server supports Server Name Indication
        (SNI), you use an SSL SNI server profile. When the appliance is both an
        SSL client and SSL server, use a two-way SSL proxy profile, or an SSL
        client profile and an SSL server profile or SSL SNI server profile to
        secure both connections."

    ::= { dpConfig 21 }

dpConfigSSLProxyServiceEntry OBJECT-TYPE
    SYNTAX      DPConfigSSLProxyServiceEntry
    MAX-ACCESS  not-accessible
    STATUS      current
    DESCRIPTION "Table row."
    INDEX { dpConfigSSLProxyServiceIndex, IMPLIED dpConfigSSLProxyServicename }

    ::= { dpConfigSSLProxyServiceTable 1 }

DPConfigSSLProxyServiceEntry ::= SEQUENCE {
    dpConfigSSLProxyServiceIndex    Unsigned32,
    dpConfigSSLProxyServicename    DisplayString
}

dpConfigSSLProxyServiceIndex OBJECT-TYPE
    SYNTAX      Unsigned32
    MAX-ACCESS  read-only
    STATUS      current
    DESCRIPTION "No description yet."

    ::= { dpConfigSSLProxyServiceEntry 1 }

dpConfigSSLProxyServicename OBJECT-TYPE
    SYNTAX      DisplayString
    MAX-ACCESS  read-only
    STATUS      current
    DESCRIPTION "No description yet."

    ::= { dpConfigSSLProxyServiceEntry 2 }

--

dpConfigStylePolicyRuleTable OBJECT-TYPE
    SYNTAX      SEQUENCE OF DPConfigStylePolicyRuleEntry
    MAX-ACCESS  not-accessible
    STATUS      current
    DESCRIPTION
        "Create, edit, or delete processing policy rules. Rules can also be created
        and edited using a drag and drop interface by opening the Services menu
        area on the left-hand navigation bar. Click the appropriate Policy link
        which will then present an opportunity to create both Rules and Actions."

    ::= { dpConfig 22 }

dpConfigStylePolicyRuleEntry OBJECT-TYPE
    SYNTAX      DPConfigStylePolicyRuleEntry
    MAX-ACCESS  not-accessible
    STATUS      current
    DESCRIPTION "Table row."
    INDEX { dpConfigStylePolicyRuleIndex, IMPLIED dpConfigStylePolicyRulename }

    ::= { dpConfigStylePolicyRuleTable 1 }

DPConfigStylePolicyRuleEntry ::= SEQUENCE {
    dpConfigStylePolicyRuleIndex    Unsigned32,
    dpConfigStylePolicyRulename    DisplayString
}

dpConfigStylePolicyRuleIndex OBJECT-TYPE
    SYNTAX      Unsigned32
    MAX-ACCESS  read-only
    STATUS      current
    DESCRIPTION "No description yet."

    ::= { dpConfigStylePolicyRuleEntry 1 }

dpConfigStylePolicyRulename OBJECT-TYPE
    SYNTAX      DisplayString
    MAX-ACCESS  read-only
    STATUS      current
    DESCRIPTION "No description yet."

    ::= { dpConfigStylePolicyRuleEntry 2 }

--

dpConfigErrorReportSettingsTable OBJECT-TYPE
    SYNTAX      SEQUENCE OF DPConfigErrorReportSettingsEntry
    MAX-ACCESS  not-accessible
    STATUS      current
    DESCRIPTION
        "Failure notification is a serviceability tool. By default, failure
        notification is disabled. To use failure notification, you must enable the
        configuration and allow the error report to be uploaded. The uploading of
        an error report allows the capture of more diagnostic information, which
        safely improves serviceability. Although there is a tradeoff between
        performance and serviceability, you should choose serviceability by
        enabling the following properties: Include Internal State Background
        Packet Capture Background Log Capture Background Memory Trace When you
        allow the error report to be uploaded, this setting enables the Failure
        Notification status provider. This status provide in combination with the
        report history tracks the error reports that the appliance generates, the
        reason why the appliance generated the error report, and its upload status
        to the specific destination. You can specify an NFS, iSCSI (deprecated),
        RAID, SMTP, or FTP destination. You can also specify the local temporary
        directory as the destination. The appliance generates error reports, the
        naming convention includes the serial number of the appliance and the
        timestamp of the report. This naming convention prevents one report from
        overwriting another. You can use Event Triggers to generate error reports
        automatically when specific events occur."

    ::= { dpConfig 23 }

dpConfigErrorReportSettingsEntry OBJECT-TYPE
    SYNTAX      DPConfigErrorReportSettingsEntry
    MAX-ACCESS  not-accessible
    STATUS      current
    DESCRIPTION "Table row."
    INDEX { dpConfigErrorReportSettingsIndex, IMPLIED dpConfigErrorReportSettingsname }

    ::= { dpConfigErrorReportSettingsTable 1 }

DPConfigErrorReportSettingsEntry ::= SEQUENCE {
    dpConfigErrorReportSettingsIndex    Unsigned32,
    dpConfigErrorReportSettingsname    DisplayString
}

dpConfigErrorReportSettingsIndex OBJECT-TYPE
    SYNTAX      Unsigned32
    MAX-ACCESS  read-only
    STATUS      current
    DESCRIPTION "No description yet."

    ::= { dpConfigErrorReportSettingsEntry 1 }

dpConfigErrorReportSettingsname OBJECT-TYPE
    SYNTAX      DisplayString
    MAX-ACCESS  read-only
    STATUS      current
    DESCRIPTION "No description yet."

    ::= { dpConfigErrorReportSettingsEntry 2 }

--

dpConfigIPInterfaceTable OBJECT-TYPE
    SYNTAX      SEQUENCE OF DPConfigIPInterfaceEntry
    MAX-ACCESS  not-accessible
    STATUS      current
    DESCRIPTION
        "Configure network Ethernet interfaces"

    ::= { dpConfig 25 }

dpConfigIPInterfaceEntry OBJECT-TYPE
    SYNTAX      DPConfigIPInterfaceEntry
    MAX-ACCESS  not-accessible
    STATUS      current
    DESCRIPTION "Table row."
    INDEX { dpConfigIPInterfaceIndex, IMPLIED dpConfigIPInterfacename }

    ::= { dpConfigIPInterfaceTable 1 }

DPConfigIPInterfaceEntry ::= SEQUENCE {
    dpConfigIPInterfaceIndex    Unsigned32,
    dpConfigIPInterfacename    DisplayString
}

dpConfigIPInterfaceIndex OBJECT-TYPE
    SYNTAX      Unsigned32
    MAX-ACCESS  read-only
    STATUS      current
    DESCRIPTION "No description yet."

    ::= { dpConfigIPInterfaceEntry 1 }

dpConfigIPInterfacename OBJECT-TYPE
    SYNTAX      DisplayString
    MAX-ACCESS  read-only
    STATUS      current
    DESCRIPTION "No description yet."

    ::= { dpConfigIPInterfaceEntry 2 }

--

dpConfigMatchingTable OBJECT-TYPE
    SYNTAX      SEQUENCE OF DPConfigMatchingEntry
    MAX-ACCESS  not-accessible
    STATUS      current
    DESCRIPTION "Table."

    ::= { dpConfig 26 }

dpConfigMatchingEntry OBJECT-TYPE
    SYNTAX      DPConfigMatchingEntry
    MAX-ACCESS  not-accessible
    STATUS      current
    DESCRIPTION "Table row."
    INDEX { dpConfigMatchingIndex, IMPLIED dpConfigMatchingname }

    ::= { dpConfigMatchingTable 1 }

DPConfigMatchingEntry ::= SEQUENCE {
    dpConfigMatchingIndex    Unsigned32,
    dpConfigMatchingname    DisplayString
}

dpConfigMatchingIndex OBJECT-TYPE
    SYNTAX      Unsigned32
    MAX-ACCESS  read-only
    STATUS      current
    DESCRIPTION "No description yet."

    ::= { dpConfigMatchingEntry 1 }

dpConfigMatchingname OBJECT-TYPE
    SYNTAX      DisplayString
    MAX-ACCESS  read-only
    STATUS      current
    DESCRIPTION "No description yet."

    ::= { dpConfigMatchingEntry 2 }

--

dpConfigSystemSettingsTable OBJECT-TYPE
    SYNTAX      SEQUENCE OF DPConfigSystemSettingsEntry
    MAX-ACCESS  not-accessible
    STATUS      current
    DESCRIPTION
        "System settings provide the following purposes. Define appliance-specific
        information, such as contact information, location, and name. Update
        serial number after a replacement. Enable interface for custom GUI
        messages and custom CLI prompt. Reserve disk space for the audit log.
        Define information about the hardware for use by the SNMP system table,
        such as serial number, and model type"

    ::= { dpConfig 27 }

dpConfigSystemSettingsEntry OBJECT-TYPE
    SYNTAX      DPConfigSystemSettingsEntry
    MAX-ACCESS  not-accessible
    STATUS      current
    DESCRIPTION "Table row."
    INDEX { dpConfigSystemSettingsIndex, IMPLIED dpConfigSystemSettingsname }

    ::= { dpConfigSystemSettingsTable 1 }

DPConfigSystemSettingsEntry ::= SEQUENCE {
    dpConfigSystemSettingsIndex    Unsigned32,
    dpConfigSystemSettingsname    DisplayString
}

dpConfigSystemSettingsIndex OBJECT-TYPE
    SYNTAX      Unsigned32
    MAX-ACCESS  read-only
    STATUS      current
    DESCRIPTION "No description yet."

    ::= { dpConfigSystemSettingsEntry 1 }

dpConfigSystemSettingsname OBJECT-TYPE
    SYNTAX      DisplayString
    MAX-ACCESS  read-only
    STATUS      current
    DESCRIPTION "No description yet."

    ::= { dpConfigSystemSettingsEntry 2 }

--

dpConfigSNMPSettingsTable OBJECT-TYPE
    SYNTAX      SEQUENCE OF DPConfigSNMPSettingsEntry
    MAX-ACCESS  not-accessible
    STATUS      current
    DESCRIPTION
        "Use this page to establish SNMP connectivity to the device, and to set
        values used by SNMP."

    ::= { dpConfig 28 }

dpConfigSNMPSettingsEntry OBJECT-TYPE
    SYNTAX      DPConfigSNMPSettingsEntry
    MAX-ACCESS  not-accessible
    STATUS      current
    DESCRIPTION "Table row."
    INDEX { dpConfigSNMPSettingsIndex, IMPLIED dpConfigSNMPSettingsname }

    ::= { dpConfigSNMPSettingsTable 1 }

DPConfigSNMPSettingsEntry ::= SEQUENCE {
    dpConfigSNMPSettingsIndex    Unsigned32,
    dpConfigSNMPSettingsname    DisplayString
}

dpConfigSNMPSettingsIndex OBJECT-TYPE
    SYNTAX      Unsigned32
    MAX-ACCESS  read-only
    STATUS      current
    DESCRIPTION "No description yet."

    ::= { dpConfigSNMPSettingsEntry 1 }

dpConfigSNMPSettingsname OBJECT-TYPE
    SYNTAX      DisplayString
    MAX-ACCESS  read-only
    STATUS      current
    DESCRIPTION "No description yet."

    ::= { dpConfigSNMPSettingsEntry 2 }

--

dpConfigRADIUSSettingsTable OBJECT-TYPE
    SYNTAX      SEQUENCE OF DPConfigRADIUSSettingsEntry
    MAX-ACCESS  not-accessible
    STATUS      current
    DESCRIPTION
        "Global RADIUS configuration"

    ::= { dpConfig 29 }

dpConfigRADIUSSettingsEntry OBJECT-TYPE
    SYNTAX      DPConfigRADIUSSettingsEntry
    MAX-ACCESS  not-accessible
    STATUS      current
    DESCRIPTION "Table row."
    INDEX { dpConfigRADIUSSettingsIndex, IMPLIED dpConfigRADIUSSettingsname }

    ::= { dpConfigRADIUSSettingsTable 1 }

DPConfigRADIUSSettingsEntry ::= SEQUENCE {
    dpConfigRADIUSSettingsIndex    Unsigned32,
    dpConfigRADIUSSettingsname    DisplayString
}

dpConfigRADIUSSettingsIndex OBJECT-TYPE
    SYNTAX      Unsigned32
    MAX-ACCESS  read-only
    STATUS      current
    DESCRIPTION "No description yet."

    ::= { dpConfigRADIUSSettingsEntry 1 }

dpConfigRADIUSSettingsname OBJECT-TYPE
    SYNTAX      DisplayString
    MAX-ACCESS  read-only
    STATUS      current
    DESCRIPTION "No description yet."

    ::= { dpConfigRADIUSSettingsEntry 2 }

--

dpConfigUserGroupTable OBJECT-TYPE
    SYNTAX      SEQUENCE OF DPConfigUserGroupEntry
    MAX-ACCESS  not-accessible
    STATUS      current
    DESCRIPTION
        "Create or edit user groups and their access privileges."

    ::= { dpConfig 30 }

dpConfigUserGroupEntry OBJECT-TYPE
    SYNTAX      DPConfigUserGroupEntry
    MAX-ACCESS  not-accessible
    STATUS      current
    DESCRIPTION "Table row."
    INDEX { dpConfigUserGroupIndex, IMPLIED dpConfigUserGroupname }

    ::= { dpConfigUserGroupTable 1 }

DPConfigUserGroupEntry ::= SEQUENCE {
    dpConfigUserGroupIndex    Unsigned32,
    dpConfigUserGroupname    DisplayString
}

dpConfigUserGroupIndex OBJECT-TYPE
    SYNTAX      Unsigned32
    MAX-ACCESS  read-only
    STATUS      current
    DESCRIPTION "No description yet."

    ::= { dpConfigUserGroupEntry 1 }

dpConfigUserGroupname OBJECT-TYPE
    SYNTAX      DisplayString
    MAX-ACCESS  read-only
    STATUS      current
    DESCRIPTION "No description yet."

    ::= { dpConfigUserGroupEntry 2 }

--

dpConfigShellAliasTable OBJECT-TYPE
    SYNTAX      SEQUENCE OF DPConfigShellAliasEntry
    MAX-ACCESS  not-accessible
    STATUS      current
    DESCRIPTION
        "The Shell Alias command is deprecated. Creates a user-defined macro that
        runs the specified sequence of commands when invoked from the CLI. You can
        use the GUI to create and modify macros, but you can invoke these macros
        from only the CLI."

    ::= { dpConfig 31 }

dpConfigShellAliasEntry OBJECT-TYPE
    SYNTAX      DPConfigShellAliasEntry
    MAX-ACCESS  not-accessible
    STATUS      current
    DESCRIPTION "Table row."
    INDEX { dpConfigShellAliasIndex, IMPLIED dpConfigShellAliasname }

    ::= { dpConfigShellAliasTable 1 }

DPConfigShellAliasEntry ::= SEQUENCE {
    dpConfigShellAliasIndex    Unsigned32,
    dpConfigShellAliasname    DisplayString
}

dpConfigShellAliasIndex OBJECT-TYPE
    SYNTAX      Unsigned32
    MAX-ACCESS  read-only
    STATUS      current
    DESCRIPTION "No description yet."

    ::= { dpConfigShellAliasEntry 1 }

dpConfigShellAliasname OBJECT-TYPE
    SYNTAX      DisplayString
    MAX-ACCESS  read-only
    STATUS      current
    DESCRIPTION "No description yet."

    ::= { dpConfigShellAliasEntry 2 }

--

dpConfigXSLCoprocServiceTable OBJECT-TYPE
    SYNTAX      SEQUENCE OF DPConfigXSLCoprocServiceEntry
    MAX-ACCESS  not-accessible
    STATUS      current
    DESCRIPTION
        "The XSL Coprocessor service is deprecated. Creates an XSL Coprocessor. An
        XSL Coprocessor accepts input not from a client, as in XSL Proxy or XML
        Firewall operation, but from a Java program or a plug-in equipped
        application running on another machine on the local network. Messages are
        sent to the coprocessor by the Java library or plug-in, the Coprocessor
        then applies the Processing Rule selected and returns the result to the
        calling routine. When the Rule is set to None, the CoProcessor uses the
        XSL stylesheet supplied by the calling entity."

    ::= { dpConfig 32 }

dpConfigXSLCoprocServiceEntry OBJECT-TYPE
    SYNTAX      DPConfigXSLCoprocServiceEntry
    MAX-ACCESS  not-accessible
    STATUS      current
    DESCRIPTION "Table row."
    INDEX { dpConfigXSLCoprocServiceIndex, IMPLIED dpConfigXSLCoprocServicename }

    ::= { dpConfigXSLCoprocServiceTable 1 }

DPConfigXSLCoprocServiceEntry ::= SEQUENCE {
    dpConfigXSLCoprocServiceIndex    Unsigned32,
    dpConfigXSLCoprocServicename    DisplayString
}

dpConfigXSLCoprocServiceIndex OBJECT-TYPE
    SYNTAX      Unsigned32
    MAX-ACCESS  read-only
    STATUS      current
    DESCRIPTION "No description yet."

    ::= { dpConfigXSLCoprocServiceEntry 1 }

dpConfigXSLCoprocServicename OBJECT-TYPE
    SYNTAX      DisplayString
    MAX-ACCESS  read-only
    STATUS      current
    DESCRIPTION "No description yet."

    ::= { dpConfigXSLCoprocServiceEntry 2 }

--

dpConfigTelnetServiceTable OBJECT-TYPE
    SYNTAX      SEQUENCE OF DPConfigTelnetServiceEntry
    MAX-ACCESS  not-accessible
    STATUS      current
    DESCRIPTION
        "Telnet services on the appliance are Telnet handlers. They are available
        for compatibility with earlier versions. A Telnet handler supports
        client-initiated access to the CLI. Telnet is an unsecure protocol and
        should be used with extreme caution. Telnet should be enabled only on the
        trusted management port or on a secure network segment. To ensure an
        encrypted connection and verify the cryptographic authenticity of the
        server, SSH is a more secure choice."

    ::= { dpConfig 33 }

dpConfigTelnetServiceEntry OBJECT-TYPE
    SYNTAX      DPConfigTelnetServiceEntry
    MAX-ACCESS  not-accessible
    STATUS      current
    DESCRIPTION "Table row."
    INDEX { dpConfigTelnetServiceIndex, IMPLIED dpConfigTelnetServicename }

    ::= { dpConfigTelnetServiceTable 1 }

DPConfigTelnetServiceEntry ::= SEQUENCE {
    dpConfigTelnetServiceIndex    Unsigned32,
    dpConfigTelnetServicename    DisplayString
}

dpConfigTelnetServiceIndex OBJECT-TYPE
    SYNTAX      Unsigned32
    MAX-ACCESS  read-only
    STATUS      current
    DESCRIPTION "No description yet."

    ::= { dpConfigTelnetServiceEntry 1 }

dpConfigTelnetServicename OBJECT-TYPE
    SYNTAX      DisplayString
    MAX-ACCESS  read-only
    STATUS      current
    DESCRIPTION "No description yet."

    ::= { dpConfigTelnetServiceEntry 2 }

--

dpConfigCryptoSSKeyTable OBJECT-TYPE
    SYNTAX      SEQUENCE OF DPConfigCryptoSSKeyEntry
    MAX-ACCESS  not-accessible
    STATUS      current
    DESCRIPTION
        "A shared secret key is a sequence of characters that is pre-shared between
        users for use with symmetric encryption."

    ::= { dpConfig 34 }

dpConfigCryptoSSKeyEntry OBJECT-TYPE
    SYNTAX      DPConfigCryptoSSKeyEntry
    MAX-ACCESS  not-accessible
    STATUS      current
    DESCRIPTION "Table row."
    INDEX { dpConfigCryptoSSKeyIndex, IMPLIED dpConfigCryptoSSKeyname }

    ::= { dpConfigCryptoSSKeyTable 1 }

DPConfigCryptoSSKeyEntry ::= SEQUENCE {
    dpConfigCryptoSSKeyIndex    Unsigned32,
    dpConfigCryptoSSKeyname    DisplayString
}

dpConfigCryptoSSKeyIndex OBJECT-TYPE
    SYNTAX      Unsigned32
    MAX-ACCESS  read-only
    STATUS      current
    DESCRIPTION "No description yet."

    ::= { dpConfigCryptoSSKeyEntry 1 }

dpConfigCryptoSSKeyname OBJECT-TYPE
    SYNTAX      DisplayString
    MAX-ACCESS  read-only
    STATUS      current
    DESCRIPTION "No description yet."

    ::= { dpConfigCryptoSSKeyEntry 2 }

--

dpConfigMessageMonitorTable OBJECT-TYPE
    SYNTAX      SEQUENCE OF DPConfigMessageMonitorEntry
    MAX-ACCESS  not-accessible
    STATUS      current
    DESCRIPTION "Table."

    ::= { dpConfig 35 }

dpConfigMessageMonitorEntry OBJECT-TYPE
    SYNTAX      DPConfigMessageMonitorEntry
    MAX-ACCESS  not-accessible
    STATUS      current
    DESCRIPTION "Table row."
    INDEX { dpConfigMessageMonitorIndex, IMPLIED dpConfigMessageMonitorname }

    ::= { dpConfigMessageMonitorTable 1 }

DPConfigMessageMonitorEntry ::= SEQUENCE {
    dpConfigMessageMonitorIndex    Unsigned32,
    dpConfigMessageMonitorname    DisplayString
}

dpConfigMessageMonitorIndex OBJECT-TYPE
    SYNTAX      Unsigned32
    MAX-ACCESS  read-only
    STATUS      current
    DESCRIPTION "No description yet."

    ::= { dpConfigMessageMonitorEntry 1 }

dpConfigMessageMonitorname OBJECT-TYPE
    SYNTAX      DisplayString
    MAX-ACCESS  read-only
    STATUS      current
    DESCRIPTION "No description yet."

    ::= { dpConfigMessageMonitorEntry 2 }

--

dpConfigURLRewritePolicyTable OBJECT-TYPE
    SYNTAX      SEQUENCE OF DPConfigURLRewritePolicyEntry
    MAX-ACCESS  not-accessible
    STATUS      current
    DESCRIPTION
        "Configure/Edit URL Rewrite Policies"

    ::= { dpConfig 36 }

dpConfigURLRewritePolicyEntry OBJECT-TYPE
    SYNTAX      DPConfigURLRewritePolicyEntry
    MAX-ACCESS  not-accessible
    STATUS      current
    DESCRIPTION "Table row."
    INDEX { dpConfigURLRewritePolicyIndex, IMPLIED dpConfigURLRewritePolicyname }

    ::= { dpConfigURLRewritePolicyTable 1 }

DPConfigURLRewritePolicyEntry ::= SEQUENCE {
    dpConfigURLRewritePolicyIndex    Unsigned32,
    dpConfigURLRewritePolicyname    DisplayString
}

dpConfigURLRewritePolicyIndex OBJECT-TYPE
    SYNTAX      Unsigned32
    MAX-ACCESS  read-only
    STATUS      current
    DESCRIPTION "No description yet."

    ::= { dpConfigURLRewritePolicyEntry 1 }

dpConfigURLRewritePolicyname OBJECT-TYPE
    SYNTAX      DisplayString
    MAX-ACCESS  read-only
    STATUS      current
    DESCRIPTION "No description yet."

    ::= { dpConfigURLRewritePolicyEntry 2 }

--

dpConfigSSLProxyProfileTable OBJECT-TYPE
    SYNTAX      SEQUENCE OF DPConfigSSLProxyProfileEntry
    MAX-ACCESS  not-accessible
    STATUS      current
    DESCRIPTION
        "The SSL proxy profile is deprecated. To secure the connections, use the
        SSL client profile and SSL server profile or SSL SNI server profile based
        on the role of the appliance. An SSL proxy profile is associated with a
        DataPower service to describe how SSL connections should be made from or
        to the proxy's port."

    ::= { dpConfig 37 }

dpConfigSSLProxyProfileEntry OBJECT-TYPE
    SYNTAX      DPConfigSSLProxyProfileEntry
    MAX-ACCESS  not-accessible
    STATUS      current
    DESCRIPTION "Table row."
    INDEX { dpConfigSSLProxyProfileIndex, IMPLIED dpConfigSSLProxyProfilename }

    ::= { dpConfigSSLProxyProfileTable 1 }

DPConfigSSLProxyProfileEntry ::= SEQUENCE {
    dpConfigSSLProxyProfileIndex    Unsigned32,
    dpConfigSSLProxyProfilename    DisplayString
}

dpConfigSSLProxyProfileIndex OBJECT-TYPE
    SYNTAX      Unsigned32
    MAX-ACCESS  read-only
    STATUS      current
    DESCRIPTION "No description yet."

    ::= { dpConfigSSLProxyProfileEntry 1 }

dpConfigSSLProxyProfilename OBJECT-TYPE
    SYNTAX      DisplayString
    MAX-ACCESS  read-only
    STATUS      current
    DESCRIPTION "No description yet."

    ::= { dpConfigSSLProxyProfileEntry 2 }

--

dpConfigHTTPProxyServiceTable OBJECT-TYPE
    SYNTAX      SEQUENCE OF DPConfigHTTPProxyServiceEntry
    MAX-ACCESS  not-accessible
    STATUS      current
    DESCRIPTION
        "Defines an HTTP Proxy Service."

    ::= { dpConfig 38 }

dpConfigHTTPProxyServiceEntry OBJECT-TYPE
    SYNTAX      DPConfigHTTPProxyServiceEntry
    MAX-ACCESS  not-accessible
    STATUS      current
    DESCRIPTION "Table row."
    INDEX { dpConfigHTTPProxyServiceIndex, IMPLIED dpConfigHTTPProxyServicename }

    ::= { dpConfigHTTPProxyServiceTable 1 }

DPConfigHTTPProxyServiceEntry ::= SEQUENCE {
    dpConfigHTTPProxyServiceIndex    Unsigned32,
    dpConfigHTTPProxyServicename    DisplayString
}

dpConfigHTTPProxyServiceIndex OBJECT-TYPE
    SYNTAX      Unsigned32
    MAX-ACCESS  read-only
    STATUS      current
    DESCRIPTION "No description yet."

    ::= { dpConfigHTTPProxyServiceEntry 1 }

dpConfigHTTPProxyServicename OBJECT-TYPE
    SYNTAX      DisplayString
    MAX-ACCESS  read-only
    STATUS      current
    DESCRIPTION "No description yet."

    ::= { dpConfigHTTPProxyServiceEntry 2 }

--

dpConfigServiceTable OBJECT-TYPE
    SYNTAX      SEQUENCE OF DPConfigServiceEntry
    MAX-ACCESS  not-accessible
    STATUS      current
    DESCRIPTION "Table."

    ::= { dpConfig 39 }

dpConfigServiceEntry OBJECT-TYPE
    SYNTAX      DPConfigServiceEntry
    MAX-ACCESS  not-accessible
    STATUS      current
    DESCRIPTION "Table row."
    INDEX { dpConfigServiceIndex, IMPLIED dpConfigServicename }

    ::= { dpConfigServiceTable 1 }

DPConfigServiceEntry ::= SEQUENCE {
    dpConfigServiceIndex    Unsigned32,
    dpConfigServicename    DisplayString
}

dpConfigServiceIndex OBJECT-TYPE
    SYNTAX      Unsigned32
    MAX-ACCESS  read-only
    STATUS      current
    DESCRIPTION "No description yet."

    ::= { dpConfigServiceEntry 1 }

dpConfigServicename OBJECT-TYPE
    SYNTAX      DisplayString
    MAX-ACCESS  read-only
    STATUS      current
    DESCRIPTION "No description yet."

    ::= { dpConfigServiceEntry 2 }

--

dpConfigCryptoFWCredTable OBJECT-TYPE
    SYNTAX      SEQUENCE OF DPConfigCryptoFWCredEntry
    MAX-ACCESS  not-accessible
    STATUS      current
    DESCRIPTION
        "The set of crypto credentials (private keys, shared secret keys, and
        certificates) usable by an xmlfirewall when calling security extension
        functions to perform actions such as encryption/decryption and digital
        signing and verification. If a firewall is using a Firewall Credentials
        object and a particular certificate or key is not included in this list,
        the cryptographic operation trying to use the key or certificate will
        fail."

    ::= { dpConfig 41 }

dpConfigCryptoFWCredEntry OBJECT-TYPE
    SYNTAX      DPConfigCryptoFWCredEntry
    MAX-ACCESS  not-accessible
    STATUS      current
    DESCRIPTION "Table row."
    INDEX { dpConfigCryptoFWCredIndex, IMPLIED dpConfigCryptoFWCredname }

    ::= { dpConfigCryptoFWCredTable 1 }

DPConfigCryptoFWCredEntry ::= SEQUENCE {
    dpConfigCryptoFWCredIndex    Unsigned32,
    dpConfigCryptoFWCredname    DisplayString
}

dpConfigCryptoFWCredIndex OBJECT-TYPE
    SYNTAX      Unsigned32
    MAX-ACCESS  read-only
    STATUS      current
    DESCRIPTION "No description yet."

    ::= { dpConfigCryptoFWCredEntry 1 }

dpConfigCryptoFWCredname OBJECT-TYPE
    SYNTAX      DisplayString
    MAX-ACCESS  read-only
    STATUS      current
    DESCRIPTION "No description yet."

    ::= { dpConfigCryptoFWCredEntry 2 }

--

dpConfigXMLFirewallServiceTable OBJECT-TYPE
    SYNTAX      SEQUENCE OF DPConfigXMLFirewallServiceEntry
    MAX-ACCESS  not-accessible
    STATUS      current
    DESCRIPTION
        "Create or edit an XML Firewall on local IP/port (device address and port).
        This firewall may communicate with a dynamically identified server (or
        servers), a static back end server (at an identified remote IP/port) or as
        a loopback. The Firewall applies the selected processing policy to
        messages flowing through the firewall (request, response or both
        directions). Message content from client or server can be characterized as
        soap, xml, Non-XML (preprocessed) or Pass-Thru (unprocessed) and verified
        accordingly. The firewall may rewrite client request URLs using a URL
        rewrite policy. The firewall may use SSL communications to client, server
        or both directions if applicable."

    ::= { dpConfig 42 }

dpConfigXMLFirewallServiceEntry OBJECT-TYPE
    SYNTAX      DPConfigXMLFirewallServiceEntry
    MAX-ACCESS  not-accessible
    STATUS      current
    DESCRIPTION "Table row."
    INDEX { dpConfigXMLFirewallServiceIndex, IMPLIED dpConfigXMLFirewallServicename }

    ::= { dpConfigXMLFirewallServiceTable 1 }

DPConfigXMLFirewallServiceEntry ::= SEQUENCE {
    dpConfigXMLFirewallServiceIndex    Unsigned32,
    dpConfigXMLFirewallServicename    DisplayString
}

dpConfigXMLFirewallServiceIndex OBJECT-TYPE
    SYNTAX      Unsigned32
    MAX-ACCESS  read-only
    STATUS      current
    DESCRIPTION "No description yet."

    ::= { dpConfigXMLFirewallServiceEntry 1 }

dpConfigXMLFirewallServicename OBJECT-TYPE
    SYNTAX      DisplayString
    MAX-ACCESS  read-only
    STATUS      current
    DESCRIPTION "No description yet."

    ::= { dpConfigXMLFirewallServiceEntry 2 }

--

dpConfigCryptoKeyTable OBJECT-TYPE
    SYNTAX      SEQUENCE OF DPConfigCryptoKeyEntry
    MAX-ACCESS  not-accessible
    STATUS      current
    DESCRIPTION
        "The private key portion of a private/public key pair, as for RSA or DSA."

    ::= { dpConfig 43 }

dpConfigCryptoKeyEntry OBJECT-TYPE
    SYNTAX      DPConfigCryptoKeyEntry
    MAX-ACCESS  not-accessible
    STATUS      current
    DESCRIPTION "Table row."
    INDEX { dpConfigCryptoKeyIndex, IMPLIED dpConfigCryptoKeyname }

    ::= { dpConfigCryptoKeyTable 1 }

DPConfigCryptoKeyEntry ::= SEQUENCE {
    dpConfigCryptoKeyIndex    Unsigned32,
    dpConfigCryptoKeyname    DisplayString
}

dpConfigCryptoKeyIndex OBJECT-TYPE
    SYNTAX      Unsigned32
    MAX-ACCESS  read-only
    STATUS      current
    DESCRIPTION "No description yet."

    ::= { dpConfigCryptoKeyEntry 1 }

dpConfigCryptoKeyname OBJECT-TYPE
    SYNTAX      DisplayString
    MAX-ACCESS  read-only
    STATUS      current
    DESCRIPTION "No description yet."

    ::= { dpConfigCryptoKeyEntry 2 }

--

dpConfigCryptoCertificateTable OBJECT-TYPE
    SYNTAX      SEQUENCE OF DPConfigCryptoCertificateEntry
    MAX-ACCESS  not-accessible
    STATUS      current
    DESCRIPTION
        "The public key portion of a private/public key pair, as for RSA or DSA,
        plus the certificate with which the key pair is used."

    ::= { dpConfig 44 }

dpConfigCryptoCertificateEntry OBJECT-TYPE
    SYNTAX      DPConfigCryptoCertificateEntry
    MAX-ACCESS  not-accessible
    STATUS      current
    DESCRIPTION "Table row."
    INDEX { dpConfigCryptoCertificateIndex, IMPLIED dpConfigCryptoCertificatename }

    ::= { dpConfigCryptoCertificateTable 1 }

DPConfigCryptoCertificateEntry ::= SEQUENCE {
    dpConfigCryptoCertificateIndex    Unsigned32,
    dpConfigCryptoCertificatename    DisplayString
}

dpConfigCryptoCertificateIndex OBJECT-TYPE
    SYNTAX      Unsigned32
    MAX-ACCESS  read-only
    STATUS      current
    DESCRIPTION "No description yet."

    ::= { dpConfigCryptoCertificateEntry 1 }

dpConfigCryptoCertificatename OBJECT-TYPE
    SYNTAX      DisplayString
    MAX-ACCESS  read-only
    STATUS      current
    DESCRIPTION "No description yet."

    ::= { dpConfigCryptoCertificateEntry 2 }

--

dpConfigCryptoIdentCredTable OBJECT-TYPE
    SYNTAX      SEQUENCE OF DPConfigCryptoIdentCredEntry
    MAX-ACCESS  not-accessible
    STATUS      current
    DESCRIPTION
        "An identification set consisting of a certificate (which contains a public
        key) and the corresponding private key. The identification set is used as
        the identity of an sslproxy, and the certificate is sent to an SSL peer
        when negotiating an SSL connection. It may also be used as the identity
        when signing, encrypting or decrypting documents."

    ::= { dpConfig 45 }

dpConfigCryptoIdentCredEntry OBJECT-TYPE
    SYNTAX      DPConfigCryptoIdentCredEntry
    MAX-ACCESS  not-accessible
    STATUS      current
    DESCRIPTION "Table row."
    INDEX { dpConfigCryptoIdentCredIndex, IMPLIED dpConfigCryptoIdentCredname }

    ::= { dpConfigCryptoIdentCredTable 1 }

DPConfigCryptoIdentCredEntry ::= SEQUENCE {
    dpConfigCryptoIdentCredIndex    Unsigned32,
    dpConfigCryptoIdentCredname    DisplayString
}

dpConfigCryptoIdentCredIndex OBJECT-TYPE
    SYNTAX      Unsigned32
    MAX-ACCESS  read-only
    STATUS      current
    DESCRIPTION "No description yet."

    ::= { dpConfigCryptoIdentCredEntry 1 }

dpConfigCryptoIdentCredname OBJECT-TYPE
    SYNTAX      DisplayString
    MAX-ACCESS  read-only
    STATUS      current
    DESCRIPTION "No description yet."

    ::= { dpConfigCryptoIdentCredEntry 2 }

--

dpConfigCryptoValCredTable OBJECT-TYPE
    SYNTAX      SEQUENCE OF DPConfigCryptoValCredEntry
    MAX-ACCESS  not-accessible
    STATUS      current
    DESCRIPTION
        "A validation credentials list is used to authenticate certificates that
        are received from SSL peers. It can also be used to validate certificates
        that are used in digital signature and encryption operations. An SSL
        client requires a Validation Credentials object only when it authenticates
        the certificate presented by the remote SSL server. The SSL standard does
        not require authentication of the server certificate. An SSL server
        requires a Validation Credentials object only when it authenticates remote
        SSL clients. The SSL standard does not require authentication of the
        client certificate."

    ::= { dpConfig 46 }

dpConfigCryptoValCredEntry OBJECT-TYPE
    SYNTAX      DPConfigCryptoValCredEntry
    MAX-ACCESS  not-accessible
    STATUS      current
    DESCRIPTION "Table row."
    INDEX { dpConfigCryptoValCredIndex, IMPLIED dpConfigCryptoValCredname }

    ::= { dpConfigCryptoValCredTable 1 }

DPConfigCryptoValCredEntry ::= SEQUENCE {
    dpConfigCryptoValCredIndex    Unsigned32,
    dpConfigCryptoValCredname    DisplayString
}

dpConfigCryptoValCredIndex OBJECT-TYPE
    SYNTAX      Unsigned32
    MAX-ACCESS  read-only
    STATUS      current
    DESCRIPTION "No description yet."

    ::= { dpConfigCryptoValCredEntry 1 }

dpConfigCryptoValCredname OBJECT-TYPE
    SYNTAX      DisplayString
    MAX-ACCESS  read-only
    STATUS      current
    DESCRIPTION "No description yet."

    ::= { dpConfigCryptoValCredEntry 2 }

--

dpConfigCryptoProfileTable OBJECT-TYPE
    SYNTAX      SEQUENCE OF DPConfigCryptoProfileEntry
    MAX-ACCESS  not-accessible
    STATUS      current
    DESCRIPTION
        "A crypto profile describes a set of configuration information for creating
        SSL connections."

    ::= { dpConfig 47 }

dpConfigCryptoProfileEntry OBJECT-TYPE
    SYNTAX      DPConfigCryptoProfileEntry
    MAX-ACCESS  not-accessible
    STATUS      current
    DESCRIPTION "Table row."
    INDEX { dpConfigCryptoProfileIndex, IMPLIED dpConfigCryptoProfilename }

    ::= { dpConfigCryptoProfileTable 1 }

DPConfigCryptoProfileEntry ::= SEQUENCE {
    dpConfigCryptoProfileIndex    Unsigned32,
    dpConfigCryptoProfilename    DisplayString
}

dpConfigCryptoProfileIndex OBJECT-TYPE
    SYNTAX      Unsigned32
    MAX-ACCESS  read-only
    STATUS      current
    DESCRIPTION "No description yet."

    ::= { dpConfigCryptoProfileEntry 1 }

dpConfigCryptoProfilename OBJECT-TYPE
    SYNTAX      DisplayString
    MAX-ACCESS  read-only
    STATUS      current
    DESCRIPTION "No description yet."

    ::= { dpConfigCryptoProfileEntry 2 }

--

dpConfigLogTargetTable OBJECT-TYPE
    SYNTAX      SEQUENCE OF DPConfigLogTargetEntry
    MAX-ACCESS  not-accessible
    STATUS      current
    DESCRIPTION
        "Log targets capture messages that are posted by the various objects and
        services that are running on the appliance. Target types enable additional
        capabilities that include rotating files, encrypting and signing files or
        messages, and sending files to remote servers. Messages in log targets can
        be restricted (filtered) by priority, event code, event category, object
        type, or IP address. By default, a log target cannot accept messages until
        it is subscribed to one or more events."

    ::= { dpConfig 48 }

dpConfigLogTargetEntry OBJECT-TYPE
    SYNTAX      DPConfigLogTargetEntry
    MAX-ACCESS  not-accessible
    STATUS      current
    DESCRIPTION "Table row."
    INDEX { dpConfigLogTargetIndex, IMPLIED dpConfigLogTargetname }

    ::= { dpConfigLogTargetTable 1 }

DPConfigLogTargetEntry ::= SEQUENCE {
    dpConfigLogTargetIndex    Unsigned32,
    dpConfigLogTargetname    DisplayString
}

dpConfigLogTargetIndex OBJECT-TYPE
    SYNTAX      Unsigned32
    MAX-ACCESS  read-only
    STATUS      current
    DESCRIPTION "No description yet."

    ::= { dpConfigLogTargetEntry 1 }

dpConfigLogTargetname OBJECT-TYPE
    SYNTAX      DisplayString
    MAX-ACCESS  read-only
    STATUS      current
    DESCRIPTION "No description yet."

    ::= { dpConfigLogTargetEntry 2 }

--

dpConfigSSHServiceTable OBJECT-TYPE
    SYNTAX      SEQUENCE OF DPConfigSSHServiceEntry
    MAX-ACCESS  not-accessible
    STATUS      current
    DESCRIPTION
        "Modify the configuration of the SSH server."

    ::= { dpConfig 49 }

dpConfigSSHServiceEntry OBJECT-TYPE
    SYNTAX      DPConfigSSHServiceEntry
    MAX-ACCESS  not-accessible
    STATUS      current
    DESCRIPTION "Table row."
    INDEX { dpConfigSSHServiceIndex, IMPLIED dpConfigSSHServicename }

    ::= { dpConfigSSHServiceTable 1 }

DPConfigSSHServiceEntry ::= SEQUENCE {
    dpConfigSSHServiceIndex    Unsigned32,
    dpConfigSSHServicename    DisplayString
}

dpConfigSSHServiceIndex OBJECT-TYPE
    SYNTAX      Unsigned32
    MAX-ACCESS  read-only
    STATUS      current
    DESCRIPTION "No description yet."

    ::= { dpConfigSSHServiceEntry 1 }

dpConfigSSHServicename OBJECT-TYPE
    SYNTAX      DisplayString
    MAX-ACCESS  read-only
    STATUS      current
    DESCRIPTION "No description yet."

    ::= { dpConfigSSHServiceEntry 2 }

--

dpConfigCryptoTable OBJECT-TYPE
    SYNTAX      SEQUENCE OF DPConfigCryptoEntry
    MAX-ACCESS  not-accessible
    STATUS      current
    DESCRIPTION "Table."

    ::= { dpConfig 50 }

dpConfigCryptoEntry OBJECT-TYPE
    SYNTAX      DPConfigCryptoEntry
    MAX-ACCESS  not-accessible
    STATUS      current
    DESCRIPTION "Table row."
    INDEX { dpConfigCryptoIndex, IMPLIED dpConfigCryptoname }

    ::= { dpConfigCryptoTable 1 }

DPConfigCryptoEntry ::= SEQUENCE {
    dpConfigCryptoIndex    Unsigned32,
    dpConfigCryptoname    DisplayString
}

dpConfigCryptoIndex OBJECT-TYPE
    SYNTAX      Unsigned32
    MAX-ACCESS  read-only
    STATUS      current
    DESCRIPTION "No description yet."

    ::= { dpConfigCryptoEntry 1 }

dpConfigCryptoname OBJECT-TYPE
    SYNTAX      DisplayString
    MAX-ACCESS  read-only
    STATUS      current
    DESCRIPTION "No description yet."

    ::= { dpConfigCryptoEntry 2 }

--

dpConfigWebGUITable OBJECT-TYPE
    SYNTAX      SEQUENCE OF DPConfigWebGUIEntry
    MAX-ACCESS  not-accessible
    STATUS      current
    DESCRIPTION
        "Modify the configuration of the web management service."

    ::= { dpConfig 51 }

dpConfigWebGUIEntry OBJECT-TYPE
    SYNTAX      DPConfigWebGUIEntry
    MAX-ACCESS  not-accessible
    STATUS      current
    DESCRIPTION "Table row."
    INDEX { dpConfigWebGUIIndex, IMPLIED dpConfigWebGUIname }

    ::= { dpConfigWebGUITable 1 }

DPConfigWebGUIEntry ::= SEQUENCE {
    dpConfigWebGUIIndex    Unsigned32,
    dpConfigWebGUIname    DisplayString
}

dpConfigWebGUIIndex OBJECT-TYPE
    SYNTAX      Unsigned32
    MAX-ACCESS  read-only
    STATUS      current
    DESCRIPTION "No description yet."

    ::= { dpConfigWebGUIEntry 1 }

dpConfigWebGUIname OBJECT-TYPE
    SYNTAX      DisplayString
    MAX-ACCESS  read-only
    STATUS      current
    DESCRIPTION "No description yet."

    ::= { dpConfigWebGUIEntry 2 }

--

dpConfigEventlogTable OBJECT-TYPE
    SYNTAX      SEQUENCE OF DPConfigEventlogEntry
    MAX-ACCESS  not-accessible
    STATUS      current
    DESCRIPTION "Table."

    ::= { dpConfig 52 }

dpConfigEventlogEntry OBJECT-TYPE
    SYNTAX      DPConfigEventlogEntry
    MAX-ACCESS  not-accessible
    STATUS      current
    DESCRIPTION "Table row."
    INDEX { dpConfigEventlogIndex, IMPLIED dpConfigEventlogname }

    ::= { dpConfigEventlogTable 1 }

DPConfigEventlogEntry ::= SEQUENCE {
    dpConfigEventlogIndex    Unsigned32,
    dpConfigEventlogname    DisplayString
}

dpConfigEventlogIndex OBJECT-TYPE
    SYNTAX      Unsigned32
    MAX-ACCESS  read-only
    STATUS      current
    DESCRIPTION "No description yet."

    ::= { dpConfigEventlogEntry 1 }

dpConfigEventlogname OBJECT-TYPE
    SYNTAX      DisplayString
    MAX-ACCESS  read-only
    STATUS      current
    DESCRIPTION "No description yet."

    ::= { dpConfigEventlogEntry 2 }

--

dpConfigAccessControlTable OBJECT-TYPE
    SYNTAX      SEQUENCE OF DPConfigAccessControlEntry
    MAX-ACCESS  not-accessible
    STATUS      current
    DESCRIPTION "Table."

    ::= { dpConfig 53 }

dpConfigAccessControlEntry OBJECT-TYPE
    SYNTAX      DPConfigAccessControlEntry
    MAX-ACCESS  not-accessible
    STATUS      current
    DESCRIPTION "Table row."
    INDEX { dpConfigAccessControlIndex, IMPLIED dpConfigAccessControlname }

    ::= { dpConfigAccessControlTable 1 }

DPConfigAccessControlEntry ::= SEQUENCE {
    dpConfigAccessControlIndex    Unsigned32,
    dpConfigAccessControlname    DisplayString
}

dpConfigAccessControlIndex OBJECT-TYPE
    SYNTAX      Unsigned32
    MAX-ACCESS  read-only
    STATUS      current
    DESCRIPTION "No description yet."

    ::= { dpConfigAccessControlEntry 1 }

dpConfigAccessControlname OBJECT-TYPE
    SYNTAX      DisplayString
    MAX-ACCESS  read-only
    STATUS      current
    DESCRIPTION "No description yet."

    ::= { dpConfigAccessControlEntry 2 }

--

dpConfigMessageFlowControlTable OBJECT-TYPE
    SYNTAX      SEQUENCE OF DPConfigMessageFlowControlEntry
    MAX-ACCESS  not-accessible
    STATUS      current
    DESCRIPTION "Table."

    ::= { dpConfig 54 }

dpConfigMessageFlowControlEntry OBJECT-TYPE
    SYNTAX      DPConfigMessageFlowControlEntry
    MAX-ACCESS  not-accessible
    STATUS      current
    DESCRIPTION "Table row."
    INDEX { dpConfigMessageFlowControlIndex, IMPLIED dpConfigMessageFlowControlname }

    ::= { dpConfigMessageFlowControlTable 1 }

DPConfigMessageFlowControlEntry ::= SEQUENCE {
    dpConfigMessageFlowControlIndex    Unsigned32,
    dpConfigMessageFlowControlname    DisplayString
}

dpConfigMessageFlowControlIndex OBJECT-TYPE
    SYNTAX      Unsigned32
    MAX-ACCESS  read-only
    STATUS      current
    DESCRIPTION "No description yet."

    ::= { dpConfigMessageFlowControlEntry 1 }

dpConfigMessageFlowControlname OBJECT-TYPE
    SYNTAX      DisplayString
    MAX-ACCESS  read-only
    STATUS      current
    DESCRIPTION "No description yet."

    ::= { dpConfigMessageFlowControlEntry 2 }

--

dpConfigMQConfigurationTable OBJECT-TYPE
    SYNTAX      SEQUENCE OF DPConfigMQConfigurationEntry
    MAX-ACCESS  not-accessible
    STATUS      current
    DESCRIPTION "Table."

    ::= { dpConfig 55 }

dpConfigMQConfigurationEntry OBJECT-TYPE
    SYNTAX      DPConfigMQConfigurationEntry
    MAX-ACCESS  not-accessible
    STATUS      current
    DESCRIPTION "Table row."
    INDEX { dpConfigMQConfigurationIndex, IMPLIED dpConfigMQConfigurationname }

    ::= { dpConfigMQConfigurationTable 1 }

DPConfigMQConfigurationEntry ::= SEQUENCE {
    dpConfigMQConfigurationIndex    Unsigned32,
    dpConfigMQConfigurationname    DisplayString
}

dpConfigMQConfigurationIndex OBJECT-TYPE
    SYNTAX      Unsigned32
    MAX-ACCESS  read-only
    STATUS      current
    DESCRIPTION "No description yet."

    ::= { dpConfigMQConfigurationEntry 1 }

dpConfigMQConfigurationname OBJECT-TYPE
    SYNTAX      DisplayString
    MAX-ACCESS  read-only
    STATUS      current
    DESCRIPTION "No description yet."

    ::= { dpConfigMQConfigurationEntry 2 }

--

dpConfigDeviceSettingsTable OBJECT-TYPE
    SYNTAX      SEQUENCE OF DPConfigDeviceSettingsEntry
    MAX-ACCESS  not-accessible
    STATUS      current
    DESCRIPTION "Table."

    ::= { dpConfig 56 }

dpConfigDeviceSettingsEntry OBJECT-TYPE
    SYNTAX      DPConfigDeviceSettingsEntry
    MAX-ACCESS  not-accessible
    STATUS      current
    DESCRIPTION "Table row."
    INDEX { dpConfigDeviceSettingsIndex, IMPLIED dpConfigDeviceSettingsname }

    ::= { dpConfigDeviceSettingsTable 1 }

DPConfigDeviceSettingsEntry ::= SEQUENCE {
    dpConfigDeviceSettingsIndex    Unsigned32,
    dpConfigDeviceSettingsname    DisplayString
}

dpConfigDeviceSettingsIndex OBJECT-TYPE
    SYNTAX      Unsigned32
    MAX-ACCESS  read-only
    STATUS      current
    DESCRIPTION "No description yet."

    ::= { dpConfigDeviceSettingsEntry 1 }

dpConfigDeviceSettingsname OBJECT-TYPE
    SYNTAX      DisplayString
    MAX-ACCESS  read-only
    STATUS      current
    DESCRIPTION "No description yet."

    ::= { dpConfigDeviceSettingsEntry 2 }

--

dpConfigDeviceManagementServiceTable OBJECT-TYPE
    SYNTAX      SEQUENCE OF DPConfigDeviceManagementServiceEntry
    MAX-ACCESS  not-accessible
    STATUS      current
    DESCRIPTION "Table."

    ::= { dpConfig 57 }

dpConfigDeviceManagementServiceEntry OBJECT-TYPE
    SYNTAX      DPConfigDeviceManagementServiceEntry
    MAX-ACCESS  not-accessible
    STATUS      current
    DESCRIPTION "Table row."
    INDEX { dpConfigDeviceManagementServiceIndex, IMPLIED dpConfigDeviceManagementServicename }

    ::= { dpConfigDeviceManagementServiceTable 1 }

DPConfigDeviceManagementServiceEntry ::= SEQUENCE {
    dpConfigDeviceManagementServiceIndex    Unsigned32,
    dpConfigDeviceManagementServicename    DisplayString
}

dpConfigDeviceManagementServiceIndex OBJECT-TYPE
    SYNTAX      Unsigned32
    MAX-ACCESS  read-only
    STATUS      current
    DESCRIPTION "No description yet."

    ::= { dpConfigDeviceManagementServiceEntry 1 }

dpConfigDeviceManagementServicename OBJECT-TYPE
    SYNTAX      DisplayString
    MAX-ACCESS  read-only
    STATUS      current
    DESCRIPTION "No description yet."

    ::= { dpConfigDeviceManagementServiceEntry 2 }

--

dpConfigNetworkConfigurationTable OBJECT-TYPE
    SYNTAX      SEQUENCE OF DPConfigNetworkConfigurationEntry
    MAX-ACCESS  not-accessible
    STATUS      current
    DESCRIPTION "Table."

    ::= { dpConfig 58 }

dpConfigNetworkConfigurationEntry OBJECT-TYPE
    SYNTAX      DPConfigNetworkConfigurationEntry
    MAX-ACCESS  not-accessible
    STATUS      current
    DESCRIPTION "Table row."
    INDEX { dpConfigNetworkConfigurationIndex, IMPLIED dpConfigNetworkConfigurationname }

    ::= { dpConfigNetworkConfigurationTable 1 }

DPConfigNetworkConfigurationEntry ::= SEQUENCE {
    dpConfigNetworkConfigurationIndex    Unsigned32,
    dpConfigNetworkConfigurationname    DisplayString
}

dpConfigNetworkConfigurationIndex OBJECT-TYPE
    SYNTAX      Unsigned32
    MAX-ACCESS  read-only
    STATUS      current
    DESCRIPTION "No description yet."

    ::= { dpConfigNetworkConfigurationEntry 1 }

dpConfigNetworkConfigurationname OBJECT-TYPE
    SYNTAX      DisplayString
    MAX-ACCESS  read-only
    STATUS      current
    DESCRIPTION "No description yet."

    ::= { dpConfigNetworkConfigurationEntry 2 }

--

dpConfigLogLabelTable OBJECT-TYPE
    SYNTAX      SEQUENCE OF DPConfigLogLabelEntry
    MAX-ACCESS  not-accessible
    STATUS      current
    DESCRIPTION
        "Allows for the configuration of custom log categories"

    ::= { dpConfig 59 }

dpConfigLogLabelEntry OBJECT-TYPE
    SYNTAX      DPConfigLogLabelEntry
    MAX-ACCESS  not-accessible
    STATUS      current
    DESCRIPTION "Table row."
    INDEX { dpConfigLogLabelIndex, IMPLIED dpConfigLogLabelname }

    ::= { dpConfigLogLabelTable 1 }

DPConfigLogLabelEntry ::= SEQUENCE {
    dpConfigLogLabelIndex    Unsigned32,
    dpConfigLogLabelname    DisplayString
}

dpConfigLogLabelIndex OBJECT-TYPE
    SYNTAX      Unsigned32
    MAX-ACCESS  read-only
    STATUS      current
    DESCRIPTION "No description yet."

    ::= { dpConfigLogLabelEntry 1 }

dpConfigLogLabelname OBJECT-TYPE
    SYNTAX      DisplayString
    MAX-ACCESS  read-only
    STATUS      current
    DESCRIPTION "No description yet."

    ::= { dpConfigLogLabelEntry 2 }

--

dpConfigMgmtInterfaceTable OBJECT-TYPE
    SYNTAX      SEQUENCE OF DPConfigMgmtInterfaceEntry
    MAX-ACCESS  not-accessible
    STATUS      current
    DESCRIPTION
        "Modify the configuration of the XML management interface. This interface
        is described in the store:///xml-mgmt.wsdl file in the 'default' domain."

    ::= { dpConfig 60 }

dpConfigMgmtInterfaceEntry OBJECT-TYPE
    SYNTAX      DPConfigMgmtInterfaceEntry
    MAX-ACCESS  not-accessible
    STATUS      current
    DESCRIPTION "Table row."
    INDEX { dpConfigMgmtInterfaceIndex, IMPLIED dpConfigMgmtInterfacename }

    ::= { dpConfigMgmtInterfaceTable 1 }

DPConfigMgmtInterfaceEntry ::= SEQUENCE {
    dpConfigMgmtInterfaceIndex    Unsigned32,
    dpConfigMgmtInterfacename    DisplayString
}

dpConfigMgmtInterfaceIndex OBJECT-TYPE
    SYNTAX      Unsigned32
    MAX-ACCESS  read-only
    STATUS      current
    DESCRIPTION "No description yet."

    ::= { dpConfigMgmtInterfaceEntry 1 }

dpConfigMgmtInterfacename OBJECT-TYPE
    SYNTAX      DisplayString
    MAX-ACCESS  read-only
    STATUS      current
    DESCRIPTION "No description yet."

    ::= { dpConfigMgmtInterfaceEntry 2 }

--

dpConfigMessageMatchingTable OBJECT-TYPE
    SYNTAX      SEQUENCE OF DPConfigMessageMatchingEntry
    MAX-ACCESS  not-accessible
    STATUS      current
    DESCRIPTION
        "Message Matching determines what messages will be monitored by any monitor
        that uses the Message Matching object. It is a definition of the traffic
        flow that is monitored. To capture all messages, set the HTTP Method field
        to 'any' and leave all other fields blank."

    ::= { dpConfig 61 }

dpConfigMessageMatchingEntry OBJECT-TYPE
    SYNTAX      DPConfigMessageMatchingEntry
    MAX-ACCESS  not-accessible
    STATUS      current
    DESCRIPTION "Table row."
    INDEX { dpConfigMessageMatchingIndex, IMPLIED dpConfigMessageMatchingname }

    ::= { dpConfigMessageMatchingTable 1 }

DPConfigMessageMatchingEntry ::= SEQUENCE {
    dpConfigMessageMatchingIndex    Unsigned32,
    dpConfigMessageMatchingname    DisplayString
}

dpConfigMessageMatchingIndex OBJECT-TYPE
    SYNTAX      Unsigned32
    MAX-ACCESS  read-only
    STATUS      current
    DESCRIPTION "No description yet."

    ::= { dpConfigMessageMatchingEntry 1 }

dpConfigMessageMatchingname OBJECT-TYPE
    SYNTAX      DisplayString
    MAX-ACCESS  read-only
    STATUS      current
    DESCRIPTION "No description yet."

    ::= { dpConfigMessageMatchingEntry 2 }

--

dpConfigMessageTypeTable OBJECT-TYPE
    SYNTAX      SEQUENCE OF DPConfigMessageTypeEntry
    MAX-ACCESS  not-accessible
    STATUS      current
    DESCRIPTION
        "On-Line Help for Message Types"

    ::= { dpConfig 62 }

dpConfigMessageTypeEntry OBJECT-TYPE
    SYNTAX      DPConfigMessageTypeEntry
    MAX-ACCESS  not-accessible
    STATUS      current
    DESCRIPTION "Table row."
    INDEX { dpConfigMessageTypeIndex, IMPLIED dpConfigMessageTypename }

    ::= { dpConfigMessageTypeTable 1 }

DPConfigMessageTypeEntry ::= SEQUENCE {
    dpConfigMessageTypeIndex    Unsigned32,
    dpConfigMessageTypename    DisplayString
}

dpConfigMessageTypeIndex OBJECT-TYPE
    SYNTAX      Unsigned32
    MAX-ACCESS  read-only
    STATUS      current
    DESCRIPTION "No description yet."

    ::= { dpConfigMessageTypeEntry 1 }

dpConfigMessageTypename OBJECT-TYPE
    SYNTAX      DisplayString
    MAX-ACCESS  read-only
    STATUS      current
    DESCRIPTION "No description yet."

    ::= { dpConfigMessageTypeEntry 2 }

--

dpConfigCountMonitorTable OBJECT-TYPE
    SYNTAX      SEQUENCE OF DPConfigCountMonitorEntry
    MAX-ACCESS  not-accessible
    STATUS      current
    DESCRIPTION
        "On-Line Help for Message-Count Monitors"

    ::= { dpConfig 63 }

dpConfigCountMonitorEntry OBJECT-TYPE
    SYNTAX      DPConfigCountMonitorEntry
    MAX-ACCESS  not-accessible
    STATUS      current
    DESCRIPTION "Table row."
    INDEX { dpConfigCountMonitorIndex, IMPLIED dpConfigCountMonitorname }

    ::= { dpConfigCountMonitorTable 1 }

DPConfigCountMonitorEntry ::= SEQUENCE {
    dpConfigCountMonitorIndex    Unsigned32,
    dpConfigCountMonitorname    DisplayString
}

dpConfigCountMonitorIndex OBJECT-TYPE
    SYNTAX      Unsigned32
    MAX-ACCESS  read-only
    STATUS      current
    DESCRIPTION "No description yet."

    ::= { dpConfigCountMonitorEntry 1 }

dpConfigCountMonitorname OBJECT-TYPE
    SYNTAX      DisplayString
    MAX-ACCESS  read-only
    STATUS      current
    DESCRIPTION "No description yet."

    ::= { dpConfigCountMonitorEntry 2 }

--

dpConfigDurationMonitorTable OBJECT-TYPE
    SYNTAX      SEQUENCE OF DPConfigDurationMonitorEntry
    MAX-ACCESS  not-accessible
    STATUS      current
    DESCRIPTION
        "On-Line Help for Message-Duration Monitors. Duration Monitors observe the
        duration, or amount of time, taken to process submissions."

    ::= { dpConfig 64 }

dpConfigDurationMonitorEntry OBJECT-TYPE
    SYNTAX      DPConfigDurationMonitorEntry
    MAX-ACCESS  not-accessible
    STATUS      current
    DESCRIPTION "Table row."
    INDEX { dpConfigDurationMonitorIndex, IMPLIED dpConfigDurationMonitorname }

    ::= { dpConfigDurationMonitorTable 1 }

DPConfigDurationMonitorEntry ::= SEQUENCE {
    dpConfigDurationMonitorIndex    Unsigned32,
    dpConfigDurationMonitorname    DisplayString
}

dpConfigDurationMonitorIndex OBJECT-TYPE
    SYNTAX      Unsigned32
    MAX-ACCESS  read-only
    STATUS      current
    DESCRIPTION "No description yet."

    ::= { dpConfigDurationMonitorEntry 1 }

dpConfigDurationMonitorname OBJECT-TYPE
    SYNTAX      DisplayString
    MAX-ACCESS  read-only
    STATUS      current
    DESCRIPTION "No description yet."

    ::= { dpConfigDurationMonitorEntry 2 }

--

dpConfigFilterActionTable OBJECT-TYPE
    SYNTAX      SEQUENCE OF DPConfigFilterActionEntry
    MAX-ACCESS  not-accessible
    STATUS      current
    DESCRIPTION
        "On-Line Help for Monitor Policies (Filter Actions)"

    ::= { dpConfig 65 }

dpConfigFilterActionEntry OBJECT-TYPE
    SYNTAX      DPConfigFilterActionEntry
    MAX-ACCESS  not-accessible
    STATUS      current
    DESCRIPTION "Table row."
    INDEX { dpConfigFilterActionIndex, IMPLIED dpConfigFilterActionname }

    ::= { dpConfigFilterActionTable 1 }

DPConfigFilterActionEntry ::= SEQUENCE {
    dpConfigFilterActionIndex    Unsigned32,
    dpConfigFilterActionname    DisplayString
}

dpConfigFilterActionIndex OBJECT-TYPE
    SYNTAX      Unsigned32
    MAX-ACCESS  read-only
    STATUS      current
    DESCRIPTION "No description yet."

    ::= { dpConfigFilterActionEntry 1 }

dpConfigFilterActionname OBJECT-TYPE
    SYNTAX      DisplayString
    MAX-ACCESS  read-only
    STATUS      current
    DESCRIPTION "No description yet."

    ::= { dpConfigFilterActionEntry 2 }

--

dpConfigHTTPInputConversionMapTable OBJECT-TYPE
    SYNTAX      SEQUENCE OF DPConfigHTTPInputConversionMapEntry
    MAX-ACCESS  not-accessible
    STATUS      current
    DESCRIPTION
        "This defines the rules for handling HTTP to XML conversion of form values
        in an HTTP GET or POST of a form. There are different conversion
        (Encoding) rules for the values. They control how the value is mapped to
        the contents of its <arg> element in the resulting XML. There is a default
        Encoding, which is all that is required. There can also be specific
        Encodings applied to values based on the name associated with a value,
        which is done using an ordered list of PCREs."

    ::= { dpConfig 66 }

dpConfigHTTPInputConversionMapEntry OBJECT-TYPE
    SYNTAX      DPConfigHTTPInputConversionMapEntry
    MAX-ACCESS  not-accessible
    STATUS      current
    DESCRIPTION "Table row."
    INDEX { dpConfigHTTPInputConversionMapIndex, IMPLIED dpConfigHTTPInputConversionMapname }

    ::= { dpConfigHTTPInputConversionMapTable 1 }

DPConfigHTTPInputConversionMapEntry ::= SEQUENCE {
    dpConfigHTTPInputConversionMapIndex    Unsigned32,
    dpConfigHTTPInputConversionMapname    DisplayString
}

dpConfigHTTPInputConversionMapIndex OBJECT-TYPE
    SYNTAX      Unsigned32
    MAX-ACCESS  read-only
    STATUS      current
    DESCRIPTION "No description yet."

    ::= { dpConfigHTTPInputConversionMapEntry 1 }

dpConfigHTTPInputConversionMapname OBJECT-TYPE
    SYNTAX      DisplayString
    MAX-ACCESS  read-only
    STATUS      current
    DESCRIPTION "No description yet."

    ::= { dpConfigHTTPInputConversionMapEntry 2 }

--

dpConfigCompileOptionsPolicyTable OBJECT-TYPE
    SYNTAX      SEQUENCE OF DPConfigCompileOptionsPolicyEntry
    MAX-ACCESS  not-accessible
    STATUS      current
    DESCRIPTION
        "Configure/Edit Compile Option Policies"

    ::= { dpConfig 68 }

dpConfigCompileOptionsPolicyEntry OBJECT-TYPE
    SYNTAX      DPConfigCompileOptionsPolicyEntry
    MAX-ACCESS  not-accessible
    STATUS      current
    DESCRIPTION "Table row."
    INDEX { dpConfigCompileOptionsPolicyIndex, IMPLIED dpConfigCompileOptionsPolicyname }

    ::= { dpConfigCompileOptionsPolicyTable 1 }

DPConfigCompileOptionsPolicyEntry ::= SEQUENCE {
    dpConfigCompileOptionsPolicyIndex    Unsigned32,
    dpConfigCompileOptionsPolicyname    DisplayString
}

dpConfigCompileOptionsPolicyIndex OBJECT-TYPE
    SYNTAX      Unsigned32
    MAX-ACCESS  read-only
    STATUS      current
    DESCRIPTION "No description yet."

    ::= { dpConfigCompileOptionsPolicyEntry 1 }

dpConfigCompileOptionsPolicyname OBJECT-TYPE
    SYNTAX      DisplayString
    MAX-ACCESS  read-only
    STATUS      current
    DESCRIPTION "No description yet."

    ::= { dpConfigCompileOptionsPolicyEntry 2 }

--

dpConfigXPathRoutingMapTable OBJECT-TYPE
    SYNTAX      SEQUENCE OF DPConfigXPathRoutingMapEntry
    MAX-ACCESS  not-accessible
    STATUS      current
    DESCRIPTION
        "An XPath Routing Map matches XPath expressions with corresponding
        destination URLs. When the XPath expression evaluates to true when applied
        to the message submitted, the target destination for the message is set to
        the corresponding URL. Use the Rules tab to establish these mappings. Use
        the Namespace Mapping tab to determine Namespace URIs for namespaces used
        in the XPath Expressions."

    ::= { dpConfig 69 }

dpConfigXPathRoutingMapEntry OBJECT-TYPE
    SYNTAX      DPConfigXPathRoutingMapEntry
    MAX-ACCESS  not-accessible
    STATUS      current
    DESCRIPTION "Table row."
    INDEX { dpConfigXPathRoutingMapIndex, IMPLIED dpConfigXPathRoutingMapname }

    ::= { dpConfigXPathRoutingMapTable 1 }

DPConfigXPathRoutingMapEntry ::= SEQUENCE {
    dpConfigXPathRoutingMapIndex    Unsigned32,
    dpConfigXPathRoutingMapname    DisplayString
}

dpConfigXPathRoutingMapIndex OBJECT-TYPE
    SYNTAX      Unsigned32
    MAX-ACCESS  read-only
    STATUS      current
    DESCRIPTION "No description yet."

    ::= { dpConfigXPathRoutingMapEntry 1 }

dpConfigXPathRoutingMapname OBJECT-TYPE
    SYNTAX      DisplayString
    MAX-ACCESS  read-only
    STATUS      current
    DESCRIPTION "No description yet."

    ::= { dpConfigXPathRoutingMapEntry 2 }

--

dpConfigSchemaExceptionMapTable OBJECT-TYPE
    SYNTAX      SEQUENCE OF DPConfigSchemaExceptionMapEntry
    MAX-ACCESS  not-accessible
    STATUS      current
    DESCRIPTION
        "This object describes exceptions to an XML Schema by identifying elements
        of the schema that may be encrypted in an instance document. When Schema
        Validation is performed on the document using this Exception Map,
        encrypted elements are considered valid when they appear in place of the
        specified elements."

    ::= { dpConfig 70 }

dpConfigSchemaExceptionMapEntry OBJECT-TYPE
    SYNTAX      DPConfigSchemaExceptionMapEntry
    MAX-ACCESS  not-accessible
    STATUS      current
    DESCRIPTION "Table row."
    INDEX { dpConfigSchemaExceptionMapIndex, IMPLIED dpConfigSchemaExceptionMapname }

    ::= { dpConfigSchemaExceptionMapTable 1 }

DPConfigSchemaExceptionMapEntry ::= SEQUENCE {
    dpConfigSchemaExceptionMapIndex    Unsigned32,
    dpConfigSchemaExceptionMapname    DisplayString
}

dpConfigSchemaExceptionMapIndex OBJECT-TYPE
    SYNTAX      Unsigned32
    MAX-ACCESS  read-only
    STATUS      current
    DESCRIPTION "No description yet."

    ::= { dpConfigSchemaExceptionMapEntry 1 }

dpConfigSchemaExceptionMapname OBJECT-TYPE
    SYNTAX      DisplayString
    MAX-ACCESS  read-only
    STATUS      current
    DESCRIPTION "No description yet."

    ::= { dpConfigSchemaExceptionMapEntry 2 }

--

dpConfigReserved71Table OBJECT-TYPE
    SYNTAX      SEQUENCE OF DPConfigReserved71Entry
    MAX-ACCESS  not-accessible
    STATUS      current
    DESCRIPTION "Table."

    ::= { dpConfig 71 }

dpConfigReserved71Entry OBJECT-TYPE
    SYNTAX      DPConfigReserved71Entry
    MAX-ACCESS  not-accessible
    STATUS      current
    DESCRIPTION "Table row."
    INDEX { dpConfigReserved71Index, IMPLIED dpConfigReserved71name }

    ::= { dpConfigReserved71Table 1 }

DPConfigReserved71Entry ::= SEQUENCE {
    dpConfigReserved71Index    Unsigned32,
    dpConfigReserved71name    DisplayString
}

dpConfigReserved71Index OBJECT-TYPE
    SYNTAX      Unsigned32
    MAX-ACCESS  read-only
    STATUS      current
    DESCRIPTION "No description yet."

    ::= { dpConfigReserved71Entry 1 }

dpConfigReserved71name OBJECT-TYPE
    SYNTAX      DisplayString
    MAX-ACCESS  read-only
    STATUS      current
    DESCRIPTION "No description yet."

    ::= { dpConfigReserved71Entry 2 }

--

dpConfigDocumentCryptoMapTable OBJECT-TYPE
    SYNTAX      SEQUENCE OF DPConfigDocumentCryptoMapEntry
    MAX-ACCESS  not-accessible
    STATUS      current
    DESCRIPTION
        "A Document Crypto Map indicates which elements, of a complete schema, to
        encrypt or decrypt. The indicated element or elements may also be signed."

    ::= { dpConfig 72 }

dpConfigDocumentCryptoMapEntry OBJECT-TYPE
    SYNTAX      DPConfigDocumentCryptoMapEntry
    MAX-ACCESS  not-accessible
    STATUS      current
    DESCRIPTION "Table row."
    INDEX { dpConfigDocumentCryptoMapIndex, IMPLIED dpConfigDocumentCryptoMapname }

    ::= { dpConfigDocumentCryptoMapTable 1 }

DPConfigDocumentCryptoMapEntry ::= SEQUENCE {
    dpConfigDocumentCryptoMapIndex    Unsigned32,
    dpConfigDocumentCryptoMapname    DisplayString
}

dpConfigDocumentCryptoMapIndex OBJECT-TYPE
    SYNTAX      Unsigned32
    MAX-ACCESS  read-only
    STATUS      current
    DESCRIPTION "No description yet."

    ::= { dpConfigDocumentCryptoMapEntry 1 }

dpConfigDocumentCryptoMapname OBJECT-TYPE
    SYNTAX      DisplayString
    MAX-ACCESS  read-only
    STATUS      current
    DESCRIPTION "No description yet."

    ::= { dpConfigDocumentCryptoMapEntry 2 }

--

dpConfigTAMTable OBJECT-TYPE
    SYNTAX      SEQUENCE OF DPConfigTAMEntry
    MAX-ACCESS  not-accessible
    STATUS      current
    DESCRIPTION
        "A DataPower appliance can support multiple IBM Security Access Manager
        registry types: LDAP or Microsoft Active Directory. Support for the
        registry type is established for each Access Manager client that starts
        according to its configuration."

    ::= { dpConfig 73 }

dpConfigTAMEntry OBJECT-TYPE
    SYNTAX      DPConfigTAMEntry
    MAX-ACCESS  not-accessible
    STATUS      current
    DESCRIPTION "Table row."
    INDEX { dpConfigTAMIndex, IMPLIED dpConfigTAMname }

    ::= { dpConfigTAMTable 1 }

DPConfigTAMEntry ::= SEQUENCE {
    dpConfigTAMIndex    Unsigned32,
    dpConfigTAMname    DisplayString
}

dpConfigTAMIndex OBJECT-TYPE
    SYNTAX      Unsigned32
    MAX-ACCESS  read-only
    STATUS      current
    DESCRIPTION "No description yet."

    ::= { dpConfigTAMEntry 1 }

dpConfigTAMname OBJECT-TYPE
    SYNTAX      DisplayString
    MAX-ACCESS  read-only
    STATUS      current
    DESCRIPTION "No description yet."

    ::= { dpConfigTAMEntry 2 }

--

dpConfigDomainTable OBJECT-TYPE
    SYNTAX      SEQUENCE OF DPConfigDomainEntry
    MAX-ACCESS  not-accessible
    STATUS      current
    DESCRIPTION
        "An application domain contains the resources that support DataPower
        services. A DataPower supports multiple application domains. Application
        domains can share read access to files in their local: directory. All
        application domains share the contents of the store: directory. After a
        user logs in to an application domain, everything the user does applies to
        only that application domain. Except for the default application domain,
        all application domains can be restarted independently. For the default
        application domain, you must restart the DataPower Gateway. When an
        application domain or the DataPower Gateway is restarted, the persisted
        configuration is used. The persisted configuration can differ from the
        running configuration. The configuration of an application domain can be
        locally stored or can be retrieved from a remote server. The use of a
        remote configuration file enables centralized management of application
        domains."

    ::= { dpConfig 74 }

dpConfigDomainEntry OBJECT-TYPE
    SYNTAX      DPConfigDomainEntry
    MAX-ACCESS  not-accessible
    STATUS      current
    DESCRIPTION "Table row."
    INDEX { dpConfigDomainIndex, IMPLIED dpConfigDomainname }

    ::= { dpConfigDomainTable 1 }

DPConfigDomainEntry ::= SEQUENCE {
    dpConfigDomainIndex    Unsigned32,
    dpConfigDomainname    DisplayString
}

dpConfigDomainIndex OBJECT-TYPE
    SYNTAX      Unsigned32
    MAX-ACCESS  read-only
    STATUS      current
    DESCRIPTION "No description yet."

    ::= { dpConfigDomainEntry 1 }

dpConfigDomainname OBJECT-TYPE
    SYNTAX      DisplayString
    MAX-ACCESS  read-only
    STATUS      current
    DESCRIPTION "No description yet."

    ::= { dpConfigDomainEntry 2 }

--

dpConfigTimeSettingsTable OBJECT-TYPE
    SYNTAX      SEQUENCE OF DPConfigTimeSettingsEntry
    MAX-ACCESS  not-accessible
    STATUS      current
    DESCRIPTION
        "The time zone for the appliance. The time zone affects the time that the
        appliance displays. All time stamps in the CLI and GUI use this time zone.
        #b#Note: #/b#The appliance clock runs on Coordinated Universal Time (UTC).
        When daylight saving time (DST), or summer time, applies to a time zone,
        the appliance adjusts the time when a DST boundary is crossed."

    ::= { dpConfig 75 }

dpConfigTimeSettingsEntry OBJECT-TYPE
    SYNTAX      DPConfigTimeSettingsEntry
    MAX-ACCESS  not-accessible
    STATUS      current
    DESCRIPTION "Table row."
    INDEX { dpConfigTimeSettingsIndex, IMPLIED dpConfigTimeSettingsname }

    ::= { dpConfigTimeSettingsTable 1 }

DPConfigTimeSettingsEntry ::= SEQUENCE {
    dpConfigTimeSettingsIndex    Unsigned32,
    dpConfigTimeSettingsname    DisplayString
}

dpConfigTimeSettingsIndex OBJECT-TYPE
    SYNTAX      Unsigned32
    MAX-ACCESS  read-only
    STATUS      current
    DESCRIPTION "No description yet."

    ::= { dpConfigTimeSettingsEntry 1 }

dpConfigTimeSettingsname OBJECT-TYPE
    SYNTAX      DisplayString
    MAX-ACCESS  read-only
    STATUS      current
    DESCRIPTION "No description yet."

    ::= { dpConfigTimeSettingsEntry 2 }

--

dpConfigDynamicXMLContentMapTable OBJECT-TYPE
    SYNTAX      SEQUENCE OF DPConfigDynamicXMLContentMapEntry
    MAX-ACCESS  not-accessible
    STATUS      current
    DESCRIPTION "Table."

    ::= { dpConfig 77 }

dpConfigDynamicXMLContentMapEntry OBJECT-TYPE
    SYNTAX      DPConfigDynamicXMLContentMapEntry
    MAX-ACCESS  not-accessible
    STATUS      current
    DESCRIPTION "Table row."
    INDEX { dpConfigDynamicXMLContentMapIndex, IMPLIED dpConfigDynamicXMLContentMapname }

    ::= { dpConfigDynamicXMLContentMapTable 1 }

DPConfigDynamicXMLContentMapEntry ::= SEQUENCE {
    dpConfigDynamicXMLContentMapIndex    Unsigned32,
    dpConfigDynamicXMLContentMapname    DisplayString
}

dpConfigDynamicXMLContentMapIndex OBJECT-TYPE
    SYNTAX      Unsigned32
    MAX-ACCESS  read-only
    STATUS      current
    DESCRIPTION "No description yet."

    ::= { dpConfigDynamicXMLContentMapEntry 1 }

dpConfigDynamicXMLContentMapname OBJECT-TYPE
    SYNTAX      DisplayString
    MAX-ACCESS  read-only
    STATUS      current
    DESCRIPTION "No description yet."

    ::= { dpConfigDynamicXMLContentMapEntry 2 }

--

dpConfigDynamicStylesheetTable OBJECT-TYPE
    SYNTAX      SEQUENCE OF DPConfigDynamicStylesheetEntry
    MAX-ACCESS  not-accessible
    STATUS      current
    DESCRIPTION "Table."

    ::= { dpConfig 78 }

dpConfigDynamicStylesheetEntry OBJECT-TYPE
    SYNTAX      DPConfigDynamicStylesheetEntry
    MAX-ACCESS  not-accessible
    STATUS      current
    DESCRIPTION "Table row."
    INDEX { dpConfigDynamicStylesheetIndex, IMPLIED dpConfigDynamicStylesheetname }

    ::= { dpConfigDynamicStylesheetTable 1 }

DPConfigDynamicStylesheetEntry ::= SEQUENCE {
    dpConfigDynamicStylesheetIndex    Unsigned32,
    dpConfigDynamicStylesheetname    DisplayString
}

dpConfigDynamicStylesheetIndex OBJECT-TYPE
    SYNTAX      Unsigned32
    MAX-ACCESS  read-only
    STATUS      current
    DESCRIPTION "No description yet."

    ::= { dpConfigDynamicStylesheetEntry 1 }

dpConfigDynamicStylesheetname OBJECT-TYPE
    SYNTAX      DisplayString
    MAX-ACCESS  read-only
    STATUS      current
    DESCRIPTION "No description yet."

    ::= { dpConfigDynamicStylesheetEntry 2 }

--

dpConfigDynamicSchemaTable OBJECT-TYPE
    SYNTAX      SEQUENCE OF DPConfigDynamicSchemaEntry
    MAX-ACCESS  not-accessible
    STATUS      current
    DESCRIPTION "Table."

    ::= { dpConfig 79 }

dpConfigDynamicSchemaEntry OBJECT-TYPE
    SYNTAX      DPConfigDynamicSchemaEntry
    MAX-ACCESS  not-accessible
    STATUS      current
    DESCRIPTION "Table row."
    INDEX { dpConfigDynamicSchemaIndex, IMPLIED dpConfigDynamicSchemaname }

    ::= { dpConfigDynamicSchemaTable 1 }

DPConfigDynamicSchemaEntry ::= SEQUENCE {
    dpConfigDynamicSchemaIndex    Unsigned32,
    dpConfigDynamicSchemaname    DisplayString
}

dpConfigDynamicSchemaIndex OBJECT-TYPE
    SYNTAX      Unsigned32
    MAX-ACCESS  read-only
    STATUS      current
    DESCRIPTION "No description yet."

    ::= { dpConfigDynamicSchemaEntry 1 }

dpConfigDynamicSchemaname OBJECT-TYPE
    SYNTAX      DisplayString
    MAX-ACCESS  read-only
    STATUS      current
    DESCRIPTION "No description yet."

    ::= { dpConfigDynamicSchemaEntry 2 }

--

dpConfigAccessControlListTable OBJECT-TYPE
    SYNTAX      SEQUENCE OF DPConfigAccessControlListEntry
    MAX-ACCESS  not-accessible
    STATUS      current
    DESCRIPTION
        "An access control list (ACL) consists of a sequence of allow and deny
        clauses. Each clause identifies an IP address or range of addresses that
        allow or deny access to a service. After associating an ACL with a
        service, the ACL grants access to addresses in allow clauses and denies
        access to all other addresses. Candidate addresses are sequentially
        evaluated against each clause in the ACL. A candidate address is denied or
        granted access in accordance with the first clause that matches.
        Consequently, the order of the clauses in the ACL is vital. An ACL with
        only deny clauses effectively disables a service by denying access to all
        addresses. To complete the ACL, include an allow clause to ensure that all
        addresses that are not explicitly denied access are granted access."

    ::= { dpConfig 80 }

dpConfigAccessControlListEntry OBJECT-TYPE
    SYNTAX      DPConfigAccessControlListEntry
    MAX-ACCESS  not-accessible
    STATUS      current
    DESCRIPTION "Table row."
    INDEX { dpConfigAccessControlListIndex, IMPLIED dpConfigAccessControlListname }

    ::= { dpConfigAccessControlListTable 1 }

DPConfigAccessControlListEntry ::= SEQUENCE {
    dpConfigAccessControlListIndex    Unsigned32,
    dpConfigAccessControlListname    DisplayString
}

dpConfigAccessControlListIndex OBJECT-TYPE
    SYNTAX      Unsigned32
    MAX-ACCESS  read-only
    STATUS      current
    DESCRIPTION "No description yet."

    ::= { dpConfigAccessControlListEntry 1 }

dpConfigAccessControlListname OBJECT-TYPE
    SYNTAX      DisplayString
    MAX-ACCESS  read-only
    STATUS      current
    DESCRIPTION "No description yet."

    ::= { dpConfigAccessControlListEntry 2 }

--

dpConfigImportPackageTable OBJECT-TYPE
    SYNTAX      SEQUENCE OF DPConfigImportPackageEntry
    MAX-ACCESS  not-accessible
    STATUS      current
    DESCRIPTION
        "Import Package allows the system to import a configuration package from an
        external server, such as a centralized configuration server, when the
        configuration of the DataPower system is reloaded (such as during a
        reboot). This package can optionally overwrite existing files or objects.
        An import package object specifies a source, content type and import
        parameters for a single import bundle."

    ::= { dpConfig 81 }

dpConfigImportPackageEntry OBJECT-TYPE
    SYNTAX      DPConfigImportPackageEntry
    MAX-ACCESS  not-accessible
    STATUS      current
    DESCRIPTION "Table row."
    INDEX { dpConfigImportPackageIndex, IMPLIED dpConfigImportPackagename }

    ::= { dpConfigImportPackageTable 1 }

DPConfigImportPackageEntry ::= SEQUENCE {
    dpConfigImportPackageIndex    Unsigned32,
    dpConfigImportPackagename    DisplayString
}

dpConfigImportPackageIndex OBJECT-TYPE
    SYNTAX      Unsigned32
    MAX-ACCESS  read-only
    STATUS      current
    DESCRIPTION "No description yet."

    ::= { dpConfigImportPackageEntry 1 }

dpConfigImportPackagename OBJECT-TYPE
    SYNTAX      DisplayString
    MAX-ACCESS  read-only
    STATUS      current
    DESCRIPTION "No description yet."

    ::= { dpConfigImportPackageEntry 2 }

--

dpConfigMQhostTable OBJECT-TYPE
    SYNTAX      SEQUENCE OF DPConfigMQhostEntry
    MAX-ACCESS  not-accessible
    STATUS      current
    DESCRIPTION "Table."

    ::= { dpConfig 82 }

dpConfigMQhostEntry OBJECT-TYPE
    SYNTAX      DPConfigMQhostEntry
    MAX-ACCESS  not-accessible
    STATUS      current
    DESCRIPTION "Table row."
    INDEX { dpConfigMQhostIndex, IMPLIED dpConfigMQhostname }

    ::= { dpConfigMQhostTable 1 }

DPConfigMQhostEntry ::= SEQUENCE {
    dpConfigMQhostIndex    Unsigned32,
    dpConfigMQhostname    DisplayString
}

dpConfigMQhostIndex OBJECT-TYPE
    SYNTAX      Unsigned32
    MAX-ACCESS  read-only
    STATUS      current
    DESCRIPTION "No description yet."

    ::= { dpConfigMQhostEntry 1 }

dpConfigMQhostname OBJECT-TYPE
    SYNTAX      DisplayString
    MAX-ACCESS  read-only
    STATUS      current
    DESCRIPTION "No description yet."

    ::= { dpConfigMQhostEntry 2 }

--

dpConfigMQproxyTable OBJECT-TYPE
    SYNTAX      SEQUENCE OF DPConfigMQproxyEntry
    MAX-ACCESS  not-accessible
    STATUS      current
    DESCRIPTION "Table."

    ::= { dpConfig 83 }

dpConfigMQproxyEntry OBJECT-TYPE
    SYNTAX      DPConfigMQproxyEntry
    MAX-ACCESS  not-accessible
    STATUS      current
    DESCRIPTION "Table row."
    INDEX { dpConfigMQproxyIndex, IMPLIED dpConfigMQproxyname }

    ::= { dpConfigMQproxyTable 1 }

DPConfigMQproxyEntry ::= SEQUENCE {
    dpConfigMQproxyIndex    Unsigned32,
    dpConfigMQproxyname    DisplayString
}

dpConfigMQproxyIndex OBJECT-TYPE
    SYNTAX      Unsigned32
    MAX-ACCESS  read-only
    STATUS      current
    DESCRIPTION "No description yet."

    ::= { dpConfigMQproxyEntry 1 }

dpConfigMQproxyname OBJECT-TYPE
    SYNTAX      DisplayString
    MAX-ACCESS  read-only
    STATUS      current
    DESCRIPTION "No description yet."

    ::= { dpConfigMQproxyEntry 2 }

--

dpConfigLoadBalancerGroupTable OBJECT-TYPE
    SYNTAX      SEQUENCE OF DPConfigLoadBalancerGroupEntry
    MAX-ACCESS  not-accessible
    STATUS      current
    DESCRIPTION
        "The DataPower device distributes traffic to members of a Load Balancer
        Group. These are back end servers and not additional DataPower devices. A
        Load Balancer Group lists members of a virtual server group and sets the
        algorithm for balancing them. Periodic health checks can be performed.
        Load Balancers may also be used to provide redundant LDAP server access.
        Once created, a top-level service (such as Multi-Protocol Gateway or XML
        Firewall) can use a Load Balancer Group by associating it with an XML
        manager that is associated with the top-level service. The back end
        destination URL is set to the name of the Load Balancer Group (example:
        'BackEndServers')."

    ::= { dpConfig 84 }

dpConfigLoadBalancerGroupEntry OBJECT-TYPE
    SYNTAX      DPConfigLoadBalancerGroupEntry
    MAX-ACCESS  not-accessible
    STATUS      current
    DESCRIPTION "Table row."
    INDEX { dpConfigLoadBalancerGroupIndex, IMPLIED dpConfigLoadBalancerGroupname }

    ::= { dpConfigLoadBalancerGroupTable 1 }

DPConfigLoadBalancerGroupEntry ::= SEQUENCE {
    dpConfigLoadBalancerGroupIndex    Unsigned32,
    dpConfigLoadBalancerGroupname    DisplayString
}

dpConfigLoadBalancerGroupIndex OBJECT-TYPE
    SYNTAX      Unsigned32
    MAX-ACCESS  read-only
    STATUS      current
    DESCRIPTION "No description yet."

    ::= { dpConfigLoadBalancerGroupEntry 1 }

dpConfigLoadBalancerGroupname OBJECT-TYPE
    SYNTAX      DisplayString
    MAX-ACCESS  read-only
    STATUS      current
    DESCRIPTION "No description yet."

    ::= { dpConfigLoadBalancerGroupEntry 2 }

--

dpConfigRBMSettingsTable OBJECT-TYPE
    SYNTAX      SEQUENCE OF DPConfigRBMSettingsEntry
    MAX-ACCESS  not-accessible
    STATUS      current
    DESCRIPTION
        "Manage role-based management (RBM) settings: RBM, password policy, and
        account policy RBM consists of the following capabilities: Authenticating
        users, evaluating the access profile, enforcing access to resources The
        password policy sets the password requirements for local user accounts.
        The account policy sets the lockout behavior and the timeout for CLI
        sessions."

    ::= { dpConfig 85 }

dpConfigRBMSettingsEntry OBJECT-TYPE
    SYNTAX      DPConfigRBMSettingsEntry
    MAX-ACCESS  not-accessible
    STATUS      current
    DESCRIPTION "Table row."
    INDEX { dpConfigRBMSettingsIndex, IMPLIED dpConfigRBMSettingsname }

    ::= { dpConfigRBMSettingsTable 1 }

DPConfigRBMSettingsEntry ::= SEQUENCE {
    dpConfigRBMSettingsIndex    Unsigned32,
    dpConfigRBMSettingsname    DisplayString
}

dpConfigRBMSettingsIndex OBJECT-TYPE
    SYNTAX      Unsigned32
    MAX-ACCESS  read-only
    STATUS      current
    DESCRIPTION "No description yet."

    ::= { dpConfigRBMSettingsEntry 1 }

dpConfigRBMSettingsname OBJECT-TYPE
    SYNTAX      DisplayString
    MAX-ACCESS  read-only
    STATUS      current
    DESCRIPTION "No description yet."

    ::= { dpConfigRBMSettingsEntry 2 }

--

dpConfigIncludeConfigTable OBJECT-TYPE
    SYNTAX      SEQUENCE OF DPConfigIncludeConfigEntry
    MAX-ACCESS  not-accessible
    STATUS      current
    DESCRIPTION
        "Allows the inclusion of external configuration files during startup. The
        included configuration files may reside on the local device or on a remote
        host."

    ::= { dpConfig 86 }

dpConfigIncludeConfigEntry OBJECT-TYPE
    SYNTAX      DPConfigIncludeConfigEntry
    MAX-ACCESS  not-accessible
    STATUS      current
    DESCRIPTION "Table row."
    INDEX { dpConfigIncludeConfigIndex, IMPLIED dpConfigIncludeConfigname }

    ::= { dpConfigIncludeConfigTable 1 }

DPConfigIncludeConfigEntry ::= SEQUENCE {
    dpConfigIncludeConfigIndex    Unsigned32,
    dpConfigIncludeConfigname    DisplayString
}

dpConfigIncludeConfigIndex OBJECT-TYPE
    SYNTAX      Unsigned32
    MAX-ACCESS  read-only
    STATUS      current
    DESCRIPTION "No description yet."

    ::= { dpConfigIncludeConfigEntry 1 }

dpConfigIncludeConfigname OBJECT-TYPE
    SYNTAX      DisplayString
    MAX-ACCESS  read-only
    STATUS      current
    DESCRIPTION "No description yet."

    ::= { dpConfigIncludeConfigEntry 2 }

--

dpConfigCertMonitorTable OBJECT-TYPE
    SYNTAX      SEQUENCE OF DPConfigCertMonitorEntry
    MAX-ACCESS  not-accessible
    STATUS      current
    DESCRIPTION
        "The Certificate Monitor periodically checks all X.509 certificates stored
        on the device for expiration. The monitor automatically creates a log
        message for each certificate that is within the Reminder time of
        expiration. Expired certificates may be automatically disabled. Note that
        the Monitor checks all certificates immediately when the Monitor is first
        enabled."

    ::= { dpConfig 87 }

dpConfigCertMonitorEntry OBJECT-TYPE
    SYNTAX      DPConfigCertMonitorEntry
    MAX-ACCESS  not-accessible
    STATUS      current
    DESCRIPTION "Table row."
    INDEX { dpConfigCertMonitorIndex, IMPLIED dpConfigCertMonitorname }

    ::= { dpConfigCertMonitorTable 1 }

DPConfigCertMonitorEntry ::= SEQUENCE {
    dpConfigCertMonitorIndex    Unsigned32,
    dpConfigCertMonitorname    DisplayString
}

dpConfigCertMonitorIndex OBJECT-TYPE
    SYNTAX      Unsigned32
    MAX-ACCESS  read-only
    STATUS      current
    DESCRIPTION "No description yet."

    ::= { dpConfigCertMonitorEntry 1 }

dpConfigCertMonitorname OBJECT-TYPE
    SYNTAX      DisplayString
    MAX-ACCESS  read-only
    STATUS      current
    DESCRIPTION "No description yet."

    ::= { dpConfigCertMonitorEntry 2 }

--

dpConfigHostAliasTable OBJECT-TYPE
    SYNTAX      SEQUENCE OF DPConfigHostAliasEntry
    MAX-ACCESS  not-accessible
    STATUS      current
    DESCRIPTION
        "A host alias is a map between a local IP address to a local alias. The
        host alias is resolved like a static host entry. Host aliases provide a
        level of abstraction between concrete network addresses and configuration.
        You can use host aliases where you can define local IP addresses. Host
        aliases ease the export and migration of service among DataPower
        appliances. The alias is exported, but the alias map is not. If the alias
        is defined on the destination system, the alias resolves to the IP address
        that is defined on the destination system."

    ::= { dpConfig 88 }

dpConfigHostAliasEntry OBJECT-TYPE
    SYNTAX      DPConfigHostAliasEntry
    MAX-ACCESS  not-accessible
    STATUS      current
    DESCRIPTION "Table row."
    INDEX { dpConfigHostAliasIndex, IMPLIED dpConfigHostAliasname }

    ::= { dpConfigHostAliasTable 1 }

DPConfigHostAliasEntry ::= SEQUENCE {
    dpConfigHostAliasIndex    Unsigned32,
    dpConfigHostAliasname    DisplayString
}

dpConfigHostAliasIndex OBJECT-TYPE
    SYNTAX      Unsigned32
    MAX-ACCESS  read-only
    STATUS      current
    DESCRIPTION "No description yet."

    ::= { dpConfigHostAliasEntry 1 }

dpConfigHostAliasname OBJECT-TYPE
    SYNTAX      DisplayString
    MAX-ACCESS  read-only
    STATUS      current
    DESCRIPTION "No description yet."

    ::= { dpConfigHostAliasEntry 2 }

--

dpConfigAAAPolicyTable OBJECT-TYPE
    SYNTAX      SEQUENCE OF DPConfigAAAPolicyEntry
    MAX-ACCESS  not-accessible
    STATUS      current
    DESCRIPTION
        "An AAA policy establishes the configuration to support the authentication
        and authorization of users requesting resources from the back-end servers.
        An AAA policy consists of the following components. Identity extraction
        One of many methods that discovers which identity is asserted in the
        service request. This processing phase answers the question, 'What is your
        name?' Authentication One of many methods that authenticates the asserted
        identity. Methods include communication with external authorities, such as
        an LDAP server. The identity is accepted as authentic or rejected. When
        authenticated successfully, the identity is used as a credential. Resource
        extraction One of many methods that discovers which resource service is
        requested (such as query an account or perform an update) This processing
        phase answers the question, 'What do you want to do?' Credential mapping
        While an identity can be authenticated by one authority as valid, this
        identity or credential might not be known to the authority that authorizes
        the requested resource. This processing phase allows the mapping of
        credentials from one form to another for interoperability between systems.
        Resource mapping While a resource can be identified from the service
        request, this resource name might not be known to the authority that
        authorizes use of the requested resource. This processing phase allows the
        mapping of resource names from one form to another for interoperability
        between systems. Authorization The combination of the authenticated and
        possibly remapped credential with the requested and possibly remapped
        resource are submitted to an authority for authorization. That authority
        could reside elsewhere on the network. The request for service is accepted
        or rejected. Postprocessing Additional processing to perform after
        authorization, such as the generation of a WS-Trust token or SAML
        assertion."

    ::= { dpConfig 91 }

dpConfigAAAPolicyEntry OBJECT-TYPE
    SYNTAX      DPConfigAAAPolicyEntry
    MAX-ACCESS  not-accessible
    STATUS      current
    DESCRIPTION "Table row."
    INDEX { dpConfigAAAPolicyIndex, IMPLIED dpConfigAAAPolicyname }

    ::= { dpConfigAAAPolicyTable 1 }

DPConfigAAAPolicyEntry ::= SEQUENCE {
    dpConfigAAAPolicyIndex    Unsigned32,
    dpConfigAAAPolicyname    DisplayString
}

dpConfigAAAPolicyIndex OBJECT-TYPE
    SYNTAX      Unsigned32
    MAX-ACCESS  read-only
    STATUS      current
    DESCRIPTION "No description yet."

    ::= { dpConfigAAAPolicyEntry 1 }

dpConfigAAAPolicyname OBJECT-TYPE
    SYNTAX      DisplayString
    MAX-ACCESS  read-only
    STATUS      current
    DESCRIPTION "No description yet."

    ::= { dpConfigAAAPolicyEntry 2 }

--

dpConfigStylePolicyActionTable OBJECT-TYPE
    SYNTAX      SEQUENCE OF DPConfigStylePolicyActionEntry
    MAX-ACCESS  not-accessible
    STATUS      current
    DESCRIPTION
        "Define XSL filters and/or transformations"

    ::= { dpConfig 92 }

dpConfigStylePolicyActionEntry OBJECT-TYPE
    SYNTAX      DPConfigStylePolicyActionEntry
    MAX-ACCESS  not-accessible
    STATUS      current
    DESCRIPTION "Table row."
    INDEX { dpConfigStylePolicyActionIndex, IMPLIED dpConfigStylePolicyActionname }

    ::= { dpConfigStylePolicyActionTable 1 }

DPConfigStylePolicyActionEntry ::= SEQUENCE {
    dpConfigStylePolicyActionIndex    Unsigned32,
    dpConfigStylePolicyActionname    DisplayString
}

dpConfigStylePolicyActionIndex OBJECT-TYPE
    SYNTAX      Unsigned32
    MAX-ACCESS  read-only
    STATUS      current
    DESCRIPTION "No description yet."

    ::= { dpConfigStylePolicyActionEntry 1 }

dpConfigStylePolicyActionname OBJECT-TYPE
    SYNTAX      DisplayString
    MAX-ACCESS  read-only
    STATUS      current
    DESCRIPTION "No description yet."

    ::= { dpConfigStylePolicyActionEntry 2 }

--

dpConfigCryptoKerberosKDCTable OBJECT-TYPE
    SYNTAX      SEQUENCE OF DPConfigCryptoKerberosKDCEntry
    MAX-ACCESS  not-accessible
    STATUS      current
    DESCRIPTION "Table."

    ::= { dpConfig 93 }

dpConfigCryptoKerberosKDCEntry OBJECT-TYPE
    SYNTAX      DPConfigCryptoKerberosKDCEntry
    MAX-ACCESS  not-accessible
    STATUS      current
    DESCRIPTION "Table row."
    INDEX { dpConfigCryptoKerberosKDCIndex, IMPLIED dpConfigCryptoKerberosKDCname }

    ::= { dpConfigCryptoKerberosKDCTable 1 }

DPConfigCryptoKerberosKDCEntry ::= SEQUENCE {
    dpConfigCryptoKerberosKDCIndex    Unsigned32,
    dpConfigCryptoKerberosKDCname    DisplayString
}

dpConfigCryptoKerberosKDCIndex OBJECT-TYPE
    SYNTAX      Unsigned32
    MAX-ACCESS  read-only
    STATUS      current
    DESCRIPTION "No description yet."

    ::= { dpConfigCryptoKerberosKDCEntry 1 }

dpConfigCryptoKerberosKDCname OBJECT-TYPE
    SYNTAX      DisplayString
    MAX-ACCESS  read-only
    STATUS      current
    DESCRIPTION "No description yet."

    ::= { dpConfigCryptoKerberosKDCEntry 2 }

--

dpConfigWebServiceMonitorTable OBJECT-TYPE
    SYNTAX      SEQUENCE OF DPConfigWebServiceMonitorEntry
    MAX-ACCESS  not-accessible
    STATUS      current
    DESCRIPTION
        "Web Service SLM (Service Level Monitor) Object An SLM watches Web Services
        traffic destined for the Endpoint URL defined in the Endpoint URL field
        using the transport method defined in the Transport Type field. The
        monitor watches only traffic the client sent to the Front End URL (which
        accepts wildcards). The Endpoint, Endpoint URL and Transport Type must
        agree with the definitions provided in the WSDL file identified by the
        WSDL URL field."

    ::= { dpConfig 94 }

dpConfigWebServiceMonitorEntry OBJECT-TYPE
    SYNTAX      DPConfigWebServiceMonitorEntry
    MAX-ACCESS  not-accessible
    STATUS      current
    DESCRIPTION "Table row."
    INDEX { dpConfigWebServiceMonitorIndex, IMPLIED dpConfigWebServiceMonitorname }

    ::= { dpConfigWebServiceMonitorTable 1 }

DPConfigWebServiceMonitorEntry ::= SEQUENCE {
    dpConfigWebServiceMonitorIndex    Unsigned32,
    dpConfigWebServiceMonitorname    DisplayString
}

dpConfigWebServiceMonitorIndex OBJECT-TYPE
    SYNTAX      Unsigned32
    MAX-ACCESS  read-only
    STATUS      current
    DESCRIPTION "No description yet."

    ::= { dpConfigWebServiceMonitorEntry 1 }

dpConfigWebServiceMonitorname OBJECT-TYPE
    SYNTAX      DisplayString
    MAX-ACCESS  read-only
    STATUS      current
    DESCRIPTION "No description yet."

    ::= { dpConfigWebServiceMonitorEntry 2 }

--

dpConfigWSGatewayTable OBJECT-TYPE
    SYNTAX      SEQUENCE OF DPConfigWSGatewayEntry
    MAX-ACCESS  not-accessible
    STATUS      current
    DESCRIPTION
        "A Web Service Proxy virtualizes application services described by WSDL
        files. The Proxy provides alternate endpoint URLs, message validation,
        service level monitoring and automatic updating when provided with only
        one or more WSDL files. In addition, a Web Service Proxy can provide the
        full range of processing services available to an XML Firewall or
        Multi-Protocol Gateway, such as Authentication and Authorization,
        cryptographic operations, transformations and dynamic routing, and more."

    ::= { dpConfig 95 }

dpConfigWSGatewayEntry OBJECT-TYPE
    SYNTAX      DPConfigWSGatewayEntry
    MAX-ACCESS  not-accessible
    STATUS      current
    DESCRIPTION "Table row."
    INDEX { dpConfigWSGatewayIndex, IMPLIED dpConfigWSGatewayname }

    ::= { dpConfigWSGatewayTable 1 }

DPConfigWSGatewayEntry ::= SEQUENCE {
    dpConfigWSGatewayIndex    Unsigned32,
    dpConfigWSGatewayname    DisplayString
}

dpConfigWSGatewayIndex OBJECT-TYPE
    SYNTAX      Unsigned32
    MAX-ACCESS  read-only
    STATUS      current
    DESCRIPTION "No description yet."

    ::= { dpConfigWSGatewayEntry 1 }

dpConfigWSGatewayname OBJECT-TYPE
    SYNTAX      DisplayString
    MAX-ACCESS  read-only
    STATUS      current
    DESCRIPTION "No description yet."

    ::= { dpConfigWSGatewayEntry 2 }

--

dpConfigStylePolicyRuleBaseTable OBJECT-TYPE
    SYNTAX      SEQUENCE OF DPConfigStylePolicyRuleBaseEntry
    MAX-ACCESS  not-accessible
    STATUS      current
    DESCRIPTION "Table."

    ::= { dpConfig 96 }

dpConfigStylePolicyRuleBaseEntry OBJECT-TYPE
    SYNTAX      DPConfigStylePolicyRuleBaseEntry
    MAX-ACCESS  not-accessible
    STATUS      current
    DESCRIPTION "Table row."
    INDEX { dpConfigStylePolicyRuleBaseIndex, IMPLIED dpConfigStylePolicyRuleBasename }

    ::= { dpConfigStylePolicyRuleBaseTable 1 }

DPConfigStylePolicyRuleBaseEntry ::= SEQUENCE {
    dpConfigStylePolicyRuleBaseIndex    Unsigned32,
    dpConfigStylePolicyRuleBasename    DisplayString
}

dpConfigStylePolicyRuleBaseIndex OBJECT-TYPE
    SYNTAX      Unsigned32
    MAX-ACCESS  read-only
    STATUS      current
    DESCRIPTION "No description yet."

    ::= { dpConfigStylePolicyRuleBaseEntry 1 }

dpConfigStylePolicyRuleBasename OBJECT-TYPE
    SYNTAX      DisplayString
    MAX-ACCESS  read-only
    STATUS      current
    DESCRIPTION "No description yet."

    ::= { dpConfigStylePolicyRuleBaseEntry 2 }

--

dpConfigWSStylePolicyRuleTable OBJECT-TYPE
    SYNTAX      SEQUENCE OF DPConfigWSStylePolicyRuleEntry
    MAX-ACCESS  not-accessible
    STATUS      current
    DESCRIPTION
        "Create, edit, or delete processing policy rules. Rules can also be created
        and edited using a drag and drop interface by opening the Services menu
        area on the left-hand navigation bar. Click the appropriate Policy link
        which will then present an opportunity to create both Rules and Actions."

    ::= { dpConfig 97 }

dpConfigWSStylePolicyRuleEntry OBJECT-TYPE
    SYNTAX      DPConfigWSStylePolicyRuleEntry
    MAX-ACCESS  not-accessible
    STATUS      current
    DESCRIPTION "Table row."
    INDEX { dpConfigWSStylePolicyRuleIndex, IMPLIED dpConfigWSStylePolicyRulename }

    ::= { dpConfigWSStylePolicyRuleTable 1 }

DPConfigWSStylePolicyRuleEntry ::= SEQUENCE {
    dpConfigWSStylePolicyRuleIndex    Unsigned32,
    dpConfigWSStylePolicyRulename    DisplayString
}

dpConfigWSStylePolicyRuleIndex OBJECT-TYPE
    SYNTAX      Unsigned32
    MAX-ACCESS  read-only
    STATUS      current
    DESCRIPTION "No description yet."

    ::= { dpConfigWSStylePolicyRuleEntry 1 }

dpConfigWSStylePolicyRulename OBJECT-TYPE
    SYNTAX      DisplayString
    MAX-ACCESS  read-only
    STATUS      current
    DESCRIPTION "No description yet."

    ::= { dpConfigWSStylePolicyRuleEntry 2 }

--

dpConfigWSStylePolicyTable OBJECT-TYPE
    SYNTAX      SEQUENCE OF DPConfigWSStylePolicyEntry
    MAX-ACCESS  not-accessible
    STATUS      current
    DESCRIPTION
        "Create, Edit or Delete a Processing Policy. A policy consists of one or
        more Processing Rules. Rules execute depending upon the direction of the
        message and on whether or not a corresponding matching rule selects the
        document for processing. A service may have only one policy active at a
        time. Click Services in the left-hand navigation menu and then click the
        appropriate policy link to use the graphical interface to create and edit
        policies."

    ::= { dpConfig 98 }

dpConfigWSStylePolicyEntry OBJECT-TYPE
    SYNTAX      DPConfigWSStylePolicyEntry
    MAX-ACCESS  not-accessible
    STATUS      current
    DESCRIPTION "Table row."
    INDEX { dpConfigWSStylePolicyIndex, IMPLIED dpConfigWSStylePolicyname }

    ::= { dpConfigWSStylePolicyTable 1 }

DPConfigWSStylePolicyEntry ::= SEQUENCE {
    dpConfigWSStylePolicyIndex    Unsigned32,
    dpConfigWSStylePolicyname    DisplayString
}

dpConfigWSStylePolicyIndex OBJECT-TYPE
    SYNTAX      Unsigned32
    MAX-ACCESS  read-only
    STATUS      current
    DESCRIPTION "No description yet."

    ::= { dpConfigWSStylePolicyEntry 1 }

dpConfigWSStylePolicyname OBJECT-TYPE
    SYNTAX      DisplayString
    MAX-ACCESS  read-only
    STATUS      current
    DESCRIPTION "No description yet."

    ::= { dpConfigWSStylePolicyEntry 2 }

--

dpConfigWebServicesAgentTable OBJECT-TYPE
    SYNTAX      SEQUENCE OF DPConfigWebServicesAgentEntry
    MAX-ACCESS  not-accessible
    STATUS      current
    DESCRIPTION
        "The Web Services Management Agent provides manageability for Web Services
        by providing status, metrics, and transaction history to external
        management stations."

    ::= { dpConfig 99 }

dpConfigWebServicesAgentEntry OBJECT-TYPE
    SYNTAX      DPConfigWebServicesAgentEntry
    MAX-ACCESS  not-accessible
    STATUS      current
    DESCRIPTION "Table row."
    INDEX { dpConfigWebServicesAgentIndex, IMPLIED dpConfigWebServicesAgentname }

    ::= { dpConfigWebServicesAgentTable 1 }

DPConfigWebServicesAgentEntry ::= SEQUENCE {
    dpConfigWebServicesAgentIndex    Unsigned32,
    dpConfigWebServicesAgentname    DisplayString
}

dpConfigWebServicesAgentIndex OBJECT-TYPE
    SYNTAX      Unsigned32
    MAX-ACCESS  read-only
    STATUS      current
    DESCRIPTION "No description yet."

    ::= { dpConfigWebServicesAgentEntry 1 }

dpConfigWebServicesAgentname OBJECT-TYPE
    SYNTAX      DisplayString
    MAX-ACCESS  read-only
    STATUS      current
    DESCRIPTION "No description yet."

    ::= { dpConfigWebServicesAgentEntry 2 }

--

dpConfigGatewayBaseTable OBJECT-TYPE
    SYNTAX      SEQUENCE OF DPConfigGatewayBaseEntry
    MAX-ACCESS  not-accessible
    STATUS      current
    DESCRIPTION "Table."

    ::= { dpConfig 100 }

dpConfigGatewayBaseEntry OBJECT-TYPE
    SYNTAX      DPConfigGatewayBaseEntry
    MAX-ACCESS  not-accessible
    STATUS      current
    DESCRIPTION "Table row."
    INDEX { dpConfigGatewayBaseIndex, IMPLIED dpConfigGatewayBasename }

    ::= { dpConfigGatewayBaseTable 1 }

DPConfigGatewayBaseEntry ::= SEQUENCE {
    dpConfigGatewayBaseIndex    Unsigned32,
    dpConfigGatewayBasename    DisplayString
}

dpConfigGatewayBaseIndex OBJECT-TYPE
    SYNTAX      Unsigned32
    MAX-ACCESS  read-only
    STATUS      current
    DESCRIPTION "No description yet."

    ::= { dpConfigGatewayBaseEntry 1 }

dpConfigGatewayBasename OBJECT-TYPE
    SYNTAX      DisplayString
    MAX-ACCESS  read-only
    STATUS      current
    DESCRIPTION "No description yet."

    ::= { dpConfigGatewayBaseEntry 2 }

--

dpConfigMultiProtocolGatewayTable OBJECT-TYPE
    SYNTAX      SEQUENCE OF DPConfigMultiProtocolGatewayEntry
    MAX-ACCESS  not-accessible
    STATUS      current
    DESCRIPTION
        "A Multi-Protocol Gateway service can accept client-originated messages in
        a variety of protocols. The Gateway can subsequently pass messages to a
        back end server using a variety of protocols. The protocol used on the
        client side need not be the same as that on the back side. A Gateway can
        support more than one client, or Front Side, protocol. Similarly, the
        Gateway can support more than one back side, or server protocol. The
        messages may be processed and routed using any of the standard Document
        Processing Actions available to a firewall or a proxy."

    ::= { dpConfig 101 }

dpConfigMultiProtocolGatewayEntry OBJECT-TYPE
    SYNTAX      DPConfigMultiProtocolGatewayEntry
    MAX-ACCESS  not-accessible
    STATUS      current
    DESCRIPTION "Table row."
    INDEX { dpConfigMultiProtocolGatewayIndex, IMPLIED dpConfigMultiProtocolGatewayname }

    ::= { dpConfigMultiProtocolGatewayTable 1 }

DPConfigMultiProtocolGatewayEntry ::= SEQUENCE {
    dpConfigMultiProtocolGatewayIndex    Unsigned32,
    dpConfigMultiProtocolGatewayname    DisplayString
}

dpConfigMultiProtocolGatewayIndex OBJECT-TYPE
    SYNTAX      Unsigned32
    MAX-ACCESS  read-only
    STATUS      current
    DESCRIPTION "No description yet."

    ::= { dpConfigMultiProtocolGatewayEntry 1 }

dpConfigMultiProtocolGatewayname OBJECT-TYPE
    SYNTAX      DisplayString
    MAX-ACCESS  read-only
    STATUS      current
    DESCRIPTION "No description yet."

    ::= { dpConfigMultiProtocolGatewayEntry 2 }

--

dpConfigSourceProtocolHandlerTable OBJECT-TYPE
    SYNTAX      SEQUENCE OF DPConfigSourceProtocolHandlerEntry
    MAX-ACCESS  not-accessible
    STATUS      current
    DESCRIPTION "Table."

    ::= { dpConfig 102 }

dpConfigSourceProtocolHandlerEntry OBJECT-TYPE
    SYNTAX      DPConfigSourceProtocolHandlerEntry
    MAX-ACCESS  not-accessible
    STATUS      current
    DESCRIPTION "Table row."
    INDEX { dpConfigSourceProtocolHandlerIndex, IMPLIED dpConfigSourceProtocolHandlername }

    ::= { dpConfigSourceProtocolHandlerTable 1 }

DPConfigSourceProtocolHandlerEntry ::= SEQUENCE {
    dpConfigSourceProtocolHandlerIndex    Unsigned32,
    dpConfigSourceProtocolHandlername    DisplayString
}

dpConfigSourceProtocolHandlerIndex OBJECT-TYPE
    SYNTAX      Unsigned32
    MAX-ACCESS  read-only
    STATUS      current
    DESCRIPTION "No description yet."

    ::= { dpConfigSourceProtocolHandlerEntry 1 }

dpConfigSourceProtocolHandlername OBJECT-TYPE
    SYNTAX      DisplayString
    MAX-ACCESS  read-only
    STATUS      current
    DESCRIPTION "No description yet."

    ::= { dpConfigSourceProtocolHandlerEntry 2 }

--

dpConfigHTTPSourceProtocolHandlerTable OBJECT-TYPE
    SYNTAX      SEQUENCE OF DPConfigHTTPSourceProtocolHandlerEntry
    MAX-ACCESS  not-accessible
    STATUS      current
    DESCRIPTION
        "An HTTP handler receives HTTP requests that are not over SSL and forwards
        them to the appropriate DataPower service. HTTP handlers conform to RFC
        2616."

    ::= { dpConfig 103 }

dpConfigHTTPSourceProtocolHandlerEntry OBJECT-TYPE
    SYNTAX      DPConfigHTTPSourceProtocolHandlerEntry
    MAX-ACCESS  not-accessible
    STATUS      current
    DESCRIPTION "Table row."
    INDEX { dpConfigHTTPSourceProtocolHandlerIndex, IMPLIED dpConfigHTTPSourceProtocolHandlername }

    ::= { dpConfigHTTPSourceProtocolHandlerTable 1 }

DPConfigHTTPSourceProtocolHandlerEntry ::= SEQUENCE {
    dpConfigHTTPSourceProtocolHandlerIndex    Unsigned32,
    dpConfigHTTPSourceProtocolHandlername    DisplayString
}

dpConfigHTTPSourceProtocolHandlerIndex OBJECT-TYPE
    SYNTAX      Unsigned32
    MAX-ACCESS  read-only
    STATUS      current
    DESCRIPTION "No description yet."

    ::= { dpConfigHTTPSourceProtocolHandlerEntry 1 }

dpConfigHTTPSourceProtocolHandlername OBJECT-TYPE
    SYNTAX      DisplayString
    MAX-ACCESS  read-only
    STATUS      current
    DESCRIPTION "No description yet."

    ::= { dpConfigHTTPSourceProtocolHandlerEntry 2 }

--

dpConfigHTTPSSourceProtocolHandlerTable OBJECT-TYPE
    SYNTAX      SEQUENCE OF DPConfigHTTPSSourceProtocolHandlerEntry
    MAX-ACCESS  not-accessible
    STATUS      current
    DESCRIPTION
        "An HTTPS handler receives HTTP requests over SSL and forwards them to the
        appropriate DataPower service. HTTPS handlers conform to RFC 2616."

    ::= { dpConfig 104 }

dpConfigHTTPSSourceProtocolHandlerEntry OBJECT-TYPE
    SYNTAX      DPConfigHTTPSSourceProtocolHandlerEntry
    MAX-ACCESS  not-accessible
    STATUS      current
    DESCRIPTION "Table row."
    INDEX { dpConfigHTTPSSourceProtocolHandlerIndex, IMPLIED dpConfigHTTPSSourceProtocolHandlername }

    ::= { dpConfigHTTPSSourceProtocolHandlerTable 1 }

DPConfigHTTPSSourceProtocolHandlerEntry ::= SEQUENCE {
    dpConfigHTTPSSourceProtocolHandlerIndex    Unsigned32,
    dpConfigHTTPSSourceProtocolHandlername    DisplayString
}

dpConfigHTTPSSourceProtocolHandlerIndex OBJECT-TYPE
    SYNTAX      Unsigned32
    MAX-ACCESS  read-only
    STATUS      current
    DESCRIPTION "No description yet."

    ::= { dpConfigHTTPSSourceProtocolHandlerEntry 1 }

dpConfigHTTPSSourceProtocolHandlername OBJECT-TYPE
    SYNTAX      DisplayString
    MAX-ACCESS  read-only
    STATUS      current
    DESCRIPTION "No description yet."

    ::= { dpConfigHTTPSSourceProtocolHandlerEntry 2 }

--

dpConfigMQSourceProtocolHandlerTable OBJECT-TYPE
    SYNTAX      SEQUENCE OF DPConfigMQSourceProtocolHandlerEntry
    MAX-ACCESS  not-accessible
    STATUS      current
    DESCRIPTION "Table."

    ::= { dpConfig 105 }

dpConfigMQSourceProtocolHandlerEntry OBJECT-TYPE
    SYNTAX      DPConfigMQSourceProtocolHandlerEntry
    MAX-ACCESS  not-accessible
    STATUS      current
    DESCRIPTION "Table row."
    INDEX { dpConfigMQSourceProtocolHandlerIndex, IMPLIED dpConfigMQSourceProtocolHandlername }

    ::= { dpConfigMQSourceProtocolHandlerTable 1 }

DPConfigMQSourceProtocolHandlerEntry ::= SEQUENCE {
    dpConfigMQSourceProtocolHandlerIndex    Unsigned32,
    dpConfigMQSourceProtocolHandlername    DisplayString
}

dpConfigMQSourceProtocolHandlerIndex OBJECT-TYPE
    SYNTAX      Unsigned32
    MAX-ACCESS  read-only
    STATUS      current
    DESCRIPTION "No description yet."

    ::= { dpConfigMQSourceProtocolHandlerEntry 1 }

dpConfigMQSourceProtocolHandlername OBJECT-TYPE
    SYNTAX      DisplayString
    MAX-ACCESS  read-only
    STATUS      current
    DESCRIPTION "No description yet."

    ::= { dpConfigMQSourceProtocolHandlerEntry 2 }

--

dpConfigXTCProtocolHandlerTable OBJECT-TYPE
    SYNTAX      SEQUENCE OF DPConfigXTCProtocolHandlerEntry
    MAX-ACCESS  not-accessible
    STATUS      current
    DESCRIPTION
        "The configuration for the stateful TCP protocol handler. This protocol
        uses raw XML - where the close of the root node delineates the document -
        PI's and comments outside of the root node are not allowed. The source
        protocol also specifies the destination address and any single TCP
        connection will use the same TCP session on the backside for all of its
        transactions (one transaction per document). Any Gateway that employs one
        of these Handlers must use a Dynamic Backend."

    ::= { dpConfig 106 }

dpConfigXTCProtocolHandlerEntry OBJECT-TYPE
    SYNTAX      DPConfigXTCProtocolHandlerEntry
    MAX-ACCESS  not-accessible
    STATUS      current
    DESCRIPTION "Table row."
    INDEX { dpConfigXTCProtocolHandlerIndex, IMPLIED dpConfigXTCProtocolHandlername }

    ::= { dpConfigXTCProtocolHandlerTable 1 }

DPConfigXTCProtocolHandlerEntry ::= SEQUENCE {
    dpConfigXTCProtocolHandlerIndex    Unsigned32,
    dpConfigXTCProtocolHandlername    DisplayString
}

dpConfigXTCProtocolHandlerIndex OBJECT-TYPE
    SYNTAX      Unsigned32
    MAX-ACCESS  read-only
    STATUS      current
    DESCRIPTION "No description yet."

    ::= { dpConfigXTCProtocolHandlerEntry 1 }

dpConfigXTCProtocolHandlername OBJECT-TYPE
    SYNTAX      DisplayString
    MAX-ACCESS  read-only
    STATUS      current
    DESCRIPTION "No description yet."

    ::= { dpConfigXTCProtocolHandlerEntry 2 }

--

dpConfigCryptoKerberosKeytabTable OBJECT-TYPE
    SYNTAX      SEQUENCE OF DPConfigCryptoKerberosKeytabEntry
    MAX-ACCESS  not-accessible
    STATUS      current
    DESCRIPTION "Table."

    ::= { dpConfig 109 }

dpConfigCryptoKerberosKeytabEntry OBJECT-TYPE
    SYNTAX      DPConfigCryptoKerberosKeytabEntry
    MAX-ACCESS  not-accessible
    STATUS      current
    DESCRIPTION "Table row."
    INDEX { dpConfigCryptoKerberosKeytabIndex, IMPLIED dpConfigCryptoKerberosKeytabname }

    ::= { dpConfigCryptoKerberosKeytabTable 1 }

DPConfigCryptoKerberosKeytabEntry ::= SEQUENCE {
    dpConfigCryptoKerberosKeytabIndex    Unsigned32,
    dpConfigCryptoKerberosKeytabname    DisplayString
}

dpConfigCryptoKerberosKeytabIndex OBJECT-TYPE
    SYNTAX      Unsigned32
    MAX-ACCESS  read-only
    STATUS      current
    DESCRIPTION "No description yet."

    ::= { dpConfigCryptoKerberosKeytabEntry 1 }

dpConfigCryptoKerberosKeytabname OBJECT-TYPE
    SYNTAX      DisplayString
    MAX-ACCESS  read-only
    STATUS      current
    DESCRIPTION "No description yet."

    ::= { dpConfigCryptoKerberosKeytabEntry 2 }

--

dpConfigStatelessTCPSourceProtocolHandlerTable OBJECT-TYPE
    SYNTAX      SEQUENCE OF DPConfigStatelessTCPSourceProtocolHandlerEntry
    MAX-ACCESS  not-accessible
    STATUS      current
    DESCRIPTION
        "The configuration for the stateless TCP protocol handler. This protocol
        uses raw XML - where the close of the root node delineates the document -
        PI's and comments outside of the root node are not allowed."

    ::= { dpConfig 110 }

dpConfigStatelessTCPSourceProtocolHandlerEntry OBJECT-TYPE
    SYNTAX      DPConfigStatelessTCPSourceProtocolHandlerEntry
    MAX-ACCESS  not-accessible
    STATUS      current
    DESCRIPTION "Table row."
    INDEX { dpConfigStatelessTCPSourceProtocolHandlerIndex, IMPLIED dpConfigStatelessTCPSourceProtocolHandlername }

    ::= { dpConfigStatelessTCPSourceProtocolHandlerTable 1 }

DPConfigStatelessTCPSourceProtocolHandlerEntry ::= SEQUENCE {
    dpConfigStatelessTCPSourceProtocolHandlerIndex    Unsigned32,
    dpConfigStatelessTCPSourceProtocolHandlername    DisplayString
}

dpConfigStatelessTCPSourceProtocolHandlerIndex OBJECT-TYPE
    SYNTAX      Unsigned32
    MAX-ACCESS  read-only
    STATUS      current
    DESCRIPTION "No description yet."

    ::= { dpConfigStatelessTCPSourceProtocolHandlerEntry 1 }

dpConfigStatelessTCPSourceProtocolHandlername OBJECT-TYPE
    SYNTAX      DisplayString
    MAX-ACCESS  read-only
    STATUS      current
    DESCRIPTION "No description yet."

    ::= { dpConfigStatelessTCPSourceProtocolHandlerEntry 2 }

--

dpConfigSLMCredClassTable OBJECT-TYPE
    SYNTAX      SEQUENCE OF DPConfigSLMCredClassEntry
    MAX-ACCESS  not-accessible
    STATUS      current
    DESCRIPTION
        "An SLM credentials class identifies a set of users (credentials) to be
        subject to an SLM policy. An SLM credentials class consists of the
        following types and properties: A credential type that specifies the
        manner to obtain user credentials A match type that determines to which
        credentials to apply the SLM policy Depending on the credential and match
        type, properties that identify specific instances of credentials"

    ::= { dpConfig 111 }

dpConfigSLMCredClassEntry OBJECT-TYPE
    SYNTAX      DPConfigSLMCredClassEntry
    MAX-ACCESS  not-accessible
    STATUS      current
    DESCRIPTION "Table row."
    INDEX { dpConfigSLMCredClassIndex, IMPLIED dpConfigSLMCredClassname }

    ::= { dpConfigSLMCredClassTable 1 }

DPConfigSLMCredClassEntry ::= SEQUENCE {
    dpConfigSLMCredClassIndex    Unsigned32,
    dpConfigSLMCredClassname    DisplayString
}

dpConfigSLMCredClassIndex OBJECT-TYPE
    SYNTAX      Unsigned32
    MAX-ACCESS  read-only
    STATUS      current
    DESCRIPTION "No description yet."

    ::= { dpConfigSLMCredClassEntry 1 }

dpConfigSLMCredClassname OBJECT-TYPE
    SYNTAX      DisplayString
    MAX-ACCESS  read-only
    STATUS      current
    DESCRIPTION "No description yet."

    ::= { dpConfigSLMCredClassEntry 2 }

--

dpConfigSLMRsrcClassTable OBJECT-TYPE
    SYNTAX      SEQUENCE OF DPConfigSLMRsrcClassEntry
    MAX-ACCESS  not-accessible
    STATUS      current
    DESCRIPTION
        "An SLM resource class identifies a set of resources to be subject to an
        SLM policy. A resource class consists of the following types and
        properties: A resource type that specifies the manner to identify
        resources A match type that determines to which resources to apply the SLM
        policy Depending on the resource and match type, properties that identify
        specific instances of resources"

    ::= { dpConfig 112 }

dpConfigSLMRsrcClassEntry OBJECT-TYPE
    SYNTAX      DPConfigSLMRsrcClassEntry
    MAX-ACCESS  not-accessible
    STATUS      current
    DESCRIPTION "Table row."
    INDEX { dpConfigSLMRsrcClassIndex, IMPLIED dpConfigSLMRsrcClassname }

    ::= { dpConfigSLMRsrcClassTable 1 }

DPConfigSLMRsrcClassEntry ::= SEQUENCE {
    dpConfigSLMRsrcClassIndex    Unsigned32,
    dpConfigSLMRsrcClassname    DisplayString
}

dpConfigSLMRsrcClassIndex OBJECT-TYPE
    SYNTAX      Unsigned32
    MAX-ACCESS  read-only
    STATUS      current
    DESCRIPTION "No description yet."

    ::= { dpConfigSLMRsrcClassEntry 1 }

dpConfigSLMRsrcClassname OBJECT-TYPE
    SYNTAX      DisplayString
    MAX-ACCESS  read-only
    STATUS      current
    DESCRIPTION "No description yet."

    ::= { dpConfigSLMRsrcClassEntry 2 }

--

dpConfigSLMScheduleTable OBJECT-TYPE
    SYNTAX      SEQUENCE OF DPConfigSLMScheduleEntry
    MAX-ACCESS  not-accessible
    STATUS      current
    DESCRIPTION
        "An SLM schedule defines the time period (hours and days) during which to
        enforce the statements in an SLM policy. Schedules allow the application
        of different statements during different time periods."

    ::= { dpConfig 113 }

dpConfigSLMScheduleEntry OBJECT-TYPE
    SYNTAX      DPConfigSLMScheduleEntry
    MAX-ACCESS  not-accessible
    STATUS      current
    DESCRIPTION "Table row."
    INDEX { dpConfigSLMScheduleIndex, IMPLIED dpConfigSLMSchedulename }

    ::= { dpConfigSLMScheduleTable 1 }

DPConfigSLMScheduleEntry ::= SEQUENCE {
    dpConfigSLMScheduleIndex    Unsigned32,
    dpConfigSLMSchedulename    DisplayString
}

dpConfigSLMScheduleIndex OBJECT-TYPE
    SYNTAX      Unsigned32
    MAX-ACCESS  read-only
    STATUS      current
    DESCRIPTION "No description yet."

    ::= { dpConfigSLMScheduleEntry 1 }

dpConfigSLMSchedulename OBJECT-TYPE
    SYNTAX      DisplayString
    MAX-ACCESS  read-only
    STATUS      current
    DESCRIPTION "No description yet."

    ::= { dpConfigSLMScheduleEntry 2 }

--

dpConfigSLMActionTable OBJECT-TYPE
    SYNTAX      SEQUENCE OF DPConfigSLMActionEntry
    MAX-ACCESS  not-accessible
    STATUS      current
    DESCRIPTION
        "An SLM action defines the control procedure to trigger for transactions in
        excess of the maximum transaction rate. As part of any control procedure,
        the monitor writes an event to the log for each transaction that exceeds a
        threshold."

    ::= { dpConfig 114 }

dpConfigSLMActionEntry OBJECT-TYPE
    SYNTAX      DPConfigSLMActionEntry
    MAX-ACCESS  not-accessible
    STATUS      current
    DESCRIPTION "Table row."
    INDEX { dpConfigSLMActionIndex, IMPLIED dpConfigSLMActionname }

    ::= { dpConfigSLMActionTable 1 }

DPConfigSLMActionEntry ::= SEQUENCE {
    dpConfigSLMActionIndex    Unsigned32,
    dpConfigSLMActionname    DisplayString
}

dpConfigSLMActionIndex OBJECT-TYPE
    SYNTAX      Unsigned32
    MAX-ACCESS  read-only
    STATUS      current
    DESCRIPTION "No description yet."

    ::= { dpConfigSLMActionEntry 1 }

dpConfigSLMActionname OBJECT-TYPE
    SYNTAX      DisplayString
    MAX-ACCESS  read-only
    STATUS      current
    DESCRIPTION "No description yet."

    ::= { dpConfigSLMActionEntry 2 }

--

dpConfigSLMPolicyTable OBJECT-TYPE
    SYNTAX      SEQUENCE OF DPConfigSLMPolicyEntry
    MAX-ACCESS  not-accessible
    STATUS      current
    DESCRIPTION
        "An SLM policy counts messages or measures latency for messages that match
        a set of select criteria and that pass through the appliance during a
        configured interval. The policy can take action when configured thresholds
        are reached. Messages can be selected based on credential class, resource
        class, or both. If neither, all messages are selected. A policy consists
        of one or more statements. Each statement establishes the credential
        class, resource class, thresholds, and actions to take when thresholds are
        met during an interval. Examples: A policy that throttles all traffic that
        arrives at a rate faster than 1000 messages per second. A policy that
        generates a log message for all messages that arrive during the last
        elapsed second that originated from a specific IP address and requested
        use of a specific resource."

    ::= { dpConfig 115 }

dpConfigSLMPolicyEntry OBJECT-TYPE
    SYNTAX      DPConfigSLMPolicyEntry
    MAX-ACCESS  not-accessible
    STATUS      current
    DESCRIPTION "Table row."
    INDEX { dpConfigSLMPolicyIndex, IMPLIED dpConfigSLMPolicyname }

    ::= { dpConfigSLMPolicyTable 1 }

DPConfigSLMPolicyEntry ::= SEQUENCE {
    dpConfigSLMPolicyIndex    Unsigned32,
    dpConfigSLMPolicyname    DisplayString
}

dpConfigSLMPolicyIndex OBJECT-TYPE
    SYNTAX      Unsigned32
    MAX-ACCESS  read-only
    STATUS      current
    DESCRIPTION "No description yet."

    ::= { dpConfigSLMPolicyEntry 1 }

dpConfigSLMPolicyname OBJECT-TYPE
    SYNTAX      DisplayString
    MAX-ACCESS  read-only
    STATUS      current
    DESCRIPTION "No description yet."

    ::= { dpConfigSLMPolicyEntry 2 }

--

dpConfigPeerGroupTable OBJECT-TYPE
    SYNTAX      SEQUENCE OF DPConfigPeerGroupEntry
    MAX-ACCESS  not-accessible
    STATUS      current
    DESCRIPTION
        "A collection of appliances that automatically update each other with real
        time data of the types selected. For example, members in the group
        exchange data to allow the enforcement of a policy across the collection."

    ::= { dpConfig 116 }

dpConfigPeerGroupEntry OBJECT-TYPE
    SYNTAX      DPConfigPeerGroupEntry
    MAX-ACCESS  not-accessible
    STATUS      current
    DESCRIPTION "Table row."
    INDEX { dpConfigPeerGroupIndex, IMPLIED dpConfigPeerGroupname }

    ::= { dpConfigPeerGroupTable 1 }

DPConfigPeerGroupEntry ::= SEQUENCE {
    dpConfigPeerGroupIndex    Unsigned32,
    dpConfigPeerGroupname    DisplayString
}

dpConfigPeerGroupIndex OBJECT-TYPE
    SYNTAX      Unsigned32
    MAX-ACCESS  read-only
    STATUS      current
    DESCRIPTION "No description yet."

    ::= { dpConfigPeerGroupEntry 1 }

dpConfigPeerGroupname OBJECT-TYPE
    SYNTAX      DisplayString
    MAX-ACCESS  read-only
    STATUS      current
    DESCRIPTION "No description yet."

    ::= { dpConfigPeerGroupEntry 2 }

--

dpConfigReserved117Table OBJECT-TYPE
    SYNTAX      SEQUENCE OF DPConfigReserved117Entry
    MAX-ACCESS  not-accessible
    STATUS      current
    DESCRIPTION "Table."

    ::= { dpConfig 117 }

dpConfigReserved117Entry OBJECT-TYPE
    SYNTAX      DPConfigReserved117Entry
    MAX-ACCESS  not-accessible
    STATUS      current
    DESCRIPTION "Table row."
    INDEX { dpConfigReserved117Index, IMPLIED dpConfigReserved117name }

    ::= { dpConfigReserved117Table 1 }

DPConfigReserved117Entry ::= SEQUENCE {
    dpConfigReserved117Index    Unsigned32,
    dpConfigReserved117name    DisplayString
}

dpConfigReserved117Index OBJECT-TYPE
    SYNTAX      Unsigned32
    MAX-ACCESS  read-only
    STATUS      current
    DESCRIPTION "No description yet."

    ::= { dpConfigReserved117Entry 1 }

dpConfigReserved117name OBJECT-TYPE
    SYNTAX      DisplayString
    MAX-ACCESS  read-only
    STATUS      current
    DESCRIPTION "No description yet."

    ::= { dpConfigReserved117Entry 2 }

--

dpConfigTFIMEndpointTable OBJECT-TYPE
    SYNTAX      SEQUENCE OF DPConfigTFIMEndpointEntry
    MAX-ACCESS  not-accessible
    STATUS      current
    DESCRIPTION
        "Tivoli Federated Identity Manager Configuration"

    ::= { dpConfig 118 }

dpConfigTFIMEndpointEntry OBJECT-TYPE
    SYNTAX      DPConfigTFIMEndpointEntry
    MAX-ACCESS  not-accessible
    STATUS      current
    DESCRIPTION "Table row."
    INDEX { dpConfigTFIMEndpointIndex, IMPLIED dpConfigTFIMEndpointname }

    ::= { dpConfigTFIMEndpointTable 1 }

DPConfigTFIMEndpointEntry ::= SEQUENCE {
    dpConfigTFIMEndpointIndex    Unsigned32,
    dpConfigTFIMEndpointname    DisplayString
}

dpConfigTFIMEndpointIndex OBJECT-TYPE
    SYNTAX      Unsigned32
    MAX-ACCESS  read-only
    STATUS      current
    DESCRIPTION "No description yet."

    ::= { dpConfigTFIMEndpointEntry 1 }

dpConfigTFIMEndpointname OBJECT-TYPE
    SYNTAX      DisplayString
    MAX-ACCESS  read-only
    STATUS      current
    DESCRIPTION "No description yet."

    ::= { dpConfigTFIMEndpointEntry 2 }

--

dpConfigxmltraceTable OBJECT-TYPE
    SYNTAX      SEQUENCE OF DPConfigxmltraceEntry
    MAX-ACCESS  not-accessible
    STATUS      current
    DESCRIPTION
        "The device can record all, or a subset, of documents that pass through it
        for later inspection. This should not be turned on in production
        environments except for problem resolution. File capture can fill the
        available storage space. Files are cycled FIFO when the available space is
        exhausted."

    ::= { dpConfig 120 }

dpConfigxmltraceEntry OBJECT-TYPE
    SYNTAX      DPConfigxmltraceEntry
    MAX-ACCESS  not-accessible
    STATUS      current
    DESCRIPTION "Table row."
    INDEX { dpConfigxmltraceIndex, IMPLIED dpConfigxmltracename }

    ::= { dpConfigxmltraceTable 1 }

DPConfigxmltraceEntry ::= SEQUENCE {
    dpConfigxmltraceIndex    Unsigned32,
    dpConfigxmltracename    DisplayString
}

dpConfigxmltraceIndex OBJECT-TYPE
    SYNTAX      Unsigned32
    MAX-ACCESS  read-only
    STATUS      current
    DESCRIPTION "No description yet."

    ::= { dpConfigxmltraceEntry 1 }

dpConfigxmltracename OBJECT-TYPE
    SYNTAX      DisplayString
    MAX-ACCESS  read-only
    STATUS      current
    DESCRIPTION "No description yet."

    ::= { dpConfigxmltraceEntry 2 }

--

dpConfigNFSClientSettingsTable OBJECT-TYPE
    SYNTAX      SEQUENCE OF DPConfigNFSClientSettingsEntry
    MAX-ACCESS  not-accessible
    STATUS      current
    DESCRIPTION
        "Use this page to configure global NFS client parameters. This is the
        global configuration for enabling NFS."

    ::= { dpConfig 121 }

dpConfigNFSClientSettingsEntry OBJECT-TYPE
    SYNTAX      DPConfigNFSClientSettingsEntry
    MAX-ACCESS  not-accessible
    STATUS      current
    DESCRIPTION "Table row."
    INDEX { dpConfigNFSClientSettingsIndex, IMPLIED dpConfigNFSClientSettingsname }

    ::= { dpConfigNFSClientSettingsTable 1 }

DPConfigNFSClientSettingsEntry ::= SEQUENCE {
    dpConfigNFSClientSettingsIndex    Unsigned32,
    dpConfigNFSClientSettingsname    DisplayString
}

dpConfigNFSClientSettingsIndex OBJECT-TYPE
    SYNTAX      Unsigned32
    MAX-ACCESS  read-only
    STATUS      current
    DESCRIPTION "No description yet."

    ::= { dpConfigNFSClientSettingsEntry 1 }

dpConfigNFSClientSettingsname OBJECT-TYPE
    SYNTAX      DisplayString
    MAX-ACCESS  read-only
    STATUS      current
    DESCRIPTION "No description yet."

    ::= { dpConfigNFSClientSettingsEntry 2 }

--

dpConfigWSEndpointRewritePolicyTable OBJECT-TYPE
    SYNTAX      SEQUENCE OF DPConfigWSEndpointRewritePolicyEntry
    MAX-ACCESS  not-accessible
    STATUS      current
    DESCRIPTION
        "Create or edit WS Endpoint Rewrite Policy"

    ::= { dpConfig 122 }

dpConfigWSEndpointRewritePolicyEntry OBJECT-TYPE
    SYNTAX      DPConfigWSEndpointRewritePolicyEntry
    MAX-ACCESS  not-accessible
    STATUS      current
    DESCRIPTION "Table row."
    INDEX { dpConfigWSEndpointRewritePolicyIndex, IMPLIED dpConfigWSEndpointRewritePolicyname }

    ::= { dpConfigWSEndpointRewritePolicyTable 1 }

DPConfigWSEndpointRewritePolicyEntry ::= SEQUENCE {
    dpConfigWSEndpointRewritePolicyIndex    Unsigned32,
    dpConfigWSEndpointRewritePolicyname    DisplayString
}

dpConfigWSEndpointRewritePolicyIndex OBJECT-TYPE
    SYNTAX      Unsigned32
    MAX-ACCESS  read-only
    STATUS      current
    DESCRIPTION "No description yet."

    ::= { dpConfigWSEndpointRewritePolicyEntry 1 }

dpConfigWSEndpointRewritePolicyname OBJECT-TYPE
    SYNTAX      DisplayString
    MAX-ACCESS  read-only
    STATUS      current
    DESCRIPTION "No description yet."

    ::= { dpConfigWSEndpointRewritePolicyEntry 2 }

--

dpConfigSQLDataSourceTable OBJECT-TYPE
    SYNTAX      SEQUENCE OF DPConfigSQLDataSourceEntry
    MAX-ACCESS  not-accessible
    STATUS      current
    DESCRIPTION
        "A SQL data source provides the configuration to establish a direct
        connection to a database instance on a remote data server. When
        configured, it is possible to dynamically perform database operations,
        such as #b#SELECT#/b# and #b#INSERT#/b#, on the remote database instance.
        A SQL data source is used by a SQL action in a processing policy. The SQL
        action retrieves the data for further processing by the processing policy.
        Conversely, the processing policy can store the processed data in the
        configured database instance. When configuring a SQL data source you can
        define optional but valid data source connection (or CLI) configuration
        parameters for your data server. Configuration parameters modify the
        behavior of the services that run with a data server. Some configuration
        parameters in the configuration file are informational and define
        characteristics about the environment. These configuration parameters
        cannot be modified."

    ::= { dpConfig 124 }

dpConfigSQLDataSourceEntry OBJECT-TYPE
    SYNTAX      DPConfigSQLDataSourceEntry
    MAX-ACCESS  not-accessible
    STATUS      current
    DESCRIPTION "Table row."
    INDEX { dpConfigSQLDataSourceIndex, IMPLIED dpConfigSQLDataSourcename }

    ::= { dpConfigSQLDataSourceTable 1 }

DPConfigSQLDataSourceEntry ::= SEQUENCE {
    dpConfigSQLDataSourceIndex    Unsigned32,
    dpConfigSQLDataSourcename    DisplayString
}

dpConfigSQLDataSourceIndex OBJECT-TYPE
    SYNTAX      Unsigned32
    MAX-ACCESS  read-only
    STATUS      current
    DESCRIPTION "No description yet."

    ::= { dpConfigSQLDataSourceEntry 1 }

dpConfigSQLDataSourcename OBJECT-TYPE
    SYNTAX      DisplayString
    MAX-ACCESS  read-only
    STATUS      current
    DESCRIPTION "No description yet."

    ::= { dpConfigSQLDataSourceEntry 2 }

--

dpConfigNFSStaticMountTable OBJECT-TYPE
    SYNTAX      SEQUENCE OF DPConfigNFSStaticMountEntry
    MAX-ACCESS  not-accessible
    STATUS      current
    DESCRIPTION
        "Use this page to create a static NFS mount, for URL or filesystem access.
        These mounts will be kept mounted whenever their application domain is up."

    ::= { dpConfig 125 }

dpConfigNFSStaticMountEntry OBJECT-TYPE
    SYNTAX      DPConfigNFSStaticMountEntry
    MAX-ACCESS  not-accessible
    STATUS      current
    DESCRIPTION "Table row."
    INDEX { dpConfigNFSStaticMountIndex, IMPLIED dpConfigNFSStaticMountname }

    ::= { dpConfigNFSStaticMountTable 1 }

DPConfigNFSStaticMountEntry ::= SEQUENCE {
    dpConfigNFSStaticMountIndex    Unsigned32,
    dpConfigNFSStaticMountname    DisplayString
}

dpConfigNFSStaticMountIndex OBJECT-TYPE
    SYNTAX      Unsigned32
    MAX-ACCESS  read-only
    STATUS      current
    DESCRIPTION "No description yet."

    ::= { dpConfigNFSStaticMountEntry 1 }

dpConfigNFSStaticMountname OBJECT-TYPE
    SYNTAX      DisplayString
    MAX-ACCESS  read-only
    STATUS      current
    DESCRIPTION "No description yet."

    ::= { dpConfigNFSStaticMountEntry 2 }

--

dpConfigNFSDynamicMountsTable OBJECT-TYPE
    SYNTAX      SEQUENCE OF DPConfigNFSDynamicMountsEntry
    MAX-ACCESS  not-accessible
    STATUS      current
    DESCRIPTION
        "Use this page to configure the parameters of dynamic NFS mounts for dpnfs:
        URL fetches. These mounts support access via URLs of the form
        dpnfs://hostname/path/file, causing the directory hostname:/path to be
        automatically mounted by NFS. It remains mounted until it times out for
        inactivity."

    ::= { dpConfig 126 }

dpConfigNFSDynamicMountsEntry OBJECT-TYPE
    SYNTAX      DPConfigNFSDynamicMountsEntry
    MAX-ACCESS  not-accessible
    STATUS      current
    DESCRIPTION "Table row."
    INDEX { dpConfigNFSDynamicMountsIndex, IMPLIED dpConfigNFSDynamicMountsname }

    ::= { dpConfigNFSDynamicMountsTable 1 }

DPConfigNFSDynamicMountsEntry ::= SEQUENCE {
    dpConfigNFSDynamicMountsIndex    Unsigned32,
    dpConfigNFSDynamicMountsname    DisplayString
}

dpConfigNFSDynamicMountsIndex OBJECT-TYPE
    SYNTAX      Unsigned32
    MAX-ACCESS  read-only
    STATUS      current
    DESCRIPTION "No description yet."

    ::= { dpConfigNFSDynamicMountsEntry 1 }

dpConfigNFSDynamicMountsname OBJECT-TYPE
    SYNTAX      DisplayString
    MAX-ACCESS  read-only
    STATUS      current
    DESCRIPTION "No description yet."

    ::= { dpConfigNFSDynamicMountsEntry 2 }

--

dpConfigWebAppErrorHandlingPolicyTable OBJECT-TYPE
    SYNTAX      SEQUENCE OF DPConfigWebAppErrorHandlingPolicyEntry
    MAX-ACCESS  not-accessible
    STATUS      current
    DESCRIPTION
        "When an error occurs this policy specifies how to handle the response to
        the user."

    ::= { dpConfig 127 }

dpConfigWebAppErrorHandlingPolicyEntry OBJECT-TYPE
    SYNTAX      DPConfigWebAppErrorHandlingPolicyEntry
    MAX-ACCESS  not-accessible
    STATUS      current
    DESCRIPTION "Table row."
    INDEX { dpConfigWebAppErrorHandlingPolicyIndex, IMPLIED dpConfigWebAppErrorHandlingPolicyname }

    ::= { dpConfigWebAppErrorHandlingPolicyTable 1 }

DPConfigWebAppErrorHandlingPolicyEntry ::= SEQUENCE {
    dpConfigWebAppErrorHandlingPolicyIndex    Unsigned32,
    dpConfigWebAppErrorHandlingPolicyname    DisplayString
}

dpConfigWebAppErrorHandlingPolicyIndex OBJECT-TYPE
    SYNTAX      Unsigned32
    MAX-ACCESS  read-only
    STATUS      current
    DESCRIPTION "No description yet."

    ::= { dpConfigWebAppErrorHandlingPolicyEntry 1 }

dpConfigWebAppErrorHandlingPolicyname OBJECT-TYPE
    SYNTAX      DisplayString
    MAX-ACCESS  read-only
    STATUS      current
    DESCRIPTION "No description yet."

    ::= { dpConfigWebAppErrorHandlingPolicyEntry 2 }

--

dpConfigSimpleCountMonitorTable OBJECT-TYPE
    SYNTAX      SEQUENCE OF DPConfigSimpleCountMonitorEntry
    MAX-ACCESS  not-accessible
    STATUS      current
    DESCRIPTION
        "A simple TPS based message monitor that limits the transaction rate any
        single user may achieve."

    ::= { dpConfig 128 }

dpConfigSimpleCountMonitorEntry OBJECT-TYPE
    SYNTAX      DPConfigSimpleCountMonitorEntry
    MAX-ACCESS  not-accessible
    STATUS      current
    DESCRIPTION "Table row."
    INDEX { dpConfigSimpleCountMonitorIndex, IMPLIED dpConfigSimpleCountMonitorname }

    ::= { dpConfigSimpleCountMonitorTable 1 }

DPConfigSimpleCountMonitorEntry ::= SEQUENCE {
    dpConfigSimpleCountMonitorIndex    Unsigned32,
    dpConfigSimpleCountMonitorname    DisplayString
}

dpConfigSimpleCountMonitorIndex OBJECT-TYPE
    SYNTAX      Unsigned32
    MAX-ACCESS  read-only
    STATUS      current
    DESCRIPTION "No description yet."

    ::= { dpConfigSimpleCountMonitorEntry 1 }

dpConfigSimpleCountMonitorname OBJECT-TYPE
    SYNTAX      DisplayString
    MAX-ACCESS  read-only
    STATUS      current
    DESCRIPTION "No description yet."

    ::= { dpConfigSimpleCountMonitorEntry 2 }

--

dpConfigNameValueProfileTable OBJECT-TYPE
    SYNTAX      SEQUENCE OF DPConfigNameValueProfileEntry
    MAX-ACCESS  not-accessible
    STATUS      current
    DESCRIPTION
        "Many HTTP things are expressed as name value pairs. These include HTTP
        headers, cookie values, url-encoded query strings, and url-encoded request
        messages. This profile provides a mechanism for what kinds of names are
        expected and for each kind of name what properties should be enforced on
        the corresponding values. When a name-value pair is not validated
        successfully that may generate an error, the pair might be stripped from
        the transaction, or the value may be mapped to another default value."

    ::= { dpConfig 129 }

dpConfigNameValueProfileEntry OBJECT-TYPE
    SYNTAX      DPConfigNameValueProfileEntry
    MAX-ACCESS  not-accessible
    STATUS      current
    DESCRIPTION "Table row."
    INDEX { dpConfigNameValueProfileIndex, IMPLIED dpConfigNameValueProfilename }

    ::= { dpConfigNameValueProfileTable 1 }

DPConfigNameValueProfileEntry ::= SEQUENCE {
    dpConfigNameValueProfileIndex    Unsigned32,
    dpConfigNameValueProfilename    DisplayString
}

dpConfigNameValueProfileIndex OBJECT-TYPE
    SYNTAX      Unsigned32
    MAX-ACCESS  read-only
    STATUS      current
    DESCRIPTION "No description yet."

    ::= { dpConfigNameValueProfileEntry 1 }

dpConfigNameValueProfilename OBJECT-TYPE
    SYNTAX      DisplayString
    MAX-ACCESS  read-only
    STATUS      current
    DESCRIPTION "No description yet."

    ::= { dpConfigNameValueProfileEntry 2 }

--

dpConfigWebAppResponseTable OBJECT-TYPE
    SYNTAX      SEQUENCE OF DPConfigWebAppResponseEntry
    MAX-ACCESS  not-accessible
    STATUS      current
    DESCRIPTION
        "The web response profile specifies various properties about the response
        side of the transaction that must be satisfied."

    ::= { dpConfig 130 }

dpConfigWebAppResponseEntry OBJECT-TYPE
    SYNTAX      DPConfigWebAppResponseEntry
    MAX-ACCESS  not-accessible
    STATUS      current
    DESCRIPTION "Table row."
    INDEX { dpConfigWebAppResponseIndex, IMPLIED dpConfigWebAppResponsename }

    ::= { dpConfigWebAppResponseTable 1 }

DPConfigWebAppResponseEntry ::= SEQUENCE {
    dpConfigWebAppResponseIndex    Unsigned32,
    dpConfigWebAppResponsename    DisplayString
}

dpConfigWebAppResponseIndex OBJECT-TYPE
    SYNTAX      Unsigned32
    MAX-ACCESS  read-only
    STATUS      current
    DESCRIPTION "No description yet."

    ::= { dpConfigWebAppResponseEntry 1 }

dpConfigWebAppResponsename OBJECT-TYPE
    SYNTAX      DisplayString
    MAX-ACCESS  read-only
    STATUS      current
    DESCRIPTION "No description yet."

    ::= { dpConfigWebAppResponseEntry 2 }

--

dpConfigWebAppRequestTable OBJECT-TYPE
    SYNTAX      SEQUENCE OF DPConfigWebAppRequestEntry
    MAX-ACCESS  not-accessible
    STATUS      current
    DESCRIPTION
        "The web request profile specifies various properties about the request
        side of the transaction that must be satisfied."

    ::= { dpConfig 131 }

dpConfigWebAppRequestEntry OBJECT-TYPE
    SYNTAX      DPConfigWebAppRequestEntry
    MAX-ACCESS  not-accessible
    STATUS      current
    DESCRIPTION "Table row."
    INDEX { dpConfigWebAppRequestIndex, IMPLIED dpConfigWebAppRequestname }

    ::= { dpConfigWebAppRequestTable 1 }

DPConfigWebAppRequestEntry ::= SEQUENCE {
    dpConfigWebAppRequestIndex    Unsigned32,
    dpConfigWebAppRequestname    DisplayString
}

dpConfigWebAppRequestIndex OBJECT-TYPE
    SYNTAX      Unsigned32
    MAX-ACCESS  read-only
    STATUS      current
    DESCRIPTION "No description yet."

    ::= { dpConfigWebAppRequestEntry 1 }

dpConfigWebAppRequestname OBJECT-TYPE
    SYNTAX      DisplayString
    MAX-ACCESS  read-only
    STATUS      current
    DESCRIPTION "No description yet."

    ::= { dpConfigWebAppRequestEntry 2 }

--

dpConfigWebAppFWTable OBJECT-TYPE
    SYNTAX      SEQUENCE OF DPConfigWebAppFWEntry
    MAX-ACCESS  not-accessible
    STATUS      current
    DESCRIPTION
        "The web application firewall provides filtering, security, and input
        validation for HTTP transactions."

    ::= { dpConfig 132 }

dpConfigWebAppFWEntry OBJECT-TYPE
    SYNTAX      DPConfigWebAppFWEntry
    MAX-ACCESS  not-accessible
    STATUS      current
    DESCRIPTION "Table row."
    INDEX { dpConfigWebAppFWIndex, IMPLIED dpConfigWebAppFWname }

    ::= { dpConfigWebAppFWTable 1 }

DPConfigWebAppFWEntry ::= SEQUENCE {
    dpConfigWebAppFWIndex    Unsigned32,
    dpConfigWebAppFWname    DisplayString
}

dpConfigWebAppFWIndex OBJECT-TYPE
    SYNTAX      Unsigned32
    MAX-ACCESS  read-only
    STATUS      current
    DESCRIPTION "No description yet."

    ::= { dpConfigWebAppFWEntry 1 }

dpConfigWebAppFWname OBJECT-TYPE
    SYNTAX      DisplayString
    MAX-ACCESS  read-only
    STATUS      current
    DESCRIPTION "No description yet."

    ::= { dpConfigWebAppFWEntry 2 }

--

dpConfigAppSecurityPolicyTable OBJECT-TYPE
    SYNTAX      SEQUENCE OF DPConfigAppSecurityPolicyEntry
    MAX-ACCESS  not-accessible
    STATUS      current
    DESCRIPTION
        "An Application Security Policy establishes the rules to use to enforce
        security for a Web Application Firewall service. This policy employs
        request maps, response maps, and error maps that provide a detailed
        security configuration. Each of these maps, in turn, matches to a Web
        Request Profile, Web Request Profile, or Error Policy, as the case might
        be."

    ::= { dpConfig 133 }

dpConfigAppSecurityPolicyEntry OBJECT-TYPE
    SYNTAX      DPConfigAppSecurityPolicyEntry
    MAX-ACCESS  not-accessible
    STATUS      current
    DESCRIPTION "Table row."
    INDEX { dpConfigAppSecurityPolicyIndex, IMPLIED dpConfigAppSecurityPolicyname }

    ::= { dpConfigAppSecurityPolicyTable 1 }

DPConfigAppSecurityPolicyEntry ::= SEQUENCE {
    dpConfigAppSecurityPolicyIndex    Unsigned32,
    dpConfigAppSecurityPolicyname    DisplayString
}

dpConfigAppSecurityPolicyIndex OBJECT-TYPE
    SYNTAX      Unsigned32
    MAX-ACCESS  read-only
    STATUS      current
    DESCRIPTION "No description yet."

    ::= { dpConfigAppSecurityPolicyEntry 1 }

dpConfigAppSecurityPolicyname OBJECT-TYPE
    SYNTAX      DisplayString
    MAX-ACCESS  read-only
    STATUS      current
    DESCRIPTION "No description yet."

    ::= { dpConfigAppSecurityPolicyEntry 2 }

--

dpConfigUDDIRegistryTable OBJECT-TYPE
    SYNTAX      SEQUENCE OF DPConfigUDDIRegistryEntry
    MAX-ACCESS  not-accessible
    STATUS      current
    DESCRIPTION
        "The UDDI registry is deprecated. Instead, use WebSphere Service Registry
        and Repository (WSRR) server. Configuration required for locating and
        accessing a UDDI registry. To configure a UDDI Subscription, the UDDI
        registry must support the UDDI Subscription API set."

    ::= { dpConfig 134 }

dpConfigUDDIRegistryEntry OBJECT-TYPE
    SYNTAX      DPConfigUDDIRegistryEntry
    MAX-ACCESS  not-accessible
    STATUS      current
    DESCRIPTION "Table row."
    INDEX { dpConfigUDDIRegistryIndex, IMPLIED dpConfigUDDIRegistryname }

    ::= { dpConfigUDDIRegistryTable 1 }

DPConfigUDDIRegistryEntry ::= SEQUENCE {
    dpConfigUDDIRegistryIndex    Unsigned32,
    dpConfigUDDIRegistryname    DisplayString
}

dpConfigUDDIRegistryIndex OBJECT-TYPE
    SYNTAX      Unsigned32
    MAX-ACCESS  read-only
    STATUS      current
    DESCRIPTION "No description yet."

    ::= { dpConfigUDDIRegistryEntry 1 }

dpConfigUDDIRegistryname OBJECT-TYPE
    SYNTAX      DisplayString
    MAX-ACCESS  read-only
    STATUS      current
    DESCRIPTION "No description yet."

    ::= { dpConfigUDDIRegistryEntry 2 }

--

dpConfigWebAppSessionPolicyTable OBJECT-TYPE
    SYNTAX      SEQUENCE OF DPConfigWebAppSessionPolicyEntry
    MAX-ACCESS  not-accessible
    STATUS      current
    DESCRIPTION
        "Session policy - specify a series of start pages that the a web
        application firewall protected host use as initial browsing points.
        Accessing these pages issues a signed and time limited cookie which must
        be presented for accessing any pages not designated as a starting point."

    ::= { dpConfig 135 }

dpConfigWebAppSessionPolicyEntry OBJECT-TYPE
    SYNTAX      DPConfigWebAppSessionPolicyEntry
    MAX-ACCESS  not-accessible
    STATUS      current
    DESCRIPTION "Table row."
    INDEX { dpConfigWebAppSessionPolicyIndex, IMPLIED dpConfigWebAppSessionPolicyname }

    ::= { dpConfigWebAppSessionPolicyTable 1 }

DPConfigWebAppSessionPolicyEntry ::= SEQUENCE {
    dpConfigWebAppSessionPolicyIndex    Unsigned32,
    dpConfigWebAppSessionPolicyname    DisplayString
}

dpConfigWebAppSessionPolicyIndex OBJECT-TYPE
    SYNTAX      Unsigned32
    MAX-ACCESS  read-only
    STATUS      current
    DESCRIPTION "No description yet."

    ::= { dpConfigWebAppSessionPolicyEntry 1 }

dpConfigWebAppSessionPolicyname OBJECT-TYPE
    SYNTAX      DisplayString
    MAX-ACCESS  read-only
    STATUS      current
    DESCRIPTION "No description yet."

    ::= { dpConfigWebAppSessionPolicyEntry 2 }

--

dpConfigJMSServerTable OBJECT-TYPE
    SYNTAX      SEQUENCE OF DPConfigJMSServerEntry
    MAX-ACCESS  not-accessible
    STATUS      current
    DESCRIPTION "Table."

    ::= { dpConfig 136 }

dpConfigJMSServerEntry OBJECT-TYPE
    SYNTAX      DPConfigJMSServerEntry
    MAX-ACCESS  not-accessible
    STATUS      current
    DESCRIPTION "Table row."
    INDEX { dpConfigJMSServerIndex, IMPLIED dpConfigJMSServername }

    ::= { dpConfigJMSServerTable 1 }

DPConfigJMSServerEntry ::= SEQUENCE {
    dpConfigJMSServerIndex    Unsigned32,
    dpConfigJMSServername    DisplayString
}

dpConfigJMSServerIndex OBJECT-TYPE
    SYNTAX      Unsigned32
    MAX-ACCESS  read-only
    STATUS      current
    DESCRIPTION "No description yet."

    ::= { dpConfigJMSServerEntry 1 }

dpConfigJMSServername OBJECT-TYPE
    SYNTAX      DisplayString
    MAX-ACCESS  read-only
    STATUS      current
    DESCRIPTION "No description yet."

    ::= { dpConfigJMSServerEntry 2 }

--

dpConfigTibcoEMSServerTable OBJECT-TYPE
    SYNTAX      SEQUENCE OF DPConfigTibcoEMSServerEntry
    MAX-ACCESS  not-accessible
    STATUS      current
    DESCRIPTION
        "TIBCO EMS Server is responsible for messaging services for communicating
        applications by periodically monitoring/polling queues, by ensuring that
        sent messages are directed to the correct receive queue, or that messages
        are routed to another queue manager."

    ::= { dpConfig 137 }

dpConfigTibcoEMSServerEntry OBJECT-TYPE
    SYNTAX      DPConfigTibcoEMSServerEntry
    MAX-ACCESS  not-accessible
    STATUS      current
    DESCRIPTION "Table row."
    INDEX { dpConfigTibcoEMSServerIndex, IMPLIED dpConfigTibcoEMSServername }

    ::= { dpConfigTibcoEMSServerTable 1 }

DPConfigTibcoEMSServerEntry ::= SEQUENCE {
    dpConfigTibcoEMSServerIndex    Unsigned32,
    dpConfigTibcoEMSServername    DisplayString
}

dpConfigTibcoEMSServerIndex OBJECT-TYPE
    SYNTAX      Unsigned32
    MAX-ACCESS  read-only
    STATUS      current
    DESCRIPTION "No description yet."

    ::= { dpConfigTibcoEMSServerEntry 1 }

dpConfigTibcoEMSServername OBJECT-TYPE
    SYNTAX      DisplayString
    MAX-ACCESS  read-only
    STATUS      current
    DESCRIPTION "No description yet."

    ::= { dpConfigTibcoEMSServerEntry 2 }

--

dpConfigTibcoEMSSourceProtocolHandlerTable OBJECT-TYPE
    SYNTAX      SEQUENCE OF DPConfigTibcoEMSSourceProtocolHandlerEntry
    MAX-ACCESS  not-accessible
    STATUS      current
    DESCRIPTION
        "TIBCO EMS Handler"

    ::= { dpConfig 138 }

dpConfigTibcoEMSSourceProtocolHandlerEntry OBJECT-TYPE
    SYNTAX      DPConfigTibcoEMSSourceProtocolHandlerEntry
    MAX-ACCESS  not-accessible
    STATUS      current
    DESCRIPTION "Table row."
    INDEX { dpConfigTibcoEMSSourceProtocolHandlerIndex, IMPLIED dpConfigTibcoEMSSourceProtocolHandlername }

    ::= { dpConfigTibcoEMSSourceProtocolHandlerTable 1 }

DPConfigTibcoEMSSourceProtocolHandlerEntry ::= SEQUENCE {
    dpConfigTibcoEMSSourceProtocolHandlerIndex    Unsigned32,
    dpConfigTibcoEMSSourceProtocolHandlername    DisplayString
}

dpConfigTibcoEMSSourceProtocolHandlerIndex OBJECT-TYPE
    SYNTAX      Unsigned32
    MAX-ACCESS  read-only
    STATUS      current
    DESCRIPTION "No description yet."

    ::= { dpConfigTibcoEMSSourceProtocolHandlerEntry 1 }

dpConfigTibcoEMSSourceProtocolHandlername OBJECT-TYPE
    SYNTAX      DisplayString
    MAX-ACCESS  read-only
    STATUS      current
    DESCRIPTION "No description yet."

    ::= { dpConfigTibcoEMSSourceProtocolHandlerEntry 2 }

--

dpConfigXACMLPDPTable OBJECT-TYPE
    SYNTAX      SEQUENCE OF DPConfigXACMLPDPEntry
    MAX-ACCESS  not-accessible
    STATUS      current
    DESCRIPTION
        "The XACML policies can be evaluated on a DataPower device, This on-box
        XACML Policy Decision Point (PDP) allows customers to define the necessary
        information so that it can evaluate the corresponding XACML policies
        against a XACML request for an XACML Policy Enforcement Point (PEP). The
        DataPower PEP is implemented with AAA action."

    ::= { dpConfig 139 }

dpConfigXACMLPDPEntry OBJECT-TYPE
    SYNTAX      DPConfigXACMLPDPEntry
    MAX-ACCESS  not-accessible
    STATUS      current
    DESCRIPTION "Table row."
    INDEX { dpConfigXACMLPDPIndex, IMPLIED dpConfigXACMLPDPname }

    ::= { dpConfigXACMLPDPTable 1 }

DPConfigXACMLPDPEntry ::= SEQUENCE {
    dpConfigXACMLPDPIndex    Unsigned32,
    dpConfigXACMLPDPname    DisplayString
}

dpConfigXACMLPDPIndex OBJECT-TYPE
    SYNTAX      Unsigned32
    MAX-ACCESS  read-only
    STATUS      current
    DESCRIPTION "No description yet."

    ::= { dpConfigXACMLPDPEntry 1 }

dpConfigXACMLPDPname OBJECT-TYPE
    SYNTAX      DisplayString
    MAX-ACCESS  read-only
    STATUS      current
    DESCRIPTION "No description yet."

    ::= { dpConfigXACMLPDPEntry 2 }

--

dpConfigJMSSourceProtocolHandlerTable OBJECT-TYPE
    SYNTAX      SEQUENCE OF DPConfigJMSSourceProtocolHandlerEntry
    MAX-ACCESS  not-accessible
    STATUS      current
    DESCRIPTION "Table."

    ::= { dpConfig 140 }

dpConfigJMSSourceProtocolHandlerEntry OBJECT-TYPE
    SYNTAX      DPConfigJMSSourceProtocolHandlerEntry
    MAX-ACCESS  not-accessible
    STATUS      current
    DESCRIPTION "Table row."
    INDEX { dpConfigJMSSourceProtocolHandlerIndex, IMPLIED dpConfigJMSSourceProtocolHandlername }

    ::= { dpConfigJMSSourceProtocolHandlerTable 1 }

DPConfigJMSSourceProtocolHandlerEntry ::= SEQUENCE {
    dpConfigJMSSourceProtocolHandlerIndex    Unsigned32,
    dpConfigJMSSourceProtocolHandlername    DisplayString
}

dpConfigJMSSourceProtocolHandlerIndex OBJECT-TYPE
    SYNTAX      Unsigned32
    MAX-ACCESS  read-only
    STATUS      current
    DESCRIPTION "No description yet."

    ::= { dpConfigJMSSourceProtocolHandlerEntry 1 }

dpConfigJMSSourceProtocolHandlername OBJECT-TYPE
    SYNTAX      DisplayString
    MAX-ACCESS  read-only
    STATUS      current
    DESCRIPTION "No description yet."

    ::= { dpConfigJMSSourceProtocolHandlerEntry 2 }

--

dpConfigWebSphereJMSServerTable OBJECT-TYPE
    SYNTAX      SEQUENCE OF DPConfigWebSphereJMSServerEntry
    MAX-ACCESS  not-accessible
    STATUS      current
    DESCRIPTION
        "WebSphere JMS is responsible for messaging services for communicating
        applications by periodically monitoring/polling queues, by ensuring that
        sent messages are directed to the correct receive queue, or that messages
        are routed to another queue manager."

    ::= { dpConfig 141 }

dpConfigWebSphereJMSServerEntry OBJECT-TYPE
    SYNTAX      DPConfigWebSphereJMSServerEntry
    MAX-ACCESS  not-accessible
    STATUS      current
    DESCRIPTION "Table row."
    INDEX { dpConfigWebSphereJMSServerIndex, IMPLIED dpConfigWebSphereJMSServername }

    ::= { dpConfigWebSphereJMSServerTable 1 }

DPConfigWebSphereJMSServerEntry ::= SEQUENCE {
    dpConfigWebSphereJMSServerIndex    Unsigned32,
    dpConfigWebSphereJMSServername    DisplayString
}

dpConfigWebSphereJMSServerIndex OBJECT-TYPE
    SYNTAX      Unsigned32
    MAX-ACCESS  read-only
    STATUS      current
    DESCRIPTION "No description yet."

    ::= { dpConfigWebSphereJMSServerEntry 1 }

dpConfigWebSphereJMSServername OBJECT-TYPE
    SYNTAX      DisplayString
    MAX-ACCESS  read-only
    STATUS      current
    DESCRIPTION "No description yet."

    ::= { dpConfigWebSphereJMSServerEntry 2 }

--

dpConfigWebSphereJMSSourceProtocolHandlerTable OBJECT-TYPE
    SYNTAX      SEQUENCE OF DPConfigWebSphereJMSSourceProtocolHandlerEntry
    MAX-ACCESS  not-accessible
    STATUS      current
    DESCRIPTION "Table."

    ::= { dpConfig 142 }

dpConfigWebSphereJMSSourceProtocolHandlerEntry OBJECT-TYPE
    SYNTAX      DPConfigWebSphereJMSSourceProtocolHandlerEntry
    MAX-ACCESS  not-accessible
    STATUS      current
    DESCRIPTION "Table row."
    INDEX { dpConfigWebSphereJMSSourceProtocolHandlerIndex, IMPLIED dpConfigWebSphereJMSSourceProtocolHandlername }

    ::= { dpConfigWebSphereJMSSourceProtocolHandlerTable 1 }

DPConfigWebSphereJMSSourceProtocolHandlerEntry ::= SEQUENCE {
    dpConfigWebSphereJMSSourceProtocolHandlerIndex    Unsigned32,
    dpConfigWebSphereJMSSourceProtocolHandlername    DisplayString
}

dpConfigWebSphereJMSSourceProtocolHandlerIndex OBJECT-TYPE
    SYNTAX      Unsigned32
    MAX-ACCESS  read-only
    STATUS      current
    DESCRIPTION "No description yet."

    ::= { dpConfigWebSphereJMSSourceProtocolHandlerEntry 1 }

dpConfigWebSphereJMSSourceProtocolHandlername OBJECT-TYPE
    SYNTAX      DisplayString
    MAX-ACCESS  read-only
    STATUS      current
    DESCRIPTION "No description yet."

    ::= { dpConfigWebSphereJMSSourceProtocolHandlerEntry 2 }

--

dpConfigProcessingMetadataTable OBJECT-TYPE
    SYNTAX      SEQUENCE OF DPConfigProcessingMetadataEntry
    MAX-ACCESS  not-accessible
    STATUS      current
    DESCRIPTION
        "A Processing Metadata object contains a list of metadata items extracted
        from a message, such as protocol header values, or from the device
        processing scope, such as system variables. This list, or manifest, of
        item values is then returned by the metadata object in an XML nodeset.
        Currently used by an AAA Policy for Identity and Resource extraction."

    ::= { dpConfig 143 }

dpConfigProcessingMetadataEntry OBJECT-TYPE
    SYNTAX      DPConfigProcessingMetadataEntry
    MAX-ACCESS  not-accessible
    STATUS      current
    DESCRIPTION "Table row."
    INDEX { dpConfigProcessingMetadataIndex, IMPLIED dpConfigProcessingMetadataname }

    ::= { dpConfigProcessingMetadataTable 1 }

DPConfigProcessingMetadataEntry ::= SEQUENCE {
    dpConfigProcessingMetadataIndex    Unsigned32,
    dpConfigProcessingMetadataname    DisplayString
}

dpConfigProcessingMetadataIndex OBJECT-TYPE
    SYNTAX      Unsigned32
    MAX-ACCESS  read-only
    STATUS      current
    DESCRIPTION "No description yet."

    ::= { dpConfigProcessingMetadataEntry 1 }

dpConfigProcessingMetadataname OBJECT-TYPE
    SYNTAX      DisplayString
    MAX-ACCESS  read-only
    STATUS      current
    DESCRIPTION "No description yet."

    ::= { dpConfigProcessingMetadataEntry 2 }

--

dpConfigMTOMPolicyTable OBJECT-TYPE
    SYNTAX      SEQUENCE OF DPConfigMTOMPolicyEntry
    MAX-ACCESS  not-accessible
    STATUS      current
    DESCRIPTION
        "An MTOM policy provides a mechanism for optimizing the transmission and
        wire format of an XML/SOAP message. Optimization is performed by selecting
        elements with base64-encoded character data. The selected elements are
        decoded and attached as MIME attachment parts before transmission.
        Decoding before transmission reduces the overhead that is associated with
        base64-encoded data."

    ::= { dpConfig 144 }

dpConfigMTOMPolicyEntry OBJECT-TYPE
    SYNTAX      DPConfigMTOMPolicyEntry
    MAX-ACCESS  not-accessible
    STATUS      current
    DESCRIPTION "Table row."
    INDEX { dpConfigMTOMPolicyIndex, IMPLIED dpConfigMTOMPolicyname }

    ::= { dpConfigMTOMPolicyTable 1 }

DPConfigMTOMPolicyEntry ::= SEQUENCE {
    dpConfigMTOMPolicyIndex    Unsigned32,
    dpConfigMTOMPolicyname    DisplayString
}

dpConfigMTOMPolicyIndex OBJECT-TYPE
    SYNTAX      Unsigned32
    MAX-ACCESS  read-only
    STATUS      current
    DESCRIPTION "No description yet."

    ::= { dpConfigMTOMPolicyEntry 1 }

dpConfigMTOMPolicyname OBJECT-TYPE
    SYNTAX      DisplayString
    MAX-ACCESS  read-only
    STATUS      current
    DESCRIPTION "No description yet."

    ::= { dpConfigMTOMPolicyEntry 2 }

--

dpConfigFTPServerSourceProtocolHandlerTable OBJECT-TYPE
    SYNTAX      SEQUENCE OF DPConfigFTPServerSourceProtocolHandlerEntry
    MAX-ACCESS  not-accessible
    STATUS      current
    DESCRIPTION
        "The FTP Server handler provides an FTP server that can be used to submit
        files for processing by the system. Each file that is written results in
        one transaction. There can be multiple FTP servers, but only one server
        can listen on the default port 21 on a given IP address. There can be
        multiple simultaneous connections from FTP clients to the same FTP server.
        #b#Notes:#/b# The 226 FTP response code at the end of an FTP #b#STOR#/b#
        or #b#STOU#/b# command is conditional on successful completion of the
        internal steps and backside operation of the transaction. Changes in the
        configuration affect only new connections to this FTP server. Existing
        connections continue to use their current configuration until they
        disconnect."

    ::= { dpConfig 145 }

dpConfigFTPServerSourceProtocolHandlerEntry OBJECT-TYPE
    SYNTAX      DPConfigFTPServerSourceProtocolHandlerEntry
    MAX-ACCESS  not-accessible
    STATUS      current
    DESCRIPTION "Table row."
    INDEX { dpConfigFTPServerSourceProtocolHandlerIndex, IMPLIED dpConfigFTPServerSourceProtocolHandlername }

    ::= { dpConfigFTPServerSourceProtocolHandlerTable 1 }

DPConfigFTPServerSourceProtocolHandlerEntry ::= SEQUENCE {
    dpConfigFTPServerSourceProtocolHandlerIndex    Unsigned32,
    dpConfigFTPServerSourceProtocolHandlername    DisplayString
}

dpConfigFTPServerSourceProtocolHandlerIndex OBJECT-TYPE
    SYNTAX      Unsigned32
    MAX-ACCESS  read-only
    STATUS      current
    DESCRIPTION "No description yet."

    ::= { dpConfigFTPServerSourceProtocolHandlerEntry 1 }

dpConfigFTPServerSourceProtocolHandlername OBJECT-TYPE
    SYNTAX      DisplayString
    MAX-ACCESS  read-only
    STATUS      current
    DESCRIPTION "No description yet."

    ::= { dpConfigFTPServerSourceProtocolHandlerEntry 2 }

--

dpConfigFilePollerSourceProtocolHandlerTable OBJECT-TYPE
    SYNTAX      SEQUENCE OF DPConfigFilePollerSourceProtocolHandlerEntry
    MAX-ACCESS  not-accessible
    STATUS      current
    DESCRIPTION "Table."

    ::= { dpConfig 146 }

dpConfigFilePollerSourceProtocolHandlerEntry OBJECT-TYPE
    SYNTAX      DPConfigFilePollerSourceProtocolHandlerEntry
    MAX-ACCESS  not-accessible
    STATUS      current
    DESCRIPTION "Table row."
    INDEX { dpConfigFilePollerSourceProtocolHandlerIndex, IMPLIED dpConfigFilePollerSourceProtocolHandlername }

    ::= { dpConfigFilePollerSourceProtocolHandlerTable 1 }

DPConfigFilePollerSourceProtocolHandlerEntry ::= SEQUENCE {
    dpConfigFilePollerSourceProtocolHandlerIndex    Unsigned32,
    dpConfigFilePollerSourceProtocolHandlername    DisplayString
}

dpConfigFilePollerSourceProtocolHandlerIndex OBJECT-TYPE
    SYNTAX      Unsigned32
    MAX-ACCESS  read-only
    STATUS      current
    DESCRIPTION "No description yet."

    ::= { dpConfigFilePollerSourceProtocolHandlerEntry 1 }

dpConfigFilePollerSourceProtocolHandlername OBJECT-TYPE
    SYNTAX      DisplayString
    MAX-ACCESS  read-only
    STATUS      current
    DESCRIPTION "No description yet."

    ::= { dpConfigFilePollerSourceProtocolHandlerEntry 2 }

--

dpConfigNFSFilePollerSourceProtocolHandlerTable OBJECT-TYPE
    SYNTAX      SEQUENCE OF DPConfigNFSFilePollerSourceProtocolHandlerEntry
    MAX-ACCESS  not-accessible
    STATUS      current
    DESCRIPTION
        "Use this front side option to have file based input from an NFS mount. The
        mount point must exist and have the appropriate permissions to perform the
        designated operations. For these configured mount points, ensure that the
        read, write, and delete permissions are available, as required."

    ::= { dpConfig 147 }

dpConfigNFSFilePollerSourceProtocolHandlerEntry OBJECT-TYPE
    SYNTAX      DPConfigNFSFilePollerSourceProtocolHandlerEntry
    MAX-ACCESS  not-accessible
    STATUS      current
    DESCRIPTION "Table row."
    INDEX { dpConfigNFSFilePollerSourceProtocolHandlerIndex, IMPLIED dpConfigNFSFilePollerSourceProtocolHandlername }

    ::= { dpConfigNFSFilePollerSourceProtocolHandlerTable 1 }

DPConfigNFSFilePollerSourceProtocolHandlerEntry ::= SEQUENCE {
    dpConfigNFSFilePollerSourceProtocolHandlerIndex    Unsigned32,
    dpConfigNFSFilePollerSourceProtocolHandlername    DisplayString
}

dpConfigNFSFilePollerSourceProtocolHandlerIndex OBJECT-TYPE
    SYNTAX      Unsigned32
    MAX-ACCESS  read-only
    STATUS      current
    DESCRIPTION "No description yet."

    ::= { dpConfigNFSFilePollerSourceProtocolHandlerEntry 1 }

dpConfigNFSFilePollerSourceProtocolHandlername OBJECT-TYPE
    SYNTAX      DisplayString
    MAX-ACCESS  read-only
    STATUS      current
    DESCRIPTION "No description yet."

    ::= { dpConfigNFSFilePollerSourceProtocolHandlerEntry 2 }

--

dpConfigFTPFilePollerSourceProtocolHandlerTable OBJECT-TYPE
    SYNTAX      SEQUENCE OF DPConfigFTPFilePollerSourceProtocolHandlerEntry
    MAX-ACCESS  not-accessible
    STATUS      current
    DESCRIPTION
        "Use this front side option to have file based input from a configured FTP
        directory. The directory must exist and have the appropriate permission to
        perform the designated operations. For these configured directories,
        ensure that the read, write, and delete permissions are available, as
        required."

    ::= { dpConfig 148 }

dpConfigFTPFilePollerSourceProtocolHandlerEntry OBJECT-TYPE
    SYNTAX      DPConfigFTPFilePollerSourceProtocolHandlerEntry
    MAX-ACCESS  not-accessible
    STATUS      current
    DESCRIPTION "Table row."
    INDEX { dpConfigFTPFilePollerSourceProtocolHandlerIndex, IMPLIED dpConfigFTPFilePollerSourceProtocolHandlername }

    ::= { dpConfigFTPFilePollerSourceProtocolHandlerTable 1 }

DPConfigFTPFilePollerSourceProtocolHandlerEntry ::= SEQUENCE {
    dpConfigFTPFilePollerSourceProtocolHandlerIndex    Unsigned32,
    dpConfigFTPFilePollerSourceProtocolHandlername    DisplayString
}

dpConfigFTPFilePollerSourceProtocolHandlerIndex OBJECT-TYPE
    SYNTAX      Unsigned32
    MAX-ACCESS  read-only
    STATUS      current
    DESCRIPTION "No description yet."

    ::= { dpConfigFTPFilePollerSourceProtocolHandlerEntry 1 }

dpConfigFTPFilePollerSourceProtocolHandlername OBJECT-TYPE
    SYNTAX      DisplayString
    MAX-ACCESS  read-only
    STATUS      current
    DESCRIPTION "No description yet."

    ::= { dpConfigFTPFilePollerSourceProtocolHandlerEntry 2 }

--

dpConfigFTPQuoteCommandsTable OBJECT-TYPE
    SYNTAX      SEQUENCE OF DPConfigFTPQuoteCommandsEntry
    MAX-ACCESS  not-accessible
    STATUS      current
    DESCRIPTION
        "The configturation creates a named list of FTP commands to be quoted to a
        remote FTP server before a file transfer. These commands are referenced by
        the FTP Policies section of a User Agent configuration."

    ::= { dpConfig 149 }

dpConfigFTPQuoteCommandsEntry OBJECT-TYPE
    SYNTAX      DPConfigFTPQuoteCommandsEntry
    MAX-ACCESS  not-accessible
    STATUS      current
    DESCRIPTION "Table row."
    INDEX { dpConfigFTPQuoteCommandsIndex, IMPLIED dpConfigFTPQuoteCommandsname }

    ::= { dpConfigFTPQuoteCommandsTable 1 }

DPConfigFTPQuoteCommandsEntry ::= SEQUENCE {
    dpConfigFTPQuoteCommandsIndex    Unsigned32,
    dpConfigFTPQuoteCommandsname    DisplayString
}

dpConfigFTPQuoteCommandsIndex OBJECT-TYPE
    SYNTAX      Unsigned32
    MAX-ACCESS  read-only
    STATUS      current
    DESCRIPTION "No description yet."

    ::= { dpConfigFTPQuoteCommandsEntry 1 }

dpConfigFTPQuoteCommandsname OBJECT-TYPE
    SYNTAX      DisplayString
    MAX-ACCESS  read-only
    STATUS      current
    DESCRIPTION "No description yet."

    ::= { dpConfigFTPQuoteCommandsEntry 2 }

--

dpConfigMQQMBaseTable OBJECT-TYPE
    SYNTAX      SEQUENCE OF DPConfigMQQMBaseEntry
    MAX-ACCESS  not-accessible
    STATUS      current
    DESCRIPTION "Table."

    ::= { dpConfig 150 }

dpConfigMQQMBaseEntry OBJECT-TYPE
    SYNTAX      DPConfigMQQMBaseEntry
    MAX-ACCESS  not-accessible
    STATUS      current
    DESCRIPTION "Table row."
    INDEX { dpConfigMQQMBaseIndex, IMPLIED dpConfigMQQMBasename }

    ::= { dpConfigMQQMBaseTable 1 }

DPConfigMQQMBaseEntry ::= SEQUENCE {
    dpConfigMQQMBaseIndex    Unsigned32,
    dpConfigMQQMBasename    DisplayString
}

dpConfigMQQMBaseIndex OBJECT-TYPE
    SYNTAX      Unsigned32
    MAX-ACCESS  read-only
    STATUS      current
    DESCRIPTION "No description yet."

    ::= { dpConfigMQQMBaseEntry 1 }

dpConfigMQQMBasename OBJECT-TYPE
    SYNTAX      DisplayString
    MAX-ACCESS  read-only
    STATUS      current
    DESCRIPTION "No description yet."

    ::= { dpConfigMQQMBaseEntry 2 }

--

dpConfigMQQMGroupTable OBJECT-TYPE
    SYNTAX      SEQUENCE OF DPConfigMQQMGroupEntry
    MAX-ACCESS  not-accessible
    STATUS      current
    DESCRIPTION
        "An IBM MQ Queue Manager Group enables automatic failover between queue
        managers when one (or more) queue manager becomes unavailable. If you
        define multiple backup queue managers, the appliance searches in the order
        in which the queue managers are listed. The first active queue manager in
        the group replaces the primary queue manager. #b#Note:#/b# In IBM MQ
        server 7.0.1 or later, you can configure the IBM MQ Queue Manager to work
        with the multi-instance feature in the IBM MQ server. Connect the primary
        queue manager to one of the instances of a queue manager in the IBM MQ
        server, and the backup queue manager to the other instance. All
        connections for the IBM MQ Queue Manager group in the DataPower appliance
        will go to the queue manager connected to the active instance. If the
        active instance in the IBM MQ server fails, the queue manager connected to
        the standby instance will automatically take over all the data and logs
        from the queue manager connected to the original active instance."

    ::= { dpConfig 151 }

dpConfigMQQMGroupEntry OBJECT-TYPE
    SYNTAX      DPConfigMQQMGroupEntry
    MAX-ACCESS  not-accessible
    STATUS      current
    DESCRIPTION "Table row."
    INDEX { dpConfigMQQMGroupIndex, IMPLIED dpConfigMQQMGroupname }

    ::= { dpConfigMQQMGroupTable 1 }

DPConfigMQQMGroupEntry ::= SEQUENCE {
    dpConfigMQQMGroupIndex    Unsigned32,
    dpConfigMQQMGroupname    DisplayString
}

dpConfigMQQMGroupIndex OBJECT-TYPE
    SYNTAX      Unsigned32
    MAX-ACCESS  read-only
    STATUS      current
    DESCRIPTION "No description yet."

    ::= { dpConfigMQQMGroupEntry 1 }

dpConfigMQQMGroupname OBJECT-TYPE
    SYNTAX      DisplayString
    MAX-ACCESS  read-only
    STATUS      current
    DESCRIPTION "No description yet."

    ::= { dpConfigMQQMGroupEntry 2 }

--

dpConfigWSRRServerTable OBJECT-TYPE
    SYNTAX      SEQUENCE OF DPConfigWSRRServerEntry
    MAX-ACCESS  not-accessible
    STATUS      current
    DESCRIPTION
        "Configuration required to locate and access WSRR (WebSphere Service
        Registry and Repository)."

    ::= { dpConfig 152 }

dpConfigWSRRServerEntry OBJECT-TYPE
    SYNTAX      DPConfigWSRRServerEntry
    MAX-ACCESS  not-accessible
    STATUS      current
    DESCRIPTION "Table row."
    INDEX { dpConfigWSRRServerIndex, IMPLIED dpConfigWSRRServername }

    ::= { dpConfigWSRRServerTable 1 }

DPConfigWSRRServerEntry ::= SEQUENCE {
    dpConfigWSRRServerIndex    Unsigned32,
    dpConfigWSRRServername    DisplayString
}

dpConfigWSRRServerIndex OBJECT-TYPE
    SYNTAX      Unsigned32
    MAX-ACCESS  read-only
    STATUS      current
    DESCRIPTION "No description yet."

    ::= { dpConfigWSRRServerEntry 1 }

dpConfigWSRRServername OBJECT-TYPE
    SYNTAX      DisplayString
    MAX-ACCESS  read-only
    STATUS      current
    DESCRIPTION "No description yet."

    ::= { dpConfigWSRRServerEntry 2 }

--

dpConfigWSRRSubscriptionTable OBJECT-TYPE
    SYNTAX      SEQUENCE OF DPConfigWSRRSubscriptionEntry
    MAX-ACCESS  not-accessible
    STATUS      current
    DESCRIPTION
        "Use this screen to provide the required configuration properties for a
        WSRR (WebSphere Service Registry and Repository) subscription. The WSRR
        Subscription is useful when you want to deploy web services with a direct
        reference to a service document required for DataPower service operations.
        The configuration requires the reference to a WSRR server, the name of the
        WSRR resource, and its namespace. If there is more than one version of the
        service document, you must specify the version to reference. DataPower
        services associated with the subscription are updated based on the
        synchronization method specified in the subscription. A DataPower service
        stores a local copy of the subscribed object. Changes performed on the
        WSRR server to service document attributes such as the name of the WSRR
        resource, namespace, or version will require updating the WSRR
        Subscription. For an indirect reference to a set of WSRR resources see
        WSRR Saved Search Subscription."

    ::= { dpConfig 153 }

dpConfigWSRRSubscriptionEntry OBJECT-TYPE
    SYNTAX      DPConfigWSRRSubscriptionEntry
    MAX-ACCESS  not-accessible
    STATUS      current
    DESCRIPTION "Table row."
    INDEX { dpConfigWSRRSubscriptionIndex, IMPLIED dpConfigWSRRSubscriptionname }

    ::= { dpConfigWSRRSubscriptionTable 1 }

DPConfigWSRRSubscriptionEntry ::= SEQUENCE {
    dpConfigWSRRSubscriptionIndex    Unsigned32,
    dpConfigWSRRSubscriptionname    DisplayString
}

dpConfigWSRRSubscriptionIndex OBJECT-TYPE
    SYNTAX      Unsigned32
    MAX-ACCESS  read-only
    STATUS      current
    DESCRIPTION "No description yet."

    ::= { dpConfigWSRRSubscriptionEntry 1 }

dpConfigWSRRSubscriptionname OBJECT-TYPE
    SYNTAX      DisplayString
    MAX-ACCESS  read-only
    STATUS      current
    DESCRIPTION "No description yet."

    ::= { dpConfigWSRRSubscriptionEntry 2 }

--

dpConfigWebServiceSubscriptionTable OBJECT-TYPE
    SYNTAX      SEQUENCE OF DPConfigWebServiceSubscriptionEntry
    MAX-ACCESS  not-accessible
    STATUS      current
    DESCRIPTION "Table."

    ::= { dpConfig 154 }

dpConfigWebServiceSubscriptionEntry OBJECT-TYPE
    SYNTAX      DPConfigWebServiceSubscriptionEntry
    MAX-ACCESS  not-accessible
    STATUS      current
    DESCRIPTION "Table row."
    INDEX { dpConfigWebServiceSubscriptionIndex, IMPLIED dpConfigWebServiceSubscriptionname }

    ::= { dpConfigWebServiceSubscriptionTable 1 }

DPConfigWebServiceSubscriptionEntry ::= SEQUENCE {
    dpConfigWebServiceSubscriptionIndex    Unsigned32,
    dpConfigWebServiceSubscriptionname    DisplayString
}

dpConfigWebServiceSubscriptionIndex OBJECT-TYPE
    SYNTAX      Unsigned32
    MAX-ACCESS  read-only
    STATUS      current
    DESCRIPTION "No description yet."

    ::= { dpConfigWebServiceSubscriptionEntry 1 }

dpConfigWebServiceSubscriptionname OBJECT-TYPE
    SYNTAX      DisplayString
    MAX-ACCESS  read-only
    STATUS      current
    DESCRIPTION "No description yet."

    ::= { dpConfigWebServiceSubscriptionEntry 2 }

--

dpConfigUDDISubscriptionTable OBJECT-TYPE
    SYNTAX      SEQUENCE OF DPConfigUDDISubscriptionEntry
    MAX-ACCESS  not-accessible
    STATUS      current
    DESCRIPTION
        "The UDDI subscription is deprecated. Instead, use WebSphere Service
        Registry and Repository (WSRR) subscription. Configuration required for a
        UDDI subscriber to receive notifications from a UDDI Server. In addition
        to configuring the UDDI Subscription, you must also enable UDDI
        Subscription as a service in the configuration of the XML Management
        Interface in the default domain. Web Service Proxies are automatically
        built and updated based on the UDDI subscription. Web Service Proxy
        virtualizes the Web Service endpoints detailed in the WSDLs returned by
        the subscription."

    ::= { dpConfig 155 }

dpConfigUDDISubscriptionEntry OBJECT-TYPE
    SYNTAX      DPConfigUDDISubscriptionEntry
    MAX-ACCESS  not-accessible
    STATUS      current
    DESCRIPTION "Table row."
    INDEX { dpConfigUDDISubscriptionIndex, IMPLIED dpConfigUDDISubscriptionname }

    ::= { dpConfigUDDISubscriptionTable 1 }

DPConfigUDDISubscriptionEntry ::= SEQUENCE {
    dpConfigUDDISubscriptionIndex    Unsigned32,
    dpConfigUDDISubscriptionname    DisplayString
}

dpConfigUDDISubscriptionIndex OBJECT-TYPE
    SYNTAX      Unsigned32
    MAX-ACCESS  read-only
    STATUS      current
    DESCRIPTION "No description yet."

    ::= { dpConfigUDDISubscriptionEntry 1 }

dpConfigUDDISubscriptionname OBJECT-TYPE
    SYNTAX      DisplayString
    MAX-ACCESS  read-only
    STATUS      current
    DESCRIPTION "No description yet."

    ::= { dpConfigUDDISubscriptionEntry 2 }

--

dpConfigVLANInterfaceTable OBJECT-TYPE
    SYNTAX      SEQUENCE OF DPConfigVLANInterfaceEntry
    MAX-ACCESS  not-accessible
    STATUS      current
    DESCRIPTION
        "A VLAN interface allows multiple logical LANs to coexist on the same
        Ethernet segment. VLAN packets are identified by the IEEE 802.1Q protocol.
        You can define multiple VLAN interfaces on a single parent interface. The
        parent interface can be an Ethernet interface or a link aggregation
        interface."

    ::= { dpConfig 156 }

dpConfigVLANInterfaceEntry OBJECT-TYPE
    SYNTAX      DPConfigVLANInterfaceEntry
    MAX-ACCESS  not-accessible
    STATUS      current
    DESCRIPTION "Table row."
    INDEX { dpConfigVLANInterfaceIndex, IMPLIED dpConfigVLANInterfacename }

    ::= { dpConfigVLANInterfaceTable 1 }

DPConfigVLANInterfaceEntry ::= SEQUENCE {
    dpConfigVLANInterfaceIndex    Unsigned32,
    dpConfigVLANInterfacename    DisplayString
}

dpConfigVLANInterfaceIndex OBJECT-TYPE
    SYNTAX      Unsigned32
    MAX-ACCESS  read-only
    STATUS      current
    DESCRIPTION "No description yet."

    ::= { dpConfigVLANInterfaceEntry 1 }

dpConfigVLANInterfacename OBJECT-TYPE
    SYNTAX      DisplayString
    MAX-ACCESS  read-only
    STATUS      current
    DESCRIPTION "No description yet."

    ::= { dpConfigVLANInterfaceEntry 2 }

--

dpConfigConformancePolicyTable OBJECT-TYPE
    SYNTAX      SEQUENCE OF DPConfigConformancePolicyEntry
    MAX-ACCESS  not-accessible
    STATUS      current
    DESCRIPTION "Table."

    ::= { dpConfig 157 }

dpConfigConformancePolicyEntry OBJECT-TYPE
    SYNTAX      DPConfigConformancePolicyEntry
    MAX-ACCESS  not-accessible
    STATUS      current
    DESCRIPTION "Table row."
    INDEX { dpConfigConformancePolicyIndex, IMPLIED dpConfigConformancePolicyname }

    ::= { dpConfigConformancePolicyTable 1 }

DPConfigConformancePolicyEntry ::= SEQUENCE {
    dpConfigConformancePolicyIndex    Unsigned32,
    dpConfigConformancePolicyname    DisplayString
}

dpConfigConformancePolicyIndex OBJECT-TYPE
    SYNTAX      Unsigned32
    MAX-ACCESS  read-only
    STATUS      current
    DESCRIPTION "No description yet."

    ::= { dpConfigConformancePolicyEntry 1 }

dpConfigConformancePolicyname OBJECT-TYPE
    SYNTAX      DisplayString
    MAX-ACCESS  read-only
    STATUS      current
    DESCRIPTION "No description yet."

    ::= { dpConfigConformancePolicyEntry 2 }

--

dpConfigSOAPHeaderDispositionTable OBJECT-TYPE
    SYNTAX      SEQUENCE OF DPConfigSOAPHeaderDispositionEntry
    MAX-ACCESS  not-accessible
    STATUS      current
    DESCRIPTION
        "The list of instructions provided by customers to control how the SOAP
        headers and/or children elements are handled. This object is used by
        store:///soap-refine.xsl transform stylesheet."

    ::= { dpConfig 158 }

dpConfigSOAPHeaderDispositionEntry OBJECT-TYPE
    SYNTAX      DPConfigSOAPHeaderDispositionEntry
    MAX-ACCESS  not-accessible
    STATUS      current
    DESCRIPTION "Table row."
    INDEX { dpConfigSOAPHeaderDispositionIndex, IMPLIED dpConfigSOAPHeaderDispositionname }

    ::= { dpConfigSOAPHeaderDispositionTable 1 }

DPConfigSOAPHeaderDispositionEntry ::= SEQUENCE {
    dpConfigSOAPHeaderDispositionIndex    Unsigned32,
    dpConfigSOAPHeaderDispositionname    DisplayString
}

dpConfigSOAPHeaderDispositionIndex OBJECT-TYPE
    SYNTAX      Unsigned32
    MAX-ACCESS  read-only
    STATUS      current
    DESCRIPTION "No description yet."

    ::= { dpConfigSOAPHeaderDispositionEntry 1 }

dpConfigSOAPHeaderDispositionname OBJECT-TYPE
    SYNTAX      DisplayString
    MAX-ACCESS  read-only
    STATUS      current
    DESCRIPTION "No description yet."

    ::= { dpConfigSOAPHeaderDispositionEntry 2 }

--

dpConfigPolicyAttachmentsTable OBJECT-TYPE
    SYNTAX      SEQUENCE OF DPConfigPolicyAttachmentsEntry
    MAX-ACCESS  not-accessible
    STATUS      current
    DESCRIPTION
        "Create and configure ws-policy attachments for WSDLs"

    ::= { dpConfig 159 }

dpConfigPolicyAttachmentsEntry OBJECT-TYPE
    SYNTAX      DPConfigPolicyAttachmentsEntry
    MAX-ACCESS  not-accessible
    STATUS      current
    DESCRIPTION "Table row."
    INDEX { dpConfigPolicyAttachmentsIndex, IMPLIED dpConfigPolicyAttachmentsname }

    ::= { dpConfigPolicyAttachmentsTable 1 }

DPConfigPolicyAttachmentsEntry ::= SEQUENCE {
    dpConfigPolicyAttachmentsIndex    Unsigned32,
    dpConfigPolicyAttachmentsname    DisplayString
}

dpConfigPolicyAttachmentsIndex OBJECT-TYPE
    SYNTAX      Unsigned32
    MAX-ACCESS  read-only
    STATUS      current
    DESCRIPTION "No description yet."

    ::= { dpConfigPolicyAttachmentsEntry 1 }

dpConfigPolicyAttachmentsname OBJECT-TYPE
    SYNTAX      DisplayString
    MAX-ACCESS  read-only
    STATUS      current
    DESCRIPTION "No description yet."

    ::= { dpConfigPolicyAttachmentsEntry 2 }

--

dpConfigPolicyParametersTable OBJECT-TYPE
    SYNTAX      SEQUENCE OF DPConfigPolicyParametersEntry
    MAX-ACCESS  not-accessible
    STATUS      current
    DESCRIPTION
        "Configuration to persist the values of ws-policy parameters."

    ::= { dpConfig 160 }

dpConfigPolicyParametersEntry OBJECT-TYPE
    SYNTAX      DPConfigPolicyParametersEntry
    MAX-ACCESS  not-accessible
    STATUS      current
    DESCRIPTION "Table row."
    INDEX { dpConfigPolicyParametersIndex, IMPLIED dpConfigPolicyParametersname }

    ::= { dpConfigPolicyParametersTable 1 }

DPConfigPolicyParametersEntry ::= SEQUENCE {
    dpConfigPolicyParametersIndex    Unsigned32,
    dpConfigPolicyParametersname    DisplayString
}

dpConfigPolicyParametersIndex OBJECT-TYPE
    SYNTAX      Unsigned32
    MAX-ACCESS  read-only
    STATUS      current
    DESCRIPTION "No description yet."

    ::= { dpConfigPolicyParametersEntry 1 }

dpConfigPolicyParametersname OBJECT-TYPE
    SYNTAX      DisplayString
    MAX-ACCESS  read-only
    STATUS      current
    DESCRIPTION "No description yet."

    ::= { dpConfigPolicyParametersEntry 2 }

--

dpConfigIMSConnectTable OBJECT-TYPE
    SYNTAX      SEQUENCE OF DPConfigIMSConnectEntry
    MAX-ACCESS  not-accessible
    STATUS      current
    DESCRIPTION
        "IMS Connect properties. Properties on the Advanced tab are default values.
        Some of these properties can be overridden in the URL and others through
        header injection."

    ::= { dpConfig 161 }

dpConfigIMSConnectEntry OBJECT-TYPE
    SYNTAX      DPConfigIMSConnectEntry
    MAX-ACCESS  not-accessible
    STATUS      current
    DESCRIPTION "Table row."
    INDEX { dpConfigIMSConnectIndex, IMPLIED dpConfigIMSConnectname }

    ::= { dpConfigIMSConnectTable 1 }

DPConfigIMSConnectEntry ::= SEQUENCE {
    dpConfigIMSConnectIndex    Unsigned32,
    dpConfigIMSConnectname    DisplayString
}

dpConfigIMSConnectIndex OBJECT-TYPE
    SYNTAX      Unsigned32
    MAX-ACCESS  read-only
    STATUS      current
    DESCRIPTION "No description yet."

    ::= { dpConfigIMSConnectEntry 1 }

dpConfigIMSConnectname OBJECT-TYPE
    SYNTAX      DisplayString
    MAX-ACCESS  read-only
    STATUS      current
    DESCRIPTION "No description yet."

    ::= { dpConfigIMSConnectEntry 2 }

--

dpConfigIMSConnectSourceProtocolHandlerTable OBJECT-TYPE
    SYNTAX      SEQUENCE OF DPConfigIMSConnectSourceProtocolHandlerEntry
    MAX-ACCESS  not-accessible
    STATUS      current
    DESCRIPTION
        "An IMS Connect Handler object handles IMS protocol communications with
        DataPower services."

    ::= { dpConfig 162 }

dpConfigIMSConnectSourceProtocolHandlerEntry OBJECT-TYPE
    SYNTAX      DPConfigIMSConnectSourceProtocolHandlerEntry
    MAX-ACCESS  not-accessible
    STATUS      current
    DESCRIPTION "Table row."
    INDEX { dpConfigIMSConnectSourceProtocolHandlerIndex, IMPLIED dpConfigIMSConnectSourceProtocolHandlername }

    ::= { dpConfigIMSConnectSourceProtocolHandlerTable 1 }

DPConfigIMSConnectSourceProtocolHandlerEntry ::= SEQUENCE {
    dpConfigIMSConnectSourceProtocolHandlerIndex    Unsigned32,
    dpConfigIMSConnectSourceProtocolHandlername    DisplayString
}

dpConfigIMSConnectSourceProtocolHandlerIndex OBJECT-TYPE
    SYNTAX      Unsigned32
    MAX-ACCESS  read-only
    STATUS      current
    DESCRIPTION "No description yet."

    ::= { dpConfigIMSConnectSourceProtocolHandlerEntry 1 }

dpConfigIMSConnectSourceProtocolHandlername OBJECT-TYPE
    SYNTAX      DisplayString
    MAX-ACCESS  read-only
    STATUS      current
    DESCRIPTION "No description yet."

    ::= { dpConfigIMSConnectSourceProtocolHandlerEntry 2 }

--

dpConfigLDAPSearchParametersTable OBJECT-TYPE
    SYNTAX      SEQUENCE OF DPConfigLDAPSearchParametersEntry
    MAX-ACCESS  not-accessible
    STATUS      current
    DESCRIPTION
        "An LDAP Search Parameters object is a container for the parameters to use
        to perform an LDAP search operation. When used with authentication, the
        search retrieves the distinguished name (DN) for the user. When used with
        credential authorization mapping, the search retrieves the group name (DN
        or attribute value) based on the DN of the authenticated user."

    ::= { dpConfig 163 }

dpConfigLDAPSearchParametersEntry OBJECT-TYPE
    SYNTAX      DPConfigLDAPSearchParametersEntry
    MAX-ACCESS  not-accessible
    STATUS      current
    DESCRIPTION "Table row."
    INDEX { dpConfigLDAPSearchParametersIndex, IMPLIED dpConfigLDAPSearchParametersname }

    ::= { dpConfigLDAPSearchParametersTable 1 }

DPConfigLDAPSearchParametersEntry ::= SEQUENCE {
    dpConfigLDAPSearchParametersIndex    Unsigned32,
    dpConfigLDAPSearchParametersname    DisplayString
}

dpConfigLDAPSearchParametersIndex OBJECT-TYPE
    SYNTAX      Unsigned32
    MAX-ACCESS  read-only
    STATUS      current
    DESCRIPTION "No description yet."

    ::= { dpConfigLDAPSearchParametersEntry 1 }

dpConfigLDAPSearchParametersname OBJECT-TYPE
    SYNTAX      DisplayString
    MAX-ACCESS  read-only
    STATUS      current
    DESCRIPTION "No description yet."

    ::= { dpConfigLDAPSearchParametersEntry 2 }

--

dpConfigConfigDeploymentPolicyTable OBJECT-TYPE
    SYNTAX      SEQUENCE OF DPConfigConfigDeploymentPolicyEntry
    MAX-ACCESS  not-accessible
    STATUS      current
    DESCRIPTION
        "A deployment policy contains a set of rules that are applied during a
        configuration import. A deployment policy can be used to accept, filter,
        or modify configuration during import."

    ::= { dpConfig 164 }

dpConfigConfigDeploymentPolicyEntry OBJECT-TYPE
    SYNTAX      DPConfigConfigDeploymentPolicyEntry
    MAX-ACCESS  not-accessible
    STATUS      current
    DESCRIPTION "Table row."
    INDEX { dpConfigConfigDeploymentPolicyIndex, IMPLIED dpConfigConfigDeploymentPolicyname }

    ::= { dpConfigConfigDeploymentPolicyTable 1 }

DPConfigConfigDeploymentPolicyEntry ::= SEQUENCE {
    dpConfigConfigDeploymentPolicyIndex    Unsigned32,
    dpConfigConfigDeploymentPolicyname    DisplayString
}

dpConfigConfigDeploymentPolicyIndex OBJECT-TYPE
    SYNTAX      Unsigned32
    MAX-ACCESS  read-only
    STATUS      current
    DESCRIPTION "No description yet."

    ::= { dpConfigConfigDeploymentPolicyEntry 1 }

dpConfigConfigDeploymentPolicyname OBJECT-TYPE
    SYNTAX      DisplayString
    MAX-ACCESS  read-only
    STATUS      current
    DESCRIPTION "No description yet."

    ::= { dpConfigConfigDeploymentPolicyEntry 2 }

--

dpConfigCompactFlashTable OBJECT-TYPE
    SYNTAX      SEQUENCE OF DPConfigCompactFlashEntry
    MAX-ACCESS  not-accessible
    STATUS      current
    DESCRIPTION
        "The configuration of a compact flash storage card as auxiliary data
        storage."

    ::= { dpConfig 165 }

dpConfigCompactFlashEntry OBJECT-TYPE
    SYNTAX      DPConfigCompactFlashEntry
    MAX-ACCESS  not-accessible
    STATUS      current
    DESCRIPTION "Table row."
    INDEX { dpConfigCompactFlashIndex, IMPLIED dpConfigCompactFlashname }

    ::= { dpConfigCompactFlashTable 1 }

DPConfigCompactFlashEntry ::= SEQUENCE {
    dpConfigCompactFlashIndex    Unsigned32,
    dpConfigCompactFlashname    DisplayString
}

dpConfigCompactFlashIndex OBJECT-TYPE
    SYNTAX      Unsigned32
    MAX-ACCESS  read-only
    STATUS      current
    DESCRIPTION "No description yet."

    ::= { dpConfigCompactFlashEntry 1 }

dpConfigCompactFlashname OBJECT-TYPE
    SYNTAX      DisplayString
    MAX-ACCESS  read-only
    STATUS      current
    DESCRIPTION "No description yet."

    ::= { dpConfigCompactFlashEntry 2 }

--

dpConfigRaidVolumeTable OBJECT-TYPE
    SYNTAX      SEQUENCE OF DPConfigRaidVolumeEntry
    MAX-ACCESS  not-accessible
    STATUS      current
    DESCRIPTION
        "Configure a RAID volume for data storage. The RAID volume consists of two
        or more hard disk drives in a RAID configuration. The subdirectory
        specified is available in the local: and logstore: directories. Each
        domain contains these subdirectories, and they are not shared across
        domains. For access permission, the following behavior exists. For XB62
        appliances, this property is not available. On appliances with the B2B
        feature, access permission must be read/write. Although the appliance
        ignores this setting, read-only permission generates a warning. B2B
        storage requires write access to the RAID volume."

    ::= { dpConfig 166 }

dpConfigRaidVolumeEntry OBJECT-TYPE
    SYNTAX      DPConfigRaidVolumeEntry
    MAX-ACCESS  not-accessible
    STATUS      current
    DESCRIPTION "Table row."
    INDEX { dpConfigRaidVolumeIndex, IMPLIED dpConfigRaidVolumename }

    ::= { dpConfigRaidVolumeTable 1 }

DPConfigRaidVolumeEntry ::= SEQUENCE {
    dpConfigRaidVolumeIndex    Unsigned32,
    dpConfigRaidVolumename    DisplayString
}

dpConfigRaidVolumeIndex OBJECT-TYPE
    SYNTAX      Unsigned32
    MAX-ACCESS  read-only
    STATUS      current
    DESCRIPTION "No description yet."

    ::= { dpConfigRaidVolumeEntry 1 }

dpConfigRaidVolumename OBJECT-TYPE
    SYNTAX      DisplayString
    MAX-ACCESS  read-only
    STATUS      current
    DESCRIPTION "No description yet."

    ::= { dpConfigRaidVolumeEntry 2 }

--

dpConfigIScsiInitiatorConfigTable OBJECT-TYPE
    SYNTAX      SEQUENCE OF DPConfigIScsiInitiatorConfigEntry
    MAX-ACCESS  not-accessible
    STATUS      current
    DESCRIPTION
        "The iSCSI protocol is deprecated. The configuration of the iSCSI
        Initiator. The Initiator can only be modified if there are no active iSCSI
        targets."

    ::= { dpConfig 167 }

dpConfigIScsiInitiatorConfigEntry OBJECT-TYPE
    SYNTAX      DPConfigIScsiInitiatorConfigEntry
    MAX-ACCESS  not-accessible
    STATUS      current
    DESCRIPTION "Table row."
    INDEX { dpConfigIScsiInitiatorConfigIndex, IMPLIED dpConfigIScsiInitiatorConfigname }

    ::= { dpConfigIScsiInitiatorConfigTable 1 }

DPConfigIScsiInitiatorConfigEntry ::= SEQUENCE {
    dpConfigIScsiInitiatorConfigIndex    Unsigned32,
    dpConfigIScsiInitiatorConfigname    DisplayString
}

dpConfigIScsiInitiatorConfigIndex OBJECT-TYPE
    SYNTAX      Unsigned32
    MAX-ACCESS  read-only
    STATUS      current
    DESCRIPTION "No description yet."

    ::= { dpConfigIScsiInitiatorConfigEntry 1 }

dpConfigIScsiInitiatorConfigname OBJECT-TYPE
    SYNTAX      DisplayString
    MAX-ACCESS  read-only
    STATUS      current
    DESCRIPTION "No description yet."

    ::= { dpConfigIScsiInitiatorConfigEntry 2 }

--

dpConfigLLMSourceProtocolHandlerTable OBJECT-TYPE
    SYNTAX      SEQUENCE OF DPConfigLLMSourceProtocolHandlerEntry
    MAX-ACCESS  not-accessible
    STATUS      current
    DESCRIPTION
        "Use this panel to define an IBM MQ Low Latency Handler that can be
        attached to a Multi-Protocol Gateway as a front side protocol handler."

    ::= { dpConfig 168 }

dpConfigLLMSourceProtocolHandlerEntry OBJECT-TYPE
    SYNTAX      DPConfigLLMSourceProtocolHandlerEntry
    MAX-ACCESS  not-accessible
    STATUS      current
    DESCRIPTION "Table row."
    INDEX { dpConfigLLMSourceProtocolHandlerIndex, IMPLIED dpConfigLLMSourceProtocolHandlername }

    ::= { dpConfigLLMSourceProtocolHandlerTable 1 }

DPConfigLLMSourceProtocolHandlerEntry ::= SEQUENCE {
    dpConfigLLMSourceProtocolHandlerIndex    Unsigned32,
    dpConfigLLMSourceProtocolHandlername    DisplayString
}

dpConfigLLMSourceProtocolHandlerIndex OBJECT-TYPE
    SYNTAX      Unsigned32
    MAX-ACCESS  read-only
    STATUS      current
    DESCRIPTION "No description yet."

    ::= { dpConfigLLMSourceProtocolHandlerEntry 1 }

dpConfigLLMSourceProtocolHandlername OBJECT-TYPE
    SYNTAX      DisplayString
    MAX-ACCESS  read-only
    STATUS      current
    DESCRIPTION "No description yet."

    ::= { dpConfigLLMSourceProtocolHandlerEntry 2 }

--

dpConfigTRVSourceProtocolHandlerTable OBJECT-TYPE
    SYNTAX      SEQUENCE OF DPConfigTRVSourceProtocolHandlerEntry
    MAX-ACCESS  not-accessible
    STATUS      current
    DESCRIPTION
        "Use this panel to define a TIBCO RV Handler that can be attached to a
        Multi-Protocol Gateway as a front side protocol handler."

    ::= { dpConfig 169 }

dpConfigTRVSourceProtocolHandlerEntry OBJECT-TYPE
    SYNTAX      DPConfigTRVSourceProtocolHandlerEntry
    MAX-ACCESS  not-accessible
    STATUS      current
    DESCRIPTION "Table row."
    INDEX { dpConfigTRVSourceProtocolHandlerIndex, IMPLIED dpConfigTRVSourceProtocolHandlername }

    ::= { dpConfigTRVSourceProtocolHandlerTable 1 }

DPConfigTRVSourceProtocolHandlerEntry ::= SEQUENCE {
    dpConfigTRVSourceProtocolHandlerIndex    Unsigned32,
    dpConfigTRVSourceProtocolHandlername    DisplayString
}

dpConfigTRVSourceProtocolHandlerIndex OBJECT-TYPE
    SYNTAX      Unsigned32
    MAX-ACCESS  read-only
    STATUS      current
    DESCRIPTION "No description yet."

    ::= { dpConfigTRVSourceProtocolHandlerEntry 1 }

dpConfigTRVSourceProtocolHandlername OBJECT-TYPE
    SYNTAX      DisplayString
    MAX-ACCESS  read-only
    STATUS      current
    DESCRIPTION "No description yet."

    ::= { dpConfigTRVSourceProtocolHandlerEntry 2 }

--

dpConfigIScsiHBAConfigTable OBJECT-TYPE
    SYNTAX      SEQUENCE OF DPConfigIScsiHBAConfigEntry
    MAX-ACCESS  not-accessible
    STATUS      current
    DESCRIPTION
        "The iSCSI protocol is deprecated. The configuration of the iSCSI Host Bus
        Adapter (HBA). The iSCSI HBA is the hardware that is responsible for the
        management of iSCSI communications."

    ::= { dpConfig 170 }

dpConfigIScsiHBAConfigEntry OBJECT-TYPE
    SYNTAX      DPConfigIScsiHBAConfigEntry
    MAX-ACCESS  not-accessible
    STATUS      current
    DESCRIPTION "Table row."
    INDEX { dpConfigIScsiHBAConfigIndex, IMPLIED dpConfigIScsiHBAConfigname }

    ::= { dpConfigIScsiHBAConfigTable 1 }

DPConfigIScsiHBAConfigEntry ::= SEQUENCE {
    dpConfigIScsiHBAConfigIndex    Unsigned32,
    dpConfigIScsiHBAConfigname    DisplayString
}

dpConfigIScsiHBAConfigIndex OBJECT-TYPE
    SYNTAX      Unsigned32
    MAX-ACCESS  read-only
    STATUS      current
    DESCRIPTION "No description yet."

    ::= { dpConfigIScsiHBAConfigEntry 1 }

dpConfigIScsiHBAConfigname OBJECT-TYPE
    SYNTAX      DisplayString
    MAX-ACCESS  read-only
    STATUS      current
    DESCRIPTION "No description yet."

    ::= { dpConfigIScsiHBAConfigEntry 2 }

--

dpConfigIScsiTargetConfigTable OBJECT-TYPE
    SYNTAX      SEQUENCE OF DPConfigIScsiTargetConfigEntry
    MAX-ACCESS  not-accessible
    STATUS      current
    DESCRIPTION
        "The iSCSI protocol is deprecated. Defines the configuration of the
        connection instance to a remote iSCSI target."

    ::= { dpConfig 171 }

dpConfigIScsiTargetConfigEntry OBJECT-TYPE
    SYNTAX      DPConfigIScsiTargetConfigEntry
    MAX-ACCESS  not-accessible
    STATUS      current
    DESCRIPTION "Table row."
    INDEX { dpConfigIScsiTargetConfigIndex, IMPLIED dpConfigIScsiTargetConfigname }

    ::= { dpConfigIScsiTargetConfigTable 1 }

DPConfigIScsiTargetConfigEntry ::= SEQUENCE {
    dpConfigIScsiTargetConfigIndex    Unsigned32,
    dpConfigIScsiTargetConfigname    DisplayString
}

dpConfigIScsiTargetConfigIndex OBJECT-TYPE
    SYNTAX      Unsigned32
    MAX-ACCESS  read-only
    STATUS      current
    DESCRIPTION "No description yet."

    ::= { dpConfigIScsiTargetConfigEntry 1 }

dpConfigIScsiTargetConfigname OBJECT-TYPE
    SYNTAX      DisplayString
    MAX-ACCESS  read-only
    STATUS      current
    DESCRIPTION "No description yet."

    ::= { dpConfigIScsiTargetConfigEntry 2 }

--

dpConfigIScsiVolumeConfigTable OBJECT-TYPE
    SYNTAX      SEQUENCE OF DPConfigIScsiVolumeConfigEntry
    MAX-ACCESS  not-accessible
    STATUS      current
    DESCRIPTION
        "The iSCSI protocol is deprecated. File system operations for iSCSI
        devices."

    ::= { dpConfig 172 }

dpConfigIScsiVolumeConfigEntry OBJECT-TYPE
    SYNTAX      DPConfigIScsiVolumeConfigEntry
    MAX-ACCESS  not-accessible
    STATUS      current
    DESCRIPTION "Table row."
    INDEX { dpConfigIScsiVolumeConfigIndex, IMPLIED dpConfigIScsiVolumeConfigname }

    ::= { dpConfigIScsiVolumeConfigTable 1 }

DPConfigIScsiVolumeConfigEntry ::= SEQUENCE {
    dpConfigIScsiVolumeConfigIndex    Unsigned32,
    dpConfigIScsiVolumeConfigname    DisplayString
}

dpConfigIScsiVolumeConfigIndex OBJECT-TYPE
    SYNTAX      Unsigned32
    MAX-ACCESS  read-only
    STATUS      current
    DESCRIPTION "No description yet."

    ::= { dpConfigIScsiVolumeConfigEntry 1 }

dpConfigIScsiVolumeConfigname OBJECT-TYPE
    SYNTAX      DisplayString
    MAX-ACCESS  read-only
    STATUS      current
    DESCRIPTION "No description yet."

    ::= { dpConfigIScsiVolumeConfigEntry 2 }

--

dpConfigIScsiChapConfigTable OBJECT-TYPE
    SYNTAX      SEQUENCE OF DPConfigIScsiChapConfigEntry
    MAX-ACCESS  not-accessible
    STATUS      current
    DESCRIPTION
        "The iSCSI protocol is deprecated. The configuration of the Challenge
        Handshake Authentication Protocol (CHAP) for iSCSI targets."

    ::= { dpConfig 173 }

dpConfigIScsiChapConfigEntry OBJECT-TYPE
    SYNTAX      DPConfigIScsiChapConfigEntry
    MAX-ACCESS  not-accessible
    STATUS      current
    DESCRIPTION "Table row."
    INDEX { dpConfigIScsiChapConfigIndex, IMPLIED dpConfigIScsiChapConfigname }

    ::= { dpConfigIScsiChapConfigTable 1 }

DPConfigIScsiChapConfigEntry ::= SEQUENCE {
    dpConfigIScsiChapConfigIndex    Unsigned32,
    dpConfigIScsiChapConfigname    DisplayString
}

dpConfigIScsiChapConfigIndex OBJECT-TYPE
    SYNTAX      Unsigned32
    MAX-ACCESS  read-only
    STATUS      current
    DESCRIPTION "No description yet."

    ::= { dpConfigIScsiChapConfigEntry 1 }

dpConfigIScsiChapConfigname OBJECT-TYPE
    SYNTAX      DisplayString
    MAX-ACCESS  read-only
    STATUS      current
    DESCRIPTION "No description yet."

    ::= { dpConfigIScsiChapConfigEntry 2 }

--

dpConfigZosNSSClientTable OBJECT-TYPE
    SYNTAX      SEQUENCE OF DPConfigZosNSSClientEntry
    MAX-ACCESS  not-accessible
    STATUS      current
    DESCRIPTION
        "The z/OS NSS client object provides the parameters for authentication with
        SAF on a z/OS Communications Server."

    ::= { dpConfig 174 }

dpConfigZosNSSClientEntry OBJECT-TYPE
    SYNTAX      DPConfigZosNSSClientEntry
    MAX-ACCESS  not-accessible
    STATUS      current
    DESCRIPTION "Table row."
    INDEX { dpConfigZosNSSClientIndex, IMPLIED dpConfigZosNSSClientname }

    ::= { dpConfigZosNSSClientTable 1 }

DPConfigZosNSSClientEntry ::= SEQUENCE {
    dpConfigZosNSSClientIndex    Unsigned32,
    dpConfigZosNSSClientname    DisplayString
}

dpConfigZosNSSClientIndex OBJECT-TYPE
    SYNTAX      Unsigned32
    MAX-ACCESS  read-only
    STATUS      current
    DESCRIPTION "No description yet."

    ::= { dpConfigZosNSSClientEntry 1 }

dpConfigZosNSSClientname OBJECT-TYPE
    SYNTAX      DisplayString
    MAX-ACCESS  read-only
    STATUS      current
    DESCRIPTION "No description yet."

    ::= { dpConfigZosNSSClientEntry 2 }

--

dpConfigSSHServerSourceProtocolHandlerTable OBJECT-TYPE
    SYNTAX      SEQUENCE OF DPConfigSSHServerSourceProtocolHandlerEntry
    MAX-ACCESS  not-accessible
    STATUS      current
    DESCRIPTION
        "The SFTP Server Handler provides an SSH SFTP server that can be used to
        submit files for processing by the system. Each file that is written
        results in one transaction. There can be multiple SFTP servers, but only
        one server can be configured to listen on the default SSH port 22 on a
        given interface. There can be multiple simultaneous connections from SFTP
        clients to the same SFTP server. #b#Note:#/b# Changes in the configuration
        affect only new connections to this SFTP server. Existing connections
        continue to use their current configuration until they disconnect."

    ::= { dpConfig 175 }

dpConfigSSHServerSourceProtocolHandlerEntry OBJECT-TYPE
    SYNTAX      DPConfigSSHServerSourceProtocolHandlerEntry
    MAX-ACCESS  not-accessible
    STATUS      current
    DESCRIPTION "Table row."
    INDEX { dpConfigSSHServerSourceProtocolHandlerIndex, IMPLIED dpConfigSSHServerSourceProtocolHandlername }

    ::= { dpConfigSSHServerSourceProtocolHandlerTable 1 }

DPConfigSSHServerSourceProtocolHandlerEntry ::= SEQUENCE {
    dpConfigSSHServerSourceProtocolHandlerIndex    Unsigned32,
    dpConfigSSHServerSourceProtocolHandlername    DisplayString
}

dpConfigSSHServerSourceProtocolHandlerIndex OBJECT-TYPE
    SYNTAX      Unsigned32
    MAX-ACCESS  read-only
    STATUS      current
    DESCRIPTION "No description yet."

    ::= { dpConfigSSHServerSourceProtocolHandlerEntry 1 }

dpConfigSSHServerSourceProtocolHandlername OBJECT-TYPE
    SYNTAX      DisplayString
    MAX-ACCESS  read-only
    STATUS      current
    DESCRIPTION "No description yet."

    ::= { dpConfigSSHServerSourceProtocolHandlerEntry 2 }

--

dpConfigFTPDemonSourceProtocolHandlerTable OBJECT-TYPE
    SYNTAX      SEQUENCE OF DPConfigFTPDemonSourceProtocolHandlerEntry
    MAX-ACCESS  not-accessible
    STATUS      current
    DESCRIPTION "Table."

    ::= { dpConfig 176 }

dpConfigFTPDemonSourceProtocolHandlerEntry OBJECT-TYPE
    SYNTAX      DPConfigFTPDemonSourceProtocolHandlerEntry
    MAX-ACCESS  not-accessible
    STATUS      current
    DESCRIPTION "Table row."
    INDEX { dpConfigFTPDemonSourceProtocolHandlerIndex, IMPLIED dpConfigFTPDemonSourceProtocolHandlername }

    ::= { dpConfigFTPDemonSourceProtocolHandlerTable 1 }

DPConfigFTPDemonSourceProtocolHandlerEntry ::= SEQUENCE {
    dpConfigFTPDemonSourceProtocolHandlerIndex    Unsigned32,
    dpConfigFTPDemonSourceProtocolHandlername    DisplayString
}

dpConfigFTPDemonSourceProtocolHandlerIndex OBJECT-TYPE
    SYNTAX      Unsigned32
    MAX-ACCESS  read-only
    STATUS      current
    DESCRIPTION "No description yet."

    ::= { dpConfigFTPDemonSourceProtocolHandlerEntry 1 }

dpConfigFTPDemonSourceProtocolHandlername OBJECT-TYPE
    SYNTAX      DisplayString
    MAX-ACCESS  read-only
    STATUS      current
    DESCRIPTION "No description yet."

    ::= { dpConfigFTPDemonSourceProtocolHandlerEntry 2 }

--

dpConfigAS3SourceProtocolHandlerTable OBJECT-TYPE
    SYNTAX      SEQUENCE OF DPConfigAS3SourceProtocolHandlerEntry
    MAX-ACCESS  not-accessible
    STATUS      current
    DESCRIPTION
        "AS3 Handler"

    ::= { dpConfig 177 }

dpConfigAS3SourceProtocolHandlerEntry OBJECT-TYPE
    SYNTAX      DPConfigAS3SourceProtocolHandlerEntry
    MAX-ACCESS  not-accessible
    STATUS      current
    DESCRIPTION "Table row."
    INDEX { dpConfigAS3SourceProtocolHandlerIndex, IMPLIED dpConfigAS3SourceProtocolHandlername }

    ::= { dpConfigAS3SourceProtocolHandlerTable 1 }

DPConfigAS3SourceProtocolHandlerEntry ::= SEQUENCE {
    dpConfigAS3SourceProtocolHandlerIndex    Unsigned32,
    dpConfigAS3SourceProtocolHandlername    DisplayString
}

dpConfigAS3SourceProtocolHandlerIndex OBJECT-TYPE
    SYNTAX      Unsigned32
    MAX-ACCESS  read-only
    STATUS      current
    DESCRIPTION "No description yet."

    ::= { dpConfigAS3SourceProtocolHandlerEntry 1 }

dpConfigAS3SourceProtocolHandlername OBJECT-TYPE
    SYNTAX      DisplayString
    MAX-ACCESS  read-only
    STATUS      current
    DESCRIPTION "No description yet."

    ::= { dpConfigAS3SourceProtocolHandlerEntry 2 }

--

dpConfigAS2SourceProtocolHandlerTable OBJECT-TYPE
    SYNTAX      SEQUENCE OF DPConfigAS2SourceProtocolHandlerEntry
    MAX-ACCESS  not-accessible
    STATUS      current
    DESCRIPTION
        "The configuration for a front side HTTP protocol handler. This handler
        receives HTTP requests sent to the device and forwards them to the
        appropriate gateway. It conforms to gateway specifications of RFC 2616."

    ::= { dpConfig 178 }

dpConfigAS2SourceProtocolHandlerEntry OBJECT-TYPE
    SYNTAX      DPConfigAS2SourceProtocolHandlerEntry
    MAX-ACCESS  not-accessible
    STATUS      current
    DESCRIPTION "Table row."
    INDEX { dpConfigAS2SourceProtocolHandlerIndex, IMPLIED dpConfigAS2SourceProtocolHandlername }

    ::= { dpConfigAS2SourceProtocolHandlerTable 1 }

DPConfigAS2SourceProtocolHandlerEntry ::= SEQUENCE {
    dpConfigAS2SourceProtocolHandlerIndex    Unsigned32,
    dpConfigAS2SourceProtocolHandlername    DisplayString
}

dpConfigAS2SourceProtocolHandlerIndex OBJECT-TYPE
    SYNTAX      Unsigned32
    MAX-ACCESS  read-only
    STATUS      current
    DESCRIPTION "No description yet."

    ::= { dpConfigAS2SourceProtocolHandlerEntry 1 }

dpConfigAS2SourceProtocolHandlername OBJECT-TYPE
    SYNTAX      DisplayString
    MAX-ACCESS  read-only
    STATUS      current
    DESCRIPTION "No description yet."

    ::= { dpConfigAS2SourceProtocolHandlerEntry 2 }

--

dpConfigB2BXPathRoutingPolicyTable OBJECT-TYPE
    SYNTAX      SEQUENCE OF DPConfigB2BXPathRoutingPolicyEntry
    MAX-ACCESS  not-accessible
    STATUS      current
    DESCRIPTION "Table."

    ::= { dpConfig 179 }

dpConfigB2BXPathRoutingPolicyEntry OBJECT-TYPE
    SYNTAX      DPConfigB2BXPathRoutingPolicyEntry
    MAX-ACCESS  not-accessible
    STATUS      current
    DESCRIPTION "Table row."
    INDEX { dpConfigB2BXPathRoutingPolicyIndex, IMPLIED dpConfigB2BXPathRoutingPolicyname }

    ::= { dpConfigB2BXPathRoutingPolicyTable 1 }

DPConfigB2BXPathRoutingPolicyEntry ::= SEQUENCE {
    dpConfigB2BXPathRoutingPolicyIndex    Unsigned32,
    dpConfigB2BXPathRoutingPolicyname    DisplayString
}

dpConfigB2BXPathRoutingPolicyIndex OBJECT-TYPE
    SYNTAX      Unsigned32
    MAX-ACCESS  read-only
    STATUS      current
    DESCRIPTION "No description yet."

    ::= { dpConfigB2BXPathRoutingPolicyEntry 1 }

dpConfigB2BXPathRoutingPolicyname OBJECT-TYPE
    SYNTAX      DisplayString
    MAX-ACCESS  read-only
    STATUS      current
    DESCRIPTION "No description yet."

    ::= { dpConfigB2BXPathRoutingPolicyEntry 2 }

--

dpConfigLLMInstanceTable OBJECT-TYPE
    SYNTAX      SEQUENCE OF DPConfigLLMInstanceEntry
    MAX-ACCESS  not-accessible
    STATUS      current
    DESCRIPTION
        "An LLM Instance object defines all port resources used by the LLM service.
        The instance aggregates a combination of objects required to transmit and
        receive the following types of data streams: Multicast Reliable Multicast
        Messaging (RMM) Unicast Reliable User Datagram Protocol (RUDP) or Reliable
        Unicast Messaging (RUM) Tier Fail over data streams The LLM Instance can
        contain the following objects: LLM Multicast Receive LLM Multicast
        Transmit LLM Unicast LLM Multicast Tier Group"

    ::= { dpConfig 180 }

dpConfigLLMInstanceEntry OBJECT-TYPE
    SYNTAX      DPConfigLLMInstanceEntry
    MAX-ACCESS  not-accessible
    STATUS      current
    DESCRIPTION "Table row."
    INDEX { dpConfigLLMInstanceIndex, IMPLIED dpConfigLLMInstancename }

    ::= { dpConfigLLMInstanceTable 1 }

DPConfigLLMInstanceEntry ::= SEQUENCE {
    dpConfigLLMInstanceIndex    Unsigned32,
    dpConfigLLMInstancename    DisplayString
}

dpConfigLLMInstanceIndex OBJECT-TYPE
    SYNTAX      Unsigned32
    MAX-ACCESS  read-only
    STATUS      current
    DESCRIPTION "No description yet."

    ::= { dpConfigLLMInstanceEntry 1 }

dpConfigLLMInstancename OBJECT-TYPE
    SYNTAX      DisplayString
    MAX-ACCESS  read-only
    STATUS      current
    DESCRIPTION "No description yet."

    ::= { dpConfigLLMInstanceEntry 2 }

--

dpConfigLLMMulticastReceiveTable OBJECT-TYPE
    SYNTAX      SEQUENCE OF DPConfigLLMMulticastReceiveEntry
    MAX-ACCESS  not-accessible
    STATUS      current
    DESCRIPTION
        "Use this panel to define the properties of a Low Latency Messaging
        Multicast Receiver object. A receiver is part of a message delivery system
        that accepts messages from one or more LLM multicast transmitters. The
        source of the data would be either another DataPower system, or more
        likely a user application using IBM MQ Low Latency Messaging (LLM)."

    ::= { dpConfig 181 }

dpConfigLLMMulticastReceiveEntry OBJECT-TYPE
    SYNTAX      DPConfigLLMMulticastReceiveEntry
    MAX-ACCESS  not-accessible
    STATUS      current
    DESCRIPTION "Table row."
    INDEX { dpConfigLLMMulticastReceiveIndex, IMPLIED dpConfigLLMMulticastReceivename }

    ::= { dpConfigLLMMulticastReceiveTable 1 }

DPConfigLLMMulticastReceiveEntry ::= SEQUENCE {
    dpConfigLLMMulticastReceiveIndex    Unsigned32,
    dpConfigLLMMulticastReceivename    DisplayString
}

dpConfigLLMMulticastReceiveIndex OBJECT-TYPE
    SYNTAX      Unsigned32
    MAX-ACCESS  read-only
    STATUS      current
    DESCRIPTION "No description yet."

    ::= { dpConfigLLMMulticastReceiveEntry 1 }

dpConfigLLMMulticastReceivename OBJECT-TYPE
    SYNTAX      DisplayString
    MAX-ACCESS  read-only
    STATUS      current
    DESCRIPTION "No description yet."

    ::= { dpConfigLLMMulticastReceiveEntry 2 }

--

dpConfigLLMMulticastTransmitTable OBJECT-TYPE
    SYNTAX      SEQUENCE OF DPConfigLLMMulticastTransmitEntry
    MAX-ACCESS  not-accessible
    STATUS      current
    DESCRIPTION
        "Use this panel to define the properties of a Low Latency Messaging
        Multicast Transmit object. A transmitter is part of a message delivery
        system that sends messages to one or more receivers. The transmitter
        supports the following types of data transmissions: one-to-one,
        one-to-many, and many-to-many."

    ::= { dpConfig 182 }

dpConfigLLMMulticastTransmitEntry OBJECT-TYPE
    SYNTAX      DPConfigLLMMulticastTransmitEntry
    MAX-ACCESS  not-accessible
    STATUS      current
    DESCRIPTION "Table row."
    INDEX { dpConfigLLMMulticastTransmitIndex, IMPLIED dpConfigLLMMulticastTransmitname }

    ::= { dpConfigLLMMulticastTransmitTable 1 }

DPConfigLLMMulticastTransmitEntry ::= SEQUENCE {
    dpConfigLLMMulticastTransmitIndex    Unsigned32,
    dpConfigLLMMulticastTransmitname    DisplayString
}

dpConfigLLMMulticastTransmitIndex OBJECT-TYPE
    SYNTAX      Unsigned32
    MAX-ACCESS  read-only
    STATUS      current
    DESCRIPTION "No description yet."

    ::= { dpConfigLLMMulticastTransmitEntry 1 }

dpConfigLLMMulticastTransmitname OBJECT-TYPE
    SYNTAX      DisplayString
    MAX-ACCESS  read-only
    STATUS      current
    DESCRIPTION "No description yet."

    ::= { dpConfigLLMMulticastTransmitEntry 2 }

--

dpConfigLLMUnicastTable OBJECT-TYPE
    SYNTAX      SEQUENCE OF DPConfigLLMUnicastEntry
    MAX-ACCESS  not-accessible
    STATUS      current
    DESCRIPTION
        "Use this panel to define the properties of a Low Latency Messaging Unicast
        object. It will contain both the receive and transmit configurations for
        an LLM connection over TCP."

    ::= { dpConfig 183 }

dpConfigLLMUnicastEntry OBJECT-TYPE
    SYNTAX      DPConfigLLMUnicastEntry
    MAX-ACCESS  not-accessible
    STATUS      current
    DESCRIPTION "Table row."
    INDEX { dpConfigLLMUnicastIndex, IMPLIED dpConfigLLMUnicastname }

    ::= { dpConfigLLMUnicastTable 1 }

DPConfigLLMUnicastEntry ::= SEQUENCE {
    dpConfigLLMUnicastIndex    Unsigned32,
    dpConfigLLMUnicastname    DisplayString
}

dpConfigLLMUnicastIndex OBJECT-TYPE
    SYNTAX      Unsigned32
    MAX-ACCESS  read-only
    STATUS      current
    DESCRIPTION "No description yet."

    ::= { dpConfigLLMUnicastEntry 1 }

dpConfigLLMUnicastname OBJECT-TYPE
    SYNTAX      DisplayString
    MAX-ACCESS  read-only
    STATUS      current
    DESCRIPTION "No description yet."

    ::= { dpConfigLLMUnicastEntry 2 }

--

dpConfigLLMMulticastTierGroupTable OBJECT-TYPE
    SYNTAX      SEQUENCE OF DPConfigLLMMulticastTierGroupEntry
    MAX-ACCESS  not-accessible
    STATUS      current
    DESCRIPTION
        "The LLM Multicast Tier Group identifies a configuration that combines a
        group of two or more machines called tier members into a tier failover
        group for stream-based Reliable and Consistent Message Streaming (RCMS). A
        tier consists of a group of application components in a configuration
        where each component is an identical replica. Each replica executes the
        application logic as if it was the only component. RCMS, by synchronizing
        inbound and outbound traffic for each tier member, ensures that the
        application remains available in the case of a failure. As a result, any
        new tier component can start fully functioning in parallel with its
        existing running peers, and support them in case of failure. RCMS is a
        part of LLM that provides high availability and consistent, ordered
        message delivery. It supports the following features: Failure detection
        and failover Total ordering State synchronization Component group
        management RCMS is based on a component replication model where all
        members of a tier group perform the following actions: Receive the same
        input Perform same processing Produce the same output RCMS enhances the
        high availability capabilities of RMM by ensuring that all instances of
        the application get exactly the same input and can therefore maintain
        identical state. For receiver tier topics this means that in all tier
        members all the tier receiver topics deliver exactly the same set of
        messages to the application. If the tier enforces total order, then all
        the messages from all topics are delivered in exactly the same order.
        Multiple instances of the application run simultaneously. If one of the
        instances of the application fails, RCMS detects the failure and
        automatically takes corrective actions (for example, to replace an
        instance that failed). Stream failover allows receivers to switch from one
        transmitter stream to another with little or no message loss when a
        transmitter fails. Both RMM and RUM support stream failover. RCMS
        implements basic stream failover by coordinating transmitters and
        synchronizing application state and message sequence numbers."

    ::= { dpConfig 184 }

dpConfigLLMMulticastTierGroupEntry OBJECT-TYPE
    SYNTAX      DPConfigLLMMulticastTierGroupEntry
    MAX-ACCESS  not-accessible
    STATUS      current
    DESCRIPTION "Table row."
    INDEX { dpConfigLLMMulticastTierGroupIndex, IMPLIED dpConfigLLMMulticastTierGroupname }

    ::= { dpConfigLLMMulticastTierGroupTable 1 }

DPConfigLLMMulticastTierGroupEntry ::= SEQUENCE {
    dpConfigLLMMulticastTierGroupIndex    Unsigned32,
    dpConfigLLMMulticastTierGroupname    DisplayString
}

dpConfigLLMMulticastTierGroupIndex OBJECT-TYPE
    SYNTAX      Unsigned32
    MAX-ACCESS  read-only
    STATUS      current
    DESCRIPTION "No description yet."

    ::= { dpConfigLLMMulticastTierGroupEntry 1 }

dpConfigLLMMulticastTierGroupname OBJECT-TYPE
    SYNTAX      DisplayString
    MAX-ACCESS  read-only
    STATUS      current
    DESCRIPTION "No description yet."

    ::= { dpConfigLLMMulticastTierGroupEntry 2 }

--

dpConfigLLMRouteTable OBJECT-TYPE
    SYNTAX      SEQUENCE OF DPConfigLLMRouteEntry
    MAX-ACCESS  not-accessible
    STATUS      current
    DESCRIPTION
        "The Route object configures the transmission characteristics for outbound
        messages. Each route object creates a logical outbound stream. An LLM
        policy can define multiple routes on which to send outbound messages. The
        routes also use Message Selection rules to filter outbound messages. Once
        a message is selected for routing, you configure a Topic Name that
        describes where to route the message. The route also provides a property
        mapping rule that controls the propagation of properties from inbound to
        outbound messages. The Copy Message Properties toggle, when enabled,
        automatically copies all inbound message properties to output properties.
        A property map allows you to change or suppress the propagation of
        properties. The TurboFlow label and/or bitmap are always copied from input
        to output independently of the copy properties setting."

    ::= { dpConfig 186 }

dpConfigLLMRouteEntry OBJECT-TYPE
    SYNTAX      DPConfigLLMRouteEntry
    MAX-ACCESS  not-accessible
    STATUS      current
    DESCRIPTION "Table row."
    INDEX { dpConfigLLMRouteIndex, IMPLIED dpConfigLLMRoutename }

    ::= { dpConfigLLMRouteTable 1 }

DPConfigLLMRouteEntry ::= SEQUENCE {
    dpConfigLLMRouteIndex    Unsigned32,
    dpConfigLLMRoutename    DisplayString
}

dpConfigLLMRouteIndex OBJECT-TYPE
    SYNTAX      Unsigned32
    MAX-ACCESS  read-only
    STATUS      current
    DESCRIPTION "No description yet."

    ::= { dpConfigLLMRouteEntry 1 }

dpConfigLLMRoutename OBJECT-TYPE
    SYNTAX      DisplayString
    MAX-ACCESS  read-only
    STATUS      current
    DESCRIPTION "No description yet."

    ::= { dpConfigLLMRouteEntry 2 }

--

dpConfigLLMPolicyTable OBJECT-TYPE
    SYNTAX      SEQUENCE OF DPConfigLLMPolicyEntry
    MAX-ACCESS  not-accessible
    STATUS      current
    DESCRIPTION
        "An LLM Policy provides the means for receiving LLM data streams. Receiving
        resources are defined in the LLM Multicast Receive object or LLM Unicast
        object associated with the LLM Instance assigned to a policy. A policy can
        contain one or more LLM routes that define outbound destinations for
        received messages. Rules for topic and message selection can be built
        using SQL-92 like expressions that use LLM properties, variables, and
        fields. You can receive messages over multiple topics and reject data
        streams from particular sources. A policy functions as a gateway for
        routing messages rapidly through the appliance or as a bridge to DataPower
        service policies."

    ::= { dpConfig 187 }

dpConfigLLMPolicyEntry OBJECT-TYPE
    SYNTAX      DPConfigLLMPolicyEntry
    MAX-ACCESS  not-accessible
    STATUS      current
    DESCRIPTION "Table row."
    INDEX { dpConfigLLMPolicyIndex, IMPLIED dpConfigLLMPolicyname }

    ::= { dpConfigLLMPolicyTable 1 }

DPConfigLLMPolicyEntry ::= SEQUENCE {
    dpConfigLLMPolicyIndex    Unsigned32,
    dpConfigLLMPolicyname    DisplayString
}

dpConfigLLMPolicyIndex OBJECT-TYPE
    SYNTAX      Unsigned32
    MAX-ACCESS  read-only
    STATUS      current
    DESCRIPTION "No description yet."

    ::= { dpConfigLLMPolicyEntry 1 }

dpConfigLLMPolicyname OBJECT-TYPE
    SYNTAX      DisplayString
    MAX-ACCESS  read-only
    STATUS      current
    DESCRIPTION "No description yet."

    ::= { dpConfigLLMPolicyEntry 2 }

--

dpConfigFibreChannelHBATable OBJECT-TYPE
    SYNTAX      SEQUENCE OF DPConfigFibreChannelHBAEntry
    MAX-ACCESS  not-accessible
    STATUS      current
    DESCRIPTION
        "The configuration of the Fibre Channel Host Bus Adapter (HBA). The Fibre
        Channel HBA is the hardware that is responsible for the management of
        Fibre Channel communications."

    ::= { dpConfig 188 }

dpConfigFibreChannelHBAEntry OBJECT-TYPE
    SYNTAX      DPConfigFibreChannelHBAEntry
    MAX-ACCESS  not-accessible
    STATUS      current
    DESCRIPTION "Table row."
    INDEX { dpConfigFibreChannelHBAIndex, IMPLIED dpConfigFibreChannelHBAname }

    ::= { dpConfigFibreChannelHBATable 1 }

DPConfigFibreChannelHBAEntry ::= SEQUENCE {
    dpConfigFibreChannelHBAIndex    Unsigned32,
    dpConfigFibreChannelHBAname    DisplayString
}

dpConfigFibreChannelHBAIndex OBJECT-TYPE
    SYNTAX      Unsigned32
    MAX-ACCESS  read-only
    STATUS      current
    DESCRIPTION "No description yet."

    ::= { dpConfigFibreChannelHBAEntry 1 }

dpConfigFibreChannelHBAname OBJECT-TYPE
    SYNTAX      DisplayString
    MAX-ACCESS  read-only
    STATUS      current
    DESCRIPTION "No description yet."

    ::= { dpConfigFibreChannelHBAEntry 2 }

--

dpConfigFibreChannelTargetTable OBJECT-TYPE
    SYNTAX      SEQUENCE OF DPConfigFibreChannelTargetEntry
    MAX-ACCESS  not-accessible
    STATUS      current
    DESCRIPTION
        "Defines the configuration of the connection instance to a remote Fibre
        Channel target."

    ::= { dpConfig 189 }

dpConfigFibreChannelTargetEntry OBJECT-TYPE
    SYNTAX      DPConfigFibreChannelTargetEntry
    MAX-ACCESS  not-accessible
    STATUS      current
    DESCRIPTION "Table row."
    INDEX { dpConfigFibreChannelTargetIndex, IMPLIED dpConfigFibreChannelTargetname }

    ::= { dpConfigFibreChannelTargetTable 1 }

DPConfigFibreChannelTargetEntry ::= SEQUENCE {
    dpConfigFibreChannelTargetIndex    Unsigned32,
    dpConfigFibreChannelTargetname    DisplayString
}

dpConfigFibreChannelTargetIndex OBJECT-TYPE
    SYNTAX      Unsigned32
    MAX-ACCESS  read-only
    STATUS      current
    DESCRIPTION "No description yet."

    ::= { dpConfigFibreChannelTargetEntry 1 }

dpConfigFibreChannelTargetname OBJECT-TYPE
    SYNTAX      DisplayString
    MAX-ACCESS  read-only
    STATUS      current
    DESCRIPTION "No description yet."

    ::= { dpConfigFibreChannelTargetEntry 2 }

--

dpConfigFibreChannelVolumeTable OBJECT-TYPE
    SYNTAX      SEQUENCE OF DPConfigFibreChannelVolumeEntry
    MAX-ACCESS  not-accessible
    STATUS      current
    DESCRIPTION
        "File system operations for Fibre Channel devices. When the volume's
        operational state changes from up to down, existing transactions using the
        volume will attempt to complete prior to the volume becoming inaccessible."

    ::= { dpConfig 190 }

dpConfigFibreChannelVolumeEntry OBJECT-TYPE
    SYNTAX      DPConfigFibreChannelVolumeEntry
    MAX-ACCESS  not-accessible
    STATUS      current
    DESCRIPTION "Table row."
    INDEX { dpConfigFibreChannelVolumeIndex, IMPLIED dpConfigFibreChannelVolumename }

    ::= { dpConfigFibreChannelVolumeTable 1 }

DPConfigFibreChannelVolumeEntry ::= SEQUENCE {
    dpConfigFibreChannelVolumeIndex    Unsigned32,
    dpConfigFibreChannelVolumename    DisplayString
}

dpConfigFibreChannelVolumeIndex OBJECT-TYPE
    SYNTAX      Unsigned32
    MAX-ACCESS  read-only
    STATUS      current
    DESCRIPTION "No description yet."

    ::= { dpConfigFibreChannelVolumeEntry 1 }

dpConfigFibreChannelVolumename OBJECT-TYPE
    SYNTAX      DisplayString
    MAX-ACCESS  read-only
    STATUS      current
    DESCRIPTION "No description yet."

    ::= { dpConfigFibreChannelVolumeEntry 2 }

--

dpConfigWebB2BViewerTable OBJECT-TYPE
    SYNTAX      SEQUENCE OF DPConfigWebB2BViewerEntry
    MAX-ACCESS  not-accessible
    STATUS      current
    DESCRIPTION
        "Configure the web B2B Viewer Management interface."

    ::= { dpConfig 192 }

dpConfigWebB2BViewerEntry OBJECT-TYPE
    SYNTAX      DPConfigWebB2BViewerEntry
    MAX-ACCESS  not-accessible
    STATUS      current
    DESCRIPTION "Table row."
    INDEX { dpConfigWebB2BViewerIndex, IMPLIED dpConfigWebB2BViewername }

    ::= { dpConfigWebB2BViewerTable 1 }

DPConfigWebB2BViewerEntry ::= SEQUENCE {
    dpConfigWebB2BViewerIndex    Unsigned32,
    dpConfigWebB2BViewername    DisplayString
}

dpConfigWebB2BViewerIndex OBJECT-TYPE
    SYNTAX      Unsigned32
    MAX-ACCESS  read-only
    STATUS      current
    DESCRIPTION "No description yet."

    ::= { dpConfigWebB2BViewerEntry 1 }

dpConfigWebB2BViewername OBJECT-TYPE
    SYNTAX      DisplayString
    MAX-ACCESS  read-only
    STATUS      current
    DESCRIPTION "No description yet."

    ::= { dpConfigWebB2BViewerEntry 2 }

--

dpConfigB2BPersistenceTable OBJECT-TYPE
    SYNTAX      SEQUENCE OF DPConfigB2BPersistenceEntry
    MAX-ACCESS  not-accessible
    STATUS      current
    DESCRIPTION
        "Data storage for B2B transaction data"

    ::= { dpConfig 193 }

dpConfigB2BPersistenceEntry OBJECT-TYPE
    SYNTAX      DPConfigB2BPersistenceEntry
    MAX-ACCESS  not-accessible
    STATUS      current
    DESCRIPTION "Table row."
    INDEX { dpConfigB2BPersistenceIndex, IMPLIED dpConfigB2BPersistencename }

    ::= { dpConfigB2BPersistenceTable 1 }

DPConfigB2BPersistenceEntry ::= SEQUENCE {
    dpConfigB2BPersistenceIndex    Unsigned32,
    dpConfigB2BPersistencename    DisplayString
}

dpConfigB2BPersistenceIndex OBJECT-TYPE
    SYNTAX      Unsigned32
    MAX-ACCESS  read-only
    STATUS      current
    DESCRIPTION "No description yet."

    ::= { dpConfigB2BPersistenceEntry 1 }

dpConfigB2BPersistencename OBJECT-TYPE
    SYNTAX      DisplayString
    MAX-ACCESS  read-only
    STATUS      current
    DESCRIPTION "No description yet."

    ::= { dpConfigB2BPersistenceEntry 2 }

--

dpConfigB2BProfileGroupTable OBJECT-TYPE
    SYNTAX      SEQUENCE OF DPConfigB2BProfileGroupEntry
    MAX-ACCESS  not-accessible
    STATUS      current
    DESCRIPTION
        "A group of B2B Partner Profile objects that can be enable or disable at
        the same time. Each partner profile in the group is identified by its name
        and optional destination. Without a destination, the configuration uses
        the first destination for the partner profile."

    ::= { dpConfig 194 }

dpConfigB2BProfileGroupEntry OBJECT-TYPE
    SYNTAX      DPConfigB2BProfileGroupEntry
    MAX-ACCESS  not-accessible
    STATUS      current
    DESCRIPTION "Table row."
    INDEX { dpConfigB2BProfileGroupIndex, IMPLIED dpConfigB2BProfileGroupname }

    ::= { dpConfigB2BProfileGroupTable 1 }

DPConfigB2BProfileGroupEntry ::= SEQUENCE {
    dpConfigB2BProfileGroupIndex    Unsigned32,
    dpConfigB2BProfileGroupname    DisplayString
}

dpConfigB2BProfileGroupIndex OBJECT-TYPE
    SYNTAX      Unsigned32
    MAX-ACCESS  read-only
    STATUS      current
    DESCRIPTION "No description yet."

    ::= { dpConfigB2BProfileGroupEntry 1 }

dpConfigB2BProfileGroupname OBJECT-TYPE
    SYNTAX      DisplayString
    MAX-ACCESS  read-only
    STATUS      current
    DESCRIPTION "No description yet."

    ::= { dpConfigB2BProfileGroupEntry 2 }

--

dpConfigB2BGatewayTable OBJECT-TYPE
    SYNTAX      SEQUENCE OF DPConfigB2BGatewayEntry
    MAX-ACCESS  not-accessible
    STATUS      current
    DESCRIPTION
        "The configuration for a B2B gateway instance. A B2B gateway can handle B2B
        messages transmitted over a variety of AS and non-AS protocols for inbound
        and outbound flows, as well as MDN messages."

    ::= { dpConfig 195 }

dpConfigB2BGatewayEntry OBJECT-TYPE
    SYNTAX      DPConfigB2BGatewayEntry
    MAX-ACCESS  not-accessible
    STATUS      current
    DESCRIPTION "Table row."
    INDEX { dpConfigB2BGatewayIndex, IMPLIED dpConfigB2BGatewayname }

    ::= { dpConfigB2BGatewayTable 1 }

DPConfigB2BGatewayEntry ::= SEQUENCE {
    dpConfigB2BGatewayIndex    Unsigned32,
    dpConfigB2BGatewayname    DisplayString
}

dpConfigB2BGatewayIndex OBJECT-TYPE
    SYNTAX      Unsigned32
    MAX-ACCESS  read-only
    STATUS      current
    DESCRIPTION "No description yet."

    ::= { dpConfigB2BGatewayEntry 1 }

dpConfigB2BGatewayname OBJECT-TYPE
    SYNTAX      DisplayString
    MAX-ACCESS  read-only
    STATUS      current
    DESCRIPTION "No description yet."

    ::= { dpConfigB2BGatewayEntry 2 }

--

dpConfigB2BProfileTable OBJECT-TYPE
    SYNTAX      SEQUENCE OF DPConfigB2BProfileEntry
    MAX-ACCESS  not-accessible
    STATUS      current
    DESCRIPTION "Table."

    ::= { dpConfig 196 }

dpConfigB2BProfileEntry OBJECT-TYPE
    SYNTAX      DPConfigB2BProfileEntry
    MAX-ACCESS  not-accessible
    STATUS      current
    DESCRIPTION "Table row."
    INDEX { dpConfigB2BProfileIndex, IMPLIED dpConfigB2BProfilename }

    ::= { dpConfigB2BProfileTable 1 }

DPConfigB2BProfileEntry ::= SEQUENCE {
    dpConfigB2BProfileIndex    Unsigned32,
    dpConfigB2BProfilename    DisplayString
}

dpConfigB2BProfileIndex OBJECT-TYPE
    SYNTAX      Unsigned32
    MAX-ACCESS  read-only
    STATUS      current
    DESCRIPTION "No description yet."

    ::= { dpConfigB2BProfileEntry 1 }

dpConfigB2BProfilename OBJECT-TYPE
    SYNTAX      DisplayString
    MAX-ACCESS  read-only
    STATUS      current
    DESCRIPTION "No description yet."

    ::= { dpConfigB2BProfileEntry 2 }

--

dpConfigWCCServiceTable OBJECT-TYPE
    SYNTAX      SEQUENCE OF DPConfigWCCServiceEntry
    MAX-ACCESS  not-accessible
    STATUS      current
    DESCRIPTION
        "Use the WebSphere Cell configuration to retrieve configuration information
        and runtime information from a Network Deployment or Virtual Enterprise
        product. Load balancer groups use this information to automate
        configuration and updates."

    ::= { dpConfig 197 }

dpConfigWCCServiceEntry OBJECT-TYPE
    SYNTAX      DPConfigWCCServiceEntry
    MAX-ACCESS  not-accessible
    STATUS      current
    DESCRIPTION "Table row."
    INDEX { dpConfigWCCServiceIndex, IMPLIED dpConfigWCCServicename }

    ::= { dpConfigWCCServiceTable 1 }

DPConfigWCCServiceEntry ::= SEQUENCE {
    dpConfigWCCServiceIndex    Unsigned32,
    dpConfigWCCServicename    DisplayString
}

dpConfigWCCServiceIndex OBJECT-TYPE
    SYNTAX      Unsigned32
    MAX-ACCESS  read-only
    STATUS      current
    DESCRIPTION "No description yet."

    ::= { dpConfigWCCServiceEntry 1 }

dpConfigWCCServicename OBJECT-TYPE
    SYNTAX      DisplayString
    MAX-ACCESS  read-only
    STATUS      current
    DESCRIPTION "No description yet."

    ::= { dpConfigWCCServiceEntry 2 }

--

dpConfigFormsLoginPolicyTable OBJECT-TYPE
    SYNTAX      SEQUENCE OF DPConfigFormsLoginPolicyEntry
    MAX-ACCESS  not-accessible
    STATUS      current
    DESCRIPTION
        "The HTML forms login policy defines the details for collecting user
        authentication information."

    ::= { dpConfig 198 }

dpConfigFormsLoginPolicyEntry OBJECT-TYPE
    SYNTAX      DPConfigFormsLoginPolicyEntry
    MAX-ACCESS  not-accessible
    STATUS      current
    DESCRIPTION "Table row."
    INDEX { dpConfigFormsLoginPolicyIndex, IMPLIED dpConfigFormsLoginPolicyname }

    ::= { dpConfigFormsLoginPolicyTable 1 }

DPConfigFormsLoginPolicyEntry ::= SEQUENCE {
    dpConfigFormsLoginPolicyIndex    Unsigned32,
    dpConfigFormsLoginPolicyname    DisplayString
}

dpConfigFormsLoginPolicyIndex OBJECT-TYPE
    SYNTAX      Unsigned32
    MAX-ACCESS  read-only
    STATUS      current
    DESCRIPTION "No description yet."

    ::= { dpConfigFormsLoginPolicyEntry 1 }

dpConfigFormsLoginPolicyname OBJECT-TYPE
    SYNTAX      DisplayString
    MAX-ACCESS  read-only
    STATUS      current
    DESCRIPTION "No description yet."

    ::= { dpConfigFormsLoginPolicyEntry 2 }

--

dpConfigTRVPolicyTable OBJECT-TYPE
    SYNTAX      SEQUENCE OF DPConfigTRVPolicyEntry
    MAX-ACCESS  not-accessible
    STATUS      current
    DESCRIPTION
        "A TIBCO RV Policy provides the means for receiving TIBCO RV data streams.
        Receiving resources are defined in the TIBCO RV Policy object. A policy
        can contain one or more TIBCO RV routes that define outbound destinations
        for received messages. Rules for subject and message selection can be
        built using SQL-92 like expressions that use TICBO RV properties,
        variables, and fields. You can receive messages over multiple subjects and
        reject data streams from particular sources. A policy functions as a
        gateway for routing messages rapidly through the appliance or as a bridge
        to DataPower service policies."

    ::= { dpConfig 199 }

dpConfigTRVPolicyEntry OBJECT-TYPE
    SYNTAX      DPConfigTRVPolicyEntry
    MAX-ACCESS  not-accessible
    STATUS      current
    DESCRIPTION "Table row."
    INDEX { dpConfigTRVPolicyIndex, IMPLIED dpConfigTRVPolicyname }

    ::= { dpConfigTRVPolicyTable 1 }

DPConfigTRVPolicyEntry ::= SEQUENCE {
    dpConfigTRVPolicyIndex    Unsigned32,
    dpConfigTRVPolicyname    DisplayString
}

dpConfigTRVPolicyIndex OBJECT-TYPE
    SYNTAX      Unsigned32
    MAX-ACCESS  read-only
    STATUS      current
    DESCRIPTION "No description yet."

    ::= { dpConfigTRVPolicyEntry 1 }

dpConfigTRVPolicyname OBJECT-TYPE
    SYNTAX      DisplayString
    MAX-ACCESS  read-only
    STATUS      current
    DESCRIPTION "No description yet."

    ::= { dpConfigTRVPolicyEntry 2 }

--

dpConfigTRVRouteTable OBJECT-TYPE
    SYNTAX      SEQUENCE OF DPConfigTRVRouteEntry
    MAX-ACCESS  not-accessible
    STATUS      current
    DESCRIPTION
        "The Route object configures the transmission characteristics for outbound
        TIBCO RV messages. Each route object creates a logical outbound stream. A
        TIBCO RV policy can define multiple routes on which to send outbound
        messages. The routes also use Message Selection rules to filter outbound
        messages. Once a message is selected for routing, you configure a Subject
        Name that describes where to route the message."

    ::= { dpConfig 200 }

dpConfigTRVRouteEntry OBJECT-TYPE
    SYNTAX      DPConfigTRVRouteEntry
    MAX-ACCESS  not-accessible
    STATUS      current
    DESCRIPTION "Table row."
    INDEX { dpConfigTRVRouteIndex, IMPLIED dpConfigTRVRoutename }

    ::= { dpConfigTRVRouteTable 1 }

DPConfigTRVRouteEntry ::= SEQUENCE {
    dpConfigTRVRouteIndex    Unsigned32,
    dpConfigTRVRoutename    DisplayString
}

dpConfigTRVRouteIndex OBJECT-TYPE
    SYNTAX      Unsigned32
    MAX-ACCESS  read-only
    STATUS      current
    DESCRIPTION "No description yet."

    ::= { dpConfigTRVRouteEntry 1 }

dpConfigTRVRoutename OBJECT-TYPE
    SYNTAX      DisplayString
    MAX-ACCESS  read-only
    STATUS      current
    DESCRIPTION "No description yet."

    ::= { dpConfigTRVRouteEntry 2 }

--

dpConfigTRVTransportTable OBJECT-TYPE
    SYNTAX      SEQUENCE OF DPConfigTRVTransportEntry
    MAX-ACCESS  not-accessible
    STATUS      current
    DESCRIPTION
        "A TIBCO RV Transport object is a container for TIBCO RV transport
        configuration properties."

    ::= { dpConfig 201 }

dpConfigTRVTransportEntry OBJECT-TYPE
    SYNTAX      DPConfigTRVTransportEntry
    MAX-ACCESS  not-accessible
    STATUS      current
    DESCRIPTION "Table row."
    INDEX { dpConfigTRVTransportIndex, IMPLIED dpConfigTRVTransportname }

    ::= { dpConfigTRVTransportTable 1 }

DPConfigTRVTransportEntry ::= SEQUENCE {
    dpConfigTRVTransportIndex    Unsigned32,
    dpConfigTRVTransportname    DisplayString
}

dpConfigTRVTransportIndex OBJECT-TYPE
    SYNTAX      Unsigned32
    MAX-ACCESS  read-only
    STATUS      current
    DESCRIPTION "No description yet."

    ::= { dpConfigTRVTransportEntry 1 }

dpConfigTRVTransportname OBJECT-TYPE
    SYNTAX      DisplayString
    MAX-ACCESS  read-only
    STATUS      current
    DESCRIPTION "No description yet."

    ::= { dpConfigTRVTransportEntry 2 }

--

dpConfigLLMPolicyBaseTable OBJECT-TYPE
    SYNTAX      SEQUENCE OF DPConfigLLMPolicyBaseEntry
    MAX-ACCESS  not-accessible
    STATUS      current
    DESCRIPTION "Table."

    ::= { dpConfig 202 }

dpConfigLLMPolicyBaseEntry OBJECT-TYPE
    SYNTAX      DPConfigLLMPolicyBaseEntry
    MAX-ACCESS  not-accessible
    STATUS      current
    DESCRIPTION "Table row."
    INDEX { dpConfigLLMPolicyBaseIndex, IMPLIED dpConfigLLMPolicyBasename }

    ::= { dpConfigLLMPolicyBaseTable 1 }

DPConfigLLMPolicyBaseEntry ::= SEQUENCE {
    dpConfigLLMPolicyBaseIndex    Unsigned32,
    dpConfigLLMPolicyBasename    DisplayString
}

dpConfigLLMPolicyBaseIndex OBJECT-TYPE
    SYNTAX      Unsigned32
    MAX-ACCESS  read-only
    STATUS      current
    DESCRIPTION "No description yet."

    ::= { dpConfigLLMPolicyBaseEntry 1 }

dpConfigLLMPolicyBasename OBJECT-TYPE
    SYNTAX      DisplayString
    MAX-ACCESS  read-only
    STATUS      current
    DESCRIPTION "No description yet."

    ::= { dpConfigLLMPolicyBaseEntry 2 }

--

dpConfigLLMRouteBaseTable OBJECT-TYPE
    SYNTAX      SEQUENCE OF DPConfigLLMRouteBaseEntry
    MAX-ACCESS  not-accessible
    STATUS      current
    DESCRIPTION "Table."

    ::= { dpConfig 203 }

dpConfigLLMRouteBaseEntry OBJECT-TYPE
    SYNTAX      DPConfigLLMRouteBaseEntry
    MAX-ACCESS  not-accessible
    STATUS      current
    DESCRIPTION "Table row."
    INDEX { dpConfigLLMRouteBaseIndex, IMPLIED dpConfigLLMRouteBasename }

    ::= { dpConfigLLMRouteBaseTable 1 }

DPConfigLLMRouteBaseEntry ::= SEQUENCE {
    dpConfigLLMRouteBaseIndex    Unsigned32,
    dpConfigLLMRouteBasename    DisplayString
}

dpConfigLLMRouteBaseIndex OBJECT-TYPE
    SYNTAX      Unsigned32
    MAX-ACCESS  read-only
    STATUS      current
    DESCRIPTION "No description yet."

    ::= { dpConfigLLMRouteBaseEntry 1 }

dpConfigLLMRouteBasename OBJECT-TYPE
    SYNTAX      DisplayString
    MAX-ACCESS  read-only
    STATUS      current
    DESCRIPTION "No description yet."

    ::= { dpConfigLLMRouteBaseEntry 2 }

--

dpConfigPOPPollerSourceProtocolHandlerBaseTable OBJECT-TYPE
    SYNTAX      SEQUENCE OF DPConfigPOPPollerSourceProtocolHandlerBaseEntry
    MAX-ACCESS  not-accessible
    STATUS      current
    DESCRIPTION "Table."

    ::= { dpConfig 204 }

dpConfigPOPPollerSourceProtocolHandlerBaseEntry OBJECT-TYPE
    SYNTAX      DPConfigPOPPollerSourceProtocolHandlerBaseEntry
    MAX-ACCESS  not-accessible
    STATUS      current
    DESCRIPTION "Table row."
    INDEX { dpConfigPOPPollerSourceProtocolHandlerBaseIndex, IMPLIED dpConfigPOPPollerSourceProtocolHandlerBasename }

    ::= { dpConfigPOPPollerSourceProtocolHandlerBaseTable 1 }

DPConfigPOPPollerSourceProtocolHandlerBaseEntry ::= SEQUENCE {
    dpConfigPOPPollerSourceProtocolHandlerBaseIndex    Unsigned32,
    dpConfigPOPPollerSourceProtocolHandlerBasename    DisplayString
}

dpConfigPOPPollerSourceProtocolHandlerBaseIndex OBJECT-TYPE
    SYNTAX      Unsigned32
    MAX-ACCESS  read-only
    STATUS      current
    DESCRIPTION "No description yet."

    ::= { dpConfigPOPPollerSourceProtocolHandlerBaseEntry 1 }

dpConfigPOPPollerSourceProtocolHandlerBasename OBJECT-TYPE
    SYNTAX      DisplayString
    MAX-ACCESS  read-only
    STATUS      current
    DESCRIPTION "No description yet."

    ::= { dpConfigPOPPollerSourceProtocolHandlerBaseEntry 2 }

--

dpConfigAS1PollerSourceProtocolHandlerTable OBJECT-TYPE
    SYNTAX      SEQUENCE OF DPConfigAS1PollerSourceProtocolHandlerEntry
    MAX-ACCESS  not-accessible
    STATUS      current
    DESCRIPTION
        "The AS1 handler is a Post Office Protocol (POP) handler. The handler
        manages the polling of a mailbox on a mail server. The mailbox receives
        mail messages from external partners. The handler retrieves and deletes
        mail messages on each polling cycle. Each mail message that the handler
        retrieves results in one transaction."

    ::= { dpConfig 205 }

dpConfigAS1PollerSourceProtocolHandlerEntry OBJECT-TYPE
    SYNTAX      DPConfigAS1PollerSourceProtocolHandlerEntry
    MAX-ACCESS  not-accessible
    STATUS      current
    DESCRIPTION "Table row."
    INDEX { dpConfigAS1PollerSourceProtocolHandlerIndex, IMPLIED dpConfigAS1PollerSourceProtocolHandlername }

    ::= { dpConfigAS1PollerSourceProtocolHandlerTable 1 }

DPConfigAS1PollerSourceProtocolHandlerEntry ::= SEQUENCE {
    dpConfigAS1PollerSourceProtocolHandlerIndex    Unsigned32,
    dpConfigAS1PollerSourceProtocolHandlername    DisplayString
}

dpConfigAS1PollerSourceProtocolHandlerIndex OBJECT-TYPE
    SYNTAX      Unsigned32
    MAX-ACCESS  read-only
    STATUS      current
    DESCRIPTION "No description yet."

    ::= { dpConfigAS1PollerSourceProtocolHandlerEntry 1 }

dpConfigAS1PollerSourceProtocolHandlername OBJECT-TYPE
    SYNTAX      DisplayString
    MAX-ACCESS  read-only
    STATUS      current
    DESCRIPTION "No description yet."

    ::= { dpConfigAS1PollerSourceProtocolHandlerEntry 2 }

--

dpConfigPOPPollerSourceProtocolHandlerTable OBJECT-TYPE
    SYNTAX      SEQUENCE OF DPConfigPOPPollerSourceProtocolHandlerEntry
    MAX-ACCESS  not-accessible
    STATUS      current
    DESCRIPTION
        "The Post Office Protocol (POP) handler manages the polling of a mailbox on
        a mail server. The mailbox receives mail messages from external partners.
        The handler retrieves and deletes mail messages on each polling cycle.
        Each mail message that the handler retrieves results in one transaction."

    ::= { dpConfig 206 }

dpConfigPOPPollerSourceProtocolHandlerEntry OBJECT-TYPE
    SYNTAX      DPConfigPOPPollerSourceProtocolHandlerEntry
    MAX-ACCESS  not-accessible
    STATUS      current
    DESCRIPTION "Table row."
    INDEX { dpConfigPOPPollerSourceProtocolHandlerIndex, IMPLIED dpConfigPOPPollerSourceProtocolHandlername }

    ::= { dpConfigPOPPollerSourceProtocolHandlerTable 1 }

DPConfigPOPPollerSourceProtocolHandlerEntry ::= SEQUENCE {
    dpConfigPOPPollerSourceProtocolHandlerIndex    Unsigned32,
    dpConfigPOPPollerSourceProtocolHandlername    DisplayString
}

dpConfigPOPPollerSourceProtocolHandlerIndex OBJECT-TYPE
    SYNTAX      Unsigned32
    MAX-ACCESS  read-only
    STATUS      current
    DESCRIPTION "No description yet."

    ::= { dpConfigPOPPollerSourceProtocolHandlerEntry 1 }

dpConfigPOPPollerSourceProtocolHandlername OBJECT-TYPE
    SYNTAX      DisplayString
    MAX-ACCESS  read-only
    STATUS      current
    DESCRIPTION "No description yet."

    ::= { dpConfigPOPPollerSourceProtocolHandlerEntry 2 }

--

dpConfigSMTPServerConnectionTable OBJECT-TYPE
    SYNTAX      SEQUENCE OF DPConfigSMTPServerConnectionEntry
    MAX-ACCESS  not-accessible
    STATUS      current
    DESCRIPTION
        "The SMTP server connection defines the connection details for a Simple
        Mail Transport Protocol (SMTP) server. The appliance uses the SMTP server
        connection for the following purposes: B2B partners use this configuration
        to send an e-mail message to an AS1 or ESMTP destination. B2B gateways use
        this configuration to request an AS1 MDN. For ease of configuration, the
        DataPower appliance provides the default SMTP server connection
        configuration in each application domain. By default, this configuration
        is empty and disabled."

    ::= { dpConfig 207 }

dpConfigSMTPServerConnectionEntry OBJECT-TYPE
    SYNTAX      DPConfigSMTPServerConnectionEntry
    MAX-ACCESS  not-accessible
    STATUS      current
    DESCRIPTION "Table row."
    INDEX { dpConfigSMTPServerConnectionIndex, IMPLIED dpConfigSMTPServerConnectionname }

    ::= { dpConfigSMTPServerConnectionTable 1 }

DPConfigSMTPServerConnectionEntry ::= SEQUENCE {
    dpConfigSMTPServerConnectionIndex    Unsigned32,
    dpConfigSMTPServerConnectionname    DisplayString
}

dpConfigSMTPServerConnectionIndex OBJECT-TYPE
    SYNTAX      Unsigned32
    MAX-ACCESS  read-only
    STATUS      current
    DESCRIPTION "No description yet."

    ::= { dpConfigSMTPServerConnectionEntry 1 }

dpConfigSMTPServerConnectionname OBJECT-TYPE
    SYNTAX      DisplayString
    MAX-ACCESS  read-only
    STATUS      current
    DESCRIPTION "No description yet."

    ::= { dpConfigSMTPServerConnectionEntry 2 }

--

dpConfigXM70PersistenceTable OBJECT-TYPE
    SYNTAX      SEQUENCE OF DPConfigXM70PersistenceEntry
    MAX-ACCESS  not-accessible
    STATUS      current
    DESCRIPTION
        "Data storage for XM70 transaction data"

    ::= { dpConfig 208 }

dpConfigXM70PersistenceEntry OBJECT-TYPE
    SYNTAX      DPConfigXM70PersistenceEntry
    MAX-ACCESS  not-accessible
    STATUS      current
    DESCRIPTION "Table row."
    INDEX { dpConfigXM70PersistenceIndex, IMPLIED dpConfigXM70Persistencename }

    ::= { dpConfigXM70PersistenceTable 1 }

DPConfigXM70PersistenceEntry ::= SEQUENCE {
    dpConfigXM70PersistenceIndex    Unsigned32,
    dpConfigXM70Persistencename    DisplayString
}

dpConfigXM70PersistenceIndex OBJECT-TYPE
    SYNTAX      Unsigned32
    MAX-ACCESS  read-only
    STATUS      current
    DESCRIPTION "No description yet."

    ::= { dpConfigXM70PersistenceEntry 1 }

dpConfigXM70Persistencename OBJECT-TYPE
    SYNTAX      DisplayString
    MAX-ACCESS  read-only
    STATUS      current
    DESCRIPTION "No description yet."

    ::= { dpConfigXM70PersistenceEntry 2 }

--

dpConfigWSRRSavedSearchSubscriptionTable OBJECT-TYPE
    SYNTAX      SEQUENCE OF DPConfigWSRRSavedSearchSubscriptionEntry
    MAX-ACCESS  not-accessible
    STATUS      current
    DESCRIPTION
        "Use this screen to provide the required configuration properties for a
        WSRR (WebSphere Service Registry and Repository) saved search
        subscription. The Saved Search Subscription is useful when you want to
        deploy services with an indirect reference to a set of WSRR resources
        required for DataPower service operations. The configuration requires a
        reference to a WSRR server and the name of an existing saved search or
        named query from the WSRR server. The management of the service documents
        is controlled from the WSRR server. DataPower services associated with the
        saved search subscription are updated based on the synchronization method
        specified in the subscription. A DataPower service virtualizes the service
        bindings based on the WSRR resources returned by executing the configured
        saved search."

    ::= { dpConfig 209 }

dpConfigWSRRSavedSearchSubscriptionEntry OBJECT-TYPE
    SYNTAX      DPConfigWSRRSavedSearchSubscriptionEntry
    MAX-ACCESS  not-accessible
    STATUS      current
    DESCRIPTION "Table row."
    INDEX { dpConfigWSRRSavedSearchSubscriptionIndex, IMPLIED dpConfigWSRRSavedSearchSubscriptionname }

    ::= { dpConfigWSRRSavedSearchSubscriptionTable 1 }

DPConfigWSRRSavedSearchSubscriptionEntry ::= SEQUENCE {
    dpConfigWSRRSavedSearchSubscriptionIndex    Unsigned32,
    dpConfigWSRRSavedSearchSubscriptionname    DisplayString
}

dpConfigWSRRSavedSearchSubscriptionIndex OBJECT-TYPE
    SYNTAX      Unsigned32
    MAX-ACCESS  read-only
    STATUS      current
    DESCRIPTION "No description yet."

    ::= { dpConfigWSRRSavedSearchSubscriptionEntry 1 }

dpConfigWSRRSavedSearchSubscriptionname OBJECT-TYPE
    SYNTAX      DisplayString
    MAX-ACCESS  read-only
    STATUS      current
    DESCRIPTION "No description yet."

    ::= { dpConfigWSRRSavedSearchSubscriptionEntry 2 }

--

dpConfigEBMS2SourceProtocolHandlerTable OBJECT-TYPE
    SYNTAX      SEQUENCE OF DPConfigEBMS2SourceProtocolHandlerEntry
    MAX-ACCESS  not-accessible
    STATUS      current
    DESCRIPTION
        "The configuration for an ebMS2 protocol handler."

    ::= { dpConfig 210 }

dpConfigEBMS2SourceProtocolHandlerEntry OBJECT-TYPE
    SYNTAX      DPConfigEBMS2SourceProtocolHandlerEntry
    MAX-ACCESS  not-accessible
    STATUS      current
    DESCRIPTION "Table row."
    INDEX { dpConfigEBMS2SourceProtocolHandlerIndex, IMPLIED dpConfigEBMS2SourceProtocolHandlername }

    ::= { dpConfigEBMS2SourceProtocolHandlerTable 1 }

DPConfigEBMS2SourceProtocolHandlerEntry ::= SEQUENCE {
    dpConfigEBMS2SourceProtocolHandlerIndex    Unsigned32,
    dpConfigEBMS2SourceProtocolHandlername    DisplayString
}

dpConfigEBMS2SourceProtocolHandlerIndex OBJECT-TYPE
    SYNTAX      Unsigned32
    MAX-ACCESS  read-only
    STATUS      current
    DESCRIPTION "No description yet."

    ::= { dpConfigEBMS2SourceProtocolHandlerEntry 1 }

dpConfigEBMS2SourceProtocolHandlername OBJECT-TYPE
    SYNTAX      DisplayString
    MAX-ACCESS  read-only
    STATUS      current
    DESCRIPTION "No description yet."

    ::= { dpConfigEBMS2SourceProtocolHandlerEntry 2 }

--

dpConfigSAMLAttributesTable OBJECT-TYPE
    SYNTAX      SEQUENCE OF DPConfigSAMLAttributesEntry
    MAX-ACCESS  not-accessible
    STATUS      current
    DESCRIPTION
        "Define a list of SAML attributes for the SAML Assertion generator."

    ::= { dpConfig 211 }

dpConfigSAMLAttributesEntry OBJECT-TYPE
    SYNTAX      DPConfigSAMLAttributesEntry
    MAX-ACCESS  not-accessible
    STATUS      current
    DESCRIPTION "Table row."
    INDEX { dpConfigSAMLAttributesIndex, IMPLIED dpConfigSAMLAttributesname }

    ::= { dpConfigSAMLAttributesTable 1 }

DPConfigSAMLAttributesEntry ::= SEQUENCE {
    dpConfigSAMLAttributesIndex    Unsigned32,
    dpConfigSAMLAttributesname    DisplayString
}

dpConfigSAMLAttributesIndex OBJECT-TYPE
    SYNTAX      Unsigned32
    MAX-ACCESS  read-only
    STATUS      current
    DESCRIPTION "No description yet."

    ::= { dpConfigSAMLAttributesEntry 1 }

dpConfigSAMLAttributesname OBJECT-TYPE
    SYNTAX      DisplayString
    MAX-ACCESS  read-only
    STATUS      current
    DESCRIPTION "No description yet."

    ::= { dpConfigSAMLAttributesEntry 2 }

--

dpConfigSSHClientProfileTable OBJECT-TYPE
    SYNTAX      SEQUENCE OF DPConfigSSHClientProfileEntry
    MAX-ACCESS  not-accessible
    STATUS      current
    DESCRIPTION
        "An SSH Client Profile is associated with an SSH URLOpener or with a Secure
        Cloud Connector. Also, a Secure Cloud Connection requires an Application
        Optimization license. The remote server's public key must be contained in
        the SSH Client Profile known hosts list."

    ::= { dpConfig 212 }

dpConfigSSHClientProfileEntry OBJECT-TYPE
    SYNTAX      DPConfigSSHClientProfileEntry
    MAX-ACCESS  not-accessible
    STATUS      current
    DESCRIPTION "Table row."
    INDEX { dpConfigSSHClientProfileIndex, IMPLIED dpConfigSSHClientProfilename }

    ::= { dpConfigSSHClientProfileTable 1 }

DPConfigSSHClientProfileEntry ::= SEQUENCE {
    dpConfigSSHClientProfileIndex    Unsigned32,
    dpConfigSSHClientProfilename    DisplayString
}

dpConfigSSHClientProfileIndex OBJECT-TYPE
    SYNTAX      Unsigned32
    MAX-ACCESS  read-only
    STATUS      current
    DESCRIPTION "No description yet."

    ::= { dpConfigSSHClientProfileEntry 1 }

dpConfigSSHClientProfilename OBJECT-TYPE
    SYNTAX      DisplayString
    MAX-ACCESS  read-only
    STATUS      current
    DESCRIPTION "No description yet."

    ::= { dpConfigSSHClientProfileEntry 2 }

--

dpConfigSFTPFilePollerSourceProtocolHandlerTable OBJECT-TYPE
    SYNTAX      SEQUENCE OF DPConfigSFTPFilePollerSourceProtocolHandlerEntry
    MAX-ACCESS  not-accessible
    STATUS      current
    DESCRIPTION
        "Use this front side option to have file based input from a configured SFTP
        directory. The directory must exist and have the appropriate permission to
        perform the designated operations. For these configured directories,
        ensure that the read, write, and delete permissions are available, as
        required."

    ::= { dpConfig 213 }

dpConfigSFTPFilePollerSourceProtocolHandlerEntry OBJECT-TYPE
    SYNTAX      DPConfigSFTPFilePollerSourceProtocolHandlerEntry
    MAX-ACCESS  not-accessible
    STATUS      current
    DESCRIPTION "Table row."
    INDEX { dpConfigSFTPFilePollerSourceProtocolHandlerIndex, IMPLIED dpConfigSFTPFilePollerSourceProtocolHandlername }

    ::= { dpConfigSFTPFilePollerSourceProtocolHandlerTable 1 }

DPConfigSFTPFilePollerSourceProtocolHandlerEntry ::= SEQUENCE {
    dpConfigSFTPFilePollerSourceProtocolHandlerIndex    Unsigned32,
    dpConfigSFTPFilePollerSourceProtocolHandlername    DisplayString
}

dpConfigSFTPFilePollerSourceProtocolHandlerIndex OBJECT-TYPE
    SYNTAX      Unsigned32
    MAX-ACCESS  read-only
    STATUS      current
    DESCRIPTION "No description yet."

    ::= { dpConfigSFTPFilePollerSourceProtocolHandlerEntry 1 }

dpConfigSFTPFilePollerSourceProtocolHandlername OBJECT-TYPE
    SYNTAX      DisplayString
    MAX-ACCESS  read-only
    STATUS      current
    DESCRIPTION "No description yet."

    ::= { dpConfigSFTPFilePollerSourceProtocolHandlerEntry 2 }

--

dpConfigZHybridTargetControlServiceTable OBJECT-TYPE
    SYNTAX      SEQUENCE OF DPConfigZHybridTargetControlServiceEntry
    MAX-ACCESS  not-accessible
    STATUS      current
    DESCRIPTION
        "The Sysplex Distributor Target Control Service on the DataPower Gateway
        establishes control connections with the z/OS Sysplex Distributor that
        allow the z/OS Sysplex Distributor to intelligently distribute traffic
        across multiple DataPower Gateway instances. The use of the Sysplex
        Distributor Target Control Service is deprecated. Multiple z/OS Sysplex
        Distributors can establish control connections to the single Sysplex
        Distributor Target Control Service on the DataPower Gateway. When the
        Sysplex Distributor Target Control Service is disabled, existing z/OS
        Sysplex Distributor control connections are closed. Ensure that the
        reverse path filtering property for Network Settings is not selected. If
        you allow reverse path filtering, the interface cannot correctly route
        requests from the Sysplex Distributor to use the Target Control Server."

    ::= { dpConfig 214 }

dpConfigZHybridTargetControlServiceEntry OBJECT-TYPE
    SYNTAX      DPConfigZHybridTargetControlServiceEntry
    MAX-ACCESS  not-accessible
    STATUS      current
    DESCRIPTION "Table row."
    INDEX { dpConfigZHybridTargetControlServiceIndex, IMPLIED dpConfigZHybridTargetControlServicename }

    ::= { dpConfigZHybridTargetControlServiceTable 1 }

DPConfigZHybridTargetControlServiceEntry ::= SEQUENCE {
    dpConfigZHybridTargetControlServiceIndex    Unsigned32,
    dpConfigZHybridTargetControlServicename    DisplayString
}

dpConfigZHybridTargetControlServiceIndex OBJECT-TYPE
    SYNTAX      Unsigned32
    MAX-ACCESS  read-only
    STATUS      current
    DESCRIPTION "No description yet."

    ::= { dpConfigZHybridTargetControlServiceEntry 1 }

dpConfigZHybridTargetControlServicename OBJECT-TYPE
    SYNTAX      DisplayString
    MAX-ACCESS  read-only
    STATUS      current
    DESCRIPTION "No description yet."

    ::= { dpConfigZHybridTargetControlServiceEntry 2 }

--

dpConfigMultipathServiceTable OBJECT-TYPE
    SYNTAX      SEQUENCE OF DPConfigMultipathServiceEntry
    MAX-ACCESS  not-accessible
    STATUS      current
    DESCRIPTION
        "Configures the Multipath server"

    ::= { dpConfig 215 }

dpConfigMultipathServiceEntry OBJECT-TYPE
    SYNTAX      DPConfigMultipathServiceEntry
    MAX-ACCESS  not-accessible
    STATUS      current
    DESCRIPTION "Table row."
    INDEX { dpConfigMultipathServiceIndex, IMPLIED dpConfigMultipathServicename }

    ::= { dpConfigMultipathServiceTable 1 }

DPConfigMultipathServiceEntry ::= SEQUENCE {
    dpConfigMultipathServiceIndex    Unsigned32,
    dpConfigMultipathServicename    DisplayString
}

dpConfigMultipathServiceIndex OBJECT-TYPE
    SYNTAX      Unsigned32
    MAX-ACCESS  read-only
    STATUS      current
    DESCRIPTION "No description yet."

    ::= { dpConfigMultipathServiceEntry 1 }

dpConfigMultipathServicename OBJECT-TYPE
    SYNTAX      DisplayString
    MAX-ACCESS  read-only
    STATUS      current
    DESCRIPTION "No description yet."

    ::= { dpConfigMultipathServiceEntry 2 }

--

dpConfigClusterServiceTable OBJECT-TYPE
    SYNTAX      SEQUENCE OF DPConfigClusterServiceEntry
    MAX-ACCESS  not-accessible
    STATUS      current
    DESCRIPTION
        "Configures the cluster service. The cluster service is useful for
        maintaining consistency of remote storage shared amongst multiple
        appliances. This configuration must be identical amongst all appliances in
        the cluster, otherwise, unexpected behavior may result."

    ::= { dpConfig 216 }

dpConfigClusterServiceEntry OBJECT-TYPE
    SYNTAX      DPConfigClusterServiceEntry
    MAX-ACCESS  not-accessible
    STATUS      current
    DESCRIPTION "Table row."
    INDEX { dpConfigClusterServiceIndex, IMPLIED dpConfigClusterServicename }

    ::= { dpConfigClusterServiceTable 1 }

DPConfigClusterServiceEntry ::= SEQUENCE {
    dpConfigClusterServiceIndex    Unsigned32,
    dpConfigClusterServicename    DisplayString
}

dpConfigClusterServiceIndex OBJECT-TYPE
    SYNTAX      Unsigned32
    MAX-ACCESS  read-only
    STATUS      current
    DESCRIPTION "No description yet."

    ::= { dpConfigClusterServiceEntry 1 }

dpConfigClusterServicename OBJECT-TYPE
    SYNTAX      DisplayString
    MAX-ACCESS  read-only
    STATUS      current
    DESCRIPTION "No description yet."

    ::= { dpConfigClusterServiceEntry 2 }

--

dpConfigSecureCloudConnectorTable OBJECT-TYPE
    SYNTAX      SEQUENCE OF DPConfigSecureCloudConnectorEntry
    MAX-ACCESS  not-accessible
    STATUS      current
    DESCRIPTION
        "Deprecated - Use this page to configure and manage a Secure Cloud
        Connector for a single cloud server instance."

    ::= { dpConfig 217 }

dpConfigSecureCloudConnectorEntry OBJECT-TYPE
    SYNTAX      DPConfigSecureCloudConnectorEntry
    MAX-ACCESS  not-accessible
    STATUS      current
    DESCRIPTION "Table row."
    INDEX { dpConfigSecureCloudConnectorIndex, IMPLIED dpConfigSecureCloudConnectorname }

    ::= { dpConfigSecureCloudConnectorTable 1 }

DPConfigSecureCloudConnectorEntry ::= SEQUENCE {
    dpConfigSecureCloudConnectorIndex    Unsigned32,
    dpConfigSecureCloudConnectorname    DisplayString
}

dpConfigSecureCloudConnectorIndex OBJECT-TYPE
    SYNTAX      Unsigned32
    MAX-ACCESS  read-only
    STATUS      current
    DESCRIPTION "No description yet."

    ::= { dpConfigSecureCloudConnectorEntry 1 }

dpConfigSecureCloudConnectorname OBJECT-TYPE
    SYNTAX      DisplayString
    MAX-ACCESS  read-only
    STATUS      current
    DESCRIPTION "No description yet."

    ::= { dpConfigSecureCloudConnectorEntry 2 }

--

dpConfigIPMILanChannelTable OBJECT-TYPE
    SYNTAX      SEQUENCE OF DPConfigIPMILanChannelEntry
    MAX-ACCESS  not-accessible
    STATUS      current
    DESCRIPTION
        "An Intelligent Platform Management Interface (IPMI) LAN channel allows
        access to the Baseboard Management Controller (BMC) on the appliance over
        a LAN. IPMI allows remote management access and can provide serial over
        LAN to the console serial port. The LAN channel must use the 'mgt0'
        management Ethernet connector."

    ::= { dpConfig 218 }

dpConfigIPMILanChannelEntry OBJECT-TYPE
    SYNTAX      DPConfigIPMILanChannelEntry
    MAX-ACCESS  not-accessible
    STATUS      current
    DESCRIPTION "Table row."
    INDEX { dpConfigIPMILanChannelIndex, IMPLIED dpConfigIPMILanChannelname }

    ::= { dpConfigIPMILanChannelTable 1 }

DPConfigIPMILanChannelEntry ::= SEQUENCE {
    dpConfigIPMILanChannelIndex    Unsigned32,
    dpConfigIPMILanChannelname    DisplayString
}

dpConfigIPMILanChannelIndex OBJECT-TYPE
    SYNTAX      Unsigned32
    MAX-ACCESS  read-only
    STATUS      current
    DESCRIPTION "No description yet."

    ::= { dpConfigIPMILanChannelEntry 1 }

dpConfigIPMILanChannelname OBJECT-TYPE
    SYNTAX      DisplayString
    MAX-ACCESS  read-only
    STATUS      current
    DESCRIPTION "No description yet."

    ::= { dpConfigIPMILanChannelEntry 2 }

--

dpConfigIPMIUserTable OBJECT-TYPE
    SYNTAX      SEQUENCE OF DPConfigIPMIUserEntry
    MAX-ACCESS  not-accessible
    STATUS      current
    DESCRIPTION
        "An Intelligent Platform Management Interface (IPMI) user can create,
        change, or destroy user authentication records in the Baseboard Management
        Controller (BMC). Authentication records allow users to communicate using
        IPMI protocols over external channels, such as an IPMI LAN channel. On an
        appliance, there can be eight IPMI users. #b#Note#/b#: If you apply the
        configuration but do not save it, the IPMI user data is written to the BMC
        but not saved to the startup configuration. In this situation, the IPMI
        user can connect to the serial port over the IPMI LAN channel."

    ::= { dpConfig 219 }

dpConfigIPMIUserEntry OBJECT-TYPE
    SYNTAX      DPConfigIPMIUserEntry
    MAX-ACCESS  not-accessible
    STATUS      current
    DESCRIPTION "Table row."
    INDEX { dpConfigIPMIUserIndex, IMPLIED dpConfigIPMIUsername }

    ::= { dpConfigIPMIUserTable 1 }

DPConfigIPMIUserEntry ::= SEQUENCE {
    dpConfigIPMIUserIndex    Unsigned32,
    dpConfigIPMIUsername    DisplayString
}

dpConfigIPMIUserIndex OBJECT-TYPE
    SYNTAX      Unsigned32
    MAX-ACCESS  read-only
    STATUS      current
    DESCRIPTION "No description yet."

    ::= { dpConfigIPMIUserEntry 1 }

dpConfigIPMIUsername OBJECT-TYPE
    SYNTAX      DisplayString
    MAX-ACCESS  read-only
    STATUS      current
    DESCRIPTION "No description yet."

    ::= { dpConfigIPMIUserEntry 2 }

--

dpConfigB2BCPACollaborationTable OBJECT-TYPE
    SYNTAX      SEQUENCE OF DPConfigB2BCPACollaborationEntry
    MAX-ACCESS  not-accessible
    STATUS      current
    DESCRIPTION "Table."

    ::= { dpConfig 220 }

dpConfigB2BCPACollaborationEntry OBJECT-TYPE
    SYNTAX      DPConfigB2BCPACollaborationEntry
    MAX-ACCESS  not-accessible
    STATUS      current
    DESCRIPTION "Table row."
    INDEX { dpConfigB2BCPACollaborationIndex, IMPLIED dpConfigB2BCPACollaborationname }

    ::= { dpConfigB2BCPACollaborationTable 1 }

DPConfigB2BCPACollaborationEntry ::= SEQUENCE {
    dpConfigB2BCPACollaborationIndex    Unsigned32,
    dpConfigB2BCPACollaborationname    DisplayString
}

dpConfigB2BCPACollaborationIndex OBJECT-TYPE
    SYNTAX      Unsigned32
    MAX-ACCESS  read-only
    STATUS      current
    DESCRIPTION "No description yet."

    ::= { dpConfigB2BCPACollaborationEntry 1 }

dpConfigB2BCPACollaborationname OBJECT-TYPE
    SYNTAX      DisplayString
    MAX-ACCESS  read-only
    STATUS      current
    DESCRIPTION "No description yet."

    ::= { dpConfigB2BCPACollaborationEntry 2 }

--

dpConfigMQFTESourceProtocolHandlerTable OBJECT-TYPE
    SYNTAX      SEQUENCE OF DPConfigMQFTESourceProtocolHandlerEntry
    MAX-ACCESS  not-accessible
    STATUS      current
    DESCRIPTION "Table."

    ::= { dpConfig 221 }

dpConfigMQFTESourceProtocolHandlerEntry OBJECT-TYPE
    SYNTAX      DPConfigMQFTESourceProtocolHandlerEntry
    MAX-ACCESS  not-accessible
    STATUS      current
    DESCRIPTION "Table row."
    INDEX { dpConfigMQFTESourceProtocolHandlerIndex, IMPLIED dpConfigMQFTESourceProtocolHandlername }

    ::= { dpConfigMQFTESourceProtocolHandlerTable 1 }

DPConfigMQFTESourceProtocolHandlerEntry ::= SEQUENCE {
    dpConfigMQFTESourceProtocolHandlerIndex    Unsigned32,
    dpConfigMQFTESourceProtocolHandlername    DisplayString
}

dpConfigMQFTESourceProtocolHandlerIndex OBJECT-TYPE
    SYNTAX      Unsigned32
    MAX-ACCESS  read-only
    STATUS      current
    DESCRIPTION "No description yet."

    ::= { dpConfigMQFTESourceProtocolHandlerEntry 1 }

dpConfigMQFTESourceProtocolHandlername OBJECT-TYPE
    SYNTAX      DisplayString
    MAX-ACCESS  read-only
    STATUS      current
    DESCRIPTION "No description yet."

    ::= { dpConfigMQFTESourceProtocolHandlerEntry 2 }

--

dpConfigB2BCPATable OBJECT-TYPE
    SYNTAX      SEQUENCE OF DPConfigB2BCPAEntry
    MAX-ACCESS  not-accessible
    STATUS      current
    DESCRIPTION "Table."

    ::= { dpConfig 222 }

dpConfigB2BCPAEntry OBJECT-TYPE
    SYNTAX      DPConfigB2BCPAEntry
    MAX-ACCESS  not-accessible
    STATUS      current
    DESCRIPTION "Table row."
    INDEX { dpConfigB2BCPAIndex, IMPLIED dpConfigB2BCPAname }

    ::= { dpConfigB2BCPATable 1 }

DPConfigB2BCPAEntry ::= SEQUENCE {
    dpConfigB2BCPAIndex    Unsigned32,
    dpConfigB2BCPAname    DisplayString
}

dpConfigB2BCPAIndex OBJECT-TYPE
    SYNTAX      Unsigned32
    MAX-ACCESS  read-only
    STATUS      current
    DESCRIPTION "No description yet."

    ::= { dpConfigB2BCPAEntry 1 }

dpConfigB2BCPAname OBJECT-TYPE
    SYNTAX      DisplayString
    MAX-ACCESS  read-only
    STATUS      current
    DESCRIPTION "No description yet."

    ::= { dpConfigB2BCPAEntry 2 }

--

dpConfigB2BCPASenderSettingTable OBJECT-TYPE
    SYNTAX      SEQUENCE OF DPConfigB2BCPASenderSettingEntry
    MAX-ACCESS  not-accessible
    STATUS      current
    DESCRIPTION "Table."

    ::= { dpConfig 223 }

dpConfigB2BCPASenderSettingEntry OBJECT-TYPE
    SYNTAX      DPConfigB2BCPASenderSettingEntry
    MAX-ACCESS  not-accessible
    STATUS      current
    DESCRIPTION "Table row."
    INDEX { dpConfigB2BCPASenderSettingIndex, IMPLIED dpConfigB2BCPASenderSettingname }

    ::= { dpConfigB2BCPASenderSettingTable 1 }

DPConfigB2BCPASenderSettingEntry ::= SEQUENCE {
    dpConfigB2BCPASenderSettingIndex    Unsigned32,
    dpConfigB2BCPASenderSettingname    DisplayString
}

dpConfigB2BCPASenderSettingIndex OBJECT-TYPE
    SYNTAX      Unsigned32
    MAX-ACCESS  read-only
    STATUS      current
    DESCRIPTION "No description yet."

    ::= { dpConfigB2BCPASenderSettingEntry 1 }

dpConfigB2BCPASenderSettingname OBJECT-TYPE
    SYNTAX      DisplayString
    MAX-ACCESS  read-only
    STATUS      current
    DESCRIPTION "No description yet."

    ::= { dpConfigB2BCPASenderSettingEntry 2 }

--

dpConfigB2BCPAReceiverSettingTable OBJECT-TYPE
    SYNTAX      SEQUENCE OF DPConfigB2BCPAReceiverSettingEntry
    MAX-ACCESS  not-accessible
    STATUS      current
    DESCRIPTION "Table."

    ::= { dpConfig 224 }

dpConfigB2BCPAReceiverSettingEntry OBJECT-TYPE
    SYNTAX      DPConfigB2BCPAReceiverSettingEntry
    MAX-ACCESS  not-accessible
    STATUS      current
    DESCRIPTION "Table row."
    INDEX { dpConfigB2BCPAReceiverSettingIndex, IMPLIED dpConfigB2BCPAReceiverSettingname }

    ::= { dpConfigB2BCPAReceiverSettingTable 1 }

DPConfigB2BCPAReceiverSettingEntry ::= SEQUENCE {
    dpConfigB2BCPAReceiverSettingIndex    Unsigned32,
    dpConfigB2BCPAReceiverSettingname    DisplayString
}

dpConfigB2BCPAReceiverSettingIndex OBJECT-TYPE
    SYNTAX      Unsigned32
    MAX-ACCESS  read-only
    STATUS      current
    DESCRIPTION "No description yet."

    ::= { dpConfigB2BCPAReceiverSettingEntry 1 }

dpConfigB2BCPAReceiverSettingname OBJECT-TYPE
    SYNTAX      DisplayString
    MAX-ACCESS  read-only
    STATUS      current
    DESCRIPTION "No description yet."

    ::= { dpConfigB2BCPAReceiverSettingEntry 2 }

--

dpConfigOAuthSupportedClientTable OBJECT-TYPE
    SYNTAX      SEQUENCE OF DPConfigOAuthSupportedClientEntry
    MAX-ACCESS  not-accessible
    STATUS      current
    DESCRIPTION
        "An OAuth client profile is the basic building block for an OAuth client
        group. When you create an OAuth client profile, you define its role. As
        you select the role, the WebGUI refreshes to display the appropriate
        properties. You can create the following types of OAuth client profiles: A
        client profile for authorization server endpoints: authorization endpoint
        and token endpoint. A client profile for the enforcement point for the
        resource server. A client profile for both authorization server endpoints
        and the enforcement point. When creating an OAuth client profile, you can
        use stylesheets or GatewayScript files for customization. You can create a
        customized OAuth client profile that defines any combination of roles.
        Customization uses stylesheets or GatewayScript files that must be in the
        local: or store: directory. For information about the operations that
        these stylesheets or GatewayScript files must define, see the topic in IBM
        Knowledge Center."

    ::= { dpConfig 225 }

dpConfigOAuthSupportedClientEntry OBJECT-TYPE
    SYNTAX      DPConfigOAuthSupportedClientEntry
    MAX-ACCESS  not-accessible
    STATUS      current
    DESCRIPTION "Table row."
    INDEX { dpConfigOAuthSupportedClientIndex, IMPLIED dpConfigOAuthSupportedClientname }

    ::= { dpConfigOAuthSupportedClientTable 1 }

DPConfigOAuthSupportedClientEntry ::= SEQUENCE {
    dpConfigOAuthSupportedClientIndex    Unsigned32,
    dpConfigOAuthSupportedClientname    DisplayString
}

dpConfigOAuthSupportedClientIndex OBJECT-TYPE
    SYNTAX      Unsigned32
    MAX-ACCESS  read-only
    STATUS      current
    DESCRIPTION "No description yet."

    ::= { dpConfigOAuthSupportedClientEntry 1 }

dpConfigOAuthSupportedClientname OBJECT-TYPE
    SYNTAX      DisplayString
    MAX-ACCESS  read-only
    STATUS      current
    DESCRIPTION "No description yet."

    ::= { dpConfigOAuthSupportedClientEntry 2 }

--

dpConfigOAuthSupportedClientGroupTable OBJECT-TYPE
    SYNTAX      SEQUENCE OF DPConfigOAuthSupportedClientGroupEntry
    MAX-ACCESS  not-accessible
    STATUS      current
    DESCRIPTION
        "To support the OAuth 2.0 protocol, an AAA policy requires the
        configuration of an OAuth client group. An OAuth client group contains the
        configured OAuth clients that the DataPower appliance accepts requests
        from. When creating an OAuth client group for an AAA policy, the OAuth
        client group consists of one or more OAuth clients with the same OAuth
        roles."

    ::= { dpConfig 226 }

dpConfigOAuthSupportedClientGroupEntry OBJECT-TYPE
    SYNTAX      DPConfigOAuthSupportedClientGroupEntry
    MAX-ACCESS  not-accessible
    STATUS      current
    DESCRIPTION "Table row."
    INDEX { dpConfigOAuthSupportedClientGroupIndex, IMPLIED dpConfigOAuthSupportedClientGroupname }

    ::= { dpConfigOAuthSupportedClientGroupTable 1 }

DPConfigOAuthSupportedClientGroupEntry ::= SEQUENCE {
    dpConfigOAuthSupportedClientGroupIndex    Unsigned32,
    dpConfigOAuthSupportedClientGroupname    DisplayString
}

dpConfigOAuthSupportedClientGroupIndex OBJECT-TYPE
    SYNTAX      Unsigned32
    MAX-ACCESS  read-only
    STATUS      current
    DESCRIPTION "No description yet."

    ::= { dpConfigOAuthSupportedClientGroupEntry 1 }

dpConfigOAuthSupportedClientGroupname OBJECT-TYPE
    SYNTAX      DisplayString
    MAX-ACCESS  read-only
    STATUS      current
    DESCRIPTION "No description yet."

    ::= { dpConfigOAuthSupportedClientGroupEntry 2 }

--

dpConfigSSLSNIServerProfileTable OBJECT-TYPE
    SYNTAX      SEQUENCE OF DPConfigSSLSNIServerProfileEntry
    MAX-ACCESS  not-accessible
    STATUS      current
    DESCRIPTION
        "The SSL Server Name Indication (SNI) server profile secures connections
        between the client and the appliance."

    ::= { dpConfig 227 }

dpConfigSSLSNIServerProfileEntry OBJECT-TYPE
    SYNTAX      DPConfigSSLSNIServerProfileEntry
    MAX-ACCESS  not-accessible
    STATUS      current
    DESCRIPTION "Table row."
    INDEX { dpConfigSSLSNIServerProfileIndex, IMPLIED dpConfigSSLSNIServerProfilename }

    ::= { dpConfigSSLSNIServerProfileTable 1 }

DPConfigSSLSNIServerProfileEntry ::= SEQUENCE {
    dpConfigSSLSNIServerProfileIndex    Unsigned32,
    dpConfigSSLSNIServerProfilename    DisplayString
}

dpConfigSSLSNIServerProfileIndex OBJECT-TYPE
    SYNTAX      Unsigned32
    MAX-ACCESS  read-only
    STATUS      current
    DESCRIPTION "No description yet."

    ::= { dpConfigSSLSNIServerProfileEntry 1 }

dpConfigSSLSNIServerProfilename OBJECT-TYPE
    SYNTAX      DisplayString
    MAX-ACCESS  read-only
    STATUS      current
    DESCRIPTION "No description yet."

    ::= { dpConfigSSLSNIServerProfileEntry 2 }

--

dpConfigXC10GridTable OBJECT-TYPE
    SYNTAX      SEQUENCE OF DPConfigXC10GridEntry
    MAX-ACCESS  not-accessible
    STATUS      current
    DESCRIPTION
        "The configuration of an XC10 Grid defines the connection details to an
        XC10 grid in an XC10 collective. To define this configuration, you must
        define the XC10 collective, the grid name, and the user and password for
        the user account who connects to the XC10 appliance. If you need to secure
        connections to XC10 appliances or perform actions that manage the grid or
        collective, you must assign an SSL client profile. To create an XC10 grid,
        the user account needs the XC10 Administrator or Creator role. The action
        submits a secured request to the remote XC10 appliance. To clear an XC10
        grid, which deletes the content of the XC10 grid, the user account needs
        the XC10 Administrator or Creator role. The action submits a secured
        request to the remote XC10 appliance. To discover an XC10 collective,
        which populates and manages the load balancer group for the XC10
        collective, the user account needs the XC10 Administrator role. The action
        submits a secured request to the remote XC10 appliance."

    ::= { dpConfig 235 }

dpConfigXC10GridEntry OBJECT-TYPE
    SYNTAX      DPConfigXC10GridEntry
    MAX-ACCESS  not-accessible
    STATUS      current
    DESCRIPTION "Table row."
    INDEX { dpConfigXC10GridIndex, IMPLIED dpConfigXC10Gridname }

    ::= { dpConfigXC10GridTable 1 }

DPConfigXC10GridEntry ::= SEQUENCE {
    dpConfigXC10GridIndex    Unsigned32,
    dpConfigXC10Gridname    DisplayString
}

dpConfigXC10GridIndex OBJECT-TYPE
    SYNTAX      Unsigned32
    MAX-ACCESS  read-only
    STATUS      current
    DESCRIPTION "No description yet."

    ::= { dpConfigXC10GridEntry 1 }

dpConfigXC10Gridname OBJECT-TYPE
    SYNTAX      DisplayString
    MAX-ACCESS  read-only
    STATUS      current
    DESCRIPTION "No description yet."

    ::= { dpConfigXC10GridEntry 2 }

--

dpConfigRuntimeSettingsTable OBJECT-TYPE
    SYNTAX      SEQUENCE OF DPConfigRuntimeSettingsEntry
    MAX-ACCESS  not-accessible
    STATUS      current
    DESCRIPTION "Table."

    ::= { dpConfig 246 }

dpConfigRuntimeSettingsEntry OBJECT-TYPE
    SYNTAX      DPConfigRuntimeSettingsEntry
    MAX-ACCESS  not-accessible
    STATUS      current
    DESCRIPTION "Table row."
    INDEX { dpConfigRuntimeSettingsIndex, IMPLIED dpConfigRuntimeSettingsname }

    ::= { dpConfigRuntimeSettingsTable 1 }

DPConfigRuntimeSettingsEntry ::= SEQUENCE {
    dpConfigRuntimeSettingsIndex    Unsigned32,
    dpConfigRuntimeSettingsname    DisplayString
}

dpConfigRuntimeSettingsIndex OBJECT-TYPE
    SYNTAX      Unsigned32
    MAX-ACCESS  read-only
    STATUS      current
    DESCRIPTION "No description yet."

    ::= { dpConfigRuntimeSettingsEntry 1 }

dpConfigRuntimeSettingsname OBJECT-TYPE
    SYNTAX      DisplayString
    MAX-ACCESS  read-only
    STATUS      current
    DESCRIPTION "No description yet."

    ::= { dpConfigRuntimeSettingsEntry 2 }

--

dpConfigSQLRuntimeSettingsTable OBJECT-TYPE
    SYNTAX      SEQUENCE OF DPConfigSQLRuntimeSettingsEntry
    MAX-ACCESS  not-accessible
    STATUS      current
    DESCRIPTION
        "Configure global sql runtime settings. A runtime environment is a
        container object that hosts objects within the system."

    ::= { dpConfig 247 }

dpConfigSQLRuntimeSettingsEntry OBJECT-TYPE
    SYNTAX      DPConfigSQLRuntimeSettingsEntry
    MAX-ACCESS  not-accessible
    STATUS      current
    DESCRIPTION "Table row."
    INDEX { dpConfigSQLRuntimeSettingsIndex, IMPLIED dpConfigSQLRuntimeSettingsname }

    ::= { dpConfigSQLRuntimeSettingsTable 1 }

DPConfigSQLRuntimeSettingsEntry ::= SEQUENCE {
    dpConfigSQLRuntimeSettingsIndex    Unsigned32,
    dpConfigSQLRuntimeSettingsname    DisplayString
}

dpConfigSQLRuntimeSettingsIndex OBJECT-TYPE
    SYNTAX      Unsigned32
    MAX-ACCESS  read-only
    STATUS      current
    DESCRIPTION "No description yet."

    ::= { dpConfigSQLRuntimeSettingsEntry 1 }

dpConfigSQLRuntimeSettingsname OBJECT-TYPE
    SYNTAX      DisplayString
    MAX-ACCESS  read-only
    STATUS      current
    DESCRIPTION "No description yet."

    ::= { dpConfigSQLRuntimeSettingsEntry 2 }

--

dpConfigWebApplicationGatewayTable OBJECT-TYPE
    SYNTAX      SEQUENCE OF DPConfigWebApplicationGatewayEntry
    MAX-ACCESS  not-accessible
    STATUS      current
    DESCRIPTION
        "A Web Application Gateway service can accept client-originated messages in
        HTTP. The gateway can subsequently pass messages to a back end server
        using HTTP. The messages may be processed and routed using any of the
        standard Document Processing Actions available to a firewall or a proxy."

    ::= { dpConfig 248 }

dpConfigWebApplicationGatewayEntry OBJECT-TYPE
    SYNTAX      DPConfigWebApplicationGatewayEntry
    MAX-ACCESS  not-accessible
    STATUS      current
    DESCRIPTION "Table row."
    INDEX { dpConfigWebApplicationGatewayIndex, IMPLIED dpConfigWebApplicationGatewayname }

    ::= { dpConfigWebApplicationGatewayTable 1 }

DPConfigWebApplicationGatewayEntry ::= SEQUENCE {
    dpConfigWebApplicationGatewayIndex    Unsigned32,
    dpConfigWebApplicationGatewayname    DisplayString
}

dpConfigWebApplicationGatewayIndex OBJECT-TYPE
    SYNTAX      Unsigned32
    MAX-ACCESS  read-only
    STATUS      current
    DESCRIPTION "No description yet."

    ::= { dpConfigWebApplicationGatewayEntry 1 }

dpConfigWebApplicationGatewayname OBJECT-TYPE
    SYNTAX      DisplayString
    MAX-ACCESS  read-only
    STATUS      current
    DESCRIPTION "No description yet."

    ::= { dpConfigWebApplicationGatewayEntry 2 }

--

dpConfigInteropServiceTable OBJECT-TYPE
    SYNTAX      SEQUENCE OF DPConfigInteropServiceEntry
    MAX-ACCESS  not-accessible
    STATUS      current
    DESCRIPTION
        "This page shows the configuration of the Interoperability Test Service.
        Interoperability Test Service is used to test stylesheets or maps. The
        service is available via HTTP or HTTPS, and it is disabled by default."

    ::= { dpConfig 249 }

dpConfigInteropServiceEntry OBJECT-TYPE
    SYNTAX      DPConfigInteropServiceEntry
    MAX-ACCESS  not-accessible
    STATUS      current
    DESCRIPTION "Table row."
    INDEX { dpConfigInteropServiceIndex, IMPLIED dpConfigInteropServicename }

    ::= { dpConfigInteropServiceTable 1 }

DPConfigInteropServiceEntry ::= SEQUENCE {
    dpConfigInteropServiceIndex    Unsigned32,
    dpConfigInteropServicename    DisplayString
}

dpConfigInteropServiceIndex OBJECT-TYPE
    SYNTAX      Unsigned32
    MAX-ACCESS  read-only
    STATUS      current
    DESCRIPTION "No description yet."

    ::= { dpConfigInteropServiceEntry 1 }

dpConfigInteropServicename OBJECT-TYPE
    SYNTAX      DisplayString
    MAX-ACCESS  read-only
    STATUS      current
    DESCRIPTION "No description yet."

    ::= { dpConfigInteropServiceEntry 2 }

--

dpConfigODRConnectorGroupTable OBJECT-TYPE
    SYNTAX      SEQUENCE OF DPConfigODRConnectorGroupEntry
    MAX-ACCESS  not-accessible
    STATUS      current
    DESCRIPTION
        "A collection of on demand router (ODR) connectors used to communicate with
        the Intelligent Management service."

    ::= { dpConfig 250 }

dpConfigODRConnectorGroupEntry OBJECT-TYPE
    SYNTAX      DPConfigODRConnectorGroupEntry
    MAX-ACCESS  not-accessible
    STATUS      current
    DESCRIPTION "Table row."
    INDEX { dpConfigODRConnectorGroupIndex, IMPLIED dpConfigODRConnectorGroupname }

    ::= { dpConfigODRConnectorGroupTable 1 }

DPConfigODRConnectorGroupEntry ::= SEQUENCE {
    dpConfigODRConnectorGroupIndex    Unsigned32,
    dpConfigODRConnectorGroupname    DisplayString
}

dpConfigODRConnectorGroupIndex OBJECT-TYPE
    SYNTAX      Unsigned32
    MAX-ACCESS  read-only
    STATUS      current
    DESCRIPTION "No description yet."

    ::= { dpConfigODRConnectorGroupEntry 1 }

dpConfigODRConnectorGroupname OBJECT-TYPE
    SYNTAX      DisplayString
    MAX-ACCESS  read-only
    STATUS      current
    DESCRIPTION "No description yet."

    ::= { dpConfigODRConnectorGroupEntry 2 }

--

dpConfigODRTable OBJECT-TYPE
    SYNTAX      SEQUENCE OF DPConfigODREntry
    MAX-ACCESS  not-accessible
    STATUS      current
    DESCRIPTION
        "Specifies an on demand router (ODR). The ODR feature acts as a collection
        of load balancer groups that distribute traffic to various clusters within
        a WebSphere cell or Liberty Collective. If multiple ODR connector groups
        are defined, the ODR distributes traffic to any of the clusters. The ODR
        feature on the DataPower Gateway supports a subset of On Demand Router in
        Intelligent Management."

    ::= { dpConfig 251 }

dpConfigODREntry OBJECT-TYPE
    SYNTAX      DPConfigODREntry
    MAX-ACCESS  not-accessible
    STATUS      current
    DESCRIPTION "Table row."
    INDEX { dpConfigODRIndex, IMPLIED dpConfigODRname }

    ::= { dpConfigODRTable 1 }

DPConfigODREntry ::= SEQUENCE {
    dpConfigODRIndex    Unsigned32,
    dpConfigODRname    DisplayString
}

dpConfigODRIndex OBJECT-TYPE
    SYNTAX      Unsigned32
    MAX-ACCESS  read-only
    STATUS      current
    DESCRIPTION "No description yet."

    ::= { dpConfigODREntry 1 }

dpConfigODRname OBJECT-TYPE
    SYNTAX      DisplayString
    MAX-ACCESS  read-only
    STATUS      current
    DESCRIPTION "No description yet."

    ::= { dpConfigODREntry 2 }

--

dpConfigSSLClientProfileTable OBJECT-TYPE
    SYNTAX      SEQUENCE OF DPConfigSSLClientProfileEntry
    MAX-ACCESS  not-accessible
    STATUS      current
    DESCRIPTION "Table."

    ::= { dpConfig 253 }

dpConfigSSLClientProfileEntry OBJECT-TYPE
    SYNTAX      DPConfigSSLClientProfileEntry
    MAX-ACCESS  not-accessible
    STATUS      current
    DESCRIPTION "Table row."
    INDEX { dpConfigSSLClientProfileIndex, IMPLIED dpConfigSSLClientProfilename }

    ::= { dpConfigSSLClientProfileTable 1 }

DPConfigSSLClientProfileEntry ::= SEQUENCE {
    dpConfigSSLClientProfileIndex    Unsigned32,
    dpConfigSSLClientProfilename    DisplayString
}

dpConfigSSLClientProfileIndex OBJECT-TYPE
    SYNTAX      Unsigned32
    MAX-ACCESS  read-only
    STATUS      current
    DESCRIPTION "No description yet."

    ::= { dpConfigSSLClientProfileEntry 1 }

dpConfigSSLClientProfilename OBJECT-TYPE
    SYNTAX      DisplayString
    MAX-ACCESS  read-only
    STATUS      current
    DESCRIPTION "No description yet."

    ::= { dpConfigSSLClientProfileEntry 2 }

--

dpConfigSSLServerProfileTable OBJECT-TYPE
    SYNTAX      SEQUENCE OF DPConfigSSLServerProfileEntry
    MAX-ACCESS  not-accessible
    STATUS      current
    DESCRIPTION "Table."

    ::= { dpConfig 254 }

dpConfigSSLServerProfileEntry OBJECT-TYPE
    SYNTAX      DPConfigSSLServerProfileEntry
    MAX-ACCESS  not-accessible
    STATUS      current
    DESCRIPTION "Table row."
    INDEX { dpConfigSSLServerProfileIndex, IMPLIED dpConfigSSLServerProfilename }

    ::= { dpConfigSSLServerProfileTable 1 }

DPConfigSSLServerProfileEntry ::= SEQUENCE {
    dpConfigSSLServerProfileIndex    Unsigned32,
    dpConfigSSLServerProfilename    DisplayString
}

dpConfigSSLServerProfileIndex OBJECT-TYPE
    SYNTAX      Unsigned32
    MAX-ACCESS  read-only
    STATUS      current
    DESCRIPTION "No description yet."

    ::= { dpConfigSSLServerProfileEntry 1 }

dpConfigSSLServerProfilename OBJECT-TYPE
    SYNTAX      DisplayString
    MAX-ACCESS  read-only
    STATUS      current
    DESCRIPTION "No description yet."

    ::= { dpConfigSSLServerProfileEntry 2 }

--

dpConfigSSLSNIMappingTable OBJECT-TYPE
    SYNTAX      SEQUENCE OF DPConfigSSLSNIMappingEntry
    MAX-ACCESS  not-accessible
    STATUS      current
    DESCRIPTION "Table."

    ::= { dpConfig 256 }

dpConfigSSLSNIMappingEntry OBJECT-TYPE
    SYNTAX      DPConfigSSLSNIMappingEntry
    MAX-ACCESS  not-accessible
    STATUS      current
    DESCRIPTION "Table row."
    INDEX { dpConfigSSLSNIMappingIndex, IMPLIED dpConfigSSLSNIMappingname }

    ::= { dpConfigSSLSNIMappingTable 1 }

DPConfigSSLSNIMappingEntry ::= SEQUENCE {
    dpConfigSSLSNIMappingIndex    Unsigned32,
    dpConfigSSLSNIMappingname    DisplayString
}

dpConfigSSLSNIMappingIndex OBJECT-TYPE
    SYNTAX      Unsigned32
    MAX-ACCESS  read-only
    STATUS      current
    DESCRIPTION "No description yet."

    ::= { dpConfigSSLSNIMappingEntry 1 }

dpConfigSSLSNIMappingname OBJECT-TYPE
    SYNTAX      DisplayString
    MAX-ACCESS  read-only
    STATUS      current
    DESCRIPTION "No description yet."

    ::= { dpConfigSSLSNIMappingEntry 2 }

--

dpConfigWebTokenServiceTable OBJECT-TYPE
    SYNTAX      SEQUENCE OF DPConfigWebTokenServiceEntry
    MAX-ACCESS  not-accessible
    STATUS      current
    DESCRIPTION
        "The web token service provides on-box HTTP services."

    ::= { dpConfig 266 }

dpConfigWebTokenServiceEntry OBJECT-TYPE
    SYNTAX      DPConfigWebTokenServiceEntry
    MAX-ACCESS  not-accessible
    STATUS      current
    DESCRIPTION "Table row."
    INDEX { dpConfigWebTokenServiceIndex, IMPLIED dpConfigWebTokenServicename }

    ::= { dpConfigWebTokenServiceTable 1 }

DPConfigWebTokenServiceEntry ::= SEQUENCE {
    dpConfigWebTokenServiceIndex    Unsigned32,
    dpConfigWebTokenServicename    DisplayString
}

dpConfigWebTokenServiceIndex OBJECT-TYPE
    SYNTAX      Unsigned32
    MAX-ACCESS  read-only
    STATUS      current
    DESCRIPTION "No description yet."

    ::= { dpConfigWebTokenServiceEntry 1 }

dpConfigWebTokenServicename OBJECT-TYPE
    SYNTAX      DisplayString
    MAX-ACCESS  read-only
    STATUS      current
    DESCRIPTION "No description yet."

    ::= { dpConfigWebTokenServiceEntry 2 }

--

dpConfigMessageContentFiltersTable OBJECT-TYPE
    SYNTAX      SEQUENCE OF DPConfigMessageContentFiltersEntry
    MAX-ACCESS  not-accessible
    STATUS      current
    DESCRIPTION
        "A Message Content Filters is a group of HTTP header-based and XPath-based
        filters. For HTTP header-based filters, the filter succeeds when the name
        and value of an HTTP header field match. For XPath-based filters, the
        filter succeeds when a document matches the element structure and content
        of the XPath expression and value."

    ::= { dpConfig 267 }

dpConfigMessageContentFiltersEntry OBJECT-TYPE
    SYNTAX      DPConfigMessageContentFiltersEntry
    MAX-ACCESS  not-accessible
    STATUS      current
    DESCRIPTION "Table row."
    INDEX { dpConfigMessageContentFiltersIndex, IMPLIED dpConfigMessageContentFiltersname }

    ::= { dpConfigMessageContentFiltersTable 1 }

DPConfigMessageContentFiltersEntry ::= SEQUENCE {
    dpConfigMessageContentFiltersIndex    Unsigned32,
    dpConfigMessageContentFiltersname    DisplayString
}

dpConfigMessageContentFiltersIndex OBJECT-TYPE
    SYNTAX      Unsigned32
    MAX-ACCESS  read-only
    STATUS      current
    DESCRIPTION "No description yet."

    ::= { dpConfigMessageContentFiltersEntry 1 }

dpConfigMessageContentFiltersname OBJECT-TYPE
    SYNTAX      DisplayString
    MAX-ACCESS  read-only
    STATUS      current
    DESCRIPTION "No description yet."

    ::= { dpConfigMessageContentFiltersEntry 2 }

--

dpConfigMCFBaseTable OBJECT-TYPE
    SYNTAX      SEQUENCE OF DPConfigMCFBaseEntry
    MAX-ACCESS  not-accessible
    STATUS      current
    DESCRIPTION "Table."

    ::= { dpConfig 268 }

dpConfigMCFBaseEntry OBJECT-TYPE
    SYNTAX      DPConfigMCFBaseEntry
    MAX-ACCESS  not-accessible
    STATUS      current
    DESCRIPTION "Table row."
    INDEX { dpConfigMCFBaseIndex, IMPLIED dpConfigMCFBasename }

    ::= { dpConfigMCFBaseTable 1 }

DPConfigMCFBaseEntry ::= SEQUENCE {
    dpConfigMCFBaseIndex    Unsigned32,
    dpConfigMCFBasename    DisplayString
}

dpConfigMCFBaseIndex OBJECT-TYPE
    SYNTAX      Unsigned32
    MAX-ACCESS  read-only
    STATUS      current
    DESCRIPTION "No description yet."

    ::= { dpConfigMCFBaseEntry 1 }

dpConfigMCFBasename OBJECT-TYPE
    SYNTAX      DisplayString
    MAX-ACCESS  read-only
    STATUS      current
    DESCRIPTION "No description yet."

    ::= { dpConfigMCFBaseEntry 2 }

--

dpConfigMCFHttpHeaderTable OBJECT-TYPE
    SYNTAX      SEQUENCE OF DPConfigMCFHttpHeaderEntry
    MAX-ACCESS  not-accessible
    STATUS      current
    DESCRIPTION
        "Filter based on HTTP header. A specific header value is used to match the
        request message."

    ::= { dpConfig 269 }

dpConfigMCFHttpHeaderEntry OBJECT-TYPE
    SYNTAX      DPConfigMCFHttpHeaderEntry
    MAX-ACCESS  not-accessible
    STATUS      current
    DESCRIPTION "Table row."
    INDEX { dpConfigMCFHttpHeaderIndex, IMPLIED dpConfigMCFHttpHeadername }

    ::= { dpConfigMCFHttpHeaderTable 1 }

DPConfigMCFHttpHeaderEntry ::= SEQUENCE {
    dpConfigMCFHttpHeaderIndex    Unsigned32,
    dpConfigMCFHttpHeadername    DisplayString
}

dpConfigMCFHttpHeaderIndex OBJECT-TYPE
    SYNTAX      Unsigned32
    MAX-ACCESS  read-only
    STATUS      current
    DESCRIPTION "No description yet."

    ::= { dpConfigMCFHttpHeaderEntry 1 }

dpConfigMCFHttpHeadername OBJECT-TYPE
    SYNTAX      DisplayString
    MAX-ACCESS  read-only
    STATUS      current
    DESCRIPTION "No description yet."

    ::= { dpConfigMCFHttpHeaderEntry 2 }

--

dpConfigMCFXPathTable OBJECT-TYPE
    SYNTAX      SEQUENCE OF DPConfigMCFXPathEntry
    MAX-ACCESS  not-accessible
    STATUS      current
    DESCRIPTION
        "Filter based on specific data in the message. An XPath expression defines
        a data element to be matched in the request message."

    ::= { dpConfig 270 }

dpConfigMCFXPathEntry OBJECT-TYPE
    SYNTAX      DPConfigMCFXPathEntry
    MAX-ACCESS  not-accessible
    STATUS      current
    DESCRIPTION "Table row."
    INDEX { dpConfigMCFXPathIndex, IMPLIED dpConfigMCFXPathname }

    ::= { dpConfigMCFXPathTable 1 }

DPConfigMCFXPathEntry ::= SEQUENCE {
    dpConfigMCFXPathIndex    Unsigned32,
    dpConfigMCFXPathname    DisplayString
}

dpConfigMCFXPathIndex OBJECT-TYPE
    SYNTAX      Unsigned32
    MAX-ACCESS  read-only
    STATUS      current
    DESCRIPTION "No description yet."

    ::= { dpConfigMCFXPathEntry 1 }

dpConfigMCFXPathname OBJECT-TYPE
    SYNTAX      DisplayString
    MAX-ACCESS  read-only
    STATUS      current
    DESCRIPTION "No description yet."

    ::= { dpConfigMCFXPathEntry 2 }

--

dpConfigMCFHttpURLTable OBJECT-TYPE
    SYNTAX      SEQUENCE OF DPConfigMCFHttpURLEntry
    MAX-ACCESS  not-accessible
    STATUS      current
    DESCRIPTION
        "Filter based on the request URL. The filter value is matched to the
        request URL."

    ::= { dpConfig 271 }

dpConfigMCFHttpURLEntry OBJECT-TYPE
    SYNTAX      DPConfigMCFHttpURLEntry
    MAX-ACCESS  not-accessible
    STATUS      current
    DESCRIPTION "Table row."
    INDEX { dpConfigMCFHttpURLIndex, IMPLIED dpConfigMCFHttpURLname }

    ::= { dpConfigMCFHttpURLTable 1 }

DPConfigMCFHttpURLEntry ::= SEQUENCE {
    dpConfigMCFHttpURLIndex    Unsigned32,
    dpConfigMCFHttpURLname    DisplayString
}

dpConfigMCFHttpURLIndex OBJECT-TYPE
    SYNTAX      Unsigned32
    MAX-ACCESS  read-only
    STATUS      current
    DESCRIPTION "No description yet."

    ::= { dpConfigMCFHttpURLEntry 1 }

dpConfigMCFHttpURLname OBJECT-TYPE
    SYNTAX      DisplayString
    MAX-ACCESS  read-only
    STATUS      current
    DESCRIPTION "No description yet."

    ::= { dpConfigMCFHttpURLEntry 2 }

--

dpConfigMCFHttpMethodTable OBJECT-TYPE
    SYNTAX      SEQUENCE OF DPConfigMCFHttpMethodEntry
    MAX-ACCESS  not-accessible
    STATUS      current
    DESCRIPTION
        "Filter based on the HTTP method. The filter value is matched to the HTTP
        method in the request message."

    ::= { dpConfig 272 }

dpConfigMCFHttpMethodEntry OBJECT-TYPE
    SYNTAX      DPConfigMCFHttpMethodEntry
    MAX-ACCESS  not-accessible
    STATUS      current
    DESCRIPTION "Table row."
    INDEX { dpConfigMCFHttpMethodIndex, IMPLIED dpConfigMCFHttpMethodname }

    ::= { dpConfigMCFHttpMethodTable 1 }

DPConfigMCFHttpMethodEntry ::= SEQUENCE {
    dpConfigMCFHttpMethodIndex    Unsigned32,
    dpConfigMCFHttpMethodname    DisplayString
}

dpConfigMCFHttpMethodIndex OBJECT-TYPE
    SYNTAX      Unsigned32
    MAX-ACCESS  read-only
    STATUS      current
    DESCRIPTION "No description yet."

    ::= { dpConfigMCFHttpMethodEntry 1 }

dpConfigMCFHttpMethodname OBJECT-TYPE
    SYNTAX      DisplayString
    MAX-ACCESS  read-only
    STATUS      current
    DESCRIPTION "No description yet."

    ::= { dpConfigMCFHttpMethodEntry 2 }

--

dpConfigIMSCalloutSourceProtocolHandlerTable OBJECT-TYPE
    SYNTAX      SEQUENCE OF DPConfigIMSCalloutSourceProtocolHandlerEntry
    MAX-ACCESS  not-accessible
    STATUS      current
    DESCRIPTION
        "An IMS Callout handler allows a Multi-Protocol Gateway to make
        asynchronous requests to an IMS application with the ICAL protocol. An IMS
        handler can retrieve IMS Callout messages from an IMS application and send
        response data to the IMS application."

    ::= { dpConfig 273 }

dpConfigIMSCalloutSourceProtocolHandlerEntry OBJECT-TYPE
    SYNTAX      DPConfigIMSCalloutSourceProtocolHandlerEntry
    MAX-ACCESS  not-accessible
    STATUS      current
    DESCRIPTION "Table row."
    INDEX { dpConfigIMSCalloutSourceProtocolHandlerIndex, IMPLIED dpConfigIMSCalloutSourceProtocolHandlername }

    ::= { dpConfigIMSCalloutSourceProtocolHandlerTable 1 }

DPConfigIMSCalloutSourceProtocolHandlerEntry ::= SEQUENCE {
    dpConfigIMSCalloutSourceProtocolHandlerIndex    Unsigned32,
    dpConfigIMSCalloutSourceProtocolHandlername    DisplayString
}

dpConfigIMSCalloutSourceProtocolHandlerIndex OBJECT-TYPE
    SYNTAX      Unsigned32
    MAX-ACCESS  read-only
    STATUS      current
    DESCRIPTION "No description yet."

    ::= { dpConfigIMSCalloutSourceProtocolHandlerEntry 1 }

dpConfigIMSCalloutSourceProtocolHandlername OBJECT-TYPE
    SYNTAX      DisplayString
    MAX-ACCESS  read-only
    STATUS      current
    DESCRIPTION "No description yet."

    ::= { dpConfigIMSCalloutSourceProtocolHandlerEntry 2 }

--

dpConfigPatternTable OBJECT-TYPE
    SYNTAX      SEQUENCE OF DPConfigPatternEntry
    MAX-ACCESS  not-accessible
    STATUS      current
    DESCRIPTION
        "Patterns simplify service creation by enabling you to create services from
        reusing predefined configurations with minimum customized inputs."

    ::= { dpConfig 274 }

dpConfigPatternEntry OBJECT-TYPE
    SYNTAX      DPConfigPatternEntry
    MAX-ACCESS  not-accessible
    STATUS      current
    DESCRIPTION "Table row."
    INDEX { dpConfigPatternIndex, IMPLIED dpConfigPatternname }

    ::= { dpConfigPatternTable 1 }

DPConfigPatternEntry ::= SEQUENCE {
    dpConfigPatternIndex    Unsigned32,
    dpConfigPatternname    DisplayString
}

dpConfigPatternIndex OBJECT-TYPE
    SYNTAX      Unsigned32
    MAX-ACCESS  read-only
    STATUS      current
    DESCRIPTION "No description yet."

    ::= { dpConfigPatternEntry 1 }

dpConfigPatternname OBJECT-TYPE
    SYNTAX      DisplayString
    MAX-ACCESS  read-only
    STATUS      current
    DESCRIPTION "No description yet."

    ::= { dpConfigPatternEntry 2 }

--

dpConfigMCFCustomRuleTable OBJECT-TYPE
    SYNTAX      SEQUENCE OF DPConfigMCFCustomRuleEntry
    MAX-ACCESS  not-accessible
    STATUS      current
    DESCRIPTION
        "A custom message content filter calls a processing rule to retrieve a
        specified value. The filter value is matched to the contents of variable
        'var://context/policy/mcf/RULE-NAME'"

    ::= { dpConfig 275 }

dpConfigMCFCustomRuleEntry OBJECT-TYPE
    SYNTAX      DPConfigMCFCustomRuleEntry
    MAX-ACCESS  not-accessible
    STATUS      current
    DESCRIPTION "Table row."
    INDEX { dpConfigMCFCustomRuleIndex, IMPLIED dpConfigMCFCustomRulename }

    ::= { dpConfigMCFCustomRuleTable 1 }

DPConfigMCFCustomRuleEntry ::= SEQUENCE {
    dpConfigMCFCustomRuleIndex    Unsigned32,
    dpConfigMCFCustomRulename    DisplayString
}

dpConfigMCFCustomRuleIndex OBJECT-TYPE
    SYNTAX      Unsigned32
    MAX-ACCESS  read-only
    STATUS      current
    DESCRIPTION "No description yet."

    ::= { dpConfigMCFCustomRuleEntry 1 }

dpConfigMCFCustomRulename OBJECT-TYPE
    SYNTAX      DisplayString
    MAX-ACCESS  read-only
    STATUS      current
    DESCRIPTION "No description yet."

    ::= { dpConfigMCFCustomRuleEntry 2 }

--

dpConfigAS2ProxySourceProtocolHandlerTable OBJECT-TYPE
    SYNTAX      SEQUENCE OF DPConfigAS2ProxySourceProtocolHandlerEntry
    MAX-ACCESS  not-accessible
    STATUS      current
    DESCRIPTION
        "A MEIG AS2 proxy handler receives AS2 requests over HTTP or HTTPS and
        forwards them to the backend which is assumed to be an IBM
        Multi-Enterprise Integration Gateway (MEIG) server. AS2 proxy handlers
        conform to gateway specifications of RFC 2616 and AS2 specification of RFC
        4130."

    ::= { dpConfig 277 }

dpConfigAS2ProxySourceProtocolHandlerEntry OBJECT-TYPE
    SYNTAX      DPConfigAS2ProxySourceProtocolHandlerEntry
    MAX-ACCESS  not-accessible
    STATUS      current
    DESCRIPTION "Table row."
    INDEX { dpConfigAS2ProxySourceProtocolHandlerIndex, IMPLIED dpConfigAS2ProxySourceProtocolHandlername }

    ::= { dpConfigAS2ProxySourceProtocolHandlerTable 1 }

DPConfigAS2ProxySourceProtocolHandlerEntry ::= SEQUENCE {
    dpConfigAS2ProxySourceProtocolHandlerIndex    Unsigned32,
    dpConfigAS2ProxySourceProtocolHandlername    DisplayString
}

dpConfigAS2ProxySourceProtocolHandlerIndex OBJECT-TYPE
    SYNTAX      Unsigned32
    MAX-ACCESS  read-only
    STATUS      current
    DESCRIPTION "No description yet."

    ::= { dpConfigAS2ProxySourceProtocolHandlerEntry 1 }

dpConfigAS2ProxySourceProtocolHandlername OBJECT-TYPE
    SYNTAX      DisplayString
    MAX-ACCESS  read-only
    STATUS      current
    DESCRIPTION "No description yet."

    ::= { dpConfigAS2ProxySourceProtocolHandlerEntry 2 }

--

dpConfigLunaTable OBJECT-TYPE
    SYNTAX      SEQUENCE OF DPConfigLunaEntry
    MAX-ACCESS  not-accessible
    STATUS      current
    DESCRIPTION
        "You can use a network-attached SafeNet Luna Network HSM appliance as the
        HSM to provide secure storage for RSA keys and accelerate RSA operations
        remotely. The configuration of the Luna HSM sets up the connection between
        the DataPower Gateway and the Luna HSM."

    ::= { dpConfig 278 }

dpConfigLunaEntry OBJECT-TYPE
    SYNTAX      DPConfigLunaEntry
    MAX-ACCESS  not-accessible
    STATUS      current
    DESCRIPTION "Table row."
    INDEX { dpConfigLunaIndex, IMPLIED dpConfigLunaname }

    ::= { dpConfigLunaTable 1 }

DPConfigLunaEntry ::= SEQUENCE {
    dpConfigLunaIndex    Unsigned32,
    dpConfigLunaname    DisplayString
}

dpConfigLunaIndex OBJECT-TYPE
    SYNTAX      Unsigned32
    MAX-ACCESS  read-only
    STATUS      current
    DESCRIPTION "No description yet."

    ::= { dpConfigLunaEntry 1 }

dpConfigLunaname OBJECT-TYPE
    SYNTAX      DisplayString
    MAX-ACCESS  read-only
    STATUS      current
    DESCRIPTION "No description yet."

    ::= { dpConfigLunaEntry 2 }

--

dpConfigLunaPartitionTable OBJECT-TYPE
    SYNTAX      SEQUENCE OF DPConfigLunaPartitionEntry
    MAX-ACCESS  not-accessible
    STATUS      current
    DESCRIPTION
        "The SafeNet Luna Network HSM appliance stores the RSA keys in independent
        partitions. The configuration of the Luna HSM partition specifies the
        partition that the DataPower Gateway accesses in the Luna HSM."

    ::= { dpConfig 279 }

dpConfigLunaPartitionEntry OBJECT-TYPE
    SYNTAX      DPConfigLunaPartitionEntry
    MAX-ACCESS  not-accessible
    STATUS      current
    DESCRIPTION "Table row."
    INDEX { dpConfigLunaPartitionIndex, IMPLIED dpConfigLunaPartitionname }

    ::= { dpConfigLunaPartitionTable 1 }

DPConfigLunaPartitionEntry ::= SEQUENCE {
    dpConfigLunaPartitionIndex    Unsigned32,
    dpConfigLunaPartitionname    DisplayString
}

dpConfigLunaPartitionIndex OBJECT-TYPE
    SYNTAX      Unsigned32
    MAX-ACCESS  read-only
    STATUS      current
    DESCRIPTION "No description yet."

    ::= { dpConfigLunaPartitionEntry 1 }

dpConfigLunaPartitionname OBJECT-TYPE
    SYNTAX      DisplayString
    MAX-ACCESS  read-only
    STATUS      current
    DESCRIPTION "No description yet."

    ::= { dpConfigLunaPartitionEntry 2 }

--

dpConfigConfigSequenceTable OBJECT-TYPE
    SYNTAX      SEQUENCE OF DPConfigConfigSequenceEntry
    MAX-ACCESS  not-accessible
    STATUS      current
    DESCRIPTION
        "A sequence of configuration files to load after the start-up
        configuration. By default, changes on the configuration files are
        automatically detected and reloaded."

    ::= { dpConfig 280 }

dpConfigConfigSequenceEntry OBJECT-TYPE
    SYNTAX      DPConfigConfigSequenceEntry
    MAX-ACCESS  not-accessible
    STATUS      current
    DESCRIPTION "Table row."
    INDEX { dpConfigConfigSequenceIndex, IMPLIED dpConfigConfigSequencename }

    ::= { dpConfigConfigSequenceTable 1 }

DPConfigConfigSequenceEntry ::= SEQUENCE {
    dpConfigConfigSequenceIndex    Unsigned32,
    dpConfigConfigSequencename    DisplayString
}

dpConfigConfigSequenceIndex OBJECT-TYPE
    SYNTAX      Unsigned32
    MAX-ACCESS  read-only
    STATUS      current
    DESCRIPTION "No description yet."

    ::= { dpConfigConfigSequenceEntry 1 }

dpConfigConfigSequencename OBJECT-TYPE
    SYNTAX      DisplayString
    MAX-ACCESS  read-only
    STATUS      current
    DESCRIPTION "No description yet."

    ::= { dpConfigConfigSequenceEntry 2 }

--

dpConfigLunaHAGroupTable OBJECT-TYPE
    SYNTAX      SEQUENCE OF DPConfigLunaHAGroupEntry
    MAX-ACCESS  not-accessible
    STATUS      current
    DESCRIPTION
        "An HA group on the SafeNet Luna Network HSM appliance allows you to define
        multiple Luna HSM partitions as a group for load balancing and failover."

    ::= { dpConfig 285 }

dpConfigLunaHAGroupEntry OBJECT-TYPE
    SYNTAX      DPConfigLunaHAGroupEntry
    MAX-ACCESS  not-accessible
    STATUS      current
    DESCRIPTION "Table row."
    INDEX { dpConfigLunaHAGroupIndex, IMPLIED dpConfigLunaHAGroupname }

    ::= { dpConfigLunaHAGroupTable 1 }

DPConfigLunaHAGroupEntry ::= SEQUENCE {
    dpConfigLunaHAGroupIndex    Unsigned32,
    dpConfigLunaHAGroupname    DisplayString
}

dpConfigLunaHAGroupIndex OBJECT-TYPE
    SYNTAX      Unsigned32
    MAX-ACCESS  read-only
    STATUS      current
    DESCRIPTION "No description yet."

    ::= { dpConfigLunaHAGroupEntry 1 }

dpConfigLunaHAGroupname OBJECT-TYPE
    SYNTAX      DisplayString
    MAX-ACCESS  read-only
    STATUS      current
    DESCRIPTION "No description yet."

    ::= { dpConfigLunaHAGroupEntry 2 }

--

dpConfigLunaHASettingsTable OBJECT-TYPE
    SYNTAX      SEQUENCE OF DPConfigLunaHASettingsEntry
    MAX-ACCESS  not-accessible
    STATUS      current
    DESCRIPTION
        "Defines the high availability (HA) settings for the SafeNet Luna Network
        HSM HA group."

    ::= { dpConfig 286 }

dpConfigLunaHASettingsEntry OBJECT-TYPE
    SYNTAX      DPConfigLunaHASettingsEntry
    MAX-ACCESS  not-accessible
    STATUS      current
    DESCRIPTION "Table row."
    INDEX { dpConfigLunaHASettingsIndex, IMPLIED dpConfigLunaHASettingsname }

    ::= { dpConfigLunaHASettingsTable 1 }

DPConfigLunaHASettingsEntry ::= SEQUENCE {
    dpConfigLunaHASettingsIndex    Unsigned32,
    dpConfigLunaHASettingsname    DisplayString
}

dpConfigLunaHASettingsIndex OBJECT-TYPE
    SYNTAX      Unsigned32
    MAX-ACCESS  read-only
    STATUS      current
    DESCRIPTION "No description yet."

    ::= { dpConfigLunaHASettingsEntry 1 }

dpConfigLunaHASettingsname OBJECT-TYPE
    SYNTAX      DisplayString
    MAX-ACCESS  read-only
    STATUS      current
    DESCRIPTION "No description yet."

    ::= { dpConfigLunaHASettingsEntry 2 }

--

dpConfigWAXHNProxyTable OBJECT-TYPE
    SYNTAX      SEQUENCE OF DPConfigWAXHNProxyEntry
    MAX-ACCESS  not-accessible
    STATUS      current
    DESCRIPTION
        "WebSphere Application Acceleration for Hybrid Networks (WAXHN). Configure
        the WAXHN application proxy before you activate the WAXHN feature. The DNS
        settings must be configured before you activate the WAXHN feature. The
        WAXHN application proxy must be in a down operational state until you
        activate the feature."

    ::= { dpConfig 300 }

dpConfigWAXHNProxyEntry OBJECT-TYPE
    SYNTAX      DPConfigWAXHNProxyEntry
    MAX-ACCESS  not-accessible
    STATUS      current
    DESCRIPTION "Table row."
    INDEX { dpConfigWAXHNProxyIndex, IMPLIED dpConfigWAXHNProxyname }

    ::= { dpConfigWAXHNProxyTable 1 }

DPConfigWAXHNProxyEntry ::= SEQUENCE {
    dpConfigWAXHNProxyIndex    Unsigned32,
    dpConfigWAXHNProxyname    DisplayString
}

dpConfigWAXHNProxyIndex OBJECT-TYPE
    SYNTAX      Unsigned32
    MAX-ACCESS  read-only
    STATUS      current
    DESCRIPTION "No description yet."

    ::= { dpConfigWAXHNProxyEntry 1 }

dpConfigWAXHNProxyname OBJECT-TYPE
    SYNTAX      DisplayString
    MAX-ACCESS  read-only
    STATUS      current
    DESCRIPTION "No description yet."

    ::= { dpConfigWAXHNProxyEntry 2 }

--

dpConfigHNApplicationTable OBJECT-TYPE
    SYNTAX      SEQUENCE OF DPConfigHNApplicationEntry
    MAX-ACCESS  not-accessible
    STATUS      current
    DESCRIPTION
        "Specifies the applications accelerated as part of the WebSphere
        Application Accelerator for Hybrid Networks (WAXHN)."

    ::= { dpConfig 301 }

dpConfigHNApplicationEntry OBJECT-TYPE
    SYNTAX      DPConfigHNApplicationEntry
    MAX-ACCESS  not-accessible
    STATUS      current
    DESCRIPTION "Table row."
    INDEX { dpConfigHNApplicationIndex, IMPLIED dpConfigHNApplicationname }

    ::= { dpConfigHNApplicationTable 1 }

DPConfigHNApplicationEntry ::= SEQUENCE {
    dpConfigHNApplicationIndex    Unsigned32,
    dpConfigHNApplicationname    DisplayString
}

dpConfigHNApplicationIndex OBJECT-TYPE
    SYNTAX      Unsigned32
    MAX-ACCESS  read-only
    STATUS      current
    DESCRIPTION "No description yet."

    ::= { dpConfigHNApplicationEntry 1 }

dpConfigHNApplicationname OBJECT-TYPE
    SYNTAX      DisplayString
    MAX-ACCESS  read-only
    STATUS      current
    DESCRIPTION "No description yet."

    ::= { dpConfigHNApplicationEntry 2 }

--

dpConfigCloudGatewayServiceTable OBJECT-TYPE
    SYNTAX      SEQUENCE OF DPConfigCloudGatewayServiceEntry
    MAX-ACCESS  not-accessible
    STATUS      current
    DESCRIPTION
        "Cloud Gateway services are used with IBM Cloud Integration Services to
        secure traffic from cloud-based applications to enterprise applications or
        data sources. The Cloud Gateway service requires an SSL proxy profile that
        defines the secure communication from the cloud into the enterprise
        network or DMZ. You must use SSL/TLS between the cloud-based client and
        its Cloud Gateway, and you must define the SSL proxy profile as reverse,
        otherwise the connection establishment fails. The SSL proxy profile
        references a Crypto Profile that includes both Identification Credentials
        and Validation Credentials. The Identification Credentials provide the
        private key and certificate that is associated with the gateway, and the
        Validation Credentials provide the certificate from the cloud. There can
        be multiple cloud certificates in the gateway's Validation Credentials,
        which allow multiple clouds to connect to a single gateway. Each Cloud
        Gateway service must have one or more enterprise applications defined.
        When a cloud-based client establishes a connection to a Cloud Gateway
        service, the client identifies which enterprise application to connect to
        using the service name."

    ::= { dpConfig 302 }

dpConfigCloudGatewayServiceEntry OBJECT-TYPE
    SYNTAX      DPConfigCloudGatewayServiceEntry
    MAX-ACCESS  not-accessible
    STATUS      current
    DESCRIPTION "Table row."
    INDEX { dpConfigCloudGatewayServiceIndex, IMPLIED dpConfigCloudGatewayServicename }

    ::= { dpConfigCloudGatewayServiceTable 1 }

DPConfigCloudGatewayServiceEntry ::= SEQUENCE {
    dpConfigCloudGatewayServiceIndex    Unsigned32,
    dpConfigCloudGatewayServicename    DisplayString
}

dpConfigCloudGatewayServiceIndex OBJECT-TYPE
    SYNTAX      Unsigned32
    MAX-ACCESS  read-only
    STATUS      current
    DESCRIPTION "No description yet."

    ::= { dpConfigCloudGatewayServiceEntry 1 }

dpConfigCloudGatewayServicename OBJECT-TYPE
    SYNTAX      DisplayString
    MAX-ACCESS  read-only
    STATUS      current
    DESCRIPTION "No description yet."

    ::= { dpConfigCloudGatewayServiceEntry 2 }

--

dpConfigCloudConnectorServiceTable OBJECT-TYPE
    SYNTAX      SEQUENCE OF DPConfigCloudConnectorServiceEntry
    MAX-ACCESS  not-accessible
    STATUS      current
    DESCRIPTION
        "Creates a Cloud Connector service, which is a type of SSL forwarder. This
        service can be used with a Cloud Gateway Service to secure traffic from
        cloud-based clients to enterprise applications. This service requires an
        SSL proxy profile that defines the connections for secure communication.
        You must use SSL between the Cloud Connector and its Cloud Gateway,
        otherwise connection establishment will fail. If the SSL proxy profile is
        defined as forward, the data is secured toward the Cloud Gateway, but is
        not secured toward the client. If the SSL proxy profile is defined as
        reverse, the connection will fail. If the SSL proxy profile is defined as
        two way, the data is secured in both directions."

    ::= { dpConfig 303 }

dpConfigCloudConnectorServiceEntry OBJECT-TYPE
    SYNTAX      DPConfigCloudConnectorServiceEntry
    MAX-ACCESS  not-accessible
    STATUS      current
    DESCRIPTION "Table row."
    INDEX { dpConfigCloudConnectorServiceIndex, IMPLIED dpConfigCloudConnectorServicename }

    ::= { dpConfigCloudConnectorServiceTable 1 }

DPConfigCloudConnectorServiceEntry ::= SEQUENCE {
    dpConfigCloudConnectorServiceIndex    Unsigned32,
    dpConfigCloudConnectorServicename    DisplayString
}

dpConfigCloudConnectorServiceIndex OBJECT-TYPE
    SYNTAX      Unsigned32
    MAX-ACCESS  read-only
    STATUS      current
    DESCRIPTION "No description yet."

    ::= { dpConfigCloudConnectorServiceEntry 1 }

dpConfigCloudConnectorServicename OBJECT-TYPE
    SYNTAX      DisplayString
    MAX-ACCESS  read-only
    STATUS      current
    DESCRIPTION "No description yet."

    ::= { dpConfigCloudConnectorServiceEntry 2 }

--

dpConfigJSONSettingsTable OBJECT-TYPE
    SYNTAX      SEQUENCE OF DPConfigJSONSettingsEntry
    MAX-ACCESS  not-accessible
    STATUS      current
    DESCRIPTION
        "The JSON settings specify constraints for parsing JSON messages. JSON
        settings work in conjunction with the parser limits specified in the XML
        Manager. The more restrictive limits apply."

    ::= { dpConfig 308 }

dpConfigJSONSettingsEntry OBJECT-TYPE
    SYNTAX      DPConfigJSONSettingsEntry
    MAX-ACCESS  not-accessible
    STATUS      current
    DESCRIPTION "Table row."
    INDEX { dpConfigJSONSettingsIndex, IMPLIED dpConfigJSONSettingsname }

    ::= { dpConfigJSONSettingsTable 1 }

DPConfigJSONSettingsEntry ::= SEQUENCE {
    dpConfigJSONSettingsIndex    Unsigned32,
    dpConfigJSONSettingsname    DisplayString
}

dpConfigJSONSettingsIndex OBJECT-TYPE
    SYNTAX      Unsigned32
    MAX-ACCESS  read-only
    STATUS      current
    DESCRIPTION "No description yet."

    ::= { dpConfigJSONSettingsEntry 1 }

dpConfigJSONSettingsname OBJECT-TYPE
    SYNTAX      DisplayString
    MAX-ACCESS  read-only
    STATUS      current
    DESCRIPTION "No description yet."

    ::= { dpConfigJSONSettingsEntry 2 }

--

dpConfigIPMulticastTable OBJECT-TYPE
    SYNTAX      SEQUENCE OF DPConfigIPMulticastEntry
    MAX-ACCESS  not-accessible
    STATUS      current
    DESCRIPTION
        "IP Multicast mode defines the properties for the multicast configuration
        used to transmit and receive peering update messages."

    ::= { dpConfig 309 }

dpConfigIPMulticastEntry OBJECT-TYPE
    SYNTAX      DPConfigIPMulticastEntry
    MAX-ACCESS  not-accessible
    STATUS      current
    DESCRIPTION "Table row."
    INDEX { dpConfigIPMulticastIndex, IMPLIED dpConfigIPMulticastname }

    ::= { dpConfigIPMulticastTable 1 }

DPConfigIPMulticastEntry ::= SEQUENCE {
    dpConfigIPMulticastIndex    Unsigned32,
    dpConfigIPMulticastname    DisplayString
}

dpConfigIPMulticastIndex OBJECT-TYPE
    SYNTAX      Unsigned32
    MAX-ACCESS  read-only
    STATUS      current
    DESCRIPTION "No description yet."

    ::= { dpConfigIPMulticastEntry 1 }

dpConfigIPMulticastname OBJECT-TYPE
    SYNTAX      DisplayString
    MAX-ACCESS  read-only
    STATUS      current
    DESCRIPTION "No description yet."

    ::= { dpConfigIPMulticastEntry 2 }

--

dpConfigDeploymentPolicyParametersBindingTable OBJECT-TYPE
    SYNTAX      SEQUENCE OF DPConfigDeploymentPolicyParametersBindingEntry
    MAX-ACCESS  not-accessible
    STATUS      current
    DESCRIPTION
        "Configuration to persist the values of the deployment policy variables."

    ::= { dpConfig 310 }

dpConfigDeploymentPolicyParametersBindingEntry OBJECT-TYPE
    SYNTAX      DPConfigDeploymentPolicyParametersBindingEntry
    MAX-ACCESS  not-accessible
    STATUS      current
    DESCRIPTION "Table row."
    INDEX { dpConfigDeploymentPolicyParametersBindingIndex, IMPLIED dpConfigDeploymentPolicyParametersBindingname }

    ::= { dpConfigDeploymentPolicyParametersBindingTable 1 }

DPConfigDeploymentPolicyParametersBindingEntry ::= SEQUENCE {
    dpConfigDeploymentPolicyParametersBindingIndex    Unsigned32,
    dpConfigDeploymentPolicyParametersBindingname    DisplayString
}

dpConfigDeploymentPolicyParametersBindingIndex OBJECT-TYPE
    SYNTAX      Unsigned32
    MAX-ACCESS  read-only
    STATUS      current
    DESCRIPTION "No description yet."

    ::= { dpConfigDeploymentPolicyParametersBindingEntry 1 }

dpConfigDeploymentPolicyParametersBindingname OBJECT-TYPE
    SYNTAX      DisplayString
    MAX-ACCESS  read-only
    STATUS      current
    DESCRIPTION "No description yet."

    ::= { dpConfigDeploymentPolicyParametersBindingEntry 2 }

--

dpConfigLDAPConnectionPoolTable OBJECT-TYPE
    SYNTAX      SEQUENCE OF DPConfigLDAPConnectionPoolEntry
    MAX-ACCESS  not-accessible
    STATUS      current
    DESCRIPTION
        "The LDAP Connection Pool settings specify the LDAP connection pool to use."

    ::= { dpConfig 311 }

dpConfigLDAPConnectionPoolEntry OBJECT-TYPE
    SYNTAX      DPConfigLDAPConnectionPoolEntry
    MAX-ACCESS  not-accessible
    STATUS      current
    DESCRIPTION "Table row."
    INDEX { dpConfigLDAPConnectionPoolIndex, IMPLIED dpConfigLDAPConnectionPoolname }

    ::= { dpConfigLDAPConnectionPoolTable 1 }

DPConfigLDAPConnectionPoolEntry ::= SEQUENCE {
    dpConfigLDAPConnectionPoolIndex    Unsigned32,
    dpConfigLDAPConnectionPoolname    DisplayString
}

dpConfigLDAPConnectionPoolIndex OBJECT-TYPE
    SYNTAX      Unsigned32
    MAX-ACCESS  read-only
    STATUS      current
    DESCRIPTION "No description yet."

    ::= { dpConfigLDAPConnectionPoolEntry 1 }

dpConfigLDAPConnectionPoolname OBJECT-TYPE
    SYNTAX      DisplayString
    MAX-ACCESS  read-only
    STATUS      current
    DESCRIPTION "No description yet."

    ::= { dpConfigLDAPConnectionPoolEntry 2 }

--

dpConfigMPGWErrorHandlingPolicyTable OBJECT-TYPE
    SYNTAX      SEQUENCE OF DPConfigMPGWErrorHandlingPolicyEntry
    MAX-ACCESS  not-accessible
    STATUS      current
    DESCRIPTION
        "A Multi-Protocol gateway error policy consists of one or more error
        actions. A service runs an error action depending on whether or not a
        corresponding matching rule selects the action for processing. A service
        can have one policy active at a time. When an error occurs in the
        Multi-Protocol Gateway from an HTTP or HTTPS request flow and no precedent
        error handler handles the error, the service calls the error policy."

    ::= { dpConfig 312 }

dpConfigMPGWErrorHandlingPolicyEntry OBJECT-TYPE
    SYNTAX      DPConfigMPGWErrorHandlingPolicyEntry
    MAX-ACCESS  not-accessible
    STATUS      current
    DESCRIPTION "Table row."
    INDEX { dpConfigMPGWErrorHandlingPolicyIndex, IMPLIED dpConfigMPGWErrorHandlingPolicyname }

    ::= { dpConfigMPGWErrorHandlingPolicyTable 1 }

DPConfigMPGWErrorHandlingPolicyEntry ::= SEQUENCE {
    dpConfigMPGWErrorHandlingPolicyIndex    Unsigned32,
    dpConfigMPGWErrorHandlingPolicyname    DisplayString
}

dpConfigMPGWErrorHandlingPolicyIndex OBJECT-TYPE
    SYNTAX      Unsigned32
    MAX-ACCESS  read-only
    STATUS      current
    DESCRIPTION "No description yet."

    ::= { dpConfigMPGWErrorHandlingPolicyEntry 1 }

dpConfigMPGWErrorHandlingPolicyname OBJECT-TYPE
    SYNTAX      DisplayString
    MAX-ACCESS  read-only
    STATUS      current
    DESCRIPTION "No description yet."

    ::= { dpConfigMPGWErrorHandlingPolicyEntry 2 }

--

dpConfigMPGWErrorActionTable OBJECT-TYPE
    SYNTAX      SEQUENCE OF DPConfigMPGWErrorActionEntry
    MAX-ACCESS  not-accessible
    STATUS      current
    DESCRIPTION
        "Define how the Multi-Protocol gateway handles errors and generates error
        responses to the client."

    ::= { dpConfig 313 }

dpConfigMPGWErrorActionEntry OBJECT-TYPE
    SYNTAX      DPConfigMPGWErrorActionEntry
    MAX-ACCESS  not-accessible
    STATUS      current
    DESCRIPTION "Table row."
    INDEX { dpConfigMPGWErrorActionIndex, IMPLIED dpConfigMPGWErrorActionname }

    ::= { dpConfigMPGWErrorActionTable 1 }

DPConfigMPGWErrorActionEntry ::= SEQUENCE {
    dpConfigMPGWErrorActionIndex    Unsigned32,
    dpConfigMPGWErrorActionname    DisplayString
}

dpConfigMPGWErrorActionIndex OBJECT-TYPE
    SYNTAX      Unsigned32
    MAX-ACCESS  read-only
    STATUS      current
    DESCRIPTION "No description yet."

    ::= { dpConfigMPGWErrorActionEntry 1 }

dpConfigMPGWErrorActionname OBJECT-TYPE
    SYNTAX      DisplayString
    MAX-ACCESS  read-only
    STATUS      current
    DESCRIPTION "No description yet."

    ::= { dpConfigMPGWErrorActionEntry 2 }

--

dpConfigLanguageTable OBJECT-TYPE
    SYNTAX      SEQUENCE OF DPConfigLanguageEntry
    MAX-ACCESS  not-accessible
    STATUS      current
    DESCRIPTION
        "The available languages. Before the appliance can support a language, its
        administrative state must be enabled. When a language is enable, you can
        set it as the system locale in the System Settings configuration. When
        multiple languages are enabled, browsers that connect to the appliance can
        view the interface in an enabled language."

    ::= { dpConfig 314 }

dpConfigLanguageEntry OBJECT-TYPE
    SYNTAX      DPConfigLanguageEntry
    MAX-ACCESS  not-accessible
    STATUS      current
    DESCRIPTION "Table row."
    INDEX { dpConfigLanguageIndex, IMPLIED dpConfigLanguagename }

    ::= { dpConfigLanguageTable 1 }

DPConfigLanguageEntry ::= SEQUENCE {
    dpConfigLanguageIndex    Unsigned32,
    dpConfigLanguagename    DisplayString
}

dpConfigLanguageIndex OBJECT-TYPE
    SYNTAX      Unsigned32
    MAX-ACCESS  read-only
    STATUS      current
    DESCRIPTION "No description yet."

    ::= { dpConfigLanguageEntry 1 }

dpConfigLanguagename OBJECT-TYPE
    SYNTAX      DisplayString
    MAX-ACCESS  read-only
    STATUS      current
    DESCRIPTION "No description yet."

    ::= { dpConfigLanguageEntry 2 }

--

dpConfigDomainAvailabilityTable OBJECT-TYPE
    SYNTAX      SEQUENCE OF DPConfigDomainAvailabilityEntry
    MAX-ACCESS  not-accessible
    STATUS      current
    DESCRIPTION
        "Domain Availability monitors the services within the domain. If the
        operational state of any service in the domain is in the down state, then
        the operational state for Domain Availability goes down, indicating that
        all services are not up and ready to accept traffic. Otherwise, the
        operational state for Domain Availability is up. At startup time, Domain
        Availability maintains all front-side handlers in a quiesced state until
        the associated services are fully configured, and a log event is created,
        indicating that the domain is ready to process traffic."

    ::= { dpConfig 315 }

dpConfigDomainAvailabilityEntry OBJECT-TYPE
    SYNTAX      DPConfigDomainAvailabilityEntry
    MAX-ACCESS  not-accessible
    STATUS      current
    DESCRIPTION "Table row."
    INDEX { dpConfigDomainAvailabilityIndex, IMPLIED dpConfigDomainAvailabilityname }

    ::= { dpConfigDomainAvailabilityTable 1 }

DPConfigDomainAvailabilityEntry ::= SEQUENCE {
    dpConfigDomainAvailabilityIndex    Unsigned32,
    dpConfigDomainAvailabilityname    DisplayString
}

dpConfigDomainAvailabilityIndex OBJECT-TYPE
    SYNTAX      Unsigned32
    MAX-ACCESS  read-only
    STATUS      current
    DESCRIPTION "No description yet."

    ::= { dpConfigDomainAvailabilityEntry 1 }

dpConfigDomainAvailabilityname OBJECT-TYPE
    SYNTAX      DisplayString
    MAX-ACCESS  read-only
    STATUS      current
    DESCRIPTION "No description yet."

    ::= { dpConfigDomainAvailabilityEntry 2 }

--

dpConfigGeneratedPolicyTable OBJECT-TYPE
    SYNTAX      SEQUENCE OF DPConfigGeneratedPolicyEntry
    MAX-ACCESS  not-accessible
    STATUS      current
    DESCRIPTION
        "The Generated Policy consists of generated configuration objects, such as
        Processing Rules. Generated configuration objects are automatically
        created based on the policy associated with a service. An example of a
        generated policy is a WS-Policy attached to a WSDL binding in a Web
        Service Proxy. This configuration ensures that the operational state of
        the service depends on the state of the Generated Policy and the state of
        the generated configuration objects."

    ::= { dpConfig 316 }

dpConfigGeneratedPolicyEntry OBJECT-TYPE
    SYNTAX      DPConfigGeneratedPolicyEntry
    MAX-ACCESS  not-accessible
    STATUS      current
    DESCRIPTION "Table row."
    INDEX { dpConfigGeneratedPolicyIndex, IMPLIED dpConfigGeneratedPolicyname }

    ::= { dpConfigGeneratedPolicyTable 1 }

DPConfigGeneratedPolicyEntry ::= SEQUENCE {
    dpConfigGeneratedPolicyIndex    Unsigned32,
    dpConfigGeneratedPolicyname    DisplayString
}

dpConfigGeneratedPolicyIndex OBJECT-TYPE
    SYNTAX      Unsigned32
    MAX-ACCESS  read-only
    STATUS      current
    DESCRIPTION "No description yet."

    ::= { dpConfigGeneratedPolicyEntry 1 }

dpConfigGeneratedPolicyname OBJECT-TYPE
    SYNTAX      DisplayString
    MAX-ACCESS  read-only
    STATUS      current
    DESCRIPTION "No description yet."

    ::= { dpConfigGeneratedPolicyEntry 2 }

--

dpConfigPasswordMapTable OBJECT-TYPE
    SYNTAX      SEQUENCE OF DPConfigPasswordMapEntry
    MAX-ACCESS  not-accessible
    STATUS      current
    DESCRIPTION
        "The Password Map, also known as a password-to-alias map, provides the
        mapping of aliases to passwords. The alias is a publicly known reference
        that is included in configuration files and exports. With an alias you
        keep the real password secret because the plaintext value for the password
        is stored in an encrypted file. The password for the alias cannot be
        viewed or accessed by anyone. Only the appliance can extract the password
        that it uses internally. No passwords in a map are written to
        configuration files. The password-to-alias map is not part of a backup or
        export operation, but it is part of the secure backup-restore operations."

    ::= { dpConfig 320 }

dpConfigPasswordMapEntry OBJECT-TYPE
    SYNTAX      DPConfigPasswordMapEntry
    MAX-ACCESS  not-accessible
    STATUS      current
    DESCRIPTION "Table row."
    INDEX { dpConfigPasswordMapIndex, IMPLIED dpConfigPasswordMapname }

    ::= { dpConfigPasswordMapTable 1 }

DPConfigPasswordMapEntry ::= SEQUENCE {
    dpConfigPasswordMapIndex    Unsigned32,
    dpConfigPasswordMapname    DisplayString
}

dpConfigPasswordMapIndex OBJECT-TYPE
    SYNTAX      Unsigned32
    MAX-ACCESS  read-only
    STATUS      current
    DESCRIPTION "No description yet."

    ::= { dpConfigPasswordMapEntry 1 }

dpConfigPasswordMapname OBJECT-TYPE
    SYNTAX      DisplayString
    MAX-ACCESS  read-only
    STATUS      current
    DESCRIPTION "No description yet."

    ::= { dpConfigPasswordMapEntry 2 }

--

dpConfigAAAJWTValidatorTable OBJECT-TYPE
    SYNTAX      SEQUENCE OF DPConfigAAAJWTValidatorEntry
    MAX-ACCESS  not-accessible
    STATUS      current
    DESCRIPTION
        "The JSON Web Token (JWT) Validator specifies credentials and different
        methods to validate a JWT."

    ::= { dpConfig 321 }

dpConfigAAAJWTValidatorEntry OBJECT-TYPE
    SYNTAX      DPConfigAAAJWTValidatorEntry
    MAX-ACCESS  not-accessible
    STATUS      current
    DESCRIPTION "Table row."
    INDEX { dpConfigAAAJWTValidatorIndex, IMPLIED dpConfigAAAJWTValidatorname }

    ::= { dpConfigAAAJWTValidatorTable 1 }

DPConfigAAAJWTValidatorEntry ::= SEQUENCE {
    dpConfigAAAJWTValidatorIndex    Unsigned32,
    dpConfigAAAJWTValidatorname    DisplayString
}

dpConfigAAAJWTValidatorIndex OBJECT-TYPE
    SYNTAX      Unsigned32
    MAX-ACCESS  read-only
    STATUS      current
    DESCRIPTION "No description yet."

    ::= { dpConfigAAAJWTValidatorEntry 1 }

dpConfigAAAJWTValidatorname OBJECT-TYPE
    SYNTAX      DisplayString
    MAX-ACCESS  read-only
    STATUS      current
    DESCRIPTION "No description yet."

    ::= { dpConfigAAAJWTValidatorEntry 2 }

--

dpConfigAAAJWTGeneratorTable OBJECT-TYPE
    SYNTAX      SEQUENCE OF DPConfigAAAJWTGeneratorEntry
    MAX-ACCESS  not-accessible
    STATUS      current
    DESCRIPTION
        "The JSON Web Token (JWT) Generator specifies the JWT content and the
        cryptographic methods, such as signing and encryption methods, used for
        generating a JWT during the AAA postprocessing phase."

    ::= { dpConfig 322 }

dpConfigAAAJWTGeneratorEntry OBJECT-TYPE
    SYNTAX      DPConfigAAAJWTGeneratorEntry
    MAX-ACCESS  not-accessible
    STATUS      current
    DESCRIPTION "Table row."
    INDEX { dpConfigAAAJWTGeneratorIndex, IMPLIED dpConfigAAAJWTGeneratorname }

    ::= { dpConfigAAAJWTGeneratorTable 1 }

DPConfigAAAJWTGeneratorEntry ::= SEQUENCE {
    dpConfigAAAJWTGeneratorIndex    Unsigned32,
    dpConfigAAAJWTGeneratorname    DisplayString
}

dpConfigAAAJWTGeneratorIndex OBJECT-TYPE
    SYNTAX      Unsigned32
    MAX-ACCESS  read-only
    STATUS      current
    DESCRIPTION "No description yet."

    ::= { dpConfigAAAJWTGeneratorEntry 1 }

dpConfigAAAJWTGeneratorname OBJECT-TYPE
    SYNTAX      DisplayString
    MAX-ACCESS  read-only
    STATUS      current
    DESCRIPTION "No description yet."

    ::= { dpConfigAAAJWTGeneratorEntry 2 }

--

dpConfigLinkAggregationTable OBJECT-TYPE
    SYNTAX      SEQUENCE OF DPConfigLinkAggregationEntry
    MAX-ACCESS  not-accessible
    STATUS      current
    DESCRIPTION
        "A link aggregation interface combines multiple Ethernet ports. When
        combined and used in parallel, the aggregate interface increases link
        speed beyond a single Ethernet port. Because the aggregate interface
        combines Ethernet ports, redundancy is increased to provider higher
        availability."

    ::= { dpConfig 333 }

dpConfigLinkAggregationEntry OBJECT-TYPE
    SYNTAX      DPConfigLinkAggregationEntry
    MAX-ACCESS  not-accessible
    STATUS      current
    DESCRIPTION "Table row."
    INDEX { dpConfigLinkAggregationIndex, IMPLIED dpConfigLinkAggregationname }

    ::= { dpConfigLinkAggregationTable 1 }

DPConfigLinkAggregationEntry ::= SEQUENCE {
    dpConfigLinkAggregationIndex    Unsigned32,
    dpConfigLinkAggregationname    DisplayString
}

dpConfigLinkAggregationIndex OBJECT-TYPE
    SYNTAX      Unsigned32
    MAX-ACCESS  read-only
    STATUS      current
    DESCRIPTION "No description yet."

    ::= { dpConfigLinkAggregationEntry 1 }

dpConfigLinkAggregationname OBJECT-TYPE
    SYNTAX      DisplayString
    MAX-ACCESS  read-only
    STATUS      current
    DESCRIPTION "No description yet."

    ::= { dpConfigLinkAggregationEntry 2 }

--

dpConfigCookieAttributePolicyTable OBJECT-TYPE
    SYNTAX      SEQUENCE OF DPConfigCookieAttributePolicyEntry
    MAX-ACCESS  not-accessible
    STATUS      current
    DESCRIPTION
        "Cookie attribute policy manages pre-defined and custom attributes of a
        cookie."

    ::= { dpConfig 334 }

dpConfigCookieAttributePolicyEntry OBJECT-TYPE
    SYNTAX      DPConfigCookieAttributePolicyEntry
    MAX-ACCESS  not-accessible
    STATUS      current
    DESCRIPTION "Table row."
    INDEX { dpConfigCookieAttributePolicyIndex, IMPLIED dpConfigCookieAttributePolicyname }

    ::= { dpConfigCookieAttributePolicyTable 1 }

DPConfigCookieAttributePolicyEntry ::= SEQUENCE {
    dpConfigCookieAttributePolicyIndex    Unsigned32,
    dpConfigCookieAttributePolicyname    DisplayString
}

dpConfigCookieAttributePolicyIndex OBJECT-TYPE
    SYNTAX      Unsigned32
    MAX-ACCESS  read-only
    STATUS      current
    DESCRIPTION "No description yet."

    ::= { dpConfigCookieAttributePolicyEntry 1 }

dpConfigCookieAttributePolicyname OBJECT-TYPE
    SYNTAX      DisplayString
    MAX-ACCESS  read-only
    STATUS      current
    DESCRIPTION "No description yet."

    ::= { dpConfigCookieAttributePolicyEntry 2 }

--

dpConfigISAMReverseProxyTable OBJECT-TYPE
    SYNTAX      SEQUENCE OF DPConfigISAMReverseProxyEntry
    MAX-ACCESS  not-accessible
    STATUS      current
    DESCRIPTION
        "A DataPower appliance can support multiple Access Manager Reverse Proxy
        instances per domain."

    ::= { dpConfig 335 }

dpConfigISAMReverseProxyEntry OBJECT-TYPE
    SYNTAX      DPConfigISAMReverseProxyEntry
    MAX-ACCESS  not-accessible
    STATUS      current
    DESCRIPTION "Table row."
    INDEX { dpConfigISAMReverseProxyIndex, IMPLIED dpConfigISAMReverseProxyname }

    ::= { dpConfigISAMReverseProxyTable 1 }

DPConfigISAMReverseProxyEntry ::= SEQUENCE {
    dpConfigISAMReverseProxyIndex    Unsigned32,
    dpConfigISAMReverseProxyname    DisplayString
}

dpConfigISAMReverseProxyIndex OBJECT-TYPE
    SYNTAX      Unsigned32
    MAX-ACCESS  read-only
    STATUS      current
    DESCRIPTION "No description yet."

    ::= { dpConfigISAMReverseProxyEntry 1 }

dpConfigISAMReverseProxyname OBJECT-TYPE
    SYNTAX      DisplayString
    MAX-ACCESS  read-only
    STATUS      current
    DESCRIPTION "No description yet."

    ::= { dpConfigISAMReverseProxyEntry 2 }

--

dpConfigISAMReverseProxyJunctionTable OBJECT-TYPE
    SYNTAX      SEQUENCE OF DPConfigISAMReverseProxyJunctionEntry
    MAX-ACCESS  not-accessible
    STATUS      current
    DESCRIPTION
        "An Access Manager junction logically combines the Web space of the Web
        application server with the Web space of the Access Manager Reverse Proxy
        server, resulting in a unified view of the entire Web object space. A
        junction allows the Access Manager Reverse Proxy to provide protective
        services on behalf of the Web application server."

    ::= { dpConfig 336 }

dpConfigISAMReverseProxyJunctionEntry OBJECT-TYPE
    SYNTAX      DPConfigISAMReverseProxyJunctionEntry
    MAX-ACCESS  not-accessible
    STATUS      current
    DESCRIPTION "Table row."
    INDEX { dpConfigISAMReverseProxyJunctionIndex, IMPLIED dpConfigISAMReverseProxyJunctionname }

    ::= { dpConfigISAMReverseProxyJunctionTable 1 }

DPConfigISAMReverseProxyJunctionEntry ::= SEQUENCE {
    dpConfigISAMReverseProxyJunctionIndex    Unsigned32,
    dpConfigISAMReverseProxyJunctionname    DisplayString
}

dpConfigISAMReverseProxyJunctionIndex OBJECT-TYPE
    SYNTAX      Unsigned32
    MAX-ACCESS  read-only
    STATUS      current
    DESCRIPTION "No description yet."

    ::= { dpConfigISAMReverseProxyJunctionEntry 1 }

dpConfigISAMReverseProxyJunctionname OBJECT-TYPE
    SYNTAX      DisplayString
    MAX-ACCESS  read-only
    STATUS      current
    DESCRIPTION "No description yet."

    ::= { dpConfigISAMReverseProxyJunctionEntry 2 }

--

dpConfigISAMRuntimeTable OBJECT-TYPE
    SYNTAX      SEQUENCE OF DPConfigISAMRuntimeEntry
    MAX-ACCESS  not-accessible
    STATUS      current
    DESCRIPTION
        "Each DataPower appliance domain can include a single Access Manager
        Runtime configuration. Each Access Manager Runtime is configured
        independently against a remote IBM Security Access Manager policy server
        and can support one or more Access Manager Reverse Proxy instances."

    ::= { dpConfig 337 }

dpConfigISAMRuntimeEntry OBJECT-TYPE
    SYNTAX      DPConfigISAMRuntimeEntry
    MAX-ACCESS  not-accessible
    STATUS      current
    DESCRIPTION "Table row."
    INDEX { dpConfigISAMRuntimeIndex, IMPLIED dpConfigISAMRuntimename }

    ::= { dpConfigISAMRuntimeTable 1 }

DPConfigISAMRuntimeEntry ::= SEQUENCE {
    dpConfigISAMRuntimeIndex    Unsigned32,
    dpConfigISAMRuntimename    DisplayString
}

dpConfigISAMRuntimeIndex OBJECT-TYPE
    SYNTAX      Unsigned32
    MAX-ACCESS  read-only
    STATUS      current
    DESCRIPTION "No description yet."

    ::= { dpConfigISAMRuntimeEntry 1 }

dpConfigISAMRuntimename OBJECT-TYPE
    SYNTAX      DisplayString
    MAX-ACCESS  read-only
    STATUS      current
    DESCRIPTION "No description yet."

    ::= { dpConfigISAMRuntimeEntry 2 }

--

dpConfigPasswordAliasTable OBJECT-TYPE
    SYNTAX      SEQUENCE OF DPConfigPasswordAliasEntry
    MAX-ACCESS  not-accessible
    STATUS      current
    DESCRIPTION
        "The Password Map Alias provides the mapping of an alias to a plaintext
        password. The alias is a publicly known reference that is included in
        configuration files and exports. With an alias you keep the real password
        secret because the plaintext value for the password is stored in an
        encrypted file. The password for the alias cannot be viewed or accessed by
        anyone. Only the appliance can extract the password that it uses
        internally. No passwords that are aliased are written to configuration
        files. The mapping of aliases to passwords is not part of a backup or
        export operation, but it is part of the secure backup-restore operations."

    ::= { dpConfig 338 }

dpConfigPasswordAliasEntry OBJECT-TYPE
    SYNTAX      DPConfigPasswordAliasEntry
    MAX-ACCESS  not-accessible
    STATUS      current
    DESCRIPTION "Table row."
    INDEX { dpConfigPasswordAliasIndex, IMPLIED dpConfigPasswordAliasname }

    ::= { dpConfigPasswordAliasTable 1 }

DPConfigPasswordAliasEntry ::= SEQUENCE {
    dpConfigPasswordAliasIndex    Unsigned32,
    dpConfigPasswordAliasname    DisplayString
}

dpConfigPasswordAliasIndex OBJECT-TYPE
    SYNTAX      Unsigned32
    MAX-ACCESS  read-only
    STATUS      current
    DESCRIPTION "No description yet."

    ::= { dpConfigPasswordAliasEntry 1 }

dpConfigPasswordAliasname OBJECT-TYPE
    SYNTAX      DisplayString
    MAX-ACCESS  read-only
    STATUS      current
    DESCRIPTION "No description yet."

    ::= { dpConfigPasswordAliasEntry 2 }

--

dpConfigAuditLogTable OBJECT-TYPE
    SYNTAX      SEQUENCE OF DPConfigAuditLogEntry
    MAX-ACCESS  not-accessible
    STATUS      current
    DESCRIPTION
        "The audit log settings control the configuration of the audit log of the
        system. The audit log configuration can be specified to keep a number of
        rotations of a specific size. This object also controls the level of
        audit. When set to full level of audit, connection information will be
        logged. More information is logged when in Common Criteria Compliance
        mode."

    ::= { dpConfig 340 }

dpConfigAuditLogEntry OBJECT-TYPE
    SYNTAX      DPConfigAuditLogEntry
    MAX-ACCESS  not-accessible
    STATUS      current
    DESCRIPTION "Table row."
    INDEX { dpConfigAuditLogIndex, IMPLIED dpConfigAuditLogname }

    ::= { dpConfigAuditLogTable 1 }

DPConfigAuditLogEntry ::= SEQUENCE {
    dpConfigAuditLogIndex    Unsigned32,
    dpConfigAuditLogname    DisplayString
}

dpConfigAuditLogIndex OBJECT-TYPE
    SYNTAX      Unsigned32
    MAX-ACCESS  read-only
    STATUS      current
    DESCRIPTION "No description yet."

    ::= { dpConfigAuditLogEntry 1 }

dpConfigAuditLogname OBJECT-TYPE
    SYNTAX      DisplayString
    MAX-ACCESS  read-only
    STATUS      current
    DESCRIPTION "No description yet."

    ::= { dpConfigAuditLogEntry 2 }

--

dpConfigJWERecipientTable OBJECT-TYPE
    SYNTAX      SEQUENCE OF DPConfigJWERecipientEntry
    MAX-ACCESS  not-accessible
    STATUS      current
    DESCRIPTION
        "JWE recipient object includes several values required by the JWE JSON
        Serialization object."

    ::= { dpConfig 345 }

dpConfigJWERecipientEntry OBJECT-TYPE
    SYNTAX      DPConfigJWERecipientEntry
    MAX-ACCESS  not-accessible
    STATUS      current
    DESCRIPTION "Table row."
    INDEX { dpConfigJWERecipientIndex, IMPLIED dpConfigJWERecipientname }

    ::= { dpConfigJWERecipientTable 1 }

DPConfigJWERecipientEntry ::= SEQUENCE {
    dpConfigJWERecipientIndex    Unsigned32,
    dpConfigJWERecipientname    DisplayString
}

dpConfigJWERecipientIndex OBJECT-TYPE
    SYNTAX      Unsigned32
    MAX-ACCESS  read-only
    STATUS      current
    DESCRIPTION "No description yet."

    ::= { dpConfigJWERecipientEntry 1 }

dpConfigJWERecipientname OBJECT-TYPE
    SYNTAX      DisplayString
    MAX-ACCESS  read-only
    STATUS      current
    DESCRIPTION "No description yet."

    ::= { dpConfigJWERecipientEntry 2 }

--

dpConfigJOSESignatureIdentifierTable OBJECT-TYPE
    SYNTAX      SEQUENCE OF DPConfigJOSESignatureIdentifierEntry
    MAX-ACCESS  not-accessible
    STATUS      current
    DESCRIPTION
        "JOSE Signature Identifier object for the JSON Web Verify."

    ::= { dpConfig 346 }

dpConfigJOSESignatureIdentifierEntry OBJECT-TYPE
    SYNTAX      DPConfigJOSESignatureIdentifierEntry
    MAX-ACCESS  not-accessible
    STATUS      current
    DESCRIPTION "Table row."
    INDEX { dpConfigJOSESignatureIdentifierIndex, IMPLIED dpConfigJOSESignatureIdentifiername }

    ::= { dpConfigJOSESignatureIdentifierTable 1 }

DPConfigJOSESignatureIdentifierEntry ::= SEQUENCE {
    dpConfigJOSESignatureIdentifierIndex    Unsigned32,
    dpConfigJOSESignatureIdentifiername    DisplayString
}

dpConfigJOSESignatureIdentifierIndex OBJECT-TYPE
    SYNTAX      Unsigned32
    MAX-ACCESS  read-only
    STATUS      current
    DESCRIPTION "No description yet."

    ::= { dpConfigJOSESignatureIdentifierEntry 1 }

dpConfigJOSESignatureIdentifiername OBJECT-TYPE
    SYNTAX      DisplayString
    MAX-ACCESS  read-only
    STATUS      current
    DESCRIPTION "No description yet."

    ::= { dpConfigJOSESignatureIdentifierEntry 2 }

--

dpConfigJWSSignatureTable OBJECT-TYPE
    SYNTAX      SEQUENCE OF DPConfigJWSSignatureEntry
    MAX-ACCESS  not-accessible
    STATUS      current
    DESCRIPTION
        "JWS signature object."

    ::= { dpConfig 347 }

dpConfigJWSSignatureEntry OBJECT-TYPE
    SYNTAX      DPConfigJWSSignatureEntry
    MAX-ACCESS  not-accessible
    STATUS      current
    DESCRIPTION "Table row."
    INDEX { dpConfigJWSSignatureIndex, IMPLIED dpConfigJWSSignaturename }

    ::= { dpConfigJWSSignatureTable 1 }

DPConfigJWSSignatureEntry ::= SEQUENCE {
    dpConfigJWSSignatureIndex    Unsigned32,
    dpConfigJWSSignaturename    DisplayString
}

dpConfigJWSSignatureIndex OBJECT-TYPE
    SYNTAX      Unsigned32
    MAX-ACCESS  read-only
    STATUS      current
    DESCRIPTION "No description yet."

    ::= { dpConfigJWSSignatureEntry 1 }

dpConfigJWSSignaturename OBJECT-TYPE
    SYNTAX      DisplayString
    MAX-ACCESS  read-only
    STATUS      current
    DESCRIPTION "No description yet."

    ::= { dpConfigJWSSignatureEntry 2 }

--

dpConfigJWEHeaderTable OBJECT-TYPE
    SYNTAX      SEQUENCE OF DPConfigJWEHeaderEntry
    MAX-ACCESS  not-accessible
    STATUS      current
    DESCRIPTION
        "JWE header object."

    ::= { dpConfig 348 }

dpConfigJWEHeaderEntry OBJECT-TYPE
    SYNTAX      DPConfigJWEHeaderEntry
    MAX-ACCESS  not-accessible
    STATUS      current
    DESCRIPTION "Table row."
    INDEX { dpConfigJWEHeaderIndex, IMPLIED dpConfigJWEHeadername }

    ::= { dpConfigJWEHeaderTable 1 }

DPConfigJWEHeaderEntry ::= SEQUENCE {
    dpConfigJWEHeaderIndex    Unsigned32,
    dpConfigJWEHeadername    DisplayString
}

dpConfigJWEHeaderIndex OBJECT-TYPE
    SYNTAX      Unsigned32
    MAX-ACCESS  read-only
    STATUS      current
    DESCRIPTION "No description yet."

    ::= { dpConfigJWEHeaderEntry 1 }

dpConfigJWEHeadername OBJECT-TYPE
    SYNTAX      DisplayString
    MAX-ACCESS  read-only
    STATUS      current
    DESCRIPTION "No description yet."

    ::= { dpConfigJWEHeaderEntry 2 }

--

dpConfigJOSERecipientIdentifierTable OBJECT-TYPE
    SYNTAX      SEQUENCE OF DPConfigJOSERecipientIdentifierEntry
    MAX-ACCESS  not-accessible
    STATUS      current
    DESCRIPTION
        "JOSE Recipient Identifier object for the JSON Web Decrypt."

    ::= { dpConfig 349 }

dpConfigJOSERecipientIdentifierEntry OBJECT-TYPE
    SYNTAX      DPConfigJOSERecipientIdentifierEntry
    MAX-ACCESS  not-accessible
    STATUS      current
    DESCRIPTION "Table row."
    INDEX { dpConfigJOSERecipientIdentifierIndex, IMPLIED dpConfigJOSERecipientIdentifiername }

    ::= { dpConfigJOSERecipientIdentifierTable 1 }

DPConfigJOSERecipientIdentifierEntry ::= SEQUENCE {
    dpConfigJOSERecipientIdentifierIndex    Unsigned32,
    dpConfigJOSERecipientIdentifiername    DisplayString
}

dpConfigJOSERecipientIdentifierIndex OBJECT-TYPE
    SYNTAX      Unsigned32
    MAX-ACCESS  read-only
    STATUS      current
    DESCRIPTION "No description yet."

    ::= { dpConfigJOSERecipientIdentifierEntry 1 }

dpConfigJOSERecipientIdentifiername OBJECT-TYPE
    SYNTAX      DisplayString
    MAX-ACCESS  read-only
    STATUS      current
    DESCRIPTION "No description yet."

    ::= { dpConfigJOSERecipientIdentifierEntry 2 }

--

dpConfigSecureGatewayClientTable OBJECT-TYPE
    SYNTAX      SEQUENCE OF DPConfigSecureGatewayClientEntry
    MAX-ACCESS  not-accessible
    STATUS      current
    DESCRIPTION
        "The Secure Gateway client creates a secure tunnel to IBM Cloud for
        establishing TCP/IP communication with backend systems."

    ::= { dpConfig 350 }

dpConfigSecureGatewayClientEntry OBJECT-TYPE
    SYNTAX      DPConfigSecureGatewayClientEntry
    MAX-ACCESS  not-accessible
    STATUS      current
    DESCRIPTION "Table row."
    INDEX { dpConfigSecureGatewayClientIndex, IMPLIED dpConfigSecureGatewayClientname }

    ::= { dpConfigSecureGatewayClientTable 1 }

DPConfigSecureGatewayClientEntry ::= SEQUENCE {
    dpConfigSecureGatewayClientIndex    Unsigned32,
    dpConfigSecureGatewayClientname    DisplayString
}

dpConfigSecureGatewayClientIndex OBJECT-TYPE
    SYNTAX      Unsigned32
    MAX-ACCESS  read-only
    STATUS      current
    DESCRIPTION "No description yet."

    ::= { dpConfigSecureGatewayClientEntry 1 }

dpConfigSecureGatewayClientname OBJECT-TYPE
    SYNTAX      DisplayString
    MAX-ACCESS  read-only
    STATUS      current
    DESCRIPTION "No description yet."

    ::= { dpConfigSecureGatewayClientEntry 2 }

--

dpConfigCacheGridTable OBJECT-TYPE
    SYNTAX      SEQUENCE OF DPConfigCacheGridEntry
    MAX-ACCESS  not-accessible
    STATUS      current
    DESCRIPTION "Table."

    ::= { dpConfig 351 }

dpConfigCacheGridEntry OBJECT-TYPE
    SYNTAX      DPConfigCacheGridEntry
    MAX-ACCESS  not-accessible
    STATUS      current
    DESCRIPTION "Table row."
    INDEX { dpConfigCacheGridIndex, IMPLIED dpConfigCacheGridname }

    ::= { dpConfigCacheGridTable 1 }

DPConfigCacheGridEntry ::= SEQUENCE {
    dpConfigCacheGridIndex    Unsigned32,
    dpConfigCacheGridname    DisplayString
}

dpConfigCacheGridIndex OBJECT-TYPE
    SYNTAX      Unsigned32
    MAX-ACCESS  read-only
    STATUS      current
    DESCRIPTION "No description yet."

    ::= { dpConfigCacheGridEntry 1 }

dpConfigCacheGridname OBJECT-TYPE
    SYNTAX      DisplayString
    MAX-ACCESS  read-only
    STATUS      current
    DESCRIPTION "No description yet."

    ::= { dpConfigCacheGridEntry 2 }

--

dpConfigWXSGridTable OBJECT-TYPE
    SYNTAX      SEQUENCE OF DPConfigWXSGridEntry
    MAX-ACCESS  not-accessible
    STATUS      current
    DESCRIPTION
        "The configuration of an eXtreme Scale Grid defines the connection details
        to an eXtreme Scale grid in an eXtreme Scale collective. To define this
        configuration, you must define the eXtreme Scale collective, the grid
        name, and the user and password for the user account who connects to the
        eXtreme Scale. If you need to secure connections to eXtreme Scale, you
        must assign an SSL Proxy Profile."

    ::= { dpConfig 352 }

dpConfigWXSGridEntry OBJECT-TYPE
    SYNTAX      DPConfigWXSGridEntry
    MAX-ACCESS  not-accessible
    STATUS      current
    DESCRIPTION "Table row."
    INDEX { dpConfigWXSGridIndex, IMPLIED dpConfigWXSGridname }

    ::= { dpConfigWXSGridTable 1 }

DPConfigWXSGridEntry ::= SEQUENCE {
    dpConfigWXSGridIndex    Unsigned32,
    dpConfigWXSGridname    DisplayString
}

dpConfigWXSGridIndex OBJECT-TYPE
    SYNTAX      Unsigned32
    MAX-ACCESS  read-only
    STATUS      current
    DESCRIPTION "No description yet."

    ::= { dpConfigWXSGridEntry 1 }

dpConfigWXSGridname OBJECT-TYPE
    SYNTAX      DisplayString
    MAX-ACCESS  read-only
    STATUS      current
    DESCRIPTION "No description yet."

    ::= { dpConfigWXSGridEntry 2 }

--

dpConfigDomainSettingsTable OBJECT-TYPE
    SYNTAX      SEQUENCE OF DPConfigDomainSettingsEntry
    MAX-ACCESS  not-accessible
    STATUS      current
    DESCRIPTION
        "The Domain Settings configuration provides properties to domain-specific
        characteristics when you save changes to the persisted configuration."

    ::= { dpConfig 353 }

dpConfigDomainSettingsEntry OBJECT-TYPE
    SYNTAX      DPConfigDomainSettingsEntry
    MAX-ACCESS  not-accessible
    STATUS      current
    DESCRIPTION "Table row."
    INDEX { dpConfigDomainSettingsIndex, IMPLIED dpConfigDomainSettingsname }

    ::= { dpConfigDomainSettingsTable 1 }

DPConfigDomainSettingsEntry ::= SEQUENCE {
    dpConfigDomainSettingsIndex    Unsigned32,
    dpConfigDomainSettingsname    DisplayString
}

dpConfigDomainSettingsIndex OBJECT-TYPE
    SYNTAX      Unsigned32
    MAX-ACCESS  read-only
    STATUS      current
    DESCRIPTION "No description yet."

    ::= { dpConfigDomainSettingsEntry 1 }

dpConfigDomainSettingsname OBJECT-TYPE
    SYNTAX      DisplayString
    MAX-ACCESS  read-only
    STATUS      current
    DESCRIPTION "No description yet."

    ::= { dpConfigDomainSettingsEntry 2 }

--

dpConfigGWScriptSettingsTable OBJECT-TYPE
    SYNTAX      SEQUENCE OF DPConfigGWScriptSettingsEntry
    MAX-ACCESS  not-accessible
    STATUS      current
    DESCRIPTION
        "You can configure the following GatewayScript settings: Whether to freeze
        the GatewayScript built-in objects. Freeze means preventing the
        modification of existing property attributes and values, the addition of
        new properties, or the removal of existing properties of the built-in
        objects. The maximum allowed number of seconds that the GatewayScript
        action can continuously use the CPU."

    ::= { dpConfig 358 }

dpConfigGWScriptSettingsEntry OBJECT-TYPE
    SYNTAX      DPConfigGWScriptSettingsEntry
    MAX-ACCESS  not-accessible
    STATUS      current
    DESCRIPTION "Table row."
    INDEX { dpConfigGWScriptSettingsIndex, IMPLIED dpConfigGWScriptSettingsname }

    ::= { dpConfigGWScriptSettingsTable 1 }

DPConfigGWScriptSettingsEntry ::= SEQUENCE {
    dpConfigGWScriptSettingsIndex    Unsigned32,
    dpConfigGWScriptSettingsname    DisplayString
}

dpConfigGWScriptSettingsIndex OBJECT-TYPE
    SYNTAX      Unsigned32
    MAX-ACCESS  read-only
    STATUS      current
    DESCRIPTION "No description yet."

    ::= { dpConfigGWScriptSettingsEntry 1 }

dpConfigGWScriptSettingsname OBJECT-TYPE
    SYNTAX      DisplayString
    MAX-ACCESS  read-only
    STATUS      current
    DESCRIPTION "No description yet."

    ::= { dpConfigGWScriptSettingsEntry 2 }

--

dpConfigAPICollectionTable OBJECT-TYPE
    SYNTAX      SEQUENCE OF DPConfigAPICollectionEntry
    MAX-ACCESS  not-accessible
    STATUS      current
    DESCRIPTION
        "An API collection is a logical partition of an API Gateway that packages
        the plans and subscribers to make APIs available to a specific group of
        clients. An API collection in the API Gateway corresponds to a catalog in
        the API manager."

    ::= { dpConfig 359 }

dpConfigAPICollectionEntry OBJECT-TYPE
    SYNTAX      DPConfigAPICollectionEntry
    MAX-ACCESS  not-accessible
    STATUS      current
    DESCRIPTION "Table row."
    INDEX { dpConfigAPICollectionIndex, IMPLIED dpConfigAPICollectionname }

    ::= { dpConfigAPICollectionTable 1 }

DPConfigAPICollectionEntry ::= SEQUENCE {
    dpConfigAPICollectionIndex    Unsigned32,
    dpConfigAPICollectionname    DisplayString
}

dpConfigAPICollectionIndex OBJECT-TYPE
    SYNTAX      Unsigned32
    MAX-ACCESS  read-only
    STATUS      current
    DESCRIPTION "No description yet."

    ::= { dpConfigAPICollectionEntry 1 }

dpConfigAPICollectionname OBJECT-TYPE
    SYNTAX      DisplayString
    MAX-ACCESS  read-only
    STATUS      current
    DESCRIPTION "No description yet."

    ::= { dpConfigAPICollectionEntry 2 }

--

dpConfigAPIGatewayTable OBJECT-TYPE
    SYNTAX      SEQUENCE OF DPConfigAPIGatewayEntry
    MAX-ACCESS  not-accessible
    STATUS      current
    DESCRIPTION
        "An API Gateway matches the API to process the API request and routes the
        request to the matched API."

    ::= { dpConfig 360 }

dpConfigAPIGatewayEntry OBJECT-TYPE
    SYNTAX      DPConfigAPIGatewayEntry
    MAX-ACCESS  not-accessible
    STATUS      current
    DESCRIPTION "Table row."
    INDEX { dpConfigAPIGatewayIndex, IMPLIED dpConfigAPIGatewayname }

    ::= { dpConfigAPIGatewayTable 1 }

DPConfigAPIGatewayEntry ::= SEQUENCE {
    dpConfigAPIGatewayIndex    Unsigned32,
    dpConfigAPIGatewayname    DisplayString
}

dpConfigAPIGatewayIndex OBJECT-TYPE
    SYNTAX      Unsigned32
    MAX-ACCESS  read-only
    STATUS      current
    DESCRIPTION "No description yet."

    ::= { dpConfigAPIGatewayEntry 1 }

dpConfigAPIGatewayname OBJECT-TYPE
    SYNTAX      DisplayString
    MAX-ACCESS  read-only
    STATUS      current
    DESCRIPTION "No description yet."

    ::= { dpConfigAPIGatewayEntry 2 }

--

dpConfigAPIDefinitionTable OBJECT-TYPE
    SYNTAX      SEQUENCE OF DPConfigAPIDefinitionEntry
    MAX-ACCESS  not-accessible
    STATUS      current
    DESCRIPTION
        "Configure a REST API definition that uses HTTP requests to GET, PUT, POST
        and DELETE data."

    ::= { dpConfig 361 }

dpConfigAPIDefinitionEntry OBJECT-TYPE
    SYNTAX      DPConfigAPIDefinitionEntry
    MAX-ACCESS  not-accessible
    STATUS      current
    DESCRIPTION "Table row."
    INDEX { dpConfigAPIDefinitionIndex, IMPLIED dpConfigAPIDefinitionname }

    ::= { dpConfigAPIDefinitionTable 1 }

DPConfigAPIDefinitionEntry ::= SEQUENCE {
    dpConfigAPIDefinitionIndex    Unsigned32,
    dpConfigAPIDefinitionname    DisplayString
}

dpConfigAPIDefinitionIndex OBJECT-TYPE
    SYNTAX      Unsigned32
    MAX-ACCESS  read-only
    STATUS      current
    DESCRIPTION "No description yet."

    ::= { dpConfigAPIDefinitionEntry 1 }

dpConfigAPIDefinitionname OBJECT-TYPE
    SYNTAX      DisplayString
    MAX-ACCESS  read-only
    STATUS      current
    DESCRIPTION "No description yet."

    ::= { dpConfigAPIDefinitionEntry 2 }

--

dpConfigAPIPathTable OBJECT-TYPE
    SYNTAX      SEQUENCE OF DPConfigAPIPathEntry
    MAX-ACCESS  not-accessible
    STATUS      current
    DESCRIPTION
        "An API Path configuration describes the operations that are available on a
        single path."

    ::= { dpConfig 362 }

dpConfigAPIPathEntry OBJECT-TYPE
    SYNTAX      DPConfigAPIPathEntry
    MAX-ACCESS  not-accessible
    STATUS      current
    DESCRIPTION "Table row."
    INDEX { dpConfigAPIPathIndex, IMPLIED dpConfigAPIPathname }

    ::= { dpConfigAPIPathTable 1 }

DPConfigAPIPathEntry ::= SEQUENCE {
    dpConfigAPIPathIndex    Unsigned32,
    dpConfigAPIPathname    DisplayString
}

dpConfigAPIPathIndex OBJECT-TYPE
    SYNTAX      Unsigned32
    MAX-ACCESS  read-only
    STATUS      current
    DESCRIPTION "No description yet."

    ::= { dpConfigAPIPathEntry 1 }

dpConfigAPIPathname OBJECT-TYPE
    SYNTAX      DisplayString
    MAX-ACCESS  read-only
    STATUS      current
    DESCRIPTION "No description yet."

    ::= { dpConfigAPIPathEntry 2 }

--

dpConfigAPIOperationTable OBJECT-TYPE
    SYNTAX      SEQUENCE OF DPConfigAPIOperationEntry
    MAX-ACCESS  not-accessible
    STATUS      current
    DESCRIPTION
        "An API operation configuration describes the actions to perform against
        the resource."

    ::= { dpConfig 363 }

dpConfigAPIOperationEntry OBJECT-TYPE
    SYNTAX      DPConfigAPIOperationEntry
    MAX-ACCESS  not-accessible
    STATUS      current
    DESCRIPTION "Table row."
    INDEX { dpConfigAPIOperationIndex, IMPLIED dpConfigAPIOperationname }

    ::= { dpConfigAPIOperationTable 1 }

DPConfigAPIOperationEntry ::= SEQUENCE {
    dpConfigAPIOperationIndex    Unsigned32,
    dpConfigAPIOperationname    DisplayString
}

dpConfigAPIOperationIndex OBJECT-TYPE
    SYNTAX      Unsigned32
    MAX-ACCESS  read-only
    STATUS      current
    DESCRIPTION "No description yet."

    ::= { dpConfigAPIOperationEntry 1 }

dpConfigAPIOperationname OBJECT-TYPE
    SYNTAX      DisplayString
    MAX-ACCESS  read-only
    STATUS      current
    DESCRIPTION "No description yet."

    ::= { dpConfigAPIOperationEntry 2 }

--

dpConfigAPIPlanTable OBJECT-TYPE
    SYNTAX      SEQUENCE OF DPConfigAPIPlanEntry
    MAX-ACCESS  not-accessible
    STATUS      current
    DESCRIPTION
        "An API is exposed for access through an API plan. An API Plan packages a
        list of APIs and defines the rate limit schemes to enforce to access the
        APIs. By default, the rate limit scheme of the plan applies to all
        operations. However, you can exclude certain operations from the plan or
        override the plan-level rate limit schemes by specifying
        operation-specific rate limit schemes."

    ::= { dpConfig 364 }

dpConfigAPIPlanEntry OBJECT-TYPE
    SYNTAX      DPConfigAPIPlanEntry
    MAX-ACCESS  not-accessible
    STATUS      current
    DESCRIPTION "Table row."
    INDEX { dpConfigAPIPlanIndex, IMPLIED dpConfigAPIPlanname }

    ::= { dpConfigAPIPlanTable 1 }

DPConfigAPIPlanEntry ::= SEQUENCE {
    dpConfigAPIPlanIndex    Unsigned32,
    dpConfigAPIPlanname    DisplayString
}

dpConfigAPIPlanIndex OBJECT-TYPE
    SYNTAX      Unsigned32
    MAX-ACCESS  read-only
    STATUS      current
    DESCRIPTION "No description yet."

    ::= { dpConfigAPIPlanEntry 1 }

dpConfigAPIPlanname OBJECT-TYPE
    SYNTAX      DisplayString
    MAX-ACCESS  read-only
    STATUS      current
    DESCRIPTION "No description yet."

    ::= { dpConfigAPIPlanEntry 2 }

--

dpConfigAPISecurityDefinitionTable OBJECT-TYPE
    SYNTAX      SEQUENCE OF DPConfigAPISecurityDefinitionEntry
    MAX-ACCESS  not-accessible
    STATUS      current
    DESCRIPTION
        "The API Security Definition configuration specifies the security schemes
        that are available to be used to secure access to the API."

    ::= { dpConfig 365 }

dpConfigAPISecurityDefinitionEntry OBJECT-TYPE
    SYNTAX      DPConfigAPISecurityDefinitionEntry
    MAX-ACCESS  not-accessible
    STATUS      current
    DESCRIPTION "Table row."
    INDEX { dpConfigAPISecurityDefinitionIndex, IMPLIED dpConfigAPISecurityDefinitionname }

    ::= { dpConfigAPISecurityDefinitionTable 1 }

DPConfigAPISecurityDefinitionEntry ::= SEQUENCE {
    dpConfigAPISecurityDefinitionIndex    Unsigned32,
    dpConfigAPISecurityDefinitionname    DisplayString
}

dpConfigAPISecurityDefinitionIndex OBJECT-TYPE
    SYNTAX      Unsigned32
    MAX-ACCESS  read-only
    STATUS      current
    DESCRIPTION "No description yet."

    ::= { dpConfigAPISecurityDefinitionEntry 1 }

dpConfigAPISecurityDefinitionname OBJECT-TYPE
    SYNTAX      DisplayString
    MAX-ACCESS  read-only
    STATUS      current
    DESCRIPTION "No description yet."

    ::= { dpConfigAPISecurityDefinitionEntry 2 }

--

dpConfigAPISecurityAPIKeyTable OBJECT-TYPE
    SYNTAX      SEQUENCE OF DPConfigAPISecurityAPIKeyEntry
    MAX-ACCESS  not-accessible
    STATUS      current
    DESCRIPTION
        "An API key security definition defines the credentials that an API client
        must provide to the API Gateway to identify itself when calling the API
        operations. You can require that the client must provide only the client
        ID, or both client ID and client secret, to call an API operation. When
        you require the client to provide both client ID and client secret, you
        must create two separate API Security API Key configurations, one of type
        ID and the other of type Secret."

    ::= { dpConfig 366 }

dpConfigAPISecurityAPIKeyEntry OBJECT-TYPE
    SYNTAX      DPConfigAPISecurityAPIKeyEntry
    MAX-ACCESS  not-accessible
    STATUS      current
    DESCRIPTION "Table row."
    INDEX { dpConfigAPISecurityAPIKeyIndex, IMPLIED dpConfigAPISecurityAPIKeyname }

    ::= { dpConfigAPISecurityAPIKeyTable 1 }

DPConfigAPISecurityAPIKeyEntry ::= SEQUENCE {
    dpConfigAPISecurityAPIKeyIndex    Unsigned32,
    dpConfigAPISecurityAPIKeyname    DisplayString
}

dpConfigAPISecurityAPIKeyIndex OBJECT-TYPE
    SYNTAX      Unsigned32
    MAX-ACCESS  read-only
    STATUS      current
    DESCRIPTION "No description yet."

    ::= { dpConfigAPISecurityAPIKeyEntry 1 }

dpConfigAPISecurityAPIKeyname OBJECT-TYPE
    SYNTAX      DisplayString
    MAX-ACCESS  read-only
    STATUS      current
    DESCRIPTION "No description yet."

    ::= { dpConfigAPISecurityAPIKeyEntry 2 }

--

dpConfigAPISecurityOAuthTable OBJECT-TYPE
    SYNTAX      SEQUENCE OF DPConfigAPISecurityOAuthEntry
    MAX-ACCESS  not-accessible
    STATUS      current
    DESCRIPTION
        "An API OAuth security definition defines the applicable settings for an
        OAuth provider."

    ::= { dpConfig 368 }

dpConfigAPISecurityOAuthEntry OBJECT-TYPE
    SYNTAX      DPConfigAPISecurityOAuthEntry
    MAX-ACCESS  not-accessible
    STATUS      current
    DESCRIPTION "Table row."
    INDEX { dpConfigAPISecurityOAuthIndex, IMPLIED dpConfigAPISecurityOAuthname }

    ::= { dpConfigAPISecurityOAuthTable 1 }

DPConfigAPISecurityOAuthEntry ::= SEQUENCE {
    dpConfigAPISecurityOAuthIndex    Unsigned32,
    dpConfigAPISecurityOAuthname    DisplayString
}

dpConfigAPISecurityOAuthIndex OBJECT-TYPE
    SYNTAX      Unsigned32
    MAX-ACCESS  read-only
    STATUS      current
    DESCRIPTION "No description yet."

    ::= { dpConfigAPISecurityOAuthEntry 1 }

dpConfigAPISecurityOAuthname OBJECT-TYPE
    SYNTAX      DisplayString
    MAX-ACCESS  read-only
    STATUS      current
    DESCRIPTION "No description yet."

    ::= { dpConfigAPISecurityOAuthEntry 2 }

--

dpConfigAPISecurityRequirementTable OBJECT-TYPE
    SYNTAX      SEQUENCE OF DPConfigAPISecurityRequirementEntry
    MAX-ACCESS  not-accessible
    STATUS      current
    DESCRIPTION
        "An API Security Requirement configuration defines the required security
        schemes that an API request must pass to execute this operation. Specify
        the security requirement by selecting from the security schemes that are
        declared in the Security Definitions configuration. When multiple security
        schemes are selected, the API request must pass all security checks (that
        is, there is a logical AND between the schemes)."

    ::= { dpConfig 369 }

dpConfigAPISecurityRequirementEntry OBJECT-TYPE
    SYNTAX      DPConfigAPISecurityRequirementEntry
    MAX-ACCESS  not-accessible
    STATUS      current
    DESCRIPTION "Table row."
    INDEX { dpConfigAPISecurityRequirementIndex, IMPLIED dpConfigAPISecurityRequirementname }

    ::= { dpConfigAPISecurityRequirementTable 1 }

DPConfigAPISecurityRequirementEntry ::= SEQUENCE {
    dpConfigAPISecurityRequirementIndex    Unsigned32,
    dpConfigAPISecurityRequirementname    DisplayString
}

dpConfigAPISecurityRequirementIndex OBJECT-TYPE
    SYNTAX      Unsigned32
    MAX-ACCESS  read-only
    STATUS      current
    DESCRIPTION "No description yet."

    ::= { dpConfigAPISecurityRequirementEntry 1 }

dpConfigAPISecurityRequirementname OBJECT-TYPE
    SYNTAX      DisplayString
    MAX-ACCESS  read-only
    STATUS      current
    DESCRIPTION "No description yet."

    ::= { dpConfigAPISecurityRequirementEntry 2 }

--

dpConfigControlListTable OBJECT-TYPE
    SYNTAX      SEQUENCE OF DPConfigControlListEntry
    MAX-ACCESS  not-accessible
    STATUS      current
    DESCRIPTION
        "A control list uses a value-matching pattern to determine whether values
        are on the whitelist or blacklist. When on the whitelist, the following
        behavior applies. A whitelist entry of ^foo indicates that only values
        that start with foo are accepted. All other values are rejected. A
        whitelist with only the .* entry indicates that all values are accepted.
        An empty whitelist indicates that all values are rejected. When on the
        blacklist, the following behavior applies. A blacklist entry of ^foo
        indicates that only values that start with foo are rejected. All other
        values are accepted. A blacklist with only the .* entry indicates that all
        values are rejected. An empty blacklist indicates that all values are
        accepted. The value-matching pattern is defined by a PCRE. When you define
        the control list, you can indicates whether evaluation is case-sensitive
        or case-insensitive."

    ::= { dpConfig 370 }

dpConfigControlListEntry OBJECT-TYPE
    SYNTAX      DPConfigControlListEntry
    MAX-ACCESS  not-accessible
    STATUS      current
    DESCRIPTION "Table row."
    INDEX { dpConfigControlListIndex, IMPLIED dpConfigControlListname }

    ::= { dpConfigControlListTable 1 }

DPConfigControlListEntry ::= SEQUENCE {
    dpConfigControlListIndex    Unsigned32,
    dpConfigControlListname    DisplayString
}

dpConfigControlListIndex OBJECT-TYPE
    SYNTAX      Unsigned32
    MAX-ACCESS  read-only
    STATUS      current
    DESCRIPTION "No description yet."

    ::= { dpConfigControlListEntry 1 }

dpConfigControlListname OBJECT-TYPE
    SYNTAX      DisplayString
    MAX-ACCESS  read-only
    STATUS      current
    DESCRIPTION "No description yet."

    ::= { dpConfigControlListEntry 2 }

--

dpConfigAPILDAPRegistryTable OBJECT-TYPE
    SYNTAX      SEQUENCE OF DPConfigAPILDAPRegistryEntry
    MAX-ACCESS  not-accessible
    STATUS      current
    DESCRIPTION "Table."

    ::= { dpConfig 371 }

dpConfigAPILDAPRegistryEntry OBJECT-TYPE
    SYNTAX      DPConfigAPILDAPRegistryEntry
    MAX-ACCESS  not-accessible
    STATUS      current
    DESCRIPTION "Table row."
    INDEX { dpConfigAPILDAPRegistryIndex, IMPLIED dpConfigAPILDAPRegistryname }

    ::= { dpConfigAPILDAPRegistryTable 1 }

DPConfigAPILDAPRegistryEntry ::= SEQUENCE {
    dpConfigAPILDAPRegistryIndex    Unsigned32,
    dpConfigAPILDAPRegistryname    DisplayString
}

dpConfigAPILDAPRegistryIndex OBJECT-TYPE
    SYNTAX      Unsigned32
    MAX-ACCESS  read-only
    STATUS      current
    DESCRIPTION "No description yet."

    ::= { dpConfigAPILDAPRegistryEntry 1 }

dpConfigAPILDAPRegistryname OBJECT-TYPE
    SYNTAX      DisplayString
    MAX-ACCESS  read-only
    STATUS      current
    DESCRIPTION "No description yet."

    ::= { dpConfigAPILDAPRegistryEntry 2 }

--

dpConfigAPIRuleTable OBJECT-TYPE
    SYNTAX      SEQUENCE OF DPConfigAPIRuleEntry
    MAX-ACCESS  not-accessible
    STATUS      current
    DESCRIPTION
        "Configure and manage the API rule. An API rule completes the processing of
        API requests or completes the operations that are required by the API
        requests."

    ::= { dpConfig 372 }

dpConfigAPIRuleEntry OBJECT-TYPE
    SYNTAX      DPConfigAPIRuleEntry
    MAX-ACCESS  not-accessible
    STATUS      current
    DESCRIPTION "Table row."
    INDEX { dpConfigAPIRuleIndex, IMPLIED dpConfigAPIRulename }

    ::= { dpConfigAPIRuleTable 1 }

DPConfigAPIRuleEntry ::= SEQUENCE {
    dpConfigAPIRuleIndex    Unsigned32,
    dpConfigAPIRulename    DisplayString
}

dpConfigAPIRuleIndex OBJECT-TYPE
    SYNTAX      Unsigned32
    MAX-ACCESS  read-only
    STATUS      current
    DESCRIPTION "No description yet."

    ::= { dpConfigAPIRuleEntry 1 }

dpConfigAPIRulename OBJECT-TYPE
    SYNTAX      DisplayString
    MAX-ACCESS  read-only
    STATUS      current
    DESCRIPTION "No description yet."

    ::= { dpConfigAPIRuleEntry 2 }

--

dpConfigAPISecurityOAuthReqTable OBJECT-TYPE
    SYNTAX      SEQUENCE OF DPConfigAPISecurityOAuthReqEntry
    MAX-ACCESS  not-accessible
    STATUS      current
    DESCRIPTION
        "An OAuth security requirement defines the allowed scopes for controlling
        access to APIs or operations through the token-based OAuth protocol. By
        using an OAuth token, a user can grant websites or applications to access
        their data that are stored with another service provider, without sharing
        their personal credentials. #b#Note:#/b# You cannot apply more than one
        OAuth security requirement to an API or operation."

    ::= { dpConfig 373 }

dpConfigAPISecurityOAuthReqEntry OBJECT-TYPE
    SYNTAX      DPConfigAPISecurityOAuthReqEntry
    MAX-ACCESS  not-accessible
    STATUS      current
    DESCRIPTION "Table row."
    INDEX { dpConfigAPISecurityOAuthReqIndex, IMPLIED dpConfigAPISecurityOAuthReqname }

    ::= { dpConfigAPISecurityOAuthReqTable 1 }

DPConfigAPISecurityOAuthReqEntry ::= SEQUENCE {
    dpConfigAPISecurityOAuthReqIndex    Unsigned32,
    dpConfigAPISecurityOAuthReqname    DisplayString
}

dpConfigAPISecurityOAuthReqIndex OBJECT-TYPE
    SYNTAX      Unsigned32
    MAX-ACCESS  read-only
    STATUS      current
    DESCRIPTION "No description yet."

    ::= { dpConfigAPISecurityOAuthReqEntry 1 }

dpConfigAPISecurityOAuthReqname OBJECT-TYPE
    SYNTAX      DisplayString
    MAX-ACCESS  read-only
    STATUS      current
    DESCRIPTION "No description yet."

    ::= { dpConfigAPISecurityOAuthReqEntry 2 }

--

dpConfigGWSRemoteDebugTable OBJECT-TYPE
    SYNTAX      SEQUENCE OF DPConfigGWSRemoteDebugEntry
    MAX-ACCESS  not-accessible
    STATUS      current
    DESCRIPTION
        "Modify the connection details for a remote GatewayScript debugger. This
        configuration defines the local GatewayScript debug endpoint for remote
        debugging."

    ::= { dpConfig 374 }

dpConfigGWSRemoteDebugEntry OBJECT-TYPE
    SYNTAX      DPConfigGWSRemoteDebugEntry
    MAX-ACCESS  not-accessible
    STATUS      current
    DESCRIPTION "Table row."
    INDEX { dpConfigGWSRemoteDebugIndex, IMPLIED dpConfigGWSRemoteDebugname }

    ::= { dpConfigGWSRemoteDebugTable 1 }

DPConfigGWSRemoteDebugEntry ::= SEQUENCE {
    dpConfigGWSRemoteDebugIndex    Unsigned32,
    dpConfigGWSRemoteDebugname    DisplayString
}

dpConfigGWSRemoteDebugIndex OBJECT-TYPE
    SYNTAX      Unsigned32
    MAX-ACCESS  read-only
    STATUS      current
    DESCRIPTION "No description yet."

    ::= { dpConfigGWSRemoteDebugEntry 1 }

dpConfigGWSRemoteDebugname OBJECT-TYPE
    SYNTAX      DisplayString
    MAX-ACCESS  read-only
    STATUS      current
    DESCRIPTION "No description yet."

    ::= { dpConfigGWSRemoteDebugEntry 2 }

--

dpConfigAssemblyActionUserSecurityTable OBJECT-TYPE
    SYNTAX      SEQUENCE OF DPConfigAssemblyActionUserSecurityEntry
    MAX-ACCESS  not-accessible
    STATUS      current
    DESCRIPTION "Table."

    ::= { dpConfig 376 }

dpConfigAssemblyActionUserSecurityEntry OBJECT-TYPE
    SYNTAX      DPConfigAssemblyActionUserSecurityEntry
    MAX-ACCESS  not-accessible
    STATUS      current
    DESCRIPTION "Table row."
    INDEX { dpConfigAssemblyActionUserSecurityIndex, IMPLIED dpConfigAssemblyActionUserSecurityname }

    ::= { dpConfigAssemblyActionUserSecurityTable 1 }

DPConfigAssemblyActionUserSecurityEntry ::= SEQUENCE {
    dpConfigAssemblyActionUserSecurityIndex    Unsigned32,
    dpConfigAssemblyActionUserSecurityname    DisplayString
}

dpConfigAssemblyActionUserSecurityIndex OBJECT-TYPE
    SYNTAX      Unsigned32
    MAX-ACCESS  read-only
    STATUS      current
    DESCRIPTION "No description yet."

    ::= { dpConfigAssemblyActionUserSecurityEntry 1 }

dpConfigAssemblyActionUserSecurityname OBJECT-TYPE
    SYNTAX      DisplayString
    MAX-ACCESS  read-only
    STATUS      current
    DESCRIPTION "No description yet."

    ::= { dpConfigAssemblyActionUserSecurityEntry 2 }

--

dpConfigAPISecurityBasicAuthTable OBJECT-TYPE
    SYNTAX      SEQUENCE OF DPConfigAPISecurityBasicAuthEntry
    MAX-ACCESS  not-accessible
    STATUS      current
    DESCRIPTION
        "A basic authentication security definition selects a user registry to
        authenticate accesses to the API operations. When you use basic
        authentication, API users must provide a valid user name and password in
        the requests to access operations that require basic authentication.
        #b#Note:#/b# You cannot apply more than one basic authentication security
        definition to an API."

    ::= { dpConfig 377 }

dpConfigAPISecurityBasicAuthEntry OBJECT-TYPE
    SYNTAX      DPConfigAPISecurityBasicAuthEntry
    MAX-ACCESS  not-accessible
    STATUS      current
    DESCRIPTION "Table row."
    INDEX { dpConfigAPISecurityBasicAuthIndex, IMPLIED dpConfigAPISecurityBasicAuthname }

    ::= { dpConfigAPISecurityBasicAuthTable 1 }

DPConfigAPISecurityBasicAuthEntry ::= SEQUENCE {
    dpConfigAPISecurityBasicAuthIndex    Unsigned32,
    dpConfigAPISecurityBasicAuthname    DisplayString
}

dpConfigAPISecurityBasicAuthIndex OBJECT-TYPE
    SYNTAX      Unsigned32
    MAX-ACCESS  read-only
    STATUS      current
    DESCRIPTION "No description yet."

    ::= { dpConfigAPISecurityBasicAuthEntry 1 }

dpConfigAPISecurityBasicAuthname OBJECT-TYPE
    SYNTAX      DisplayString
    MAX-ACCESS  read-only
    STATUS      current
    DESCRIPTION "No description yet."

    ::= { dpConfigAPISecurityBasicAuthEntry 2 }

--

dpConfigAPISchemaTable OBJECT-TYPE
    SYNTAX      SEQUENCE OF DPConfigAPISchemaEntry
    MAX-ACCESS  not-accessible
    STATUS      current
    DESCRIPTION
        "An API schema configuration defines schemas to validate JSON, XML, WSDL,
        or SOAP messages for an API path or an API operation."

    ::= { dpConfig 378 }

dpConfigAPISchemaEntry OBJECT-TYPE
    SYNTAX      DPConfigAPISchemaEntry
    MAX-ACCESS  not-accessible
    STATUS      current
    DESCRIPTION "Table row."
    INDEX { dpConfigAPISchemaIndex, IMPLIED dpConfigAPISchemaname }

    ::= { dpConfigAPISchemaTable 1 }

DPConfigAPISchemaEntry ::= SEQUENCE {
    dpConfigAPISchemaIndex    Unsigned32,
    dpConfigAPISchemaname    DisplayString
}

dpConfigAPISchemaIndex OBJECT-TYPE
    SYNTAX      Unsigned32
    MAX-ACCESS  read-only
    STATUS      current
    DESCRIPTION "No description yet."

    ::= { dpConfigAPISchemaEntry 1 }

dpConfigAPISchemaname OBJECT-TYPE
    SYNTAX      DisplayString
    MAX-ACCESS  read-only
    STATUS      current
    DESCRIPTION "No description yet."

    ::= { dpConfigAPISchemaEntry 2 }

--

dpConfigAPIUserRegistryTable OBJECT-TYPE
    SYNTAX      SEQUENCE OF DPConfigAPIUserRegistryEntry
    MAX-ACCESS  not-accessible
    STATUS      current
    DESCRIPTION
        "The API user registry specifies the authentication mechanism to validate
        credentials."

    ::= { dpConfig 379 }

dpConfigAPIUserRegistryEntry OBJECT-TYPE
    SYNTAX      DPConfigAPIUserRegistryEntry
    MAX-ACCESS  not-accessible
    STATUS      current
    DESCRIPTION "Table row."
    INDEX { dpConfigAPIUserRegistryIndex, IMPLIED dpConfigAPIUserRegistryname }

    ::= { dpConfigAPIUserRegistryTable 1 }

DPConfigAPIUserRegistryEntry ::= SEQUENCE {
    dpConfigAPIUserRegistryIndex    Unsigned32,
    dpConfigAPIUserRegistryname    DisplayString
}

dpConfigAPIUserRegistryIndex OBJECT-TYPE
    SYNTAX      Unsigned32
    MAX-ACCESS  read-only
    STATUS      current
    DESCRIPTION "No description yet."

    ::= { dpConfigAPIUserRegistryEntry 1 }

dpConfigAPIUserRegistryname OBJECT-TYPE
    SYNTAX      DisplayString
    MAX-ACCESS  read-only
    STATUS      current
    DESCRIPTION "No description yet."

    ::= { dpConfigAPIUserRegistryEntry 2 }

--

dpConfigAPIAuthURLRegistryTable OBJECT-TYPE
    SYNTAX      SEQUENCE OF DPConfigAPIAuthURLRegistryEntry
    MAX-ACCESS  not-accessible
    STATUS      current
    DESCRIPTION "Table."

    ::= { dpConfig 380 }

dpConfigAPIAuthURLRegistryEntry OBJECT-TYPE
    SYNTAX      DPConfigAPIAuthURLRegistryEntry
    MAX-ACCESS  not-accessible
    STATUS      current
    DESCRIPTION "Table row."
    INDEX { dpConfigAPIAuthURLRegistryIndex, IMPLIED dpConfigAPIAuthURLRegistryname }

    ::= { dpConfigAPIAuthURLRegistryTable 1 }

DPConfigAPIAuthURLRegistryEntry ::= SEQUENCE {
    dpConfigAPIAuthURLRegistryIndex    Unsigned32,
    dpConfigAPIAuthURLRegistryname    DisplayString
}

dpConfigAPIAuthURLRegistryIndex OBJECT-TYPE
    SYNTAX      Unsigned32
    MAX-ACCESS  read-only
    STATUS      current
    DESCRIPTION "No description yet."

    ::= { dpConfigAPIAuthURLRegistryEntry 1 }

dpConfigAPIAuthURLRegistryname OBJECT-TYPE
    SYNTAX      DisplayString
    MAX-ACCESS  read-only
    STATUS      current
    DESCRIPTION "No description yet."

    ::= { dpConfigAPIAuthURLRegistryEntry 2 }

--

dpConfigAssemblyActionClientSecurityTable OBJECT-TYPE
    SYNTAX      SEQUENCE OF DPConfigAssemblyActionClientSecurityEntry
    MAX-ACCESS  not-accessible
    STATUS      current
    DESCRIPTION "Table."

    ::= { dpConfig 381 }

dpConfigAssemblyActionClientSecurityEntry OBJECT-TYPE
    SYNTAX      DPConfigAssemblyActionClientSecurityEntry
    MAX-ACCESS  not-accessible
    STATUS      current
    DESCRIPTION "Table row."
    INDEX { dpConfigAssemblyActionClientSecurityIndex, IMPLIED dpConfigAssemblyActionClientSecurityname }

    ::= { dpConfigAssemblyActionClientSecurityTable 1 }

DPConfigAssemblyActionClientSecurityEntry ::= SEQUENCE {
    dpConfigAssemblyActionClientSecurityIndex    Unsigned32,
    dpConfigAssemblyActionClientSecurityname    DisplayString
}

dpConfigAssemblyActionClientSecurityIndex OBJECT-TYPE
    SYNTAX      Unsigned32
    MAX-ACCESS  read-only
    STATUS      current
    DESCRIPTION "No description yet."

    ::= { dpConfigAssemblyActionClientSecurityEntry 1 }

dpConfigAssemblyActionClientSecurityname OBJECT-TYPE
    SYNTAX      DisplayString
    MAX-ACCESS  read-only
    STATUS      current
    DESCRIPTION "No description yet."

    ::= { dpConfigAssemblyActionClientSecurityEntry 2 }

--

dpConfigRestMgmtInterfaceTable OBJECT-TYPE
    SYNTAX      SEQUENCE OF DPConfigRestMgmtInterfaceEntry
    MAX-ACCESS  not-accessible
    STATUS      current
    DESCRIPTION
        "Configure the REST management interface."

    ::= { dpConfig 400 }

dpConfigRestMgmtInterfaceEntry OBJECT-TYPE
    SYNTAX      DPConfigRestMgmtInterfaceEntry
    MAX-ACCESS  not-accessible
    STATUS      current
    DESCRIPTION "Table row."
    INDEX { dpConfigRestMgmtInterfaceIndex, IMPLIED dpConfigRestMgmtInterfacename }

    ::= { dpConfigRestMgmtInterfaceTable 1 }

DPConfigRestMgmtInterfaceEntry ::= SEQUENCE {
    dpConfigRestMgmtInterfaceIndex    Unsigned32,
    dpConfigRestMgmtInterfacename    DisplayString
}

dpConfigRestMgmtInterfaceIndex OBJECT-TYPE
    SYNTAX      Unsigned32
    MAX-ACCESS  read-only
    STATUS      current
    DESCRIPTION "No description yet."

    ::= { dpConfigRestMgmtInterfaceEntry 1 }

dpConfigRestMgmtInterfacename OBJECT-TYPE
    SYNTAX      DisplayString
    MAX-ACCESS  read-only
    STATUS      current
    DESCRIPTION "No description yet."

    ::= { dpConfigRestMgmtInterfaceEntry 2 }

--

dpConfigSecureBackupModeTable OBJECT-TYPE
    SYNTAX      SEQUENCE OF DPConfigSecureBackupModeEntry
    MAX-ACCESS  not-accessible
    STATUS      current
    DESCRIPTION
        "Sets the backup operational mode. This mode controls whether a
        secure-backup is allowed. After this mode is set, it cannot be changed.
        Operational modes are set the first time the DataPower Gateway is started."

    ::= { dpConfig 402 }

dpConfigSecureBackupModeEntry OBJECT-TYPE
    SYNTAX      DPConfigSecureBackupModeEntry
    MAX-ACCESS  not-accessible
    STATUS      current
    DESCRIPTION "Table row."
    INDEX { dpConfigSecureBackupModeIndex, IMPLIED dpConfigSecureBackupModename }

    ::= { dpConfigSecureBackupModeTable 1 }

DPConfigSecureBackupModeEntry ::= SEQUENCE {
    dpConfigSecureBackupModeIndex    Unsigned32,
    dpConfigSecureBackupModename    DisplayString
}

dpConfigSecureBackupModeIndex OBJECT-TYPE
    SYNTAX      Unsigned32
    MAX-ACCESS  read-only
    STATUS      current
    DESCRIPTION "No description yet."

    ::= { dpConfigSecureBackupModeEntry 1 }

dpConfigSecureBackupModename OBJECT-TYPE
    SYNTAX      DisplayString
    MAX-ACCESS  read-only
    STATUS      current
    DESCRIPTION "No description yet."

    ::= { dpConfigSecureBackupModeEntry 2 }

--

dpConfigAPIConnectGatewayServiceTable OBJECT-TYPE
    SYNTAX      SEQUENCE OF DPConfigAPIConnectGatewayServiceEntry
    MAX-ACCESS  not-accessible
    STATUS      current
    DESCRIPTION
        "The API Connect Gateway Service defines the connection to API Connect and
        settings to use for creating the gateway for service. When an API Connect
        Gateway Service is configured and starts to work, DataPower starts a
        process that retrieves data from API Connect, transmits into DataPower
        Gateway, and stores the data as DataPower configurations that the API
        gateway can subsequently use to handle API calls."

    ::= { dpConfig 403 }

dpConfigAPIConnectGatewayServiceEntry OBJECT-TYPE
    SYNTAX      DPConfigAPIConnectGatewayServiceEntry
    MAX-ACCESS  not-accessible
    STATUS      current
    DESCRIPTION "Table row."
    INDEX { dpConfigAPIConnectGatewayServiceIndex, IMPLIED dpConfigAPIConnectGatewayServicename }

    ::= { dpConfigAPIConnectGatewayServiceTable 1 }

DPConfigAPIConnectGatewayServiceEntry ::= SEQUENCE {
    dpConfigAPIConnectGatewayServiceIndex    Unsigned32,
    dpConfigAPIConnectGatewayServicename    DisplayString
}

dpConfigAPIConnectGatewayServiceIndex OBJECT-TYPE
    SYNTAX      Unsigned32
    MAX-ACCESS  read-only
    STATUS      current
    DESCRIPTION "No description yet."

    ::= { dpConfigAPIConnectGatewayServiceEntry 1 }

dpConfigAPIConnectGatewayServicename OBJECT-TYPE
    SYNTAX      DisplayString
    MAX-ACCESS  read-only
    STATUS      current
    DESCRIPTION "No description yet."

    ::= { dpConfigAPIConnectGatewayServiceEntry 2 }

--

dpConfigStandaloneStandbyControlInterfaceTable OBJECT-TYPE
    SYNTAX      SEQUENCE OF DPConfigStandaloneStandbyControlInterfaceEntry
    MAX-ACCESS  not-accessible
    STATUS      current
    DESCRIPTION
        "There is a StandaloneStandbyControlInterface for each kernel interface
        that is capable of being used with StandaloneStandbyControl. This is the
        interface being referred to in StandaloneStandbyControl and
        YieldStandaloneStandby."

    ::= { dpConfig 450 }

dpConfigStandaloneStandbyControlInterfaceEntry OBJECT-TYPE
    SYNTAX      DPConfigStandaloneStandbyControlInterfaceEntry
    MAX-ACCESS  not-accessible
    STATUS      current
    DESCRIPTION "Table row."
    INDEX { dpConfigStandaloneStandbyControlInterfaceIndex, IMPLIED dpConfigStandaloneStandbyControlInterfacename }

    ::= { dpConfigStandaloneStandbyControlInterfaceTable 1 }

DPConfigStandaloneStandbyControlInterfaceEntry ::= SEQUENCE {
    dpConfigStandaloneStandbyControlInterfaceIndex    Unsigned32,
    dpConfigStandaloneStandbyControlInterfacename    DisplayString
}

dpConfigStandaloneStandbyControlInterfaceIndex OBJECT-TYPE
    SYNTAX      Unsigned32
    MAX-ACCESS  read-only
    STATUS      current
    DESCRIPTION "No description yet."

    ::= { dpConfigStandaloneStandbyControlInterfaceEntry 1 }

dpConfigStandaloneStandbyControlInterfacename OBJECT-TYPE
    SYNTAX      DisplayString
    MAX-ACCESS  read-only
    STATUS      current
    DESCRIPTION "No description yet."

    ::= { dpConfigStandaloneStandbyControlInterfaceEntry 2 }

--

dpConfigStandaloneStandbyControlTable OBJECT-TYPE
    SYNTAX      SEQUENCE OF DPConfigStandaloneStandbyControlEntry
    MAX-ACCESS  not-accessible
    STATUS      current
    DESCRIPTION
        "The standby configuration defines the policies for the group that this
        interface is a member. A standby group is the collection of interfaces on
        different appliances in the multicast domain that share the responsibility
        for one virtual IP address. When at least one member of a standby group
        can reach the multicast domain, the virtual IP group receives the traffic.
        #b#Attention:#/b# Virtual IP addresses in a standby configuration must be
        IPv4 addresses."

    ::= { dpConfig 451 }

dpConfigStandaloneStandbyControlEntry OBJECT-TYPE
    SYNTAX      DPConfigStandaloneStandbyControlEntry
    MAX-ACCESS  not-accessible
    STATUS      current
    DESCRIPTION "Table row."
    INDEX { dpConfigStandaloneStandbyControlIndex, IMPLIED dpConfigStandaloneStandbyControlname }

    ::= { dpConfigStandaloneStandbyControlTable 1 }

DPConfigStandaloneStandbyControlEntry ::= SEQUENCE {
    dpConfigStandaloneStandbyControlIndex    Unsigned32,
    dpConfigStandaloneStandbyControlname    DisplayString
}

dpConfigStandaloneStandbyControlIndex OBJECT-TYPE
    SYNTAX      Unsigned32
    MAX-ACCESS  read-only
    STATUS      current
    DESCRIPTION "No description yet."

    ::= { dpConfigStandaloneStandbyControlEntry 1 }

dpConfigStandaloneStandbyControlname OBJECT-TYPE
    SYNTAX      DisplayString
    MAX-ACCESS  read-only
    STATUS      current
    DESCRIPTION "No description yet."

    ::= { dpConfigStandaloneStandbyControlEntry 2 }

--

dpConfigTenantTable OBJECT-TYPE
    SYNTAX      SEQUENCE OF DPConfigTenantEntry
    MAX-ACCESS  not-accessible
    STATUS      current
    DESCRIPTION
        "Modify the connection details for a tenant. Each tenant and the landlord
        have different management interfaces and a different quota enforcement
        server. When you define the addresses for tenant management interfaces,
        use an explicit IP address to isolate tenant management traffic from
        landlord management traffic. Tenant services that use the IP address
        values of 0.0.0.0 or :: can cause port contention on the landlord. When
        you define listening ports for tenant management interfaces and for the
        quota enforcement server, ensure that they are unique across the tenants
        and the landlord."

    ::= { dpConfig 452 }

dpConfigTenantEntry OBJECT-TYPE
    SYNTAX      DPConfigTenantEntry
    MAX-ACCESS  not-accessible
    STATUS      current
    DESCRIPTION "Table row."
    INDEX { dpConfigTenantIndex, IMPLIED dpConfigTenantname }

    ::= { dpConfigTenantTable 1 }

DPConfigTenantEntry ::= SEQUENCE {
    dpConfigTenantIndex    Unsigned32,
    dpConfigTenantname    DisplayString
}

dpConfigTenantIndex OBJECT-TYPE
    SYNTAX      Unsigned32
    MAX-ACCESS  read-only
    STATUS      current
    DESCRIPTION "No description yet."

    ::= { dpConfigTenantEntry 1 }

dpConfigTenantname OBJECT-TYPE
    SYNTAX      DisplayString
    MAX-ACCESS  read-only
    STATUS      current
    DESCRIPTION "No description yet."

    ::= { dpConfigTenantEntry 2 }

--

dpConfigSocialLoginPolicyTable OBJECT-TYPE
    SYNTAX      SEQUENCE OF DPConfigSocialLoginPolicyEntry
    MAX-ACCESS  not-accessible
    STATUS      current
    DESCRIPTION
        "DataPower can act as an OpenID Connect client. In this case, a social
        login policy enables DataPower to redirect the user to a social login
        provider like Google for user authentication and consent for
        authorization."

    ::= { dpConfig 455 }

dpConfigSocialLoginPolicyEntry OBJECT-TYPE
    SYNTAX      DPConfigSocialLoginPolicyEntry
    MAX-ACCESS  not-accessible
    STATUS      current
    DESCRIPTION "Table row."
    INDEX { dpConfigSocialLoginPolicyIndex, IMPLIED dpConfigSocialLoginPolicyname }

    ::= { dpConfigSocialLoginPolicyTable 1 }

DPConfigSocialLoginPolicyEntry ::= SEQUENCE {
    dpConfigSocialLoginPolicyIndex    Unsigned32,
    dpConfigSocialLoginPolicyname    DisplayString
}

dpConfigSocialLoginPolicyIndex OBJECT-TYPE
    SYNTAX      Unsigned32
    MAX-ACCESS  read-only
    STATUS      current
    DESCRIPTION "No description yet."

    ::= { dpConfigSocialLoginPolicyEntry 1 }

dpConfigSocialLoginPolicyname OBJECT-TYPE
    SYNTAX      DisplayString
    MAX-ACCESS  read-only
    STATUS      current
    DESCRIPTION "No description yet."

    ::= { dpConfigSocialLoginPolicyEntry 2 }

--

dpConfigEBMS3SourceProtocolHandlerTable OBJECT-TYPE
    SYNTAX      SEQUENCE OF DPConfigEBMS3SourceProtocolHandlerEntry
    MAX-ACCESS  not-accessible
    STATUS      current
    DESCRIPTION
        "The configuration for an ebMS3 protocol handler."

    ::= { dpConfig 456 }

dpConfigEBMS3SourceProtocolHandlerEntry OBJECT-TYPE
    SYNTAX      DPConfigEBMS3SourceProtocolHandlerEntry
    MAX-ACCESS  not-accessible
    STATUS      current
    DESCRIPTION "Table row."
    INDEX { dpConfigEBMS3SourceProtocolHandlerIndex, IMPLIED dpConfigEBMS3SourceProtocolHandlername }

    ::= { dpConfigEBMS3SourceProtocolHandlerTable 1 }

DPConfigEBMS3SourceProtocolHandlerEntry ::= SEQUENCE {
    dpConfigEBMS3SourceProtocolHandlerIndex    Unsigned32,
    dpConfigEBMS3SourceProtocolHandlername    DisplayString
}

dpConfigEBMS3SourceProtocolHandlerIndex OBJECT-TYPE
    SYNTAX      Unsigned32
    MAX-ACCESS  read-only
    STATUS      current
    DESCRIPTION "No description yet."

    ::= { dpConfigEBMS3SourceProtocolHandlerEntry 1 }

dpConfigEBMS3SourceProtocolHandlername OBJECT-TYPE
    SYNTAX      DisplayString
    MAX-ACCESS  read-only
    STATUS      current
    DESCRIPTION "No description yet."

    ::= { dpConfigEBMS3SourceProtocolHandlerEntry 2 }

--

dpConfigDFDLSettingsTable OBJECT-TYPE
    SYNTAX      SEQUENCE OF DPConfigDFDLSettingsEntry
    MAX-ACCESS  not-accessible
    STATUS      current
    DESCRIPTION
        "The DFDL settings specify constraints for parsing and serializing binary
        data, where the data is modeled by a DFDL schema."

    ::= { dpConfig 460 }

dpConfigDFDLSettingsEntry OBJECT-TYPE
    SYNTAX      DPConfigDFDLSettingsEntry
    MAX-ACCESS  not-accessible
    STATUS      current
    DESCRIPTION "Table row."
    INDEX { dpConfigDFDLSettingsIndex, IMPLIED dpConfigDFDLSettingsname }

    ::= { dpConfigDFDLSettingsTable 1 }

DPConfigDFDLSettingsEntry ::= SEQUENCE {
    dpConfigDFDLSettingsIndex    Unsigned32,
    dpConfigDFDLSettingsname    DisplayString
}

dpConfigDFDLSettingsIndex OBJECT-TYPE
    SYNTAX      Unsigned32
    MAX-ACCESS  read-only
    STATUS      current
    DESCRIPTION "No description yet."

    ::= { dpConfigDFDLSettingsEntry 1 }

dpConfigDFDLSettingsname OBJECT-TYPE
    SYNTAX      DisplayString
    MAX-ACCESS  read-only
    STATUS      current
    DESCRIPTION "No description yet."

    ::= { dpConfigDFDLSettingsEntry 2 }

--

dpConfigParseSettingsTable OBJECT-TYPE
    SYNTAX      SEQUENCE OF DPConfigParseSettingsEntry
    MAX-ACCESS  not-accessible
    STATUS      current
    DESCRIPTION
        "Specifies the constraints for parsing document. The set constraints
        overwrite the parser limits that are specified in the XML Manager."

    ::= { dpConfig 461 }

dpConfigParseSettingsEntry OBJECT-TYPE
    SYNTAX      DPConfigParseSettingsEntry
    MAX-ACCESS  not-accessible
    STATUS      current
    DESCRIPTION "Table row."
    INDEX { dpConfigParseSettingsIndex, IMPLIED dpConfigParseSettingsname }

    ::= { dpConfigParseSettingsTable 1 }

DPConfigParseSettingsEntry ::= SEQUENCE {
    dpConfigParseSettingsIndex    Unsigned32,
    dpConfigParseSettingsname    DisplayString
}

dpConfigParseSettingsIndex OBJECT-TYPE
    SYNTAX      Unsigned32
    MAX-ACCESS  read-only
    STATUS      current
    DESCRIPTION "No description yet."

    ::= { dpConfigParseSettingsEntry 1 }

dpConfigParseSettingsname OBJECT-TYPE
    SYNTAX      DisplayString
    MAX-ACCESS  read-only
    STATUS      current
    DESCRIPTION "No description yet."

    ::= { dpConfigParseSettingsEntry 2 }

--

dpConfigAccessProfileTable OBJECT-TYPE
    SYNTAX      SEQUENCE OF DPConfigAccessProfileEntry
    MAX-ACCESS  not-accessible
    STATUS      current
    DESCRIPTION
        "Create or edit an access profile."

    ::= { dpConfig 462 }

dpConfigAccessProfileEntry OBJECT-TYPE
    SYNTAX      DPConfigAccessProfileEntry
    MAX-ACCESS  not-accessible
    STATUS      current
    DESCRIPTION "Table row."
    INDEX { dpConfigAccessProfileIndex, IMPLIED dpConfigAccessProfilename }

    ::= { dpConfigAccessProfileTable 1 }

DPConfigAccessProfileEntry ::= SEQUENCE {
    dpConfigAccessProfileIndex    Unsigned32,
    dpConfigAccessProfilename    DisplayString
}

dpConfigAccessProfileIndex OBJECT-TYPE
    SYNTAX      Unsigned32
    MAX-ACCESS  read-only
    STATUS      current
    DESCRIPTION "No description yet."

    ::= { dpConfigAccessProfileEntry 1 }

dpConfigAccessProfilename OBJECT-TYPE
    SYNTAX      DisplayString
    MAX-ACCESS  read-only
    STATUS      current
    DESCRIPTION "No description yet."

    ::= { dpConfigAccessProfileEntry 2 }

--

dpConfigILMTScannerTable OBJECT-TYPE
    SYNTAX      SEQUENCE OF DPConfigILMTScannerEntry
    MAX-ACCESS  not-accessible
    STATUS      current
    DESCRIPTION
        "For DataPower Gateway for VMware, you can create IBM License Metric Tool
        packages on a schedule or on demand. Independent of how you create
        packages, these packages with the scan results are created in the
        local:///ilmt/output directory. The package name includes the time stamp
        of when the package was created. By default, the DataPower Gateway does
        not create ILMT packages. To create packages on a schedule, you must
        enable the disconnected ILMT scanner. When enabled, packages are once a
        week. You can change scan interval. To create a package on demand, you
        force a scan."

    ::= { dpConfig 500 }

dpConfigILMTScannerEntry OBJECT-TYPE
    SYNTAX      DPConfigILMTScannerEntry
    MAX-ACCESS  not-accessible
    STATUS      current
    DESCRIPTION "Table row."
    INDEX { dpConfigILMTScannerIndex, IMPLIED dpConfigILMTScannername }

    ::= { dpConfigILMTScannerTable 1 }

DPConfigILMTScannerEntry ::= SEQUENCE {
    dpConfigILMTScannerIndex    Unsigned32,
    dpConfigILMTScannername    DisplayString
}

dpConfigILMTScannerIndex OBJECT-TYPE
    SYNTAX      Unsigned32
    MAX-ACCESS  read-only
    STATUS      current
    DESCRIPTION "No description yet."

    ::= { dpConfigILMTScannerEntry 1 }

dpConfigILMTScannername OBJECT-TYPE
    SYNTAX      DisplayString
    MAX-ACCESS  read-only
    STATUS      current
    DESCRIPTION "No description yet."

    ::= { dpConfigILMTScannerEntry 2 }

--

dpConfigQuotaEnforcementServerTable OBJECT-TYPE
    SYNTAX      SEQUENCE OF DPConfigQuotaEnforcementServerEntry
    MAX-ACCESS  not-accessible
    STATUS      current
    DESCRIPTION
        "On each DataPower appliance, you configure the quota enforcement server to
        store the thresholds and associated metadata in memory or persist them on
        the RAID volume. The quota enforcement server can work in standalone mode
        or peer group mode. A peer group is collection of at least three DataPower
        appliances across which quota enforcement is implemented. In each peer
        group, one appliance is the master and other appliances are slaves.
        Failover might occur when the master becomes unavailable. When you enable
        the peer group mode, the appropriate configuration properties are
        displayed. You must configure the connection among peers. Based on your
        requirements for quota enforcement, you can enable or disable strict mode.
        Strict mode affects data-consistency across the peer group. When strict
        mode is enabled, the following effects are caused: When the master is
        operational and when strict mode of all appliances in a peer group is
        enabled, threshold synchronization is more frequent to ensure
        data-consistency across the peer group. However, more network bandwidth is
        used. Therefore, strict mode is suitable for peers in the same data
        center. When the master becomes unavailable, before failover occurs, the
        slave with enabled strict mode cannot process the request. If service
        performance and availability are more important than data-consistency, you
        can disable strict mode for the slave so that this slave can process the
        request. The slave with disabled strict mode writes the threshold and
        associated metadata to the local data storage. After failover occurs, the
        connection is resumed between the slave and the new master. The threshold
        and associated metadata stored by the slave might be overwritten by the
        new master when the new master synchronizes the data to all slaves.
        Data-consistency might be affected across the peer group. By default, data
        is stored in memory and quota enforcement server works in standalone mode."

    ::= { dpConfig 504 }

dpConfigQuotaEnforcementServerEntry OBJECT-TYPE
    SYNTAX      DPConfigQuotaEnforcementServerEntry
    MAX-ACCESS  not-accessible
    STATUS      current
    DESCRIPTION "Table row."
    INDEX { dpConfigQuotaEnforcementServerIndex, IMPLIED dpConfigQuotaEnforcementServername }

    ::= { dpConfigQuotaEnforcementServerTable 1 }

DPConfigQuotaEnforcementServerEntry ::= SEQUENCE {
    dpConfigQuotaEnforcementServerIndex    Unsigned32,
    dpConfigQuotaEnforcementServername    DisplayString
}

dpConfigQuotaEnforcementServerIndex OBJECT-TYPE
    SYNTAX      Unsigned32
    MAX-ACCESS  read-only
    STATUS      current
    DESCRIPTION "No description yet."

    ::= { dpConfigQuotaEnforcementServerEntry 1 }

dpConfigQuotaEnforcementServername OBJECT-TYPE
    SYNTAX      DisplayString
    MAX-ACCESS  read-only
    STATUS      current
    DESCRIPTION "No description yet."

    ::= { dpConfigQuotaEnforcementServerEntry 2 }

--

dpConfigSSHServerProfileTable OBJECT-TYPE
    SYNTAX      SEQUENCE OF DPConfigSSHServerProfileEntry
    MAX-ACCESS  not-accessible
    STATUS      current
    DESCRIPTION
        "Modify the configuration of the SSH server. #b#Warning#/b#: You must
        reboot the system for the changes to take effect."

    ::= { dpConfig 505 }

dpConfigSSHServerProfileEntry OBJECT-TYPE
    SYNTAX      DPConfigSSHServerProfileEntry
    MAX-ACCESS  not-accessible
    STATUS      current
    DESCRIPTION "Table row."
    INDEX { dpConfigSSHServerProfileIndex, IMPLIED dpConfigSSHServerProfilename }

    ::= { dpConfigSSHServerProfileTable 1 }

DPConfigSSHServerProfileEntry ::= SEQUENCE {
    dpConfigSSHServerProfileIndex    Unsigned32,
    dpConfigSSHServerProfilename    DisplayString
}

dpConfigSSHServerProfileIndex OBJECT-TYPE
    SYNTAX      Unsigned32
    MAX-ACCESS  read-only
    STATUS      current
    DESCRIPTION "No description yet."

    ::= { dpConfigSSHServerProfileEntry 1 }

dpConfigSSHServerProfilename OBJECT-TYPE
    SYNTAX      DisplayString
    MAX-ACCESS  read-only
    STATUS      current
    DESCRIPTION "No description yet."

    ::= { dpConfigSSHServerProfileEntry 2 }

--

dpConfigQuotaEnforcementMatchClassTable OBJECT-TYPE
    SYNTAX      SEQUENCE OF DPConfigQuotaEnforcementMatchClassEntry
    MAX-ACCESS  not-accessible
    STATUS      current
    DESCRIPTION
        "Quota enforcement match class."

    ::= { dpConfig 506 }

dpConfigQuotaEnforcementMatchClassEntry OBJECT-TYPE
    SYNTAX      DPConfigQuotaEnforcementMatchClassEntry
    MAX-ACCESS  not-accessible
    STATUS      current
    DESCRIPTION "Table row."
    INDEX { dpConfigQuotaEnforcementMatchClassIndex, IMPLIED dpConfigQuotaEnforcementMatchClassname }

    ::= { dpConfigQuotaEnforcementMatchClassTable 1 }

DPConfigQuotaEnforcementMatchClassEntry ::= SEQUENCE {
    dpConfigQuotaEnforcementMatchClassIndex    Unsigned32,
    dpConfigQuotaEnforcementMatchClassname    DisplayString
}

dpConfigQuotaEnforcementMatchClassIndex OBJECT-TYPE
    SYNTAX      Unsigned32
    MAX-ACCESS  read-only
    STATUS      current
    DESCRIPTION "No description yet."

    ::= { dpConfigQuotaEnforcementMatchClassEntry 1 }

dpConfigQuotaEnforcementMatchClassname OBJECT-TYPE
    SYNTAX      DisplayString
    MAX-ACCESS  read-only
    STATUS      current
    DESCRIPTION "No description yet."

    ::= { dpConfigQuotaEnforcementMatchClassEntry 2 }

--

dpConfigQuotaEnforcementGroupClassTable OBJECT-TYPE
    SYNTAX      SEQUENCE OF DPConfigQuotaEnforcementGroupClassEntry
    MAX-ACCESS  not-accessible
    STATUS      current
    DESCRIPTION
        "Quota enforcement group class."

    ::= { dpConfig 507 }

dpConfigQuotaEnforcementGroupClassEntry OBJECT-TYPE
    SYNTAX      DPConfigQuotaEnforcementGroupClassEntry
    MAX-ACCESS  not-accessible
    STATUS      current
    DESCRIPTION "Table row."
    INDEX { dpConfigQuotaEnforcementGroupClassIndex, IMPLIED dpConfigQuotaEnforcementGroupClassname }

    ::= { dpConfigQuotaEnforcementGroupClassTable 1 }

DPConfigQuotaEnforcementGroupClassEntry ::= SEQUENCE {
    dpConfigQuotaEnforcementGroupClassIndex    Unsigned32,
    dpConfigQuotaEnforcementGroupClassname    DisplayString
}

dpConfigQuotaEnforcementGroupClassIndex OBJECT-TYPE
    SYNTAX      Unsigned32
    MAX-ACCESS  read-only
    STATUS      current
    DESCRIPTION "No description yet."

    ::= { dpConfigQuotaEnforcementGroupClassEntry 1 }

dpConfigQuotaEnforcementGroupClassname OBJECT-TYPE
    SYNTAX      DisplayString
    MAX-ACCESS  read-only
    STATUS      current
    DESCRIPTION "No description yet."

    ::= { dpConfigQuotaEnforcementGroupClassEntry 2 }

--

dpConfigQuotaEnforcementAlgorithmTable OBJECT-TYPE
    SYNTAX      SEQUENCE OF DPConfigQuotaEnforcementAlgorithmEntry
    MAX-ACCESS  not-accessible
    STATUS      current
    DESCRIPTION
        "Quota enforcement algorithm."

    ::= { dpConfig 508 }

dpConfigQuotaEnforcementAlgorithmEntry OBJECT-TYPE
    SYNTAX      DPConfigQuotaEnforcementAlgorithmEntry
    MAX-ACCESS  not-accessible
    STATUS      current
    DESCRIPTION "Table row."
    INDEX { dpConfigQuotaEnforcementAlgorithmIndex, IMPLIED dpConfigQuotaEnforcementAlgorithmname }

    ::= { dpConfigQuotaEnforcementAlgorithmTable 1 }

DPConfigQuotaEnforcementAlgorithmEntry ::= SEQUENCE {
    dpConfigQuotaEnforcementAlgorithmIndex    Unsigned32,
    dpConfigQuotaEnforcementAlgorithmname    DisplayString
}

dpConfigQuotaEnforcementAlgorithmIndex OBJECT-TYPE
    SYNTAX      Unsigned32
    MAX-ACCESS  read-only
    STATUS      current
    DESCRIPTION "No description yet."

    ::= { dpConfigQuotaEnforcementAlgorithmEntry 1 }

dpConfigQuotaEnforcementAlgorithmname OBJECT-TYPE
    SYNTAX      DisplayString
    MAX-ACCESS  read-only
    STATUS      current
    DESCRIPTION "No description yet."

    ::= { dpConfigQuotaEnforcementAlgorithmEntry 2 }

--

dpConfigQuotaEnforcementScheduleTable OBJECT-TYPE
    SYNTAX      SEQUENCE OF DPConfigQuotaEnforcementScheduleEntry
    MAX-ACCESS  not-accessible
    STATUS      current
    DESCRIPTION
        "Quota enforcement schedule."

    ::= { dpConfig 509 }

dpConfigQuotaEnforcementScheduleEntry OBJECT-TYPE
    SYNTAX      DPConfigQuotaEnforcementScheduleEntry
    MAX-ACCESS  not-accessible
    STATUS      current
    DESCRIPTION "Table row."
    INDEX { dpConfigQuotaEnforcementScheduleIndex, IMPLIED dpConfigQuotaEnforcementSchedulename }

    ::= { dpConfigQuotaEnforcementScheduleTable 1 }

DPConfigQuotaEnforcementScheduleEntry ::= SEQUENCE {
    dpConfigQuotaEnforcementScheduleIndex    Unsigned32,
    dpConfigQuotaEnforcementSchedulename    DisplayString
}

dpConfigQuotaEnforcementScheduleIndex OBJECT-TYPE
    SYNTAX      Unsigned32
    MAX-ACCESS  read-only
    STATUS      current
    DESCRIPTION "No description yet."

    ::= { dpConfigQuotaEnforcementScheduleEntry 1 }

dpConfigQuotaEnforcementSchedulename OBJECT-TYPE
    SYNTAX      DisplayString
    MAX-ACCESS  read-only
    STATUS      current
    DESCRIPTION "No description yet."

    ::= { dpConfigQuotaEnforcementScheduleEntry 2 }

--

dpConfigSSHDomainClientProfileTable OBJECT-TYPE
    SYNTAX      SEQUENCE OF DPConfigSSHDomainClientProfileEntry
    MAX-ACCESS  not-accessible
    STATUS      current
    DESCRIPTION
        "Modify the list of supported SSH cipher suites for the domain."

    ::= { dpConfig 510 }

dpConfigSSHDomainClientProfileEntry OBJECT-TYPE
    SYNTAX      DPConfigSSHDomainClientProfileEntry
    MAX-ACCESS  not-accessible
    STATUS      current
    DESCRIPTION "Table row."
    INDEX { dpConfigSSHDomainClientProfileIndex, IMPLIED dpConfigSSHDomainClientProfilename }

    ::= { dpConfigSSHDomainClientProfileTable 1 }

DPConfigSSHDomainClientProfileEntry ::= SEQUENCE {
    dpConfigSSHDomainClientProfileIndex    Unsigned32,
    dpConfigSSHDomainClientProfilename    DisplayString
}

dpConfigSSHDomainClientProfileIndex OBJECT-TYPE
    SYNTAX      Unsigned32
    MAX-ACCESS  read-only
    STATUS      current
    DESCRIPTION "No description yet."

    ::= { dpConfigSSHDomainClientProfileEntry 1 }

dpConfigSSHDomainClientProfilename OBJECT-TYPE
    SYNTAX      DisplayString
    MAX-ACCESS  read-only
    STATUS      current
    DESCRIPTION "No description yet."

    ::= { dpConfigSSHDomainClientProfileEntry 2 }

--

dpConfigQuotaEnforcementPolicyGroupTable OBJECT-TYPE
    SYNTAX      SEQUENCE OF DPConfigQuotaEnforcementPolicyGroupEntry
    MAX-ACCESS  not-accessible
    STATUS      current
    DESCRIPTION
        "Quota enforcement policy group."

    ::= { dpConfig 511 }

dpConfigQuotaEnforcementPolicyGroupEntry OBJECT-TYPE
    SYNTAX      DPConfigQuotaEnforcementPolicyGroupEntry
    MAX-ACCESS  not-accessible
    STATUS      current
    DESCRIPTION "Table row."
    INDEX { dpConfigQuotaEnforcementPolicyGroupIndex, IMPLIED dpConfigQuotaEnforcementPolicyGroupname }

    ::= { dpConfigQuotaEnforcementPolicyGroupTable 1 }

DPConfigQuotaEnforcementPolicyGroupEntry ::= SEQUENCE {
    dpConfigQuotaEnforcementPolicyGroupIndex    Unsigned32,
    dpConfigQuotaEnforcementPolicyGroupname    DisplayString
}

dpConfigQuotaEnforcementPolicyGroupIndex OBJECT-TYPE
    SYNTAX      Unsigned32
    MAX-ACCESS  read-only
    STATUS      current
    DESCRIPTION "No description yet."

    ::= { dpConfigQuotaEnforcementPolicyGroupEntry 1 }

dpConfigQuotaEnforcementPolicyGroupname OBJECT-TYPE
    SYNTAX      DisplayString
    MAX-ACCESS  read-only
    STATUS      current
    DESCRIPTION "No description yet."

    ::= { dpConfigQuotaEnforcementPolicyGroupEntry 2 }

--

dpConfigQuotaEnforcementPolicyBaseTable OBJECT-TYPE
    SYNTAX      SEQUENCE OF DPConfigQuotaEnforcementPolicyBaseEntry
    MAX-ACCESS  not-accessible
    STATUS      current
    DESCRIPTION "Table."

    ::= { dpConfig 512 }

dpConfigQuotaEnforcementPolicyBaseEntry OBJECT-TYPE
    SYNTAX      DPConfigQuotaEnforcementPolicyBaseEntry
    MAX-ACCESS  not-accessible
    STATUS      current
    DESCRIPTION "Table row."
    INDEX { dpConfigQuotaEnforcementPolicyBaseIndex, IMPLIED dpConfigQuotaEnforcementPolicyBasename }

    ::= { dpConfigQuotaEnforcementPolicyBaseTable 1 }

DPConfigQuotaEnforcementPolicyBaseEntry ::= SEQUENCE {
    dpConfigQuotaEnforcementPolicyBaseIndex    Unsigned32,
    dpConfigQuotaEnforcementPolicyBasename    DisplayString
}

dpConfigQuotaEnforcementPolicyBaseIndex OBJECT-TYPE
    SYNTAX      Unsigned32
    MAX-ACCESS  read-only
    STATUS      current
    DESCRIPTION "No description yet."

    ::= { dpConfigQuotaEnforcementPolicyBaseEntry 1 }

dpConfigQuotaEnforcementPolicyBasename OBJECT-TYPE
    SYNTAX      DisplayString
    MAX-ACCESS  read-only
    STATUS      current
    DESCRIPTION "No description yet."

    ::= { dpConfigQuotaEnforcementPolicyBaseEntry 2 }

--

dpConfigQuotaEnforcementActionTable OBJECT-TYPE
    SYNTAX      SEQUENCE OF DPConfigQuotaEnforcementActionEntry
    MAX-ACCESS  not-accessible
    STATUS      current
    DESCRIPTION
        "Quota enforcement action."

    ::= { dpConfig 513 }

dpConfigQuotaEnforcementActionEntry OBJECT-TYPE
    SYNTAX      DPConfigQuotaEnforcementActionEntry
    MAX-ACCESS  not-accessible
    STATUS      current
    DESCRIPTION "Table row."
    INDEX { dpConfigQuotaEnforcementActionIndex, IMPLIED dpConfigQuotaEnforcementActionname }

    ::= { dpConfigQuotaEnforcementActionTable 1 }

DPConfigQuotaEnforcementActionEntry ::= SEQUENCE {
    dpConfigQuotaEnforcementActionIndex    Unsigned32,
    dpConfigQuotaEnforcementActionname    DisplayString
}

dpConfigQuotaEnforcementActionIndex OBJECT-TYPE
    SYNTAX      Unsigned32
    MAX-ACCESS  read-only
    STATUS      current
    DESCRIPTION "No description yet."

    ::= { dpConfigQuotaEnforcementActionEntry 1 }

dpConfigQuotaEnforcementActionname OBJECT-TYPE
    SYNTAX      DisplayString
    MAX-ACCESS  read-only
    STATUS      current
    DESCRIPTION "No description yet."

    ::= { dpConfigQuotaEnforcementActionEntry 2 }

--

dpConfigQuotaEnforcementPolicyTable OBJECT-TYPE
    SYNTAX      SEQUENCE OF DPConfigQuotaEnforcementPolicyEntry
    MAX-ACCESS  not-accessible
    STATUS      current
    DESCRIPTION
        "Quota enforcement policy."

    ::= { dpConfig 514 }

dpConfigQuotaEnforcementPolicyEntry OBJECT-TYPE
    SYNTAX      DPConfigQuotaEnforcementPolicyEntry
    MAX-ACCESS  not-accessible
    STATUS      current
    DESCRIPTION "Table row."
    INDEX { dpConfigQuotaEnforcementPolicyIndex, IMPLIED dpConfigQuotaEnforcementPolicyname }

    ::= { dpConfigQuotaEnforcementPolicyTable 1 }

DPConfigQuotaEnforcementPolicyEntry ::= SEQUENCE {
    dpConfigQuotaEnforcementPolicyIndex    Unsigned32,
    dpConfigQuotaEnforcementPolicyname    DisplayString
}

dpConfigQuotaEnforcementPolicyIndex OBJECT-TYPE
    SYNTAX      Unsigned32
    MAX-ACCESS  read-only
    STATUS      current
    DESCRIPTION "No description yet."

    ::= { dpConfigQuotaEnforcementPolicyEntry 1 }

dpConfigQuotaEnforcementPolicyname OBJECT-TYPE
    SYNTAX      DisplayString
    MAX-ACCESS  read-only
    STATUS      current
    DESCRIPTION "No description yet."

    ::= { dpConfigQuotaEnforcementPolicyEntry 2 }

--

dpConfigGatewayPeeringTable OBJECT-TYPE
    SYNTAX      SEQUENCE OF DPConfigGatewayPeeringEntry
    MAX-ACCESS  not-accessible
    STATUS      current
    DESCRIPTION
        "The gateway peering configuration can work in standalone or in peer group
        mode. Standalone mode should be used for only development or testing
        purposes. When you enable peer group mode, you can add peers to the group
        and configure the connection among the peers."

    ::= { dpConfig 526 }

dpConfigGatewayPeeringEntry OBJECT-TYPE
    SYNTAX      DPConfigGatewayPeeringEntry
    MAX-ACCESS  not-accessible
    STATUS      current
    DESCRIPTION "Table row."
    INDEX { dpConfigGatewayPeeringIndex, IMPLIED dpConfigGatewayPeeringname }

    ::= { dpConfigGatewayPeeringTable 1 }

DPConfigGatewayPeeringEntry ::= SEQUENCE {
    dpConfigGatewayPeeringIndex    Unsigned32,
    dpConfigGatewayPeeringname    DisplayString
}

dpConfigGatewayPeeringIndex OBJECT-TYPE
    SYNTAX      Unsigned32
    MAX-ACCESS  read-only
    STATUS      current
    DESCRIPTION "No description yet."

    ::= { dpConfigGatewayPeeringEntry 1 }

dpConfigGatewayPeeringname OBJECT-TYPE
    SYNTAX      DisplayString
    MAX-ACCESS  read-only
    STATUS      current
    DESCRIPTION "No description yet."

    ::= { dpConfigGatewayPeeringEntry 2 }

--

dpConfigStylePolicyActionBaseTable OBJECT-TYPE
    SYNTAX      SEQUENCE OF DPConfigStylePolicyActionBaseEntry
    MAX-ACCESS  not-accessible
    STATUS      current
    DESCRIPTION "Table."

    ::= { dpConfig 600 }

dpConfigStylePolicyActionBaseEntry OBJECT-TYPE
    SYNTAX      DPConfigStylePolicyActionBaseEntry
    MAX-ACCESS  not-accessible
    STATUS      current
    DESCRIPTION "Table row."
    INDEX { dpConfigStylePolicyActionBaseIndex, IMPLIED dpConfigStylePolicyActionBasename }

    ::= { dpConfigStylePolicyActionBaseTable 1 }

DPConfigStylePolicyActionBaseEntry ::= SEQUENCE {
    dpConfigStylePolicyActionBaseIndex    Unsigned32,
    dpConfigStylePolicyActionBasename    DisplayString
}

dpConfigStylePolicyActionBaseIndex OBJECT-TYPE
    SYNTAX      Unsigned32
    MAX-ACCESS  read-only
    STATUS      current
    DESCRIPTION "No description yet."

    ::= { dpConfigStylePolicyActionBaseEntry 1 }

dpConfigStylePolicyActionBasename OBJECT-TYPE
    SYNTAX      DisplayString
    MAX-ACCESS  read-only
    STATUS      current
    DESCRIPTION "No description yet."

    ::= { dpConfigStylePolicyActionBaseEntry 2 }

--

dpConfigAssemblyActionBaseTable OBJECT-TYPE
    SYNTAX      SEQUENCE OF DPConfigAssemblyActionBaseEntry
    MAX-ACCESS  not-accessible
    STATUS      current
    DESCRIPTION "Table."

    ::= { dpConfig 601 }

dpConfigAssemblyActionBaseEntry OBJECT-TYPE
    SYNTAX      DPConfigAssemblyActionBaseEntry
    MAX-ACCESS  not-accessible
    STATUS      current
    DESCRIPTION "Table row."
    INDEX { dpConfigAssemblyActionBaseIndex, IMPLIED dpConfigAssemblyActionBasename }

    ::= { dpConfigAssemblyActionBaseTable 1 }

DPConfigAssemblyActionBaseEntry ::= SEQUENCE {
    dpConfigAssemblyActionBaseIndex    Unsigned32,
    dpConfigAssemblyActionBasename    DisplayString
}

dpConfigAssemblyActionBaseIndex OBJECT-TYPE
    SYNTAX      Unsigned32
    MAX-ACCESS  read-only
    STATUS      current
    DESCRIPTION "No description yet."

    ::= { dpConfigAssemblyActionBaseEntry 1 }

dpConfigAssemblyActionBasename OBJECT-TYPE
    SYNTAX      DisplayString
    MAX-ACCESS  read-only
    STATUS      current
    DESCRIPTION "No description yet."

    ::= { dpConfigAssemblyActionBaseEntry 2 }

--

dpConfigAssemblyActionTable OBJECT-TYPE
    SYNTAX      SEQUENCE OF DPConfigAssemblyActionEntry
    MAX-ACCESS  not-accessible
    STATUS      current
    DESCRIPTION "Table."

    ::= { dpConfig 602 }

dpConfigAssemblyActionEntry OBJECT-TYPE
    SYNTAX      DPConfigAssemblyActionEntry
    MAX-ACCESS  not-accessible
    STATUS      current
    DESCRIPTION "Table row."
    INDEX { dpConfigAssemblyActionIndex, IMPLIED dpConfigAssemblyActionname }

    ::= { dpConfigAssemblyActionTable 1 }

DPConfigAssemblyActionEntry ::= SEQUENCE {
    dpConfigAssemblyActionIndex    Unsigned32,
    dpConfigAssemblyActionname    DisplayString
}

dpConfigAssemblyActionIndex OBJECT-TYPE
    SYNTAX      Unsigned32
    MAX-ACCESS  read-only
    STATUS      current
    DESCRIPTION "No description yet."

    ::= { dpConfigAssemblyActionEntry 1 }

dpConfigAssemblyActionname OBJECT-TYPE
    SYNTAX      DisplayString
    MAX-ACCESS  read-only
    STATUS      current
    DESCRIPTION "No description yet."

    ::= { dpConfigAssemblyActionEntry 2 }

--

dpConfigAssemblyLogicTable OBJECT-TYPE
    SYNTAX      SEQUENCE OF DPConfigAssemblyLogicEntry
    MAX-ACCESS  not-accessible
    STATUS      current
    DESCRIPTION "Table."

    ::= { dpConfig 603 }

dpConfigAssemblyLogicEntry OBJECT-TYPE
    SYNTAX      DPConfigAssemblyLogicEntry
    MAX-ACCESS  not-accessible
    STATUS      current
    DESCRIPTION "Table row."
    INDEX { dpConfigAssemblyLogicIndex, IMPLIED dpConfigAssemblyLogicname }

    ::= { dpConfigAssemblyLogicTable 1 }

DPConfigAssemblyLogicEntry ::= SEQUENCE {
    dpConfigAssemblyLogicIndex    Unsigned32,
    dpConfigAssemblyLogicname    DisplayString
}

dpConfigAssemblyLogicIndex OBJECT-TYPE
    SYNTAX      Unsigned32
    MAX-ACCESS  read-only
    STATUS      current
    DESCRIPTION "No description yet."

    ::= { dpConfigAssemblyLogicEntry 1 }

dpConfigAssemblyLogicname OBJECT-TYPE
    SYNTAX      DisplayString
    MAX-ACCESS  read-only
    STATUS      current
    DESCRIPTION "No description yet."

    ::= { dpConfigAssemblyLogicEntry 2 }

--

dpConfigAPIExecuteTable OBJECT-TYPE
    SYNTAX      SEQUENCE OF DPConfigAPIExecuteEntry
    MAX-ACCESS  not-accessible
    STATUS      current
    DESCRIPTION
        "An API execute action executes the assembly rule that is identified at the
        runtime for the incoming API request."

    ::= { dpConfig 605 }

dpConfigAPIExecuteEntry OBJECT-TYPE
    SYNTAX      DPConfigAPIExecuteEntry
    MAX-ACCESS  not-accessible
    STATUS      current
    DESCRIPTION "Table row."
    INDEX { dpConfigAPIExecuteIndex, IMPLIED dpConfigAPIExecutename }

    ::= { dpConfigAPIExecuteTable 1 }

DPConfigAPIExecuteEntry ::= SEQUENCE {
    dpConfigAPIExecuteIndex    Unsigned32,
    dpConfigAPIExecutename    DisplayString
}

dpConfigAPIExecuteIndex OBJECT-TYPE
    SYNTAX      Unsigned32
    MAX-ACCESS  read-only
    STATUS      current
    DESCRIPTION "No description yet."

    ::= { dpConfigAPIExecuteEntry 1 }

dpConfigAPIExecutename OBJECT-TYPE
    SYNTAX      DisplayString
    MAX-ACCESS  read-only
    STATUS      current
    DESCRIPTION "No description yet."

    ::= { dpConfigAPIExecuteEntry 2 }

--

dpConfigAPIResultTable OBJECT-TYPE
    SYNTAX      SEQUENCE OF DPConfigAPIResultEntry
    MAX-ACCESS  not-accessible
    STATUS      current
    DESCRIPTION
        "An API result action prepares responses to the client based on the result
        from the API execute action."

    ::= { dpConfig 607 }

dpConfigAPIResultEntry OBJECT-TYPE
    SYNTAX      DPConfigAPIResultEntry
    MAX-ACCESS  not-accessible
    STATUS      current
    DESCRIPTION "Table row."
    INDEX { dpConfigAPIResultIndex, IMPLIED dpConfigAPIResultname }

    ::= { dpConfigAPIResultTable 1 }

DPConfigAPIResultEntry ::= SEQUENCE {
    dpConfigAPIResultIndex    Unsigned32,
    dpConfigAPIResultname    DisplayString
}

dpConfigAPIResultIndex OBJECT-TYPE
    SYNTAX      Unsigned32
    MAX-ACCESS  read-only
    STATUS      current
    DESCRIPTION "No description yet."

    ::= { dpConfigAPIResultEntry 1 }

dpConfigAPIResultname OBJECT-TYPE
    SYNTAX      DisplayString
    MAX-ACCESS  read-only
    STATUS      current
    DESCRIPTION "No description yet."

    ::= { dpConfigAPIResultEntry 2 }

--

dpConfigAssemblyLogicSwitchTable OBJECT-TYPE
    SYNTAX      SEQUENCE OF DPConfigAssemblyLogicSwitchEntry
    MAX-ACCESS  not-accessible
    STATUS      current
    DESCRIPTION
        "The switch action evaluates a list of conditions and runs the API rule
        that is associated with the first condition that matches the API context."

    ::= { dpConfig 609 }

dpConfigAssemblyLogicSwitchEntry OBJECT-TYPE
    SYNTAX      DPConfigAssemblyLogicSwitchEntry
    MAX-ACCESS  not-accessible
    STATUS      current
    DESCRIPTION "Table row."
    INDEX { dpConfigAssemblyLogicSwitchIndex, IMPLIED dpConfigAssemblyLogicSwitchname }

    ::= { dpConfigAssemblyLogicSwitchTable 1 }

DPConfigAssemblyLogicSwitchEntry ::= SEQUENCE {
    dpConfigAssemblyLogicSwitchIndex    Unsigned32,
    dpConfigAssemblyLogicSwitchname    DisplayString
}

dpConfigAssemblyLogicSwitchIndex OBJECT-TYPE
    SYNTAX      Unsigned32
    MAX-ACCESS  read-only
    STATUS      current
    DESCRIPTION "No description yet."

    ::= { dpConfigAssemblyLogicSwitchEntry 1 }

dpConfigAssemblyLogicSwitchname OBJECT-TYPE
    SYNTAX      DisplayString
    MAX-ACCESS  read-only
    STATUS      current
    DESCRIPTION "No description yet."

    ::= { dpConfigAssemblyLogicSwitchEntry 2 }

--

dpConfigAssemblyTable OBJECT-TYPE
    SYNTAX      SEQUENCE OF DPConfigAssemblyEntry
    MAX-ACCESS  not-accessible
    STATUS      current
    DESCRIPTION
        "An assembly specifies the API rule to apply to the API call and how to
        handle errors during the assembly execution. The API rule for the assembly
        comprises only assembly actions that are executed in order to control a
        specific aspect of processing such as data transformation during API call
        at run time. When an API is identified for the incoming request, its
        assembly is executed."

    ::= { dpConfig 610 }

dpConfigAssemblyEntry OBJECT-TYPE
    SYNTAX      DPConfigAssemblyEntry
    MAX-ACCESS  not-accessible
    STATUS      current
    DESCRIPTION "Table row."
    INDEX { dpConfigAssemblyIndex, IMPLIED dpConfigAssemblyname }

    ::= { dpConfigAssemblyTable 1 }

DPConfigAssemblyEntry ::= SEQUENCE {
    dpConfigAssemblyIndex    Unsigned32,
    dpConfigAssemblyname    DisplayString
}

dpConfigAssemblyIndex OBJECT-TYPE
    SYNTAX      Unsigned32
    MAX-ACCESS  read-only
    STATUS      current
    DESCRIPTION "No description yet."

    ::= { dpConfigAssemblyEntry 1 }

dpConfigAssemblyname OBJECT-TYPE
    SYNTAX      DisplayString
    MAX-ACCESS  read-only
    STATUS      current
    DESCRIPTION "No description yet."

    ::= { dpConfigAssemblyEntry 2 }

--

dpConfigAssemblyActionInvokeTable OBJECT-TYPE
    SYNTAX      SEQUENCE OF DPConfigAssemblyActionInvokeEntry
    MAX-ACCESS  not-accessible
    STATUS      current
    DESCRIPTION
        "You use the invoke action to call another service from within your
        assembly."

    ::= { dpConfig 611 }

dpConfigAssemblyActionInvokeEntry OBJECT-TYPE
    SYNTAX      DPConfigAssemblyActionInvokeEntry
    MAX-ACCESS  not-accessible
    STATUS      current
    DESCRIPTION "Table row."
    INDEX { dpConfigAssemblyActionInvokeIndex, IMPLIED dpConfigAssemblyActionInvokename }

    ::= { dpConfigAssemblyActionInvokeTable 1 }

DPConfigAssemblyActionInvokeEntry ::= SEQUENCE {
    dpConfigAssemblyActionInvokeIndex    Unsigned32,
    dpConfigAssemblyActionInvokename    DisplayString
}

dpConfigAssemblyActionInvokeIndex OBJECT-TYPE
    SYNTAX      Unsigned32
    MAX-ACCESS  read-only
    STATUS      current
    DESCRIPTION "No description yet."

    ::= { dpConfigAssemblyActionInvokeEntry 1 }

dpConfigAssemblyActionInvokename OBJECT-TYPE
    SYNTAX      DisplayString
    MAX-ACCESS  read-only
    STATUS      current
    DESCRIPTION "No description yet."

    ::= { dpConfigAssemblyActionInvokeEntry 2 }

--

dpConfigAssemblyActionSetVarTable OBJECT-TYPE
    SYNTAX      SEQUENCE OF DPConfigAssemblyActionSetVarEntry
    MAX-ACCESS  not-accessible
    STATUS      current
    DESCRIPTION
        "You use the set variable action for setting, adding, or clearing an API
        context variable within your assembly."

    ::= { dpConfig 612 }

dpConfigAssemblyActionSetVarEntry OBJECT-TYPE
    SYNTAX      DPConfigAssemblyActionSetVarEntry
    MAX-ACCESS  not-accessible
    STATUS      current
    DESCRIPTION "Table row."
    INDEX { dpConfigAssemblyActionSetVarIndex, IMPLIED dpConfigAssemblyActionSetVarname }

    ::= { dpConfigAssemblyActionSetVarTable 1 }

DPConfigAssemblyActionSetVarEntry ::= SEQUENCE {
    dpConfigAssemblyActionSetVarIndex    Unsigned32,
    dpConfigAssemblyActionSetVarname    DisplayString
}

dpConfigAssemblyActionSetVarIndex OBJECT-TYPE
    SYNTAX      Unsigned32
    MAX-ACCESS  read-only
    STATUS      current
    DESCRIPTION "No description yet."

    ::= { dpConfigAssemblyActionSetVarEntry 1 }

dpConfigAssemblyActionSetVarname OBJECT-TYPE
    SYNTAX      DisplayString
    MAX-ACCESS  read-only
    STATUS      current
    DESCRIPTION "No description yet."

    ::= { dpConfigAssemblyActionSetVarEntry 2 }

--

dpConfigAssemblyActionThrowTable OBJECT-TYPE
    SYNTAX      SEQUENCE OF DPConfigAssemblyActionThrowEntry
    MAX-ACCESS  not-accessible
    STATUS      current
    DESCRIPTION
        "You can customize an error in the throw action. When the throw action is
        triggered, the custom error is thrown. After the throw action is
        triggered, the API Gateway does not run subsequent assembly actions and
        the current assembly rule is ended. The thrown error, including the error
        identifier and text for the error message, is saved in the API context."

    ::= { dpConfig 613 }

dpConfigAssemblyActionThrowEntry OBJECT-TYPE
    SYNTAX      DPConfigAssemblyActionThrowEntry
    MAX-ACCESS  not-accessible
    STATUS      current
    DESCRIPTION "Table row."
    INDEX { dpConfigAssemblyActionThrowIndex, IMPLIED dpConfigAssemblyActionThrowname }

    ::= { dpConfigAssemblyActionThrowTable 1 }

DPConfigAssemblyActionThrowEntry ::= SEQUENCE {
    dpConfigAssemblyActionThrowIndex    Unsigned32,
    dpConfigAssemblyActionThrowname    DisplayString
}

dpConfigAssemblyActionThrowIndex OBJECT-TYPE
    SYNTAX      Unsigned32
    MAX-ACCESS  read-only
    STATUS      current
    DESCRIPTION "No description yet."

    ::= { dpConfigAssemblyActionThrowEntry 1 }

dpConfigAssemblyActionThrowname OBJECT-TYPE
    SYNTAX      DisplayString
    MAX-ACCESS  read-only
    STATUS      current
    DESCRIPTION "No description yet."

    ::= { dpConfigAssemblyActionThrowEntry 2 }

--

dpConfigAPIRoutingTable OBJECT-TYPE
    SYNTAX      SEQUENCE OF DPConfigAPIRoutingEntry
    MAX-ACCESS  not-accessible
    STATUS      current
    DESCRIPTION
        "An API routing action examines the information that is carried in the API
        request and matches the API and operation to respond to the request."

    ::= { dpConfig 614 }

dpConfigAPIRoutingEntry OBJECT-TYPE
    SYNTAX      DPConfigAPIRoutingEntry
    MAX-ACCESS  not-accessible
    STATUS      current
    DESCRIPTION "Table row."
    INDEX { dpConfigAPIRoutingIndex, IMPLIED dpConfigAPIRoutingname }

    ::= { dpConfigAPIRoutingTable 1 }

DPConfigAPIRoutingEntry ::= SEQUENCE {
    dpConfigAPIRoutingIndex    Unsigned32,
    dpConfigAPIRoutingname    DisplayString
}

dpConfigAPIRoutingIndex OBJECT-TYPE
    SYNTAX      Unsigned32
    MAX-ACCESS  read-only
    STATUS      current
    DESCRIPTION "No description yet."

    ::= { dpConfigAPIRoutingEntry 1 }

dpConfigAPIRoutingname OBJECT-TYPE
    SYNTAX      DisplayString
    MAX-ACCESS  read-only
    STATUS      current
    DESCRIPTION "No description yet."

    ::= { dpConfigAPIRoutingEntry 2 }

--

dpConfigAPISecurityTable OBJECT-TYPE
    SYNTAX      SEQUENCE OF DPConfigAPISecurityEntry
    MAX-ACCESS  not-accessible
    STATUS      current
    DESCRIPTION
        "An API security action enforces the security requirements that are defined
        for the target API or operation."

    ::= { dpConfig 615 }

dpConfigAPISecurityEntry OBJECT-TYPE
    SYNTAX      DPConfigAPISecurityEntry
    MAX-ACCESS  not-accessible
    STATUS      current
    DESCRIPTION "Table row."
    INDEX { dpConfigAPISecurityIndex, IMPLIED dpConfigAPISecurityname }

    ::= { dpConfigAPISecurityTable 1 }

DPConfigAPISecurityEntry ::= SEQUENCE {
    dpConfigAPISecurityIndex    Unsigned32,
    dpConfigAPISecurityname    DisplayString
}

dpConfigAPISecurityIndex OBJECT-TYPE
    SYNTAX      Unsigned32
    MAX-ACCESS  read-only
    STATUS      current
    DESCRIPTION "No description yet."

    ::= { dpConfigAPISecurityEntry 1 }

dpConfigAPISecurityname OBJECT-TYPE
    SYNTAX      DisplayString
    MAX-ACCESS  read-only
    STATUS      current
    DESCRIPTION "No description yet."

    ::= { dpConfigAPISecurityEntry 2 }

--

dpConfigAPIRateLimitTable OBJECT-TYPE
    SYNTAX      SEQUENCE OF DPConfigAPIRateLimitEntry
    MAX-ACCESS  not-accessible
    STATUS      current
    DESCRIPTION
        "An API rate limit action enforces the rate limit schemes that are defined
        for an API or operation."

    ::= { dpConfig 616 }

dpConfigAPIRateLimitEntry OBJECT-TYPE
    SYNTAX      DPConfigAPIRateLimitEntry
    MAX-ACCESS  not-accessible
    STATUS      current
    DESCRIPTION "Table row."
    INDEX { dpConfigAPIRateLimitIndex, IMPLIED dpConfigAPIRateLimitname }

    ::= { dpConfigAPIRateLimitTable 1 }

DPConfigAPIRateLimitEntry ::= SEQUENCE {
    dpConfigAPIRateLimitIndex    Unsigned32,
    dpConfigAPIRateLimitname    DisplayString
}

dpConfigAPIRateLimitIndex OBJECT-TYPE
    SYNTAX      Unsigned32
    MAX-ACCESS  read-only
    STATUS      current
    DESCRIPTION "No description yet."

    ::= { dpConfigAPIRateLimitEntry 1 }

dpConfigAPIRateLimitname OBJECT-TYPE
    SYNTAX      DisplayString
    MAX-ACCESS  read-only
    STATUS      current
    DESCRIPTION "No description yet."

    ::= { dpConfigAPIRateLimitEntry 2 }

--

dpConfigAssemblyActionXml2JsonTable OBJECT-TYPE
    SYNTAX      SEQUENCE OF DPConfigAssemblyActionXml2JsonEntry
    MAX-ACCESS  not-accessible
    STATUS      current
    DESCRIPTION
        "You use the XML to JSON action to convert the payload of an API message
        from XML format to equivalent JSON format."

    ::= { dpConfig 617 }

dpConfigAssemblyActionXml2JsonEntry OBJECT-TYPE
    SYNTAX      DPConfigAssemblyActionXml2JsonEntry
    MAX-ACCESS  not-accessible
    STATUS      current
    DESCRIPTION "Table row."
    INDEX { dpConfigAssemblyActionXml2JsonIndex, IMPLIED dpConfigAssemblyActionXml2Jsonname }

    ::= { dpConfigAssemblyActionXml2JsonTable 1 }

DPConfigAssemblyActionXml2JsonEntry ::= SEQUENCE {
    dpConfigAssemblyActionXml2JsonIndex    Unsigned32,
    dpConfigAssemblyActionXml2Jsonname    DisplayString
}

dpConfigAssemblyActionXml2JsonIndex OBJECT-TYPE
    SYNTAX      Unsigned32
    MAX-ACCESS  read-only
    STATUS      current
    DESCRIPTION "No description yet."

    ::= { dpConfigAssemblyActionXml2JsonEntry 1 }

dpConfigAssemblyActionXml2Jsonname OBJECT-TYPE
    SYNTAX      DisplayString
    MAX-ACCESS  read-only
    STATUS      current
    DESCRIPTION "No description yet."

    ::= { dpConfigAssemblyActionXml2JsonEntry 2 }

--

dpConfigAPIActionTable OBJECT-TYPE
    SYNTAX      SEQUENCE OF DPConfigAPIActionEntry
    MAX-ACCESS  not-accessible
    STATUS      current
    DESCRIPTION "Table."

    ::= { dpConfig 618 }

dpConfigAPIActionEntry OBJECT-TYPE
    SYNTAX      DPConfigAPIActionEntry
    MAX-ACCESS  not-accessible
    STATUS      current
    DESCRIPTION "Table row."
    INDEX { dpConfigAPIActionIndex, IMPLIED dpConfigAPIActionname }

    ::= { dpConfigAPIActionTable 1 }

DPConfigAPIActionEntry ::= SEQUENCE {
    dpConfigAPIActionIndex    Unsigned32,
    dpConfigAPIActionname    DisplayString
}

dpConfigAPIActionIndex OBJECT-TYPE
    SYNTAX      Unsigned32
    MAX-ACCESS  read-only
    STATUS      current
    DESCRIPTION "No description yet."

    ::= { dpConfigAPIActionEntry 1 }

dpConfigAPIActionname OBJECT-TYPE
    SYNTAX      DisplayString
    MAX-ACCESS  read-only
    STATUS      current
    DESCRIPTION "No description yet."

    ::= { dpConfigAPIActionEntry 2 }

--

dpConfigAssemblyActionXSLTTable OBJECT-TYPE
    SYNTAX      SEQUENCE OF DPConfigAssemblyActionXSLTEntry
    MAX-ACCESS  not-accessible
    STATUS      current
    DESCRIPTION
        "You use the XSLT action to run a stylesheet from within your assembly.
        This action is not supported in IBM Cloud. Any assembly that includes it
        will fail."

    ::= { dpConfig 619 }

dpConfigAssemblyActionXSLTEntry OBJECT-TYPE
    SYNTAX      DPConfigAssemblyActionXSLTEntry
    MAX-ACCESS  not-accessible
    STATUS      current
    DESCRIPTION "Table row."
    INDEX { dpConfigAssemblyActionXSLTIndex, IMPLIED dpConfigAssemblyActionXSLTname }

    ::= { dpConfigAssemblyActionXSLTTable 1 }

DPConfigAssemblyActionXSLTEntry ::= SEQUENCE {
    dpConfigAssemblyActionXSLTIndex    Unsigned32,
    dpConfigAssemblyActionXSLTname    DisplayString
}

dpConfigAssemblyActionXSLTIndex OBJECT-TYPE
    SYNTAX      Unsigned32
    MAX-ACCESS  read-only
    STATUS      current
    DESCRIPTION "No description yet."

    ::= { dpConfigAssemblyActionXSLTEntry 1 }

dpConfigAssemblyActionXSLTname OBJECT-TYPE
    SYNTAX      DisplayString
    MAX-ACCESS  read-only
    STATUS      current
    DESCRIPTION "No description yet."

    ::= { dpConfigAssemblyActionXSLTEntry 2 }

--

dpConfigAssemblyActionGatewayScriptTable OBJECT-TYPE
    SYNTAX      SEQUENCE OF DPConfigAssemblyActionGatewayScriptEntry
    MAX-ACCESS  not-accessible
    STATUS      current
    DESCRIPTION
        "Use the GatewayScript action to run a GatewayScript file. This action is
        not supported in IBM Cloud. Any assembly that includes it will fail."

    ::= { dpConfig 620 }

dpConfigAssemblyActionGatewayScriptEntry OBJECT-TYPE
    SYNTAX      DPConfigAssemblyActionGatewayScriptEntry
    MAX-ACCESS  not-accessible
    STATUS      current
    DESCRIPTION "Table row."
    INDEX { dpConfigAssemblyActionGatewayScriptIndex, IMPLIED dpConfigAssemblyActionGatewayScriptname }

    ::= { dpConfigAssemblyActionGatewayScriptTable 1 }

DPConfigAssemblyActionGatewayScriptEntry ::= SEQUENCE {
    dpConfigAssemblyActionGatewayScriptIndex    Unsigned32,
    dpConfigAssemblyActionGatewayScriptname    DisplayString
}

dpConfigAssemblyActionGatewayScriptIndex OBJECT-TYPE
    SYNTAX      Unsigned32
    MAX-ACCESS  read-only
    STATUS      current
    DESCRIPTION "No description yet."

    ::= { dpConfigAssemblyActionGatewayScriptEntry 1 }

dpConfigAssemblyActionGatewayScriptname OBJECT-TYPE
    SYNTAX      DisplayString
    MAX-ACCESS  read-only
    STATUS      current
    DESCRIPTION "No description yet."

    ::= { dpConfigAssemblyActionGatewayScriptEntry 2 }

--

dpConfigAPIClientIdentificationTable OBJECT-TYPE
    SYNTAX      SEQUENCE OF DPConfigAPIClientIdentificationEntry
    MAX-ACCESS  not-accessible
    STATUS      current
    DESCRIPTION
        "An API client identification action examines the API key credentials that
        are carried in the API request and validates the subscription of the
        client."

    ::= { dpConfig 621 }

dpConfigAPIClientIdentificationEntry OBJECT-TYPE
    SYNTAX      DPConfigAPIClientIdentificationEntry
    MAX-ACCESS  not-accessible
    STATUS      current
    DESCRIPTION "Table row."
    INDEX { dpConfigAPIClientIdentificationIndex, IMPLIED dpConfigAPIClientIdentificationname }

    ::= { dpConfigAPIClientIdentificationTable 1 }

DPConfigAPIClientIdentificationEntry ::= SEQUENCE {
    dpConfigAPIClientIdentificationIndex    Unsigned32,
    dpConfigAPIClientIdentificationname    DisplayString
}

dpConfigAPIClientIdentificationIndex OBJECT-TYPE
    SYNTAX      Unsigned32
    MAX-ACCESS  read-only
    STATUS      current
    DESCRIPTION "No description yet."

    ::= { dpConfigAPIClientIdentificationEntry 1 }

dpConfigAPIClientIdentificationname OBJECT-TYPE
    SYNTAX      DisplayString
    MAX-ACCESS  read-only
    STATUS      current
    DESCRIPTION "No description yet."

    ::= { dpConfigAPIClientIdentificationEntry 2 }

--

dpConfigAssemblyActionMapTable OBJECT-TYPE
    SYNTAX      SEQUENCE OF DPConfigAssemblyActionMapEntry
    MAX-ACCESS  not-accessible
    STATUS      current
    DESCRIPTION
        "A map action applies data transformations to the assembly flow according
        to a specified map file. The map file is a JSON file that defines all
        mapping operations. Prepare a valid map file as follows: If you do not get
        the map file automatically, you need to create the map file manually. See
        the reference information about map file examples on IBM API Connect
        Knowledge center. Make sure that the map file is JSON formatted. If the
        map file is YAML formatted, convert it to JSON format. Import the JSON
        file to the DataPower Gateway. The file must be in the local:///
        directory, the temporary:/// directory, or one of their subdirectories."

    ::= { dpConfig 622 }

dpConfigAssemblyActionMapEntry OBJECT-TYPE
    SYNTAX      DPConfigAssemblyActionMapEntry
    MAX-ACCESS  not-accessible
    STATUS      current
    DESCRIPTION "Table row."
    INDEX { dpConfigAssemblyActionMapIndex, IMPLIED dpConfigAssemblyActionMapname }

    ::= { dpConfigAssemblyActionMapTable 1 }

DPConfigAssemblyActionMapEntry ::= SEQUENCE {
    dpConfigAssemblyActionMapIndex    Unsigned32,
    dpConfigAssemblyActionMapname    DisplayString
}

dpConfigAssemblyActionMapIndex OBJECT-TYPE
    SYNTAX      Unsigned32
    MAX-ACCESS  read-only
    STATUS      current
    DESCRIPTION "No description yet."

    ::= { dpConfigAssemblyActionMapEntry 1 }

dpConfigAssemblyActionMapname OBJECT-TYPE
    SYNTAX      DisplayString
    MAX-ACCESS  read-only
    STATUS      current
    DESCRIPTION "No description yet."

    ::= { dpConfigAssemblyActionMapEntry 2 }

--

dpConfigAssemblyActionJWTValidateTable OBJECT-TYPE
    SYNTAX      SEQUENCE OF DPConfigAssemblyActionJWTValidateEntry
    MAX-ACCESS  not-accessible
    STATUS      current
    DESCRIPTION
        "The validate JSON Web Token (JWT) action specifies credentials and methods
        to validate a JWT in the request. The following guidelines apply. All
        claims that are specified in the validate JWT action are validated. If any
        specified claim fails, the JWT validation fails. You can use a
        cryptographic object or a JWK to decrypt or verify the JWT. When both are
        specified, the cryptographic object is used. If the original message is
        signed with a shared secret key, the cryptographic object that is
        specified must also be a shared secret key. If the original message is
        signed with a private key, the cryptographic object that is specified must
        be a crypto certificate (public certificate). If a JWK header parameter is
        included in the header of the JWT, the parameter must match the
        cryptographic object or JWK that is specified in the action. Otherwise,
        the JWT validation fails."

    ::= { dpConfig 623 }

dpConfigAssemblyActionJWTValidateEntry OBJECT-TYPE
    SYNTAX      DPConfigAssemblyActionJWTValidateEntry
    MAX-ACCESS  not-accessible
    STATUS      current
    DESCRIPTION "Table row."
    INDEX { dpConfigAssemblyActionJWTValidateIndex, IMPLIED dpConfigAssemblyActionJWTValidatename }

    ::= { dpConfigAssemblyActionJWTValidateTable 1 }

DPConfigAssemblyActionJWTValidateEntry ::= SEQUENCE {
    dpConfigAssemblyActionJWTValidateIndex    Unsigned32,
    dpConfigAssemblyActionJWTValidatename    DisplayString
}

dpConfigAssemblyActionJWTValidateIndex OBJECT-TYPE
    SYNTAX      Unsigned32
    MAX-ACCESS  read-only
    STATUS      current
    DESCRIPTION "No description yet."

    ::= { dpConfigAssemblyActionJWTValidateEntry 1 }

dpConfigAssemblyActionJWTValidatename OBJECT-TYPE
    SYNTAX      DisplayString
    MAX-ACCESS  read-only
    STATUS      current
    DESCRIPTION "No description yet."

    ::= { dpConfigAssemblyActionJWTValidateEntry 2 }

--

dpConfigAssemblyActionParseTable OBJECT-TYPE
    SYNTAX      SEQUENCE OF DPConfigAssemblyActionParseEntry
    MAX-ACCESS  not-accessible
    STATUS      current
    DESCRIPTION
        "You use the parse action to parse a request or a message as XML or JSON,
        or parse binary data into a binary large object (BLOB)."

    ::= { dpConfig 624 }

dpConfigAssemblyActionParseEntry OBJECT-TYPE
    SYNTAX      DPConfigAssemblyActionParseEntry
    MAX-ACCESS  not-accessible
    STATUS      current
    DESCRIPTION "Table row."
    INDEX { dpConfigAssemblyActionParseIndex, IMPLIED dpConfigAssemblyActionParsename }

    ::= { dpConfigAssemblyActionParseTable 1 }

DPConfigAssemblyActionParseEntry ::= SEQUENCE {
    dpConfigAssemblyActionParseIndex    Unsigned32,
    dpConfigAssemblyActionParsename    DisplayString
}

dpConfigAssemblyActionParseIndex OBJECT-TYPE
    SYNTAX      Unsigned32
    MAX-ACCESS  read-only
    STATUS      current
    DESCRIPTION "No description yet."

    ::= { dpConfigAssemblyActionParseEntry 1 }

dpConfigAssemblyActionParsename OBJECT-TYPE
    SYNTAX      DisplayString
    MAX-ACCESS  read-only
    STATUS      current
    DESCRIPTION "No description yet."

    ::= { dpConfigAssemblyActionParseEntry 2 }

--

dpConfigAPICORSTable OBJECT-TYPE
    SYNTAX      SEQUENCE OF DPConfigAPICORSEntry
    MAX-ACCESS  not-accessible
    STATUS      current
    DESCRIPTION
        "An API CORS action handles cross-origin resource sharing (CORS) requests
        that are required by the API."

    ::= { dpConfig 625 }

dpConfigAPICORSEntry OBJECT-TYPE
    SYNTAX      DPConfigAPICORSEntry
    MAX-ACCESS  not-accessible
    STATUS      current
    DESCRIPTION "Table row."
    INDEX { dpConfigAPICORSIndex, IMPLIED dpConfigAPICORSname }

    ::= { dpConfigAPICORSTable 1 }

DPConfigAPICORSEntry ::= SEQUENCE {
    dpConfigAPICORSIndex    Unsigned32,
    dpConfigAPICORSname    DisplayString
}

dpConfigAPICORSIndex OBJECT-TYPE
    SYNTAX      Unsigned32
    MAX-ACCESS  read-only
    STATUS      current
    DESCRIPTION "No description yet."

    ::= { dpConfigAPICORSEntry 1 }

dpConfigAPICORSname OBJECT-TYPE
    SYNTAX      DisplayString
    MAX-ACCESS  read-only
    STATUS      current
    DESCRIPTION "No description yet."

    ::= { dpConfigAPICORSEntry 2 }

--

dpConfigOperationRateLimitTable OBJECT-TYPE
    SYNTAX      SEQUENCE OF DPConfigOperationRateLimitEntry
    MAX-ACCESS  not-accessible
    STATUS      current
    DESCRIPTION
        "An API Operation Rate Limit configuration defines the operation-specific
        rate limit scheme. By default, the rate limit scheme setting for the plan
        applies to all operations in the associated APIs. However, you can define
        a different rate limit scheme for an operation."

    ::= { dpConfig 626 }

dpConfigOperationRateLimitEntry OBJECT-TYPE
    SYNTAX      DPConfigOperationRateLimitEntry
    MAX-ACCESS  not-accessible
    STATUS      current
    DESCRIPTION "Table row."
    INDEX { dpConfigOperationRateLimitIndex, IMPLIED dpConfigOperationRateLimitname }

    ::= { dpConfigOperationRateLimitTable 1 }

DPConfigOperationRateLimitEntry ::= SEQUENCE {
    dpConfigOperationRateLimitIndex    Unsigned32,
    dpConfigOperationRateLimitname    DisplayString
}

dpConfigOperationRateLimitIndex OBJECT-TYPE
    SYNTAX      Unsigned32
    MAX-ACCESS  read-only
    STATUS      current
    DESCRIPTION "No description yet."

    ::= { dpConfigOperationRateLimitEntry 1 }

dpConfigOperationRateLimitname OBJECT-TYPE
    SYNTAX      DisplayString
    MAX-ACCESS  read-only
    STATUS      current
    DESCRIPTION "No description yet."

    ::= { dpConfigOperationRateLimitEntry 2 }

--

dpConfigAnalyticsEndpointTable OBJECT-TYPE
    SYNTAX      SEQUENCE OF DPConfigAnalyticsEndpointEntry
    MAX-ACCESS  not-accessible
    STATUS      current
    DESCRIPTION
        "Configure an analytics endpoint to forward the logged API events to a
        remote Elasticsearch server for display and analysis."

    ::= { dpConfig 627 }

dpConfigAnalyticsEndpointEntry OBJECT-TYPE
    SYNTAX      DPConfigAnalyticsEndpointEntry
    MAX-ACCESS  not-accessible
    STATUS      current
    DESCRIPTION "Table row."
    INDEX { dpConfigAnalyticsEndpointIndex, IMPLIED dpConfigAnalyticsEndpointname }

    ::= { dpConfigAnalyticsEndpointTable 1 }

DPConfigAnalyticsEndpointEntry ::= SEQUENCE {
    dpConfigAnalyticsEndpointIndex    Unsigned32,
    dpConfigAnalyticsEndpointname    DisplayString
}

dpConfigAnalyticsEndpointIndex OBJECT-TYPE
    SYNTAX      Unsigned32
    MAX-ACCESS  read-only
    STATUS      current
    DESCRIPTION "No description yet."

    ::= { dpConfigAnalyticsEndpointEntry 1 }

dpConfigAnalyticsEndpointname OBJECT-TYPE
    SYNTAX      DisplayString
    MAX-ACCESS  read-only
    STATUS      current
    DESCRIPTION "No description yet."

    ::= { dpConfigAnalyticsEndpointEntry 2 }

--

dpConfigAssemblyActionJWTGenerateTable OBJECT-TYPE
    SYNTAX      SEQUENCE OF DPConfigAssemblyActionJWTGenerateEntry
    MAX-ACCESS  not-accessible
    STATUS      current
    DESCRIPTION
        "The generate JSON Web Token (JWT) action generates JWT claims and
        specifies the cryptographic material for generating a JWT during API
        processing."

    ::= { dpConfig 628 }

dpConfigAssemblyActionJWTGenerateEntry OBJECT-TYPE
    SYNTAX      DPConfigAssemblyActionJWTGenerateEntry
    MAX-ACCESS  not-accessible
    STATUS      current
    DESCRIPTION "Table row."
    INDEX { dpConfigAssemblyActionJWTGenerateIndex, IMPLIED dpConfigAssemblyActionJWTGeneratename }

    ::= { dpConfigAssemblyActionJWTGenerateTable 1 }

DPConfigAssemblyActionJWTGenerateEntry ::= SEQUENCE {
    dpConfigAssemblyActionJWTGenerateIndex    Unsigned32,
    dpConfigAssemblyActionJWTGeneratename    DisplayString
}

dpConfigAssemblyActionJWTGenerateIndex OBJECT-TYPE
    SYNTAX      Unsigned32
    MAX-ACCESS  read-only
    STATUS      current
    DESCRIPTION "No description yet."

    ::= { dpConfigAssemblyActionJWTGenerateEntry 1 }

dpConfigAssemblyActionJWTGeneratename OBJECT-TYPE
    SYNTAX      DisplayString
    MAX-ACCESS  read-only
    STATUS      current
    DESCRIPTION "No description yet."

    ::= { dpConfigAssemblyActionJWTGenerateEntry 2 }

--

dpConfigAssemblyActionJson2XmlTable OBJECT-TYPE
    SYNTAX      SEQUENCE OF DPConfigAssemblyActionJson2XmlEntry
    MAX-ACCESS  not-accessible
    STATUS      current
    DESCRIPTION
        "You use the JSON to XML action to convert the payload of an API message
        from JSON format to equivalent XML format."

    ::= { dpConfig 629 }

dpConfigAssemblyActionJson2XmlEntry OBJECT-TYPE
    SYNTAX      DPConfigAssemblyActionJson2XmlEntry
    MAX-ACCESS  not-accessible
    STATUS      current
    DESCRIPTION "Table row."
    INDEX { dpConfigAssemblyActionJson2XmlIndex, IMPLIED dpConfigAssemblyActionJson2Xmlname }

    ::= { dpConfigAssemblyActionJson2XmlTable 1 }

DPConfigAssemblyActionJson2XmlEntry ::= SEQUENCE {
    dpConfigAssemblyActionJson2XmlIndex    Unsigned32,
    dpConfigAssemblyActionJson2Xmlname    DisplayString
}

dpConfigAssemblyActionJson2XmlIndex OBJECT-TYPE
    SYNTAX      Unsigned32
    MAX-ACCESS  read-only
    STATUS      current
    DESCRIPTION "No description yet."

    ::= { dpConfigAssemblyActionJson2XmlEntry 1 }

dpConfigAssemblyActionJson2Xmlname OBJECT-TYPE
    SYNTAX      DisplayString
    MAX-ACCESS  read-only
    STATUS      current
    DESCRIPTION "No description yet."

    ::= { dpConfigAssemblyActionJson2XmlEntry 2 }

--

dpConfigAssemblyActionOAuthTable OBJECT-TYPE
    SYNTAX      SEQUENCE OF DPConfigAssemblyActionOAuthEntry
    MAX-ACCESS  not-accessible
    STATUS      current
    DESCRIPTION
        "An OAuth action performs the requested OAuth flow based on the defined
        OAuth provider settings."

    ::= { dpConfig 630 }

dpConfigAssemblyActionOAuthEntry OBJECT-TYPE
    SYNTAX      DPConfigAssemblyActionOAuthEntry
    MAX-ACCESS  not-accessible
    STATUS      current
    DESCRIPTION "Table row."
    INDEX { dpConfigAssemblyActionOAuthIndex, IMPLIED dpConfigAssemblyActionOAuthname }

    ::= { dpConfigAssemblyActionOAuthTable 1 }

DPConfigAssemblyActionOAuthEntry ::= SEQUENCE {
    dpConfigAssemblyActionOAuthIndex    Unsigned32,
    dpConfigAssemblyActionOAuthname    DisplayString
}

dpConfigAssemblyActionOAuthIndex OBJECT-TYPE
    SYNTAX      Unsigned32
    MAX-ACCESS  read-only
    STATUS      current
    DESCRIPTION "No description yet."

    ::= { dpConfigAssemblyActionOAuthEntry 1 }

dpConfigAssemblyActionOAuthname OBJECT-TYPE
    SYNTAX      DisplayString
    MAX-ACCESS  read-only
    STATUS      current
    DESCRIPTION "No description yet."

    ::= { dpConfigAssemblyActionOAuthEntry 2 }

--

dpConfigOAuthProviderSettingsTable OBJECT-TYPE
    SYNTAX      SEQUENCE OF DPConfigOAuthProviderSettingsEntry
    MAX-ACCESS  not-accessible
    STATUS      current
    DESCRIPTION
        "An OAuth provider settings configuration defines how a client application
        is authorized to access resources on behalf of the resource owner."

    ::= { dpConfig 640 }

dpConfigOAuthProviderSettingsEntry OBJECT-TYPE
    SYNTAX      DPConfigOAuthProviderSettingsEntry
    MAX-ACCESS  not-accessible
    STATUS      current
    DESCRIPTION "Table row."
    INDEX { dpConfigOAuthProviderSettingsIndex, IMPLIED dpConfigOAuthProviderSettingsname }

    ::= { dpConfigOAuthProviderSettingsTable 1 }

DPConfigOAuthProviderSettingsEntry ::= SEQUENCE {
    dpConfigOAuthProviderSettingsIndex    Unsigned32,
    dpConfigOAuthProviderSettingsname    DisplayString
}

dpConfigOAuthProviderSettingsIndex OBJECT-TYPE
    SYNTAX      Unsigned32
    MAX-ACCESS  read-only
    STATUS      current
    DESCRIPTION "No description yet."

    ::= { dpConfigOAuthProviderSettingsEntry 1 }

dpConfigOAuthProviderSettingsname OBJECT-TYPE
    SYNTAX      DisplayString
    MAX-ACCESS  read-only
    STATUS      current
    DESCRIPTION "No description yet."

    ::= { dpConfigOAuthProviderSettingsEntry 2 }

--

dpConfigAPISecurityTokenManagerTable OBJECT-TYPE
    SYNTAX      SEQUENCE OF DPConfigAPISecurityTokenManagerEntry
    MAX-ACCESS  not-accessible
    STATUS      current
    DESCRIPTION
        "The security token manager provides storage configuration to security
        objects such as OAuth Provider and User Security."

    ::= { dpConfig 641 }

dpConfigAPISecurityTokenManagerEntry OBJECT-TYPE
    SYNTAX      DPConfigAPISecurityTokenManagerEntry
    MAX-ACCESS  not-accessible
    STATUS      current
    DESCRIPTION "Table row."
    INDEX { dpConfigAPISecurityTokenManagerIndex, IMPLIED dpConfigAPISecurityTokenManagername }

    ::= { dpConfigAPISecurityTokenManagerTable 1 }

DPConfigAPISecurityTokenManagerEntry ::= SEQUENCE {
    dpConfigAPISecurityTokenManagerIndex    Unsigned32,
    dpConfigAPISecurityTokenManagername    DisplayString
}

dpConfigAPISecurityTokenManagerIndex OBJECT-TYPE
    SYNTAX      Unsigned32
    MAX-ACCESS  read-only
    STATUS      current
    DESCRIPTION "No description yet."

    ::= { dpConfigAPISecurityTokenManagerEntry 1 }

dpConfigAPISecurityTokenManagername OBJECT-TYPE
    SYNTAX      DisplayString
    MAX-ACCESS  read-only
    STATUS      current
    DESCRIPTION "No description yet."

    ::= { dpConfigAPISecurityTokenManagerEntry 2 }

--

dpConfigAssemblyActionValidateTable OBJECT-TYPE
    SYNTAX      SEQUENCE OF DPConfigAssemblyActionValidateEntry
    MAX-ACCESS  not-accessible
    STATUS      current
    DESCRIPTION
        "You use the assembly validate action to validate payloads against a
        schema."

    ::= { dpConfig 642 }

dpConfigAssemblyActionValidateEntry OBJECT-TYPE
    SYNTAX      DPConfigAssemblyActionValidateEntry
    MAX-ACCESS  not-accessible
    STATUS      current
    DESCRIPTION "Table row."
    INDEX { dpConfigAssemblyActionValidateIndex, IMPLIED dpConfigAssemblyActionValidatename }

    ::= { dpConfigAssemblyActionValidateTable 1 }

DPConfigAssemblyActionValidateEntry ::= SEQUENCE {
    dpConfigAssemblyActionValidateIndex    Unsigned32,
    dpConfigAssemblyActionValidatename    DisplayString
}

dpConfigAssemblyActionValidateIndex OBJECT-TYPE
    SYNTAX      Unsigned32
    MAX-ACCESS  read-only
    STATUS      current
    DESCRIPTION "No description yet."

    ::= { dpConfigAssemblyActionValidateEntry 1 }

dpConfigAssemblyActionValidatename OBJECT-TYPE
    SYNTAX      DisplayString
    MAX-ACCESS  read-only
    STATUS      current
    DESCRIPTION "No description yet."

    ::= { dpConfigAssemblyActionValidateEntry 2 }

--

dpConfigAPIDebugProbeTable OBJECT-TYPE
    SYNTAX      SEQUENCE OF DPConfigAPIDebugProbeEntry
    MAX-ACCESS  not-accessible
    STATUS      current
    DESCRIPTION
        "This domain-specific configuration defines the settings for the probe that
        you can use to troubleshoot the processing of assembly actions by the API
        Gateway."

    ::= { dpConfig 643 }

dpConfigAPIDebugProbeEntry OBJECT-TYPE
    SYNTAX      DPConfigAPIDebugProbeEntry
    MAX-ACCESS  not-accessible
    STATUS      current
    DESCRIPTION "Table row."
    INDEX { dpConfigAPIDebugProbeIndex, IMPLIED dpConfigAPIDebugProbename }

    ::= { dpConfigAPIDebugProbeTable 1 }

DPConfigAPIDebugProbeEntry ::= SEQUENCE {
    dpConfigAPIDebugProbeIndex    Unsigned32,
    dpConfigAPIDebugProbename    DisplayString
}

dpConfigAPIDebugProbeIndex OBJECT-TYPE
    SYNTAX      Unsigned32
    MAX-ACCESS  read-only
    STATUS      current
    DESCRIPTION "No description yet."

    ::= { dpConfigAPIDebugProbeEntry 1 }

dpConfigAPIDebugProbename OBJECT-TYPE
    SYNTAX      DisplayString
    MAX-ACCESS  read-only
    STATUS      current
    DESCRIPTION "No description yet."

    ::= { dpConfigAPIDebugProbeEntry 2 }

--

dpConfigAPIApplicationTypeTable OBJECT-TYPE
    SYNTAX      SEQUENCE OF DPConfigAPIApplicationTypeEntry
    MAX-ACCESS  not-accessible
    STATUS      current
    DESCRIPTION "Table."

    ::= { dpConfig 644 }

dpConfigAPIApplicationTypeEntry OBJECT-TYPE
    SYNTAX      DPConfigAPIApplicationTypeEntry
    MAX-ACCESS  not-accessible
    STATUS      current
    DESCRIPTION "Table row."
    INDEX { dpConfigAPIApplicationTypeIndex, IMPLIED dpConfigAPIApplicationTypename }

    ::= { dpConfigAPIApplicationTypeTable 1 }

DPConfigAPIApplicationTypeEntry ::= SEQUENCE {
    dpConfigAPIApplicationTypeIndex    Unsigned32,
    dpConfigAPIApplicationTypename    DisplayString
}

dpConfigAPIApplicationTypeIndex OBJECT-TYPE
    SYNTAX      Unsigned32
    MAX-ACCESS  read-only
    STATUS      current
    DESCRIPTION "No description yet."

    ::= { dpConfigAPIApplicationTypeEntry 1 }

dpConfigAPIApplicationTypename OBJECT-TYPE
    SYNTAX      DisplayString
    MAX-ACCESS  read-only
    STATUS      current
    DESCRIPTION "No description yet."

    ::= { dpConfigAPIApplicationTypeEntry 2 }

--

dpConfigAssemblyFunctionTable OBJECT-TYPE
    SYNTAX      SEQUENCE OF DPConfigAssemblyFunctionEntry
    MAX-ACCESS  not-accessible
    STATUS      current
    DESCRIPTION
        "An assembly function augments the actions performed by the API Gateway.
        You can implement an assembly function in one of the following ways.
        Define an assembly function to add custom logic to an assembly. After you
        define the assembly function, you can add it to an assembly function call
        action. When you configure the API Connect Gateway Service as not V5
        compatible, use assembly functions to specify user-defined policies that
        API Connect advertises and makes available in the API Connect assembly
        editor. User-defined policies provide custom processing control of APIs in
        the Gateway server. For an assembly function that is intended to be used
        as a user-defined policy in the API Connect Gateway Service configuration,
        it is recommended to configure the assembly function using a mechanism
        other than a configuration file processed by a configuration sequence.
        Objects created using configuration files are not persisted to the domain
        startup configuration."

    ::= { dpConfig 645 }

dpConfigAssemblyFunctionEntry OBJECT-TYPE
    SYNTAX      DPConfigAssemblyFunctionEntry
    MAX-ACCESS  not-accessible
    STATUS      current
    DESCRIPTION "Table row."
    INDEX { dpConfigAssemblyFunctionIndex, IMPLIED dpConfigAssemblyFunctionname }

    ::= { dpConfigAssemblyFunctionTable 1 }

DPConfigAssemblyFunctionEntry ::= SEQUENCE {
    dpConfigAssemblyFunctionIndex    Unsigned32,
    dpConfigAssemblyFunctionname    DisplayString
}

dpConfigAssemblyFunctionIndex OBJECT-TYPE
    SYNTAX      Unsigned32
    MAX-ACCESS  read-only
    STATUS      current
    DESCRIPTION "No description yet."

    ::= { dpConfigAssemblyFunctionEntry 1 }

dpConfigAssemblyFunctionname OBJECT-TYPE
    SYNTAX      DisplayString
    MAX-ACCESS  read-only
    STATUS      current
    DESCRIPTION "No description yet."

    ::= { dpConfigAssemblyFunctionEntry 2 }

--

dpConfigAssemblyActionFunctionCallTable OBJECT-TYPE
    SYNTAX      SEQUENCE OF DPConfigAssemblyActionFunctionCallEntry
    MAX-ACCESS  not-accessible
    STATUS      current
    DESCRIPTION
        "An assembly function call action specifies an assembly function that
        contains custom logic to add to an assembly."

    ::= { dpConfig 646 }

dpConfigAssemblyActionFunctionCallEntry OBJECT-TYPE
    SYNTAX      DPConfigAssemblyActionFunctionCallEntry
    MAX-ACCESS  not-accessible
    STATUS      current
    DESCRIPTION "Table row."
    INDEX { dpConfigAssemblyActionFunctionCallIndex, IMPLIED dpConfigAssemblyActionFunctionCallname }

    ::= { dpConfigAssemblyActionFunctionCallTable 1 }

DPConfigAssemblyActionFunctionCallEntry ::= SEQUENCE {
    dpConfigAssemblyActionFunctionCallIndex    Unsigned32,
    dpConfigAssemblyActionFunctionCallname    DisplayString
}

dpConfigAssemblyActionFunctionCallIndex OBJECT-TYPE
    SYNTAX      Unsigned32
    MAX-ACCESS  read-only
    STATUS      current
    DESCRIPTION "No description yet."

    ::= { dpConfigAssemblyActionFunctionCallEntry 1 }

dpConfigAssemblyActionFunctionCallname OBJECT-TYPE
    SYNTAX      DisplayString
    MAX-ACCESS  read-only
    STATUS      current
    DESCRIPTION "No description yet."

    ::= { dpConfigAssemblyActionFunctionCallEntry 2 }

--

dpConfigGatewayPeeringManagerTable OBJECT-TYPE
    SYNTAX      SEQUENCE OF DPConfigGatewayPeeringManagerEntry
    MAX-ACCESS  not-accessible
    STATUS      current
    DESCRIPTION
        "The gateway peering manager provides storage configuration to rate limit,
        subscription, and debug probe objects."

    ::= { dpConfig 648 }

dpConfigGatewayPeeringManagerEntry OBJECT-TYPE
    SYNTAX      DPConfigGatewayPeeringManagerEntry
    MAX-ACCESS  not-accessible
    STATUS      current
    DESCRIPTION "Table row."
    INDEX { dpConfigGatewayPeeringManagerIndex, IMPLIED dpConfigGatewayPeeringManagername }

    ::= { dpConfigGatewayPeeringManagerTable 1 }

DPConfigGatewayPeeringManagerEntry ::= SEQUENCE {
    dpConfigGatewayPeeringManagerIndex    Unsigned32,
    dpConfigGatewayPeeringManagername    DisplayString
}

dpConfigGatewayPeeringManagerIndex OBJECT-TYPE
    SYNTAX      Unsigned32
    MAX-ACCESS  read-only
    STATUS      current
    DESCRIPTION "No description yet."

    ::= { dpConfigGatewayPeeringManagerEntry 1 }

dpConfigGatewayPeeringManagername OBJECT-TYPE
    SYNTAX      DisplayString
    MAX-ACCESS  read-only
    STATUS      current
    DESCRIPTION "No description yet."

    ::= { dpConfigGatewayPeeringManagerEntry 2 }

--

dpConfigAssemblyActionLogTable OBJECT-TYPE
    SYNTAX      SEQUENCE OF DPConfigAssemblyActionLogEntry
    MAX-ACCESS  not-accessible
    STATUS      current
    DESCRIPTION
        "An assembly log action writes transaction data to the API context to send
        to the analytics server. The API activity logging settings specified in
        the API definition determine the type of transaction data that is
        gathered. This action is not supported in IBM Cloud. Any assembly that
        includes it will fail."

    ::= { dpConfig 649 }

dpConfigAssemblyActionLogEntry OBJECT-TYPE
    SYNTAX      DPConfigAssemblyActionLogEntry
    MAX-ACCESS  not-accessible
    STATUS      current
    DESCRIPTION "Table row."
    INDEX { dpConfigAssemblyActionLogIndex, IMPLIED dpConfigAssemblyActionLogname }

    ::= { dpConfigAssemblyActionLogTable 1 }

DPConfigAssemblyActionLogEntry ::= SEQUENCE {
    dpConfigAssemblyActionLogIndex    Unsigned32,
    dpConfigAssemblyActionLogname    DisplayString
}

dpConfigAssemblyActionLogIndex OBJECT-TYPE
    SYNTAX      Unsigned32
    MAX-ACCESS  read-only
    STATUS      current
    DESCRIPTION "No description yet."

    ::= { dpConfigAssemblyActionLogEntry 1 }

dpConfigAssemblyActionLogname OBJECT-TYPE
    SYNTAX      DisplayString
    MAX-ACCESS  read-only
    STATUS      current
    DESCRIPTION "No description yet."

    ::= { dpConfigAssemblyActionLogEntry 2 }

--

dpConfigAssemblyActionRateLimitTable OBJECT-TYPE
    SYNTAX      SEQUENCE OF DPConfigAssemblyActionRateLimitEntry
    MAX-ACCESS  not-accessible
    STATUS      current
    DESCRIPTION
        "An assembly rate limit action applies rate limiting, burst limiting, count
        limiting, or any combination of these to subsequent actions in the
        assembly. This action is not supported in IBM Cloud. Any assembly that
        includes it will fail."

    ::= { dpConfig 650 }

dpConfigAssemblyActionRateLimitEntry OBJECT-TYPE
    SYNTAX      DPConfigAssemblyActionRateLimitEntry
    MAX-ACCESS  not-accessible
    STATUS      current
    DESCRIPTION "Table row."
    INDEX { dpConfigAssemblyActionRateLimitIndex, IMPLIED dpConfigAssemblyActionRateLimitname }

    ::= { dpConfigAssemblyActionRateLimitTable 1 }

DPConfigAssemblyActionRateLimitEntry ::= SEQUENCE {
    dpConfigAssemblyActionRateLimitIndex    Unsigned32,
    dpConfigAssemblyActionRateLimitname    DisplayString
}

dpConfigAssemblyActionRateLimitIndex OBJECT-TYPE
    SYNTAX      Unsigned32
    MAX-ACCESS  read-only
    STATUS      current
    DESCRIPTION "No description yet."

    ::= { dpConfigAssemblyActionRateLimitEntry 1 }

dpConfigAssemblyActionRateLimitname OBJECT-TYPE
    SYNTAX      DisplayString
    MAX-ACCESS  read-only
    STATUS      current
    DESCRIPTION "No description yet."

    ::= { dpConfigAssemblyActionRateLimitEntry 2 }

--

dpConfigAssemblyActionRedactTable OBJECT-TYPE
    SYNTAX      SEQUENCE OF DPConfigAssemblyActionRedactEntry
    MAX-ACCESS  not-accessible
    STATUS      current
    DESCRIPTION
        "You use the Redact action to redact or remove specified fields from the
        request body, the response body, or the activity logs."

    ::= { dpConfig 651 }

dpConfigAssemblyActionRedactEntry OBJECT-TYPE
    SYNTAX      DPConfigAssemblyActionRedactEntry
    MAX-ACCESS  not-accessible
    STATUS      current
    DESCRIPTION "Table row."
    INDEX { dpConfigAssemblyActionRedactIndex, IMPLIED dpConfigAssemblyActionRedactname }

    ::= { dpConfigAssemblyActionRedactTable 1 }

DPConfigAssemblyActionRedactEntry ::= SEQUENCE {
    dpConfigAssemblyActionRedactIndex    Unsigned32,
    dpConfigAssemblyActionRedactname    DisplayString
}

dpConfigAssemblyActionRedactIndex OBJECT-TYPE
    SYNTAX      Unsigned32
    MAX-ACCESS  read-only
    STATUS      current
    DESCRIPTION "No description yet."

    ::= { dpConfigAssemblyActionRedactEntry 1 }

dpConfigAssemblyActionRedactname OBJECT-TYPE
    SYNTAX      DisplayString
    MAX-ACCESS  read-only
    STATUS      current
    DESCRIPTION "No description yet."

    ::= { dpConfigAssemblyActionRedactEntry 2 }

--

dpConfigProductInsightsTable OBJECT-TYPE
    SYNTAX      SEQUENCE OF DPConfigProductInsightsEntry
    MAX-ACCESS  not-accessible
    STATUS      current
    DESCRIPTION "Table."

    ::= { dpConfig 850 }

dpConfigProductInsightsEntry OBJECT-TYPE
    SYNTAX      DPConfigProductInsightsEntry
    MAX-ACCESS  not-accessible
    STATUS      current
    DESCRIPTION "Table row."
    INDEX { dpConfigProductInsightsIndex, IMPLIED dpConfigProductInsightsname }

    ::= { dpConfigProductInsightsTable 1 }

DPConfigProductInsightsEntry ::= SEQUENCE {
    dpConfigProductInsightsIndex    Unsigned32,
    dpConfigProductInsightsname    DisplayString
}

dpConfigProductInsightsIndex OBJECT-TYPE
    SYNTAX      Unsigned32
    MAX-ACCESS  read-only
    STATUS      current
    DESCRIPTION "No description yet."

    ::= { dpConfigProductInsightsEntry 1 }

dpConfigProductInsightsname OBJECT-TYPE
    SYNTAX      DisplayString
    MAX-ACCESS  read-only
    STATUS      current
    DESCRIPTION "No description yet."

    ::= { dpConfigProductInsightsEntry 2 }

END
