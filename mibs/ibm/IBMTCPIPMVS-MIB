---------------------------------------------------------------------
 --
 -- March     23, 2001
 --
 -- Kristine Adamson,  Internet: adamson§us.ibm.com
 --    IBM Communications Server Development
 --    Research Triangle Park, NC
 --
 -- Replace   IBMTCPIPMVS
 --           ibmTcpIpMvs
 --
 -- Program name : IBM Communications Server
 --                Enterprise Specific MIB ASN.1 Description file
 -- Requires: IBM Communications Server
 --           Version 1 Release 2
 -- Description : Managing the IBM Communications Server
 --               Enterprise Specific MIB
 --
 ---------------------------------------------------------------------
 IBMTCPIPMVS-MIB DEFINITIONS ::= BEGIN

        IMPORTS
            MODULE-IDENTITY, OBJECT-TYPE, NOTIFICATION-TYPE,
            enterprises, Integer32, IpAddress, TimeTicks, Counter32,
            Unsigned32, Gauge32, BITS
               FROM SNMPv2-SMI                 -- RFC1902

            TEXTUAL-CONVENTION, DisplayString, DateAndTime, TruthValue,
            RowStatus
               FROM SNMPv2-TC                  -- RFC1903

           MODULE-COMPLIANCE, OBJECT-GROUP, NOTIFICATION-GROUP
              FROM SNMPv2-CONF                 -- RFC1904

           ifIndex
              FROM IF-MIB                      -- RFC2233

           ipForwardEntry
              FROM IP-FORWARD-MIB

           tcpConnEntry
              FROM TCP-MIB                     -- RFC2012

           udpEntry
              FROM UDP-MIB

           SnmpAdminString
              FROM SNMP-FRAMEWORK-MIB          -- RFC2571

           InetAddressType, InetAddress
              FROM INET-ADDRESS-MIB;           -- RFC2851

--
--      mvsSNMPagent OID mappings
--
--      mvsSNMPagent ::= { 1.3.6.1.4.1.2.6.19 }
--      mvsSNMPRemPing ::= { mvsSNMPagent 1 } <- obsolete
--      ibmTCPIPmvsMIB ::= { mvsSNMPagent 2 }
--         ibmRemotePingGroup        ::= { ibmTCPIPmvsMIBObjects 1 }
--         ibmTcpipMvsSystem         ::= { ibmTCPIPmvsMIBObjects 2 }
--         ibmTcpipMvsInterfaceGroup ::= { ibmTCPIPmvsMIBObjects 3 }
--         ibmTcpipMvsPortGroup      ::= { ibmTCPIPmvsMIBObjects 4 }
--         ibmTcpipMvsRouteGroup     ::= { ibmTCPIPmvsMIBObjects 5 }
--         ibmTcpipMvsAtmGroup       ::= { ibmTCPIPmvsMIBObjects 6 }
--         ibmTcpipMvsTcpGroup       ::= { ibmTCPIPmvsMIBObjects 7 }
--         ibmTcpipMvsUdpGroup       ::= { ibmTCPIPmvsMIBObjects 8 }
--         ibmTcpipMvsIpGroup        ::= { ibmTCPIPmvsMIBObjects 9 }
--         ibmTcpipMvsOsaExpGroup    ::= { ibmTCPIPmvsMIBObjects 10 }
--         ibmTcpipMvsDVIPAGroup     ::= { ibmTCPIPmvsMIBObjects 11 }
--
--      SNMPv2 Agent's sysObjectId
--         ibmTcpIpMvs ::= { 1.3.6.1.4.1.2.3.13 }
--      SNMPv2 Agent's sysORTable entry
--           ::= { 1.3.6.1.4.1.2.11.7.1 }
--      DPI Subagent OID used with DPI and placed in sysORTable
--         ibmTcpIpMvsDpiSaCaps ::= { 1.3.6.1.4.1.2.11.7.2 }
--

        ibmTCPIPmvsMIB MODULE-IDENTITY
           LAST-UPDATED "200103230000Z"
           ORGANIZATION "IBM z/OS Communications Server
                         Development"
           CONTACT-INFO
               "        Kristine Adamson

                Postal: International Business Machines Corporation
                        P.O. Box 12195
                        Dept. G86A/Bldg. 501
                        Research Triangle Park, NC 27709
                        USA

                   Tel: +1 919 254 7911

              Internet: adamson§us.ibm.com"
           DESCRIPTION
               "The IBM Communications Server
                Enterprise Specific MIB definitions for enabling
                management of an IBM Communications Server
                IP system.

                Licensed Materials - Property of IBM
                Restricted Materials of IBM
                5694-A01 (C) Copyright IBM Corp. 1997, 2001
                US Government Users Restricted Rights -
                Use, duplication or disclosure restricted by
                GSA ADP Schedule Contract with IBM Corp."
           REVISION "200103230000Z"
           DESCRIPTION
                  "Changes in this revision
                   - Obsoleted the following MIB objects:
                       ibmMvsTcpConnTcpTimer
                       ibmMvsTcpConnTcpSig
                       ibmMvsTcpConnTcpSel
                       ibmMvsTcpConnTcpDet
                       ibmMvsTcpConnTcpPol
                   - Added ibmTCPIPmvsTcpGroup6
                   - Added the following TCP statistics MIB objects:
                       ibmMvsTcpConnsClosed
                       ibmMvsTcpPassiveDrops
                       ibmMvsTcpTimeWaitReused
                       ibmMvsTcpPredictAck
                       ibmMvsTcpPredictData
                       ibmMvsTcpInDupAck
                       ibmMvsTcpInBadSum
                       ibmMvsTcpInBadLen
                       ibmMvsTcpInShort
                       ibmMvsTcpInPawsDrop
                       ibmMvsTcpInAllBeforeWin
                       ibmMvsTcpInSomeBeforeWin
                       ibmMvsTcpInAllAfterWin
                       ibmMvsTcpInSomeAfterWin
                       ibmMvsTcpInOutOfOrder
                       ibmMvsTcpInAfterClose
                       ibmMvsTcpInWinProbes
                       ibmMvsTcpInWinUpdates
                       ibmMvsTcpOutWinUpdates
                       ibmMvsTcpOutDelayAcks
                       ibmMvsTcpOutWinProbes
                       ibmMvsTcpRxmtTimers
                       ibmMvsTcpRxmtDrops
                       ibmMvsTcpPMTURxmts
                       ibmMvsTcpPMTUErrors
                       ibmMvsTcpProbeDrops
                       ibmMvsTcpKeepAliveProbes
                       ibmMvsTcpKeepAliveDrops
                       ibmMvsTcpFinwait2Drops
                   - Added ibmTCPIPmvsIpGroup
                   - Added the following IP statistics MIB objects:
                       ibmMvsIpInDevLayerCalls
                       ibmMvsIpInUnpackErrors
                       ibmMvsIpInDiscardsMemory
                       ibmMvsIpOutDiscardsDlcSynch
                       ibmMvsIpOutDiscardsDlcAsynch
                       ibmMvsIpOutDiscardsMemory
                   - Added the following MIB objects to the TCP
                     connection table:
                       ibmMvsTcpConnSndBufSize
                       ibmMvsTcpConnAcceptCount
                       ibmMvsTcpConnExceedBacklog
                       ibmMvsTcpConnCurrBacklog
                       ibmMvsTcpConnMaxBacklog
                       ibmMvsTcpConnWindowScale
                       ibmMvsTcpConnTimeStamp
                       ibmMvsTcpConnServerResourceId
                   - Added ibmTCPIPmvsSystemGroup7
                   - Added the following MIB objects to the System
                     group:
                       ibmMvsTcpFinwait2Time
                       ibmMvsTcpTimeStamp
                       ibmMvsTcpipSubagentVersion
                   - Added OSA-Express adapter management data
                     - Added ibmTCPIPmvsOsaExpGroup
                     - Added the following new MIB tables for
                       OSA-Express adapters:
                         osaexpChannelTable
                         osaexpPerfTable
                         osaexpEthPortTable
                         osaexpEthSnaTable
                     - Moved channel management data for OSA-Express
                       ATM155 adapters from the osasfChannelTable to
                       the osaexpChannelTable
                   - The DeviceLinkTypes textual convention was
                     updated
                   - ibmMvsAtmSnaLeLlcTi object was updated
                     - Removed range values from SYNTAX
                     - Changed DESCRIPTION
                   - Changed DESCRIPTION of ibmMvsAtmSnaLeLlcT1
                   - Changed DESCRIPTION of ibmMvsAtmSnaceLlcT2
                   - Changed DESCRIPTION of
                     ibmMvsAtmOsasfPortIpAddress object
                   - Changed SYNTAX and DESCRIPTION of the following
                     MIB objects:
                       ibmMvsDeviceNetmanEnabled
                       ibmMvsDeviceRouterStatus
                       ibmMvsDeviceActualRouterStatus
                       ibmMvsLinkIbmtrCanonical
                       ibmMvsLinkIbmtrBcast
                       ibmMvsAtmOsasfChannelSubType
                   - Changed DESCRIPTION of ibmMvsTcpConnReXmt
                   - Changed DESCRIPTION of ibmMvsTcpConnReXmtCount
                   - Added ibmTCPIPmvsInterfacesGroup5
                   - Added the following MIB objects to the Device
                     table:
                       ibmMvsDeviceConfigPackingMode
                       ibmMvsDeviceActualPackingMode
                   - Added MIB object ibmMvsLinkMacAddress to the
                     Link table
                   - Added Dynamic VIPA management data
                     - Added ibmTCPIPmvsDVIPAGroup
                     - Added the following MIB tables:
                         ibmMvsDVIPATable
                         ibmMvsDVIPARangeConfTable
                         ibmMvsDVIPADistConfTable
                         ibmMvsDVIPAConnRoutingTable
                         ibmMvsDVIPADistPortTable
                     - Added the following MIB traps:
                         ibmMvsDVIPAStatusChange
                         ibmMvsDVIPARemoved
                         ibmMvsDVIPATargetAdded
                         ibmMvsDVIPATargetRemoved
                         ibmMvsDVIPATargetServerStarted
                         ibmMvsDVIPATargetServerEnded
                   - Added ibmTcpipMvsTcpListenerTable
                   - Added Subagent MIB trap
                     ibmMvsTcpipSubagentColdStart"
           REVISION "0005080000Z"
           DESCRIPTION
                  "Changes in this revision
                   - Added ibmMvsPortBindIpAddr
                   - Added ibmMvsPortSAFResource
                   - Changed DESCRIPTION of ibmMvsDeviceRouterStatus
                   - Added ibmMvsDeviceActualRouterStatus
                   - Added ibmMvsLinkArpSupport
                   - Added enumerated values to object
                     ibmMvsAtmOsasfChannelType
                   - Added an enumerated value to object
                     ibmMvsAtmOsasfChannelSubType
                   - Added an enumerated value to object
                     ibmMvsAtmOsasfChannelHwModel
                   - Obsoleted the following ATM MIB objects
                       ibmMvsAtmOsasfChannelEcLevel
                       ibmMvsAtmOsasfChannelDate
                       ibmMvsAtmOsasfChannelTime
                   - Changed DESCRIPTION of ibmMvsAtmOsasfPortType
                   - Changed DESCRIPTION of ibmMvsAtmOsasfPortPcmName
                   - Added an enumerated value to object
                     ibmMvsAtmOsasfPortCodeLoadStatus
                   - Changed the range of the values for objects
                     ibmMvsAtmSnaleMaxStations and
                     ibmMvsAtmSnaleMaxSaps
                   - Changed DESCRIPTION of ibmMvsAtmSnaLeLlcTi
                   - Changed DESCRIPTION of ibmMvsAtmSnaLeLlcT1
                   - Changed DESCRIPTION of ibmMvsAtmSnaLeLlcT2
                   - Changed DESCRIPTION of ibmMvsAtmSnaLeMaxStations
                   - Changed DESCRIPTION of ibmMvsAtmSnaLeMaxSaps
                   - Changed DESCRIPTION of ibmMvsAtmSnaLeMaxIn
                   - Changed DESCRIPTION of ibmMvsAtmSnaLeMaxOut
                   - Changed DESCRIPTION of
                       ibmMvsAtmSnaLeTrEnableLoadBalancing
                   - Changed DESCRIPTION of
                       ibmMvsAtmSnaLeTrLoadBalancing
                   - Changed DESCRIPTION of
                       ibmMvsAtmSnaLeTrSessionDelay
                   - Added ibmTCPIPmvsInterfacesGroup4
                   - Added ibmTCPIPmvsPortGroup2
                   - Added ibmTCPIPmvsAtmSupportGroup4
                   - The DeviceLinkTypes textual convention was
                     updated
                   - Obsoleted the following TCP/UDP MIB objects
                       ibmMvsTcpConnIpTos
                       ibmMvsUdpTos
                   - Obsoleted the TypeOfService textual convention
                   - Added ibmMvsTcpConnDSField
                   - Added ibmMvsUdpDSField
                   - Added ibmTCPIPmvsTcpGroup5
                   - Added ibmTCPIPmvsUdpGroup3
                   - Changed DESCRIPTION of
                       ibmMvsAtmLecConfigTable
                       ibmMvsAtmLecStatusTable
                       ibmMvsAtmLecStatisticsTable
                       ibmMvsAtmLecServerTable
                       ibmMvsAtmLecMacAddressTable
                   - Added ibmMvsAtmLecPortName
                   - Added ibmMvsPortReuse
                   - Added an enumerated value to object
                     ibmMvsAtmOsasfPortHardwareState
                   - Added ibmTCPIPmvsSystemGroup6
                   - Added ibmMvsDevRetryDuration"
           REVISION "9904010000Z"
           DESCRIPTION
                  "Changes in this revision
                   - The DeviceLinkTypes textual convention was
                     updated
                   - several MIB objects were changed from Integer32
                     to Counter32:
                       ibmMvsTcpConnUsrSndNxt
                       ibmMvsTcpConnSndNxt
                       ibmMvsTcpConnSndUna
                       ibmMvsTcpConnOutgoingPush
                       ibmMvsTcpConnOutgoingUrg
                       ibmMvsTcpConnOutgoingWinSeq
                       ibmMvsTcpConnRcvNxt
                       ibmMvsTcpConnUsrRcvNxt
                       ibmMvsTcpConnIncomingPush
                       ibmMvsTcpConnIncomingUrg
                       ibmMvsTcpConnIncomingWinSeq
                       ibmMvsTcpConnSndWl1
                       ibmMvsTcpConnSndWl2
                       ibmMvsTcpConnRttSeq
                       ibmMvsTcpConnRttSeq
                       ibmMvsUdpDgramIn
                       ibmMvsUdpBytesIn
                       ibmMvsUdpDgramOut
                       ibmMvsUdpBytesOut
                   - several MIB objects were changed from Integer32
                     to Unsigned32:
                       ibmMvsLinkMcastRefCount
                       ibmMvsAtmOsasfPvcFwdCellBurstSize
                       ibmMvsAtmOsasfPvcBwdCellBurstSize
                       ibmMvsAtmSnaLeBestEffortPeakRate
                       ibmMvsAtmLecMulticastSendAvgRate
                       ibmMvsAtmLecMulticastSendPeakRate
                       ibmMvsTcpConnBytesIn
                       ibmMvsTcpConnBytesOut
                       ibmMvsTcpConnOutBuffered
                       ibmMvsTcpConnInBuffered
                       ibmMvsTcpConnMaxSndWnd
                       ibmMvsTcpConnCongestionWnd
                       ibmMvsTcpConnSSThresh
                       ibmMvsTcpConnRoundTripTime
                       ibmMvsTcpConnRoundTripVariance
                       ibmMvsTcpConnInitSndSeq
                       ibmMvsTcpConnInitRcvSeq
                       ibmMvsTcpConnSendMSS
                       ibmMvsTcpConnSndWnd
                       ibmMvsTcpConnRcvBufSize
                       ibmMvsTcpConnSubtask
                       ibmMvsTcpConnResourceId
                       ibmMvsTcpConnDupAcks
                       ibmMvsUdpSubtask
                       ibmMvsUdpResourceId
                       ibmMvsUdpSendLim
                       ibmMvsUdpRecvLim
                   - A couple MIB objects were changed from Integer32
                     to OCTET STRING (SIZE(1)):
                       ibmMvsTcpConnTcpTimer
                       ibmMvsTcpConnTcpSig
                       ibmMvsTcpConnTcpSel
                   - Some MIB objects were changed from STATUS of
                     current to obsolete:
                       ibmMvsAtmOsasfChannelVtamid
                       ibmMvsTcpConnActiveOpen
                       ibmMvsTcpConnPendTcpRecv
                       ibmMvsTcpConnBackoffCount
                   - Updated description of ibmMvsTcpConnTcpSig
                     MIB object
                   - Added values to the DeviceLinkTypes textual
                     convention
                   - Removed unused definition of ibmAgents
                   - Corrected name of ibmAgentCapabilities to
                     to ibmAgentCaps
                   - Obsoleted ibmMvsMultipathEnabled
                   - Added ibmMvsMultipathType
                   - Added ibmMvsTcpConnInSegs
                   - Added ibmMvsTcpConnOutSegs
                   - Added ibmTCPIPmvsSystemGroup5
                   - Added ibmTCPIPmvsTcpGroup4
                   - Added ibmTCPIPmvsAtmSupportGroup3
                   - Added ibmMvsIpForwarding"
           REVISION "9809160000Z"
           DESCRIPTION
                  "Changes in this revision
                   - Added ibmMvsLinkChecksumEnabled"
           REVISION "9808260000Z"
           DESCRIPTION
                  "Updated descriptions of following objects:
                   - ibmMvsTcpConnSockOpt
                   - ibmMvsTcpConnTcpTimer
                   - ibmMvsTcpConnTcpSig
                   - ibmMvsTcpConnTcpSel
                   - ibmMvsTcpConnTcpDet
                   - ibmMvsTcpConnTcpPol"
           REVISION "9806030000Z"
           DESCRIPTION
                  "Changes in this revision
                   - Added ibmTCPIPmvsSystemGroup4
                   - Added ibmMvsPathMtuDscEnabled
                   - Added ibmTCPIPmvsInterfacesGroup3
                   - Added ibmMvsDeviceRouterStatus"
           REVISION "9803050000Z"
           DESCRIPTION
                  "Changes in this revision
                   - Added copyright
                   - Changed CONTACT-INFO
                   - Added ibmTCPIPmvsSystemGroup3
                   - Added ibmTCPIPmvsInterfacesGroup2
                   - Added ibmTCPIPmvsUdpGroup2
                   - Added ibmMvsTcpMaxReceiveBufferSize
                   - Added ibmMvsMultipathEnabled
                   - Added ibmMvsLinkMcast
                   - Added ibmMvsLinkMcastRefCount"
        ::= { mvsSNMPagent 2 }


        ibm OBJECT IDENTIFIER ::= { enterprises 2 }
        ibmProd OBJECT IDENTIFIER ::= { ibm 6 }
        mvsSNMPagent OBJECT IDENTIFIER ::= { ibmProd 19 }
        ibmAgentCaps OBJECT IDENTIFIER ::= { ibm 11 }


 ibmTCPIPmvsMIBTraps     OBJECT IDENTIFIER ::= { ibmTCPIPmvsMIB 0 }
 ibmTCPIPmvsAdmin        OBJECT IDENTIFIER ::= { ibmTCPIPmvsMIB 1 }
 ibmTCPIPmvsMIBObjects   OBJECT IDENTIFIER ::= { ibmTCPIPmvsMIB 2 }
 ibmTCPIPmvsConformance  OBJECT IDENTIFIER ::= { ibmTCPIPmvsMIB 3 }

 ---------------------------------------------------------------------
 -- Textual Conventions
 ---------------------------------------------------------------------

     TypeOfService ::= TEXTUAL-CONVENTION
          DISPLAY-HINT "1a"
          STATUS       obsolete
          DESCRIPTION
           "Definition of Type-of-Service (tos). The TOS facility is
            one of the features of the Type of Service octet in the
            IP datagram header.  The Type of Service octet consists
            of three fields:

                 0     1     2     3     4     5     6     7
              +-----+-----+-----+-----+-----+-----+-----+-----+
              :                 :                       :     :
              :   PRECEDENCE    :          TOS          : MBZ :
              :                 :                       :     :
              +-----+-----+-----+-----+-----+-----+-----+-----+

            The first field, labeled 'PRECEDENCE' above, is intended
            to denote the importance or priority of the datagram.
            The second field, labeled 'TOS' above, denotes how the
            network should make tradeoffs between throughput, delay,
            reliability, and cost.

            The last field, labeled 'MBZ' (for 'must be zero') above,
            is currently unused.  The originator of a datagram sets
            this field zero (unless participating in an Internet
            protocol experiment which makes use of that bit).  Routers
            and recipients of datagrams ignore the value of this field.
            This field is copied fragmentation.

            In the past there has been some confusion about the size
            of the TOS field.  RFC-791 defined it as a three bit field,
            including bits 3-5 in the figure above.  It included bit 6
            in the MBZ field.  RFC-1122 added bits 6 and 7 to the TOS
            field, eliminating the MBZ field.  RFC-1349 further
            redefined the TOS field to be the four bits shown in the
            figure above.

            The semantics of the following TOS field values (expressed
            as binary numbers):

               1000   --   minimize delay
               0100   --   maximize throughput
               0010   --   maximize reliability
               0001   --   minimize monetary cost
               0000   --   normal service

            Precendence declarations

                111   --    network control
                110   --    internetwork control
                101   --    critic ECP
                100   --    flash override
                011   --    flash
                010   --    immediate
                001   --    priority
                000   --    routine

            TOS default is 0."
          SYNTAX       Integer32
-- OCTET STRING (SIZE(1))

     DeviceLinkTypes ::= TEXTUAL-CONVENTION
          DISPLAY-HINT "1a"
          STATUS       current
          DESCRIPTION
           "Defines the various device and link types."
          SYNTAX  INTEGER {
                             unknown(0),
                             lcs(1),
                             ctc(2),
                             claw(3),
                             cdlc(4),
                             atm(5),
                             x25npsi(6),
                             vipa(7),
                             loopback(8),
                             hch(9),
                             ethernet(10),
                             t8023(11),
                             etheror8023(12),
                             ibmtr(13),
                             fddi(14),
                             ip(15),
                             iucv(16),
                             stack(17),
                             mpcptp(18),
                             snalu0(19),
                             snalu62(20),
                             mpcipa(21),
                             ipaqenet(22),
                             mpcosa(24),
                             osafddi(25),
                             osaenet(26),
                             ipaqtr(27),
                             ipaqidio(28)
                           }

 ---------------------------------------------------------------------
 -- Define the groups of objects within the MIBObjects subtree
 ---------------------------------------------------------------------

 ibmRemotePingGroup OBJECT IDENTIFIER ::= { ibmTCPIPmvsMIBObjects 1 }
 -- This group of objects provides the remote ping function for
 -- release OS/390 TCP/IP OpenEdition and later releases.

 ibmTcpipMvsSystem OBJECT IDENTIFIER
          ::= { ibmTCPIPmvsMIBObjects 2 }
 -- This group defines various global controls or
 -- system parameters/settings.

 ibmTcpipMvsInterfaceGroup OBJECT IDENTIFIER
          ::= { ibmTCPIPmvsMIBObjects 3 }

 ibmTcpipMvsPortGroup OBJECT IDENTIFIER
          ::= { ibmTCPIPmvsMIBObjects 4 }

 ibmTcpipMvsRouteGroup OBJECT IDENTIFIER
          ::= { ibmTCPIPmvsMIBObjects 5 }

 ibmTcpipMvsAtmGroup OBJECT IDENTIFIER
          ::= { ibmTCPIPmvsMIBObjects 6 }

 ibmTcpipMvsTcpGroup OBJECT IDENTIFIER
          ::= { ibmTCPIPmvsMIBObjects 7 }

 ibmTcpipMvsUdpGroup OBJECT IDENTIFIER
          ::= { ibmTCPIPmvsMIBObjects 8 }

 ibmTcpipMvsIpGroup  OBJECT IDENTIFIER
          ::= { ibmTCPIPmvsMIBObjects 9 }

 ibmTcpipMvsOsaExpGroup OBJECT IDENTIFIER
          ::= { ibmTCPIPmvsMIBObjects 10 }

 ibmTcpipMvsDVIPAGroup OBJECT IDENTIFIER
          ::= { ibmTCPIPmvsMIBObjects 11 }


 --
 --     This object is obsolete, don't use it}
 --
        ibmSNMPRemPing OBJECT-TYPE
           SYNTAX  Integer32
           MAX-ACCESS  read-only
           STATUS  obsolete
           DESCRIPTION
                 "The number of milliseconds it takes for an icmp
                  echo request to respond.  ibmSNMPRemPing is -1 if
                  there is an internal error, -2 if the echo request
                  timed out, -4 if the packet size is invalid,
                  -5 if the timeout is invalid, -6 if
                  the IP address was not valid and -7 if the
                  format of the MIB instance is not valid.
                    To request the icmp response time for ip
                  address a.b.c.d with a timeout of e and a packet
                  size of f, send an snmp get request for
                  ibmSNMPRemPing.f.e.a.b.c.d.  For example,
                  suppose one wanted to find out the number of
                  milliseconds it took to ping address 9.67.30.4,
                  with a timeout of 8 seconds, and a packet size of
                  94 bytes.  Accordingly,
                  ibmSNMPRemPing.94.8.9.67.30.4 would identify the
                  number of milliseconds."
        REFERENCE
                 "Refer to the IBM Communications Server:
                  IP User's Guide for an explanation of the
                  remote ping function."
        ::= { mvsSNMPagent 1 }

 ---------------------------------------------------------------------
 -- ibmRemotePingGroup
 ---------------------------------------------------------------------

        --
        -- Definition of the remote ping table for use in requesting
        -- the ping time between two TCP/IP hosts.
        --
        ibmRemotePingTable OBJECT-TYPE
        SYNTAX SEQUENCE OF IbmRemotePingEntry
        MAX-ACCESS not-accessible
        STATUS current
        DESCRIPTION
           "Defines the a remote ping table in order to use
            the various parameters as indeces into the table."
        ::= { ibmRemotePingGroup 1 }

        ibmRemotePingEntry OBJECT-TYPE
        SYNTAX IbmRemotePingEntry
        MAX-ACCESS not-accessible
        STATUS current
        DESCRIPTION
           "Defines an entry in the ibmRemotePingTable. This table
            does not actual exist, but is used to faciliate passing
            the remote ping parameters."
        INDEX { ibmMvsRPingPacketSize, ibmMvsRPingTimeOut,
                ibmMvsRPingHostAddress }
        ::= { ibmRemotePingTable 1 }

        IbmRemotePingEntry ::=
          SEQUENCE
          {
          ibmMvsRPingPacketSize    Integer32,
          ibmMvsRPingTimeOut       Integer32,
          ibmMvsRPingHostAddress   IpAddress,
          ibmMvsRPingResponseTime  Integer32
          }

        ibmMvsRPingPacketSize OBJECT-TYPE
        SYNTAX Integer32
        MAX-ACCESS not-accessible
        STATUS current
        DESCRIPTION
           "Specifies the packet size in octets of the PING request.
            Valid values for packet size are 0 or from 16 to 4096."
        ::= { ibmRemotePingEntry 1 }

        ibmMvsRPingTimeOut OBJECT-TYPE
        SYNTAX Integer32
        MAX-ACCESS not-accessible
        STATUS current
        DESCRIPTION
           "Specifies the time-out value, in seconds, for the actual
            PING request made by the remote host. Valid values for
            time out are 0 or 3 to 15 seconds."
        ::= { ibmRemotePingEntry 2 }

        ibmMvsRPingHostAddress OBJECT-TYPE
        SYNTAX IpAddress
        MAX-ACCESS not-accessible
        STATUS current
        DESCRIPTION
           "Specifies the host address used on by PING request by
            the remote host. The host address specified is
            required to be an ipAddress."
        ::= { ibmRemotePingEntry 3 }

        ibmMvsRPingResponseTime OBJECT-TYPE
        SYNTAX Integer32
        MAX-ACCESS read-only
        STATUS current
        DESCRIPTION
           "The result of the PING request made by the remote host:
            >0   Round-trip response time in milliseconds.
            -1   Internal error.
            -2   ICMP echo request timed out.
            -4   Incorrect packet size.
            -5   Incorrect Time-out.
            -6   Unknown destination address.
            -7   Incorrect MIB instance format. The generic
                 noSuchInstance SNMP error could also occur if the
                 instance specified is incorrect."
        ::= { ibmRemotePingEntry 4 }

 ---------------------------------------------------------------------
 -- ibmTcpipMvsSystemGroup7
 ---------------------------------------------------------------------

     --
     --         IBM TCPIP MVS System Group
     --
     --  Provides specific information and control for the
     --  IBM TCP/IP MVS Product. All simple objects are
     --  grouped within this object.
     --

     ibmMvsSubagentCacheTime OBJECT-TYPE
     SYNTAX Integer32 (0 .. 3600)
     MAX-ACCESS read-write
     STATUS current
     DESCRIPTION
           "Specifies the amount of time to wait for re-retrieval
            of specific MIB data from target. A value of 0
            implies that every GET or GET-NEXT request should
            result in the re-retrieval of the needed data. Maximum
            amount of time to cache is 1 hour (3600 seconds)."
     DEFVAL { 30 }
     ::= { ibmTcpipMvsSystem 1 }

     ibmMvsIgnoreRedirect OBJECT-TYPE
     SYNTAX INTEGER { process(0), ignore(1) }
     MAX-ACCESS read-write
     STATUS current
     DESCRIPTION
           "IP Layer attribute, default of process redirects.
            current stack: IGNOREREDIRECT parm on
            ASSORTEDPARMS statement"
     DEFVAL { process }
     ::= { ibmTcpipMvsSystem 2 }

     ibmMvsArpCacheTimeout OBJECT-TYPE
     SYNTAX Integer32 (60 .. 86400)
     MAX-ACCESS read-write
     STATUS current
     DESCRIPTION
           "IF Layer attribute. ARP cache timeout - ARPAGE statement;
            default= 1200 seconds; 60 <= ARPAGE <= 86400 (24 hours).
            current stack: ARPAGE statement; default=
            20 minutes (1200 seconds). The value of this object is
            expressed in seconds."
     DEFVAL { 1200 }
     ::= { ibmTcpipMvsSystem 3 }

     ibmMvsTcpKeepAliveTimer OBJECT-TYPE
     SYNTAX Integer32 (0..35791)
     MAX-ACCESS read-write
     STATUS current
     DESCRIPTION
           "TCP Keepalive timer, expressed in minutes.
            A value of 0 deactivates the timer."
     DEFVAL { 120 }
     ::= { ibmTcpipMvsSystem 4 }

     ibmMvsTcpReceiveBufferSize OBJECT-TYPE
     SYNTAX Integer32 (256..524288)
     MAX-ACCESS read-write
     STATUS current
     DESCRIPTION
           "TCP Receive buffer size, expressed in bytes."
     DEFVAL { 16384 }
     ::= { ibmTcpipMvsSystem 5 }

     ibmMvsTcpSendBufferSize OBJECT-TYPE
     SYNTAX Integer32 (256..262144)
     MAX-ACCESS read-write
     STATUS current
     DESCRIPTION
           "TCP Send buffer size, expressed in bytes."
     DEFVAL { 16384 }
     ::= { ibmTcpipMvsSystem 6 }

     ibmMvsUdpChecksum OBJECT-TYPE
     SYNTAX INTEGER { off(0), on(1) }
     MAX-ACCESS read-write
     STATUS current
     DESCRIPTION
           "UDP checksum - on or off"
     DEFVAL  {  on }
     ::= { ibmTcpipMvsSystem 7 }

     ibmMvsIplDateAndTime OBJECT-TYPE
     SYNTAX DateAndTime
     MAX-ACCESS read-only
     STATUS current
     DESCRIPTION
           "The date and time that this TCP/IP instance was
            started. sysUpTime provides the time from when
            the SNMP Agent was started, not corresponding TCP/IP
            instance."
     ::= { ibmTcpipMvsSystem 8 }

     ibmMvsNoUdpQueueLimit OBJECT-TYPE
     SYNTAX INTEGER { queueLimit(0), noQueueLimit(1) }
     MAX-ACCESS read-write
     STATUS current
     DESCRIPTION
           "Indicates if the UDP queue limit of 163,840 bytes
            of UDP data per socket is in effect or not.
            163,840 is equal to 8K times 20 datagrams. This limit
            is based on the total number of bytes, not datagrams."
     DEFVAL { queueLimit }
     ::= { ibmTcpipMvsSystem 9 }

     ibmMvsSoMaxConn OBJECT-TYPE
     SYNTAX Integer32 (1..2147483647)
     MAX-ACCESS read-write
     STATUS current
     DESCRIPTION
           "Maximum number of socket connections."
     DEFVAL { 10 }
     ::= { ibmTcpipMvsSystem 10 }

     ibmMvsTcpipProcname OBJECT-TYPE
     SYNTAX DisplayString (SIZE(1..8))
     MAX-ACCESS read-only
     STATUS current
     DESCRIPTION
           "MVS Procname of this TCP/IP instance."
     ::= { ibmTcpipMvsSystem 11 }

     ibmMvsTcpipAsid OBJECT-TYPE
     SYNTAX Integer32
     MAX-ACCESS read-only
     STATUS current
     DESCRIPTION
           "MVS Address Space  ID of this TCP/IP instance."
     ::= { ibmTcpipMvsSystem 12 }

     ibmMvsSourceVipaEnabled  OBJECT-TYPE
     SYNTAX INTEGER { false(0), true(1) }
     MAX-ACCESS read-only
     STATUS current
     DESCRIPTION
           "Indicates if set to true(1) that SOURCEVIPA support
            is enabled. This object can be changed via
            the ASSORTEDPARMS TCP/IP Profile statement."
     DEFVAL { false }
     ::= { ibmTcpipMvsSystem 13 }

     ibmMvsOsasfSysplexName OBJECT-TYPE
     SYNTAX DisplayString (SIZE(0..8))
     MAX-ACCESS read-only
     STATUS current
     DESCRIPTION
           "Sysplex name, if unknown the value of the zero length
            string"
     ::= { ibmTcpipMvsSystem 14 }

     ibmMvsOsasfHostName OBJECT-TYPE
     SYNTAX DisplayString (SIZE(0..8))
     MAX-ACCESS read-only
     STATUS current
     DESCRIPTION
           "OSASF Host Name, if unknown the value of the zero length
            string"
     ::= { ibmTcpipMvsSystem 15 }

     ibmMvsOsasfProductVersion OBJECT-TYPE
     SYNTAX DisplayString (SIZE(0..8))
     MAX-ACCESS read-only
     STATUS current
     DESCRIPTION
           "version/release of product, if unknown the value of the
            zero length string"
     ::= { ibmTcpipMvsSystem 16 }

     ibmMvsPrimaryInterfaceIfIndex OBJECT-TYPE
     SYNTAX Integer32
     MAX-ACCESS read-write
     STATUS current
     DESCRIPTION
           "The ifIndex of the designated primary interface.
            A value of zero implies that this option wasn't
            configured."
     DEFVAL { 0 }
     ::= { ibmTcpipMvsSystem 17 }

     ibmMvsIpMaxReassemblySize  OBJECT-TYPE
     SYNTAX Integer32
     MAX-ACCESS read-only
     STATUS current
     DESCRIPTION
           "The maximum ip reassembly size in units of
            octets."
     DEFVAL { 65535 }
     ::= { ibmTcpipMvsSystem 18 }

     ibmMvsTcpRestrictLowPorts  OBJECT-TYPE
     SYNTAX INTEGER { false(0), true(1) }
     MAX-ACCESS read-write
     STATUS current
     DESCRIPTION
           "Indicates if TCP low ports are restricted to
            authorized servers/socket applications."
     DEFVAL { false }
     ::= { ibmTcpipMvsSystem 19 }

     ibmMvsUdpRestrictLowPorts  OBJECT-TYPE
     SYNTAX INTEGER { false(0), true(1) }
     MAX-ACCESS read-write
     STATUS current
     DESCRIPTION
           "Indicates if UDP low ports are restricted to
            authorized servers/socket applications."
     DEFVAL { false }
     ::= { ibmTcpipMvsSystem 20 }

     ibmMvsUdpSendBufferSize  OBJECT-TYPE
     SYNTAX Integer32 (1..65535)
     MAX-ACCESS read-write
     STATUS current
     DESCRIPTION
           "The default UDP send buffer size."
     DEFVAL { 65535 }
     ::= { ibmTcpipMvsSystem 21 }

     ibmMvsUdpRecvBufferSize  OBJECT-TYPE
     SYNTAX Integer32 (1..65535)
     MAX-ACCESS read-write
     STATUS current
     DESCRIPTION
           "The default UDP receive buffer size."
     DEFVAL { 65535 }
     ::= { ibmTcpipMvsSystem 22 }

     ibmMvsTcpipStatisticsEnabled  OBJECT-TYPE
     SYNTAX INTEGER { false(0), true(1) }
     MAX-ACCESS read-only
     STATUS current
     DESCRIPTION
           "Indicates if set to true(1) that the generation
            of tcp/ip statistics is enabled. Statistics if
            enabled will be recorded at the SMF interval
            via SMF record subtype 5."
     DEFVAL { false }
     ::= { ibmTcpipMvsSystem 23 }

     ibmMvsFirewallEnabled  OBJECT-TYPE
     SYNTAX INTEGER { false(0), true(1) }
     MAX-ACCESS read-only
     STATUS current
     DESCRIPTION
           "Indicates if set to true(1) that firewall support
            is enabled. This object can be changed via
            the IPCONFIG TCP/IP Profile statement."
     DEFVAL { false }
     ::= { ibmTcpipMvsSystem 24 }

     ibmMvsMaximumRetransmitTime OBJECT-TYPE
     SYNTAX Integer32
     MAX-ACCESS read-only
     STATUS current
     DESCRIPTION
           "Used in the TCP/IP re-transmission time-out calculation
            to determine how long to wait for an acknowledgement
            before resending a packet. Expressed as a integer in
            units of 100th of a second."
     DEFVAL { 120000 }
     ::= { ibmTcpipMvsSystem 25 }

     ibmMvsMinimumRetransmitTime OBJECT-TYPE
     SYNTAX Integer32
     MAX-ACCESS read-only
     STATUS current
     DESCRIPTION
           "Used in the TCP/IP re-transmission time-out calculation
            to determine how long to wait for an acknowledgement
            before resending a packet. Expressed as a integer in
            units of 100th of a second."
     DEFVAL { 500 }
     ::= { ibmTcpipMvsSystem 26 }

     ibmMvsRoundTripGain OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 125 }
     ::= { ibmTcpipMvsSystem 27 }

     ibmMvsVarianceGain OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 250 }
     ::= { ibmTcpipMvsSystem 28 }

     ibmMvsVarianceMultiplier OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 2000 }
     ::= { ibmTcpipMvsSystem 29 }

     ibmMvsSendGarbageEnabled OBJECT-TYPE
     SYNTAX INTEGER { false(0), true(1) }
     MAX-ACCESS read-only
     STATUS current
     DESCRIPTION
           "If true(1) indicates that the TCP option SENDGARBAGE
            is enabled."
     DEFVAL { false }
     ::= { ibmTcpipMvsSystem 30 }

     ibmMvsTcpMaxReceiveBufferSize OBJECT-TYPE
     SYNTAX Integer32 (256..524288)
     MAX-ACCESS read-write
     STATUS current
     DESCRIPTION
           "TCP Maximum Receive buffer size, expressed in bytes."
     DEFVAL { 262144 }
     ::= { ibmTcpipMvsSystem 31 }

     ibmMvsMultipathEnabled OBJECT-TYPE
     SYNTAX      TruthValue
     MAX-ACCESS  read-write
     STATUS obsolete
     DESCRIPTION
           "If true(1) indicates that the MULTIPATH IP option
            is enabled.  If false(2) indicates that the MULTIPATH
            IP option is disabled.
            This object is obsolete.  It has been replaced by the
            ibmMvsMultipathType object."
     DEFVAL { false }
     ::= { ibmTcpipMvsSystem 32 }

     ibmMvsPathMtuDscEnabled OBJECT-TYPE
     SYNTAX      TruthValue
     MAX-ACCESS  read-write
     STATUS current
     DESCRIPTION
           "If true(1) indicates that the PATHMTUDISCOVERY IP option
            is enabled.  If false(2) indicates that the
            PATHMTUDISCOVERY IP option is disabled."
     DEFVAL { false }
     ::= { ibmTcpipMvsSystem 33 }

     ibmMvsMultipathType    OBJECT-TYPE
     SYNTAX  INTEGER {
                        nomultipath(0),
                        perconnection(2),
                        perpacket(3)
                     }
     MAX-ACCESS  read-write
     STATUS current
     DESCRIPTION
           "The type of Multipath processing currently
            active.  The types are defined under the MULTIPATH
            parameter on the IPCONFIG Profile statement."
     DEFVAL { nomultipath }
     ::= { ibmTcpipMvsSystem 34 }

     ibmMvsIpForwarding     OBJECT-TYPE
     SYNTAX  INTEGER {
                        notForwarding(1),
                        forwardingNoMultipath(2),
                        forwardingMultipathPkt(3)
                     }
     MAX-ACCESS  read-write
     STATUS current
     DESCRIPTION
           "The indication of whether this entity is acting as an IP
            router in respect to the forwarding of datagrams received
            by, but not addressed to, this entity.  If this entity is
            acting as a router, this object also indicates what type
            of forwarding is in effect.  The value of this object
            is originally determined by the TCP/IP Profile
            ASSORTEDPARMS or IPCONFIG statements.  A value of
            notForwarding(1) indicates that this entity is not
            forwarding datagrams.  A value of forwardingNoMultipath(2)
            indicates that this entity is forwarding datagrams using
            the first available route.  A value of
            forwardingMultipathPkt(3) indicates that this entity,
            when forwarding datagrams, will select a route on a
            round-robin basis from a multipath routing list.
               This object is related to the ipForwarding object
            from RFC2011.  If ipForwarding is set to notForwarding,
            this object will also be set to notForwarding.  If
            ipForwarding is set to forwarding, this object will be
            set to forwardingNoMultipath.  If the value of this MIB
            object is changed, the value of ipForwarding will be
            changed accordingly."
     DEFVAL { forwardingNoMultipath }
     ::= { ibmTcpipMvsSystem 35 }

     ibmMvsDevRetryDuration OBJECT-TYPE
     SYNTAX Unsigned32 (0..4294967295)
     MAX-ACCESS read-write
     STATUS current
     DESCRIPTION
           "Specifies the duration of the retry period for a failed
            device. TCP/IP will perform reactivation attempts at 30
            second intervals during this retry period. The default
            duration is 90 seconds. A specification of 0 generates
            an infinite recovery period, meaning reactivation
            attempts will be performed until the device is either
            successfully reactivated, or manually stopped.
            The value of this object is originally determined by
            the DEVRETRYDURATION parameter on the IPCONFIG Profile
            statement."
     DEFVAL { 90 }
     ::= { ibmTcpipMvsSystem 36 }

     ibmMvsTcpFinwait2Time  OBJECT-TYPE
     SYNTAX Integer32 (60..3600)
     MAX-ACCESS read-write
     STATUS current
     DESCRIPTION
           "The number of seconds a TCP connection should remain in the
            FINWAIT2 state. When this timer expires, it is reset to
            75 seconds.  When it expires a second time the
            connection is dropped."
     DEFVAL { 600 }
     ::= { ibmTcpipMvsSystem 37 }

     ibmMvsTcpTimeStamp     OBJECT-TYPE
     SYNTAX     TruthValue
     MAX-ACCESS read-write
     STATUS current
     DESCRIPTION
           "If true(1), indicates that the TCPTIMESTAMP option was
            specified (or defaulted to) on the TCPCONFIG Profile
            statement. For active connections (TCP/IP initiates the
            connection) a TCP timestamp option will be sent.  For
            passive connections (TCP/IP receives a connect request)
            TCP/IP will send a SYN-ACK with its own TCP timestamp
            option.
            If false(2), indicates that the NOTCPTIMESTAMP
            option was specified on the TCPCONFIG Profile statement.
            TCP/IP will not participate in TCP timestamp negotiations
            during connection setup or at any future time in the
            life of the connection."
     DEFVAL { true }
     ::= { ibmTcpipMvsSystem 38 }

     ibmMvsTcpipSubagentVersion    OBJECT-TYPE
     SYNTAX  INTEGER {
                        v1r2(1)
                     }
     MAX-ACCESS  read-only
     STATUS current
     DESCRIPTION
           "The version/release of the TCP/IP Subagent.  The actual
            product names associated with the values of this object
            are:
               v1r2(1)    -  z/OS V1R2 Communications Server"
     ::= { ibmTcpipMvsSystem 39 }

 ---------------------------------------------------------------------
 -- ibmTcpipMvsInterfacesGroup5
 ---------------------------------------------------------------------

     --
     --         IBM TCPIP MVS Device Table
     --
     ibmTcpipMvsDeviceTable OBJECT-TYPE
     SYNTAX SEQUENCE OF IbmTcpipMvsDeviceEntry
     MAX-ACCESS not-accessible
     STATUS current
     DESCRIPTION
          "Defines the device definition known to an IBM MVS
           TCP/IP system. A virtual interface entry exists for
           every entry in this table."
     ::= { ibmTcpipMvsInterfaceGroup 1 }

     ibmTcpipMvsDeviceEntry OBJECT-TYPE
     SYNTAX IbmTcpipMvsDeviceEntry
     MAX-ACCESS not-accessible
     STATUS current
     DESCRIPTION
          "Descibes a particular device definition"
     INDEX { ifIndex }
     ::= { ibmTcpipMvsDeviceTable 1 }

     IbmTcpipMvsDeviceEntry ::=
          SEQUENCE
          {
          ibmMvsDeviceType                 DeviceLinkTypes,
          ibmMvsDeviceBaseNumber           OCTET STRING,
          ibmMvsDeviceIoBufferSize         Integer32,
          ibmMvsDeviceAutoRestart          INTEGER,
          ibmMvsDeviceNetmanEnabled        Integer32,
          ibmMvsDeviceHostClawName         DisplayString,
          ibmMvsDeviceWorkstationClawName  DisplayString,
          ibmMvsDeviceReadBuffers          Integer32,
          ibmMvsDeviceReadSize             Integer32,
          ibmMvsDeviceWriteBuffers         Integer32,
          ibmMvsDeviceWriteSize            Integer32,
          ibmMvsDeviceProcname             DisplayString,
          ibmMvsDeviceIncomingSvcEnabled   INTEGER,
          ibmMvsDeviceLuName               DisplayString,
          ibmMvsDeviceRouterStatus         Integer32,
          ibmMvsDeviceActualRouterStatus   Integer32,
          ibmMvsDeviceConfigPackingMode    Integer32,
          ibmMvsDeviceActualPackingMode    Integer32
          }

     ibmMvsDeviceType OBJECT-TYPE
     SYNTAX DeviceLinkTypes
     MAX-ACCESS read-only
     STATUS current
     DESCRIPTION
           "Indicates the device type."
     ::= { ibmTcpipMvsDeviceEntry 1 }

     ibmMvsDeviceBaseNumber OBJECT-TYPE
     SYNTAX OCTET STRING (SIZE(2))
     MAX-ACCESS read-only
     STATUS current
     DESCRIPTION
          "If this entry is for a CTC, HCH or Vipa device then this
           object represents its base device number.  For an LCS
           device this object represents the lcs address.  For a CLAW
           device this object represents the device number of the
           RS/6000 device.  For a CDLC device this object represents
           the device number.  A value of 0 implies that this object
           is not valid for the associated device table entry."
     ::= { ibmTcpipMvsDeviceEntry 2 }

     ibmMvsDeviceIoBufferSize OBJECT-TYPE
     SYNTAX Integer32 (32768 .. 65535)
     MAX-ACCESS read-only
     STATUS current
     DESCRIPTION
         "The I/O buffersize attribute for this device definition.
           This is only value for a CTC Device. A reported value
           of -1 implies that the corresponding device doesn't
            not support this attribute."
     DEFVAL { 32768 }
     ::= { ibmTcpipMvsDeviceEntry 3 }

     ibmMvsDeviceAutoRestart  OBJECT-TYPE
     SYNTAX INTEGER { false(0), true(1) }
     MAX-ACCESS read-only
     STATUS current
     DESCRIPTION
        "A value of true indicates that this device was defined
         as autorestartable. False indicates that it was not."
     ::= { ibmTcpipMvsDeviceEntry 4 }

     ibmMvsDeviceNetmanEnabled OBJECT-TYPE
     SYNTAX Integer32
     MAX-ACCESS read-only
     STATUS current
     DESCRIPTION
        "A value of 1 indicates that this is an LCS device that
         was defined to support the 3172 ICP MIB. A value of 0
         indicates that this is an LCS device that was not defined
         to support the 3172 ICP MIB. A reported value of
         -1 implies that this object is invalid for the
         corresponding device table entry."
     DEFVAL { -1 }
     ::= { ibmTcpipMvsDeviceEntry 5 }

     ibmMvsDeviceHostClawName OBJECT-TYPE
     SYNTAX DisplayString (SIZE(0..8))
     MAX-ACCESS read-only
     STATUS current
     DESCRIPTION
        "A non NULL OCTET STRING implies that this is the Host Claw
         Name for a CLAW Device definition."
     ::= { ibmTcpipMvsDeviceEntry 6 }

     ibmMvsDeviceWorkstationClawName  OBJECT-TYPE
     SYNTAX DisplayString (SIZE(0..8))
     MAX-ACCESS read-only
     STATUS current
     DESCRIPTION
        "A non NULL OCTET STRING implies that this is the Workstation
         Claw name for a CLAW Device definition."
     ::= { ibmTcpipMvsDeviceEntry 7 }

     ibmMvsDeviceReadBuffers OBJECT-TYPE
     SYNTAX Integer32
     MAX-ACCESS read-only
     STATUS current
     DESCRIPTION
        "The number of read buffers for either a CLAW RS/6000 IP
         or a CDLC device definition. A value of -1 implies that
         the value of this object is invalid."
     ::= { ibmTcpipMvsDeviceEntry 8 }

     ibmMvsDeviceReadSize  OBJECT-TYPE
     SYNTAX Integer32
     MAX-ACCESS read-only
     STATUS current
     DESCRIPTION
        "The read buffer size for either a CLAW RS/6000 IP
         or a CDLC device definition. A value of -1 implies that
         the value of this object is invalid."
     ::= { ibmTcpipMvsDeviceEntry 9 }

     ibmMvsDeviceWriteBuffers OBJECT-TYPE
     SYNTAX Integer32
     MAX-ACCESS read-only
     STATUS current
     DESCRIPTION
        "The number of write buffers for either a CLAW RS/6000 IP
         or a CDLC device definition. A value of -1 implies that
         the value of this object is invalid."
     ::= { ibmTcpipMvsDeviceEntry 10 }

     ibmMvsDeviceWriteSize OBJECT-TYPE
     SYNTAX Integer32
     MAX-ACCESS read-only
     STATUS current
     DESCRIPTION
        "The write buffer size for either a CLAW RS/6000 IP
         or a CDLC device definition. A value of -1 implies that
         the value of this object is invalid."
     ::= { ibmTcpipMvsDeviceEntry 11 }

     ibmMvsDeviceProcname OBJECT-TYPE
     SYNTAX DisplayString (SIZE(0..8))
     MAX-ACCESS read-only
     STATUS current
     DESCRIPTION
        "A non NULL OCTET STRING implies that this is the procname
         for an X25NPSI, SNA LU0, or SNA LU6.2 Device definition."
     ::= { ibmTcpipMvsDeviceEntry 12 }

     ibmMvsDeviceIncomingSvcEnabled OBJECT-TYPE
     SYNTAX INTEGER { false(0), true(1) }
     MAX-ACCESS read-only
     STATUS current
     DESCRIPTION
        "This object is valid only for an ATM Device. If true then
         incoming SVCs will be allowed. A value of false for an
         ATM Device implies that incoming SVC call setup will be
         rejected."
     DEFVAL { true }
     ::= { ibmTcpipMvsDeviceEntry 13 }

     ibmMvsDeviceLuName   OBJECT-TYPE
     SYNTAX DisplayString (SIZE(0..8))
     MAX-ACCESS read-only
     STATUS current
     DESCRIPTION
        "A non NULL OCTET STRING implies that this is the Logical
         Unit name for a SNA LU0 Device definition."
     ::= { ibmTcpipMvsDeviceEntry 14 }

     ibmMvsDeviceRouterStatus OBJECT-TYPE
     SYNTAX Integer32
     MAX-ACCESS read-only
     STATUS current
     DESCRIPTION
        "This object is valid only for an MPCIPA device and reflects
         the specified or default parameter from the MPCIPA DEVICE
         Profile statement.  For other devices the value will
         be set to -1.  A value of 0 represents the NONROUTER
         parameter on the MPCIPA DEVICE profile statement.  It
         indicates that the device will discard any packets
         received for an unknown IP address.  A value of 1 represents
         the PRIROUTER parameter on the MPCIPA DEVICE profile
         statement.  It indicates that the device will route
         inbound packets destined for an unknown IP address
         to this TCP/IP instance.  A value of 2 represents the
         SECROUTER parameter on the MPCIPA DEVICE profile statement.
         It is similar to a value of 1 but the device will only
         route the packet to this TCP/IP instance if there is no
         TCP/IP instance registered as primary router."
     DEFVAL  { -1 }
     ::= { ibmTcpipMvsDeviceEntry 15 }

     ibmMvsDeviceActualRouterStatus OBJECT-TYPE
     SYNTAX Integer32
     MAX-ACCESS read-only
     STATUS current
     DESCRIPTION
        "This object is valid only for an MPCIPA device and is
         determined when the device is started.  For other devices
         the value will be set to -1.  When the device is
         started, the TCP/IP instance tries to set the router status
         to the value of the ibmMvsDeviceRouterStatus MIB object.  The
         ibmMvsDeviceActualRouterStatus MIB object reflects the
         status that was sucessfully set.  A value of 0 represents
         the NONROUTER parameter from the MPCIPA DEVICE profile
         statement.  It indicates the device will discard any
         inbound packets destined for an unknown IP address.
         A value of 1 represents the PRIROUTER parameter from
         the MPCIPA DEVICE profile statement.  It indicates
         that the device will route inbound packets destined
         for an unknown IP address to this TCP/IP instance.
         A value of 2 represents the SECROUTER parameter from the
         MPCIPA DEVICE profile statement.  It is similar to a
         value of 1 but the device will only route the packet
         to this TCP/IP instance if there is no TCP/IP instance
         registered as primary router.  If the MPCIPA device has
         not yet been started, the value will be 3, which means
         the router status of the device is unknown."
     DEFVAL  { -1 }
     ::= { ibmTcpipMvsDeviceEntry 16 }

     ibmMvsDeviceConfigPackingMode  OBJECT-TYPE
     SYNTAX Integer32
     MAX-ACCESS read-only
     STATUS current
     DESCRIPTION
        "This object is valid only for a CLAW device and is
         specified on the CLAW Device definition.  For other devices
         the value will be set to -1.  A value of 1 implies
         that the PACKED parameter was not specified on the CLAW
         DEVICE Profile statement.  A value of 2 implies that
         that the PACKED parameter was specified on the CLAW
         DEVICE Profile statement."
     DEFVAL  { -1 }
     ::= { ibmTcpipMvsDeviceEntry 17 }

     ibmMvsDeviceActualPackingMode  OBJECT-TYPE
     SYNTAX Integer32
     MAX-ACCESS read-only
     STATUS current
     DESCRIPTION
        "This object is valid only for a CLAW device and is
         determined when the device is started.  For other devices
         the value will be set to -1.  A value of 1 implies
         that the router for the device does not support packing
         mode.  A value of 2 implies that the router for the device
         does support packing mode.  If the CLAW device has
         not yet been started, the value will be 3, which means
         the packing support of the router is unknown."
     DEFVAL  { -1 }
     ::= { ibmTcpipMvsDeviceEntry 18 }



     --
     --         IBM TCPIP MVS Link Table
     --

     ibmTcpipMvsLinkTable OBJECT-TYPE
     SYNTAX SEQUENCE OF IbmTcpipMvsLinkEntry
     MAX-ACCESS not-accessible
     STATUS current
     DESCRIPTION
          "Defines the link definition known to an IBM MVS
           TCP/IP system. A physical interface entry exists
           for every entry in this table."
     ::= { ibmTcpipMvsInterfaceGroup 2 }

     ibmTcpipMvsLinkEntry OBJECT-TYPE
     SYNTAX IbmTcpipMvsLinkEntry
     MAX-ACCESS not-accessible
     STATUS current
     DESCRIPTION
          "Descibes a particular link definition"
     INDEX { ifIndex }
     ::= { ibmTcpipMvsLinkTable 1 }

     IbmTcpipMvsLinkEntry ::=
          SEQUENCE
          {
          ibmMvsLinkType            DeviceLinkTypes,
          ibmMvsLinkDeviceIndex     Integer32,
          ibmMvsLinkAdapterAddr     Integer32,
          ibmMvsLinkNumber          Integer32,
          ibmMvsLinkIbmtrCanonical  Integer32,
          ibmMvsLinkIbmtrBcast      Integer32,
          ibmMvsLinkMcast           TruthValue,
          ibmMvsLinkChecksumEnabled TruthValue,
          ibmMvsLinkArpSupport      INTEGER,
          ibmMvsLinkMacAddress      OCTET STRING (SIZE(6))
          }

     ibmMvsLinkType OBJECT-TYPE
     SYNTAX DeviceLinkTypes
     MAX-ACCESS read-only
     STATUS current
     DESCRIPTION
           "Indicates the link type."
     ::= { ibmTcpipMvsLinkEntry 1 }

     ibmMvsLinkDeviceIndex OBJECT-TYPE
     SYNTAX Integer32
     MAX-ACCESS read-only
     STATUS current
     DESCRIPTION
           "ifIndex of corresponding DEVICE entry."
     ::= { ibmTcpipMvsLinkEntry 2 }

     ibmMvsLinkAdapterAddr OBJECT-TYPE
     SYNTAX Integer32
     MAX-ACCESS read-only
     STATUS current
     DESCRIPTION
           "The adapter address associated with this link
            definition. A value of -1 indicates that this
            object is invalid for the corresponding link table
            entry."
     DEFVAL { -1 }
     ::= { ibmTcpipMvsLinkEntry 3 }

     ibmMvsLinkNumber OBJECT-TYPE
     SYNTAX Integer32
     MAX-ACCESS read-only
     STATUS current
     DESCRIPTION
           "The link number associated with this link
            definition. A value of -1 indicates that this
            object is invalid for the corresponding link table
            entry."
     DEFVAL { -1 }
     ::= { ibmTcpipMvsLinkEntry 4 }

     ibmMvsLinkIbmtrCanonical OBJECT-TYPE
     SYNTAX Integer32
     MAX-ACCESS read-only
     STATUS current
     DESCRIPTION
        "For an IBMTR LCS Link, a value of 1 implies that this
         link was defined with a value of CANONICAL. A value of
         0 implies this link was defined with a value of
         NONCANONICAL.  A reported value of -1 implies
         that the object is not supported by the associated
         link."
     DEFVAL { -1 }
     ::= { ibmTcpipMvsLinkEntry 5 }

     ibmMvsLinkIbmtrBcast  OBJECT-TYPE
     SYNTAX Integer32
     MAX-ACCESS read-only
     STATUS current
     DESCRIPTION
        "For a IBMTR LCS Link, a value of 1 implies that this
         link was defined with a value of ALLRINGSBCAST. A value of
         2 implies this link was defined with a value of
         LOCALBCAST.  A value of 0 implies that the link does
         not support broadcast.  A reported value of -1 implies
         that the object is not supported by the associated
         link."
     DEFVAL  { -1 }
     ::= { ibmTcpipMvsLinkEntry 6 }

     ibmMvsLinkMcast  OBJECT-TYPE
     SYNTAX TruthValue
     MAX-ACCESS read-only
     STATUS current
     DESCRIPTION
        "A value of true(1) indicates that the link is capable
         of receiving multicast datagrams.  A value of false(2)
         indicates that either the link is not capable of
         receiving multicast datagrams or, the multicast capability
         of the link is unknown.  Point-to-point links are
         always multicast capable.  For Token Ring, Ethernet,
         and FDDI, the multicast capability of the link will not
         be known until after the link is successfully started.
         Multicast is not supported for ATM links."
     DEFVAL  { false }
     ::= { ibmTcpipMvsLinkEntry 7 }

     ibmMvsLinkChecksumEnabled  OBJECT-TYPE
     SYNTAX TruthValue
     MAX-ACCESS read-only
     STATUS current
     DESCRIPTION
        "The value of this object can vary only for MPCPTP LINK
         interfaces.  For all other LINK interfaces the value is
         set to true(1).  A value of true(1) indicates that an
         inbound checksum calculation will be performed for all
         packets received on this interface.  A value of false(2)
         indicates that an inbound checksum calculation will not
         be performed for any packets received on this interface."
     DEFVAL  { true }
     ::= { ibmTcpipMvsLinkEntry 8 }

     ibmMvsLinkArpSupport  OBJECT-TYPE
     SYNTAX INTEGER {
                            none(1),
                            tcpipArp(2),
                            offloadNoInfo(3),
                            offloadArpInfo(4),
                            unknown(5)
                    }
     MAX-ACCESS read-only
     STATUS current
     DESCRIPTION
        "This object reflects the status of the interface's ARP
         support.  A value of 'none' indicates that the interface does
         not support ARP. If the interface supports ARP but the
         interface is inactive, then the object will be set to a
         value of 'unknown'. If the interface is active and supports
         ARP, the object will be set to one of remaining values.
         A value of 'tcpipArp' indicates that the TCP/IP instance
         maintains the ARP cache entries and ARP counters for the
         interface.  A value of 'offloadNoInfo' indicates that the
         interface maintains its ARP cache entries and ARP counters
         and the TCP/IP instance can not retrieve this information.
         A value of 'offloadArpInfo' indicates that the interface
         maintains its ARP cache entries and ARP counters but
         supports retrieval of this information by the TCP/IP instance.
         If the value of the MIB object is 'offloadArpInfo', then
         the ARP cache entries and ARP counters retrieved represent
         aggregated information and may reflect shared usage of the
         interface by more than one TCP/IP instance."
     DEFVAL  { none }
     ::= { ibmTcpipMvsLinkEntry 9 }

     ibmMvsLinkMacAddress  OBJECT-TYPE
     SYNTAX  OCTET STRING (SIZE(6))
     MAX-ACCESS read-only
     STATUS current
     DESCRIPTION
           "A 6 byte OCTET STRING which contains the configured
            MAC address for IPAQTR link interfaces.  If the MAC
            address was not specified, or if the interface is not
            an IPAQTR link, then the value will be zeros."
     ::= { ibmTcpipMvsLinkEntry 10 }

 ---------------------------------------------------------------------
 -- ibmTcpipMvsLinkMcastTable
 ---------------------------------------------------------------------

     ibmTcpipMvsLinkMcastTable OBJECT-TYPE
     SYNTAX SEQUENCE OF IbmTcpipMvsLinkMcastEntry
     MAX-ACCESS not-accessible
     STATUS current
     DESCRIPTION
          "The table listing those multicast groups for which an
           application wishes to receive multicast data.  An
           application requests this by issuing a setsockopt() with
           IP_ADD_MEMBERSHIP option.  An entry exists for every
           multicast group registered per interface."
     ::= { ibmTcpipMvsInterfaceGroup 3 }

     ibmTcpipMvsLinkMcastEntry OBJECT-TYPE
     SYNTAX IbmTcpipMvsLinkMcastEntry
     MAX-ACCESS not-accessible
     STATUS current
     DESCRIPTION
          "An entry representing a multicast group on an interface."
     INDEX { ifIndex, ibmMvsLinkMcastGroupAddr }
     ::= { ibmTcpipMvsLinkMcastTable 1 }

     IbmTcpipMvsLinkMcastEntry ::= SEQUENCE {
          ibmMvsLinkMcastGroupAddr         IpAddress,
          ibmMvsLinkMcastRefCount          Unsigned32
     }


     ibmMvsLinkMcastGroupAddr OBJECT-TYPE
     SYNTAX IpAddress
     MAX-ACCESS not-accessible
     STATUS current
     DESCRIPTION
          "Specifies the ipAddress of the multicast group"
     ::= { ibmTcpipMvsLinkMcastEntry 1 }

     ibmMvsLinkMcastRefCount OBJECT-TYPE
     SYNTAX Unsigned32
     MAX-ACCESS read-only
     STATUS current
     DESCRIPTION
          "A count of the number of sockets that are
           members of this multicast group."
     ::= { ibmTcpipMvsLinkMcastEntry 2 }

 ---------------------------------------------------------------------
 -- ibmTcpipMvsPortGroup2
 ---------------------------------------------------------------------

     --
     --       IBM TCPIP Port Table
     --

     ibmTcpipMvsPortTable OBJECT-TYPE
     SYNTAX SEQUENCE OF IbmTcpipMvsPortEntry
     MAX-ACCESS not-accessible
     STATUS current
     DESCRIPTION
          "Reserved ports within a TCP/IP address space."
     ::= { ibmTcpipMvsPortGroup 1 }

     ibmTcpipMvsPortEntry OBJECT-TYPE
     SYNTAX IbmTcpipMvsPortEntry
     MAX-ACCESS not-accessible
     STATUS current
     DESCRIPTION
          "Defines a single ibmTcpipMvsPortTable entry."
     INDEX { ibmMvsPortNumberLow, ibmMvsPortNumberHigh,
             ibmMvsPortProtocol, ibmMvsPortProcName }
     ::= { ibmTcpipMvsPortTable 1 }

     IbmTcpipMvsPortEntry ::=
          SEQUENCE
          {
          ibmMvsPortNumberLow    Integer32,
          ibmMvsPortNumberHigh   Integer32,
          ibmMvsPortProtocol       INTEGER,
          ibmMvsPortProcName     DisplayString,
          ibmMvsPortAutoLoggable  INTEGER,
          ibmMvsPortDelayAcks    INTEGER,
          ibmMvsPortOptMaxSegmentSize INTEGER,
          ibmMvsPortSharePort         INTEGER,
          ibmMvsPortBindIpAddr        IpAddress,
          ibmMvsPortSAFResource       DisplayString,
          ibmMvsPortReuse             TruthValue
          }

     ibmMvsPortNumberLow OBJECT-TYPE
     SYNTAX Integer32
     MAX-ACCESS read-only
     STATUS current
     DESCRIPTION
           "Low port number of entry."
      ::= { ibmTcpipMvsPortEntry 1 }

     ibmMvsPortNumberHigh OBJECT-TYPE
     SYNTAX Integer32
     MAX-ACCESS read-only
     STATUS current
     DESCRIPTION
           "High port number of entry."
      ::= { ibmTcpipMvsPortEntry 2 }

     ibmMvsPortProtocol OBJECT-TYPE
     SYNTAX INTEGER { tcp(0), udp(1) }
     MAX-ACCESS read-only
     STATUS current
     DESCRIPTION
           "The protocol of the associating port entry."
      ::= { ibmTcpipMvsPortEntry 3 }

     ibmMvsPortProcName OBJECT-TYPE
     SYNTAX DisplayString (SIZE(1..8))
     MAX-ACCESS read-only
     STATUS current
     DESCRIPTION
           "Text Name of the associating mvs procedure."
      ::= { ibmTcpipMvsPortEntry 4 }

     ibmMvsPortAutoLoggable OBJECT-TYPE
     SYNTAX INTEGER { false(0), true(1) }
     MAX-ACCESS read-only
     STATUS current
     DESCRIPTION
           "Should proc be autologged."
     DEFVAL { true }
     ::= { ibmTcpipMvsPortEntry 5 }

     ibmMvsPortDelayAcks OBJECT-TYPE
     SYNTAX INTEGER { false(0), true(1) }
     MAX-ACCESS read-only
     STATUS current
     DESCRIPTION
           "A value of true implies that DELAYACKS was selected
            for this port entry."
     DEFVAL { false }
     ::= { ibmTcpipMvsPortEntry 6 }

     ibmMvsPortOptMaxSegmentSize OBJECT-TYPE
     SYNTAX INTEGER { false(0), true(1) }
     MAX-ACCESS read-only
     STATUS current
     DESCRIPTION
           "A value of true implies that the Optimal Maximum
            Segment Size option was selected for this port entry."
     DEFVAL { false }
     ::= { ibmTcpipMvsPortEntry 7 }

     ibmMvsPortSharePort OBJECT-TYPE
     SYNTAX INTEGER { false(0), true(1) }
     MAX-ACCESS read-only
     STATUS current
     DESCRIPTION
           "A value of true implies that SHAREPORT was selected
            for this port entry."
     DEFVAL { false }
     ::= { ibmTcpipMvsPortEntry 8 }

     ibmMvsPortBindIpAddr OBJECT-TYPE
     SYNTAX IpAddress
     MAX-ACCESS read-only
     STATUS current
     DESCRIPTION
           "The IP address specified on the BIND parameter of the
            PORT Profile statement.  If an application issues
            a bind() with an IP address of zeros (INADDR_ANY),
            the value of this MIB object will be used to replace
            the zero IP address.  A value of 0.0.0.0 indicates
            that the BIND parameter was not specified for this PORT."
     ::= { ibmTcpipMvsPortEntry 9 }

     ibmMvsPortSAFResource OBJECT-TYPE
     SYNTAX DisplayString (SIZE(0..8))
     MAX-ACCESS read-only
     STATUS current
     DESCRIPTION
           "The SAF resource name specified on the SAF parameter of
            the PORT Profile statement.  The value of this MIB
            object is appended to a security product profile name
            of the format: EZB.PORTACCESS.sysname.tcpname., where
            'sysname' is the MVS image name, and 'tcpname' is the
            TCP/IP instance name.  During bind() processing
            the security product will be invoked to verify that
            the user ID associated with the application has authority
            to the resulting security product profile name.  A value
            of NULL indicates that the SAF parameter was not
            specified for this PORT."
     ::= { ibmTcpipMvsPortEntry 10 }

     ibmMvsPortReuse     OBJECT-TYPE
     SYNTAX   TruthValue
     MAX-ACCESS read-only
     STATUS current
     DESCRIPTION
           "This object only applies to TCP port entries.  A value
            of true(1) means that the port is reusable, as if the
            SO_REUSEADDR socket option had been set in a socket
            using the port.  A value of true will be set for the
            port if the BIND paramter was also specified on this
            port reservation, or if the BIND parameter was specified
            on another port reservation for the same port number.
            For UDP port entries, this value will always be false(2)."
     DEFVAL { false }
     ::= { ibmTcpipMvsPortEntry 11 }

 ---------------------------------------------------------------------
 -- ibmTcpipMvsRouteGroup
 ---------------------------------------------------------------------

      --
      --   IBM TCPIP Gateway Table
      --

     ibmTcpipMvsGatewayTable OBJECT-TYPE
     SYNTAX SEQUENCE OF IbmTcpipMvsGatewayEntry
     MAX-ACCESS not-accessible
     STATUS current
     DESCRIPTION
          "Extends ipForwardTable to support gateway semantic."
     ::= { ibmTcpipMvsRouteGroup 1 }

     ibmTcpipMvsGatewayEntry OBJECT-TYPE
     SYNTAX IbmTcpipMvsGatewayEntry
     MAX-ACCESS not-accessible
     STATUS current
     DESCRIPTION
          "Descibes a particular gateway entry"
     AUGMENTS { ipForwardEntry }
     ::= { ibmTcpipMvsGatewayTable 1 }

     IbmTcpipMvsGatewayEntry ::=
          SEQUENCE
          {
          ibmMvsGatewayMaximumRetransmitTime       Integer32,
          ibmMvsGatewayMinimumRetransmitTime       Integer32,
          ibmMvsGatewayRoundTripGain               Integer32,
          ibmMvsGatewayVarianceGain                Integer32,
          ibmMvsGatewayVarianceMultiplier          Integer32,
          ibmMvsGatewayDelayAcks                   INTEGER
          }

     ibmMvsGatewayMaximumRetransmitTime OBJECT-TYPE
     SYNTAX Integer32
     MAX-ACCESS read-only
     STATUS current
     DESCRIPTION
           "Used in the TCP/IP re-transmission time-out calculation
            to determine how long to wait for an acknowledgement
            before resending a packet. Expressed as a integer in
            units of 100th of a second."
     DEFVAL { 6000 }
     ::= { ibmTcpipMvsGatewayEntry 1 }

     ibmMvsGatewayMinimumRetransmitTime OBJECT-TYPE
     SYNTAX Integer32
     MAX-ACCESS read-only
     STATUS current
     DESCRIPTION
           "Used in the TCP/IP re-transmission time-out calculation
            to determine how long to wait for an acknowledgement
            before resending a packet. Expressed as a integer in
            units of 100th of a second."
     DEFVAL { 75 }
     ::= { ibmTcpipMvsGatewayEntry 2 }

     ibmMvsGatewayRoundTripGain OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 1200 }
     ::= { ibmTcpipMvsGatewayEntry 3 }

     ibmMvsGatewayVarianceGain OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 2500 }
     ::= { ibmTcpipMvsGatewayEntry 4 }

     ibmMvsGatewayVarianceMultiplier OBJECT-TYPE
     SYNTAX Integer32
     MAX-ACCESS read-only
     STATUS current
     DESCRIPTION
           "Used in the TCP/IP re-transmission time-out calculation
            to determine how long to wait for an acknowledgement
            before resending a packet. Expressed as a integer in
            units of .0001."
     DEFVAL { 20000 }
     ::= { ibmTcpipMvsGatewayEntry 5 }

     ibmMvsGatewayDelayAcks OBJECT-TYPE
     SYNTAX INTEGER { false(0), true(1) }
     MAX-ACCESS read-only
     STATUS current
     DESCRIPTION
           "Delays transmission of acknowledgements when a packet
            is received with the PUSH bit on in the TCP header. The
            DELAYACKS parameter on the GATEWAY statement only
            applies to the TCP protocol and only affects
            acknowledgements returned to the foreign host. To
            delay acknowledgements on a TCP/IP port connection
            use the DELAYACKS parameter on the PORT statement."
     DEFVAL { false }
     ::= { ibmTcpipMvsGatewayEntry 6 }

 ---------------------------------------------------------------------
 -- ibmTcpipMvsAtmGroup4
 ---------------------------------------------------------------------

 -- osasfChannelTable

     osasfChannelTable OBJECT-TYPE
     SYNTAX SEQUENCE OF OsasfChannelEntry
     MAX-ACCESS not-accessible
     STATUS current
     DESCRIPTION
        "Indexed by ifIndex. One entry in this table will exist per
         OSA-2 ATM Device Interface.  If the values for objects
         ibmMvsAtmOsasfChannelCurLparName/Num are not the same as
         values for objects ibmMvsAtmOsasfChannelManParnName/Num
         then the OSA/SF running in the current LPAR is not the
         managing OSA/SF for this Device.  SNMP Set commands for
         ibmMvsAtmOsasfPortIpAddress (to set an IP address
         at the ATM port) will be rejected by OSA/SF if the OSA/SF
         in the current LPAR is not the managing OSA/SF for
         the Device."
     ::= { ibmTcpipMvsAtmGroup 1 }

     osasfChannelEntry OBJECT-TYPE
     SYNTAX OsasfChannelEntry
     MAX-ACCESS not-accessible
     STATUS current
     DESCRIPTION
        "Definition of a single entry in the osasfChannelTable.
         Indexed by the ifIndex of the corresponding DEVICE interface."
     INDEX { ifIndex }
     ::= { osasfChannelTable 1 }

     OsasfChannelEntry ::=
     SEQUENCE
       {
       ibmMvsAtmOsasfChannelNumber              Integer32,
       ibmMvsAtmOsasfChannelType                INTEGER,
       ibmMvsAtmOsasfChannelSubType             Integer32,
       ibmMvsAtmOsasfChannelMode                INTEGER,
       ibmMvsAtmOsasfChannelHwModel             INTEGER,
       ibmMvsAtmOsasfChannelState               INTEGER,
       ibmMvsAtmOsasfChannelShared              INTEGER,
       ibmMvsAtmOsasfChannelNumPorts            Integer32,
       ibmMvsAtmOsasfChannelDeterNodeDesc       OCTET STRING,
       ibmMvsAtmOsasfChannelControlUnitNumber   Integer32,
       ibmMvsAtmOsasfChannelCodeLevel           Integer32,
       ibmMvsAtmOsasfChannelEcLevel             DisplayString,
       ibmMvsAtmOsasfChannelCurLparName         DisplayString,
       ibmMvsAtmOsasfChannelCurLparNum          Integer32,
       ibmMvsAtmOsasfChannelManParnName         DisplayString,
       ibmMvsAtmOsasfChannelManParnNum          Integer32,
       ibmMvsAtmOsasfChannelDate                DisplayString,
       ibmMvsAtmOsasfChannelTime                DisplayString,
       ibmMvsAtmOsasfChannelFlashLevel          DisplayString,
       ibmMvsAtmOsasfChannelVtamId              Integer32
       }

     ibmMvsAtmOsasfChannelNumber OBJECT-TYPE
     SYNTAX Integer32
     MAX-ACCESS read-only
     STATUS current
     DESCRIPTION
           "The channel number for this interface"
     ::= { osasfChannelEntry 1 }

     ibmMvsAtmOsasfChannelType OBJECT-TYPE
     SYNTAX INTEGER {
                      other(1),
                      osaExp155(16),
                      osaExp155QDIO(17),
                      osa(18)
                    }
     MAX-ACCESS read-only
     STATUS current
     DESCRIPTION
           "The value will be osa(18) for ATM OSA-2 adapters.
            The values of osaExp155(16) and osaExp155QDIO(17)
            apply only to OSA-Express ATM155 adapters.  Since
            the channel management data for OSA-Express ATM155
            adapters has moved to the osaexpChannelTable, these
            values will never be set for this MIB object. The value
            should never be other(1) for an OSA ATM adapter."
     ::= { osasfChannelEntry 2 }

     ibmMvsAtmOsasfChannelSubType OBJECT-TYPE
     SYNTAX Integer32
     MAX-ACCESS read-only
     STATUS current
     DESCRIPTION
           "Indicates how the channel is configured.  The value
            is one of the following:
                 -1 - Invalid
                  0 - Unknown
                  1 - Ethernet
                  2 - Token Ring
                  3 - Two Token Ring ports
                  4 - Token Ring and Ethernet ports
                  5 - Ethernet and Token Ring ports
                  6 - Two Ethernet ports
                  7 - FDDI
                  8 - No ports defined
                  9 - ATM Native or IP Forwarding
                 10 - One Logical Ethernet port
                 11 - One Logical Token Ring port
                 12 - ATM LAN Emulation

            A value of 12 applies only to OSA-Express ATM155
            adapters.  Since the channel management data for
            OSA-Express ATM155 adapters has moved to the
            osaexpChannelTable, this value will never be set
            for this MIB object.  A value of -1 should not
            occur for this object."
     ::= { osasfChannelEntry 3 }

     ibmMvsAtmOsasfChannelMode OBJECT-TYPE
     SYNTAX INTEGER {
                       other(1),
                       passthruMode(2),
                       snaMode(3),
                       atmLeTcpipMode(4),
                       atmLeSnaMode(5),
                       atmLeSnaTcpipMode(6),
                       atmNativeMode(7),
                       atmIpFwdMode(8)
                    }
     MAX-ACCESS read-only
     STATUS current
     DESCRIPTION
           "Config mode of the ATM adapter."
     ::= { osasfChannelEntry 4 }

     ibmMvsAtmOsasfChannelHwModel OBJECT-TYPE
     SYNTAX INTEGER {
                           undefined(0),
                           osa1(1),
                           osa2(2),
                           osa2Atm(3),
                           osaExp155(4)
                         }
     MAX-ACCESS read-only
     STATUS current
     DESCRIPTION
           "Hardware model of the channel. The field NDModelNum
            contained in ibmMvsAtmOsasfChannelDeterNodeDesc
            is a char(3) field that contains a readable format of
            this object's value.  The value of osaExp155(4)
            applies only to OSA-Express ATM155 adapters.  Since
            the channel management data for OSA-Express ATM155
            adapters has moved to the osaexpChannelTable, this
            value will never be set for this MIB object."
     ::= { osasfChannelEntry 5 }

     ibmMvsAtmOsasfChannelState   OBJECT-TYPE
     SYNTAX INTEGER {
                           online(1),
                           notinst(3),
                           offline(5)
                         }
     MAX-ACCESS read-only
     STATUS current
     DESCRIPTION
           "Hardware channel state: online, offline, or
            not installed."
     ::= { osasfChannelEntry 6 }

     ibmMvsAtmOsasfChannelShared  OBJECT-TYPE
     SYNTAX INTEGER { no(0), yes(1) }
     MAX-ACCESS read-only
     STATUS current
     DESCRIPTION
           "An OSA Channel can be shared across multiple
            LPARs. This object indicates if this channel
            is currently being shared."
     ::= { osasfChannelEntry 7 }

     ibmMvsAtmOsasfChannelNumPorts  OBJECT-TYPE
     SYNTAX Integer32
     MAX-ACCESS read-only
     STATUS current
     DESCRIPTION
           "Number of physical ports on OSA channel."
     ::= { osasfChannelEntry 8 }

     ibmMvsAtmOsasfChannelDeterNodeDesc OBJECT-TYPE
     SYNTAX  OCTET STRING (SIZE(32))
     MAX-ACCESS read-only
     STATUS current
     DESCRIPTION
           "Describes the generic node descriptor layout.
            This object represents the ND obtained from the
            CHSC instruction:
                                       /* ND Flags                */
            int   bValidity      :3;   /* 1:is ND valid           */
            int   bNodeType      :1;   /* 1:0=dev,1=chnlsubstm nod*/
            int   bInternal      :1;   /* internal(1)/external(0) */
            int   bCHPinvalid    :1;   /* IF =1,NDCHPID is invalid*/
            int   bNDRsvd1       :2;   /* spare bits for alignment*/
            char  NDRsvd1;             /* reserved by architecture*/
            char  NDClass;             /* Class for subsystem node*/
            char  NDCHPID;             /* CHP ID for specified int*/
            char  NDTypeNum 6 ;        /* type number of the SDC  */
            char  NDModelNum 3 ;       /* ND model number in the
                                          form of 3 EBCDIC OCTETS */
            char  NDMfgr 3 ;           /* ND manufacturer in the
                                          form of 3 EBCDIC OCTETS */
            char  NDMfgrPlant 2 ;      /* ND plant of manufacture
                                          (2 EBCDIC OCTETS)       */
            char  NDSeqNum 12 ;        /* ND sequence number
                                          (12 EBCDIC OCTETS)      */
            char  NDTag 2 ;            /* ND tag                  */"
     ::= { osasfChannelEntry 9 }

     ibmMvsAtmOsasfChannelControlUnitNumber OBJECT-TYPE
     SYNTAX  Integer32
     MAX-ACCESS read-only
     STATUS current
     DESCRIPTION
           "The control unit number associated with the OSA Channel."
     ::= { osasfChannelEntry 10 }

     ibmMvsAtmOsasfChannelCodeLevel OBJECT-TYPE
     SYNTAX  Integer32
     MAX-ACCESS read-only
     STATUS current
     DESCRIPTION
           "ibmMvsAtmOsasfChannelCodeLevel is the firmware
            (or micro code level) of the OSA adapter. For example,
            ATM OSA-2 adapter level 05.60 would be represented as
            0x0560 by this object."
     ::= { osasfChannelEntry 11 }

     ibmMvsAtmOsasfChannelEcLevel OBJECT-TYPE
     SYNTAX  DisplayString (SIZE(0..8))
     MAX-ACCESS read-only
     STATUS obsolete
     DESCRIPTION
           "The Box EC Level Identifier of the OSA adapter which
            identifies the current Engineering Change (EC) Level of
            this OSA adapter (Channel)."
     ::= { osasfChannelEntry 12 }

     ibmMvsAtmOsasfChannelCurLparName OBJECT-TYPE
     SYNTAX  DisplayString (SIZE(0..8))
     MAX-ACCESS read-only
     STATUS current
     DESCRIPTION
           "LPAR name of the OSA/SF from which this data was
            retrieved from"
     ::= { osasfChannelEntry 13 }

     ibmMvsAtmOsasfChannelCurLparNum OBJECT-TYPE
     SYNTAX  Integer32
     MAX-ACCESS read-only
     STATUS current
     DESCRIPTION
           "LPAR number of the OSA/SF from which this data was
            retrieved"
     ::= { osasfChannelEntry 14 }

     ibmMvsAtmOsasfChannelManParnName OBJECT-TYPE
     SYNTAX  DisplayString (SIZE(0..8))
     MAX-ACCESS read-only
     STATUS current
     DESCRIPTION
           "LPAR name of the OSA Support Facility managing this
            channel. Only one OSA/SF can manage a OSA Channel
            within an MVS Sysplex even though multiple OSA/SFs
            can retrieve information from the same OSA Channel."
     ::= { osasfChannelEntry 15 }

     ibmMvsAtmOsasfChannelManParnNum  OBJECT-TYPE
     SYNTAX  Integer32
     MAX-ACCESS read-only
     STATUS current
     DESCRIPTION
           "LPAR number of the OSA Support Facility managing this
            channel (set to 0xFFFF if not being managed by a
            OSA/SF)."
     ::= { osasfChannelEntry 16 }

     ibmMvsAtmOsasfChannelDate OBJECT-TYPE
     SYNTAX  DisplayString (SIZE(1..12))
     MAX-ACCESS read-only
     STATUS obsolete
     DESCRIPTION
           "Date on this channel (set to 'NOTVALID' if there
            the disk serving function is not active)."
     ::= { osasfChannelEntry 17 }

     ibmMvsAtmOsasfChannelTime        OBJECT-TYPE
     SYNTAX  DisplayString (SIZE(0..8))
     MAX-ACCESS read-only
     STATUS obsolete
     DESCRIPTION
           "Time on this channel (set to 'NOTVALID' if there
            the disk serving function is not active)."
     ::= { osasfChannelEntry 18 }

     ibmMvsAtmOsasfChannelFlashLevel OBJECT-TYPE
     SYNTAX  DisplayString (SIZE(1..32))
     MAX-ACCESS read-only
     STATUS current
     DESCRIPTION
            "Flashlevel is the LAN driver level running on an OSA
             adapter.  For OSA-1 and OSA-2, there is only 1 LAN driver.
             For OSA-2 ATM, you can have up to 2 LAN driver.
             The first driver if configured is for SNA and the second
             driver is for ATM LAN. FlashLevel consists of two 16
             OCTET fields, one for each LAN driver.
             FOR example, S:05:20:A0  for SNA & A:05.60.00  for ATM.
             This object is not supported for OSA-Express ATM
             adapters, so the value will be null."
     ::= { osasfChannelEntry 19 }

     ibmMvsAtmOsasfChannelVtamId OBJECT-TYPE
     SYNTAX  Integer32
     MAX-ACCESS read-only
     STATUS obsolete
     DESCRIPTION
           "VTAM ID if in SNA mode"
     ::= { osasfChannelEntry 20 }

 -- osasfPortTable

     osasfPortTable OBJECT-TYPE
     SYNTAX SEQUENCE OF OsasfPortEntry
     MAX-ACCESS not-accessible
     STATUS current
     DESCRIPTION
        "This table is intended to represent the ports supported
         (or associated) with the osasfChannelTable entries and,
         for OSA-Express ATM155 adapters, with the
         osaexpChannelTable entries. Each OSA channel has one
         or more OSA Ports.  For an ATM OSA-2 device configured
         for ATM IP Forwarding mode, the following
         fields do not apply:
             - ibmMvsAtmOsasfPortMacAddrBurntIn
             - ibmMvsAtmOsasfPortMacAddrActive
             - ibmMvsAtmOsasfPortMaxPcmConnections
             - ibmMvsAtmOsasfPortPcmName  "
     ::= { ibmTcpipMvsAtmGroup 2 }

     osasfPortEntry OBJECT-TYPE
     SYNTAX OsasfPortEntry
     MAX-ACCESS not-accessible
     STATUS current
     DESCRIPTION
        "Describes a particular OSA port entry, index by
         corresponding AAL5 entry's ifIndex."
     INDEX { ifIndex }
     ::= { osasfPortTable 1 }

     OsasfPortEntry ::=
     SEQUENCE
       {
       ibmMvsAtmOsasfPortNumber                  Integer32,
       ibmMvsAtmOsasfPortType                     INTEGER,
       ibmMvsAtmOsasfPortHardwareState           INTEGER,
       ibmMvsAtmOsasfPortMediaType               INTEGER,
       ibmMvsAtmOsasfPortUniType                  INTEGER,
       ibmMvsAtmOsasfPortUniVersion               INTEGER,
       ibmMvsAtmOsasfPortNetPrefix               Integer32,
       ibmMvsAtmOsasfPortNetPrefixPrefix        OCTET STRING (SIZE(13)),
       ibmMvsAtmOsasfPortNetPrefixStatus          INTEGER,
       ibmMvsAtmOsasfPortCodeLoadStatus          INTEGER,
       ibmMvsAtmOsasfPortMacAddrBurntIn          OCTET STRING (SIZE(6)),
       ibmMvsAtmOsasfPortMacAddrActive           OCTET STRING (SIZE(6)),
       ibmMvsAtmOsasfPortMaxPcmConnections       Integer32,
       ibmMvsAtmOsasfPortPcmName                 DisplayString,
       ibmMvsAtmOsasfPortAAL5InPackets           Counter32,
       ibmMvsAtmOsasfPortAAL5OutPackets          Counter32,
       ibmMvsAtmOsasfPortIpAddress               IpAddress
       }

     ibmMvsAtmOsasfPortNumber        OBJECT-TYPE
     SYNTAX  Integer32
     MAX-ACCESS read-only
     STATUS current
     DESCRIPTION
           "Port number, starts at 0."
     ::= { osasfPortEntry 1 }

     ibmMvsAtmOsasfPortType          OBJECT-TYPE
     SYNTAX  INTEGER { ethernet(1),
                       tokenRing(2),
                       atm(9),
                       osaExp155(41)
                     }
     MAX-ACCESS read-only
     STATUS current
     DESCRIPTION
           "For an ATM OSA-2 adapter configured for ATM native
            traffic, the value of this object is atm(9).  For
            an ATM OSA-2 adapter configured for ATM LAN Emulation,
            the value is either ethernet(1) or tokenRing(2)
            and represents the configuration of the first logical
            port on the adapter.  For an OSA-Express ATM155 adapter
            the value is osaExp155(41).
            Note that when a port is configured to be running
            ATM LAN Emulation then up to two logical
            ATM LE port entities may exist with any combination
            of ethernet or tokenring port types."
     ::= { osasfPortEntry 2 }

     ibmMvsAtmOsasfPortHardwareState  OBJECT-TYPE
     SYNTAX  INTEGER {
                            enabled(0),
                            hostDisabled(1),
                            externallyDisabled(2),
                            internallyDisabled(3),
                            secmHostDisabled(4),
                            secmExternallyDisabled(5),
                            secmInternallyDisabled(6),
                            linkMonitor(7)
                          }
     MAX-ACCESS read-only
     STATUS current
     DESCRIPTION
           "The hardware state value ranges from 0 to 6 as follows:
            0 - enable
            1 - disabled from host
            2 - disabled from external source
            3 - disabled from internal error
            4 - service element control mode/disabled from host
            5 - service element control mode/disabled from external
                source
            6 - service element control mode/disabled from internal
                error
            7 - link not operational because ATM155 adapter was unable
                to register with the switch (only valid for ATM155)

            where Host - OSA/SF or other host programming product
                  external source - human intervention on the service
                                    element"
     ::= { osasfPortEntry 3 }

     ibmMvsAtmOsasfPortMediaType     OBJECT-TYPE
     SYNTAX  INTEGER { coaxCable(1), singleModeFiber(2),
                        multimodeFiber(3), shieldedTwistedPair(4),
                        unshieldedTwistedPair(5) }
     MAX-ACCESS read-only
     STATUS current
     DESCRIPTION
           "ILMI atmfPortMediaType equivalent. OSA supports types
            2 and 3"
     ::= { osasfPortEntry 4 }

     ibmMvsAtmOsasfPortUniType        OBJECT-TYPE
     SYNTAX  INTEGER { public(1), private(2) }
     MAX-ACCESS read-only
     STATUS current
     DESCRIPTION
           "ILMI atmfAtmLayerUniType. OSA supports only 2"
     ::= { osasfPortEntry 5 }

     ibmMvsAtmOsasfPortUniVersion     OBJECT-TYPE
     SYNTAX  INTEGER { version20(1), version30(2), version31(3) }
     MAX-ACCESS read-only
     STATUS current
     DESCRIPTION
           "ILMI atmfAtmLayerUniVersion. OSA supports only 3.
            This is the highest UNI version supported."
     ::= { osasfPortEntry 6 }

     ibmMvsAtmOsasfPortNetPrefix      OBJECT-TYPE
     SYNTAX  Integer32
     MAX-ACCESS read-only
     STATUS current
     DESCRIPTION
           "A unique value which identifies the UNI port for which
            the network prefix for ATM addresses is in effect. The
            value of 0 has the special meaning of identifying the
            local UNI. OSA currently supports only 0."
     ::= { osasfPortEntry 7 }

     ibmMvsAtmOsasfPortNetPrefixPrefix OBJECT-TYPE
     SYNTAX  OCTET STRING (SIZE(13))
     MAX-ACCESS read-only
     STATUS current
     DESCRIPTION
           "The network prefix for ATM addresses which is in effect
            on the user-side of the ATM UNIT port. Network prefix is
            defined as the ATM address, not including the ESA and
            SEL portions. The meaningful portion of the OCTET STRING
            is size 8 if it is E.164, 13 if private. In the case
             of E.164 the remaining 5 octets are padded with zeros."
     ::= { osasfPortEntry 8 }

     ibmMvsAtmOsasfPortNetPrefixStatus OBJECT-TYPE
     SYNTAX  INTEGER { valid(1), invalid(2) }
     MAX-ACCESS read-only
     STATUS current
     DESCRIPTION
           "Equivalent to the atmfNetPrefixStatus as defined in
            the Network Prefix Table in the ILMI Address Registration
            MIB. An indication of the validity of the network prefix
            for ATM addresses on the user-side of the UNI port."
     ::= { osasfPortEntry 9 }

     ibmMvsAtmOsasfPortCodeLoadStatus  OBJECT-TYPE
     SYNTAX  INTEGER {
                 operational(1),
                 notOperational(2),
                 configRejected(3),
                 outOfSync(4),
                 notApplicable(5)
             }
     MAX-ACCESS read-only
     STATUS current
     DESCRIPTION
           "This object specifies whether the ATM code has been loaded
            on to the adapter. The configRejected state indicates
            that the ATM configuration file download via OSA/SF has
            been found to be incorrect. The outOfSync condition
            indicates that the OSA firmware and the ATM code both
            running on the OSA have been found to be at incompatible
            levels. Any state other than operational infers that
            the data associated with a port may be incorrect.
            Note: OSA/SF should only report states operational
            and notOperational.  This object is only valid for
            ATM OSA-2 adapters.  For other ATM adapters the value
            is notApplicable."
     ::= { osasfPortEntry 10 }

     ibmMvsAtmOsasfPortMacAddrBurntIn  OBJECT-TYPE
     SYNTAX  OCTET STRING (SIZE(6))
     MAX-ACCESS read-only
     STATUS current
     DESCRIPTION
           "A 6 byte OCTET STRING which contains the adapter's
            burned in MAC address.  Does not apply to ATM OSA-2
            device configured for ATM IP Forwarding mode."
     ::= { osasfPortEntry 11 }

     ibmMvsAtmOsasfPortMacAddrActive   OBJECT-TYPE
     SYNTAX  OCTET STRING (SIZE(6))
     MAX-ACCESS read-only
     STATUS current
     DESCRIPTION
           "A 6 byte OCTET STRING which contains the current
            MAC address in use on the adapter.  Does not apply to
            ATM OSA-2 device configured for ATM IP Forwarding mode."
     ::= { osasfPortEntry 12 }

     ibmMvsAtmOsasfPortMaxPcmConnections   OBJECT-TYPE
     SYNTAX  Integer32
     MAX-ACCESS read-only
     STATUS current
     DESCRIPTION
           "Specifies the maximum number of connects on an OSA port
            which can be used for ATM exploitation purposes. It can
            range from 0 to the number specified by
            atmInterfaceMaxVccs (RFC 1695). A 0 indicates either that
            the connections on this port are being used by an ATM
            configured for LAN Emulation or ATM IP Forwarding.
            If the value specified here is the same
            as what is specified by atmInterfaceMaxVccs then all
            connections are allocated to ATM exploitation."
     ::= { osasfPortEntry 13 }

     ibmMvsAtmOsasfPortPcmName       OBJECT-TYPE
     SYNTAX  DisplayString (SIZE(1..16))
     MAX-ACCESS read-only
     STATUS current
     DESCRIPTION
           "Specifies the Port Name which must also be entered at the
            connection manager on the host and the application. Port
            Name is specifed to OSA/SF as a config file parameter
            (PCM_NAME). This value is also specified via ILMI as
            the value of the atmfPortMyIfName object.  Does not
            apply to an ATM OSA-2 adapter configured for
            ATM IP Forwarding mode, or an OSA-Express ATM155
            adapter configured for QDIO LAN Emulation mode."
     ::= { osasfPortEntry 14 }

     ibmMvsAtmOsasfPortAAL5InPackets OBJECT-TYPE
     SYNTAX  Counter32
     MAX-ACCESS read-only
     STATUS current
     DESCRIPTION
           "inbound packets at the corresponding AAL5 interface layer."
     ::= { osasfPortEntry 15 }

     ibmMvsAtmOsasfPortAAL5OutPackets OBJECT-TYPE
     SYNTAX  Counter32
     MAX-ACCESS read-only
     STATUS current
     DESCRIPTION
           "outbound packets at the corresponding AAL5 interface layer."
     ::= { osasfPortEntry 16 }

     ibmMvsAtmOsasfPortIpAddress      OBJECT-TYPE
     SYNTAX  IpAddress
     MAX-ACCESS  read-write
     STATUS  current
     DESCRIPTION
           "The managing IpAddress reported by the ATM port as
            its atmfMyIpNmAddress as specified by the ATM Forum
            User-NetworkInterface (UNI) specification.  An SNMP Set
            for this object is only supported for OSA-2 ATM adapters.
            If the values for objects
            ibmMvsAtmOsasfChannelCurLparName/Num are not the same as
            values for objects ibmMvsAtmOsasfChannelManParnName/Num
            then the OSA/SF running in the current LPAR is not the
            managing OSA/SF for this adapter.
            SNMP Set commands for ibmMvsAtmOsasfPortIpAddress
            (to set an IP address at the ATM port) will be rejected
            by OSA/SF if the OSA/SF in the current LPAR is not the
            managing OSA/SF for the adapter."
     ::= { osasfPortEntry 17 }

 -- osasfPvcTable

     osasfPvcTable OBJECT-TYPE
     SYNTAX SEQUENCE OF OsasfPvcEntry
     MAX-ACCESS not-accessible
     STATUS current
     DESCRIPTION
        "This table is intended to represent the locally
         configured PVCs associated with a given OSA Port.
         There is a limit of 128 PVCs per Port per Channel."
     ::= { ibmTcpipMvsAtmGroup 3 }

     osasfPvcEntry OBJECT-TYPE
     SYNTAX OsasfPvcEntry
     MAX-ACCESS not-accessible
     STATUS current
     DESCRIPTION
        "This object is intended to represent a single PVC
         entry for the osasfPvcTable."
     INDEX { ifIndex, ibmMvsAtmOsasfPvcName }
     ::= { osasfPvcTable 1 }

     OsasfPvcEntry ::=
     SEQUENCE
       {
       ibmMvsAtmOsasfPvcName               DisplayString,
       ibmMvsAtmOsasfPvcBestEffort         Integer32,
       ibmMvsAtmOsasfPvcFwdPeakCellRate    Integer32,
       ibmMvsAtmOsasfPvcBwdPeakCellRate    Integer32,
       ibmMvsAtmOsasfPvcFwdsustainCellRate Integer32,
       ibmMvsAtmOsasfPvcBwdsustainCellRate Integer32,
       ibmMvsAtmOsasfPvcFwdCellBurstSize   Unsigned32,
       ibmMvsAtmOsasfPvcBwdCellBurstSize   Unsigned32,
       ibmMvsAtmOsasfPvcVpi                Integer32,
       ibmMvsAtmOsasfPvcVci                Integer32,
       ibmMvsAtmOsasfPvcFwdMaxAal5PduSize  INTEGER,
       ibmMvsAtmOsasfPvcBwdMaxAal5PduSize  INTEGER
       }

     ibmMvsAtmOsasfPvcName            OBJECT-TYPE
     SYNTAX  DisplayString (SIZE(1..8))
     MAX-ACCESS read-only
     STATUS current
     DESCRIPTION
           "PVC Name"
     ::= { osasfPvcEntry 1 }

     ibmMvsAtmOsasfPvcBestEffort         OBJECT-TYPE
     SYNTAX  Integer32 ( 0..1 )
     MAX-ACCESS read-only
     STATUS current
     DESCRIPTION
           "Best Effort rate. 0 indicated that best effort
            delivery is not desired. 1 indicates that best
            effort delivery is desired."
     ::= { osasfPvcEntry 2 }

     ibmMvsAtmOsasfPvcFwdPeakCellRate    OBJECT-TYPE
     SYNTAX  Integer32
     MAX-ACCESS read-only
     STATUS current
     DESCRIPTION
           "Forward peak cell rate specified as cells per second.
            Needed in order to set up either a best effort or
            a reserved bandwidth PVC. It applies to the outbound
            direction (OSA to network) and specifies an upper bound
            on the outbound traffic that can be transmitted on this
            PVC. This value can not exceed the the link speed of
            the ATM link which, currently, is 353207."
     ::= { osasfPvcEntry 3 }

     ibmMvsAtmOsasfPvcBwdPeakCellRate    OBJECT-TYPE
     SYNTAX  Integer32
     MAX-ACCESS read-only
     STATUS current
     DESCRIPTION
           "Backward peak cell rate specified as cells per second.
            Needed in order to set up either a best effort or
            a reserved bandwidth PVC. It applies to the inbound
            direction (network to OSA) and specifies an upper bound
            on the inbound traffic that can be received on this
            PVC. This value can not exceed the the link speed of
            the ATM link which, currently, is 353207."
     ::= { osasfPvcEntry 4 }

     ibmMvsAtmOsasfPvcFwdsustainCellRate OBJECT-TYPE
     SYNTAX  Integer32
     MAX-ACCESS read-only
     STATUS current
     DESCRIPTION
           "Forward sustain cell rate specified as cells per second.
            If the best effort indicator is on, the value of this
            object is ignored. Otherwise (for a reserved bandwidth
            PVC) this value is utilized by OSA. A value of 0xFF
            indicates that this value is not being used.
            Forward sustain cell rate specifies the desired cell rate
            for outbound traffic that can be sustained for life of
            a connection on this PVC. This value can not exceed the
            link speed of the ATM port which, currently, is 353207."
     ::= { osasfPvcEntry 5 }

     ibmMvsAtmOsasfPvcBwdsustainCellRate OBJECT-TYPE
     SYNTAX  Integer32
     MAX-ACCESS read-only
     STATUS current
     DESCRIPTION
           "Backward sustain cell rate specified as cells per second.
            If the best effort indicator is on, the value of this
            object is ignored. Otherwise (for a reserved bandwidth
            PVC) this value is utilized by OSA. A value of 0xFF
            indicates that this value is not being used.
            Backward sustain cell rate specifies the desired cell rate
            for inbound traffic that can be sustained for life of
            a connection on this PVC. This value can not exceed the
            link speed of the ATM port which, currently, is 353207."
     ::= { osasfPvcEntry 6 }

     ibmMvsAtmOsasfPvcFwdCellBurstSize   OBJECT-TYPE
     SYNTAX  Unsigned32
     MAX-ACCESS read-only
     STATUS current
     DESCRIPTION
           "Forward cell burst size specified as number of cells.
            If the best effort indicator is on, the value of this
            object is ignored. Otherwise (for a reserved bandwidth
            PVC) this value is utilized by OSA. A value of 0xFF
            indicates that this value is not being used.
            Forward cell burst size specifies the maximum number of
            cells that can be transmitted in the outbound direction at
            the peak cell rate while maintaining conformance to the
            PVC traffic contract."
     ::= { osasfPvcEntry 7 }

     ibmMvsAtmOsasfPvcBwdCellBurstSize   OBJECT-TYPE
     SYNTAX  Unsigned32
     MAX-ACCESS read-only
     STATUS current
     DESCRIPTION
           "Backward cell burst size specified as number of cells.
            If the best effort indicator is on, the value of this
            object is ignored. Otherwise (for a reserved bandwidth
            PVC) this value is utilized by OSA. A value of 0xFF
            indicates that this value is not being used.
            Backward cell burst size specifies the maximum number of
            cells that can be received in the inbound direction at
            the peak cell rate while maintaining conformance to the
            PVC traffic contract."
     ::= { osasfPvcEntry 8 }

     ibmMvsAtmOsasfPvcVpi      OBJECT-TYPE
     SYNTAX  Integer32
     MAX-ACCESS read-only
     STATUS current
     DESCRIPTION
           "vpi for this PVC"
     ::= { osasfPvcEntry 9 }

     ibmMvsAtmOsasfPvcVci      OBJECT-TYPE
     SYNTAX  Integer32
     MAX-ACCESS read-only
     STATUS current
     DESCRIPTION
           "vci for this PVC. This value must be greater than or
            equal to 32 since the first 32 vci code points have
            been reserved by the ATM Forum."
     ::= { osasfPvcEntry 10 }

     ibmMvsAtmOsasfPvcFwdMaxAal5PduSize  OBJECT-TYPE
     SYNTAX  INTEGER (64..9188)
     MAX-ACCESS read-only
     STATUS current
     DESCRIPTION
           "This field is used to setup the PVC. Units are in
            OCTETs and represents the largest PDU size for the
            AAL5 CPCS layer that can be processed in the forward
            direction for this PVC by the AAL5 entity. For best
            effort PVCs only, OSA/SF should attempt to default the
            value to the largest size (9188)."
     ::= { osasfPvcEntry 11 }

     ibmMvsAtmOsasfPvcBwdMaxAal5PduSize  OBJECT-TYPE
     SYNTAX  INTEGER (64..9188)
     MAX-ACCESS read-only
     STATUS current
     DESCRIPTION
           "This field is used to setup the PVC. Units are in
            OCTETs and represents the largest PDU size for the
            AAL5 CPCS layer that can be processed in the backward
            direction for this PVC by the AAL5 entity. For best
            effort PVCs only, OSA/SF should attempt to default the
            value to the largest size (9188)."
     ::= { osasfPvcEntry 12 }

 -- ibmMvsAtmSnaLeTable

     ibmMvsAtmSnaLeTable OBJECT-TYPE
     SYNTAX SEQUENCE OF IbmMvsAtmSnaLeEntry
     MAX-ACCESS not-accessible
     STATUS current
     DESCRIPTION
        "This table is intended to represent the data that is
         available from an OSA Port that is running SNA LAN
         Emulation mode. An entry in this table is indexed by a
         LAN Emulation ifIndex. An ifEntry who's ifType is either
         aflane802.3 (59) or aflane802.5 (60) will have a
         corresponding entry in this table."
     ::= { ibmTcpipMvsAtmGroup 4 }

     ibmMvsAtmSnaLeEntry OBJECT-TYPE
     SYNTAX IbmMvsAtmSnaLeEntry
     MAX-ACCESS not-accessible
     STATUS current
     DESCRIPTION
        "Describes a particular OSA SNA LAN Emulation entry, index by
         corresponding LAN Emulation ifIndex."
     INDEX { ifIndex }
     ::= { ibmMvsAtmSnaLeTable 1 }

     IbmMvsAtmSnaLeEntry ::=
     SEQUENCE
       {
         ibmMvsAtmSnaLeLlcTi                Integer32,
         ibmMvsAtmSnaLeLlcT1                Integer32,
         ibmMvsAtmSnaLeLlcT2                Integer32,
         ibmMvsAtmSnaleMaxStations          Integer32,
         ibmMvsAtmSnaLeMaxSaps              Integer32,
         ibmMvsAtmSnaleMaxIn                Integer32,
         ibmMvsAtmSnaLeMaxOut               Integer32,
         ibmMvsAtmSnaLeCrsGroupAddress      OCTET STRING,
         ibmMvsAtmSnaLeUserData             OCTET STRING,
         ibmMvsAtmSnaLeClientEnableState      INTEGER,
         ibmMvsAtmSnaLeBestEffortPeakRate   Unsigned32,
         ibmMvsAtmSnaLeMaxLECConnections    Integer32,
         ibmMvsAtmSnaLeTrEnableLoadBalancing INTEGER,
         ibmMvsAtmSnaLeTrLoadBalancing        INTEGER,
         ibmMvsAtmSnaLeTrSessionDelay         INTEGER
       }

     ibmMvsAtmSnaLeLlcTi  OBJECT-TYPE
     SYNTAX  Integer32
     MAX-ACCESS read-only
     STATUS current
     DESCRIPTION
           "The inactivity timer. An enabled inactivity timer (Ti)
            periodically tests the viability of the network media.
            The timer setting applies to all the clients on the
            target LAN, not to individual clients.  The timer
            interval indicates how quickly a failure of the network
            media can be detected when the connection is quiescent.
            If the Ti timer times out, a supervisory poll frame is
            sent over the connection.  The T1 response, or reply,
            timer clocks the supervisory poll.  If the T1 timer
            times out, the supervisory poll is retransmitted.
            OSA can retransmit a supervisory poll up to 8 times.
            If no response is received after the last retransmission,
            the link is declared inoperative, and the S/390 program
            issues a message.
            The value is represented in ticks.  The value will
            either be zero, or in the range of 2 to 750. Each tick
            equals .12 of a second."
     ::= { ibmMvsAtmSnaLeEntry 1 }

     ibmMvsAtmSnaLeLlcT1 OBJECT-TYPE
     SYNTAX  Integer32 (1..255)
     MAX-ACCESS read-only
     STATUS current
     DESCRIPTION
           "The response timer.  The T1 timer clocks link events that
            require responses from clients on the network.  These
            link events include SABME/UA exchanges, I-frame link
            protocol data unit (LPDU) transmissions, and
            supervisory polls.
            The value is represented in ticks.  Each tick
            equals .2 of a second."
     ::= { ibmMvsAtmSnaLeEntry 2 }

     ibmMvsAtmSnaLeLlcT2 OBJECT-TYPE
     SYNTAX  Integer32 (1..255)
     MAX-ACCESS read-only
     STATUS current
     DESCRIPTION
           "The acknowledgement timer.  An OSA starts the T2 timer
            when it receives an I-format LPDU and stops when it
            sends an acknowledgement.  An acknowledgement is sent
            either when an outgoing I frame is sent, which acts
            as the acknowledgement, or when N3 number of I-format
            LPDUs has been received.  If the T2 timer times out,
            the OSA must send an acknowledgement.
            The value is represented in ticks.  Each tick
            equals .08 of a second."
     ::= { ibmMvsAtmSnaLeEntry 3 }

     ibmMvsAtmSnaleMaxStations  OBJECT-TYPE
     SYNTAX  Integer32 (0..255)
     MAX-ACCESS read-only
     STATUS current
     DESCRIPTION
           "The maximum number of connections (PUs) supported by
            an OSA for this port.  This object is not supported
            for OSA-Express ATM so the value will be set to zero."
     ::= { ibmMvsAtmSnaLeEntry 4 }

     ibmMvsAtmSnaLeMaxSaps  OBJECT-TYPE
     SYNTAX  Integer32 (0..127)
     MAX-ACCESS read-only
     STATUS current
     DESCRIPTION
           "The maximum number of service access points (SAP)
            supported by an OSA for this for this port.  This
            object is not supported for OSA-Express ATM so
            the value will be set to zero."
     ::= { ibmMvsAtmSnaLeEntry 5 }

     ibmMvsAtmSnaleMaxIn OBJECT-TYPE
     SYNTAX  Integer32 (1..127)
     MAX-ACCESS read-only
     STATUS current
     DESCRIPTION
           "Maximum I frames before ACK (N3).  The maximum number
            of I-format link protocol data units (LPDUs) that
            can be received by an OSA before it sends an
            acknowledgement (N3 count).  It is also called
            the receive window count."
     ::= { ibmMvsAtmSnaLeEntry 6 }

     ibmMvsAtmSnaLeMaxOut OBJECT-TYPE
     SYNTAX  Integer32 (1..127)
     MAX-ACCESS read-only
     STATUS current
     DESCRIPTION
           "SNA maximum transmit window (TW).  The maximum number
            of outstanding I-format link protocol data units (LPDUs).
            It is also called the maximum transmit window count
            or the maximum window out count.  The TW count
            allows the sender to transmit frames before that
            sender is forced to halt and wait for an acknowledgement.
            Therefore, the receiver should be able to absorb that
            number of frames, either in its service access point (SAP)
            buffers or within the buffers in workstation memory."
     ::= { ibmMvsAtmSnaLeEntry 7 }

     ibmMvsAtmSnaLeCrsGroupAddress OBJECT-TYPE
     SYNTAX  OCTET STRING(SIZE(256))
     MAX-ACCESS read-only
     STATUS current
     DESCRIPTION
            "This field contains the active Group Addresses.
             An individual Group Address is 6 bytes long.
             Therefore, this field is actually 32 times
             (OCTET STRING(SIZE(6)) + 2 bytes of padding) long."
     ::= { ibmMvsAtmSnaLeEntry 8 }

     ibmMvsAtmSnaLeUserData  OBJECT-TYPE
     SYNTAX  OCTET STRING (SIZE(32))
     MAX-ACCESS read-only
     STATUS current
     DESCRIPTION
            "This field contains a character string of user
             data that can be used to further describe this port."
     ::= { ibmMvsAtmSnaLeEntry 9 }

     ibmMvsAtmSnaLeClientEnableState  OBJECT-TYPE
     SYNTAX  INTEGER {
                          notDefined(1),
                          lecActivating(2),
                          enabled(3),
                          internalFailureDisabled(4),
                          physicalPortDisabled(5),
                          osasfDisabled(6),
                          externalDisabled(7),
                          unknown(8)
                       }
     MAX-ACCESS read-only
     STATUS current
     DESCRIPTION
           "This object describes the state of the specified LAN
            Emulation Port. notDefined implies that the port is
            not defined in the configuration file. lecActivating
            indicates the port is in the process of being enabled.
            There are for possible reasons that the port could be
            diabled as implied by the enumeration list."
     ::= { ibmMvsAtmSnaLeEntry 10 }

     ibmMvsAtmSnaLeBestEffortPeakRate OBJECT-TYPE
     SYNTAX  Unsigned32
     MAX-ACCESS read-only
     STATUS current
     DESCRIPTION
           "This object is the signaling parameter that should
            be used by the LEC when setting up all best effort VCCs.
            This parameter applies to the forward and backward
            direction on a per best effort VCC basis. Thus a 155 Mb
            adapter may be configured to send best effort traffic at
            25.6 Mb (per VCC), but with a total adapter bandwidth of
            up to 155 Mb. Since this parameter has an integer value
            the unis are 10xMbits/sec."
     ::= { ibmMvsAtmSnaLeEntry 11 }

     ibmMvsAtmSnaLeMaxLECConnections  OBJECT-TYPE
     SYNTAX  Integer32 (1..65536)
     MAX-ACCESS read-only
     STATUS current
     DESCRIPTION
           "This object specifies the maximum number of connections
            on an OSA port which can be used for LAN Emulation
            purposes. It can range from 0 to the number specified
            by atmInterfaceMaxVccs. 0 would indicate that the
            connections on this port are only being used by ATM
            Exploitation. If the value of this parameter was equal
            to atmInterfaceMaxVccs then all connections are allocated
            to LAN Emulation.  Note that this number is the same for
            all LECs. It is NOT defined on a per LEC basis."
     ::= { ibmMvsAtmSnaLeEntry 12 }

    ibmMvsAtmSnaLeTrEnableLoadBalancing OBJECT-TYPE
    SYNTAX  INTEGER (0..1)
    MAX-ACCESS read-only
    STATUS current
    DESCRIPTION
          "Load balancing control used to enable the load balancing
           option."
    ::= { ibmMvsAtmSnaLeEntry 13 }

    ibmMvsAtmSnaLeTrLoadBalancing  OBJECT-TYPE
    SYNTAX  INTEGER (0..25)
    MAX-ACCESS read-only
    STATUS current
    DESCRIPTION
          "Load balancing factor.  Specifies whether this port will
           be delayed and, if so, by how much time, in establishing
           a session.  This factor is related to the number of
           connections (PUs) through the OSA port, not the type
           nor the amount of work that is being done on those
           connections."
    ::= { ibmMvsAtmSnaLeEntry 14 }

    ibmMvsAtmSnaLeTrSessionDelay OBJECT-TYPE
    SYNTAX  INTEGER (0..375)
    MAX-ACCESS read-only
    STATUS current
    DESCRIPTION
          "Session delay is specified to delay the response of this
           port to a new session request and by the specified length
           of time.  By establishing a longer session delay timeout
           for this port copmpared with another port in the same
           set, this port serves as a backup for another port in
           an overflow condition."
    ::= { ibmMvsAtmSnaLeEntry 15 }


 -- ibmMvsAtmLecConfigTable

     ibmMvsAtmLecConfigTable OBJECT-TYPE
     SYNTAX SEQUENCE OF IbmMvsAtmLecConfigEntry
     MAX-ACCESS not-accessible
     STATUS current
     DESCRIPTION
        "This table is intended to represent the data that is
         available from an OSA Port that is running LAN
         Emulation mode. An entry in this table is indexed by a
         LAN Emulation ifIndex. An ifEntry who's ifType is either
         aflane802.3 (59) or aflane802.5 (60) will have a
         corresponding entry in this table. This table is modeled
         after the LEC Config Table from the LAN Emulation MIB
         defined by the ATM Forum."
     ::= { ibmTcpipMvsAtmGroup 5 }

     ibmMvsAtmLecConfigEntry OBJECT-TYPE
     SYNTAX IbmMvsAtmLecConfigEntry
     MAX-ACCESS not-accessible
     STATUS current
     DESCRIPTION
        "Describes a particular ATM Lec Config Table entry, index by
         either a aflan802.3 or a aflane802.5 ifEntry's ifIndex."
     INDEX { ifIndex }
     ::= { ibmMvsAtmLecConfigTable 1 }

     IbmMvsAtmLecConfigEntry ::=
     SEQUENCE
       {
         ibmMvsAtmLecConfigMode              INTEGER,
         ibmMvsAtmLecConfigLanType           INTEGER,
         ibmMvsAtmLecConfigMaxDataFrameSize  INTEGER,
         ibmMvsAtmLecConfigLanName           OCTET STRING (SIZE(32)),
         ibmMvsAtmLecConfigLesAtmAddress     OCTET STRING (SIZE(20)),
         ibmMvsAtmLecControlTimeout          Integer32,
         ibmMvsAtmLecMaxUnknownFrameCount    Integer32,
         ibmMvsAtmLecMaxUnknownFrameTime     Integer32,
         ibmMvsAtmLecVccTimeoutPeriod        Integer32,
         ibmMvsAtmLecMaxRetryCount           Integer32,
         ibmMvsAtmLecAgingTime               Integer32,
         ibmMvsAtmLecForwardDelayTime        Integer32,
         ibmMvsAtmLecExpectedArpResponseTime Integer32,
         ibmMvsAtmLecFlushTimeout            Integer32,
         ibmMvsAtmLecPathSwitchingDelay      Integer32,
         ibmMvsAtmLecLocalSegmentID          Integer32,
         ibmMvsAtmLecMulticastSendType       INTEGER,
         ibmMvsAtmLecMulticastSendAvgRate    Unsigned32,
         ibmMvsAtmLecMulticastSendPeakRate   Unsigned32,
         ibmMvsAtmLecConnectionCompleteTimer Integer32,
         ibmMvsAtmLecPortName                DisplayString
       }

     ibmMvsAtmLecConfigMode   OBJECT-TYPE
     SYNTAX  INTEGER { automatic(1), manual(2) }
     MAX-ACCESS read-only
     STATUS current
     DESCRIPTION
           "Indicates whether this LAN Emulation Client should
            auto-configure the next time it is (re)started. In
            automatic (1) mode, a client uses a LAN Emulation
            Configuration Server to learn the ATM address of its
            LAN Emulation Server, and to obtain other parameters.
            lecConfig (LanType, MaxDataFrameSize, LanName) are
            used in the configure request. lecConfigLesAtmAddress
            is ignored. In manual (2) mode, management tells the
            client the ATM address of its LAN Emulation Server
            and the value of the other parmeters. lecConfig
            (LanType, MaxDataFrameSize, LanName) are used in the
            Join request. lecConfigLesAtmAddress tells the client
            which LES to call."
     ::= { ibmMvsAtmLecConfigEntry 1 }

     ibmMvsAtmLecConfigLanType   OBJECT-TYPE
     SYNTAX  INTEGER { unspecified (1), ethernet(2), tokenRing(3) }
     MAX-ACCESS read-only
     STATUS current
     DESCRIPTION
           "The data frame format which this client will use
            the next time it returns to the Initial State.
            Auto-configuring clients use this parameter in their
            configure requests. Manually configured clients use
            it in their joint requests."
     ::= { ibmMvsAtmLecConfigEntry 2 }

     ibmMvsAtmLecConfigMaxDataFrameSize  OBJECT-TYPE
     SYNTAX  INTEGER {
                         unspecified (1),
                         f1516 (2),
                         f4544 (3),
                         f9234 (4),
                         f18190 (5)
                       }
     MAX-ACCESS read-only
     STATUS current
     DESCRIPTION
           "The maximum data frame size (in bytes) which this
            client will use the next time it returns to the Initial
            State. Auto-configuring clients use this parameter in
            their configure requests. Manually configured clients use
            it in their joint requests."
     ::= { ibmMvsAtmLecConfigEntry 3 }

     ibmMvsAtmLecConfigLanName   OBJECT-TYPE
     SYNTAX   OCTET STRING (SIZE(32))
     MAX-ACCESS read-only
     STATUS current
     DESCRIPTION
           "The ELAN Name this client will use the
            next time it returns to the Initial State.
            Auto-configuring clients use this parameter in
            their configure requests. Manually configured clients use
            it in their joint requests."
     ::= { ibmMvsAtmLecConfigEntry 4 }

     ibmMvsAtmLecConfigLesAtmAddress     OBJECT-TYPE
     SYNTAX   OCTET STRING (SIZE(20))
     MAX-ACCESS read-only
     STATUS current
     DESCRIPTION
          "The LAN Emulation Server which this client will use the
           next time it is started in manual configuration mode.
           When lecConfigMode is 'automatic', there is no need to set
           this address, Address) and no advantage to doing so. The
           client will use the LECS to find a LES, putting the
           auto-configured address in lecActualLesAtmAddress
           while leaving lecConfigLesAtmAddress alone. Corresponds to
           Initial State Parameter C9. In LAN Emulation MIB, the
           OCTET STRING has length 0 or 20. For OSA, the length shall
           be 20, with  the value 0 defined to mean that
           lecConfigMode is 'automatic'."
     ::= { ibmMvsAtmLecConfigEntry 5 }

     ibmMvsAtmLecControlTimeout   OBJECT-TYPE
     SYNTAX   Integer32 (10..300)
     MAX-ACCESS read-only
     STATUS current
     DESCRIPTION
          "Control Time-out. Time out period used for timing out most
           request/response control frame interactions, as specified
           elsewhere in the LAN Emulation specification.
           This time value is expressed in seconds. Corresponds to
           Initial State Parameter C7."
     ::= { ibmMvsAtmLecConfigEntry 6 }

     ibmMvsAtmLecMaxUnknownFrameCount OBJECT-TYPE
     SYNTAX   Integer32 (1..10)
     MAX-ACCESS read-only
     STATUS current
     DESCRIPTION
          "Maximum Unknown Frame Count. See the description of
           lecMaxUnknownFrameTime below. Corresponds to Initial
           State Parameter C10."
     ::= { ibmMvsAtmLecConfigEntry 7 }

     ibmMvsAtmLecMaxUnknownFrameTime  OBJECT-TYPE
     SYNTAX   Integer32 (1..60)
     MAX-ACCESS read-only
     STATUS current
     DESCRIPTION
          "Maximum Unknown Frame Time. Within the period of time
           defined by the Maximum Unknown Frame Time, a LE Client
           will send no more than Maximum Unknown Frame Count
           frames to the BUS for a given unicast LAN Destination,
           and it must also initiate the address resolution
           protocol to resolve that LAN Destination. This time
           value is expressed in seconds. Corresponds Initial State
           Parameter C11."
     ::= { ibmMvsAtmLecConfigEntry 8 }

     ibmMvsAtmLecVccTimeoutPeriod  OBJECT-TYPE
     SYNTAX   Integer32
     MAX-ACCESS read-only
     STATUS current
     DESCRIPTION
          "VCC Time-out Period. A LE Client SHOULD release any
           Data Direct VCC that it has not used to transmit
           or receive any data frames for the length of the VCC
           Time-out Period. This parameter is only meaningful for
           SVC Data Direct VCCs.
           This time value is expressed in seconds. The default
           value is 20 minutes. A value of 0 seconds means
           that the timeout period is infinite.
           Negative values will be rejected by the agent.
           Corresponds to Initial State Parameter C12."
     ::= { ibmMvsAtmLecConfigEntry 9 }

     ibmMvsAtmLecMaxRetryCount  OBJECT-TYPE
     SYNTAX   Integer32 (0..2)
     MAX-ACCESS read-only
     STATUS current
     DESCRIPTION
          "Maximum Retry Count. A LE CLient MUST not retry a
           LE_ARP_REQUEST for a given frame's LAN destination
           more than Maximum Retry Count times, after the first
           LE_ARP_REQUEST for that same frame's LAN destination.
           Corresponds to Initial State Parameter C13."
     ::= { ibmMvsAtmLecConfigEntry 10 }

     ibmMvsAtmLecAgingTime  OBJECT-TYPE
     SYNTAX   Integer32 (10..300)
     MAX-ACCESS read-only
     STATUS current
     DESCRIPTION
          "Aging Time. The maximum time that a LE Client will
           maintain an entry in its LE_ARP cache in the absence
           of a verification of that relationship.
           This time value is expressed in seconds. Corresponds to
           Initial State Parameter C17."
     ::= { ibmMvsAtmLecConfigEntry 11 }

     ibmMvsAtmLecForwardDelayTime  OBJECT-TYPE
     SYNTAX   Integer32 (4..30)
     MAX-ACCESS read-only
     STATUS current
     DESCRIPTION
          "Forward Delay Time. The maximum time that a LE Client
           will maintain an entry for a non-local MAC address in
           its LE_ARP cache in the absence of a verification of
           that relationship, as long as the Topology Change flag
           C19 is true. lecForwardDelayTime SHOULD BE less than
           lecAgingTime. When it is not, lecAgingTime governs LE_ARP
           aging.
           This time value is expressed in seconds. Corresponds to
           Initial State Parameter C18."
     ::= { ibmMvsAtmLecConfigEntry 12 }

     ibmMvsAtmLecExpectedArpResponseTime  OBJECT-TYPE
     SYNTAX   Integer32 (1..30)
     MAX-ACCESS read-only
     STATUS current
     DESCRIPTION
          "Expected LE_ARP Reponse Time. The maximum time that
           the LEC expects an LE_ARP_REQUEST/LE_ARP_RESPONSE
           cycle to take. Used for retries and verifies. This
           time value is expressed in Time) seconds. Corresponds
           to Initial State Parameter C20."
     ::= { ibmMvsAtmLecConfigEntry 13 }

     ibmMvsAtmLecFlushTimeout OBJECT-TYPE
     SYNTAX   Integer32 (1..4)
     MAX-ACCESS read-only
     STATUS current
     DESCRIPTION
          "Flush Time-out. Time limit to wait to receive a
           LE_FLUSH_RESPONSE after the LE_FLUSH_REQUEST has been
           sent before taking recovery action. This time value
           is expressed in seconds. Corresponds to Initial State
           Parameter C21."
     ::= { ibmMvsAtmLecConfigEntry 14 }

     ibmMvsAtmLecPathSwitchingDelay  OBJECT-TYPE
     SYNTAX   Integer32 (1..8)
     MAX-ACCESS read-only
     STATUS current
     DESCRIPTION
          "Path Switching Delay. The time since sending a
           frame to the BUS after which the LE Client may
           assume that the frame has been either discarded
           or delivered to the recipient. May be used to
           bypass the Flush protocol. This time value is
           expressed in seconds. Corresponds to Initial State
           Parameter C22."
     ::= { ibmMvsAtmLecConfigEntry 15 }

     ibmMvsAtmLecLocalSegmentID  OBJECT-TYPE
     SYNTAX   Integer32 (0..4095)
     MAX-ACCESS read-only
     STATUS current
     DESCRIPTION
          "Local Segment ID. The segment ID of the emulated LAN.
           This is only required for IEEE 802.5 clients that
           are Source Routing bridges. Corresponds to Initial
           State Parameter C23."
     ::= { ibmMvsAtmLecConfigEntry 16 }

     ibmMvsAtmLecMulticastSendType  OBJECT-TYPE
     SYNTAX   INTEGER {
                          bestEffort(1),
                          variableBitRate(2),
                          constantBitRate(3)
                        }
     MAX-ACCESS read-only
     STATUS current
     DESCRIPTION
          "Multicast Send VCC Type. Signalling parameter that
           SHOULD be used by the LE Client when establishing
           the Multicast Send VCC. This is the method to be used
           by the LE Client when specifying traffic parameters
           when it sets up the Multicast Send VCC for this
           emulated LAN. Corresponds to Initial State
           Parameter C24."
     ::= { ibmMvsAtmLecConfigEntry 17 }

     ibmMvsAtmLecMulticastSendAvgRate  OBJECT-TYPE
     SYNTAX   Unsigned32
     MAX-ACCESS read-only
     STATUS current
     DESCRIPTION
          "Multicast Send VCC AvgRate. Signalling parameter
           that SHOULD be used by the LE Client when estabishing
           the Multicast Send VCC. Forward and Backward Sustained
           Cell Rate to be requested by LE Client when setting
           up Multicast Send VCC, if using Variable bit rate
           codings. Corresponds to Initial State Parameter C25."
     ::= { ibmMvsAtmLecConfigEntry 18 }

     ibmMvsAtmLecMulticastSendPeakRate  OBJECT-TYPE
     SYNTAX   Unsigned32
     MAX-ACCESS read-only
     STATUS current
     DESCRIPTION
          "Multicast Send VCC PeakRate. Signalling parameter that
           SHOULD be used by the LE Client when establishing the
           Multicast Send VCC. Forward and Backward Peak Cell
           Rate to be requested by LE Client when setting up the
           Multicast Send VCC when using either Variable or
           Constant bit rate codings. Corresponds to Initial
           State Parameter C26."
     ::= { ibmMvsAtmLecConfigEntry 19 }

     ibmMvsAtmLecConnectionCompleteTimer OBJECT-TYPE
     SYNTAX   Integer32 (1..10)
     MAX-ACCESS read-only
     STATUS current
     DESCRIPTION
          "Connection Complete Timer. Optional. In Connection
           Establish ment this is the time period in which
           data or a READY_IND message is expected from a Calling
           Party. This time value is expressed in seconds.
           Corresponds to Initial State Parameter C28."
     ::= { ibmMvsAtmLecConfigEntry 20 }

     ibmMvsAtmLecPortName       OBJECT-TYPE
     SYNTAX  DisplayString (SIZE(1..8))
     MAX-ACCESS read-only
     STATUS current
     DESCRIPTION
           "Specifies the Port Name for the logical port.  This
            object only applies to OSA-Express ATM155 adapters
            configured for QDIO LAN Emulation mode.  For ATM OSA-2
            adapters, or OSA-Express ATM155 adapters configured
            for non-QDIO mode, the value will be null."
     ::= { ibmMvsAtmLecConfigEntry 21 }


 -- ibmMvsAtmLecStatusTable

     ibmMvsAtmLecStatusTable OBJECT-TYPE
     SYNTAX SEQUENCE OF IbmMvsAtmLecStatusEntry
     MAX-ACCESS not-accessible
     STATUS current
     DESCRIPTION
        "This table is intended to represent the data that is
         available from an OSA Port that is running LAN
         Emulation mode. An entry in this table is indexed by a
         LAN Emulation ifIndex. An ifEntry who's ifType is either
         aflane802.3 (59) or aflane802.5 (60) will have a
         corresponding entry in this table. This table is modeled
         after the LEC Status Table from the LAN Emulation MIB
         defined by the ATM Forum."
     ::= { ibmTcpipMvsAtmGroup 6 }

     ibmMvsAtmLecStatusEntry OBJECT-TYPE
     SYNTAX IbmMvsAtmLecStatusEntry
     MAX-ACCESS not-accessible
     STATUS current
     DESCRIPTION
        "Describes a particular ATM Lec Status Table entry, indexed
         by either a aflan802.3 or a aflane802.5 ifEntry's ifIndex."
     INDEX { ifIndex }
     ::= { ibmMvsAtmLecStatusTable 1 }

     IbmMvsAtmLecStatusEntry ::=
     SEQUENCE
       {
         ibmMvsAtmLecPrimaryAtmAddress        OCTET STRING(SIZE(20)),
         ibmMvsAtmLecID                       Integer32,
         ibmMvsAtmLecInterfaceState           INTEGER,
         ibmMvsAtmLecLastFailureRespCode      INTEGER,
         ibmMvsAtmLecLastFailureState         INTEGER,
         ibmMvsAtmLecProtocol                 Integer32,
         ibmMvsAtmLecVersion                  Integer32,
         ibmMvsAtmLecTopologyChange           INTEGER,
         ibmMvsAtmLecConfigServerAtmAddress   OCTET STRING(SIZE(20)),
         ibmMvsAtmLecConfigSource             INTEGER,
         ibmMvsAtmLecActualLanType            INTEGER,
         ibmMvsAtmLecActualMaxDataFrameSize   INTEGER,
         ibmMvsAtmLecActualLanName            OCTET STRING(SIZE(32)),
         ibmMvsAtmLecAtmAddress               OCTET STRING(SIZE(20)),
         ibmMvsAtmLecProxyClient              INTEGER
       }

     ibmMvsAtmLecPrimaryAtmAddress  OBJECT-TYPE
     SYNTAX  OCTET STRING (SIZE(20))
     MAX-ACCESS read-only
     STATUS current
     DESCRIPTION
          "LE Client's ATM Addresses. The primary ATM address
           of this LAN Emulation Client. This address is used
           to establish the Control Direct and Multicast Send
           VCCs, and may also be used to set up Data Direct
           VCCs. A client may have additional ATM addresses
           for use with Data Direct VCCs. These addresses are
           readable via the lecAtmAddressTable. Corresponds to
           Initial State Parameter C1."
     ::= { ibmMvsAtmLecStatusEntry 1 }

     ibmMvsAtmLecID  OBJECT-TYPE
     SYNTAX  Integer32 (0..65279)
     MAX-ACCESS read-only
     STATUS current
     DESCRIPTION
          "LE Client Identifier. Each LE Client requires a
           LE Client Identifier (LECID) assigned by the LE
           Server during the Join phase. The LECID is placed
           in control requests by the LE Client and MAY be used
           for echo suppression on multicast data frames sent
           by that LE Client. This value MUST NOT change without
           terminating the LE Client and returning to the Initial
           state. A valid LECID MUST be in the range X'0001'
           through X'FEFF'. The value of this object is only
           meaningful for a LEC that is connected to a LES. For
           a LEC which does not belong to an emulated LAN, the
           value of this object is defined to be 0. Corresponds to
           Initial State Parameter C14."
     ::= { ibmMvsAtmLecStatusEntry 2 }

     ibmMvsAtmLecInterfaceState  OBJECT-TYPE
     SYNTAX  INTEGER {
                         initialState (1),
                         lecsConnect (2),
                         configure (3),
                         join (4),
                         initialRegistration (5),
                         busConnect (6),
                         operational (7)
                       }
     MAX-ACCESS read-only
     STATUS current
     DESCRIPTION
          "The current state of the LAN Emulation Client. Note
           that 'ifOperStatus' is defined to be 'up' when, and
           only when, lecInterfaceState' is 'operational'."
     ::= { ibmMvsAtmLecStatusEntry 3 }

     ibmMvsAtmLecLastFailureRespCode  OBJECT-TYPE
     SYNTAX  INTEGER {
                         none (1),
                         timeout (2),
                         undefinedError (3),
                         versionNotSupported (4),
                         invalidRequestParameters (5),
                         duplicateLanDestination (6),
                         duplicateAtmAddress (7),
                         insufficientResources (8),
                         accessDenied (9),
                         invalidRequesterId (10),
                         invalidLanDestination (11),
                         invalidAtmAddress (12),
                         noConfiguration (13),
                         leConfigureError (14),
                         insufficientInformation (15)
                       }
     MAX-ACCESS read-only
     STATUS current
     DESCRIPTION
          "Status code from the last failed Configure response
           or Join response. Failed responses are those for which
           the LE_CONFIGURE_RESPONSE / LE_JOIN_RESPONSE frame
           contains a non-zero code, or fails to arrive within a
           timeout period. If none of this client's requests have
           failed, this object has the value 'none'. If the
           failed response contained a STATUS code that is not
           defined in the LAN Emulation specification, this
           object has the value 'undefinedError'. The value
           'timeout' is self explanatory. Other failure codes
           correspond to those defined in the specification,
           although they may have different numeric values."
     ::= { ibmMvsAtmLecStatusEntry 4 }

     ibmMvsAtmLecLastFailureState  OBJECT-TYPE
     SYNTAX  INTEGER {
                          initialState (1),
                          lecsConnect (2),
                          configure (3),
                          join (4),
                          initialRegistration (5),
                          busConnect (6),
                          operational (7)
                       }
     MAX-ACCESS read-only
     STATUS current
     DESCRIPTION
          "The state this client was in when it updated the
           'lecLastFailureRespCode'. If 'lecLastFailureRespCode'
           is 'none', this object has the value initialState(1)."
      ::= { ibmMvsAtmLecStatusEntry 5 }

     ibmMvsAtmLecProtocol  OBJECT-TYPE
     SYNTAX  Integer32 (1..255)
     MAX-ACCESS read-only
     STATUS current
     DESCRIPTION
          "The LAN Emulation protocol which this client supports,
           and specifies in its LE_JOIN_REQUESTs."
     ::= { ibmMvsAtmLecStatusEntry 6 }

     ibmMvsAtmLecVersion  OBJECT-TYPE
     SYNTAX  Integer32 (1..255)
     MAX-ACCESS read-only
     STATUS current
     DESCRIPTION
          "The LAN Emulation protocol version which this client
           supports, and specifies in its LE_JOIN_REQUESTs."
     ::= { ibmMvsAtmLecStatusEntry 7 }

     ibmMvsAtmLecTopologyChange  OBJECT-TYPE
     SYNTAX  INTEGER {
                         true (1),
                         false (2)
                       }
     MAX-ACCESS read-only
     STATUS current
     DESCRIPTION
          "Topology Change. Boolean indication that the LE Client
           is using the Forward Delay Time C18, instead of the
           Aging Time C17, to age non-local entries in its LE_ARP
           cache C16. For a client which is not connected to the
           LES, this object is defined to have the value 'false'.
           Corresponds to Initial State Parameter C19."
     ::= { ibmMvsAtmLecStatusEntry 8 }

     ibmMvsAtmLecConfigServerAtmAddress  OBJECT-TYPE
     SYNTAX  OCTET STRING (SIZE(20))
     MAX-ACCESS read-only
     STATUS current
     DESCRIPTION
          "The ATM address of the LAN Emulation Configuration
           Server (if known) or the 0 (otherwise). In LAN
           Emulation MIB, the OCTET STRING is either 0 length
           or 20 octets. For OSA-ATM, this Address) has been
           changed to a constant 20 octets, with the value 0
           equivalent to the 0 length OCTET STRING."
     ::= { ibmMvsAtmLecStatusEntry 9 }

     ibmMvsAtmLecConfigSource   OBJECT-TYPE
     SYNTAX  INTEGER {
                         gotAddressViaIlmi(1),
                         usedWellKnownAddress(2),
                         usedLecsPvc(3),
                         didNotUseLecs(4)
                       }
     MAX-ACCESS read-only
     STATUS current
     DESCRIPTION
           "Indicates whether this LAN Emulation Client used the
            LAN Emulation Configuration Server, and, if so, what
            method it used to establish the Configuration Direct
            VCC."
     ::= { ibmMvsAtmLecStatusEntry 10 }

     ibmMvsAtmLecActualLanType  OBJECT-TYPE
     SYNTAX  INTEGER {
                         unspecified (1),
                         ethernet (2),
                         tokenRing (3)
                       }
     MAX-ACCESS read-only
     STATUS current
     DESCRIPTION
           "The data frame format that this LAN Emulation Client
            is using right now. This may come from lecConfigLanType,
            the LAN Emulation Configuration Server, or the LAN
            Emulation Server. This value is related to 'ifMtu' and
            'ifType'. See the LEC management specification for more
            details. Corresponds to Initial State Parameter C2."
     ::= { ibmMvsAtmLecStatusEntry 11 }

     ibmMvsAtmLecActualMaxDataFrameSize  OBJECT-TYPE
     SYNTAX  INTEGER {
                         unspecified (1),
                         f1516 (2),
                         f4544 (3),
                         f9234 (4),
                         f18190 (5)
                       }
     MAX-ACCESS read-only
     STATUS current
     DESCRIPTION
           "Maximum Data Frame Size. The maximum data frame size
            that this LAN Emulation client is using right now.
            This may come from lecConfigMaxDataFrameSize,
            the LAN Emulation Configuration Server, or the LAN
            Emulation Server Corresponds to Initial State
            Parameter C3."
     ::= { ibmMvsAtmLecStatusEntry 12 }

     ibmMvsAtmLecActualLanName  OBJECT-TYPE
     SYNTAX  OCTET STRING (SIZE(32))
     MAX-ACCESS read-only
     STATUS current
     DESCRIPTION
           "ELAN Name. The identity of the emulated LAN which
            this client last joined, or wishes to join. This
            may come from lecConfigLanName, the LAN Emulation
            Configuration Server, or the LAN Emulation Server.
            Corresponds to Initial State Parameter C5."
     ::= { ibmMvsAtmLecStatusEntry 13 }

     ibmMvsAtmLecAtmAddress  OBJECT-TYPE
     SYNTAX  OCTET STRING (SIZE(20))
     MAX-ACCESS read-only
     STATUS current
     DESCRIPTION
           "LE Server ATM Address. The LAN Emulation Server
            address currently in use or most recently attempted.
            If no LAN Emulation Server attachment has been tried,
            this object's value is zero. Corresponds to Initial
            State Parameter C9. In LAN Emulation MIB, the
            OCTET STRING is 0 to 20 octets in length. For OSA-ATM,
            this has been changed to a constant 20 octets, with
            the value 0 equivalent to the 0 length OCTET STRING."
     ::= { ibmMvsAtmLecStatusEntry 14 }

     ibmMvsAtmLecProxyClient  OBJECT-TYPE
     SYNTAX  INTEGER {
                         true (1),
                         false (2)
                       }
     MAX-ACCESS read-only
     STATUS current
     DESCRIPTION
           "Indicates whether this client is acting as a proxy.
            Proxy clients are allowed to represent unregistered
            MAC addresses, and receive copies of LE_ARP_REQUEST
            frames for such addresses. Corresponds to Initial
            State Parameter C4."
     ::= { ibmMvsAtmLecStatusEntry 15 }

 -- ibmMvsAtmLecStatisticsTable

     ibmMvsAtmLecStatisticsTable OBJECT-TYPE
     SYNTAX SEQUENCE OF IbmMvsAtmLecStatisticsEntry
     MAX-ACCESS not-accessible
     STATUS current
     DESCRIPTION
        "This table is intended to represent the data that is
         available from an OSA Port that is running LAN
         Emulation mode. An entry in this table is indexed by a
         LAN Emulation ifIndex. An ifEntry who's ifType is either
         aflane802.3 (59) or aflane802.5 (60) will have a
         corresponding entry in this table. This table is modeled
         after the LEC Statistics Table from the LAN Emulation MIB
         defined by the ATM Forum."
     ::= { ibmTcpipMvsAtmGroup 7 }

     ibmMvsAtmLecStatisticsEntry OBJECT-TYPE
     SYNTAX IbmMvsAtmLecStatisticsEntry
     MAX-ACCESS not-accessible
     STATUS current
     DESCRIPTION
        "Describes a particular ATM Lec Statistics Table entry, indexed
         by either a aflan802.3 or a aflane802.5 ifEntry's ifIndex."
     INDEX { ifIndex }
     ::= { ibmMvsAtmLecStatisticsTable 1 }

     IbmMvsAtmLecStatisticsEntry ::=
     SEQUENCE
       {
         ibmMvsAtmLecArpRequestsOut      Counter32,
         ibmMvsAtmLecArpRequestsIn       Counter32,
         ibmMvsAtmLecArpRepliesOut       Counter32,
         ibmMvsAtmLecArpRepliesIn        Counter32,
         ibmMvsAtmLecControlFramesOut    Counter32,
         ibmMvsAtmLecControlFramesIn     Counter32,
         ibmMvsAtmLecSvcFailures         Counter32
       }

     ibmMvsAtmLecArpRequestsOut  OBJECT-TYPE
     SYNTAX  Counter32
     MAX-ACCESS read-only
     STATUS current
     DESCRIPTION
           "The number of LE_ARP_REQUESTs sent over the
            LUNI by this LAN Emulation Client."
     ::= { ibmMvsAtmLecStatisticsEntry 1 }

     ibmMvsAtmLecArpRequestsIn OBJECT-TYPE
     SYNTAX  Counter32
     MAX-ACCESS read-only
     STATUS current
     DESCRIPTION
           "The number of LE_ARP_REQUESTs received over the LUNI
            by this LAN Emulation Client. Requests may arrive
            on the Control Direct VCC or on the Control Distribute
            VCC, depending upon how the LES is implemented and the
            chances it has had for learning. This counter covers
            both VCCs."
     ::= { ibmMvsAtmLecStatisticsEntry 2 }

     ibmMvsAtmLecArpRepliesOut  OBJECT-TYPE
     SYNTAX  Counter32
     MAX-ACCESS read-only
     STATUS current
     DESCRIPTION
           "The number of LE_ARP_RESPONSEs sent over the LUNI
            by this LAN Emulation Client."
     ::= { ibmMvsAtmLecStatisticsEntry 3 }

     ibmMvsAtmLecArpRepliesIn  OBJECT-TYPE
     SYNTAX  Counter32
     MAX-ACCESS read-only
     STATUS current
     DESCRIPTION
           "The number of LE_ARP_RESPONSEs received over the
            LUNI by this LAN Emulation Client. This count includes
            all such replies, whether solicited or not. Replies
            may arrive on the Control Direct VCC or on the
            Control Distribute VCC, depending upon how the LES
            is implemented. This counter covers both VCCs."
     ::= { ibmMvsAtmLecStatisticsEntry 4 }

     ibmMvsAtmLecControlFramesOut OBJECT-TYPE
     SYNTAX  Counter32
     MAX-ACCESS read-only
     STATUS current
     DESCRIPTION
           "The total number of control packets sent by this
            LAN Emulation Client over the LUNI."
     ::= { ibmMvsAtmLecStatisticsEntry 5 }

     ibmMvsAtmLecControlFramesIn OBJECT-TYPE
     SYNTAX  Counter32
     MAX-ACCESS read-only
     STATUS current
     DESCRIPTION
           "The total number of control packets received by this
           LAN Emulation Client over the LUNI."
     ::= { ibmMvsAtmLecStatisticsEntry 6 }

     ibmMvsAtmLecSvcFailures OBJECT-TYPE
     SYNTAX  Counter32
     MAX-ACCESS read-only
     STATUS current
     DESCRIPTION
           "The total number of outgoing LAN Emulation SVCs
            which this client tried, but failed, to open;
            incoming LAN Emulation SVCs which this client tried,
            but failed to establish; and incoming LAN Emulation
            SVCs which this client rejected for protocol or
            security reasons."
     ::= { ibmMvsAtmLecStatisticsEntry 7 }


 -- ibmMvsAtmLecServerTable

     ibmMvsAtmLecServerTable OBJECT-TYPE
     SYNTAX SEQUENCE OF IbmMvsAtmLecServerEntry
     MAX-ACCESS not-accessible
     STATUS current
     DESCRIPTION
        "This table is intended to represent the data that is
         available from an OSA Port that is running LAN
         Emulation mode. An entry in this table is indexed by a
         LAN Emulation ifIndex. An ifEntry who's ifType is either
         aflane802.3 (59) or aflane802.5 (60) will have a
         corresponding entry in this table. This table is modeled
         after the LEC Server Table from the LAN Emulation MIB
         defined by the ATM Forum."
     ::= { ibmTcpipMvsAtmGroup 8 }

     ibmMvsAtmLecServerEntry OBJECT-TYPE
     SYNTAX IbmMvsAtmLecServerEntry
     MAX-ACCESS not-accessible
     STATUS current
     DESCRIPTION
        "Describes a particular ATM Lec Server Table entry, indexed
         by either a aflan802.3 or a aflane802.5 ifEntry's ifIndex."
     INDEX { ifIndex }
     ::= { ibmMvsAtmLecServerTable 1 }

     IbmMvsAtmLecServerEntry ::=
     SEQUENCE
       {
        ibmMvsAtmLecConfigDirectInterface       Integer32,
        ibmMvsAtmLecConfigDirectVPI             Integer32,
        ibmMvsAtmLecConfigDirectVCI             Integer32,
        ibmMvsAtmLecControlDirectInterface      Integer32,
        ibmMvsAtmLecControlDirectVPI            Integer32,
        ibmMvsAtmLecControlDirectVCI            Integer32,
        ibmMvsAtmLecControlDistributeInterface  Integer32,
        ibmMvsAtmLecControlDistributeVPI        Integer32,
        ibmMvsAtmLecControlDistributeVCI        Integer32,
        ibmMvsAtmLecMulticastSendInterface      Integer32,
        ibmMvsAtmLecMulticastSendVPI            Integer32,
        ibmMvsAtmLecMulticastSendVCI            Integer32,
        ibmMvsAtmLecMulticastFwdInterface       Integer32,
        ibmMvsAtmLecMulticastFwdVPI             Integer32,
        ibmMvsAtmLecMulticastFwdVCI             Integer32
       }

     ibmMvsAtmLecConfigDirectInterface  OBJECT-TYPE
     SYNTAX  Integer32 (0..2147483647)
     MAX-ACCESS read-only
     STATUS current
     DESCRIPTION
             "The interface associated with the Configuration
              Direct VCC. If no Configuration Direct VCC exists,
              this object has the value 0. Otherwise, the objects
              ( lecConfigDirectInterface, lecConfigDirectVPI,
              lecConfigDirectVCI ) identify the circuit."
     ::= { ibmMvsAtmLecServerEntry 1 }

     ibmMvsAtmLecConfigDirectVPI  OBJECT-TYPE
     SYNTAX  Integer32 (0..255)
     MAX-ACCESS read-only
     STATUS current
     DESCRIPTION
             "If the Configuration Direct VCC exists, this object
              contains the VPI which identifies that VCC at the
              point where it connects to this LE client.
              Otherwise, this object has the value 0."
     ::= { ibmMvsAtmLecServerEntry 2 }

     ibmMvsAtmLecConfigDirectVCI  OBJECT-TYPE
     SYNTAX  Integer32 (0..65535)
     MAX-ACCESS read-only
     STATUS current
     DESCRIPTION
             "If the Configuration Direct VCC exists, this
              object contains the VCI which identifies that
              VCC at the point where it connects to this LE
              client. Otherwise, this object has the value 0."
     ::= { ibmMvsAtmLecServerEntry 3 }

     ibmMvsAtmLecControlDirectInterface  OBJECT-TYPE
     SYNTAX  Integer32 (0..2147483647)
     MAX-ACCESS read-only
     STATUS current
     DESCRIPTION
           "The interface associated with the Control Direct
            VCC. If no Control Direct VCC exists, this object
            has the value 0. Otherwise, the objects
            ( lecControlDirectInterface, lecControlDirectVPI,
            lecControlDirectVCI ) identify the circuit."
     ::= { ibmMvsAtmLecServerEntry 4 }

     ibmMvsAtmLecControlDirectVPI OBJECT-TYPE
     SYNTAX  Integer32 (0..255)
     MAX-ACCESS read-only
     STATUS current
     DESCRIPTION
           "If the Control Direct VCC exists, this object
            contains the VPI which identifies that VCC at
            the point where it connects to this LE client.
            Otherwise, this object has the value 0."
     ::= { ibmMvsAtmLecServerEntry 5 }

     ibmMvsAtmLecControlDirectVCI OBJECT-TYPE
     SYNTAX  Integer32 (0..65535)
     MAX-ACCESS read-only
     STATUS current
     DESCRIPTION
           "If the Control Direct VCC exists, this object
            contains the VCI which identifies that VCC at
            the point where it connects to this LE client.
            Otherwise, this object has the value 0."
     ::= { ibmMvsAtmLecServerEntry 6 }

     ibmMvsAtmLecControlDistributeInterface OBJECT-TYPE
     SYNTAX  Integer32 (0..2147483647)
     MAX-ACCESS read-only
     STATUS current
     DESCRIPTION
           "The interface associated with the Control Distribute
            VCC. If no Control Distribute VCC has been set up to
            this client, this object has the value 0. Otherwise,
            the objects ( lecControlDistributeInterface,
            lecControlDistributeVPI, lecControlDistributeVCI )
            identify the circuit."
     ::= { ibmMvsAtmLecServerEntry 7 }

     ibmMvsAtmLecControlDistributeVPI  OBJECT-TYPE
     SYNTAX  Integer32 (0..255)
     MAX-ACCESS read-only
     STATUS current
     DESCRIPTION
           "If the Control Distribute VCC exists, this object
            contains the VPI which identifies that VCC at the
            point where it connects to this LE client.
            Otherwise, this object has the value 0."
     ::= { ibmMvsAtmLecServerEntry 8 }

     ibmMvsAtmLecControlDistributeVCI  OBJECT-TYPE
     SYNTAX  Integer32 (0..65535)
     MAX-ACCESS read-only
     STATUS current
     DESCRIPTION
           "If the Control Distribute VCC exists, this object
            contains the VCI which identifies that VCC at the
            point where it connects to this LE client.
            Otherwise, this object contains the value 0."
     ::= { ibmMvsAtmLecServerEntry 9 }

     ibmMvsAtmLecMulticastSendInterface  OBJECT-TYPE
     SYNTAX  Integer32 (0..2147483647)
     MAX-ACCESS read-only
     STATUS current
     DESCRIPTION
          "The interface associated with the Multicast Send
           VCC. If no Multicast Send VCC exists, this object
           has the value 0. Otherwise, the objects
           ( lecMulticastSendInterface, lecMulticastSendVPI,
           lecMulticastSendVCI ) identify the circuit."
     ::= { ibmMvsAtmLecServerEntry 10 }

     ibmMvsAtmLecMulticastSendVPI  OBJECT-TYPE
     SYNTAX  Integer32 (0..255)
     MAX-ACCESS read-only
     STATUS current
     DESCRIPTION
          "If the Multicast Send VCC exists, this object
           contains the VPI which identifies that VCC at
           the point where it connects to this LE client.
           Otherwise, this object has the value 0."
     ::= { ibmMvsAtmLecServerEntry 11 }

     ibmMvsAtmLecMulticastSendVCI  OBJECT-TYPE
     SYNTAX  Integer32 (0..65535)
     MAX-ACCESS read-only
     STATUS current
     DESCRIPTION
          "If the Multicast Send VCC exists, this object
           contains the VCI which identifies that VCC at
           the point where it connects to this LE client.
           Otherwise, this object has the value 0."
     ::= { ibmMvsAtmLecServerEntry 12 }

     ibmMvsAtmLecMulticastFwdInterface  OBJECT-TYPE
     SYNTAX  Integer32 (0..2147483647)
     MAX-ACCESS read-only
     STATUS current
     DESCRIPTION
           "The interface associated with the Multicast
            Forward VCC. If no Multicast Forward VCC has
            been set up to this client, this object has the
            value 0. Otherwise, the objects
            ( lecMulticastForwardInterface, lecMulticastForwardVPI,
            lecMulticastForwardVCI ) identify the circuit."
     ::= { ibmMvsAtmLecServerEntry 13 }

     ibmMvsAtmLecMulticastFwdVPI  OBJECT-TYPE
     SYNTAX  Integer32 (0..255)
     MAX-ACCESS read-only
     STATUS current
     DESCRIPTION
           "If the Multicast Forward VCC exists, this object
            contains the VPI which identifies that VCC at the
            point where it connects to this LE client.
            Otherwise, this object has the value 0."
     ::= { ibmMvsAtmLecServerEntry 14 }

     ibmMvsAtmLecMulticastFwdVCI  OBJECT-TYPE
     SYNTAX  Integer32 (0..65535)
     MAX-ACCESS read-only
     STATUS current
     DESCRIPTION
           "If the Multicast Forward VCC exists, this object
            contains the VCI which identifies that VCC at the
            point where it connects to this LE client.
            Otherwise, this object has the value 0."
     ::= { ibmMvsAtmLecServerEntry 15 }

 -- ibmMvsAtmLecMacAddressTable

     ibmMvsAtmLecMacAddressTable OBJECT-TYPE
     SYNTAX SEQUENCE OF IbmMvsAtmLecMacAddressEntry
     MAX-ACCESS not-accessible
     STATUS current
     DESCRIPTION
        "This table is intended to represent the data that is
         available from an OSA Port that is running LAN
         Emulation mode. An entry in this table is indexed by a
         LAN Emulation ifIndex. An ifEntry who's ifType is either
         aflane802.3 (59) or aflane802.5 (60) will have a
         corresponding entry in this table. This table is modeled
         after the LEC MAC Address Table from the LAN Emulation MIB
         defined by the ATM Forum."
     ::= { ibmTcpipMvsAtmGroup 9 }

     ibmMvsAtmLecMacAddressEntry OBJECT-TYPE
     SYNTAX IbmMvsAtmLecMacAddressEntry
     MAX-ACCESS not-accessible
     STATUS current
     DESCRIPTION
        "Describes a particular ATM Lec Mac Address Table entry,
         indexed by either a aflan802.3 or a aflane802.5 ifEntry's
         ifIndex."
     INDEX { ifIndex }
     ::= { ibmMvsAtmLecMacAddressTable 1 }

     IbmMvsAtmLecMacAddressEntry ::=
     SEQUENCE
       {
          ibmMvsAtmLecMacAddress    OCTET STRING (SIZE(6))
       }

     ibmMvsAtmLecMacAddress  OBJECT-TYPE
     SYNTAX  OCTET STRING (SIZE(6))
     MAX-ACCESS read-only
     STATUS current
     DESCRIPTION
         "A unicast MAC address which the LE client
          denoted by 'lecIndex' has registered with its
          LE Server. This value is expressed in canonical
          form for Ethernet."
     ::= { ibmMvsAtmLecMacAddressEntry 1 }



 ---------------------------------------------------------------------
 -- ibmTcpipMvsTcpGroup6
 ---------------------------------------------------------------------

     ibmTcpipMvsTcpConnTable OBJECT-TYPE
     SYNTAX SEQUENCE OF IbmTcpipMvsTcpConnEntry
     MAX-ACCESS not-accessible
     STATUS current
     DESCRIPTION
          "Extends tcpConnTable to provide additional TCP
           connection information."
     ::= { ibmTcpipMvsTcpGroup 1 }

     ibmTcpipMvsTcpConnEntry OBJECT-TYPE
     SYNTAX IbmTcpipMvsTcpConnEntry
     MAX-ACCESS not-accessible
     STATUS current
     DESCRIPTION
          "Descibes a particular tcp connection entry."
     AUGMENTS { tcpConnEntry }
     ::= { ibmTcpipMvsTcpConnTable 1 }

     IbmTcpipMvsTcpConnEntry ::=
          SEQUENCE
          {
          ibmMvsTcpConnLastActivity       TimeTicks,
          ibmMvsTcpConnBytesIn            Unsigned32,
          ibmMvsTcpConnBytesOut           Unsigned32,
          ibmMvsTcpConnActiveOpen         Integer32,
          ibmMvsTcpConnIpTos              TypeOfService,
          ibmMvsTcpConnOptions            OCTET STRING  (SIZE(1..40)),
          ibmMvsTcpConnOutBuffered        Unsigned32,
          ibmMvsTcpConnUsrSndNxt          Counter32,
          ibmMvsTcpConnSndNxt             Counter32,
          ibmMvsTcpConnSndUna             Counter32,
          ibmMvsTcpConnOutgoingPush       Counter32,
          ibmMvsTcpConnOutgoingUrg        Counter32,
          ibmMvsTcpConnOutgoingWinSeq     Counter32,
          ibmMvsTcpConnSendWindowSeq      Integer32,
          ibmMvsTcpConnSendWindowAck      Integer32,
          ibmMvsTcpConnInBuffered         Unsigned32,
          ibmMvsTcpConnRcvNxt             Counter32,
          ibmMvsTcpConnUsrRcvNxt          Counter32,
          ibmMvsTcpConnIncomingPush       Counter32,
          ibmMvsTcpConnIncomingUrg        Counter32,
          ibmMvsTcpConnIncomingWinSeq     Counter32,
          ibmMvsTcpConnReXmt              Integer32,
          ibmMvsTcpConnMaxSndWnd          Unsigned32,
          ibmMvsTcpConnReXmtCount         Integer32,
          ibmMvsTcpConnCongestionWnd      Unsigned32,
          ibmMvsTcpConnSSThresh           Unsigned32,
          ibmMvsTcpConnRoundTripTime      Unsigned32,
          ibmMvsTcpConnRoundTripVariance  Unsigned32,
          ibmMvsTcpConnInitSndSeq         Unsigned32,
          ibmMvsTcpConnInitRcvSeq         Unsigned32,
          ibmMvsTcpConnSendMSS            Unsigned32,
          ibmMvsTcpConnSndWl1             Counter32,
          ibmMvsTcpConnSndWl2             Counter32,
          ibmMvsTcpConnSndWnd             Unsigned32,
          ibmMvsTcpConnPendTcpRecv        Integer32,
          ibmMvsTcpConnRcvBufSize         Unsigned32,
          ibmMvsTcpConnResourceName       DisplayString  (SIZE(0..8)),
          ibmMvsTcpConnSubtask            Unsigned32,
          ibmMvsTcpConnResourceId         Unsigned32,
          ibmMvsTcpConnSockOpt            OCTET STRING (SIZE(1)),
          ibmMvsTcpConnTcpTimer           OCTET STRING (SIZE(1)),
          ibmMvsTcpConnTcpSig             OCTET STRING (SIZE(1)),
          ibmMvsTcpConnTcpSel             OCTET STRING (SIZE(1)),
          ibmMvsTcpConnRttSeq             Counter32,
          ibmMvsTcpConnBackoffCount       Integer32,
          ibmMvsTcpConnTcpDet             OCTET STRING (SIZE(1)),
          ibmMvsTcpConnTcpPol             OCTET STRING (SIZE(1)),
          ibmMvsTcpConnTargetAppl         DisplayString  (SIZE(0..8)),
          ibmMvsTcpConnLuName             DisplayString  (SIZE(0..8)),
          ibmMvsTcpConnClientUserId       DisplayString  (SIZE(0..8)),
          ibmMvsTcpConnLogMode            DisplayString  (SIZE(0..8)),
          ibmMvsTcpConnProto              OCTET STRING (SIZE(1)),
          ibmMvsTcpConnDupacks            Unsigned32,
          ibmMvsTcpConnOptMaxSegmentSize  Integer32,
          ibmMvsTcpConnClusterConnFlag    OCTET STRING (SIZE(1)),
          ibmMvsTcpConnInSegs             Counter32,
          ibmMvsTcpConnOutSegs            Counter32,
          ibmMvsTcpConnDSField            OCTET STRING (SIZE(1)),
          ibmMvsTcpConnSndBufSize         Unsigned32,
          ibmMvsTcpConnAcceptCount        Counter32,
          ibmMvsTcpConnExceedBacklog      Integer32,
          ibmMvsTcpConnCurrBacklog        Integer32,
          ibmMvsTcpConnMaxBacklog         Integer32,
          ibmMvsTcpConnWindowScale        TruthValue,
          ibmMvsTcpConnTimeStamp          TruthValue,
          ibmMvsTcpConnServerResourceId   Unsigned32
          }

       ibmMvsTcpConnLastActivity OBJECT-TYPE
             SYNTAX   TimeTicks
             MAX-ACCESS   read-only
             STATUS   current
             DESCRIPTION
                "The number of 100ths of seconds  since  this  entry
                was last used."
             DEFVAL  { 0 }
             ::= { ibmTcpipMvsTcpConnEntry 1 }

          ibmMvsTcpConnBytesIn  OBJECT-TYPE
             SYNTAX   Unsigned32
             MAX-ACCESS   read-only
             STATUS   current
             DESCRIPTION
                "The number of bytes received from IP for this
                 connection."
             DEFVAL  { 0 }
             ::= { ibmTcpipMvsTcpConnEntry 2 }

          ibmMvsTcpConnBytesOut OBJECT-TYPE
             SYNTAX   Unsigned32
             MAX-ACCESS   read-only
             STATUS   current
             DESCRIPTION
                "The number of bytes sent to IP for this connection."
             DEFVAL  { 0 }
             ::= { ibmTcpipMvsTcpConnEntry 3 }

          ibmMvsTcpConnActiveOpen OBJECT-TYPE
             SYNTAX   Integer32
             MAX-ACCESS   read-only
             STATUS   obsolete
             DESCRIPTION
                "The number of times that this connection has made a
                 direct transition to the SYN-RCVD state from the
                 listen state."
             DEFVAL  { 0 }
             ::= { ibmTcpipMvsTcpConnEntry 4 }

          ibmMvsTcpConnIpTos OBJECT-TYPE
             SYNTAX   TypeOfService
             MAX-ACCESS   read-only
             STATUS   obsolete
             DESCRIPTION
                "Type of Service (tos) in effect for this tcpConnTable
                 entry. Currently not supported and should return a
                 zero."
             ::= { ibmTcpipMvsTcpConnEntry 5 }

          ibmMvsTcpConnOptions OBJECT-TYPE
             SYNTAX   OCTET STRING (SIZE(1..40))
             MAX-ACCESS   read-only
             STATUS   current
             DESCRIPTION
                "IP options (see RFC 791)"
             ::= { ibmTcpipMvsTcpConnEntry 6 }

          ibmMvsTcpConnOutBuffered OBJECT-TYPE
             SYNTAX   Unsigned32
             MAX-ACCESS   read-only
             STATUS   current
             DESCRIPTION
                "Number of outgoing bytes buffered"
             DEFVAL  { 0 }
             ::= { ibmTcpipMvsTcpConnEntry 7 }

          ibmMvsTcpConnUsrSndNxt OBJECT-TYPE
             SYNTAX   Counter32
             MAX-ACCESS   read-only
             STATUS   current
             DESCRIPTION
                "Sequence number of next byte for user"
             ::= { ibmTcpipMvsTcpConnEntry 8 }

          ibmMvsTcpConnSndNxt OBJECT-TYPE
             SYNTAX   Counter32
             MAX-ACCESS   read-only
             STATUS   current
             DESCRIPTION
                "Sequence number of next byte for TCP"
             ::= { ibmTcpipMvsTcpConnEntry 9 }

          ibmMvsTcpConnSndUna OBJECT-TYPE
             SYNTAX   Counter32
             MAX-ACCESS   read-only
             STATUS   current
             DESCRIPTION
                "Sequence number of sent/unacked byte"
             ::= { ibmTcpipMvsTcpConnEntry 10 }

          ibmMvsTcpConnOutgoingPush OBJECT-TYPE
             SYNTAX   Counter32
             MAX-ACCESS   read-only
             STATUS   current
             DESCRIPTION
                "Sequence number of last pushed byte"
             ::= { ibmTcpipMvsTcpConnEntry 11 }

          ibmMvsTcpConnOutgoingUrg OBJECT-TYPE
             SYNTAX   Counter32
             MAX-ACCESS   read-only
             STATUS   current
             DESCRIPTION
                "Sequence number of last urg byte"
             ::= { ibmTcpipMvsTcpConnEntry 12 }

          ibmMvsTcpConnOutgoingWinSeq OBJECT-TYPE
             SYNTAX   Counter32
             MAX-ACCESS   read-only
             STATUS   current
             DESCRIPTION
                "Last sequence number in snd window"
             ::= { ibmTcpipMvsTcpConnEntry 13 }

          ibmMvsTcpConnSendWindowSeq OBJECT-TYPE
             SYNTAX   Integer32
             MAX-ACCESS   read-only
             STATUS   obsolete
             DESCRIPTION
                "Last sequence number used, win update"
             DEFVAL  { 0 }
             ::= { ibmTcpipMvsTcpConnEntry 14 }

          ibmMvsTcpConnSendWindowAck OBJECT-TYPE
             SYNTAX   Integer32
             MAX-ACCESS   read-only
             STATUS   obsolete
             DESCRIPTION
                "Last Ack number used, win update"
             DEFVAL  { 0 }
             ::= { ibmTcpipMvsTcpConnEntry 15 }

          ibmMvsTcpConnInBuffered OBJECT-TYPE
             SYNTAX   Unsigned32
             MAX-ACCESS   read-only
             STATUS current
             DESCRIPTION
                "Number of incoming bytes buffered"
             DEFVAL  { 0 }
             ::= { ibmTcpipMvsTcpConnEntry 16 }

          ibmMvsTcpConnRcvNxt OBJECT-TYPE
             SYNTAX   Counter32
             MAX-ACCESS   read-only
             STATUS   current
             DESCRIPTION
                "Sequence number of next byte for TCP"
             ::= { ibmTcpipMvsTcpConnEntry 17 }

          ibmMvsTcpConnUsrRcvNxt OBJECT-TYPE
             SYNTAX   Counter32
             MAX-ACCESS   read-only
             STATUS   current
             DESCRIPTION
                "Sequence number of next byte for user"
             ::= { ibmTcpipMvsTcpConnEntry 18 }

          ibmMvsTcpConnIncomingPush OBJECT-TYPE
             SYNTAX   Counter32
             MAX-ACCESS   read-only
             STATUS   current
             DESCRIPTION
                "Sequence number of last pushed byte"
             ::= { ibmTcpipMvsTcpConnEntry 19 }

          ibmMvsTcpConnIncomingUrg OBJECT-TYPE
             SYNTAX   Counter32
             MAX-ACCESS   read-only
             STATUS   current
             DESCRIPTION
                "Sequence number of 'urgent' byte received"
             ::= { ibmTcpipMvsTcpConnEntry 20 }

          ibmMvsTcpConnIncomingWinSeq OBJECT-TYPE
             SYNTAX   Counter32
             MAX-ACCESS   read-only
             STATUS   current
             DESCRIPTION
                "Last sequence number in receive window"
             ::= { ibmTcpipMvsTcpConnEntry 21 }

          ibmMvsTcpConnReXmt OBJECT-TYPE
             SYNTAX   Integer32
             MAX-ACCESS   read-only
             STATUS   current
             DESCRIPTION
                "Total number of retransmissions for this connection."
             DEFVAL  { 0 }
             ::= { ibmTcpipMvsTcpConnEntry 22 }

          ibmMvsTcpConnMaxSndWnd OBJECT-TYPE
             SYNTAX   Unsigned32
             MAX-ACCESS   read-only
             STATUS   current
             DESCRIPTION
                "Maximum send window seen"
             DEFVAL  { 0 }
             ::= { ibmTcpipMvsTcpConnEntry 23 }

          ibmMvsTcpConnReXmtCount OBJECT-TYPE
             SYNTAX   Integer32
             MAX-ACCESS   read-only
             STATUS   current
             DESCRIPTION
                "Number of times the current segment has been
                 retransmitted."
             DEFVAL  { 0 }
             ::= { ibmTcpipMvsTcpConnEntry 24 }

          ibmMvsTcpConnCongestionWnd OBJECT-TYPE
             SYNTAX   Unsigned32
             MAX-ACCESS   read-only
             STATUS   current
             DESCRIPTION
                "Congestion window"
             DEFVAL  { 0 }
             ::= { ibmTcpipMvsTcpConnEntry 25 }

          ibmMvsTcpConnSSThresh OBJECT-TYPE
             SYNTAX   Unsigned32
             MAX-ACCESS   read-only
             STATUS   current
             DESCRIPTION
                "Slow start threshold"
             DEFVAL  { 0 }
             ::= { ibmTcpipMvsTcpConnEntry 26 }

          ibmMvsTcpConnRoundTripTime OBJECT-TYPE
             SYNTAX   Unsigned32
             MAX-ACCESS   read-only
             STATUS   current
             DESCRIPTION
                "The amount of time that has elapsed, measured in
                 milliseconds, from when the last TCP segment was
                 transmitted by the TCP Stack until the ACK was
                 received."
             DEFVAL  { 0 }
             ::= { ibmTcpipMvsTcpConnEntry 27 }

          ibmMvsTcpConnRoundTripVariance OBJECT-TYPE
             SYNTAX   Unsigned32
             MAX-ACCESS   read-only
             STATUS   current
             DESCRIPTION
                "Round trip time variance."
             DEFVAL  { 0 }
             ::= { ibmTcpipMvsTcpConnEntry 28 }

          ibmMvsTcpConnInitSndSeq OBJECT-TYPE
             SYNTAX   Unsigned32
             MAX-ACCESS   read-only
             STATUS   current
             DESCRIPTION
                "Initial Send Sequence Number"
             DEFVAL  { 0 }
             ::= { ibmTcpipMvsTcpConnEntry 29 }

          ibmMvsTcpConnInitRcvSeq OBJECT-TYPE
             SYNTAX   Unsigned32
             MAX-ACCESS   read-only
             STATUS   current
             DESCRIPTION
                "Initial Receive Sequence Number"
             DEFVAL  { 0 }
             ::= { ibmTcpipMvsTcpConnEntry 30 }

          ibmMvsTcpConnSendMSS OBJECT-TYPE
             SYNTAX   Unsigned32
             MAX-ACCESS   read-only
             STATUS   current
             DESCRIPTION
                "Maximum Segment Size we can send"
             DEFVAL  { 0 }
             ::= { ibmTcpipMvsTcpConnEntry 31 }

          ibmMvsTcpConnSndWl1 OBJECT-TYPE
             SYNTAX   Counter32
             MAX-ACCESS   read-only
             STATUS   current
             DESCRIPTION
                "Sequence of last window"
             ::= { ibmTcpipMvsTcpConnEntry 32 }

          ibmMvsTcpConnSndWl2 OBJECT-TYPE
             SYNTAX   Counter32
             MAX-ACCESS   read-only
             STATUS   current
             DESCRIPTION
                "Ack of last window"
             ::= { ibmTcpipMvsTcpConnEntry 33 }

          ibmMvsTcpConnSndWnd OBJECT-TYPE
             SYNTAX   Unsigned32
             MAX-ACCESS   read-only
             STATUS   current
             DESCRIPTION
                "Send Window size"
             DEFVAL  { 0 }
             ::= { ibmTcpipMvsTcpConnEntry 34 }

          ibmMvsTcpConnPendTcpRecv OBJECT-TYPE
             SYNTAX   Integer32
             MAX-ACCESS   read-only
             STATUS   obsolete
             DESCRIPTION
                "TCP non_block read flag"
             DEFVAL  { 0 }
             ::= { ibmTcpipMvsTcpConnEntry 35 }

          ibmMvsTcpConnRcvBufSize OBJECT-TYPE
             SYNTAX   Unsigned32
             MAX-ACCESS   read-only
             STATUS   current
             DESCRIPTION
                "Receive buffer size"
             DEFVAL  { 0 }
             ::= { ibmTcpipMvsTcpConnEntry 36 }

          ibmMvsTcpConnResourceName OBJECT-TYPE
             SYNTAX   DisplayString (SIZE(0..8))
             MAX-ACCESS   read-only
             STATUS   current
             DESCRIPTION
                "Resource Name is the text identification of this
                 resource. It represents the user who opened the
                 socket and is updated again during the bind
                 processing."
             ::= { ibmTcpipMvsTcpConnEntry 37 }

          ibmMvsTcpConnSubtask OBJECT-TYPE
             SYNTAX   Unsigned32
             MAX-ACCESS   read-only
             STATUS   current
             DESCRIPTION
                "The subtask ID represents the task that opened the
                 socket and is updated again during bind
                 processing. It is actually the TCB address."
             DEFVAL  { 0 }
             ::= { ibmTcpipMvsTcpConnEntry 38 }

          ibmMvsTcpConnResourceId OBJECT-TYPE
             SYNTAX   Unsigned32
             MAX-ACCESS   read-only
             STATUS   current
             DESCRIPTION
                "Resource ID is the numeric identification of this
                 resource."
             DEFVAL  { 0 }
             ::= { ibmTcpipMvsTcpConnEntry 39 }

          ibmMvsTcpConnSockOpt OBJECT-TYPE
             SYNTAX   OCTET STRING (SIZE(1))
             MAX-ACCESS   read-only
             STATUS   current
             DESCRIPTION
                "flag for socket options (1 byte hex value)
                 -bit(1) = Sockets SO_REUSEADDR option
                 -bit(2) = SO_OOBINLINE option
                 -bit(3) = SO_LINGER option
                 -bit(4) = T_MSGDONTROUTE
                 -bit(5) = No delay (Nagle off) option
                 -bit(6) = SO_Keepalive option
                 -bit(7) = Currently timing linger
                 -bit(8) = Currently timing keep alive"
             ::= { ibmTcpipMvsTcpConnEntry 40 }

          ibmMvsTcpConnTcpTimer OBJECT-TYPE
             SYNTAX   OCTET STRING (SIZE(1))
             MAX-ACCESS   read-only
             STATUS   obsolete
             DESCRIPTION
                "flag for TCP timers (1 byte hex value)
                 -bit(1) = Currently timing round trip
                 -bit(2) = Currently timing rexmt
                 -bit(3) = Currently timing window probe
                 -bit(4) = Dally timer currently set
                 -bit(5) = Max Seg Lifetime timer set
                 -bit(6) = T_ORDREL_IND is pending
                 -bit(7) = Blocked for writing
                 -bit(8) = Need to send a FIN"
             ::= { ibmTcpipMvsTcpConnEntry 41 }

          ibmMvsTcpConnTcpSig OBJECT-TYPE
             SYNTAX   OCTET STRING (SIZE(1))
             MAX-ACCESS   read-only
             STATUS   obsolete
             DESCRIPTION
                "1 byte hex flag for TCP signals
                -bit(1) = Signal urgent data
                -bit(2) = Signal normal data
                -bit(3) = Signal timing finwait2
                -bit(4) = <reserved>
                -bit(5) = <reserved>
                -bit(6) = Window scale option was received
                -bit(7) = Tcb on accept queue
                -bit(8) = Socket OPTMSS option"
             ::= { ibmTcpipMvsTcpConnEntry 42 }

          ibmMvsTcpConnTcpSel OBJECT-TYPE
             SYNTAX   OCTET STRING (SIZE(1))
             MAX-ACCESS   read-only
             STATUS   obsolete
             DESCRIPTION
                "TCP select flag byte for TCP select conditions.
                 It is mapped as follows:
                 -bit(1) = ON if active open, off passive
                 -bit(2) = ON means timestamp option supported
                 -bit(3) = ON when select for read issued
                 -bit(4) = ON when select for write
                 -bit(5) = ON when select for exception
                 -bit(6) = ON means this is controlling
                 -bit(7) = ON if accept in progress
                 -bit(8) = ON means we are at OOB mark"
             ::= { ibmTcpipMvsTcpConnEntry 43 }

          ibmMvsTcpConnRttSeq OBJECT-TYPE
             SYNTAX   Counter32
             MAX-ACCESS   read-only
             STATUS   current
             DESCRIPTION
                "4 byte value for the TCP sequence number"
             ::= { ibmTcpipMvsTcpConnEntry 44 }

          ibmMvsTcpConnBackoffCount OBJECT-TYPE
             SYNTAX   Integer32
             MAX-ACCESS   read-only
             STATUS   obsolete
             DESCRIPTION
                "The value of this object will always be zero since
                 it currently isn't reported."
             DEFVAL  { 0 }
             ::= { ibmTcpipMvsTcpConnEntry 45 }

          ibmMvsTcpConnTcpDet OBJECT-TYPE
             SYNTAX   OCTET STRING (SIZE(1))
             MAX-ACCESS   read-only
             STATUS   obsolete
             DESCRIPTION
                "This flag will hold special TCP protocol
                 conditions:
                 - bit(1) = Delay Acks requested on PORT/PORTRANGE
                 - bit(2) = Delay Acks requested on GATEWAY
                 - bit(3) = Use default round trip parms
                 - bit(4) = Connection is one hop away
                 - bit(5) = Optimal max segment size request on
                            PORT/PORTRANGE
                 - bit(6) = FRCA conn deleted
                 - bit(7) = PASCAL Multi Client
                 - bit(8) = Load Balancing child"
             ::= { ibmTcpipMvsTcpConnEntry 46 }

          ibmMvsTcpConnTcpPol OBJECT-TYPE
             SYNTAX   OCTET STRING (SIZE(1))
             MAX-ACCESS   read-only
             STATUS   obsolete
             DESCRIPTION
                "This flag will indicates the following TCP
                 poll conditions:
                 - bit(1) = High priority data received
                 - bit(2) = <reserved>
                 - bit(3) = Written Normal
                 - bit(4) = <reserved>
                 - bit(5) = Reading Normal
                 - bit(6) = <reserved>
                 - bit(7) = <reserved>
                 - bit(8) = <reserved>"
             ::= { ibmTcpipMvsTcpConnEntry 47 }

          ibmMvsTcpConnTargetAppl OBJECT-TYPE
             SYNTAX   DisplayString (SIZE(0..8))
             MAX-ACCESS   read-only
             STATUS   current
             DESCRIPTION
                "When the corresponding TCP connection is for a
                 3172 Telnet session then this object contains the
                 Target VTAM Application name."
             ::= { ibmTcpipMvsTcpConnEntry 48 }

          ibmMvsTcpConnLuName OBJECT-TYPE
             SYNTAX   DisplayString (SIZE(0..8))
             MAX-ACCESS   read-only
             STATUS   current
             DESCRIPTION
                "When the corresponding TCP connection is for a
                 3172 Telnet session then this object contains the
                 VTAM LU name."
             ::= { ibmTcpipMvsTcpConnEntry 49 }

          ibmMvsTcpConnClientUserId OBJECT-TYPE
             SYNTAX   DisplayString (SIZE(0..8))
             MAX-ACCESS   read-only
             STATUS   current
             DESCRIPTION
                "When the corresponding TCP connection is for a
                 3172 Telnet session then this object contains the
                 Client's userid."
             ::= { ibmTcpipMvsTcpConnEntry 50 }

          ibmMvsTcpConnLogMode OBJECT-TYPE
             SYNTAX   DisplayString (SIZE(0..8))
             MAX-ACCESS   read-only
             STATUS   current
             DESCRIPTION
                "When the corresponding TCP connection is for a
                 3172 Telnet session then this object contains the
                 LOG Mode."
             ::= { ibmTcpipMvsTcpConnEntry 51 }

          ibmMvsTcpConnProto OBJECT-TYPE
             SYNTAX   OCTET STRING (SIZE(1))
             MAX-ACCESS   read-only
             STATUS   current
             DESCRIPTION
                "This flag will indicates the following Telnet modes:
                 -bit(1 - 5) = <reserved>
                 -bit(6)     = TN3270 mode
                 -bit(7)     = TN3270E mode
                 -bit(8)     = line mode"
            ::= { ibmTcpipMvsTcpConnEntry 52 }

          ibmMvsTcpConnDupacks OBJECT-TYPE
             SYNTAX   Unsigned32
             MAX-ACCESS   read-only
             STATUS   current
             DESCRIPTION
                "Number of duplicate ACKs received for this
                 connection."
             DEFVAL  { 0 }
             ::= { ibmTcpipMvsTcpConnEntry 53 }

          ibmMvsTcpConnOptMaxSegmentSize OBJECT-TYPE
             SYNTAX   Integer32
             MAX-ACCESS   read-only
             STATUS   current
             DESCRIPTION
                "Optimal maximum segment size. The range of this
                 value is from 0 to 65535."
             DEFVAL  { 0 }
             ::= { ibmTcpipMvsTcpConnEntry 54 }

          ibmMvsTcpConnClusterConnFlag OBJECT-TYPE
             SYNTAX   OCTET STRING (SIZE(1))
             MAX-ACCESS   read-only
             STATUS   current
             DESCRIPTION
                "This flag contains sysplex cluster connection types
                 for this connection:
                 -bit(1)     = getsockopt(clusterconntype) requested
                 -bit(2 - 4) = <reserved>
                 -bit(5)     = cluster internal
                 -bit(6)     = same image
                 -bit(7)     = same cluster
                 -bit(8)     = none"
            ::= { ibmTcpipMvsTcpConnEntry 55 }

          ibmMvsTcpConnInSegs   OBJECT-TYPE
             SYNTAX   Counter32
             MAX-ACCESS   read-only
             STATUS   current
             DESCRIPTION
                "The number of segments received from IP for this
                 connection."
             ::= { ibmTcpipMvsTcpConnEntry 56 }

          ibmMvsTcpConnOutSegs  OBJECT-TYPE
             SYNTAX   Counter32
             MAX-ACCESS   read-only
             STATUS   current
             DESCRIPTION
                "The number of segments sent to IP for this
                 connection."
             ::= { ibmTcpipMvsTcpConnEntry 57 }

          ibmMvsTcpConnDSField OBJECT-TYPE
             SYNTAX   OCTET STRING (SIZE(1))
             MAX-ACCESS   read-only
             STATUS   current
             DESCRIPTION
                "The Differentiated Services field value in effect
                 for this tcpConnTable entry.  The value may be
                 one of the following:
                  - If there is a Service Policy Agent policy in
                    effect for this entry, the value will be
                    either:
                      - The IPv4 TOS value defined by RFC 791 and 1349
                      - The Differentiated Services field value
                        defined by RFC 2474
                      - If there is no Service Policy Agent policy in
                        effect for this entry, the value will be 0."
             ::= { ibmTcpipMvsTcpConnEntry 58 }

          ibmMvsTcpConnSndBufSize OBJECT-TYPE
             SYNTAX   Unsigned32
             MAX-ACCESS   read-only
             STATUS   current
             DESCRIPTION
                "Send buffer size"
             DEFVAL  { 0 }
             ::= { ibmTcpipMvsTcpConnEntry 59 }

          ibmMvsTcpConnAcceptCount    OBJECT-TYPE
             SYNTAX   Counter32
             MAX-ACCESS   read-only
             STATUS   current
             DESCRIPTION
                "The total number of connections accepted
                 by this listener.  Applies only to listener
                 entries."
             ::= { ibmTcpipMvsTcpConnEntry 60 }

          ibmMvsTcpConnExceedBacklog  OBJECT-TYPE
             SYNTAX   Integer32
             MAX-ACCESS   read-only
             STATUS   current
             DESCRIPTION
                "The total number of connections dropped by this
                 listener due to backlog exceeded.  Applies only
                 to listener entries."
             ::= { ibmTcpipMvsTcpConnEntry 61 }

          ibmMvsTcpConnCurrBacklog  OBJECT-TYPE
             SYNTAX   Integer32
             MAX-ACCESS   read-only
             STATUS   current
             DESCRIPTION
                "The current number of connections in backlog.
                 Applies only to listener entries."
             ::= { ibmTcpipMvsTcpConnEntry 62 }

          ibmMvsTcpConnMaxBacklog  OBJECT-TYPE
             SYNTAX   Integer32
             MAX-ACCESS   read-only
             STATUS   current
             DESCRIPTION
                "The maximum number of connections allowed in
                 backlog at one time.  Applies only to
                 listener entries."
             ::= { ibmTcpipMvsTcpConnEntry 63 }

          ibmMvsTcpConnWindowScale OBJECT-TYPE
             SYNTAX   TruthValue
             MAX-ACCESS   read-only
             STATUS   current
             DESCRIPTION
                "If true(1), the TCP window scale option is active for
                 this connection.  If false(2), the TCP window scale
                 option is not active."
             ::= { ibmTcpipMvsTcpConnEntry 64 }

          ibmMvsTcpConnTimeStamp   OBJECT-TYPE
             SYNTAX   TruthValue
             MAX-ACCESS   read-only
             STATUS   current
             DESCRIPTION
                "If true(1), the TCP timestamp option is active for
                 this connection.  If false(2), the TCP timestamp
                 option is not active."
             ::= { ibmTcpipMvsTcpConnEntry 65 }

          ibmMvsTcpConnServerResourceId  OBJECT-TYPE
             SYNTAX   Unsigned32
             MAX-ACCESS   read-only
             STATUS   current
             DESCRIPTION
                "The numeric identification of the server (i.e.
                 listener connection) associated with this client
                 connection.  This value only applies to load
                 balancing servers which have bound to a port
                 number for which SHAREPORT was specified on the
                 PORT/PORTRANGE Profile statement.  This value
                 will be zero for client connections to servers
                 which are not load balancing servers.  The value
                 of this object can be used to retrieve the
                 listener entry from the ibmTcpipMvsTcpListenerTable."
             ::= { ibmTcpipMvsTcpConnEntry 66 }


     ibmMvsTcpConnsClosed    OBJECT-TYPE
     SYNTAX Counter32
     MAX-ACCESS read-only
     STATUS current
     DESCRIPTION
           "Number of TCP connections that have corresponding
            sockets closed."
     ::= { ibmTcpipMvsTcpGroup 2 }

     ibmMvsTcpPassiveDrops   OBJECT-TYPE
     SYNTAX Counter32
     MAX-ACCESS read-only
     STATUS current
     DESCRIPTION
           "Number of passive connection requests discarded."
     ::= { ibmTcpipMvsTcpGroup 3 }

     ibmMvsTcpTimeWaitReused OBJECT-TYPE
     SYNTAX Counter32
     MAX-ACCESS read-only
     STATUS current
     DESCRIPTION
           "Number of TCP connections in the TIMEWAIT state
            that have been reused for connections in the
            SYN-RCVD state."
     ::= { ibmTcpipMvsTcpGroup 4 }

     ibmMvsTcpPredictAck     OBJECT-TYPE
     SYNTAX Counter32
     MAX-ACCESS read-only
     STATUS current
     DESCRIPTION
           "Number of inbound TCP acknowledgements with successful
            header prediction."
     ::= { ibmTcpipMvsTcpGroup 5 }

     ibmMvsTcpPredictData    OBJECT-TYPE
     SYNTAX Counter32
     MAX-ACCESS read-only
     STATUS current
     DESCRIPTION
           "Number of inbound TCP data segments with successful
            header prediction."
     ::= { ibmTcpipMvsTcpGroup 6 }

     ibmMvsTcpInDupAck       OBJECT-TYPE
     SYNTAX Counter32
     MAX-ACCESS read-only
     STATUS current
     DESCRIPTION
           "Number of inbound duplicate TCP acknowledgements."
     ::= { ibmTcpipMvsTcpGroup 7 }

     ibmMvsTcpInBadSum       OBJECT-TYPE
     SYNTAX Counter32
     MAX-ACCESS read-only
     STATUS current
     DESCRIPTION
           "Number of inbound TCP segments discarded due to
            bad checksum."
     ::= { ibmTcpipMvsTcpGroup 8 }

     ibmMvsTcpInBadLen       OBJECT-TYPE
     SYNTAX Counter32
     MAX-ACCESS read-only
     STATUS current
     DESCRIPTION
           "Number of inbound TCP segments discarded due to
            bad header len."
     ::= { ibmTcpipMvsTcpGroup 9 }

     ibmMvsTcpInShort        OBJECT-TYPE
     SYNTAX Counter32
     MAX-ACCESS read-only
     STATUS current
     DESCRIPTION
           "Number of inbound TCP data segments discarded due
            to data length shorter than segment length."
     ::= { ibmTcpipMvsTcpGroup 10 }

     ibmMvsTcpInPawsDrop     OBJECT-TYPE
     SYNTAX Counter32
     MAX-ACCESS read-only
     STATUS current
     DESCRIPTION
           "Number of inbound TCP data segments discarded due
            to old timestamp."
     ::= { ibmTcpipMvsTcpGroup 11 }

     ibmMvsTcpInAllBeforeWin  OBJECT-TYPE
     SYNTAX Counter32
     MAX-ACCESS read-only
     STATUS current
     DESCRIPTION
           "Number of inbound TCP data segments with all data
            before current TCP window."
     ::= { ibmTcpipMvsTcpGroup 12 }

     ibmMvsTcpInSomeBeforeWin OBJECT-TYPE
     SYNTAX Counter32
     MAX-ACCESS read-only
     STATUS current
     DESCRIPTION
           "Number of inbound TCP data segments with some data
            before current TCP window."
     ::= { ibmTcpipMvsTcpGroup 13 }

     ibmMvsTcpInAllAfterWin   OBJECT-TYPE
     SYNTAX Counter32
     MAX-ACCESS read-only
     STATUS current
     DESCRIPTION
           "Number of inbound TCP data segments with all data
            after current TCP window."
     ::= { ibmTcpipMvsTcpGroup 14 }

     ibmMvsTcpInSomeAfterWin  OBJECT-TYPE
     SYNTAX Counter32
     MAX-ACCESS read-only
     STATUS current
     DESCRIPTION
           "Number of inbound TCP data segments with some data
            after current TCP window."
     ::= { ibmTcpipMvsTcpGroup 15 }

     ibmMvsTcpInOutOfOrder    OBJECT-TYPE
     SYNTAX Counter32
     MAX-ACCESS read-only
     STATUS current
     DESCRIPTION
           "Number of inbound TCP data segments that did not
            contain the next expected sequence number
            (ie. out-of-order)."
     ::= { ibmTcpipMvsTcpGroup 16 }

     ibmMvsTcpInAfterClose    OBJECT-TYPE
     SYNTAX Counter32
     MAX-ACCESS read-only
     STATUS current
     DESCRIPTION
           "Number of inbound TCP data segments received after
            corresponding sockets have been closed."
     ::= { ibmTcpipMvsTcpGroup 17 }

     ibmMvsTcpInWinProbes     OBJECT-TYPE
     SYNTAX Counter32
     MAX-ACCESS read-only
     STATUS current
     DESCRIPTION
           "Number of inbound TCP segments processed while
            current receive window size is zero."
     ::= { ibmTcpipMvsTcpGroup 18 }

     ibmMvsTcpInWinUpdates    OBJECT-TYPE
     SYNTAX Counter32
     MAX-ACCESS read-only
     STATUS current
     DESCRIPTION
           "Number of inbound TCP segments that only change
            receive window size."
     ::= { ibmTcpipMvsTcpGroup 19 }

     ibmMvsTcpOutWinUpdates    OBJECT-TYPE
     SYNTAX Counter32
     MAX-ACCESS read-only
     STATUS current
     DESCRIPTION
           "Number of outbound TCP segments that only change
            receive window size."
     ::= { ibmTcpipMvsTcpGroup 20 }

     ibmMvsTcpOutDelayAcks     OBJECT-TYPE
     SYNTAX Counter32
     MAX-ACCESS read-only
     STATUS current
     DESCRIPTION
           "Number of delayed outbound TCP acknowledgements."
     ::= { ibmTcpipMvsTcpGroup 21 }

     ibmMvsTcpOutWinProbes     OBJECT-TYPE
     SYNTAX Counter32
     MAX-ACCESS read-only
     STATUS current
     DESCRIPTION
           "Number of outbound window probe requests."
     ::= { ibmTcpipMvsTcpGroup 22 }

     ibmMvsTcpRxmtTimers       OBJECT-TYPE
     SYNTAX Counter32
     MAX-ACCESS read-only
     STATUS current
     DESCRIPTION
           "Number of TCP retransmit timer pops."
     ::= { ibmTcpipMvsTcpGroup 23 }

     ibmMvsTcpRxmtDrops        OBJECT-TYPE
     SYNTAX Counter32
     MAX-ACCESS read-only
     STATUS current
     DESCRIPTION
           "Number of TCP connections dropped due to retransmit
            threshold exceeded."
     ::= { ibmTcpipMvsTcpGroup 24 }

     ibmMvsTcpPMTURxmts        OBJECT-TYPE
     SYNTAX Counter32
     MAX-ACCESS read-only
     STATUS current
     DESCRIPTION
           "Number of outbound TCP segments retransmitted due
            to path MTU discovery."
     ::= { ibmTcpipMvsTcpGroup 25 }

     ibmMvsTcpPMTUErrors       OBJECT-TYPE
     SYNTAX Counter32
     MAX-ACCESS read-only
     STATUS current
     DESCRIPTION
           "Number of TCP connections that exceeded path MTU
            discovery retransmit threshold."
     ::= { ibmTcpipMvsTcpGroup 26 }

     ibmMvsTcpProbeDrops       OBJECT-TYPE
     SYNTAX Counter32
     MAX-ACCESS read-only
     STATUS current
     DESCRIPTION
           "Number of TCP connections dropped due to no response
            while sending window probe requests."
     ::= { ibmTcpipMvsTcpGroup 27 }

     ibmMvsTcpKeepAliveProbes  OBJECT-TYPE
     SYNTAX Counter32
     MAX-ACCESS read-only
     STATUS current
     DESCRIPTION
           "Number of keepalive probe requests."
     ::= { ibmTcpipMvsTcpGroup 28 }

     ibmMvsTcpKeepAliveDrops   OBJECT-TYPE
     SYNTAX Counter32
     MAX-ACCESS read-only
     STATUS current
     DESCRIPTION
           "Number of TCP connections dropped due to no response
            while sending keepalive probe requests."
     ::= { ibmTcpipMvsTcpGroup 29 }

     ibmMvsTcpFinwait2Drops    OBJECT-TYPE
     SYNTAX Counter32
     MAX-ACCESS read-only
     STATUS current
     DESCRIPTION
           "Number of TCP connections dropped due to FINWAIT2 timer
            expiring prior to receiving FIN segment."
     ::= { ibmTcpipMvsTcpGroup 30 }

 -- ibmTcpipMvsTcpListenerTable

     ibmTcpipMvsTcpListenerTable OBJECT-TYPE
     SYNTAX SEQUENCE OF IbmTcpipMvsTcpListenerEntry
     MAX-ACCESS not-accessible
     STATUS current
     DESCRIPTION
          "Provides TCP connection information for connections in
           Listen state.  Connections in this state are assumed to
           be servers so only server MIB objects are supported."
     ::= { ibmTcpipMvsTcpGroup 31 }

     ibmTcpipMvsTcpListenerEntry OBJECT-TYPE
     SYNTAX IbmTcpipMvsTcpListenerEntry
     MAX-ACCESS not-accessible
     STATUS current
     DESCRIPTION
          "Descibes a particular tcp listener entry."
     INDEX { ibmMvsTcpListenerResourceId }
     ::= { ibmTcpipMvsTcpListenerTable 1 }

     IbmTcpipMvsTcpListenerEntry ::=
          SEQUENCE
          {
          ibmMvsTcpListenerResourceId     Unsigned32,
          ibmMvsTcpListenerLocalAddrType  InetAddressType,
          ibmMvsTcpListenerLocalAddr      InetAddress,
          ibmMvsTcpListenerLocalPort      INTEGER,
          ibmMvsTcpListenerRemoteAddrType InetAddressType,
          ibmMvsTcpListenerRemoteAddr     InetAddress,
          ibmMvsTcpListenerRemotePort     INTEGER,
          ibmMvsTcpListenerAcceptCount    Counter32,
          ibmMvsTcpListenerExceedBacklog  Integer32,
          ibmMvsTcpListenerCurrBacklog    Integer32,
          ibmMvsTcpListenerMaxBacklog     Integer32,
          ibmMvsTcpListenerResourceName   SnmpAdminString
          }

     ibmMvsTcpListenerResourceId  OBJECT-TYPE
        SYNTAX   Unsigned32
        MAX-ACCESS   not-accessible
        STATUS   current
        DESCRIPTION
           "Resource ID is the numeric identification of this
            resource.  This value is also known as the
            connection ID."
        ::= { ibmTcpipMvsTcpListenerEntry 1 }

     ibmMvsTcpListenerLocalAddrType   OBJECT-TYPE
         SYNTAX      InetAddressType
         MAX-ACCESS  read-only
         STATUS      current
         DESCRIPTION
            "The IP address type of the
             ibmMvsTcpListenerLocalAddr object."
         ::= { ibmTcpipMvsTcpListenerEntry 2 }

     ibmMvsTcpListenerLocalAddr   OBJECT-TYPE
         SYNTAX      InetAddress  (SIZE (1..20))
         MAX-ACCESS  read-only
         STATUS      current
         DESCRIPTION
            "The local IP address for this TCP connection.  In
             the case of a connection in the listen state which is
             willing to accept connections for any IP interface
             associated with the node, the value 0.0.0.0 is used."
         ::= { ibmTcpipMvsTcpListenerEntry 3 }

     ibmMvsTcpListenerLocalPort  OBJECT-TYPE
         SYNTAX      INTEGER (0..65535)
         MAX-ACCESS  read-only
         STATUS      current
         DESCRIPTION
            "The local port number for this TCP connection."
         ::= { ibmTcpipMvsTcpListenerEntry 4 }

     ibmMvsTcpListenerRemoteAddrType  OBJECT-TYPE
         SYNTAX      InetAddressType
         MAX-ACCESS  read-only
         STATUS      current
         DESCRIPTION
            "The IP address type of the
             ibmMvsTcpListenerRemoteAddr object."
         ::= { ibmTcpipMvsTcpListenerEntry 5 }

     ibmMvsTcpListenerRemoteAddr  OBJECT-TYPE
         SYNTAX      InetAddress  (SIZE (1..20))
         MAX-ACCESS  read-only
         STATUS      current
         DESCRIPTION
            "The remote ip address for this TCP connection."
         ::= { ibmTcpipMvsTcpListenerEntry 6 }

     ibmMvsTcpListenerRemotePort OBJECT-TYPE
         SYNTAX      INTEGER (0..65535)
         MAX-ACCESS  read-only
         STATUS      current
         DESCRIPTION
            "The remote port number for this TCP connection."
         ::= { ibmTcpipMvsTcpListenerEntry 7 }

     ibmMvsTcpListenerAcceptCount OBJECT-TYPE
        SYNTAX   Counter32
        MAX-ACCESS   read-only
        STATUS   current
        DESCRIPTION
           "The total number of connections accepted
            by this listener."
        ::= { ibmTcpipMvsTcpListenerEntry 8 }

     ibmMvsTcpListenerExceedBacklog OBJECT-TYPE
        SYNTAX   Integer32
        MAX-ACCESS   read-only
        STATUS   current
        DESCRIPTION
           "The total number of connections dropped by this
            listener due to backlog exceeded."
        ::= { ibmTcpipMvsTcpListenerEntry 9 }

     ibmMvsTcpListenerCurrBacklog OBJECT-TYPE
        SYNTAX   Integer32
        MAX-ACCESS   read-only
        STATUS   current
        DESCRIPTION
           "The current number of connections in backlog."
        ::= { ibmTcpipMvsTcpListenerEntry 10 }

     ibmMvsTcpListenerMaxBacklog OBJECT-TYPE
        SYNTAX   Integer32
        MAX-ACCESS   read-only
        STATUS   current
        DESCRIPTION
           "The maximum number of connections allowed in
            backlog at one time."
        ::= { ibmTcpipMvsTcpListenerEntry 11 }

     ibmMvsTcpListenerResourceName OBJECT-TYPE
        SYNTAX   SnmpAdminString (SIZE(0..8))
        MAX-ACCESS   read-only
        STATUS   current
        DESCRIPTION
           "Resource Name is the text identification of this
            resource. It represents the user who opened the
            socket and is updated again during the bind
            processing."
        ::= { ibmTcpipMvsTcpListenerEntry 12 }

 ---------------------------------------------------------------------
 -- ibmTcpipMvsUdpGroup3
 ---------------------------------------------------------------------

     ibmTcpipMvsUdpTable OBJECT-TYPE
     SYNTAX SEQUENCE OF IbmTcpipMvsUdpEntry
     MAX-ACCESS not-accessible
     STATUS current
     DESCRIPTION
          "Extends udp table to support additional UDP
           listener information."
     ::= { ibmTcpipMvsUdpGroup 1 }

     ibmTcpipMvsUdpEntry OBJECT-TYPE
     SYNTAX IbmTcpipMvsUdpEntry
     MAX-ACCESS not-accessible
     STATUS current
     DESCRIPTION
          "Descibes a particular udp entry."
     AUGMENTS { udpEntry }
     ::= { ibmTcpipMvsUdpTable 1 }

     IbmTcpipMvsUdpEntry ::=
          SEQUENCE
          {
          ibmMvsUdpLastAct        TimeTicks,
          ibmMvsUdpTos             TypeOfService,
          ibmMvsUdpIpOpts          OCTET STRING,
          ibmMvsUdpDgramIn         Counter32,
          ibmMvsUdpBytesIn         Counter32,
          ibmMvsUdpDgramOut        Counter32,
          ibmMvsUdpBytesOut        Counter32,
          ibmMvsUdpResourceName    DisplayString,
          ibmMvsUdpSubtask         Unsigned32,
          ibmMvsUdpResourceId      Unsigned32,
          ibmMvsUdpSockOpt         OCTET STRING,
          ibmMvsUdpSendLim         Unsigned32,
          ibmMvsUdpRecvLim         Unsigned32,
          ibmMvsUdpEntryState      INTEGER,
          ibmMvsUdpMcastTTL        Integer32,
          ibmMvsUdpMcastLoopback   TruthValue,
          ibmMvsUdpMcastLinkAddr   IpAddress,
          ibmMvsUdpDSField         OCTET STRING (SIZE(1))
          }

     ibmMvsUdpLastAct OBJECT-TYPE
        SYNTAX   TimeTicks
        MAX-ACCESS   read-only
        STATUS   current
        DESCRIPTION
           "The amount of time that has elapsed since the corresponding
            entry has had any activity. Measured in hundreds of
            seconds."
        DEFVAL  { 0 }
        ::= { ibmTcpipMvsUdpEntry 1 }

     ibmMvsUdpTos OBJECT-TYPE
        SYNTAX   TypeOfService
        MAX-ACCESS   read-only
        STATUS   obsolete
        DESCRIPTION
           "The type of service in effect for this entry. Currently,
            not supported and will return a zero when retrieved."
        DEFVAL  { 0 }
        ::= { ibmTcpipMvsUdpEntry 2 }

     ibmMvsUdpIpOpts OBJECT-TYPE
        SYNTAX   OCTET STRING (SIZE(40))
        MAX-ACCESS   read-only
        STATUS   current
        DESCRIPTION
           "IP Options (see RFC 791)"
        ::= { ibmTcpipMvsUdpEntry 3 }

     ibmMvsUdpDgramIn OBJECT-TYPE
        SYNTAX   Counter32
        MAX-ACCESS   read-only
        STATUS   current
        DESCRIPTION
           "Number of received datagrams."
        ::= { ibmTcpipMvsUdpEntry 4 }

     ibmMvsUdpBytesIn OBJECT-TYPE
        SYNTAX   Counter32
        MAX-ACCESS   read-only
        STATUS   current
        DESCRIPTION
           "Number of bytes received."
        ::= { ibmTcpipMvsUdpEntry 5 }

     ibmMvsUdpDgramOut OBJECT-TYPE
        SYNTAX   Counter32
        MAX-ACCESS   read-only
        STATUS   current
        DESCRIPTION
           "Number of send datagrams."
        ::= { ibmTcpipMvsUdpEntry 6 }

     ibmMvsUdpBytesOut OBJECT-TYPE
        SYNTAX   Counter32
        MAX-ACCESS   read-only
        STATUS   current
        DESCRIPTION
           "Number of bytes sent."
        ::= { ibmTcpipMvsUdpEntry 7 }

     ibmMvsUdpResourceName OBJECT-TYPE
        SYNTAX   DisplayString (SIZE(0..8))
        MAX-ACCESS   read-only
        STATUS   current
        DESCRIPTION
           "Resource Name is the text identification of this
            resource. It represents the ?itName value of the
            associating resource's relationship with the UDP
            Stack."
        ::= { ibmTcpipMvsUdpEntry 8 }

     ibmMvsUdpSubtask OBJECT-TYPE
        SYNTAX   Unsigned32
        MAX-ACCESS   read-only
        STATUS   current
        DESCRIPTION
           "4 bytes hex decimal"
        DEFVAL  { 0 }
        ::= { ibmTcpipMvsUdpEntry 9 }

     ibmMvsUdpResourceId OBJECT-TYPE
        SYNTAX   Unsigned32
        MAX-ACCESS   read-only
        STATUS   current
        DESCRIPTION
           "Resource ID is the numeric identification of this
            resource."
        DEFVAL  { 0 }
        ::= { ibmTcpipMvsUdpEntry 10 }

     ibmMvsUdpSockOpt OBJECT-TYPE
        SYNTAX   OCTET STRING (SIZE(1))
        MAX-ACCESS   read-only
        STATUS   current
        DESCRIPTION
          "flag for socket options (1 byte hex valuel)
          -bit(1) = allow broadcast address
          -bit(2) = allow loopback of datagrams
          -bit(3) = bypass normal routing
          -bit(4) = forward ICMP message (Pascal)
          -bit(5) = outgoing multicast datagrams
          -bit(6) = incoming multicast datagrams
          -bit(7) = <reserved>
          -bit(8) = <reserved>"
        ::= { ibmTcpipMvsUdpEntry 11 }

     ibmMvsUdpSendLim OBJECT-TYPE
        SYNTAX   Unsigned32
        MAX-ACCESS   read-only
        STATUS   current
        DESCRIPTION
           "maximum transmit datagram size "
        DEFVAL  { 0 }
        ::= { ibmTcpipMvsUdpEntry 12 }

     ibmMvsUdpRecvLim OBJECT-TYPE
        SYNTAX   Unsigned32
        MAX-ACCESS   read-only
        STATUS   current
        DESCRIPTION
           "maximum received datagram size"
        DEFVAL  { 0 }
        ::= { ibmTcpipMvsUdpEntry 13 }

     ibmMvsUdpEntryState OBJECT-TYPE
        SYNTAX   INTEGER   {
                              active(1),
                              delete(2)
                           }
        MAX-ACCESS   read-write
        STATUS   current
        DESCRIPTION
           "A entry's state will always be active unless it is
            to be deleted. This is accomplished by setting this
            object to delete. A set of active is invalid."
        DEFVAL  { active }
        ::= { ibmTcpipMvsUdpEntry 14 }

     ibmMvsUdpMcastTTL OBJECT-TYPE
        SYNTAX   Integer32
        MAX-ACCESS   read-only
        STATUS   current
        DESCRIPTION
           "Time-to-live value for a multicast datagram."
        DEFVAL  { 1 }
        ::= { ibmTcpipMvsUdpEntry 15 }

     ibmMvsUdpMcastLoopback  OBJECT-TYPE
        SYNTAX   TruthValue
        MAX-ACCESS   read-only
        STATUS   current
        DESCRIPTION
           "If true(1), indicates that loopback is enabled for
            outbound multicast datagrams.  If false(2), indicates
            either that loopback is disabled for outbound multicast
            datagrams or that the socket is not processing
            outgoing multicast datagrams.  The value of object
            ibmMvsUdpSockOpt will indicate whether or not the
            socket is processing outgoing multicast datagrams."
        ::= { ibmTcpipMvsUdpEntry 16 }


     ibmMvsUdpMcastLinkAddr  OBJECT-TYPE
        SYNTAX   IpAddress
        MAX-ACCESS   read-only
        STATUS   current
        DESCRIPTION
           "IP address of the interface used for outbound multicast
            datagrams."
        ::= { ibmTcpipMvsUdpEntry 17 }

     ibmMvsUdpDSField OBJECT-TYPE
        SYNTAX   OCTET STRING (SIZE(1))
        MAX-ACCESS   read-only
        STATUS   current
        DESCRIPTION
           "The Differentiated Services field value in effect
            for this udpTable entry.  The value may be one
            of the following:
             - If there is a Service Policy Agent policy in
               effect for this entry, the value will be
               either:
                 - The IPv4 TOS value defined by RFC 791 and 1349
                 - The Differentiated Services field value
                   defined by RFC 2474
             - If there is no Service Policy Agent policy in
               effect for this entry, but the entry is being
               used for an Enterprise Extender connection, the
               value will be one of the following VTAM IP Type of
               Service values in hexadecimal.  See the SNA Network
               Implementation Guide for a descripton of VTAM
               IP Type of Service):
                  20 - Low
                  40 - Medium
                  80 - High
                  C0 - Network
             - If neither of the above are true, then this value
               will be 0."
        ::= { ibmTcpipMvsUdpEntry 18 }

 ---------------------------------------------------------------------
 -- ibmTcpipMvsUdpMcastRecvTable
 ---------------------------------------------------------------------

     ibmTcpipMvsUdpMcastRecvTable OBJECT-TYPE
     SYNTAX SEQUENCE OF IbmTcpipMvsUdpMcastRecvEntry
     MAX-ACCESS not-accessible
     STATUS current
     DESCRIPTION
          "The table listing UDP sockets that receive multicast data.
           The table is ordered by the interface being used by the
           socket for incoming datagrams, the UDP socket (local
           IP address and port), and the mulitcast group to which
           the socket is registerd."
     ::= { ibmTcpipMvsUdpGroup 2 }

     ibmTcpipMvsUdpMcastRecvEntry OBJECT-TYPE
     SYNTAX IbmTcpipMvsUdpMcastRecvEntry
     MAX-ACCESS not-accessible
     STATUS current
     DESCRIPTION
          "Entry defining a UDP socket that receives multicast data."
     INDEX { ibmMvsUdpMcastRecvLocalAddress,
             ibmMvsUdpMcastRecvLocalPort, ibmMvsUdpMcastRecvGroup,
             ibmMvsUdpMcastRecvLinkAddr }
     ::= { ibmTcpipMvsUdpMcastRecvTable 1 }

     IbmTcpipMvsUdpMcastRecvEntry ::=  SEQUENCE {
          ibmMvsUdpMcastRecvLocalAddress   IpAddress,
          ibmMvsUdpMcastRecvLocalPort      INTEGER,
          ibmMvsUdpMcastRecvGroup          IpAddress,
          ibmMvsUdpMcastRecvLinkAddr       IpAddress
     }

     ibmMvsUdpMcastRecvLocalAddress OBJECT-TYPE
         SYNTAX      IpAddress
         MAX-ACCESS  not-accessible
         STATUS      current
         DESCRIPTION
                 "The local IP address for this UDP listener.  In the
                 case of a UDP listener which is willing to accept
                 datagrams for any IP interface associated with the
                 node, the value 0.0.0.0 is used."
         ::= { ibmTcpipMvsUdpMcastRecvEntry 1 }

     ibmMvsUdpMcastRecvLocalPort OBJECT-TYPE
         SYNTAX      INTEGER (0..65535)
         MAX-ACCESS  not-accessible
         STATUS      current
         DESCRIPTION
                 "The local port number for this UDP listener."
         ::= { ibmTcpipMvsUdpMcastRecvEntry 2 }

     ibmMvsUdpMcastRecvGroup OBJECT-TYPE
        SYNTAX IpAddress
        MAX-ACCESS not-accessible
        STATUS current
        DESCRIPTION
             "Specifies the IP address of the multicast group"
        ::= { ibmTcpipMvsUdpMcastRecvEntry 3 }

     ibmMvsUdpMcastRecvLinkAddr  OBJECT-TYPE
        SYNTAX IpAddress
        MAX-ACCESS read-only
        STATUS current
        DESCRIPTION
             "The IP address of the interface used for incoming
              packets for this multicast group on this socket."
        ::= { ibmTcpipMvsUdpMcastRecvEntry 4 }

 ---------------------------------------------------------------------
 -- ibmTcpipMvsIpGroup
 ---------------------------------------------------------------------

     ibmMvsIpInDevLayerCalls   OBJECT-TYPE
     SYNTAX Counter32
     MAX-ACCESS read-only
     STATUS current
     DESCRIPTION
           "Number of times the inbound TCP/IP Data Path has received
            control from the Device Layer. This counter may be less
            than the number of packets received (ipInReceives), as a
            single inbound call may process several inbound packets."
     ::= { ibmTcpipMvsIpGroup 1 }

     ibmMvsIpInUnpackErrors    OBJECT-TYPE
     SYNTAX Counter32
     MAX-ACCESS read-only
     STATUS current
     DESCRIPTION
           "Number of times a received frame could not be unpacked
            into its consistuent datagrams, resulting in packet
            loss.  A non-zero value in this counter may be evidence
            of a buffer-formatting problem within a device."
     ::= { ibmTcpipMvsIpGroup 2 }

     ibmMvsIpInDiscardsMemory  OBJECT-TYPE
     SYNTAX Counter32
     MAX-ACCESS read-only
     STATUS current
     DESCRIPTION
           "Number of inbound packets discarded due to a CSM
            storage shortage."
     ::= { ibmTcpipMvsIpGroup 3 }

     ibmMvsIpOutDiscardsDlcSynch  OBJECT-TYPE
     SYNTAX Counter32
     MAX-ACCESS read-only
     STATUS current
     DESCRIPTION
           "Number of outbound packets discarded due to a
            synchronous error in the Data Link Control.
            Synchronous DLC errors are detected on the interface
            between TCP/IP and VTAM, and are typically not
            related to channel or device errors."
     ::= { ibmTcpipMvsIpGroup 4 }

     ibmMvsIpOutDiscardsDlcAsynch  OBJECT-TYPE
     SYNTAX Counter32
     MAX-ACCESS read-only
     STATUS current
     DESCRIPTION
           "Number of outbound packets discarded due to an
            asynchronous error in the Data Link Control.
            Asynchronous DLC errors may occur for a variety of
            reasons, including channel/device errors,
            incorrectly formatted data, or storage shortage
            within VTAM."
     ::= { ibmTcpipMvsIpGroup 5 }

     ibmMvsIpOutDiscardsMemory  OBJECT-TYPE
     SYNTAX Counter32
     MAX-ACCESS read-only
     STATUS current
     DESCRIPTION
           "Number of outbound packets discarded due to a CSM
            storage shortage."
     ::= { ibmTcpipMvsIpGroup 6 }

 ---------------------------------------------------------------------
 -- ibmTcpipMvsOsaExpGroup
 ---------------------------------------------------------------------

 -- osaexpChannelTable

     osaexpChannelTable OBJECT-TYPE
     SYNTAX SEQUENCE OF OsaexpChannelEntry
     MAX-ACCESS not-accessible
     STATUS current
     DESCRIPTION
        "One entry in this table will exist per OSA-Express
         Device Interface.  If the values for objects
         ibmMvsOsaExpCurLparName/Num are not the same as the values
         for objects ibmMvsOsaExpManLparName/Num then the OSA/SF
         running in the current LPAR is not the managing OSA/SF for
         this Device.  The utilization object values will be reset
         when the CHPID is reset.  The processor utilization
         objects are the sum of the per LPAR processor utilization
         values in the corresponding osaexpPerfTable entries for
         the adapter."
     ::= { ibmTcpipMvsOsaExpGroup 1 }

     osaexpChannelEntry OBJECT-TYPE
     SYNTAX OsaexpChannelEntry
     MAX-ACCESS not-accessible
     STATUS current
     DESCRIPTION
        "Definition of a single entry in the osaexpChannelTable.
         Indexed by the ifIndex of the corresponding DEVICE interface."
     INDEX { ifIndex }
     ::= { osaexpChannelTable 1 }

     OsaexpChannelEntry ::=
     SEQUENCE
       {
       ibmMvsOsaExpChannelNumber                Integer32,
       ibmMvsOsaExpChannelType                  INTEGER,
       ibmMvsOsaExpChannelSubType               INTEGER,
       ibmMvsOsaExpChannelMode                  INTEGER,
       ibmMvsOsaExpChannelState                 INTEGER,
       ibmMvsOsaExpChannelShared                INTEGER,
       ibmMvsOsaExpChannelNumPorts              Integer32,
       ibmMvsOsaExpChannelDeterNodeDesc         OCTET STRING,
       ibmMvsOsaExpChannelControlUnitNumber     OCTET STRING (SIZE(2)),
       ibmMvsOsaExpChannelCodeLevel             OCTET STRING (SIZE(2)),
       ibmMvsOsaExpChannelCurLparName           DisplayString,
       ibmMvsOsaExpChannelCurLparNum            Integer32,
       ibmMvsOsaExpChannelManLparName           DisplayString,
       ibmMvsOsaExpChannelManLparNum            Integer32,
       ibmMvsOsaExpChannelPCIBusUtil1Min        Integer32,
       ibmMvsOsaExpChannelProcessorUtil1Min     Integer32,
       ibmMvsOsaExpChannelPCIBusUtil5Min        Integer32,
       ibmMvsOsaExpChannelProcessorUtil5Min     Integer32,
       ibmMvsOsaExpChannelPCIBusUtilHour        Integer32,
       ibmMvsOsaExpChannelProcessorUtilHour     Integer32
       }

     ibmMvsOsaExpChannelNumber OBJECT-TYPE
     SYNTAX Integer32
     MAX-ACCESS read-only
     STATUS current
     DESCRIPTION
           "The channel number for this interface."
     ::= { osaexpChannelEntry 1 }

     ibmMvsOsaExpChannelType OBJECT-TYPE
     SYNTAX INTEGER {
                      ose(16),
                      osd(17)
                    }
     MAX-ACCESS read-only
     STATUS current
     DESCRIPTION
           "For OSA-Express adapters supporting QDIO mode, the value
            will be osd(17).  For OSA-Express adapters supporting
            non-QDIO mode, the value will be ose(16)."
     ::= { osaexpChannelEntry 2 }

     ibmMvsOsaExpChannelSubType OBJECT-TYPE
     SYNTAX INTEGER {
                      unknown(1),
                      gigabit(2),
                      fastEthernet(3),
                      atmNative(4),
                      atmLanEmulation(5),
                      noPortsDefined(6),
                      oneLogicalEthPort(7),
                      oneLogicalTokenRingPort(8),
                      twoLogicalEthPorts(9),
                      twoLogicalTokenRingPorts(10),
                      logicalEthernetAndTokenRingPorts(11),
                      logicalTokenRingAndEthPorts(12)
                    }
     MAX-ACCESS read-only
     STATUS current
     DESCRIPTION
           "Indicates how the channel is configured."
     ::= { osaexpChannelEntry 3 }

     ibmMvsOsaExpChannelMode OBJECT-TYPE
     SYNTAX INTEGER {
                       nothingConfigured(1),
                       passthruMode(2),
                       snaMode(3),
                       passthruAndSna(4),
                       atmLePassthru(5),
                       atmLeSna(6),
                       atmLePassthruAndSna(7),
                       atmNative(8),
                       atmLe(9)
                    }
     MAX-ACCESS read-only
     STATUS current
     DESCRIPTION
           "Configured mode of the OSA-Express adapter.  This value
            will be set to nothingConfigured(1) for QDIO adapters
            that are not configured for LAN Emulation."
     ::= { osaexpChannelEntry 4 }

     ibmMvsOsaExpChannelState     OBJECT-TYPE
     SYNTAX INTEGER {
                           online(1),
                           notinst(3),
                           offline(5)
                         }
     MAX-ACCESS read-only
     STATUS current
     DESCRIPTION
           "Hardware channel state: online, not installed,
            or offline."
     ::= { osaexpChannelEntry 5 }

     ibmMvsOsaExpChannelShared    OBJECT-TYPE
     SYNTAX INTEGER { no(0), yes(1) }
     MAX-ACCESS read-only
     STATUS current
     DESCRIPTION
           "An OSA-Express Channel can be shared across multiple
            LPARs. This object indicates if this channel
            is currently being shared."
     ::= { osaexpChannelEntry 6 }

     ibmMvsOsaExpChannelNumPorts    OBJECT-TYPE
     SYNTAX Integer32
     MAX-ACCESS read-only
     STATUS current
     DESCRIPTION
           "Number of ports on the OSA-Express adapter. For non-ATM
            adapters, the value reflects the number of physical
            ports.  For ATM adapters the value reflects the number
            of logical ports.  For ATM155 Native mode adapters,
            the value should be 1.  For ATM155 QDIO LAN Emulation
            mode adapters, the value can be 1 or 2 depending on
            the number of logical ports configured."
     ::= { osaexpChannelEntry 7 }

     ibmMvsOsaExpChannelDeterNodeDesc OBJECT-TYPE
     SYNTAX  OCTET STRING (SIZE(32))
     MAX-ACCESS read-only
     STATUS current
     DESCRIPTION
           "Describes the generic node descriptor layout.
            This object represents the ND obtained from the
            CHSC instruction:
                                       /* ND Flags                */
            int   bValidity      :3;   /* 1:is ND valid           */
            int   bNodeType      :1;   /* 1:0=dev,1=chnlsubstm nod*/
            int   bInternal      :1;   /* internal(1)/external(0) */
            int   bCHPinvalid    :1;   /* IF =1,NDCHPID is invalid*/
            int   bNDRsvd1       :2;   /* spare bits for alignment*/
            char  NDType;              /* reserved by architecture*/
            char  NDClass;             /* Class for subsystem node*/
            char  NDCHPID;             /* CHP ID for specified int*/
            char  NDTypeNum 6 ;        /* type number of the SDC  */
            char  NDModelNum 3 ;       /* ND model number in the
                                          form of 3 EBCDIC OCTETS */
            char  NDMfgr 3 ;           /* ND manufacturer in the
                                          form of 3 EBCDIC OCTETS */
            char  NDMfgrPlant 2 ;      /* ND plant of manufacture
                                          (2 EBCDIC OCTETS)       */
            char  NDSeqNum 12 ;        /* ND sequence number
                                          (12 EBCDIC OCTETS)      */
            char  NDTag 2 ;            /* ND tag                  */"
     ::= { osaexpChannelEntry 8 }

     ibmMvsOsaExpChannelControlUnitNumber OBJECT-TYPE
     SYNTAX  OCTET STRING (SIZE(2))
     MAX-ACCESS read-only
     STATUS current
     DESCRIPTION
           "The control unit number associated with the
            OSA-Express Channel."
     ::= { osaexpChannelEntry 9 }

     ibmMvsOsaExpChannelCodeLevel OBJECT-TYPE
     SYNTAX  OCTET STRING (SIZE(2))
     MAX-ACCESS read-only
     STATUS current
     DESCRIPTION
           "ibmMvsOsaExpChannelCodeLevel is the firmware
            (or micro code level) of the OSA adapter. For example,
            OSA adapter level 05.60 would be represented as
            0x0560 by this object."
     ::= { osaexpChannelEntry 10 }

     ibmMvsOsaExpChannelCurLparName OBJECT-TYPE
     SYNTAX  DisplayString (SIZE(0..8))
     MAX-ACCESS read-only
     STATUS current
     DESCRIPTION
           "LPAR name of the OSA/SF from which this data was
            retrieved."
     ::= { osaexpChannelEntry 11 }

     ibmMvsOsaExpChannelCurLparNum OBJECT-TYPE
     SYNTAX  Integer32
     MAX-ACCESS read-only
     STATUS current
     DESCRIPTION
           "LPAR number of the OSA/SF from which this data was
            retrieved."
     ::= { osaexpChannelEntry 12 }

     ibmMvsOsaExpChannelManLparName OBJECT-TYPE
     SYNTAX  DisplayString (SIZE(0..8))
     MAX-ACCESS read-only
     STATUS current
     DESCRIPTION
           "LPAR name of the OSA Support Facility managing this
            channel. Only one OSA/SF can manage a OSA-Express Channel
            within an MVS Sysplex even though multiple OSA/SFs
            can retrieve information from the same OSA-Express
            Channel."
     ::= { osaexpChannelEntry 13 }

     ibmMvsOsaExpChannelManLparNum    OBJECT-TYPE
     SYNTAX  Integer32
     MAX-ACCESS read-only
     STATUS current
     DESCRIPTION
           "LPAR number of the OSA Support Facility managing this
            channel (set to 0xFFFF if not being managed by a
            OSA/SF)."
     ::= { osaexpChannelEntry 14 }

     ibmMvsOsaExpChannelPCIBusUtil1Min     OBJECT-TYPE
     SYNTAX  Integer32
     MAX-ACCESS read-only
     STATUS current
     DESCRIPTION
           "The average, over a 1 minute interval, of the percentage
            of time that the PCI bus was utilized to transfer data.
            It does not include idle time or time used by
            routine maintenance tasks.  The range of valid values
            for this object is 0 to 100%.  A value of -1 indicates
            that the value could not be retrieved from the adapter."
     ::= { osaexpChannelEntry 15 }

     ibmMvsOsaExpChannelProcessorUtil1Min  OBJECT-TYPE
     SYNTAX  Integer32
     MAX-ACCESS read-only
     STATUS current
     DESCRIPTION
           "The average, over a 1 minute interval, of the percentage
            of time that the CHPID Processor was utilized to transfer
            data.  It does not include idle time or time used by
            routine maintenance tasks.  The range of valid values
            for this object is 0 to 100%.  A value of -1 indicates
            that the value could not be retrieved from the adapter."
     ::= { osaexpChannelEntry 16 }

     ibmMvsOsaExpChannelPCIBusUtil5Min     OBJECT-TYPE
     SYNTAX  Integer32
     MAX-ACCESS read-only
     STATUS current
     DESCRIPTION
           "The average, over a 5 minute interval, of the percentage
            of time that the PCI bus was utilized to transfer data.
            It does not include idle time or time used by
            routine maintenance tasks.  The range of valid values
            for this object is 0 to 100%.  A value of -1 indicates
            that the value could not be retrieved from the adapter."
     ::= { osaexpChannelEntry 17 }

     ibmMvsOsaExpChannelProcessorUtil5Min  OBJECT-TYPE
     SYNTAX  Integer32
     MAX-ACCESS read-only
     STATUS current
     DESCRIPTION
           "The average, over a 5 minute interval, of the percentage
            of time that the CHPID Processor was utilized to transfer
            data.  It does not include idle time or time used by
            routine maintenance tasks.  The range of valid values
            for this object is 0 to 100%.  A value of -1 indicates
            that the value could not be retrieved from the adapter."
     ::= { osaexpChannelEntry 18 }

     ibmMvsOsaExpChannelPCIBusUtilHour     OBJECT-TYPE
     SYNTAX  Integer32
     MAX-ACCESS read-only
     STATUS current
     DESCRIPTION
           "The average, over an hour interval, of the percentage
            of time that the PCI bus was utilized to transfer data.
            It does not include idle time or time used by
            routine maintenance tasks.  The range of valid values
            for this object is 0 to 100%.  A value of -1 indicates
            that the value could not be retrieved from the adapter."
     ::= { osaexpChannelEntry 19 }

     ibmMvsOsaExpChannelProcessorUtilHour  OBJECT-TYPE
     SYNTAX  Integer32
     MAX-ACCESS read-only
     STATUS current
     DESCRIPTION
           "The average, over an hour interval, of the percentage
            of time that the CHPID Processor was utilized to transfer
            data.  It does not include idle time or time used by
            routine maintenance tasks.  The range of valid values
            for this object is 0 to 100%.  A value of -1 indicates
            that the value could not be retrieved from the adapter."
     ::= { osaexpChannelEntry 20 }

 -- osaexpPerfTable

     osaexpPerfTable OBJECT-TYPE
     SYNTAX SEQUENCE OF OsaexpPerfEntry
     MAX-ACCESS not-accessible
     STATUS current
     DESCRIPTION
        "This table provides performance information per each
         LPAR's utilization of an OSA-Express adapter.  The values
         will be reset when the adapter CHPID is reset."
     ::= { ibmTcpipMvsOsaExpGroup 2 }

     osaexpPerfEntry OBJECT-TYPE
     SYNTAX OsaexpPerfEntry
     MAX-ACCESS not-accessible
     STATUS current
     DESCRIPTION
        "Definition of a single entry in the osaexpPerfTable.
         Indexed by the ifIndex of the corresponding DEVICE interface
         and the LPAR number."
     INDEX { ifIndex,
             ibmMvsOsaExpPerfLparNum  }
     ::= { osaexpPerfTable 1 }

     OsaexpPerfEntry ::=
     SEQUENCE
       {
       ibmMvsOsaExpPerfLparNum                  Integer32,
       ibmMvsOsaExpPerfProcessorUtil1Min        Integer32,
       ibmMvsOsaExpPerfInKbytesRate1Min         Counter32,
       ibmMvsOsaExpPerfOutKbytesRate1Min        Counter32,
       ibmMvsOsaExpPerfProcessorUtil5Min        Integer32,
       ibmMvsOsaExpPerfInKbytesRate5Min         Counter32,
       ibmMvsOsaExpPerfOutKbytesRate5Min        Counter32,
       ibmMvsOsaExpPerfProcessorUtilHour        Integer32,
       ibmMvsOsaExpPerfInKbytesRateHour         Counter32,
       ibmMvsOsaExpPerfOutKbytesRateHour        Counter32
       }

     ibmMvsOsaExpPerfLparNum OBJECT-TYPE
     SYNTAX  Integer32
     MAX-ACCESS not-accessible
     STATUS current
     DESCRIPTION
           "LPAR number of the LPAR to which the performance
            objects apply."
     ::= { osaexpPerfEntry 1 }

     ibmMvsOsaExpPerfProcessorUtil1Min     OBJECT-TYPE
     SYNTAX Integer32
     MAX-ACCESS read-only
     STATUS current
     DESCRIPTION
           "The average, over a 1 minute interval, of the percentage
            of time that the CHPID Processor was utilized to
            transfer data for a specific LPAR.  It does not include
            idle time or time used by routine maintenance tasks.
            The range of valid values for this object is 0 to 100%.
            A value of -1 indicates that the value could not be
            retrieved from the adapter."
     ::= { osaexpPerfEntry 2 }

     ibmMvsOsaExpPerfInKbytesRate1Min      OBJECT-TYPE
     SYNTAX Counter32
     MAX-ACCESS read-only
     STATUS current
     DESCRIPTION
           "The average, over a 1 minute interval, of the number of
            inbound kilobytes processed for a specific LPAR.
            When the ibmMvsOsaExpPerfProcessorUtil1Min object
            for a specific LPAR has a value of -1, then the interval
            data could not be retrieved from the adapter and
            this object will have a value of zero."
     ::= { osaexpPerfEntry 3 }

     ibmMvsOsaExpPerfOutKbytesRate1Min     OBJECT-TYPE
     SYNTAX Counter32
     MAX-ACCESS read-only
     STATUS current
     DESCRIPTION
           "The average, over a 1 minute interval, of the number of
            outbound kilobytes processed for a specific LPAR.
            When the ibmMvsOsaExpPerfProcessorUtil1Min object
            for a specific LPAR has a value of -1, then the interval
            data could not be retrieved from the adapter and
            this object will have a value of zero."
     ::= { osaexpPerfEntry 4 }

     ibmMvsOsaExpPerfProcessorUtil5Min     OBJECT-TYPE
     SYNTAX Integer32
     MAX-ACCESS read-only
     STATUS current
     DESCRIPTION
           "The average, over a 5 minute interval, of the percentage
            of time that the CHPID Processor was utilized to
            transfer data for a specific LPAR.  It does not include
            idle time or time used by routine maintenance tasks.
            The range of valid values for this object is 0 to 100%.
            A value of -1 indicates that the value could not be
            retrieved from the adapter."
     ::= { osaexpPerfEntry 5 }

     ibmMvsOsaExpPerfInKbytesRate5Min      OBJECT-TYPE
     SYNTAX Counter32
     MAX-ACCESS read-only
     STATUS current
     DESCRIPTION
           "The average, over a 5 minute interval, of the number of
            inbound kilobytes processed for a specific LPAR.
            When the ibmMvsOsaExpPerfProcessorUtil5Min object
            for a specific LPAR has a value of -1, then the interval
            data could not be retrieved from the adapter and
            this object will have a value of zero."
     ::= { osaexpPerfEntry 6 }

     ibmMvsOsaExpPerfOutKbytesRate5Min     OBJECT-TYPE
     SYNTAX Counter32
     MAX-ACCESS read-only
     STATUS current
     DESCRIPTION
           "The average, over a 5 minute interval, of the number of
            outbound kilobytes processed for a specific LPAR.
            When the ibmMvsOsaExpPerfProcessorUtil5Min object
            for a specific LPAR has a value of -1, then the interval
            data could not be retrieved from the adapter and
            this object will have a value of zero."
     ::= { osaexpPerfEntry 7 }

     ibmMvsOsaExpPerfProcessorUtilHour     OBJECT-TYPE
     SYNTAX Integer32
     MAX-ACCESS read-only
     STATUS current
     DESCRIPTION
           "The average, over an hour interval, of the percentage
            of time that the CHPID Processor was utilized to
            transfer data for a specific LPAR.  It does not include
            idle time or time used by routine maintenance tasks.
            The range of valid values for this object is 0 to 100%.
            A value of -1 indicates that the value could not be
            retrieved from the adapter."
     ::= { osaexpPerfEntry 8 }

     ibmMvsOsaExpPerfInKbytesRateHour      OBJECT-TYPE
     SYNTAX Counter32
     MAX-ACCESS read-only
     STATUS current
     DESCRIPTION
           "The average, over an hour interval, of the number of
            inbound kilobytes processed for a specific LPAR.
            When the ibmMvsOsaExpPerfProcessorUtilHour object
            for a specific LPAR has a value of -1, then the interval
            data could not be retrieved from the adapter and
            this object will have a value of zero."
     ::= { osaexpPerfEntry 9 }

     ibmMvsOsaExpPerfOutKbytesRateHour     OBJECT-TYPE
     SYNTAX Counter32
     MAX-ACCESS read-only
     STATUS current
     DESCRIPTION
           "The average, over an hour interval, of the number of
            outbound kilobytes processed for a specific LPAR.
            When the ibmMvsOsaExpPerfProcessorUtilHour object
            for a specific LPAR has a value of -1, then the interval
            data could not be retrieved from the adapter and
            this object will have a value of zero."
     ::= { osaexpPerfEntry 10 }


 -- osaexpEthPortTable

     osaexpEthPortTable OBJECT-TYPE
     SYNTAX SEQUENCE OF OsaexpEthPortEntry
     MAX-ACCESS not-accessible
     STATUS current
     DESCRIPTION
        "This table is intended to represent the ethernet Ports
         associated with the osaexpChannelTable entries
         for ethernet adapters. Each OSA-Express Channel
         has one or more Ports."
     ::= { ibmTcpipMvsOsaExpGroup 3 }

     osaexpEthPortEntry OBJECT-TYPE
     SYNTAX OsaexpEthPortEntry
     MAX-ACCESS not-accessible
     STATUS current
     DESCRIPTION
        "Definition of a single entry in the osaexpEthPortTable.
         Indexed by the ifIndex of the corresponding LINK interface."
     INDEX { ifIndex }
     ::= { osaexpEthPortTable 1 }

     OsaexpEthPortEntry ::=
     SEQUENCE
       {
       ibmMvsOsaExpEthPortNumber              Integer32,
       ibmMvsOsaExpEthPortType                INTEGER,
       ibmMvsOsaExpEthPortHardwareState       INTEGER,
       ibmMvsOsaExpEthPortServiceMode         INTEGER,
       ibmMvsOsaExpEthPortDisabledStatus      OCTET STRING (SIZE(2)),
       ibmMvsOsaExpEthPortConfigName          DisplayString,
       ibmMvsOsaExpEthPortConfigSpeed         INTEGER,
       ibmMvsOsaExpEthPortActiveSpeed         INTEGER,
       ibmMvsOsaExpEthPortMacAddrActive       OCTET STRING (SIZE(6)),
       ibmMvsOsaExpEthPortMacAddrBurntIn      OCTET STRING (SIZE(6)),
       ibmMvsOsaExpEthPortUserData            DisplayString,
       ibmMvsOsaExpEthPortOutPackets          Counter32,
       ibmMvsOsaExpEthPortInPackets           Counter32,
       ibmMvsOsaExpEthPortInGroupFrames       Counter32,
       ibmMvsOsaExpEthPortInBroadcastFrames   Counter32,
       ibmMvsOsaExpEthPortName                DisplayString,
       ibmMvsOsaExpEthPortInUnknownIPFrames   Counter32,
       ibmMvsOsaExpEthPortGroupMacAddrs       OCTET STRING (SIZE(256))
       }

     ibmMvsOsaExpEthPortNumber       OBJECT-TYPE
     SYNTAX  Integer32
     MAX-ACCESS read-only
     STATUS current
     DESCRIPTION
           "Port number, starts at 0."
     ::= { osaexpEthPortEntry 1 }

     ibmMvsOsaExpEthPortType         OBJECT-TYPE
     SYNTAX  INTEGER { gigabitEthernet(65),
                       fastEthernet(81)
                     }
     MAX-ACCESS read-only
     STATUS current
     DESCRIPTION
           "The physical port type."
     ::= { osaexpEthPortEntry 2 }

     ibmMvsOsaExpEthPortHardwareState OBJECT-TYPE
     SYNTAX  INTEGER {
                       unknown(1),
                       linkFailure(2),
                       disabled(3),
                       enabled(4)
                      }
     MAX-ACCESS read-only
     STATUS current
     DESCRIPTION
           "The hardware state of the port:
            1 - Unknown port hardware state.
            2 - OSA has detected a loss of signal on the link.
                (A likely cause of this condition is an improperly
                installed or missing cable connection on the port).
                For OSA-Express ATM, this condition can also be
                caused by registration failure.
            3 - Port is disabled.  The reason for the port being
                disabled is set in object
                ibmMvsOsaExpEthPortDisabledStatus.
            4 - Port is enabled."
     ::= { osaexpEthPortEntry 3 }

     ibmMvsOsaExpEthPortServiceMode OBJECT-TYPE
     SYNTAX  INTEGER {
                       nonserviceMode(0),
                       serviceMode(1)
                      }
     MAX-ACCESS read-only
     STATUS current
     DESCRIPTION
           " "
     ::= { osaexpEthPortEntry 4 }

     ibmMvsOsaExpEthPortDisabledStatus OBJECT-TYPE
     SYNTAX  OCTET STRING (SIZE(2))
     MAX-ACCESS read-only
     STATUS current
     DESCRIPTION
           "When the value of ibmMvsOsaExpEthPortHardwareState is
            disabled(3), this object explains the reason for the
            disabled state.  The value for this object may be a
            combination of the following:
              0x0001  Disabled internal port failure
              0x0002  Disabled service processor request
              0x0004  Disabled network request
              0x0008  Disabled OSA/SF request
              0x0010  Disabled configuration change
              0x0020  Disabled link failure threshold exceeded
              0x0040  Disabled port temporarily disabled
            When the value of ibmMvsOsaExpEthPortHardwareState
            is not disabled(3), the value of this object will be
            zero."
     ::= { osaexpEthPortEntry 5 }

     ibmMvsOsaExpEthPortConfigName OBJECT-TYPE
     SYNTAX  DisplayString (SIZE(1..34))
     MAX-ACCESS read-only
     STATUS current
     DESCRIPTION
           "Configuration name."
     ::= { osaexpEthPortEntry 6 }

     ibmMvsOsaExpEthPortConfigSpeed OBJECT-TYPE
     SYNTAX  INTEGER {
                       autoNegotiate(0),
                       halfDuplex10Mb(1),
                       fullDuplex10Mb(2),
                       halfDuplex100Mb(3),
                       fullDuplex100Mb(4),
                       fullDuplex1000Mb(7)
                      }
     MAX-ACCESS read-only
     STATUS current
     DESCRIPTION
           "The configured port speed.  For OSA-Express Gigabit
            Ethernet adapters the port speed can not be configured
            so the value of this object will be 1000MbFullDuplex(7)."
     ::= { osaexpEthPortEntry 7 }

     ibmMvsOsaExpEthPortActiveSpeed OBJECT-TYPE
     SYNTAX  INTEGER {
                       unknown(0),
                       halfDuplex10Mb(1),
                       fullDuplex10Mb(2),
                       halfDuplex100Mb(3),
                       fullDuplex100Mb(4),
                       fullDuplex1000Mb(7)
                      }
     MAX-ACCESS read-only
     STATUS current
     DESCRIPTION
           "The actual port speed."
     ::= { osaexpEthPortEntry 8 }

     ibmMvsOsaExpEthPortMacAddrActive OBJECT-TYPE
     SYNTAX  OCTET STRING (SIZE(6))
     MAX-ACCESS read-only
     STATUS current
     DESCRIPTION
           "A 6 byte OCTET STRING which contains the current
            MAC address in use on the adapter."
     ::= { osaexpEthPortEntry 9 }

     ibmMvsOsaExpEthPortMacAddrBurntIn OBJECT-TYPE
     SYNTAX  OCTET STRING (SIZE(6))
     MAX-ACCESS read-only
     STATUS current
     DESCRIPTION
           "A 6 byte OCTET STRING which contains the adapter's
            burned in MAC address."
     ::= { osaexpEthPortEntry 10 }

     ibmMvsOsaExpEthPortUserData OBJECT-TYPE
     SYNTAX  DisplayString
     MAX-ACCESS read-only
     STATUS current
     DESCRIPTION
           "Configured port description."
     ::= { osaexpEthPortEntry 11 }

     ibmMvsOsaExpEthPortOutPackets OBJECT-TYPE
     SYNTAX  Counter32
     MAX-ACCESS read-only
     STATUS current
     DESCRIPTION
           "The count of the total number of packets transmitted
            from this port. A CHPID reset will cause this value
            to be reset to zero."
     ::= { osaexpEthPortEntry 12 }

     ibmMvsOsaExpEthPortInPackets OBJECT-TYPE
     SYNTAX  Counter32
     MAX-ACCESS read-only
     STATUS current
     DESCRIPTION
           "The count of the total number of packets received
            by this port. A CHPID reset will cause this value
            to be reset to zero."
     ::= { osaexpEthPortEntry 13 }

     ibmMvsOsaExpEthPortInGroupFrames OBJECT-TYPE
     SYNTAX  Counter32
     MAX-ACCESS read-only
     STATUS current
     DESCRIPTION
           "The count of the total number of group frames
            received by this port. A CHPID reset will cause
            this value to be reset to zero."
     ::= { osaexpEthPortEntry 14 }

     ibmMvsOsaExpEthPortInBroadcastFrames OBJECT-TYPE
     SYNTAX  Counter32
     MAX-ACCESS read-only
     STATUS current
     DESCRIPTION
           "The count of the total number of broadcast frames
            received by this port. A CHPID reset will cause
            this value to be reset to zero."
     ::= { osaexpEthPortEntry 15 }

     ibmMvsOsaExpEthPortName          OBJECT-TYPE
     SYNTAX  DisplayString (SIZE(1..8))
     MAX-ACCESS read-only
     STATUS current
     DESCRIPTION
           "Specifies the Port Name which must also be entered at the
            connection manager on the host and the application. Port
            Name is specifed to OSA/SF as a config file parameter
            (PCM_NAME). This value is also specified via ILMI as
            the value of the atmfPortMyIfName object.  Does not
            apply to an ATM OSA-2 adapter configured for
            ATM IP Forwarding mode, or an OSA-Express ATM155
            adapter configured for QDIO LAN Emulation mode."
     ::= { osaexpEthPortEntry 16 }

     ibmMvsOsaExpEthPortInUnknownIPFrames OBJECT-TYPE
     SYNTAX  Counter32
     MAX-ACCESS read-only
     STATUS current
     DESCRIPTION
           "The count of the total number of packets that were
            discarded because they did not have a matching IP
            address and there was no primary nor secondary
            router default defined.  This object is not supported
            for Fast Ethernet adapters so the value will be
            zero."
     ::= { osaexpEthPortEntry 17 }

     ibmMvsOsaExpEthPortGroupMacAddrs OBJECT-TYPE
     SYNTAX  OCTET STRING(SIZE(256))
     MAX-ACCESS read-only
     STATUS current
     DESCRIPTION
            "This field contains the active Group Addresses.
             An individual Group Address is 6 bytes long.
             Therefore, this field is actually 32 times
             (OCTET STRING(SIZE(6)) + 2 bytes of padding) long."
     ::= { osaexpEthPortEntry 18 }

 -- osaexpEthSnaTable

     osaexpEthSnaTable OBJECT-TYPE
     SYNTAX SEQUENCE OF OsaexpEthSnaEntry
     MAX-ACCESS not-accessible
     STATUS current
     DESCRIPTION
        "This table is intended to represent the data that is
         available from an OSA-Express ethernet Port that is running
         in SNA mode. An entry in this table is associated with
         the osaexpEthPortTable entries."
     ::= { ibmTcpipMvsOsaExpGroup 4 }

     osaexpEthSnaEntry OBJECT-TYPE
     SYNTAX OsaexpEthSnaEntry
     MAX-ACCESS not-accessible
     STATUS current
     DESCRIPTION
        "Definition of a single entry in the osaexpEthSnaTable.
         Indexed by the ifIndex of the corresponding LINK interface."
     INDEX { ifIndex }
     ::= { osaexpEthSnaTable 1 }

     OsaexpEthSnaEntry ::=
     SEQUENCE
       {
       ibmMvsOsaExpEthSnaInactTimer           Integer32,
       ibmMvsOsaExpEthSnaRespTimer            Integer32,
       ibmMvsOsaExpEthSnaAckTimer             Integer32,
       ibmMvsOsaExpEthSnaMaxIFramesBeforeAck  Integer32,
       ibmMvsOsaExpEthSnaMaxTransmitWindow    Integer32
       }

     ibmMvsOsaExpEthSnaInactTimer    OBJECT-TYPE
     SYNTAX  Integer32
     MAX-ACCESS read-only
     STATUS current
     DESCRIPTION
           "The inactivity timer. An enabled inactivity timer (Ti)
            periodically tests the viability of the network media.
            The timer setting applies to all the clients on the
            target LAN, not to individual clients.  The timer
            interval indicates how quickly a failure of the network
            media can be detected when the connection is quiescent.
            If the Ti timer times out, a supervisory poll frame is
            sent over the connection.  The T1 response, or reply,
            timer clocks the supervisory poll.  If the T1 timer
            times out, the supervisory poll is retransmitted.
            OSA can retransmit a supervisory poll up to 8 times.
            If no response is received after the last retransmission,
            the link is declared inoperative, and the MVS program
            issues a message.  The value will either be zero, or
            in the range of 24 to 9000 in units of 100th of
            a second."
     ::= { osaexpEthSnaEntry 1 }

     ibmMvsOsaExpEthSnaRespTimer    OBJECT-TYPE
     SYNTAX  Integer32 (0..510)
     MAX-ACCESS read-only
     STATUS current
     DESCRIPTION
           "The response timer.  The T1 timer clocks link events that
            require responses from clients on the network.  These
            link events include SABME/UA exchanges, I-frame link
            protocol data unit (LPDU) transmissions, and
            supervisory polls.  The value is expressed as an
            integer in units of 10th of a second."
     ::= { osaexpEthSnaEntry 2 }

     ibmMvsOsaExpEthSnaAckTimer     OBJECT-TYPE
     SYNTAX  Integer32 (0..2040)
     MAX-ACCESS read-only
     STATUS current
     DESCRIPTION
           "The acknowledgement timer.  An OSA starts the T2 timer
            when it receives an I-format LPDU and stops when it
            sends an acknowledgement.  An acknowledgement is sent
            either when an outgoing I frame is sent, which acts
            as the acknowledgement, or when N3 number of I-format
            LPDUs has been received.  If the T2 timer times out,
            the OSA must send an acknowledgement.  The value is
            expressed as an integer in units of 100th of a
            second."
     ::= { osaexpEthSnaEntry 3 }

     ibmMvsOsaExpEthSnaMaxIFramesBeforeAck  OBJECT-TYPE
     SYNTAX  Integer32 (1..4)
     MAX-ACCESS read-only
     STATUS current
     DESCRIPTION
           "Maximum I frames before ACK (N3).  The maximum number
            of I-format link protocol data units (LPDUs) that
            can be received by an OSA before it sends an
            acknowledgement (N3 count).  It is also called
            the receive window count."
     ::= { osaexpEthSnaEntry 4 }

     ibmMvsOsaExpEthSnaMaxTransmitWindow    OBJECT-TYPE
     SYNTAX  Integer32 (1..16)
     MAX-ACCESS read-only
     STATUS current
     DESCRIPTION
           "SNA maximum transmit window (TW).  The maximum number
            of outstanding I-format link protocol data units (LPDUs).
            It is also called the maximum transmit window count
            or the maximum window out count.  The TW count
            allows the sender to transmit frames before that
            sender is forced to halt and wait for an acknowledgement.
            Therefore, the receiver should be able to absorb that
            number of frames, either in its service access point (SAP)
            buffers or within the buffers in workstation memory."
     ::= { osaexpEthSnaEntry 5 }

 ---------------------------------------------------------------------
 -- ibmTcpipMvsDVIPAGroup
 ---------------------------------------------------------------------

 -- ibmMvsDVIPATable

     ibmMvsDVIPATable OBJECT-TYPE
        SYNTAX SEQUENCE OF IbmMvsDVIPAEntry
        MAX-ACCESS not-accessible
        STATUS current
        DESCRIPTION
           "Each entry in this table represents a Dynamic VIPA (DVIPA)
            interface configured to this stack, and supports DVIPA
            status information."
        ::= { ibmTcpipMvsDVIPAGroup 1 }

     ibmMvsDVIPAEntry OBJECT-TYPE
        SYNTAX IbmMvsDVIPAEntry
        MAX-ACCESS not-accessible
        STATUS current
        DESCRIPTION
           "Definition of a single entry in the ibmMvsDVIPATable."
        INDEX { ibmMvsDVIPAIpAddrType, ibmMvsDVIPAIpAddr }
        ::= { ibmMvsDVIPATable 1 }

     IbmMvsDVIPAEntry ::=
     SEQUENCE
       {
       ibmMvsDVIPAIpAddrType               InetAddressType,
       ibmMvsDVIPAIpAddr                   InetAddress,
       ibmMvsDVIPAMaskType                 InetAddressType,
       ibmMvsDVIPAMaskAddr                 InetAddress,
       ibmMvsDVIPAStatus                   INTEGER,
       ibmMvsDVIPAOrigin                   INTEGER,
       ibmMvsDVIPARank                     Integer32,
       ibmMvsDVIPADistributeStatus         INTEGER,
       ibmMvsDVIPAMoveable                 INTEGER,
       ibmMvsDVIPAServMgrEnabled           TruthValue
       }

     ibmMvsDVIPAIpAddrType            OBJECT-TYPE
         SYNTAX      InetAddressType
         MAX-ACCESS  not-accessible
         STATUS      current
         DESCRIPTION
            "The IP address type of the ibmMvsDVIPAIpAddr object."
         ::= { ibmMvsDVIPAEntry 1 }

     ibmMvsDVIPAIpAddr            OBJECT-TYPE
        SYNTAX      InetAddress  (SIZE (1..20))
        MAX-ACCESS  not-accessible
        STATUS      current
        DESCRIPTION
           "The dynamic VIPA IP address."
        ::= { ibmMvsDVIPAEntry 2 }

     ibmMvsDVIPAMaskType        OBJECT-TYPE
        SYNTAX      InetAddressType
        MAX-ACCESS  read-only
        STATUS      current
        DESCRIPTION
           "The IP address type of the ibmMvsDVIPAMaskAddr object
            This object will be set to unknown(0) for entries whose
            ibmMvsDVIPAOrigin value is backup(2)."
        ::= { ibmMvsDVIPAEntry 3 }

     ibmMvsDVIPAMaskAddr        OBJECT-TYPE
        SYNTAX      InetAddress  (SIZE (0..16))
        MAX-ACCESS  read-only
        STATUS      current
        DESCRIPTION
           "The address mask.  This object will be set to a
            zero-length string for entries whose ibmMvsDVIPAOrigin
            value is backup(2)."
        ::= { ibmMvsDVIPAEntry 4 }

     ibmMvsDVIPAStatus          OBJECT-TYPE
        SYNTAX  INTEGER {
                          unknown(1),
                          active(2),
                          backup(3),
                          moving(4),
                          quiescing(5)
                         }
        MAX-ACCESS read-only
        STATUS current
        DESCRIPTION
           "The status of this DVIPA on the stack.  A status of
            unknown(1) should not occur and represents an error."
        ::= { ibmMvsDVIPAEntry 5 }

     ibmMvsDVIPAOrigin          OBJECT-TYPE
        SYNTAX  INTEGER {
                          unknown(1),
                          backup(2),
                          define(3),
                          rangeBind(4),
                          rangeIoctl(5),
                          target(6)
                         }
        MAX-ACCESS read-only
        STATUS current
        DESCRIPTION
           "The origin of how this DVIPA came to be configured to
            the stack.  A value of backup(2) or define(3) indicates
            which VIPADYNAMIC Profile statement was used to configure
            the DVIPA to the stack.  A value of rangeBind(4)
            indicates that the DVIPA was dynamically defined when an
            application issued a BIND function call.  A value of
            rangeIoctl(5) indicates that the DVIPA was dynamically
            defined when an application issued the SIOCSVIPA IOCTL
            function call.  A value of target(6) indicates that the
            DVIPA was dynamically defined on the stack because this
            stack is a target stack for the Sysplex Distributor
            function.  A status of unknown(1) should not occur and
            represents an error."
        ::= { ibmMvsDVIPAEntry 6 }

     ibmMvsDVIPARank           OBJECT-TYPE
        SYNTAX  Integer32
        MAX-ACCESS read-only
        STATUS current
        DESCRIPTION
           "This stack's rank in the chain of backup stacks for a given
            dynamic VIPA.  For entries whose ibmMvsDVIPAOrigin value
            is not backup(2) or define(3), this object does not
            apply and will be set to -1."
        ::= { ibmMvsDVIPAEntry 7 }

     ibmMvsDVIPADistributeStatus    OBJECT-TYPE
        SYNTAX  INTEGER {
                          none(1),
                          distributor(2),
                          target(3),
                          disgtributorAndTarget(4)
                         }
        MAX-ACCESS read-only
        STATUS current
        DESCRIPTION
           "The status of this DVIPA on the stack in relation to
            the Sysplex Distributor function.  A value of none(1)
            indicates that the DVIPA is not participating in the
            Sysplex Distributor function.  A value of distributor(2)
            indicates that the stack is a distributor for this
            DVIPA.  A value of target(3) indicates that the stack
            is a target stack for this DVIPA.  A value of
            distributorAndTarget(4) indicates that the stack is
            both a distributor and a target stack for this DVIPA."
        ::= { ibmMvsDVIPAEntry 8 }

     ibmMvsDVIPAMoveable            OBJECT-TYPE
        SYNTAX  INTEGER {
                          none(1),
                          immediate(2),
                          whenIdle(3),
                          nonDisruptive(4),
                          disruptive(5)
                         }
        MAX-ACCESS read-only
        STATUS current
        DESCRIPTION
           "The manner in which a dynamic VIPA IP address should
            be moved to another stack.  A value of none(1) indicates
            that moveable status does not apply to this DVIPA.
            This value would be set for entries where backup is set
            as the value for the ibmMvsDVIPAOrigin and
            ibmMvsDVIPAStatus objects.  For DVIPA IP addresses
            activated as the result of a VIPADEFINE configuration
            statement, a value of immediate(2) means that this dynamic
            VIPA can be moved to another stack as soon as the other
            stack requests ownership of the DVIPA by executing a
            VIPADEFINE for the same dynamic VIPA.  Any existing
            connections on this stack will be maintained by the new
            owning stack until the connections are closed.  All new
            connection requests will be directed to the new owning
            stack.  A value of whenIdle(3) means that this dynamic
            VIPA can be moved to another stack when there are no
            connections for this dynamic VIPA on this stack.  While
            there are existing connections, any new connection requests
            will continue to be directed to this stack.
            For DVIPA IP addresses activated as the result of a
            VIPARANGE configuration and a subsequent SIOCSVIPA IOCTL
            or BIND, a value of nonDisruptive(4) means that this
            DVIPA can be moved to another stack as soon as the other
            stack requests ownership of the DVIPA by creating the
            same  DVIPA via a subsequent BIND or SIOCSVIPA IOCTL.
            Any existing connections on this stack will be maintained
            by the new owning stack until the connections are closed.
            All new connection requests will be directed to the new
            stack.  A value of disruptive(5) means that one of two
            different behaviors will occur:
              - In the case of a subsequent BIND by an application on
                another stack, no movement of the DVIPA will occur
                the second application will presumably be disrupted
                because the BIND fails. (The first application is
                unaware that another BIND occurred.)
              - In the case of a subsequent SIOCSVIPA IOCTL, the DVIPA
                will move to another stack but connections to the DVIPA
                on this stack will be broken."
        ::= { ibmMvsDVIPAEntry 9 }

     ibmMvsDVIPAServMgrEnabled    OBJECT-TYPE
        SYNTAX   TruthValue
        MAX-ACCESS   read-only
        STATUS   current
        DESCRIPTION
           "The status of this DVIPA on the stack in relation to the
            Service Manager function.  A value of true(1) indicates
            that the DVIPA is participating in the Service Manager
            function.  A value of false(2) indicates that the DVIPA
            is not participating in the Service Manager function."
        ::= { ibmMvsDVIPAEntry 10 }


 -- ibmMvsDVIPARangeConfTable

     ibmMvsDVIPARangeConfTable OBJECT-TYPE
        SYNTAX SEQUENCE OF IbmMvsDVIPARangeConfEntry
        MAX-ACCESS not-accessible
        STATUS current
        DESCRIPTION
           "Each entry in this table represents a subnet defined by
            the VIPARANGE Profile statement in which requests for
            activating a DVIPA via a BIND or SIOCSVIPA IOCTL, will be
            honored."
        ::= { ibmTcpipMvsDVIPAGroup 2 }

     ibmMvsDVIPARangeConfEntry OBJECT-TYPE
        SYNTAX IbmMvsDVIPARangeConfEntry
        MAX-ACCESS not-accessible
        STATUS current
        DESCRIPTION
           "Definition of a single entry in the
            ibmMvsDVIPARangeConfTable."
        INDEX { ibmMvsDVIPARangeConfIpAddrType,
                ibmMvsDVIPARangeConfIpAddr,
                ibmMvsDVIPARangeConfMaskType,
                ibmMvsDVIPARangeConfMaskAddr }
        ::= { ibmMvsDVIPARangeConfTable 1 }

     IbmMvsDVIPARangeConfEntry ::=
     SEQUENCE
       {
       ibmMvsDVIPARangeConfIpAddrType      InetAddressType,
       ibmMvsDVIPARangeConfIpAddr          InetAddress,
       ibmMvsDVIPARangeConfMaskType        InetAddressType,
       ibmMvsDVIPARangeConfMaskAddr        InetAddress,
       ibmMvsDVIPARangeConfMoveable        INTEGER,
       ibmMvsDVIPARangeConfStatus          RowStatus
       }

     ibmMvsDVIPARangeConfIpAddrType   OBJECT-TYPE
        SYNTAX      InetAddressType
        MAX-ACCESS  not-accessible
        STATUS      current
        DESCRIPTION
            "The IP address type of the
             ibmMvsDVIPARangeConfIpAddr object."
        ::= { ibmMvsDVIPARangeConfEntry 1 }

     ibmMvsDVIPARangeConfIpAddr   OBJECT-TYPE
        SYNTAX      InetAddress  (SIZE (1..20))
        MAX-ACCESS  not-accessible
        STATUS      current
        DESCRIPTION
           "The dynamic VIPA IP address."
        ::= { ibmMvsDVIPARangeConfEntry 2 }

     ibmMvsDVIPARangeConfMaskType   OBJECT-TYPE
        SYNTAX      InetAddressType
        MAX-ACCESS  not-accessible
        STATUS      current
        DESCRIPTION
           "The IP address type of the ibmMvsDVIPARangeConfMaskAddr
            object."
        ::= { ibmMvsDVIPARangeConfEntry 3 }

     ibmMvsDVIPARangeConfMaskAddr   OBJECT-TYPE
        SYNTAX      InetAddress  (SIZE (1..16))
        MAX-ACCESS  not-accessible
        STATUS      current
        DESCRIPTION
           "The dynamic VIPA IP address."
        ::= { ibmMvsDVIPARangeConfEntry 4 }

     ibmMvsDVIPARangeConfMoveable   OBJECT-TYPE
        SYNTAX  INTEGER {
                          nonDisruptive(1),
                          disruptive(2)
                         }
        MAX-ACCESS read-create
        STATUS current
        DESCRIPTION
           "The manner in which a dynamic VIPA IP address defined
            by a VIPARANGE statement, should be moved to another
            stack.  A value of nonDisruptive(1) means that this
            DVIPA can be moved to another stack as soon as the other
            stack requests ownership of the DVIPA by creating the
            same DVIPA via a subsequent BIND or SIOCSVIPA IOCTL.
            Any existing connections on this stack will be maintained
            by the new owning stack until the connections are closed.
            All new connection requests will be directed to the new
            stack.  A value of disruptive(2) means that one of two
            different behaviors will occur:
              - In the case of a subsequent BIND by an application on
                another stack, no movement of the DVIPA will occur
                the second application will presumably be disrupted
                because the BIND fails. (The first application is
                unaware that another BIND occurred.)
              - In the case of a subsequent SIOCSVIPA IOCTL, the DVIPA
                will move to another stack but connections to the DVIPA
                on this stack will be broken."
        ::= { ibmMvsDVIPARangeConfEntry 5 }

     ibmMvsDVIPARangeConfStatus     OBJECT-TYPE
        SYNTAX       RowStatus
        MAX-ACCESS   read-create
        STATUS       current
        DESCRIPTION
          "This object allows entries to be created and deleted
           in the ibmMvsDVIPARangeConfTable.  Note that an attempt
           to set any read-create object defined within an
           ibmMvsDVIPARangeConfEntry while the value of
           ibmMvsDVIPARangeConfStatus is active(1) should result
           in an inconsistentValue error."
        ::= { ibmMvsDVIPARangeConfEntry 6 }


 -- ibmMvsDVIPADistConfTable

     ibmMvsDVIPADistConfTable OBJECT-TYPE
        SYNTAX SEQUENCE OF IbmMvsDVIPADistConfEntry
        MAX-ACCESS not-accessible
        STATUS current
        DESCRIPTION
           "Each entry in this table represents a dynamic VIPA and
            port for which connection requests are to be distributed
            to other stacks as defined by the VIPADISTRIBUTE Profile
            statement."
        ::= { ibmTcpipMvsDVIPAGroup 3 }

     ibmMvsDVIPADistConfEntry OBJECT-TYPE
        SYNTAX IbmMvsDVIPADistConfEntry
        MAX-ACCESS not-accessible
        STATUS current
        DESCRIPTION
           "Definition of a single entry in the
            ibmMvsDVIPADistConfTable."
        INDEX { ibmMvsDVIPADistConfIpAddrType,
                ibmMvsDVIPADistConfIpAddr,
                ibmMvsDVIPADistConfPort,
                ibmMvsDVIPADistConfTargetDynXcfIpAddrType,
                ibmMvsDVIPADistConfTargetDynXcfIpAddr }
        ::= { ibmMvsDVIPADistConfTable 1 }

     IbmMvsDVIPADistConfEntry ::=
     SEQUENCE
       {
       ibmMvsDVIPADistConfIpAddrType              InetAddressType,
       ibmMvsDVIPADistConfIpAddr                  InetAddress,
       ibmMvsDVIPADistConfPort                    INTEGER,
       ibmMvsDVIPADistConfTargetDynXcfIpAddrType  InetAddressType,
       ibmMvsDVIPADistConfTargetDynXcfIpAddr      InetAddress,
       ibmMvsDVIPADistConfStatus                  RowStatus
       }

     ibmMvsDVIPADistConfIpAddrType    OBJECT-TYPE
        SYNTAX      InetAddressType
        MAX-ACCESS  not-accessible
        STATUS      current
        DESCRIPTION
            "The IP address type of the
             ibmMvsDVIPADistConfIpAddr object."
        ::= { ibmMvsDVIPADistConfEntry 1 }

     ibmMvsDVIPADistConfIpAddr    OBJECT-TYPE
        SYNTAX      InetAddress  (SIZE (1..20))
        MAX-ACCESS  not-accessible
        STATUS      current
        DESCRIPTION
           "The dynamic VIPA IP address."
        ::= { ibmMvsDVIPADistConfEntry 2 }

     ibmMvsDVIPADistConfPort      OBJECT-TYPE
        SYNTAX      INTEGER (0..65535)
        MAX-ACCESS  not-accessible
        STATUS      current
        DESCRIPTION
           "The dynamic VIPA distributed port."
        ::= { ibmMvsDVIPADistConfEntry 3 }

     ibmMvsDVIPADistConfTargetDynXcfIpAddrType OBJECT-TYPE
        SYNTAX      InetAddressType
        MAX-ACCESS  not-accessible
        STATUS      current
        DESCRIPTION
           "The IP address type of the
            ibmMvsDVIPADistConfTargetDynXcfIpAddr object.  If the
            ALL parameter was specified on the VIPADISTRIBUTE
            Profile statement, this object will be set to unknown(0)."
        ::= { ibmMvsDVIPADistConfEntry 4 }

     ibmMvsDVIPADistConfTargetDynXcfIpAddr OBJECT-TYPE
        SYNTAX      InetAddress  (SIZE (0..20))
        MAX-ACCESS  not-accessible
        STATUS      current
        DESCRIPTION
           "The dynamic XCF IP address of the target stack.  If the
            ALL parameter was specified on the VIPADISTRIBUTE
            Profile statement, this object will be set to a
            zero-length string."
        ::= { ibmMvsDVIPADistConfEntry 5 }

     ibmMvsDVIPADistConfStatus      OBJECT-TYPE
        SYNTAX       RowStatus
        MAX-ACCESS   read-create
        STATUS       current
        DESCRIPTION
          "This object allows entries to be created and deleted
           in the ibmMvsDVIPADistConfTable."
        ::= { ibmMvsDVIPADistConfEntry 6 }


 -- ibmMvsDVIPAConnRoutingTable

     ibmMvsDVIPAConnRoutingTable OBJECT-TYPE
        SYNTAX SEQUENCE OF IbmMvsDVIPAConnRoutingEntry
        MAX-ACCESS not-accessible
        STATUS current
        DESCRIPTION
           "Each entry in this table represents a dynamic VIPA TCP
            connection.  Entries will be supported in the table for
            all dynamic VIPA interfaces for which MOVEABLE IMMEDIATE
            or NONDISRUPTIVE was specified.  On a Sysplex Distributor
            routing stack, there will be an entry in this table for
            every connection being routed through the distributor.
            On a stack taking over a dynamic VIPA, there will be an
            entry in this table for every connection to the
            dynamic VIPA.  On a Sysplex Distributor target stack or
            a stack which is in the process of giving up a dynamic
            VIPA, there will be an entry in this table for every
            connection for which the stack is an endpoint."
        ::= { ibmTcpipMvsDVIPAGroup 4 }

     ibmMvsDVIPAConnRoutingEntry OBJECT-TYPE
        SYNTAX IbmMvsDVIPAConnRoutingEntry
        MAX-ACCESS not-accessible
        STATUS current
        DESCRIPTION
           "Definition of a single entry in the
            ibmMvsDVIPAConnRoutingTable."
        INDEX { ibmMvsDVIPAIpAddrType,
                ibmMvsDVIPAIpAddr,
                ibmMvsDVIPAConnPort,
                ibmMvsDVIPAConnRemIpAddrType,
                ibmMvsDVIPAConnRemIpAddr,
                ibmMvsDVIPAConnRemPort }
        ::= { ibmMvsDVIPAConnRoutingTable 1 }

     IbmMvsDVIPAConnRoutingEntry ::=
     SEQUENCE
       {
       ibmMvsDVIPAConnPort                        INTEGER,
       ibmMvsDVIPAConnRemIpAddrType               InetAddressType,
       ibmMvsDVIPAConnRemIpAddr                   InetAddress,
       ibmMvsDVIPAConnRemPort                     INTEGER,
       ibmMvsDVIPAConnDynXcfIpAddrType            InetAddressType,
       ibmMvsDVIPAConnDynXcfIpAddr                InetAddress,
       ibmMvsDVIPAConnPolicyRuleName              SnmpAdminString,
       ibmMvsDVIPAConnPolicyActionName            SnmpAdminString
       }

     ibmMvsDVIPAConnPort          OBJECT-TYPE
        SYNTAX      INTEGER (0..65535)
        MAX-ACCESS  not-accessible
        STATUS      current
        DESCRIPTION
           "The dynamic VIPA port."
        ::= { ibmMvsDVIPAConnRoutingEntry 1 }

     ibmMvsDVIPAConnRemIpAddrType OBJECT-TYPE
        SYNTAX      InetAddressType
        MAX-ACCESS  not-accessible
        STATUS      current
        DESCRIPTION
           "The IP address type of the
            ibmMvsDVIPAConnRemIpAddr object."
        ::= { ibmMvsDVIPAConnRoutingEntry 2 }

     ibmMvsDVIPAConnRemIpAddr OBJECT-TYPE
        SYNTAX      InetAddress  (SIZE (1..20))
        MAX-ACCESS  not-accessible
        STATUS      current
        DESCRIPTION
           "The remote IP address for this TCP connection."
        ::= { ibmMvsDVIPAConnRoutingEntry 3 }

     ibmMvsDVIPAConnRemPort       OBJECT-TYPE
        SYNTAX      INTEGER (0..65535)
        MAX-ACCESS  not-accessible
        STATUS      current
        DESCRIPTION
           "The remote port for this TCP connection."
        ::= { ibmMvsDVIPAConnRoutingEntry 4 }

     ibmMvsDVIPAConnDynXcfIpAddrType OBJECT-TYPE
        SYNTAX      InetAddressType
        MAX-ACCESS  read-only
        STATUS      current
        DESCRIPTION
           "The IP address type of the
            ibmMvsDVIPAConnDynXcfIpAddr object."
        ::= { ibmMvsDVIPAConnRoutingEntry 5 }

     ibmMvsDVIPAConnDynXcfIpAddr OBJECT-TYPE
        SYNTAX      InetAddress  (SIZE (1..20))
        MAX-ACCESS  read-only
        STATUS      current
        DESCRIPTION
           "The dynamic XCF IP address of the Sysplex
            Distributor target stack, or stack which is the
            endpoint of the connection."
        ::= { ibmMvsDVIPAConnRoutingEntry 6 }

     ibmMvsDVIPAConnPolicyRuleName     OBJECT-TYPE
        SYNTAX   SnmpAdminString (SIZE(1..48))
        MAX-ACCESS   read-only
        STATUS   current
        DESCRIPTION
           "The Service Policy Agent Policy Rule name that the
            connection maps to.  If the Service Policy Agent is
            not active or the connection does not map to a policy,
            this object will be set to the string value *NONE*."
        ::= { ibmMvsDVIPAConnRoutingEntry 7 }

     ibmMvsDVIPAConnPolicyActionName   OBJECT-TYPE
        SYNTAX   SnmpAdminString (SIZE(1..48))
        MAX-ACCESS   read-only
        STATUS   current
        DESCRIPTION
           "The Service Policy Agent Policy Action name that the
            connection maps to.  If the Service Policy Agent is
            not active or the connection does not map to a policy,
            this object will be set to the string value *NONE*."
        ::= { ibmMvsDVIPAConnRoutingEntry 8 }


 -- ibmMvsDVIPADistPortTable

     ibmMvsDVIPADistPortTable OBJECT-TYPE
        SYNTAX SEQUENCE OF IbmMvsDVIPADistPortEntry
        MAX-ACCESS not-accessible
        STATUS current
        DESCRIPTION
           "An entry exists in this table for every target stack
            per distributed dynamic VIPA and port.  This table is
            supported only by stacks which are distributing
            connection requests as part of the Sysplex Distributor
            function.  This table is not supported by stacks which
            are only targets of the Sysplex Distributor function."
        ::= { ibmTcpipMvsDVIPAGroup 5 }

     ibmMvsDVIPADistPortEntry OBJECT-TYPE
        SYNTAX IbmMvsDVIPADistPortEntry
        MAX-ACCESS not-accessible
        STATUS current
        DESCRIPTION
           "Definition of a single entry in the
            ibmMvsDVIPADistPortTable."
        INDEX { ibmMvsDVIPAIpAddrType,
                ibmMvsDVIPAIpAddr,
                ibmMvsDVIPADistPortPort,
                ibmMvsDVIPADistPortTargetDynXcfIpAddrType,
                ibmMvsDVIPADistPortTargetDynXcfIpAddr }
        ::= { ibmMvsDVIPADistPortTable 1 }

     IbmMvsDVIPADistPortEntry ::=
     SEQUENCE
       {
       ibmMvsDVIPADistPortPort                    INTEGER,
       ibmMvsDVIPADistPortTargetDynXcfIpAddrType  InetAddressType,
       ibmMvsDVIPADistPortTargetDynXcfIpAddr      InetAddress,
       ibmMvsDVIPADistPortReadyCount              Gauge32,
       ibmMvsDVIPADistPortTotalConn               Counter32,
       ibmMvsDVIPADistPortWlmWeight               Unsigned32
       }

     ibmMvsDVIPADistPortPort      OBJECT-TYPE
        SYNTAX      INTEGER (0..65535)
        MAX-ACCESS  not-accessible
        STATUS      current
        DESCRIPTION
           "The dynamic VIPA distributed port."
        ::= { ibmMvsDVIPADistPortEntry 1 }

     ibmMvsDVIPADistPortTargetDynXcfIpAddrType OBJECT-TYPE
        SYNTAX      InetAddressType
        MAX-ACCESS  not-accessible
        STATUS      current
        DESCRIPTION
           "The IP address type of the
            ibmMvsDVIPADistPortTargetDynXcfIpAddr object."
        ::= { ibmMvsDVIPADistPortEntry 2 }

     ibmMvsDVIPADistPortTargetDynXcfIpAddr OBJECT-TYPE
        SYNTAX      InetAddress  (SIZE (0..20))
        MAX-ACCESS  not-accessible
        STATUS      current
        DESCRIPTION
           "The dynamic XCF IP address of the target stack."
        ::= { ibmMvsDVIPADistPortEntry 3 }

     ibmMvsDVIPADistPortReadyCount   OBJECT-TYPE
        SYNTAX   Gauge32
        MAX-ACCESS   read-only
        STATUS   current
        DESCRIPTION
           "The number of servers ready at the port on the target
            stack, to service connection requests."
        ::= { ibmMvsDVIPADistPortEntry 4 }

     ibmMvsDVIPADistPortTotalConn    OBJECT-TYPE
        SYNTAX   Counter32
        MAX-ACCESS   read-only
        STATUS   current
        DESCRIPTION
           "The total number of connections for the dynamic VIPA
            IP address and port which have been distributed to
            the target stack."
        ::= { ibmMvsDVIPADistPortEntry 5 }

     ibmMvsDVIPADistPortWlmWeight    OBJECT-TYPE
        SYNTAX   Unsigned32
        MAX-ACCESS   read-only
        STATUS   current
        DESCRIPTION
           "The Workload Manager weight value for the MVS system
            on which the target stack is located.  The value is
            normalized such that the lowest value is 1.  This
            weight value is an indication of the MVS system's
            available CPU capacity.  The lower the value the lower
            the capacity."
        ::= { ibmMvsDVIPADistPortEntry 6 }


 -- DVIPA Group scalar objects

     ibmMvsDVIPAServMgrMulticastIpAddrType OBJECT-TYPE
        SYNTAX      InetAddressType
        MAX-ACCESS  read-only
        STATUS      current
        DESCRIPTION
           "The IP address type of the
            ibmMvsDVIPAServMgrMulticastIpAddr object."
        ::= { ibmTcpipMvsDVIPAGroup 6 }

     ibmMvsDVIPAServMgrMulticastIpAddr OBJECT-TYPE
        SYNTAX      InetAddress  (SIZE (0..20))
        MAX-ACCESS  read-only
        STATUS      current
        DESCRIPTION
           "The type of multicast IP address that will be used for
            communications between the Sysplex Distributor and the
            routers acting as Forwarding Agents.  This object reflects
            values from the VIPASMPARMS Profile statement for the
            Sysplex Distributor Service Manager function."
        ::= { ibmTcpipMvsDVIPAGroup 7 }

     ibmMvsDVIPAServMgrPort    OBJECT-TYPE
        SYNTAX      INTEGER (0..65535)
        MAX-ACCESS  read-only
        STATUS      current
        DESCRIPTION
           "The type of multicast IP address that will be used for
            communications between the Sysplex Distributor and the
            routers acting as Forwarding Agents.  This object reflects
            values from the VIPASMPARMS Profile statement for the
            Sysplex Distributor Service Manager function."
        ::= { ibmTcpipMvsDVIPAGroup 8 }

     ibmMvsDVIPAServMgrPasswordSpecified    OBJECT-TYPE
        SYNTAX      TruthValue
        MAX-ACCESS  read-only
        STATUS      current
        DESCRIPTION
           "Indicates whether a password value was specified on the
            VIPASMPARMS Profile statement for the Sysplex Distributor
            Service Manager function.  A value of true(1) indicates
            that a password was specified.  A value of false(2)
            indicates that a password was not specified.  The
            password enables MD5 encryption for all communications
            between the Sysplex Distributor function and routers
            acting as Forwarding Agents.  This password must match
            configured on the Forwarding Agents."
        ::= { ibmTcpipMvsDVIPAGroup 9 }

     ibmMvsDVIPATrapControl    OBJECT-TYPE
        SYNTAX      BITS {
                          dvipaStatusChange(0),
                          dvipaRemoved(1),
                          targetAdded(2),
                          targetRemoved(3),
                          targetServerStarted(4),
                          targetServerEnded(5)
                         }
        MAX-ACCESS  read-write
        STATUS      current
        DESCRIPTION
           "The value of this object determines which traps will be
            generated for all dynamic VIPA events.  The value of this
            object is initialized to dvipaStatusChange(0) and
            dvipaRemoved(1) so that only those traps will be
            automatically generated.  The following values are only
            applicable to Sysplex Distributor distributing stacks:
              - targetAdded(2)
              - targetRemoved(3)
              - targetServerStarted(4)
              - targetServerEnded(5)
            The following traps are generated when the corresponding
            bit value for this object is set:
              BIT value                 Trap
              -----------------------   ----------
              dvipaStatusChange(0)      ibmMvsDVIPAStatusChange
              dvipaRemoved(1)           ibmMvsDVIPARemoved
              targetAdded(2)            ibmMvsDVIPATargetAdded
              targetRemoved(3)          ibmMvsDVIPATargetRemoved
              targetServerStarted(4 )   ibmMvsDVIPATargetServerStarted
              targetServerEnded(5)      ibmMvsDVIPATargetServerEnded"
        ::= { ibmTcpipMvsDVIPAGroup 10 }

 ---------------------------------------------------------------------
 -- Notifications if any
 --
 ---------------------------------------------------------------------
     ibmMvsAtmOsasfAtmPvcCreate NOTIFICATION-TYPE
        OBJECTS {
           ibmMvsAtmOsasfPvcName
        }
        STATUS  current
        DESCRIPTION
           "This trap is generated when OSA/SF sends a asynch
            notification to the TCP/IP DPI Subagent that a
            PVC was created for a given OSA Port. This
            notification contains the corresponding
            ibmMvsAtmOsasfPortName instance. Representation
            of this will contain the aal5 layer interface ifIndex
            of the port, the PVC name len, and the PVC name in
            ASCII as 'ifIndex.pvcNameOctetCount.pvcNameInASCIINvt'."
        ::= { ibmTCPIPmvsMIBTraps 1 }

     ibmMvsAtmOsasfAtmPvcDelete NOTIFICATION-TYPE
        OBJECTS {
           ibmMvsAtmOsasfPvcName
        }
        STATUS  current
        DESCRIPTION
           "This trap is generated when OSA/SF sends a asyn
            notification to the TCP/IP DPI Subagent that a
            PVC was deleted for a given OSA Port. This
            notification contains the corresponding
            ibmMvsAtmOsasfPortName instance. Representation
            of this will contain the aal5 layer interface ifIndex
            of the port, the PVC name len, and the PVC name in
            ASCII as 'ifIndex.pvcNameOctetCount.pvcNameInASCIINvt'."
        ::= { ibmTCPIPmvsMIBTraps 2 }

     ibmMvsDVIPAStatusChange    NOTIFICATION-TYPE
        OBJECTS {
           ibmMvsDVIPAStatus,
           ibmMvsDVIPAOrigin,
           ibmMvsDVIPARank,
           ibmMvsDVIPAMoveable,
           ibmMvsDVIPAServMgrEnabled
        }
        STATUS  current
        DESCRIPTION
           "This trap is generated when a dynamic VIPA is defined
            or its status changes on a TCP/IP stack.  The
            ibmMvsDVIPAOrigin value indicates the reason why the
            DVIPA was originally defined.  The instance value for
            the trap objects will contain the affected DVIPA IP
            address."
        ::= { ibmTCPIPmvsMIBTraps 3 }

     ibmMvsDVIPARemoved         NOTIFICATION-TYPE
        OBJECTS {
           ibmMvsDVIPAStatus,
           ibmMvsDVIPAOrigin,
           ibmMvsDVIPARank,
           ibmMvsDVIPAMoveable,
           ibmMvsDVIPAServMgrEnabled
        }
        STATUS  current
        DESCRIPTION
           "This trap is generated when a dynamic VIPA is removed
            from a TCP/Id stack.  The ibmMvsDVIPAOrigin value
            indicates the reason why the DVIPA was previously defined.
            The ibmMvsDVIPAStatus object reflects the status before
            DVIPA was removed.  The instance value for
            the trap objects will contain the affected DVIPA IP
            address."
        ::= { ibmTCPIPmvsMIBTraps 4 }

     ibmMvsDVIPATargetAdded     NOTIFICATION-TYPE
        OBJECTS {
           ibmMvsDVIPADistConfStatus
        }
        STATUS  current
        DESCRIPTION
           "This trap is generated by a Sysplex Distributor stack
            when it determines that a designated target stack is
            active.  Stacks are designated as target stacks on the
            VIPADISTRIBUTE Profile statement.  The instance value
            for the ibmMvsDVIPADistConfStatus object will indicate
            the affected DVIPA IP address, the distributed port,
            and the target stack's dynamic XCF IP address."
        ::= { ibmTCPIPmvsMIBTraps 5 }

     ibmMvsDVIPATargetRemoved   NOTIFICATION-TYPE
        OBJECTS {
           ibmMvsDVIPADistConfStatus
        }
        STATUS  current
        DESCRIPTION
           "This trap is generated by a Sysplex Distributor stack
            when an active target stack is removed from distribution.
            This can occur when a VIPADISTRIBUTE DELETE Profile
            statement is processed, or the target stack ends.
            The instance value for the ibmMvsDVIPADistConfStatus
            object will indicate the affected DVIPA IP address,
            the distributed port, and the dynamic XCF IP address
            of the target stack that is removed from distribution.
            if the ALL parameter was specified on the VIPADISTRIBUTE
            DELETE statement, the target stack's IP address type
            will be unknown (0) and its IP address will be a
            zero-length string."
        ::= { ibmTCPIPmvsMIBTraps 6 }

     ibmMvsDVIPATargetServerStarted    NOTIFICATION-TYPE
        OBJECTS {
           ibmMvsDVIPADistPortReadyCount
        }
        STATUS  current
        DESCRIPTION
           "This trap is generated by a Sysplex Distributor stack
            when it receives notification from a target stack that
            a server has become active on a distributed port.
            The instance value for the ibmMvsDVIPADistPortReadyCount
            object will indicate the affected DVIPA IP address,
            the distributed port, and the target stack's dynamic
            XCF IP address."
        ::= { ibmTCPIPmvsMIBTraps 7 }

     ibmMvsDVIPATargetServerEnded      NOTIFICATION-TYPE
        OBJECTS {
           ibmMvsDVIPADistPortReadyCount
        }
        STATUS  current
        DESCRIPTION
           "This trap is generated by a Sysplex Distributor stack
            when it receives notification from a target stack that
            a server has ended on a distributed port.
            The instance value for the ibmMvsDVIPADistPortReadyCount
            object will indicate the affected DVIPA IP address,
            the distributed port, and the target stack's dynamic
            XCF IP address."
        ::= { ibmTCPIPmvsMIBTraps 8 }

     ibmMvsTcpipSubagentColdStart      NOTIFICATION-TYPE
        STATUS  current
        DESCRIPTION
           "This trap is generated by the TCP/IP Subagent.  It
            signifies that the Subagent, acting in a subagent role,
            has reinitialized itself and that its configuration
            may have been altered."
        ::= { ibmTCPIPmvsMIBTraps 9 }


 ---------------------------------------------------------------------
 -- Conformance information
 -- Compliance statements
 ---------------------------------------------------------------------

 ibmTCPIPmvsCompliances OBJECT
                        IDENTIFIER ::= { ibmTCPIPmvsConformance 1 }
 ibmTCPIPmvsGroups      OBJECT
                        IDENTIFIER ::= { ibmTCPIPmvsConformance 2 }

 ---------------------------------------------------------------------
 -- Compliance statements
 ---------------------------------------------------------------------
 ibmTCPIPmvsCompliance MODULE-COMPLIANCE
    STATUS  current
    DESCRIPTION
            "The compliance statement for the IBM
            Communications Server product."
    MODULE  -- this module
        MANDATORY-GROUPS {
                           ibmTCPIPmvsPingGroup,
                           ibmTCPIPmvsSystemGroup7,
                           ibmTCPIPmvsTcpGroup6,
                           ibmTCPIPmvsUdpGroup3,
                           ibmTCPIPmvsInterfacesGroup5,
                           ibmTCPIPmvsPortGroup2,
                           ibmTCPIPmvsRoutingGroup,
                           ibmTCPIPmvsIpGroup,
                           ibmTCPIPmvsSystemNotificationGroup
                         }
        GROUP  ibmTCPIPmvsAtmSupportGroup4
        DESCRIPTION
            "The ATM Support Group of objects is only present if
              OSAENABLED was selected on the SACONFIG statement
              in a TCP/IP Profile that was used to configure
              TCP/IP. In addition, one or more OSA-2 ATM Device and
              Links must be defined."
        GROUP  ibmTCPIPmvsAtmNotificationGroup
           DESCRIPTION
                "OSA ATM Management notifications"
        GROUP    ibmTCPIPmvsAtmLeGroup2
        DESCRIPTION
            "The ATM LAN Emulation Group consists of objects that
              provide information if a ATM Port was configured
              to run in LAN Emulation mode."
        GROUP  ibmTCPIPmvsOsaExpGroup
        DESCRIPTION
            "The OSA-Express Group of objects is only present if
              OSAENABLED was selected on the SACONFIG statement
              in a TCP/IP Profile that was used to configure
              TCP/IP. In addition, one or more Device and Links
              for OSA-Express adapters must be defined."
        GROUP  ibmTCPIPmvsDVIPAGroup
        DESCRIPTION
            "The DVIPA Group of objects is only present if
             Dynamic VIPA interfaces have been configured to the
             TCP/IP stack."
        GROUP  ibmTCPIPmvsDVIPANotificationGroup
           DESCRIPTION
                "Dynamic VIPA group notifications"
    ::= { ibmTCPIPmvsCompliances 1 }

 ---------------------------------------------------------------------
 -- MIB groupings
 ---------------------------------------------------------------------
 ibmTCPIPmvsPingGroup OBJECT-GROUP
   OBJECTS {
               ibmMvsRPingResponseTime
              }
   STATUS  current
   DESCRIPTION  " "
    ::= { ibmTCPIPmvsGroups 1 }

   ibmTCPIPmvsRoutingGroup OBJECT-GROUP
   OBJECTS {
                 ibmMvsGatewayMaximumRetransmitTime,
                 ibmMvsGatewayMinimumRetransmitTime,
                 ibmMvsGatewayRoundTripGain,
                 ibmMvsGatewayVarianceGain,
                 ibmMvsGatewayVarianceMultiplier,
                 ibmMvsGatewayDelayAcks
              }
   STATUS  current
   DESCRIPTION
           "This group comprises the TCP/IP retransmission parms
             that are in effect for a locally configured route entry."
    ::= { ibmTCPIPmvsGroups 11 }

   ibmTCPIPmvsPortGroup2 OBJECT-GROUP
   OBJECTS {
                ibmMvsPortNumberLow,
                ibmMvsPortNumberHigh,
                ibmMvsPortProtocol,
                ibmMvsPortProcName,
                ibmMvsPortAutoLoggable,
                ibmMvsPortDelayAcks,
                ibmMvsPortOptMaxSegmentSize,
                ibmMvsPortSharePort,
                ibmMvsPortBindIpAddr,
                ibmMvsPortSAFResource,
                ibmMvsPortReuse
             }
   STATUS  current
   DESCRIPTION
           "This group comprises those objects that represent the
             current set of PORT and PORTRANGE definitions
             for this TCP/IP instance."
    ::= { ibmTCPIPmvsGroups 26 }

 ibmTCPIPmvsAtmSupportGroup4 OBJECT-GROUP
   OBJECTS {
               ibmMvsAtmOsasfChannelNumber,
               ibmMvsAtmOsasfChannelType,
               ibmMvsAtmOsasfChannelSubType,
               ibmMvsAtmOsasfChannelMode,
               ibmMvsAtmOsasfChannelHwModel,
               ibmMvsAtmOsasfChannelState,
               ibmMvsAtmOsasfChannelShared,
               ibmMvsAtmOsasfChannelNumPorts,
               ibmMvsAtmOsasfChannelDeterNodeDesc,
               ibmMvsAtmOsasfChannelControlUnitNumber,
               ibmMvsAtmOsasfChannelCodeLevel,
               ibmMvsAtmOsasfChannelCurLparName,
               ibmMvsAtmOsasfChannelCurLparNum,
               ibmMvsAtmOsasfChannelManParnName,
               ibmMvsAtmOsasfChannelManParnNum,
               ibmMvsAtmOsasfChannelFlashLevel,
               ibmMvsAtmOsasfPortNumber,
               ibmMvsAtmOsasfPortType,
               ibmMvsAtmOsasfPortHardwareState,
               ibmMvsAtmOsasfPortMediaType,
               ibmMvsAtmOsasfPortUniType,
               ibmMvsAtmOsasfPortUniVersion,
               ibmMvsAtmOsasfPortNetPrefix,
               ibmMvsAtmOsasfPortNetPrefixPrefix,
               ibmMvsAtmOsasfPortNetPrefixStatus,
               ibmMvsAtmOsasfPortCodeLoadStatus,
               ibmMvsAtmOsasfPortMacAddrBurntIn,
               ibmMvsAtmOsasfPortMacAddrActive,
               ibmMvsAtmOsasfPortMaxPcmConnections,
               ibmMvsAtmOsasfPortPcmName,
               ibmMvsAtmOsasfPortAAL5InPackets,
               ibmMvsAtmOsasfPortAAL5OutPackets,
               ibmMvsAtmOsasfPortIpAddress,
               ibmMvsAtmOsasfPvcName,
               ibmMvsAtmOsasfPvcBestEffort,
               ibmMvsAtmOsasfPvcFwdPeakCellRate,
               ibmMvsAtmOsasfPvcBwdPeakCellRate,
               ibmMvsAtmOsasfPvcFwdsustainCellRate,
               ibmMvsAtmOsasfPvcBwdsustainCellRate,
               ibmMvsAtmOsasfPvcFwdCellBurstSize,
               ibmMvsAtmOsasfPvcBwdCellBurstSize,
               ibmMvsAtmOsasfPvcVpi,
               ibmMvsAtmOsasfPvcVci,
               ibmMvsAtmOsasfPvcFwdMaxAal5PduSize,
               ibmMvsAtmOsasfPvcBwdMaxAal5PduSize
              }
   STATUS  current
   DESCRIPTION
           "This group comprises those objects that are related
             to atm support."
    ::= { ibmTCPIPmvsGroups 27 }

ibmTCPIPmvsUdpGroup3 OBJECT-GROUP
   OBJECTS {
               ibmMvsUdpLastAct,
               ibmMvsUdpIpOpts,
               ibmMvsUdpDgramIn,
               ibmMvsUdpBytesIn,
               ibmMvsUdpDgramOut,
               ibmMvsUdpBytesOut,
               ibmMvsUdpResourceName,
               ibmMvsUdpSubtask,
               ibmMvsUdpResourceId,
               ibmMvsUdpSockOpt,
               ibmMvsUdpSendLim,
               ibmMvsUdpRecvLim,
               ibmMvsUdpEntryState,
               ibmMvsUdpMcastTTL,
               ibmMvsUdpMcastLoopback,
               ibmMvsUdpMcastLinkAddr,
               ibmMvsUdpDSField,
               ibmMvsUdpMcastRecvLinkAddr
              }
   STATUS  current
   DESCRIPTION
           "This group defines those objects that are augmented to
             a udp listen table entry."
    ::= { ibmTCPIPmvsGroups 29 }

   ibmTCPIPmvsAtmLeGroup2 OBJECT-GROUP
   OBJECTS {
                ibmMvsAtmSnaLeLlcTi,
                ibmMvsAtmSnaLeLlcT1,
                ibmMvsAtmSnaLeLlcT2,
                ibmMvsAtmSnaleMaxStations,
                ibmMvsAtmSnaLeMaxSaps,
                ibmMvsAtmSnaleMaxIn,
                ibmMvsAtmSnaLeMaxOut,
                ibmMvsAtmSnaLeCrsGroupAddress,
                ibmMvsAtmSnaLeUserData,
                ibmMvsAtmSnaLeClientEnableState,
                ibmMvsAtmSnaLeBestEffortPeakRate,
                ibmMvsAtmSnaLeMaxLECConnections,
                ibmMvsAtmSnaLeTrEnableLoadBalancing,
                ibmMvsAtmSnaLeTrLoadBalancing,
                ibmMvsAtmSnaLeTrSessionDelay,
                ibmMvsAtmLecConfigMode,
                ibmMvsAtmLecConfigLanType,
                ibmMvsAtmLecConfigMaxDataFrameSize,
                ibmMvsAtmLecConfigLanName,
                ibmMvsAtmLecConfigLesAtmAddress,
                ibmMvsAtmLecControlTimeout,
                ibmMvsAtmLecMaxUnknownFrameCount,
                ibmMvsAtmLecMaxUnknownFrameTime,
                ibmMvsAtmLecVccTimeoutPeriod,
                ibmMvsAtmLecMaxRetryCount,
                ibmMvsAtmLecAgingTime,
                ibmMvsAtmLecForwardDelayTime,
                ibmMvsAtmLecExpectedArpResponseTime,
                ibmMvsAtmLecFlushTimeout,
                ibmMvsAtmLecPathSwitchingDelay,
                ibmMvsAtmLecLocalSegmentID,
                ibmMvsAtmLecMulticastSendType,
                ibmMvsAtmLecMulticastSendAvgRate,
                ibmMvsAtmLecMulticastSendPeakRate,
                ibmMvsAtmLecConnectionCompleteTimer,
                ibmMvsAtmLecPortName,
                ibmMvsAtmLecPrimaryAtmAddress,
                ibmMvsAtmLecID,
                ibmMvsAtmLecInterfaceState,
                ibmMvsAtmLecLastFailureRespCode,
                ibmMvsAtmLecLastFailureState,
                ibmMvsAtmLecProtocol,
                ibmMvsAtmLecVersion,
                ibmMvsAtmLecTopologyChange,
                ibmMvsAtmLecConfigServerAtmAddress,
                ibmMvsAtmLecConfigSource,
                ibmMvsAtmLecActualLanType,
                ibmMvsAtmLecActualMaxDataFrameSize,
                ibmMvsAtmLecActualLanName,
                ibmMvsAtmLecAtmAddress,
                ibmMvsAtmLecProxyClient,
                ibmMvsAtmLecArpRequestsOut,
                ibmMvsAtmLecArpRequestsIn,
                ibmMvsAtmLecArpRepliesOut,
                ibmMvsAtmLecArpRepliesIn,
                ibmMvsAtmLecControlFramesOut,
                ibmMvsAtmLecControlFramesIn,
                ibmMvsAtmLecSvcFailures,
                ibmMvsAtmLecConfigDirectInterface,
                ibmMvsAtmLecConfigDirectVPI,
                ibmMvsAtmLecConfigDirectVCI,
                ibmMvsAtmLecControlDirectInterface,
                ibmMvsAtmLecControlDirectVPI,
                ibmMvsAtmLecControlDirectVCI,
                ibmMvsAtmLecControlDistributeInterface,
                ibmMvsAtmLecControlDistributeVPI,
                ibmMvsAtmLecControlDistributeVCI,
                ibmMvsAtmLecMulticastSendInterface,
                ibmMvsAtmLecMulticastSendVPI,
                ibmMvsAtmLecMulticastSendVCI,
                ibmMvsAtmLecMulticastFwdInterface,
                ibmMvsAtmLecMulticastFwdVPI,
                ibmMvsAtmLecMulticastFwdVCI,
                ibmMvsAtmLecMacAddress
              }
   STATUS  current
   DESCRIPTION
           "This group comprises those objects that are related
             to ATM LAN Emulation support."
    ::= { ibmTCPIPmvsGroups 30 }

ibmTCPIPmvsTcpGroup6 OBJECT-GROUP
   OBJECTS {
               ibmMvsTcpConnLastActivity,
               ibmMvsTcpConnBytesIn,
               ibmMvsTcpConnBytesOut,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnRcvBufSize,
               ibmMvsTcpConnResourceName,
               ibmMvsTcpConnSubtask,
               ibmMvsTcpConnResourceId,
               ibmMvsTcpConnSockOpt,
               ibmMvsTcpConnRttSeq,
               ibmMvsTcpConnTargetAppl,
               ibmMvsTcpConnLuName,
               ibmMvsTcpConnClientUserId,
               ibmMvsTcpConnLogMode,
               ibmMvsTcpConnProto,
               ibmMvsTcpConnDupacks,
               ibmMvsTcpConnOptMaxSegmentSize,
               ibmMvsTcpConnClusterConnFlag,
               ibmMvsTcpConnInSegs,
               ibmMvsTcpConnOutSegs,
               ibmMvsTcpConnDSField,
               ibmMvsTcpConnSndBufSize,
               ibmMvsTcpConnAcceptCount,
               ibmMvsTcpConnExceedBacklog,
               ibmMvsTcpConnCurrBacklog,
               ibmMvsTcpConnMaxBacklog,
               ibmMvsTcpConnWindowScale,
               ibmMvsTcpConnTimeStamp,
               ibmMvsTcpConnServerResourceId,
               ibmMvsTcpConnsClosed,
               ibmMvsTcpPassiveDrops,
               ibmMvsTcpTimeWaitReused,
               ibmMvsTcpPredictAck,
               ibmMvsTcpPredictData,
               ibmMvsTcpInDupAck,
               ibmMvsTcpInBadSum,
               ibmMvsTcpInBadLen,
               ibmMvsTcpInShort,
               ibmMvsTcpInPawsDrop,
               ibmMvsTcpInAllBeforeWin,
               ibmMvsTcpInSomeBeforeWin,
               ibmMvsTcpInAllAfterWin,
               ibmMvsTcpInSomeAfterWin,
               ibmMvsTcpInOutOfOrder,
               ibmMvsTcpInAfterClose,
               ibmMvsTcpInWinProbes,
               ibmMvsTcpInWinUpdates,
               ibmMvsTcpOutWinUpdates,
               ibmMvsTcpOutDelayAcks,
               ibmMvsTcpOutWinProbes,
               ibmMvsTcpRxmtTimers,
               ibmMvsTcpRxmtDrops,
               ibmMvsTcpPMTURxmts,
               ibmMvsTcpPMTUErrors,
               ibmMvsTcpProbeDrops,
               ibmMvsTcpKeepAliveProbes,
               ibmMvsTcpKeepAliveDrops,
               ibmMvsTcpFinwait2Drops,
               ibmMvsTcpListenerLocalAddrType,
               ibmMvsTcpListenerLocalAddr,
               ibmMvsTcpListenerLocalPort,
               ibmMvsTcpListenerRemoteAddrType,
               ibmMvsTcpListenerRemoteAddr,
               ibmMvsTcpListenerRemotePort,
               ibmMvsTcpListenerAcceptCount,
               ibmMvsTcpListenerExceedBacklog,
               ibmMvsTcpListenerCurrBacklog,
               ibmMvsTcpListenerMaxBacklog,
               ibmMvsTcpListenerResourceName
              }
   STATUS  current
   DESCRIPTION
           "Defines objects that are augmented to the tcpConnTable
            and statistical objects for TCP entities."
    ::= { ibmTCPIPmvsGroups 32 }

ibmTCPIPmvsIpGroup OBJECT-GROUP
   OBJECTS {
               ibmMvsIpInDevLayerCalls,
               ibmMvsIpInUnpackErrors,
               ibmMvsIpInDiscardsMemory,
               ibmMvsIpOutDiscardsDlcSynch,
               ibmMvsIpOutDiscardsDlcAsynch,
               ibmMvsIpOutDiscardsMemory
              }
   STATUS  current
   DESCRIPTION
           "This group defines statistical objects for IP entities."
    ::= { ibmTCPIPmvsGroups 33 }

ibmTCPIPmvsSystemGroup7 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled,
                ibmMvsTcpMaxReceiveBufferSize,
                ibmMvsPathMtuDscEnabled,
                ibmMvsMultipathType,
                ibmMvsIpForwarding,
                ibmMvsDevRetryDuration,
                ibmMvsTcpFinwait2Time,
                ibmMvsTcpTimeStamp,
                ibmMvsTcpipSubagentVersion
              }
   STATUS  current
   DESCRIPTION
           " "
    ::= { ibmTCPIPmvsGroups 34 }

 ibmTCPIPmvsOsaExpGroup OBJECT-GROUP
   OBJECTS {
             ibmMvsOsaExpChannelNumber,
             ibmMvsOsaExpChannelType,
             ibmMvsOsaExpChannelSubType,
             ibmMvsOsaExpChannelMode,
             ibmMvsOsaExpChannelState,
             ibmMvsOsaExpChannelShared,
             ibmMvsOsaExpChannelNumPorts,
             ibmMvsOsaExpChannelDeterNodeDesc,
             ibmMvsOsaExpChannelControlUnitNumber,
             ibmMvsOsaExpChannelCodeLevel,
             ibmMvsOsaExpChannelCurLparName,
             ibmMvsOsaExpChannelCurLparNum,
             ibmMvsOsaExpChannelManLparName,
             ibmMvsOsaExpChannelManLparNum,
             ibmMvsOsaExpChannelPCIBusUtil1Min,
             ibmMvsOsaExpChannelProcessorUtil1Min,
             ibmMvsOsaExpChannelPCIBusUtil5Min,
             ibmMvsOsaExpChannelProcessorUtil5Min,
             ibmMvsOsaExpChannelPCIBusUtilHour,
             ibmMvsOsaExpChannelProcessorUtilHour,
             ibmMvsOsaExpPerfProcessorUtil1Min,
             ibmMvsOsaExpPerfInKbytesRate1Min,
             ibmMvsOsaExpPerfOutKbytesRate1Min,
             ibmMvsOsaExpPerfProcessorUtil5Min,
             ibmMvsOsaExpPerfInKbytesRate5Min,
             ibmMvsOsaExpPerfOutKbytesRate5Min,
             ibmMvsOsaExpPerfProcessorUtilHour,
             ibmMvsOsaExpPerfInKbytesRateHour,
             ibmMvsOsaExpPerfOutKbytesRateHour,
             ibmMvsOsaExpEthPortNumber,
             ibmMvsOsaExpEthPortType,
             ibmMvsOsaExpEthPortHardwareState,
             ibmMvsOsaExpEthPortServiceMode,
             ibmMvsOsaExpEthPortDisabledStatus,
             ibmMvsOsaExpEthPortConfigName,
             ibmMvsOsaExpEthPortConfigSpeed,
             ibmMvsOsaExpEthPortActiveSpeed,
             ibmMvsOsaExpEthPortMacAddrActive,
             ibmMvsOsaExpEthPortMacAddrBurntIn,
             ibmMvsOsaExpEthPortUserData,
             ibmMvsOsaExpEthPortOutPackets,
             ibmMvsOsaExpEthPortInPackets,
             ibmMvsOsaExpEthPortInGroupFrames,
             ibmMvsOsaExpEthPortInBroadcastFrames,
             ibmMvsOsaExpEthPortName,
             ibmMvsOsaExpEthPortInUnknownIPFrames,
             ibmMvsOsaExpEthPortGroupMacAddrs,
             ibmMvsOsaExpEthSnaInactTimer,
             ibmMvsOsaExpEthSnaRespTimer,
             ibmMvsOsaExpEthSnaAckTimer,
             ibmMvsOsaExpEthSnaMaxIFramesBeforeAck,
             ibmMvsOsaExpEthSnaMaxTransmitWindow
            }
   STATUS  current
   DESCRIPTION
           "This group comprises those objects that are related
            to OSA-Express adapter support."
    ::= { ibmTCPIPmvsGroups 35 }

   ibmTCPIPmvsInterfacesGroup5 OBJECT-GROUP
   OBJECTS {
                ibmMvsDeviceType,
                ibmMvsDeviceBaseNumber,
                ibmMvsDeviceIoBufferSize,
                ibmMvsDeviceAutoRestart,
                ibmMvsDeviceNetmanEnabled,
                ibmMvsDeviceHostClawName,
                ibmMvsDeviceWorkstationClawName,
                ibmMvsDeviceReadBuffers,
                ibmMvsDeviceReadSize,
                ibmMvsDeviceWriteBuffers,
                ibmMvsDeviceWriteSize,
                ibmMvsDeviceProcname,
                ibmMvsDeviceIncomingSvcEnabled,
                ibmMvsDeviceLuName,
                ibmMvsDeviceRouterStatus,
                ibmMvsDeviceActualRouterStatus,
                ibmMvsDeviceConfigPackingMode,
                ibmMvsDeviceActualPackingMode,
                ibmMvsLinkType,
                ibmMvsLinkDeviceIndex,
                ibmMvsLinkAdapterAddr,
                ibmMvsLinkNumber,
                ibmMvsLinkIbmtrCanonical,
                ibmMvsLinkIbmtrBcast,
                ibmMvsLinkMcast,
                ibmMvsLinkChecksumEnabled,
                ibmMvsLinkArpSupport,
                ibmMvsLinkMacAddress,
                ibmMvsLinkMcastRefCount
              }
   STATUS  current
   DESCRIPTION
           "This group comprises those objects that are related
             to interface entries in the IF-MIB."
    ::= { ibmTCPIPmvsGroups 36 }

 ibmTCPIPmvsDVIPAGroup OBJECT-GROUP
   OBJECTS {
             ibmMvsDVIPAMaskType,
             ibmMvsDVIPAMaskAddr,
             ibmMvsDVIPAStatus,
             ibmMvsDVIPAOrigin,
             ibmMvsDVIPARank,
             ibmMvsDVIPADistributeStatus,
             ibmMvsDVIPAMoveable,
             ibmMvsDVIPAServMgrEnabled,
             ibmMvsDVIPARangeConfMoveable,
             ibmMvsDVIPARangeConfStatus,
             ibmMvsDVIPADistConfStatus,
             ibmMvsDVIPAConnDynXcfIpAddrType,
             ibmMvsDVIPAConnDynXcfIpAddr,
             ibmMvsDVIPAConnPolicyRuleName,
             ibmMvsDVIPAConnPolicyActionName,
             ibmMvsDVIPADistPortReadyCount,
             ibmMvsDVIPADistPortTotalConn,
             ibmMvsDVIPADistPortWlmWeight,
             ibmMvsDVIPAServMgrMulticastIpAddrType,
             ibmMvsDVIPAServMgrMulticastIpAddr,
             ibmMvsDVIPAServMgrPort,
             ibmMvsDVIPAServMgrPasswordSpecified,
             ibmMvsDVIPATrapControl
            }
   STATUS  current
   DESCRIPTION
           "This group comprises those objects that are related
            to Dynamic VIPA interfaces."
    ::= { ibmTCPIPmvsGroups 37 }

   ibmTCPIPmvsDVIPANotificationGroup NOTIFICATION-GROUP
   NOTIFICATIONS {
                ibmMvsDVIPAStatusChange,
                ibmMvsDVIPARemoved,
                ibmMvsDVIPATargetAdded,
                ibmMvsDVIPATargetRemoved,
                ibmMvsDVIPATargetServerStarted,
                ibmMvsDVIPATargetServerEnded
               }
   STATUS  current
   DESCRIPTION
           "This group comprises those notification objects that
            are related to Dynamic VIPA support."
   ::= { ibmTCPIPmvsGroups 38 }

   ibmTCPIPmvsSystemNotificationGroup NOTIFICATION-GROUP
   NOTIFICATIONS {
                ibmMvsTcpipSubagentColdStart
               }
   STATUS  current
   DESCRIPTION
           "This group comprises those notification objects that
            are related to the MVS System group."
   ::= { ibmTCPIPmvsGroups 39 }


   ibmTCPIPmvsAtmNotificationGroup NOTIFICATION-GROUP
   NOTIFICATIONS {
                ibmMvsAtmOsasfAtmPvcCreate,
                ibmMvsAtmOsasfAtmPvcDelete
               }
   STATUS  current
   DESCRIPTION
           "This group comprises those objects that are related
             to atm support."
   ::= { ibmTCPIPmvsGroups 7 }

--
-- obsolete definitions
--

   ibmTCPIPmvsObsoleteGroup OBJECT-GROUP
   OBJECTS {
                ibmSNMPRemPing
              }
   STATUS  obsolete
   DESCRIPTION
           "This group comprises those objects that are obsolete."
    ::= { ibmTCPIPmvsGroups 6 }

ibmTCPIPmvsTcpGroup OBJECT-GROUP
   OBJECTS {
               ibmMvsTcpConnLastActivity,
               ibmMvsTcpConnBytesIn,
               ibmMvsTcpConnBytesOut,
               ibmMvsTcpConnActiveOpen,
               ibmMvsTcpConnIpTos,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnSendWindowSeq,
               ibmMvsTcpConnSendWindowAck,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnPendTcpRecv,
               ibmMvsTcpConnRcvBufSize,
               ibmMvsTcpConnResourceName,
               ibmMvsTcpConnSubtask,
               ibmMvsTcpConnResourceId,
               ibmMvsTcpConnSockOpt,
               ibmMvsTcpConnTcpTimer,
               ibmMvsTcpConnTcpSig,
               ibmMvsTcpConnTcpSel,
               ibmMvsTcpConnRttSeq,
               ibmMvsTcpConnBackoffCount,
               ibmMvsTcpConnTcpDet,
               ibmMvsTcpConnTcpPol
                        }
   STATUS  obsolete
   DESCRIPTION
           "Defines the objects that are argumented to the tcpConnTable"
    ::= { ibmTCPIPmvsGroups 3 }

ibmTCPIPmvsSystemGroup OBJECT-GROUP
   OBJECTS {
                ibmMvsSubagentCacheTime
              }
   STATUS  obsolete
   DESCRIPTION
           " "
    ::= { ibmTCPIPmvsGroups 2 }

ibmTCPIPmvsSystemGroup2 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled
              }
   STATUS  obsolete
   DESCRIPTION
           " "
    ::= { ibmTCPIPmvsGroups 13 }

 ibmTCPIPmvsAtmSupportGroup OBJECT-GROUP
   OBJECTS {
               ibmMvsAtmOsasfChannelNumber,
               ibmMvsAtmOsasfChannelType,
               ibmMvsAtmOsasfChannelSubType,
               ibmMvsAtmOsasfChannelMode,
               ibmMvsAtmOsasfChannelHwModel,
               ibmMvsAtmOsasfChannelState,
               ibmMvsAtmOsasfChannelShared,
               ibmMvsAtmOsasfChannelNumPorts,
               ibmMvsAtmOsasfChannelDeterNodeDesc,
               ibmMvsAtmOsasfChannelControlUnitNumber,
               ibmMvsAtmOsasfChannelCodeLevel,
               ibmMvsAtmOsasfChannelEcLevel,
               ibmMvsAtmOsasfChannelCurLparName,
               ibmMvsAtmOsasfChannelCurLparNum,
               ibmMvsAtmOsasfChannelManParnName,
               ibmMvsAtmOsasfChannelManParnNum,
               ibmMvsAtmOsasfChannelDate,
               ibmMvsAtmOsasfChannelTime,
               ibmMvsAtmOsasfChannelFlashLevel,
               ibmMvsAtmOsasfChannelVtamId,
               ibmMvsAtmOsasfPortNumber,
               ibmMvsAtmOsasfPortType,
               ibmMvsAtmOsasfPortHardwareState,
               ibmMvsAtmOsasfPortMediaType,
               ibmMvsAtmOsasfPortUniType,
               ibmMvsAtmOsasfPortUniVersion,
               ibmMvsAtmOsasfPortNetPrefix,
               ibmMvsAtmOsasfPortNetPrefixPrefix,
               ibmMvsAtmOsasfPortNetPrefixStatus,
               ibmMvsAtmOsasfPortCodeLoadStatus,
               ibmMvsAtmOsasfPortMacAddrBurntIn,
               ibmMvsAtmOsasfPortMacAddrActive,
               ibmMvsAtmOsasfPortMaxPcmConnections,
               ibmMvsAtmOsasfPortPcmName,
               ibmMvsAtmOsasfPvcName,
               ibmMvsAtmOsasfPvcBestEffort,
               ibmMvsAtmOsasfPvcFwdPeakCellRate,
               ibmMvsAtmOsasfPvcBwdPeakCellRate,
               ibmMvsAtmOsasfPvcFwdsustainCellRate,
               ibmMvsAtmOsasfPvcBwdsustainCellRate,
               ibmMvsAtmOsasfPvcFwdCellBurstSize,
               ibmMvsAtmOsasfPvcBwdCellBurstSize,
               ibmMvsAtmOsasfPvcVpi,
               ibmMvsAtmOsasfPvcVci,
               ibmMvsAtmOsasfPvcFwdMaxAal5PduSize,
               ibmMvsAtmOsasfPvcBwdMaxAal5PduSize
              }
   STATUS  obsolete
   DESCRIPTION
           "This group comprises those objects that are related
             to atm support."
    ::= { ibmTCPIPmvsGroups 5 }

   ibmTCPIPmvsInterfacesGroup OBJECT-GROUP
   OBJECTS {
                ibmMvsDeviceType,
                ibmMvsDeviceBaseNumber,
                ibmMvsDeviceIoBufferSize,
                ibmMvsDeviceAutoRestart,
                ibmMvsDeviceNetmanEnabled,
                ibmMvsDeviceHostClawName,
                ibmMvsDeviceWorkstationClawName,
                ibmMvsDeviceReadBuffers,
                ibmMvsDeviceReadSize,
                ibmMvsDeviceWriteBuffers,
                ibmMvsDeviceWriteSize,
                ibmMvsDeviceProcname,
                ibmMvsDeviceIncomingSvcEnabled,
                ibmMvsDeviceLuName,
                ibmMvsLinkType,
                ibmMvsLinkDeviceIndex,
                ibmMvsLinkAdapterAddr,
                ibmMvsLinkNumber,
                ibmMvsLinkIbmtrCanonical,
                ibmMvsLinkIbmtrBcast
              }
   STATUS  obsolete
   DESCRIPTION
           "This group comprises those objects that are related
             to interface entries in the IF-MIB."
    ::= { ibmTCPIPmvsGroups 8 }

ibmTCPIPmvsUdpGroup OBJECT-GROUP
   OBJECTS {
               ibmMvsUdpLastAct,
               ibmMvsUdpTos,
               ibmMvsUdpIpOpts,
               ibmMvsUdpDgramIn,
               ibmMvsUdpBytesIn,
               ibmMvsUdpDgramOut,
               ibmMvsUdpBytesOut,
               ibmMvsUdpResourceName,
               ibmMvsUdpSubtask,
               ibmMvsUdpResourceId,
               ibmMvsUdpSockOpt,
               ibmMvsUdpSendLim,
               ibmMvsUdpRecvLim,
               ibmMvsUdpEntryState
              }
   STATUS  obsolete
   DESCRIPTION
           "This group defines those objects that are augmented to
             a udp listen table entry."
    ::= { ibmTCPIPmvsGroups 4 }

ibmTCPIPmvsSystemGroup3 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled,
                ibmMvsTcpMaxReceiveBufferSize,
                ibmMvsMultipathEnabled
              }
   STATUS  obsolete
   DESCRIPTION
           " "
    ::= { ibmTCPIPmvsGroups 15 }

   ibmTCPIPmvsInterfacesGroup2 OBJECT-GROUP
   OBJECTS {
                ibmMvsDeviceType,
                ibmMvsDeviceBaseNumber,
                ibmMvsDeviceIoBufferSize,
                ibmMvsDeviceAutoRestart,
                ibmMvsDeviceNetmanEnabled,
                ibmMvsDeviceHostClawName,
                ibmMvsDeviceWorkstationClawName,
                ibmMvsDeviceReadBuffers,
                ibmMvsDeviceReadSize,
                ibmMvsDeviceWriteBuffers,
                ibmMvsDeviceWriteSize,
                ibmMvsDeviceProcname,
                ibmMvsDeviceIncomingSvcEnabled,
                ibmMvsDeviceLuName,
                ibmMvsLinkType,
                ibmMvsLinkDeviceIndex,
                ibmMvsLinkAdapterAddr,
                ibmMvsLinkNumber,
                ibmMvsLinkIbmtrCanonical,
                ibmMvsLinkIbmtrBcast,
                ibmMvsLinkMcast,
                ibmMvsLinkMcastRefCount
              }
   STATUS  obsolete
   DESCRIPTION
           "This group comprises those objects that are related
             to interface entries in the IF-MIB."
    ::= { ibmTCPIPmvsGroups 16 }

ibmTCPIPmvsTcpGroup2 OBJECT-GROUP
   OBJECTS {
               ibmMvsTcpConnLastActivity,
               ibmMvsTcpConnBytesIn,
               ibmMvsTcpConnBytesOut,
               ibmMvsTcpConnActiveOpen,
               ibmMvsTcpConnIpTos,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnPendTcpRecv,
               ibmMvsTcpConnRcvBufSize,
               ibmMvsTcpConnResourceName,
               ibmMvsTcpConnSubtask,
               ibmMvsTcpConnResourceId,
               ibmMvsTcpConnSockOpt,
               ibmMvsTcpConnTcpTimer,
               ibmMvsTcpConnTcpSig,
               ibmMvsTcpConnTcpSel,
               ibmMvsTcpConnRttSeq,
               ibmMvsTcpConnBackoffCount,
               ibmMvsTcpConnTcpDet,
               ibmMvsTcpConnTcpPol,
               ibmMvsTcpConnTargetAppl,
               ibmMvsTcpConnLuName,
               ibmMvsTcpConnClientUserId,
               ibmMvsTcpConnLogMode,
               ibmMvsTcpConnProto,
               ibmMvsTcpConnDupacks,
               ibmMvsTcpConnOptMaxSegmentSize
              }
   STATUS  obsolete
   DESCRIPTION
           "Defines the objects that are augmented to the tcpConnTable"
    ::= { ibmTCPIPmvsGroups 12 }

ibmTCPIPmvsSystemGroup4 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled,
                ibmMvsTcpMaxReceiveBufferSize,
                ibmMvsMultipathEnabled,
                ibmMvsPathMtuDscEnabled
              }
   STATUS  obsolete
   DESCRIPTION
           " "
    ::= { ibmTCPIPmvsGroups 18 }

ibmTCPIPmvsTcpGroup3 OBJECT-GROUP
   OBJECTS {
               ibmMvsTcpConnLastActivity,
               ibmMvsTcpConnBytesIn,
               ibmMvsTcpConnBytesOut,
               ibmMvsTcpConnActiveOpen,
               ibmMvsTcpConnIpTos,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnPendTcpRecv,
               ibmMvsTcpConnRcvBufSize,
               ibmMvsTcpConnResourceName,
               ibmMvsTcpConnSubtask,
               ibmMvsTcpConnResourceId,
               ibmMvsTcpConnSockOpt,
               ibmMvsTcpConnTcpTimer,
               ibmMvsTcpConnTcpSig,
               ibmMvsTcpConnTcpSel,
               ibmMvsTcpConnRttSeq,
               ibmMvsTcpConnBackoffCount,
               ibmMvsTcpConnTcpDet,
               ibmMvsTcpConnTcpPol,
               ibmMvsTcpConnTargetAppl,
               ibmMvsTcpConnLuName,
               ibmMvsTcpConnClientUserId,
               ibmMvsTcpConnLogMode,
               ibmMvsTcpConnProto,
               ibmMvsTcpConnDupacks,
               ibmMvsTcpConnOptMaxSegmentSize,
               ibmMvsTcpConnClusterConnFlag
              }
   STATUS  obsolete
   DESCRIPTION
           "Defines the objects that are augmented to the tcpConnTable"
    ::= { ibmTCPIPmvsGroups 20 }

 ibmTCPIPmvsAtmSupportGroup2 OBJECT-GROUP
   OBJECTS {
               ibmMvsAtmOsasfChannelNumber,
               ibmMvsAtmOsasfChannelType,
               ibmMvsAtmOsasfChannelSubType,
               ibmMvsAtmOsasfChannelMode,
               ibmMvsAtmOsasfChannelHwModel,
               ibmMvsAtmOsasfChannelState,
               ibmMvsAtmOsasfChannelShared,
               ibmMvsAtmOsasfChannelNumPorts,
               ibmMvsAtmOsasfChannelDeterNodeDesc,
               ibmMvsAtmOsasfChannelControlUnitNumber,
               ibmMvsAtmOsasfChannelCodeLevel,
               ibmMvsAtmOsasfChannelEcLevel,
               ibmMvsAtmOsasfChannelCurLparName,
               ibmMvsAtmOsasfChannelCurLparNum,
               ibmMvsAtmOsasfChannelManParnName,
               ibmMvsAtmOsasfChannelManParnNum,
               ibmMvsAtmOsasfChannelDate,
               ibmMvsAtmOsasfChannelTime,
               ibmMvsAtmOsasfChannelFlashLevel,
               ibmMvsAtmOsasfChannelVtamId,
               ibmMvsAtmOsasfPortNumber,
               ibmMvsAtmOsasfPortType,
               ibmMvsAtmOsasfPortHardwareState,
               ibmMvsAtmOsasfPortMediaType,
               ibmMvsAtmOsasfPortUniType,
               ibmMvsAtmOsasfPortUniVersion,
               ibmMvsAtmOsasfPortNetPrefix,
               ibmMvsAtmOsasfPortNetPrefixPrefix,
               ibmMvsAtmOsasfPortNetPrefixStatus,
               ibmMvsAtmOsasfPortCodeLoadStatus,
               ibmMvsAtmOsasfPortMacAddrBurntIn,
               ibmMvsAtmOsasfPortMacAddrActive,
               ibmMvsAtmOsasfPortMaxPcmConnections,
               ibmMvsAtmOsasfPortPcmName,
               ibmMvsAtmOsasfPortAAL5InPackets,
               ibmMvsAtmOsasfPortAAL5OutPackets,
               ibmMvsAtmOsasfPortIpAddress,
               ibmMvsAtmOsasfPvcName,
               ibmMvsAtmOsasfPvcBestEffort,
               ibmMvsAtmOsasfPvcFwdPeakCellRate,
               ibmMvsAtmOsasfPvcBwdPeakCellRate,
               ibmMvsAtmOsasfPvcFwdsustainCellRate,
               ibmMvsAtmOsasfPvcBwdsustainCellRate,
               ibmMvsAtmOsasfPvcFwdCellBurstSize,
               ibmMvsAtmOsasfPvcBwdCellBurstSize,
               ibmMvsAtmOsasfPvcVpi,
               ibmMvsAtmOsasfPvcVci,
               ibmMvsAtmOsasfPvcFwdMaxAal5PduSize,
               ibmMvsAtmOsasfPvcBwdMaxAal5PduSize
              }
   STATUS  obsolete
   DESCRIPTION
           "This group comprises those objects that are related
             to atm support."
    ::= { ibmTCPIPmvsGroups 14 }

   ibmTCPIPmvsInterfacesGroup3 OBJECT-GROUP
   OBJECTS {
                ibmMvsDeviceType,
                ibmMvsDeviceBaseNumber,
                ibmMvsDeviceIoBufferSize,
                ibmMvsDeviceAutoRestart,
                ibmMvsDeviceNetmanEnabled,
                ibmMvsDeviceHostClawName,
                ibmMvsDeviceWorkstationClawName,
                ibmMvsDeviceReadBuffers,
                ibmMvsDeviceReadSize,
                ibmMvsDeviceWriteBuffers,
                ibmMvsDeviceWriteSize,
                ibmMvsDeviceProcname,
                ibmMvsDeviceIncomingSvcEnabled,
                ibmMvsDeviceLuName,
                ibmMvsDeviceRouterStatus,
                ibmMvsLinkType,
                ibmMvsLinkDeviceIndex,
                ibmMvsLinkAdapterAddr,
                ibmMvsLinkNumber,
                ibmMvsLinkIbmtrCanonical,
                ibmMvsLinkIbmtrBcast,
                ibmMvsLinkMcast,
                ibmMvsLinkChecksumEnabled,
                ibmMvsLinkMcastRefCount
              }
   STATUS  obsolete
   DESCRIPTION
           "This group comprises those objects that are related
             to interface entries in the IF-MIB."
    ::= { ibmTCPIPmvsGroups 19 }

   ibmTCPIPmvsPortGroup OBJECT-GROUP
   OBJECTS {
                ibmMvsPortNumberLow,
                ibmMvsPortNumberHigh,
                ibmMvsPortProtocol,
                ibmMvsPortProcName,
                ibmMvsPortAutoLoggable,
                ibmMvsPortDelayAcks,
                ibmMvsPortOptMaxSegmentSize,
                ibmMvsPortSharePort
             }
   STATUS  obsolete
   DESCRIPTION
           "This group comprises those objects that represent the
             current set of PORT and PORTRANGE definitions
             for this TCP/IP instance."
    ::= { ibmTCPIPmvsGroups 10 }

 ibmTCPIPmvsAtmSupportGroup3 OBJECT-GROUP
   OBJECTS {
               ibmMvsAtmOsasfChannelNumber,
               ibmMvsAtmOsasfChannelType,
               ibmMvsAtmOsasfChannelSubType,
               ibmMvsAtmOsasfChannelMode,
               ibmMvsAtmOsasfChannelHwModel,
               ibmMvsAtmOsasfChannelState,
               ibmMvsAtmOsasfChannelShared,
               ibmMvsAtmOsasfChannelNumPorts,
               ibmMvsAtmOsasfChannelDeterNodeDesc,
               ibmMvsAtmOsasfChannelControlUnitNumber,
               ibmMvsAtmOsasfChannelCodeLevel,
               ibmMvsAtmOsasfChannelEcLevel,
               ibmMvsAtmOsasfChannelCurLparName,
               ibmMvsAtmOsasfChannelCurLparNum,
               ibmMvsAtmOsasfChannelManParnName,
               ibmMvsAtmOsasfChannelManParnNum,
               ibmMvsAtmOsasfChannelDate,
               ibmMvsAtmOsasfChannelTime,
               ibmMvsAtmOsasfChannelFlashLevel,
               ibmMvsAtmOsasfPortNumber,
               ibmMvsAtmOsasfPortType,
               ibmMvsAtmOsasfPortHardwareState,
               ibmMvsAtmOsasfPortMediaType,
               ibmMvsAtmOsasfPortUniType,
               ibmMvsAtmOsasfPortUniVersion,
               ibmMvsAtmOsasfPortNetPrefix,
               ibmMvsAtmOsasfPortNetPrefixPrefix,
               ibmMvsAtmOsasfPortNetPrefixStatus,
               ibmMvsAtmOsasfPortCodeLoadStatus,
               ibmMvsAtmOsasfPortMacAddrBurntIn,
               ibmMvsAtmOsasfPortMacAddrActive,
               ibmMvsAtmOsasfPortMaxPcmConnections,
               ibmMvsAtmOsasfPortPcmName,
               ibmMvsAtmOsasfPortAAL5InPackets,
               ibmMvsAtmOsasfPortAAL5OutPackets,
               ibmMvsAtmOsasfPortIpAddress,
               ibmMvsAtmOsasfPvcName,
               ibmMvsAtmOsasfPvcBestEffort,
               ibmMvsAtmOsasfPvcFwdPeakCellRate,
               ibmMvsAtmOsasfPvcBwdPeakCellRate,
               ibmMvsAtmOsasfPvcFwdsustainCellRate,
               ibmMvsAtmOsasfPvcBwdsustainCellRate,
               ibmMvsAtmOsasfPvcFwdCellBurstSize,
               ibmMvsAtmOsasfPvcBwdCellBurstSize,
               ibmMvsAtmOsasfPvcVpi,
               ibmMvsAtmOsasfPvcVci,
               ibmMvsAtmOsasfPvcFwdMaxAal5PduSize,
               ibmMvsAtmOsasfPvcBwdMaxAal5PduSize
              }
   STATUS  obsolete
   DESCRIPTION
           "This group comprises those objects that are related
             to atm support."
    ::= { ibmTCPIPmvsGroups 24 }

ibmTCPIPmvsTcpGroup4 OBJECT-GROUP
   OBJECTS {
               ibmMvsTcpConnLastActivity,
               ibmMvsTcpConnBytesIn,
               ibmMvsTcpConnBytesOut,
               ibmMvsTcpConnIpTos,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnRcvBufSize,
               ibmMvsTcpConnResourceName,
               ibmMvsTcpConnSubtask,
               ibmMvsTcpConnResourceId,
               ibmMvsTcpConnSockOpt,
               ibmMvsTcpConnTcpTimer,
               ibmMvsTcpConnTcpSig,
               ibmMvsTcpConnTcpSel,
               ibmMvsTcpConnRttSeq,
               ibmMvsTcpConnTcpDet,
               ibmMvsTcpConnTcpPol,
               ibmMvsTcpConnTargetAppl,
               ibmMvsTcpConnLuName,
               ibmMvsTcpConnClientUserId,
               ibmMvsTcpConnLogMode,
               ibmMvsTcpConnProto,
               ibmMvsTcpConnDupacks,
               ibmMvsTcpConnOptMaxSegmentSize,
               ibmMvsTcpConnClusterConnFlag,
               ibmMvsTcpConnInSegs,
               ibmMvsTcpConnOutSegs
              }
   STATUS  obsolete
   DESCRIPTION
           "Defines the objects that are augmented to the tcpConnTable"
    ::= { ibmTCPIPmvsGroups 22 }

ibmTCPIPmvsUdpGroup2 OBJECT-GROUP
   OBJECTS {
               ibmMvsUdpLastAct,
               ibmMvsUdpTos,
               ibmMvsUdpIpOpts,
               ibmMvsUdpDgramIn,
               ibmMvsUdpBytesIn,
               ibmMvsUdpDgramOut,
               ibmMvsUdpBytesOut,
               ibmMvsUdpResourceName,
               ibmMvsUdpSubtask,
               ibmMvsUdpResourceId,
               ibmMvsUdpSockOpt,
               ibmMvsUdpSendLim,
               ibmMvsUdpRecvLim,
               ibmMvsUdpEntryState,
               ibmMvsUdpMcastTTL,
               ibmMvsUdpMcastLoopback,
               ibmMvsUdpMcastLinkAddr,
               ibmMvsUdpMcastRecvLinkAddr
              }
   STATUS  obsolete
   DESCRIPTION
           "This group defines those objects that are argumented to
             a udp listen table entry."
    ::= { ibmTCPIPmvsGroups 17 }

   ibmTCPIPmvsAtmLeGroup OBJECT-GROUP
   OBJECTS {
                ibmMvsAtmSnaLeLlcTi,
                ibmMvsAtmSnaLeLlcT1,
                ibmMvsAtmSnaLeLlcT2,
                ibmMvsAtmSnaleMaxStations,
                ibmMvsAtmSnaLeMaxSaps,
                ibmMvsAtmSnaleMaxIn,
                ibmMvsAtmSnaLeMaxOut,
                ibmMvsAtmSnaLeCrsGroupAddress,
                ibmMvsAtmSnaLeUserData,
                ibmMvsAtmSnaLeClientEnableState,
                ibmMvsAtmSnaLeBestEffortPeakRate,
                ibmMvsAtmSnaLeMaxLECConnections,
                ibmMvsAtmSnaLeTrEnableLoadBalancing,
                ibmMvsAtmSnaLeTrLoadBalancing,
                ibmMvsAtmSnaLeTrSessionDelay,
                ibmMvsAtmLecConfigMode,
                ibmMvsAtmLecConfigLanType,
                ibmMvsAtmLecConfigMaxDataFrameSize,
                ibmMvsAtmLecConfigLanName,
                ibmMvsAtmLecConfigLesAtmAddress,
                ibmMvsAtmLecControlTimeout,
                ibmMvsAtmLecMaxUnknownFrameCount,
                ibmMvsAtmLecMaxUnknownFrameTime,
                ibmMvsAtmLecVccTimeoutPeriod,
                ibmMvsAtmLecMaxRetryCount,
                ibmMvsAtmLecAgingTime,
                ibmMvsAtmLecForwardDelayTime,
                ibmMvsAtmLecExpectedArpResponseTime,
                ibmMvsAtmLecFlushTimeout,
                ibmMvsAtmLecPathSwitchingDelay,
                ibmMvsAtmLecLocalSegmentID,
                ibmMvsAtmLecMulticastSendType,
                ibmMvsAtmLecMulticastSendAvgRate,
                ibmMvsAtmLecMulticastSendPeakRate,
                ibmMvsAtmLecConnectionCompleteTimer,
                ibmMvsAtmLecPrimaryAtmAddress,
                ibmMvsAtmLecID,
                ibmMvsAtmLecInterfaceState,
                ibmMvsAtmLecLastFailureRespCode,
                ibmMvsAtmLecLastFailureState,
                ibmMvsAtmLecProtocol,
                ibmMvsAtmLecVersion,
                ibmMvsAtmLecTopologyChange,
                ibmMvsAtmLecConfigServerAtmAddress,
                ibmMvsAtmLecConfigSource,
                ibmMvsAtmLecActualLanType,
                ibmMvsAtmLecActualMaxDataFrameSize,
                ibmMvsAtmLecActualLanName,
                ibmMvsAtmLecAtmAddress,
                ibmMvsAtmLecProxyClient,
                ibmMvsAtmLecArpRequestsOut,
                ibmMvsAtmLecArpRequestsIn,
                ibmMvsAtmLecArpRepliesOut,
                ibmMvsAtmLecArpRepliesIn,
                ibmMvsAtmLecControlFramesOut,
                ibmMvsAtmLecControlFramesIn,
                ibmMvsAtmLecSvcFailures,
                ibmMvsAtmLecConfigDirectInterface,
                ibmMvsAtmLecConfigDirectVPI,
                ibmMvsAtmLecConfigDirectVCI,
                ibmMvsAtmLecControlDirectInterface,
                ibmMvsAtmLecControlDirectVPI,
                ibmMvsAtmLecControlDirectVCI,
                ibmMvsAtmLecControlDistributeInterface,
                ibmMvsAtmLecControlDistributeVPI,
                ibmMvsAtmLecControlDistributeVCI,
                ibmMvsAtmLecMulticastSendInterface,
                ibmMvsAtmLecMulticastSendVPI,
                ibmMvsAtmLecMulticastSendVCI,
                ibmMvsAtmLecMulticastFwdInterface,
                ibmMvsAtmLecMulticastFwdVPI,
                ibmMvsAtmLecMulticastFwdVCI,
                ibmMvsAtmLecMacAddress
              }
   STATUS  obsolete
   DESCRIPTION
           "This group comprises those objects that are related
             to ATM LAN Emulation support."
    ::= { ibmTCPIPmvsGroups 9 }

ibmTCPIPmvsSystemGroup5 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled,
                ibmMvsTcpMaxReceiveBufferSize,
                ibmMvsPathMtuDscEnabled,
                ibmMvsMultipathType,
                ibmMvsIpForwarding
              }
   STATUS  obsolete
   DESCRIPTION
           " "
    ::= { ibmTCPIPmvsGroups 21 }

ibmTCPIPmvsTcpGroup5 OBJECT-GROUP
   OBJECTS {
               ibmMvsTcpConnLastActivity,
               ibmMvsTcpConnBytesIn,
               ibmMvsTcpConnBytesOut,
               ibmMvsTcpConnOptions,
               ibmMvsTcpConnOutBuffered,
               ibmMvsTcpConnUsrSndNxt,
               ibmMvsTcpConnSndNxt,
               ibmMvsTcpConnSndUna,
               ibmMvsTcpConnOutgoingPush,
               ibmMvsTcpConnOutgoingUrg,
               ibmMvsTcpConnOutgoingWinSeq,
               ibmMvsTcpConnInBuffered,
               ibmMvsTcpConnRcvNxt,
               ibmMvsTcpConnUsrRcvNxt,
               ibmMvsTcpConnIncomingPush,
               ibmMvsTcpConnIncomingUrg,
               ibmMvsTcpConnIncomingWinSeq,
               ibmMvsTcpConnReXmt,
               ibmMvsTcpConnMaxSndWnd,
               ibmMvsTcpConnReXmtCount,
               ibmMvsTcpConnCongestionWnd,
               ibmMvsTcpConnSSThresh,
               ibmMvsTcpConnRoundTripTime,
               ibmMvsTcpConnRoundTripVariance,
               ibmMvsTcpConnInitSndSeq,
               ibmMvsTcpConnInitRcvSeq,
               ibmMvsTcpConnSendMSS,
               ibmMvsTcpConnSndWl1,
               ibmMvsTcpConnSndWl2,
               ibmMvsTcpConnSndWnd,
               ibmMvsTcpConnRcvBufSize,
               ibmMvsTcpConnResourceName,
               ibmMvsTcpConnSubtask,
               ibmMvsTcpConnResourceId,
               ibmMvsTcpConnSockOpt,
               ibmMvsTcpConnTcpTimer,
               ibmMvsTcpConnTcpSig,
               ibmMvsTcpConnTcpSel,
               ibmMvsTcpConnRttSeq,
               ibmMvsTcpConnTcpDet,
               ibmMvsTcpConnTcpPol,
               ibmMvsTcpConnTargetAppl,
               ibmMvsTcpConnLuName,
               ibmMvsTcpConnClientUserId,
               ibmMvsTcpConnLogMode,
               ibmMvsTcpConnProto,
               ibmMvsTcpConnDupacks,
               ibmMvsTcpConnOptMaxSegmentSize,
               ibmMvsTcpConnClusterConnFlag,
               ibmMvsTcpConnInSegs,
               ibmMvsTcpConnOutSegs,
               ibmMvsTcpConnDSField
              }
   STATUS  obsolete
   DESCRIPTION
           "Defines the objects that are augmented to the tcpConnTable"
    ::= { ibmTCPIPmvsGroups 28 }

ibmTCPIPmvsSystemGroup6 OBJECT-GROUP
   OBJECTS {
                ibmMvsSubagentCacheTime,
                ibmMvsIgnoreRedirect,
                ibmMvsArpCacheTimeout,
                ibmMvsTcpKeepAliveTimer,
                ibmMvsTcpReceiveBufferSize,
                ibmMvsTcpSendBufferSize,
                ibmMvsUdpChecksum,
                ibmMvsIplDateAndTime,
                ibmMvsNoUdpQueueLimit,
                ibmMvsSoMaxConn,
                ibmMvsTcpipProcname,
                ibmMvsTcpipAsid,
                ibmMvsSourceVipaEnabled,
                ibmMvsOsasfSysplexName,
                ibmMvsOsasfHostName,
                ibmMvsOsasfProductVersion,
                ibmMvsPrimaryInterfaceIfIndex,
                ibmMvsIpMaxReassemblySize,
                ibmMvsTcpRestrictLowPorts,
                ibmMvsUdpRestrictLowPorts,
                ibmMvsUdpSendBufferSize,
                ibmMvsUdpRecvBufferSize,
                ibmMvsTcpipStatisticsEnabled,
                ibmMvsFirewallEnabled,
                ibmMvsMaximumRetransmitTime,
                ibmMvsMinimumRetransmitTime,
                ibmMvsRoundTripGain,
                ibmMvsVarianceMultiplier,
                ibmMvsVarianceGain,
                ibmMvsSendGarbageEnabled,
                ibmMvsTcpMaxReceiveBufferSize,
                ibmMvsPathMtuDscEnabled,
                ibmMvsMultipathType,
                ibmMvsIpForwarding,
                ibmMvsDevRetryDuration
              }
   STATUS  obsolete
   DESCRIPTION
           " "
    ::= { ibmTCPIPmvsGroups 31 }

   ibmTCPIPmvsInterfacesGroup4 OBJECT-GROUP
   OBJECTS {
                ibmMvsDeviceType,
                ibmMvsDeviceBaseNumber,
                ibmMvsDeviceIoBufferSize,
                ibmMvsDeviceAutoRestart,
                ibmMvsDeviceNetmanEnabled,
                ibmMvsDeviceHostClawName,
                ibmMvsDeviceWorkstationClawName,
                ibmMvsDeviceReadBuffers,
                ibmMvsDeviceReadSize,
                ibmMvsDeviceWriteBuffers,
                ibmMvsDeviceWriteSize,
                ibmMvsDeviceProcname,
                ibmMvsDeviceIncomingSvcEnabled,
                ibmMvsDeviceLuName,
                ibmMvsDeviceRouterStatus,
                ibmMvsDeviceActualRouterStatus,
                ibmMvsLinkType,
                ibmMvsLinkDeviceIndex,
                ibmMvsLinkAdapterAddr,
                ibmMvsLinkNumber,
                ibmMvsLinkIbmtrCanonical,
                ibmMvsLinkIbmtrBcast,
                ibmMvsLinkMcast,
                ibmMvsLinkChecksumEnabled,
                ibmMvsLinkArpSupport,
                ibmMvsLinkMcastRefCount
              }
   STATUS  obsolete
   DESCRIPTION
           "This group comprises those objects that are related
             to interface entries in the IF-MIB."
    ::= { ibmTCPIPmvsGroups 25 }
END
