DATAPOWER-NOTIFICATION-MIB DEFINITIONS ::= BEGIN


-- Programmatically Generated; do not edit

-- Licensed Materials - Property of IBM
-- IBM WebSphere DataPower Appliances
-- Copyright IBM Corporation 2007,2017. All Rights Reserved.
-- US Government Users Restricted Rights - Use, duplication or disclosure
-- restricted by GSA ADP Schedule Contract with IBM Corp.

IMPORTS
    enterprises, MODULE-IDENTITY, OBJECT-TYPE,
    NOTIFICATION-TYPE, Unsigned32
        FROM SNMPv2-SMI
    TEXTUAL-CONVENTION, DisplayString
        FROM SNMPv2-TC;

dpNotificationMIB MODULE-IDENTITY
    LAST-UPDATED "200701110000Z"
    ORGANIZATION "IBM Corporation"
    CONTACT-INFO "IBM Corporation, Application Integration and Middleware, DataPower SOA Appliances. Web:
    http://www-306.ibm.com/software/integration/datapower/support/ Email: csupport@us.ibm.com"
    DESCRIPTION "The MIB module for notifications of a DataPower XML device."
    REVISION "200701110000Z"
    DESCRIPTION "Updated"

    ::= { dpModules 3 }

datapower OBJECT IDENTIFIER ::= { enterprises 14685 }

dpModules OBJECT IDENTIFIER ::= { datapower 2 }

dpManagement OBJECT IDENTIFIER ::= { datapower 3 }

dpNotifications OBJECT IDENTIFIER ::= { dpManagement 3 }

dpNotificationElements OBJECT IDENTIFIER ::= { dpNotifications 1 }

dpNotificationType OBJECT-TYPE
    SYNTAX      INTEGER {
                        all(3),
                        aaa(4),
                        auth(5),
                        cli(6),
                        crypto(7),
                        file(8),
                        file-capture(9),
                        http(10),
                        ldap(11),
                        mgmt(12),
                        mime(13),
                        monitor(14),
                        mq(15),
                        multistep(16),
                        network(17),
                        ssl(18),
                        schema(19),
                        smtp(20),
                        system(21),
                        tam(22),
                        user(23),
                        useragent(24),
                        xslcoproc(25),
                        xmlfilter(26),
                        xmlfirewall(27),
                        xslt(28),
                        xsltmsg(29),
                        xmlparse(30),
                        xslproxy(31),
                        xmlroute(32),
                        cert-monitor(33),
                        ocsp(34),
                        ftp(68),
                        ws-proxy(69),
                        wsm-agent(70),
                        mpgw(71),
                        kerberos(72),
                        slm(73),
                        sql(74),
                        network-file(76),
                        icap(77),
                        webapp-firewall(78),
                        http-convert(79),
                        tibco-ems(80),
                        xacml(81),
                        ltpa(82),
                        latency(83),
                        wasjms(84),
                        file-poller(85),
                        tfim(86),
                        uddisub(87),
                        wsrr(88),
                        rbm(89),
                        rpcsec-gss(90),
                        secure-conversation(91),
                        ims(92),
                        iscsi(93),
                        audit(94),
                        wtx(95),
                        zosnss(96),
                        llm(97),
                        ssh(98),
                        sftp(99),
                        b2bgw(100),
                        b2bp(101),
                        cms(102),
                        uddi(246),
                        wcc(247),
                        self-balancing(248),
                        sysplexdistributor(249),
                        quiesce(250),
                        fibre-channel(251),
                        cluster-service(252),
                        secure-cloud-connector(253),
                        ipmi(254),
                        memory-report(255),
                        waxhn(256),
                        wag(257),
                        ip-multicast(258),
                        peer-group(259),
                        web-token-service(260),
                        oauth(261),
                        xc10-grid(262),
                        odr-connector-group(264),
                        odr(265),
                        odrlib(266),
                        gatewayscript(267),
                        gatewayscript-user(268),
                        extlatency(269),
                        cloud-gateway(270),
                        cloud-connector(271),
                        isamproxy(272),
                        wxs-grid(273),
                        sgclient(274),
                        apiconnect(275),
                        redis(276),
                        quota-enforcement(277),
                        networkhsm-luna(278),
                        dfdl(279),
                        xformng(280),
                        xquery(281),
                        parse(283),
                        tenant(284),
                        product-insights(285),
                        apigw(286),
                        apic-gw-service(287),
                        gateway-peering(288),
                        ilmt-scanner(289),
                        ilmt-force-scan(290),
                        gateway-peering-manager(291),
                        opentracing(292)
                }
    MAX-ACCESS  accessible-for-notify
    STATUS      current
    DESCRIPTION "No description yet."

    ::= { dpNotificationElements 1 }

dpNotificationSeverity OBJECT-TYPE
    SYNTAX      INTEGER {
                        emerg(1),
                        alert(2),
                        critic(3),
                        error(4),
                        warn(5),
                        notice(6),
                        info(7),
                        debug(8)
                }
    MAX-ACCESS  accessible-for-notify
    STATUS      current
    DESCRIPTION "No description yet."

    ::= { dpNotificationElements 2 }

dpNotificationTime OBJECT-TYPE
    SYNTAX      DisplayString
    MAX-ACCESS  accessible-for-notify
    STATUS      current
    DESCRIPTION "No description yet."

    ::= { dpNotificationElements 3 }

dpNotificationText OBJECT-TYPE
    SYNTAX      DisplayString
    MAX-ACCESS  accessible-for-notify
    STATUS      current
    DESCRIPTION "No description yet."

    ::= { dpNotificationElements 4 }

dpNotificationObject OBJECT-TYPE
    SYNTAX      OBJECT IDENTIFIER
    MAX-ACCESS  accessible-for-notify
    STATUS      current
    DESCRIPTION "No description yet."

    ::= { dpNotificationElements 5 }

dpNotificationObjectName OBJECT-TYPE
    SYNTAX      DisplayString
    MAX-ACCESS  accessible-for-notify
    STATUS      current
    DESCRIPTION "No description yet."

    ::= { dpNotificationElements 6 }

dpNotificationTransId OBJECT-TYPE
    SYNTAX      Unsigned32
    MAX-ACCESS  accessible-for-notify
    STATUS      current
    DESCRIPTION "No description yet."

    ::= { dpNotificationElements 7 }

dpNotificationDomain OBJECT-TYPE
    SYNTAX      DisplayString
    MAX-ACCESS  accessible-for-notify
    STATUS      current
    DESCRIPTION "No description yet."

    ::= { dpNotificationElements 8 }

dpNotificationEventCode OBJECT-TYPE
    SYNTAX      DisplayString
    MAX-ACCESS  accessible-for-notify
    STATUS      current
    DESCRIPTION
        "The Log Event Code defined by the system or by users"

    ::= { dpNotificationElements 9 }

dpNotificationDefinitions OBJECT IDENTIFIER ::= { dpNotifications 2 }

dpLogNotification NOTIFICATION-TYPE
    OBJECTS {
        dpNotificationType,
        dpNotificationSeverity,
        dpNotificationTime,
        dpNotificationObject,
        dpNotificationObjectName,
        dpNotificationTransId,
        dpNotificationText,
        dpNotificationDomain    }
    STATUS current
    DESCRIPTION
        "Encapsulates a DataPower logging message in an SNMP notification."
    ::= { dpNotificationDefinitions 0 1 }

dpLogInternalNotification NOTIFICATION-TYPE
    OBJECTS {
        dpNotificationType,
        dpNotificationSeverity,
        dpNotificationTime,
        dpNotificationTransId,
        dpNotificationText,
        dpNotificationDomain    }
    STATUS current
    DESCRIPTION
        "Encapsulates a generic DataPower logging message in SNMP notification."
    ::= { dpNotificationDefinitions 0 2 }

END
