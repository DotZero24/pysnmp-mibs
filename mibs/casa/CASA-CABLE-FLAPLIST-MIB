CASA-CABLE-FLAPLIST-MIB DEFINITIONS ::= BEGIN

		IMPORTS
			casa
				FROM CASA-MIB
			ifIndex
				FROM IF-MIB
			Integer32, Unsigned32, BITS, OBJECT-TYPE, MODULE-IDENTITY
				FROM SNMPv2-SMI
			TruthValue,MacAddress, RowStatus, DateAndTime
				FROM SNMPv2-TC;         -- [RFC2579]


		-- 1.3.6.1.4.1.20858.10.11
		casaFlapListMib MODULE-IDENTITY
			LAST-UPDATED "200809051453Z"		-- September 05, 2008 at 14:53 GMT
			ORGANIZATION
				"Casa Systems Inc"
			CONTACT-INFO
				"Guangzhou Casa Communications Ltd.
				No.206 YueHe Bld,Huacui Str.
				Tianhe Industrial Park Guangzhou China
				TEL:020 85545002/85577786 ext.212
				FAX:020 85545002 ext.230
				E-mail: huangxiaole@casachina.com.cn "
			DESCRIPTION
				"This is the enterprise MIB Module for CASA systems CMTS."
			::= { casaMgmt 11 }




--
-- Node definitions
--

		-- 1.3.6.1.4.1.20858.10
		casaMgmt OBJECT IDENTIFIER ::= { casa 10 }


		-- 1.3.6.1.4.1.20858.10.11.1
		casaFlapListMIBObjects OBJECT IDENTIFIER ::= { casaFlapListMib 1 }


		-- 1.3.6.1.4.1.20858.10.11.1.1
		casaFlapListGlobal OBJECT IDENTIFIER ::= { casaFlapListMIBObjects 1 }


		-- 1.3.6.1.4.1.20858.10.11.1.1.1
		casaFlapInsertionTime OBJECT-TYPE
			SYNTAX Unsigned32
			UNITS "seconds"
			MAX-ACCESS read-write
			STATUS current
			DESCRIPTION
				"If the Cable Modem continuously send initial ranging request within a fixed time
				 interval ,the Cable Modem will be added to the casaFlapListTable.
				 0 means no matter the Cable Modem continuously send initial rangeing in any interval,
				 the Cable Modem won't be added to the casaFlapListTable.
				"
			DEFVAL { 60 }
			::= { casaFlapListGlobal 1 }


		-- 1.3.6.1.4.1.20858.10.11.1.1.2
		casaFlapMissThreshold OBJECT-TYPE
			SYNTAX Unsigned32 (0..20)
			UNITS "times"
			MAX-ACCESS read-write
			STATUS current
			DESCRIPTION
				"When the number of times a Cable Modem does not acknowledge
				 	a MAC-layer station maintenance message from a CMTS exceeds
				 	this threshold, the Cable Modem will be add to the
				 	casaFlapListTable.
				 0 means no matter how many times the Cable Modem does not acknowledge
				 	a MAC-layer station maintenance message from a CMTS, the Cable Modem
				 	won't be added to the casaFlapListTable.
				"
			DEFVAL { 6 }
			::= { casaFlapListGlobal 2 }


		-- 1.3.6.1.4.1.20858.10.11.1.1.3
		casaFlapPowerAdjThreshold OBJECT-TYPE
			SYNTAX Unsigned32
			UNITS "dB"
			MAX-ACCESS read-write
			STATUS current
			DESCRIPTION
				"When the power level a Cable Modem send to Cmts after online exceeds
				 	this threshold, the Cable Modem will be add to the
				 	casaFlapListTable.
				 0 means no metter how much power level the Cable Modem send to Cmts after
				 online, the Cable Modem won't be added to the casaFlapListTable.
				"
			DEFVAL { 2 }
			::= { casaFlapListGlobal 3 }


		-- 1.3.6.1.4.1.20858.10.11.1.1.4
		casaFlapListAging OBJECT-TYPE
			SYNTAX Unsigned32 (15..86400)
			UNITS "minutes"
			MAX-ACCESS read-write
			STATUS current
			DESCRIPTION
				"Aging threshold for the CM.  Periodically, a
				 	process scans through the CM and removes those
				 	Cable Modems from casaFlapListTable and
				 	casaFlapListTable that have no new detections for a
				 	time interval longer than this threshold in minutes.
				"
			DEFVAL { 10080 }
			::= { casaFlapListGlobal 4 }


		-- 1.3.6.1.4.1.20858.10.11.1.1.5
		casaFlapListMaxSize OBJECT-TYPE
			SYNTAX Unsigned32 (0..2147483647)
			UNITS "entries"
			MAX-ACCESS read-write
			STATUS current
			DESCRIPTION
				"The maximum number of Cable Modem entries that
				casaFlapListTable can report.
				"
			::= { casaFlapListGlobal 5 }


		-- 1.3.6.1.4.1.20858.10.11.1.1.6
		casaFlapListResetAll OBJECT-TYPE
        SYNTAX      TruthValue
        MAX-ACCESS  read-write
        STATUS      current
			DESCRIPTION
				"	If set to 'true', all counter objects for all entries in casaFlapListTable are reset to zero. Reading this object always returns
				 	'false'.
				"
			::= { casaFlapListGlobal 6 }


		-- 1.3.6.1.4.1.20858.10.11.1.1.7
		casaFlapListLastResetTime OBJECT-TYPE
			SYNTAX DateAndTime
			MAX-ACCESS read-only
			STATUS current
			DESCRIPTION
				"The last time that all the counters in the casaFlapListTable are
				reset to 0. The special value of all '00'Hs indicates that the Entries
				in these tables have never been reset.
				"
			::= { casaFlapListGlobal 7 }


		-- 1.3.6.1.4.1.20858.10.11.1.1.8
		casaFlapListClearAll OBJECT-TYPE
        SYNTAX      TruthValue
        MAX-ACCESS  read-write
        STATUS      current
			DESCRIPTION
				"If set to 'true', all entries from the casaFlapListTable are removed.
				 	Reading this object always returns 'false'."
			::= { casaFlapListGlobal 8 }


		-- 1.3.6.1.4.1.20858.10.11.1.1.9
		casaFlapListLastClearTime OBJECT-TYPE
			SYNTAX DateAndTime
			MAX-ACCESS read-only
			STATUS current
			DESCRIPTION
				"The last time that all the entries in the casaFlapListTable are destroyed. The special
				 	value of all '00'Hs indicates that the
				 	entries in these tables have never been destroyed."
			::= { casaFlapListGlobal 9 }


		-- 1.3.6.1.4.1.20858.10.11.1.1.10
		casaFlapListCheckInterval OBJECT-TYPE
			SYNTAX Unsigned32
			UNITS "minutes"
			MAX-ACCESS read-write
			STATUS current
			DESCRIPTION
				"Scaning threshold for the casaFlapListTable.  Periodically, a
				 	process scans through the casaFlapListTable and removes those
				 	Cable Modems from casaFlapListTable and
				 	casaFlapListTable that have no new detections for a
				 	time interval longer than this threshold in minutes."
			DEFVAL { 120 }
			::= { casaFlapListGlobal 10 }

		-- 1.3.6.1.4.1.20858.10.11.1.2
		casaFlapListTable OBJECT-TYPE
			SYNTAX SEQUENCE OF CasaFlapListEntry
			MAX-ACCESS not-accessible
			STATUS current
			DESCRIPTION
				"Description."
			::= { casaFlapListMIBObjects 2 }


		-- 1.3.6.1.4.1.20858.10.11.1.2.1
		casaFlapListEntry OBJECT-TYPE
			SYNTAX CasaFlapListEntry
			MAX-ACCESS not-accessible
			STATUS current
			DESCRIPTION
				"Description."
			INDEX {casaFlapCmMacAddress}
			::= { casaFlapListTable 1 }


		CasaFlapListEntry ::=
			SEQUENCE {
				casaFlapCmMacAddress
					MacAddress,
				casaFlapCmUpstreamIfIndex
					Unsigned32,
				casaFlapCmDownstreamIfIndex
					Unsigned32,
				casaFlapCmInsertionFails
					Integer32,
				casaFlapCmHits
					Unsigned32,
				casaFlapCmMisses
					Unsigned32,
				casaFlapCmCRCCounts
					Integer32,
				casaFlapCmPowerAdjustments
					Unsigned32,
				casaFlapCmFlapCounts
					Integer32,
				casaFlapCmLastFlapTime
					DateAndTime,
				casaFlapCmFlapRowStatus
					RowStatus
			 }

		-- 1.3.6.1.4.1.20858.10.11.1.2.1.1
		casaFlapCmMacAddress OBJECT-TYPE
			SYNTAX MacAddress
			MAX-ACCESS read-only
			STATUS current
			DESCRIPTION
				"The Cable Modem mac address"
			::= { casaFlapListEntry 1 }


		-- 1.3.6.1.4.1.20858.10.11.1.2.1.2
		casaFlapCmUpstreamIfIndex OBJECT-TYPE
			SYNTAX Unsigned32
			MAX-ACCESS read-only
			STATUS current
			DESCRIPTION
				"The upstream channel index for the CM"
			::= { casaFlapListEntry 2 }


		-- 1.3.6.1.4.1.20858.10.11.1.2.1.3
		casaFlapCmDownstreamIfIndex OBJECT-TYPE
			SYNTAX Unsigned32
			MAX-ACCESS read-only
			STATUS current
			DESCRIPTION
				"The downstream channel index for the CM"
			::= { casaFlapListEntry 3 }


		-- 1.3.6.1.4.1.20858.10.11.1.2.1.4
		casaFlapCmInsertionFails OBJECT-TYPE
			SYNTAX Integer32
			UNITS "times"
			MAX-ACCESS read-only
			STATUS current
			DESCRIPTION
				"The CM total ranging count after CM is added to casaFalpListTable."
			::= { casaFlapListEntry 4 }


		-- 1.3.6.1.4.1.20858.10.11.1.2.1.5
		casaFlapCmHits OBJECT-TYPE
			SYNTAX Unsigned32
			UNITS "times"
			MAX-ACCESS read-only
			STATUS current
			DESCRIPTION
				"The count a Cable Modem acknowledge a MAC-layer station maintenance message after the Cable Modem is added to casaFalpListTable."
			::= { casaFlapListEntry 5 }


		-- 1.3.6.1.4.1.20858.10.11.1.2.1.6
		casaFlapCmMisses OBJECT-TYPE
			SYNTAX Unsigned32
			UNITS "times"
			MAX-ACCESS read-only
			STATUS current
			DESCRIPTION
				"The count a Cable Modem does not acknowledge a MAC-layer station maintenance message after the Cable Modem is added to casaFalpListTable."
			::= { casaFlapListEntry 6 }


		-- 1.3.6.1.4.1.20858.10.11.1.2.1.7
		casaFlapCmCRCCounts OBJECT-TYPE
			SYNTAX Integer32
			MAX-ACCESS read-only
			STATUS current
			DESCRIPTION
				"The CM CRC count after a CM is added to casaFlapListTable"
			::= { casaFlapListEntry 7 }


		-- 1.3.6.1.4.1.20858.10.11.1.2.1.8
		casaFlapCmPowerAdjustments OBJECT-TYPE
			SYNTAX Unsigned32
			MAX-ACCESS read-only
			STATUS current
			DESCRIPTION
				"The count Cmts require Cable Modem to adjust power level that more than 2 dB after the Cable Modem is added to casaFalpListTable."
			::= { casaFlapListEntry 8 }


		-- 1.3.6.1.4.1.20858.10.11.1.2.1.9
		casaFlapCmFlapCounts OBJECT-TYPE
			SYNTAX Integer32
			MAX-ACCESS read-only
			STATUS current
			DESCRIPTION
				"The total count that Cable Modem ranging count plus P-ADJ count after the cable modem is added to casaFlapListTable."
			::= { casaFlapListEntry 9 }


		-- 1.3.6.1.4.1.20858.10.11.1.2.1.10
		casaFlapCmLastFlapTime OBJECT-TYPE
			SYNTAX DateAndTime
			MAX-ACCESS read-only
			STATUS current
			DESCRIPTION
				"The last offline time a Cable Modem after added to casaFlapListTable"
			::= { casaFlapListEntry 10 }


		-- 1.3.6.1.4.1.20858.10.11.1.2.1.11
		casaFlapCmFlapRowStatus OBJECT-TYPE
			SYNTAX RowStatus
			MAX-ACCESS read-write
			STATUS current
			DESCRIPTION
				"The status of this instance."
			::= { casaFlapListEntry 11 }

		-- 1.3.6.1.4.1.20858.10.11.2
		casaFlapListGroups OBJECT IDENTIFIER ::= { casaFlapListMib 2 }

        -- 1.3.6.1.4.1.20858.10.11.2.1
		casaFlapListGroup OBJECT-GROUP
			OBJECTS { casaFlapInsertionTime, casaFlapMissThreshold, casaFlapPowerAdjThreshold, casaFlapListAging, casaFlapListMaxSize,
				casaFlapListResetAll, casaFlapListLastResetTime, casaFlapListClearAll, casaFlapListLastClearTime,
				casaFlapListCheckInterval, casaFlapCmUpstreamIfIndex, casaFlapCmDownstreamIfIndex, casaFlapCmInsertionFails, casaFlapCmHits,
				casaFlapCmMisses, casaFlapCmCRCCounts, casaFlapCmPowerAdjustments, casaFlapCmFlapCounts, casaFlapCmLastFlapTime, casaFlapCmFlapRowStatus }
			STATUS current
			DESCRIPTION
				"Group of objects implemented in."
			::= { casaFlapListGroups 1 }


		-- 1.3.6.1.4.1.20858.10.11.3
		casaFlapListCompliances OBJECT IDENTIFIER ::= { casaFlapListMib 3 }

		-- 1.3.6.1.4.1.20858.10.11.3.1
		casaFlapListCompliance MODULE-COMPLIANCE
			STATUS current
			DESCRIPTION
				"The compliance statement of managed objects common for Cable Modem Termination Sytems (CMTS) and Cable Modems (CM)."
			MODULE -- this module
				MANDATORY-GROUPS { casaFlapListGroup }
			::= { casaFlapListCompliances 1 }
	END
--
-- CASA-CABLE-FLAPLIST-MIB.my
--
