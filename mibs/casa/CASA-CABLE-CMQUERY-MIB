CASA-CABLE-CMQUERY-MIB DEFINITIONS ::= BEGIN

		IMPORTS
        TEXTUAL-CONVENTION,
        MacAddress,
        RowStatus,
        TruthValue,
        TimeInterval,
        TimeStamp
        FROM SNMPv2-TC
			casa
				FROM CASA-MIB
			ifIndex
				FROM IF-MIB
			OBJECT-GROUP, MODULE-COMPLIANCE
				FROM SNMPv2-CONF
			IpAddress, Integer32, Unsigned32, OBJECT-TYPE, MODULE-IDENTITY
				FROM SNMPv2-SMI;


		-- 1.3.6.1.4.1.20858.10.18
		casaCmQueryMib MODULE-IDENTITY
			LAST-UPDATED "200809051453Z"		-- September 05, 2008 at 14:53 GMT
			ORGANIZATION
				"Casa Systems Inc"
			CONTACT-INFO
				"Guangzhou Casa Communications Ltd.
				No.206 YueHe Bld,Huacui Str.
				Tianhe Industrial Park Guangzhou
				TEL:020 85545002/85577786 ext.212
				FAX:020 85545002 ext.230
				E-mail: huangxiaole@casachina.com.cn "
			DESCRIPTION
				"This is the enterprise MIB Module for CASA systems CMTS."
			::= { casaMgmt 18 }

-- Textual Conventions

TenthdBmV ::= TEXTUAL-CONVENTION
        DISPLAY-HINT "d-1"
        STATUS       current
        DESCRIPTION
            "This data type represents power levels that are normally
             expressed in dBmV. Units are in tenths of a dBmV;
             for example, 5.1 dBmV will be represented as 51."
        SYNTAX       Integer32

TenthdB ::= TEXTUAL-CONVENTION
        DISPLAY-HINT "d-1"
        STATUS       current
        DESCRIPTION
            "This data type represents power levels that are normally
             expressed in dB. Units are in tenths of a dB;
             for example, 5.1 dB will be represented as 51."
        SYNTAX       Integer32


--
-- Node definitions
--

--  1.3.6.1.4.1.20858.10.10
-- September 05, 2008 at 14:53 GMT
--
-- Node definitions
--
-- 1.3.6.1.4.1.20858.10
		-- 1.3.6.1.4.1.20858.10
		casaMgmt OBJECT IDENTIFIER ::= { casa 10 }


--  1.3.6.1.4.1.20858.10.10.1
		-- 1.3.6.1.4.1.20858.10.18.1
		casaCmQueryMibObjects OBJECT IDENTIFIER ::= { casaCmQueryMib 1 }


		-- 1.3.6.1.4.1.20858.10.18.1.1
		casaCmQueryTable OBJECT-TYPE
			SYNTAX SEQUENCE OF CasaCmQueryEntry
			MAX-ACCESS not-accessible
			STATUS current
			DESCRIPTION
				"describes the PHY signal quality and Tx/Rx parameter of cable modem.
				"
			::= { casaCmQueryMibObjects 1 }


		-- 1.3.6.1.4.1.20858.10.18.1.1.1
		casaCmQueryEntry OBJECT-TYPE
			SYNTAX CasaCmQueryEntry
			MAX-ACCESS not-accessible
			STATUS current
			DESCRIPTION
				"describes the PHY signal quality and Tx/Rx parameter of cable modem,index of this table is casaQueryCmMacAddress.
				"
			INDEX { casaQueryCmMacAddress }
			::= { casaCmQueryTable 1 }



		CasaCmQueryEntry ::=
			SEQUENCE {
				casaQueryCmMacAddress
					MacAddress,
				casaQueryCmIpAddress
					IpAddress,
				casaQueryCmTxTimeOffset
					Unsigned32,
				casaQueryCmMicroReflection
					Integer32,
				casaQueryCmStatusTxPower
					TenthdBmV,
				casaQueryCmStatusRxPower
					TenthdBmV,
				casaQueryCmSigQSignalNoise
					TenthdB,
				casaQueryCmtsSigQSignalNoise
					TenthdB
			 }

		-- 1.3.6.1.4.1.20858.10.18.1.1.1.1
		casaQueryCmMacAddress OBJECT-TYPE
			SYNTAX MacAddress
			MAX-ACCESS not-accessible
			STATUS current
			DESCRIPTION
				"The cable modem Mac Address.
				"
			::= { casaCmQueryEntry 1 }


		-- 1.3.6.1.4.1.20858.10.18.1.1.1.2
		casaQueryCmIpAddress OBJECT-TYPE
			SYNTAX IpAddress
			MAX-ACCESS read-only
			STATUS current
			DESCRIPTION
				"The cable modem Ip Address.
				"
			::= { casaCmQueryEntry 2 }


-- 3
		-- 1.3.6.1.4.1.20858.10.18.1.1.1.3
		casaQueryCmTxTimeOffset OBJECT-TYPE
			SYNTAX Unsigned32
			MAX-ACCESS read-only
			STATUS current
			DESCRIPTION
				"A measure of the current round trip time at the CM, or the
      	maximum round trip time seen by the CMTS.  Used for timing
 				of CM upstream transmissions to ensure synchronized
 				arrivals at the CMTS. Units are in terms of
 				(6.25 microseconds/64)."
			::= { casaCmQueryEntry 3 }


		-- 1.3.6.1.4.1.20858.10.18.1.1.1.4
		casaQueryCmMicroReflection OBJECT-TYPE
      SYNTAX      Integer32 (0..255)
      UNITS       "dBc"
			MAX-ACCESS read-only
			STATUS current
			DESCRIPTION
				"Total microreflections including in-channel response
 				as perceived on this interface, measured in dBc below
 				the signal level.
 				This object is not assumed to return an absolutely
 				accurate value, but should give a rough indication
 				of microreflections received on this interface.
 				It is up to the implementor to provide information
 				as accurate as possible.
				"
			::= { casaCmQueryEntry 4 }


		-- 1.3.6.1.4.1.20858.10.18.1.1.1.5
		casaQueryCmStatusTxPower OBJECT-TYPE
      SYNTAX      TenthdBmV
      UNITS       "dBmV"
			MAX-ACCESS read-only
			STATUS current
			DESCRIPTION
				"The operational transmit power of the cable modem downstream channel,the most current value (CM)
             or the value of 0.
				"
			::= { casaCmQueryEntry 5 }


		-- 1.3.6.1.4.1.20858.10.18.1.1.1.6
		casaQueryCmStatusRxPower OBJECT-TYPE
      SYNTAX      TenthdBmV
      UNITS       "dBmV"
			MAX-ACCESS read-only
			STATUS current
			DESCRIPTION
				"The operational receive power of the cable modem upstream channel,the most current value (CM)
             or the value of 0"
			::= { casaCmQueryEntry 6 }


		-- 1.3.6.1.4.1.20858.10.18.1.1.1.7
		casaQueryCmSigQSignalNoise OBJECT-TYPE
      SYNTAX      TenthdB
      UNITS       "dB"
			MAX-ACCESS read-only
			STATUS current
			DESCRIPTION
				"Signal/Noise ratio as perceived for this channel.
 				describes the Signal/Noise of the upstream
 				channel of CM .
				"
			::= { casaCmQueryEntry 7 }


		-- 1.3.6.1.4.1.20858.10.18.1.1.1.8
		casaQueryCmtsSigQSignalNoise OBJECT-TYPE
      SYNTAX      TenthdB
      UNITS       "dB"
			MAX-ACCESS read-only
			STATUS current
			DESCRIPTION
				"Signal/Noise ratio as perceived for this channel.
 				 describes the average Signal/Noiseof the upstream
 				 channel of CMTS.
				"
			::= { casaCmQueryEntry 8 }


		-- 1.3.6.1.4.1.20858.10.18.2
		casaCmQueryGroups OBJECT IDENTIFIER ::= { casaCmQueryMib 2 }


		-- 1.3.6.1.4.1.20858.10.18.2.1
		casaCmQueryroup OBJECT-GROUP
			OBJECTS { casaQueryCmIpAddress, casaQueryCmTxTimeOffset, casaQueryCmMicroReflection, casaQueryCmStatusTxPower, casaQueryCmStatusRxPower,
				casaQueryCmSigQSignalNoise, casaQueryCmtsSigQSignalNoise }
			STATUS current
			DESCRIPTION
				"Box is required to support objects in this group
				"
			::= { casaCmQueryGroups 1 }


--  1.3.6.1.4.1.20858.10.10.4
		-- 1.3.6.1.4.1.20858.10.18.3
		casaCmQueryCompliances OBJECT IDENTIFIER ::= { casaCmQueryMib 3 }


--  1.3.6.1.4.1.20858.10.10.4.1
-- this module
		-- 1.3.6.1.4.1.20858.10.18.3.1
		casaCmQueryCompliance MODULE-COMPLIANCE
			STATUS current
			DESCRIPTION
				"Description."
			MODULE -- this module
				MANDATORY-GROUPS { casaCmQueryroup }
			::= { casaCmQueryCompliances 1 }



	END

--
-- CASA-CABLE-CMQUERY-MIB.my
--
