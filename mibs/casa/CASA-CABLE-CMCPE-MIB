CASA-CABLE-CMCPE-MIB DEFINITIONS ::= BEGIN

		IMPORTS
			casa
				FROM CASA-MIB
			ifIndex, InterfaceIndex
				FROM IF-MIB
			InetAddress, InetAddressType
				FROM INET-ADDRESS-MIB
			OBJECT-GROUP, MODULE-COMPLIANCE
				FROM SNMPv2-CONF
			IpAddress, Integer32, Unsigned32, OBJECT-TYPE, MODULE-IDENTITY
				FROM SNMPv2-SMI
			MacAddress, TruthValue, PhysAddress
				FROM SNMPv2-TC;


		-- 1.3.6.1.4.1.20858.10.12
		casaCmtsCmCpeMib MODULE-IDENTITY
			LAST-UPDATED "200812021453Z"		-- December 02, 2008 at 14:53 GMT
			ORGANIZATION
				"Casa Systems Inc"
			CONTACT-INFO
				"Guangzhou Casa Communications Ltd.
				No.206 YueHe Bld,Huacui Str.
				Tianhe Industrial Park Guangzhou China
				TEL:020 85545002/85577786 ext.212
				FAX:020 85545002 ext.230
				E-mail: huangxiaole@casachina.com.cn "
			DESCRIPTION
				"This is the enterprise MIB Module for CASA systems CMTS."
			::= { casaMgmt 12 }




--
-- Node definitions
--

--  1.3.6.1.4.1.20858.10.12
-- December 02, 2008 at 14:53 GMT
--
-- Node definitions
--
--  1.3.6.1.4.1.20858.10.12
-- December 02, 2008 at 14:53 GMT
--
-- Node definitions
--
--  [RFC2579]
-- 1.3.6.1.4.1.20858.10.12
-- September 05, 2008 at 14:53 GMT
--
-- Node definitions
--
-- 1.3.6.1.4.1.20858.10
-- 1.3.6.1.4.1.20858.10
-- 1.3.6.1.4.1.20858.10
		-- 1.3.6.1.4.1.20858.10
		casaMgmt OBJECT IDENTIFIER ::= { casa 10 }


		-- 1.3.6.1.4.1.20858.10.12.1
		casaCmtsCmCpeObjects OBJECT IDENTIFIER ::= { casaCmtsCmCpeMib 1 }


		-- 1.3.6.1.4.1.20858.10.12.1.1
		casaCmtsUSModemTable OBJECT-TYPE
			SYNTAX SEQUENCE OF CasaCmtsUSModemEntry
			MAX-ACCESS not-accessible
			STATUS current
			DESCRIPTION
				"Modem count for each upstream channel."
			::= { casaCmtsCmCpeObjects 1 }


		-- 1.3.6.1.4.1.20858.10.12.1.1.1
		casaCmtsUSModemEntry OBJECT-TYPE
			SYNTAX CasaCmtsUSModemEntry
			MAX-ACCESS not-accessible
			STATUS current
			DESCRIPTION
				"Index of the table is logical uptream channel ifIndex ."
			INDEX { ifIndex }
			::= { casaCmtsUSModemTable 1 }


		CasaCmtsUSModemEntry ::=
			SEQUENCE {
				casaCmtsUSActiveModemCount
					Unsigned32,
				casaCmtsUSRegisteredModemCount
					Unsigned32,
				casaCmtsUSTotalModemCount
					Unsigned32
			 }

		-- 1.3.6.1.4.1.20858.10.12.1.1.1.1
		casaCmtsUSActiveModemCount OBJECT-TYPE
			SYNTAX Unsigned32
			MAX-ACCESS read-only
			STATUS current
			DESCRIPTION
				"Active modem count for each upstream channel."
			::= { casaCmtsUSModemEntry 1 }


		-- 1.3.6.1.4.1.20858.10.12.1.1.1.2
		casaCmtsUSRegisteredModemCount OBJECT-TYPE
			SYNTAX Unsigned32
			MAX-ACCESS read-only
			STATUS current
			DESCRIPTION
				"Registered modem count for each upstream channel."
			::= { casaCmtsUSModemEntry 2 }


		-- 1.3.6.1.4.1.20858.10.12.1.1.1.3
		casaCmtsUSTotalModemCount OBJECT-TYPE
			SYNTAX Unsigned32
			MAX-ACCESS read-only
			STATUS current
			DESCRIPTION
				"Modem total for each upstream channel."
			::= { casaCmtsUSModemEntry 3 }


		-- 1.3.6.1.4.1.20858.10.12.1.2
		casaCmtsDSModemTable OBJECT-TYPE
			SYNTAX SEQUENCE OF CasaCmtsDSModemEntry
			MAX-ACCESS not-accessible
			STATUS current
			DESCRIPTION
				"Modem count for each downstream channel."
			::= { casaCmtsCmCpeObjects 2 }


		-- 1.3.6.1.4.1.20858.10.12.1.2.1
		casaCmtsDSModemEntry OBJECT-TYPE
			SYNTAX CasaCmtsDSModemEntry
			MAX-ACCESS not-accessible
			STATUS current
			DESCRIPTION
				"Index of the table is  downstream channel ifIndex ."
			INDEX { ifIndex }
			::= { casaCmtsDSModemTable 1 }


		CasaCmtsDSModemEntry ::=
			SEQUENCE {
				casaCmtsDSActiveModemCount
					Unsigned32,
				casaCmtsDSRegisteredModemCount
					Unsigned32,
				casaCmtsDSTotalModemCount
					Unsigned32
			 }

		-- 1.3.6.1.4.1.20858.10.12.1.2.1.1
		casaCmtsDSActiveModemCount OBJECT-TYPE
			SYNTAX Unsigned32
			MAX-ACCESS read-only
			STATUS current
			DESCRIPTION
				"Active modem count for each downstream channel."
			::= { casaCmtsDSModemEntry 1 }


		-- 1.3.6.1.4.1.20858.10.12.1.2.1.2
		casaCmtsDSRegisteredModemCount OBJECT-TYPE
			SYNTAX Unsigned32
			MAX-ACCESS read-only
			STATUS current
			DESCRIPTION
				"Registered modem count for each downstream channel."
			::= { casaCmtsDSModemEntry 2 }


		-- 1.3.6.1.4.1.20858.10.12.1.2.1.3
		casaCmtsDSTotalModemCount OBJECT-TYPE
			SYNTAX Unsigned32
			MAX-ACCESS read-only
			STATUS current
			DESCRIPTION
				"Modem total for each downstream channel."
			::= { casaCmtsDSModemEntry 3 }


		-- 1.3.6.1.4.1.20858.10.12.1.3
		casaCmtsCmCpeTable OBJECT-TYPE
			SYNTAX SEQUENCE OF CasaCmtsCmCpeEntry
			MAX-ACCESS not-accessible
			STATUS current
			DESCRIPTION
				"Describes the relation between CPE and CM.
				"
			::= { casaCmtsCmCpeObjects 3 }


		-- 1.3.6.1.4.1.20858.10.12.1.3.1
		casaCmtsCmCpeEntry OBJECT-TYPE
			SYNTAX CasaCmtsCmCpeEntry
			MAX-ACCESS not-accessible
			STATUS current
			DESCRIPTION
				"The list contains information for a cable modem (CM) or a
				Customer Premises Equipment (CPE). An entry exist for
				each cable modem supported by CMTS and each Customer
				Premises Equipment connected to a cable modem supported by
				CMTS. "
			REFERENCE
				"Data-Over-Cable Service Interface Specifications (DOCSIS)
				Radio Frequency Interface Specification
				(SP-RFI-I04-980724.) docsIfCmtsCmStatusTable,
				docsIfCmtsServiceTable in DOCS-IF-MIB.my. "
			INDEX { casaCmtsCmCpeMacAddress }
			::= { casaCmtsCmCpeTable 1 }


		CasaCmtsCmCpeEntry ::=
			SEQUENCE {
				casaCmtsCmCpeMacAddress
					MacAddress,
				casaCmtsCmCpeType
					INTEGER,
				casaCmtsCmCpeIpAddress
					IpAddress,
				casaCmtsCmCpeIfIndex
					InterfaceIndex,
				casaCmtsCmCpeCmtsServiceId
					Integer32,
				casaCmtsCmCpeCmStatusIndex
					Integer32,
				casaCmtsCmCpeResetNow
					TruthValue
			 }

		-- 1.3.6.1.4.1.20858.10.12.1.3.1.1
		casaCmtsCmCpeMacAddress OBJECT-TYPE
			SYNTAX MacAddress
			MAX-ACCESS not-accessible
			STATUS current
			DESCRIPTION
				"The Mac address to identify a cable modem or a Customer
				Premises Equipment."
			::= { casaCmtsCmCpeEntry 1 }


		-- 1.3.6.1.4.1.20858.10.12.1.3.1.2
		casaCmtsCmCpeType OBJECT-TYPE
			SYNTAX INTEGER
				{
				cm(1),
				cpe(2)
				}
			MAX-ACCESS read-only
			STATUS current
			DESCRIPTION
				"ndicate this entry is for cable modem or Customer Premises
				Equipment.  The enumerations are:
				 cm(1): cable modem
				 cpe(2): Customer Premises Equipment"
			::= { casaCmtsCmCpeEntry 2 }


		-- 1.3.6.1.4.1.20858.10.12.1.3.1.3
		casaCmtsCmCpeIpAddress OBJECT-TYPE
			SYNTAX IpAddress
			MAX-ACCESS read-only
			STATUS current
			DESCRIPTION
				"Ip address of the cable modem or Customer Premises
				Equipment."
			::= { casaCmtsCmCpeEntry 3 }


		-- 1.3.6.1.4.1.20858.10.12.1.3.1.4
		casaCmtsCmCpeIfIndex OBJECT-TYPE
			SYNTAX InterfaceIndex
			MAX-ACCESS read-only
			STATUS current
			DESCRIPTION
				"The CMTS cable MAC interface index (ifType of
				docsCableMaclayer(127)) that cable modem or Customer
				Premises Equipment connects to.

				Use casaCmtsCmCpeIfIndex and casaCmtsCmCpeCmtsServiceId to identify
				an  entry in docsIfCmtsServiceTable. "
			::= { casaCmtsCmCpeEntry 4 }


		-- 1.3.6.1.4.1.20858.10.12.1.3.1.5
		casaCmtsCmCpeCmtsServiceId OBJECT-TYPE
			SYNTAX Integer32 (1..16383)
			MAX-ACCESS read-only
			STATUS current
			DESCRIPTION
				"The cable modem's primary Service ID if the type is cm.
				The primary Service ID for the CM which the CPE connects if
				the type is cpe.

				Use casaCmtsCmCpeIfIndex and casaCmtsCmCpeCmtsServiceId to identify
				an entry in docsIfCmtsServiceTable."
			::= { casaCmtsCmCpeEntry 5 }


		-- 1.3.6.1.4.1.20858.10.12.1.3.1.6
		casaCmtsCmCpeCmStatusIndex OBJECT-TYPE
			SYNTAX Integer32 (1..2147483647)
			MAX-ACCESS read-only
			STATUS current
			DESCRIPTION
				"Pointer to an entry in docsIfCmtsCmStatusTable identifying
				status of the CM (which the CPE connects to.)"
			::= { casaCmtsCmCpeEntry 6 }


		-- 1.3.6.1.4.1.20858.10.12.1.3.1.7
		casaCmtsCmCpeResetNow OBJECT-TYPE
			SYNTAX TruthValue
			MAX-ACCESS read-write
			STATUS current
			DESCRIPTION
				"Setting this object to true(1) causes the device to
				reset.  Reading this object always returns false(2).

				For casaCmtsCmCpeType value cm(1),  CMTS removes the
				CM from the Station Maintenance List and would cause
				the CM to reset its interface.

				For casaCmtsCmCpeType value cpe(2), CMTS removes the
				CPE's MAC address from the internal address table.
				It then rediscovers and associates the CPE with the
				correct CM during the next DHCP lease cycle.  By resetting
				the CPE, the user can replace an existing CPE or change
				its network interface card (NIC)"
			::= { casaCmtsCmCpeEntry 7 }


		-- 1.3.6.1.4.1.20858.10.12.1.4
		casaCmtsCpeIpNetToPhysicalTable OBJECT-TYPE
			SYNTAX SEQUENCE OF CasaCmtsCpeIpNetToPhysicalEntry
			MAX-ACCESS not-accessible
			STATUS current
			DESCRIPTION
				"The IP Address Translation table used for mapping from IP
				 	addresses to physical addresses.
				 	"
			::= { casaCmtsCmCpeObjects 4 }


		-- 1.3.6.1.4.1.20858.10.12.1.4.1
		casaCmtsCpeIpNetToPhysicalEntry OBJECT-TYPE
			SYNTAX CasaCmtsCpeIpNetToPhysicalEntry
			MAX-ACCESS not-accessible
			STATUS current
			DESCRIPTION
				"Each entry contains one IP address to `physical' address
				 	equivalence..
				"
			INDEX { casaCmtsCpeIpNetToPhysicalIfIndex, casaCmtsCpeIpNetToPhysicalNetAddressType, casaCmtsCpeIpNetToPhysicalNetAddress }
			::= { casaCmtsCpeIpNetToPhysicalTable 1 }


		CasaCmtsCpeIpNetToPhysicalEntry ::=
			SEQUENCE {
				casaCmtsCpeIpNetToPhysicalIfIndex
					InterfaceIndex,
				casaCmtsCpeIpNetToPhysicalNetAddressType
					InetAddressType,
				casaCmtsCpeIpNetToPhysicalNetAddress
					InetAddress,
				casaCmtsCpeIpNetToPhysicalCmPhysAddress
					PhysAddress,
				casaCmtsCpeIpNetToPhysicalType
					INTEGER
			 }

		-- 1.3.6.1.4.1.20858.10.12.1.4.1.1
		casaCmtsCpeIpNetToPhysicalIfIndex OBJECT-TYPE
			SYNTAX InterfaceIndex
			MAX-ACCESS not-accessible
			STATUS current
			DESCRIPTION
				"The index value that uniquely identifies the interface to
				which this entry is applicable.  The interface identified by
				a particular value of this index is the same interface as
				identified by the same value of the IF-MIB's ifIndex.
				"
			::= { casaCmtsCpeIpNetToPhysicalEntry 1 }


		-- 1.3.6.1.4.1.20858.10.12.1.4.1.2
		casaCmtsCpeIpNetToPhysicalNetAddressType OBJECT-TYPE
			SYNTAX InetAddressType
			MAX-ACCESS not-accessible
			STATUS current
			DESCRIPTION
				"The type of casaCmtsCpeIpNetToPhysicalNetAddress."
			::= { casaCmtsCpeIpNetToPhysicalEntry 2 }


		-- 1.3.6.1.4.1.20858.10.12.1.4.1.3
		casaCmtsCpeIpNetToPhysicalNetAddress OBJECT-TYPE
			SYNTAX InetAddress
			MAX-ACCESS not-accessible
			STATUS current
			DESCRIPTION
				"The IP Address corresponding to the media-dependent
				`physical' address.  The address type of this object is
				specified in casaCmtsCpeIpNetToPhysicalAddressType.


				"
			::= { casaCmtsCpeIpNetToPhysicalEntry 3 }


		-- 1.3.6.1.4.1.20858.10.12.1.4.1.5
		casaCmtsCpeIpNetToPhysicalCmPhysAddress OBJECT-TYPE
			SYNTAX PhysAddress
			MAX-ACCESS read-only
			STATUS current
			DESCRIPTION
				"The CM MAC address."
			::= { casaCmtsCpeIpNetToPhysicalEntry 5 }


		-- 1.3.6.1.4.1.20858.10.12.1.4.1.7
		casaCmtsCpeIpNetToPhysicalType OBJECT-TYPE
			SYNTAX INTEGER
				{
				other(1),
				invalid(2),
				dynamic(3),
				static(4)
				}
			MAX-ACCESS read-only
			STATUS current
			DESCRIPTION
				"The type of mapping.

				Setting this object to the value invalid(2) has the effect
				of invalidating the corresponding entry in the
				ipNetToPhysicalTable.  That is, it effectively dis-
				associates the interface identified with said entry from the
				mapping identified with said entry.  It is an
				implementation-specific matter as to whether the agent





				removes an invalidated entry from the table.  Accordingly,
				management stations must be prepared to receive tabular
				information from agents that corresponds to entries not
				currently in use.  Proper interpretation of such entries
				requires examination of the relevant ipNetToPhysicalType
				object.

				The 'dynamic(3)' type indicates that the IP address to
				physical addresses mapping has been dynamically resolved
				using e.g., IPv4 ARP or the IPv6 Neighbor Discovery
				protocol.

				The 'static(4)' type indicates that the mapping has been
				statically configured.  Both of these refer to entries that
				provide mappings for other entities addresses.

				The 'local(5)' type indicates that the mapping is provided
				for an entity's own interface address.

				As the entries in this table are typically not persistent
				when this object is written the entity SHOULD NOT save the
				change to non-volatile storage.
				"
			::= { casaCmtsCpeIpNetToPhysicalEntry 7 }


		-- 1.3.6.1.4.1.20858.10.12.1.5
		casaCmtsCmReset OBJECT IDENTIFIER ::= { casaCmtsCmCpeObjects 5 }


		-- 1.3.6.1.4.1.20858.10.12.1.5.1
		casaCmtsCmResetByIpAddr OBJECT-TYPE
			SYNTAX IpAddress
			MAX-ACCESS read-write
			STATUS current
			DESCRIPTION
				"to reset cable modem by ip address"
			::= { casaCmtsCmReset 1 }


		-- 1.3.6.1.4.1.20858.10.12.1.5.2
		casaCmtsCmResetByMacAddr OBJECT-TYPE
			SYNTAX MacAddress
			MAX-ACCESS read-write
			STATUS current
			DESCRIPTION
				"to reset cable modem by mac address"
			::= { casaCmtsCmReset 2 }


--
		-- 1.3.6.1.4.1.20858.10.12.1.5.3
		casaCmtsCmResetAll OBJECT-TYPE
			SYNTAX TruthValue
			MAX-ACCESS read-write
			STATUS current
			DESCRIPTION
				" If set to 'true', all cable modem are reset. Reading this object always returns
				'false'."
			DEFVAL { false }
			::= { casaCmtsCmReset 3 }


		-- 1.3.6.1.4.1.20858.10.12.2
		casaCmCpeGroups OBJECT IDENTIFIER ::= { casaCmtsCmCpeMib 2 }


		-- 1.3.6.1.4.1.20858.10.12.2.1
		casaCmCpeGroup OBJECT-GROUP
			OBJECTS { casaCmtsUSActiveModemCount, casaCmtsUSRegisteredModemCount, casaCmtsUSTotalModemCount, casaCmtsDSActiveModemCount, casaCmtsDSRegisteredModemCount,
				casaCmtsDSTotalModemCount, casaCmtsCmResetAll, casaCmtsCmResetByMacAddr, casaCmtsCmResetByIpAddr, casaCmtsCmCpeResetNow,
				casaCmtsCmCpeCmStatusIndex, casaCmtsCmCpeCmtsServiceId, casaCmtsCmCpeIfIndex, casaCmtsCpeIpNetToPhysicalType, casaCmtsCmCpeType,
				casaCmtsCmCpeIpAddress, casaCmtsCpeIpNetToPhysicalCmPhysAddress }
			STATUS current
			DESCRIPTION
				"Description."
			::= { casaCmCpeGroups 1 }


		-- 1.3.6.1.4.1.20858.10.12.3
		casaCmCpeCompliances OBJECT IDENTIFIER ::= { casaCmtsCmCpeMib 3 }


		-- 1.3.6.1.4.1.20858.10.12.3.1
		casaCmCpeCompliance MODULE-COMPLIANCE
			STATUS current
			DESCRIPTION
				"Description."
			MODULE -- this module
				MANDATORY-GROUPS { casaCmCpeGroup }
			::= { casaCmCpeCompliances 1 }



	END

--
-- CASA-CABLE-CMCPE-MIB.my
--
