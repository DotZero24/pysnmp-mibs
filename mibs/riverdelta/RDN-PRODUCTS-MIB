-- *****************************************************************
-- RDN-PRODUCTS-MIB.mib:
-- Motorola BSR's Products Definitions MIB
--
-- Copyright (C) 2001, 2008 by Motorola, Inc.
-- All rights reserved.
-- *****************************************************************
RDN-PRODUCTS-MIB DEFINITIONS ::= BEGIN

    IMPORTS
        MODULE-IDENTITY
            FROM SNMPv2-SMI
        rdnDefinitions
            FROM RDN-DEFINITIONS-MIB;

    -- riverdelta products definitions mib module

    rdnProducts MODULE-IDENTITY
        LAST-UPDATED "200808080000Z"  -- 08 August 2008
        ORGANIZATION "Motorola"
        CONTACT-INFO "Motorola
	              Customer Service
                      101 Tournament Drive
                      Horsham, PA 19044
                      US Tel: +1 888 944 4357
                      Int Tel: +1 215 323 0044
	              Fax: +1 215 323 1502
                      Email: CPSSupport@Motorola.com"
        DESCRIPTION
                "MIB module for Motorola Product definitions.
                These Product definitions are the object identifiers
                that are assigned to various hardware platforms and are
                returned as values for sysObjectID.

		Copyright (C) 2001, 2008 by Motorola, Inc.
		All rights reserved."

	REVISION     "200808080000Z"  -- 08 August 2008
	DESCRIPTION
		"Added Copyright Statement into MIB modules's
	       	 description."
        REVISION     "200311050000Z"
        DESCRIPTION
                "+ Updated the CONTACT-INFO.
	         + Reorder REVISION/DESCRIPTION in required
                   reverse chronological order."
	REVISION     "200304290000Z"
        DESCRIPTION
                "Clean up of CONTACT-INFO."
        REVISION     "200104170000Z"
        DESCRIPTION
                "Initial creation."
        ::= { rdnDefinitions 1 }


      --
      -- product definitions for all riverdelta products
      --

      rdnProductsUnknown     OBJECT IDENTIFIER ::= { rdnProducts 0 }
      rdnProductsBSR64000    OBJECT IDENTIFIER ::= { rdnProducts 1 }
      rdnProductsBSR1000B    OBJECT IDENTIFIER ::= { rdnProducts 2 }
      rdnProductsBSR1000R    OBJECT IDENTIFIER ::= { rdnProducts 3 }
      rdnProductsOSR2000     OBJECT IDENTIFIER ::= { rdnProducts 4 }

END
