-- *****************************************************************
-- RDN-CHASSIS-MIB.mib:
-- Motorola BSR's Chassis MIB
--
-- Copyright (C) 2000, 2008 by Motorola, Inc.
-- All rights reserved.
-- *****************************************************************
RDN-CHASSIS-MIB DEFINITIONS ::= BEGIN

        IMPORTS
            MODULE-IDENTITY,
	    OBJECT-TYPE,
            TimeTicks,
            Integer32,
            Counter32,
	    Unsigned32
                            FROM SNMPv2-SMI
        ifIndex, ifDescr, ifType, ifAdminStatus, ifOperStatus
                            FROM IF-MIB
            sysDescr
                            FROM SNMPv2-MIB
            docsDevEvLevel
                            FROM DOCS-CABLE-DEVICE-MIB

            riverdelta
		            FROM RDN-MIB
            DisplayString,
            TruthValue
			    FROM SNMPv2-TC;


		-- chassis module definitions

        rdnChassis MODULE-IDENTITY
            LAST-UPDATED "201111090000Z"  -- 09 November 2011
            ORGANIZATION "Motorola"
            CONTACT-INFO "Motorola
                          Customer Service
                          101 Tournament Drive
                          Horsham, PA 19044
                          US Tel: +1 888 944 4357
                          Int Tel: +1 215 323 0044
	                  Fax: +1 215 323 1502
                          Email: CPSSupport@Motorola.com"

            DESCRIPTION
		"MIB module for Motorola Chassis.

		Copyright (C) 2001, 2008 by Motorola, Inc.
		All rights reserved."

            REVISION	 "201111090000Z"  -- 09 November 2011
	    DESCRIPTION
		"add lag(8) type to rdnCardIfPortType"

            REVISION	 "200808080000Z"  -- 08 August 2008
	    DESCRIPTION
		"Added Copyright Statement into MIB modules's
	       	 description."

            REVISION	  "200601060000Z"
            DESCRIPTION
                "+ adding rdnBsrTestTrap
                 + adding rdnCardIfPortType"

            REVISION 	  "200503010000Z"
            DESCRIPTION
                "changing rdnResetSlotStats to a TruthValue"

            REVISION 	  "200502220000Z"
            DESCRIPTION
                "clarifying descriptive text related to proprietary linkUp/Down traps"

	    REVISION      "200403180000Z"
            DESCRIPTION
                     "Modified the description of rdnSysUpTimeAtLastConfigChange."

	    REVISION      "200311040000Z"
	    DESCRIPTION
		   "+ Updated CONTACT-INFO.
	            + Added 'hsim(4)' and 'cmts(5)' to rdnSlotType.
		    + Reorder REVISION/DESCRIPTION in required
                      reverse chronological order.
                    + Added rdnLinkUpTrap, rdnLinkDownTrap, rdnCardIfLinkUpDownEnable"
	    REVISION      "200304300000Z"
	    DESCRIPTION
                   "The rdnCardIndex objects MAX-ACCESS was changed to be
	            not-accessible. Also rdnCardIndex object's the SYNTAX
		    was changed to reflect an index of a table."

            REVISION      "200304290000Z"
	    DESCRIPTION
                   "Clean up of CONTACT-INFO."

            REVISION      "200105080000Z"
            DESCRIPTION
                   "Changed rdnCardSerial to DisplayString;
                    removed rdnCardSlots, rdnConfigReg, rdnConfigRegNext,
                    and rdnChassisPartner; added options bsr1000 and
                    bsr2000 to rdnChassisType; plus other syntax changes."

	    REVISION      "200101150000Z"
            DESCRIPTION
                   "Added option 'unknown' to variable chassisPartner."

            REVISION      "200005230000Z"
            DESCRIPTION
                   "Moved 'riverdelta' definition into a separate
                    file; this allows an external module to
                    not include the entire riverdelta chassis mib
                    when needing only the 'riverdelta' definition."

	    REVISION      "200004040000Z"
	    DESCRIPTION
		   "- Changed the rdnSlotTable to start with a index of
	              1 rather than 0. SNMP does not allow a table to
                      start with a index of 0.

                    - Change the access of the rdnSlotIndex to be
                      not-accessible; since this object is an index
                      to the rdnSlotTable."

	    REVISION      "200004040000Z"
            DESCRIPTION
                   "Initial creation."

            ::= { riverdelta 1 }


          --
          -- chassis group should be present in all products.
          --

               rdnChassisType OBJECT-TYPE
                   SYNTAX  INTEGER {
                        unknown(1),
                        bsr64000(2),
                        bsr1000(3),
                        osr2000(4)
                        }
                   MAX-ACCESS  read-only
                   STATUS  current
                   DESCRIPTION
                           "Chassis type."
                   ::= { rdnChassis 1 }

               rdnChassisVersion OBJECT-TYPE
                   SYNTAX  DisplayString
                   MAX-ACCESS  read-only
                   STATUS  current
                   DESCRIPTION
                           "Chassis hardware revision level, or an empty
                           string if unavailable."
                   ::= { rdnChassis 2 }

               rdnChassisId OBJECT-TYPE
                   SYNTAX  DisplayString
                   MAX-ACCESS  read-write
                   STATUS  current
                   DESCRIPTION
                           "Unique ID string. Defaults to chassis serial
                           number if available, otherwise empty. Can
                           also be set with 'snmp-server chassis-id'."
                   ::= { rdnChassis 3 }

               rdnProcessorRam OBJECT-TYPE
                   SYNTAX  Integer32
                   MAX-ACCESS  read-only
                   STATUS  current
                   DESCRIPTION
                           "Megabytes of RAM available to CPU."
                   ::= { rdnChassis 4 }

               rdnNvRAMSize OBJECT-TYPE
                   SYNTAX  Integer32
                   MAX-ACCESS  read-only
                   STATUS  current
                   DESCRIPTION
                           "Bytes of non-volatile configuration memory."
                   ::= { rdnChassis 5 }

               rdnNvRAMUsed OBJECT-TYPE
                   SYNTAX  Integer32
                   MAX-ACCESS  read-only
                   STATUS  current
                   DESCRIPTION
                           "Bytes of non-volatile configuration memory
                           in use."
                   ::= { rdnChassis 6 }

               rdnFlashSize OBJECT-TYPE
                   SYNTAX  Integer32
                   MAX-ACCESS  read-only
                   STATUS  current
                   DESCRIPTION
                           "Bytes flash memory."
                   ::= { rdnChassis 7 }

               rdnCardTable OBJECT-TYPE
                   SYNTAX  SEQUENCE OF RdnCardEntry
                   MAX-ACCESS  not-accessible
                   STATUS  current
                   DESCRIPTION
                            "Chassis card table."
                   ::= { rdnChassis 8 }

               rdnCardEntry OBJECT-TYPE
                   SYNTAX RdnCardEntry
                   MAX-ACCESS  not-accessible
                   STATUS  current
                   DESCRIPTION
                            "Chassis card table."
                   INDEX { rdnCardIndex }
               ::= { rdnCardTable 1 }

               RdnCardEntry ::=
                   SEQUENCE {
                       rdnCardIndex
                           Unsigned32,
                       rdnCardType
                           INTEGER,
                       rdnCardDescr
                           DisplayString,
                       rdnCardSerial
                           DisplayString,
                       rdnCardHwVersion
                           DisplayString,
                       rdnCardSwVersion
                           DisplayString,
                       rdnCardSlotNumber
                           Integer32,
                       rdnCardContainedByIndex
                           Integer32,
                       rdnCardOperStatus
                           INTEGER
                   }

               --
               -- start of card table
               --

               rdnCardIndex OBJECT-TYPE
                   SYNTAX  Unsigned32(1..4294967295)
                   MAX-ACCESS  not-accessible
                   STATUS  current
                   DESCRIPTION
                           "Index into cardTable (not physical chassis
                            slot number)."
                   ::= { rdnCardEntry 1 }

               rdnCardType OBJECT-TYPE
                   SYNTAX  INTEGER {
                        unknown(1),
                        srm(2),
                        io(3)
                        }
                   MAX-ACCESS  read-only
                   STATUS  current
                   DESCRIPTION
                           "Functional type of this card."
                   ::= { rdnCardEntry 2 }

               rdnCardDescr OBJECT-TYPE
                   SYNTAX  DisplayString
                   MAX-ACCESS  read-only
                   STATUS  current
                   DESCRIPTION
                           "Text description of this card."
                   ::= { rdnCardEntry 3 }

               rdnCardSerial OBJECT-TYPE
                   SYNTAX  DisplayString
                   MAX-ACCESS  read-only
                   STATUS  current
                   DESCRIPTION
                           "The serial number of this card, or zero if
                           unavailable."
                   ::= { rdnCardEntry 4 }

               rdnCardHwVersion OBJECT-TYPE
                   SYNTAX  DisplayString
                   MAX-ACCESS  read-only
                   STATUS  current
                   DESCRIPTION
                           "Hardware revision level of this card, or an
                           empty string if unavailable."
                   ::= { rdnCardEntry 5 }

               rdnCardSwVersion OBJECT-TYPE
                   SYNTAX  DisplayString
                   MAX-ACCESS  read-only
                   STATUS  current
                   DESCRIPTION
                           "Version of the firmware or microcode
                           installed on this card, or an empty string if
                           unavailable."
                   ::= { rdnCardEntry 6 }

               rdnCardSlotNumber OBJECT-TYPE
                   SYNTAX  Integer32
                   MAX-ACCESS  read-only
                   STATUS  current
                   DESCRIPTION
                           "Slot number relative to the containing card or
                           chassis, or -1 if neither applicable nor
                           determinable."
                   ::= { rdnCardEntry 7 }

               rdnCardContainedByIndex OBJECT-TYPE
                   SYNTAX  Integer32
                   MAX-ACCESS  read-only
                   STATUS  current
                   DESCRIPTION
                           "cardIndex of the parent card which
                           directly contains this card, or 0 if
                           contained by the chassis, or -1 if not
                           applicable nor determinable."
                   ::= { rdnCardEntry 8 }

               rdnCardOperStatus OBJECT-TYPE
                   SYNTAX  INTEGER {
                          not-specified(1),
                          up(2),
                          down(3),
                          standby(4),
                          rom(5),
                          flash(6),
                          diag(7),
                          boot(8),
                          config(9)
                          }
                   MAX-ACCESS  read-only
                   STATUS  current
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave.
                           Intermediate stages (rom,flash,diag,boot,config)
                           are also exposed."
                   ::= { rdnCardEntry 9 }


               -- end of card table


               rdnChassisSlots OBJECT-TYPE
                   SYNTAX  Integer32
                   MAX-ACCESS  read-only
                   STATUS  current
                   DESCRIPTION
                           "Number of slots in this chassis, or -1 if
                           neither applicable nor determinable."
                   ::= { rdnChassis 9 }

               rdnSlotTable OBJECT-TYPE
                   SYNTAX  SEQUENCE OF RdnSlotEntry
                   MAX-ACCESS  not-accessible
                   STATUS  current
                   DESCRIPTION
                            "Chassis slot table."
                   ::= { rdnChassis 10 }

               --
               -- start of slot table
               --

               rdnSlotEntry OBJECT-TYPE
                   SYNTAX RdnSlotEntry
                   MAX-ACCESS  not-accessible
                   STATUS  current
                   DESCRIPTION
                            "Chassis slot table."
                   INDEX { rdnSlotIndex }
               ::= { rdnSlotTable 1 }

               RdnSlotEntry ::=
                   SEQUENCE {
                       rdnSlotIndex               Integer32,
                       rdnSlotType                INTEGER,
                       rdnSlotNumber              Integer32,
                       rdnSlotOperStatus          INTEGER,
                       rdnOfflineModemCount       Integer32,
                       rdnOnlineModemCount        Integer32,
                       rdnActiveModemCount        Integer32,
                       rdnRegisteredModemCount    Integer32,
                       rdnProvisionedModemCount   Integer32,
                       rdnUnregisteredModemCount  Integer32,
                       rdnResetSlotStats          TruthValue,
		       rdnSlotUnerroreds	  Counter32,
                       rdnSlotCorrecteds          Counter32,
                       rdnSlotUncorrectables      Counter32
                   }

               rdnSlotIndex OBJECT-TYPE
                   SYNTAX  Integer32 (1..2147483647)
                   MAX-ACCESS  not-accessible
                   STATUS  current
                   DESCRIPTION
                           "The index into rdnSlotTable (not physical slot number).
			   This object's instance is always one number greater than
			   the rdnSlotNumber (physical slot number) instance that it
			   indexes."
                   ::= { rdnSlotEntry 1 }

               rdnSlotType OBJECT-TYPE
                   SYNTAX  INTEGER {
                        unknown(1),
                        srm(2),
                        io(3),
	                hsim(4),
                        cmts(5)
                        }
                   MAX-ACCESS  read-only
                   STATUS  current
                   DESCRIPTION
                           "Functional type of this slot.
		           'io(3)' was used by older agents to report
		           either CMTS, HSIM, or none. Newer agents
	                   will no longer report 'io(3)' and instead
			   will use either 'hsim(4)' for HSIM, 'cmts(5)'
	                   for CMTS, or 'unkown(1)' for no module
			   present."
                   ::= { rdnSlotEntry 2 }

               rdnSlotNumber OBJECT-TYPE
                   SYNTAX  Integer32 (-1..15)
                   MAX-ACCESS  read-only
                   STATUS  current
                   DESCRIPTION
                           "The physical chasis slot number relative to the
			   containing card or chassis, or -1 if neither applicable
			   nor determinable."
                   ::= { rdnSlotEntry 3 }

               rdnSlotOperStatus OBJECT-TYPE
                   SYNTAX  INTEGER {
                          not-specified(1),
                          up(2),
                          down(3),
                          standby(4)
                          }
                   MAX-ACCESS  read-only
                   STATUS  current
                   DESCRIPTION
                           "The operational status of the chassis physical
                            slot.  rdnSlotOperStatus is up when a card is
                           recognized by the system and is enabled for
                           operation. rdnSlotOperStatus is down if a
                           card is not present or recognized by the system,
                           or if it is not enabled for operation.
                           rdnSlotOperStatus is standby if the card is
                           enabled and acting as a standby slave.  A
                           not-specified state indicates an unknown error
                           condition"
                   ::= { rdnSlotEntry 4 }

               rdnOfflineModemCount OBJECT-TYPE
                   SYNTAX      Integer32 (0..2147483647)
                   MAX-ACCESS  read-only
                   STATUS      current
                   DESCRIPTION "Number of offline modems for this slot"
                   ::= { rdnSlotEntry 5 }

               rdnOnlineModemCount OBJECT-TYPE
                   SYNTAX      Integer32 (0..2147483647)
                   MAX-ACCESS  read-only
                   STATUS      current
                   DESCRIPTION "Number of online modems for this slot"
                   ::= { rdnSlotEntry 6 }

               rdnActiveModemCount OBJECT-TYPE
                   SYNTAX      Integer32 (0..2147483647)
                   MAX-ACCESS  read-only
                   STATUS      current
                   DESCRIPTION "Number of active modems for this slot"
                   ::= { rdnSlotEntry 7 }

               rdnRegisteredModemCount OBJECT-TYPE
                   SYNTAX      Integer32 (0..2147483647)
                   MAX-ACCESS  read-only
                   STATUS      current
                   DESCRIPTION "Number of registered modems for this slot"
                   ::= { rdnSlotEntry 8 }

               rdnProvisionedModemCount OBJECT-TYPE
                   SYNTAX      Integer32 (0..2147483647)
                   MAX-ACCESS  read-only
                   STATUS      current
                   DESCRIPTION "Number of provisioned modems for this slot"
                   ::= { rdnSlotEntry 9 }

               rdnUnregisteredModemCount OBJECT-TYPE
                   SYNTAX      Integer32 (0..2147483647)
                   MAX-ACCESS  read-only
                   STATUS      current
                   DESCRIPTION "Number of Unregistered modems for this slot"
                   ::= { rdnSlotEntry 10 }

               rdnResetSlotStats OBJECT-TYPE
                   SYNTAX      TruthValue
                   MAX-ACCESS  read-write
                   STATUS      current
                   DESCRIPTION "The byte and packet counters for all the cable
                                modems for the given slot are reset by a 'set'
                                of this object to TRUE(1).  This object will
                                always return FALSE(2) when read."
                   ::= { rdnSlotEntry 11 }

		rdnSlotUnerroreds OBJECT-TYPE
		SYNTAX		  Counter32
		MAX-ACCESS	  read-only
		STATUS		  current
		DESCRIPTION
                    "Codewords received on this cmts slot without error.
                     This includes all codewords, whether or not they
                     were part of frames destined for this device."
		::= { rdnSlotEntry 12 }

		rdnSlotCorrecteds OBJECT-TYPE
		SYNTAX		  Counter32
		MAX-ACCESS	  read-only
		STATUS		  current
		DESCRIPTION
                    "Codewords received on this cmts slot with correctable
                     errors. This includes all codewords, whether or not
                     they were part of frames destined for this device."
		::= { rdnSlotEntry 13 }

		rdnSlotUncorrectables OBJECT-TYPE
		SYNTAX		  Counter32
		MAX-ACCESS	  read-only
		STATUS		  current
		DESCRIPTION
	            "Codewords received on this cmts slot with uncorrectable
        	     errors. This includes all codewords, whether or not
	             they were part of frames destined for this device."
		::= { rdnSlotEntry 14 }

               -- end of slot table


               rdnCardIfIndexTable OBJECT-TYPE
                   SYNTAX  SEQUENCE OF RdnCardIfIndexEntry
                   MAX-ACCESS  not-accessible
                   STATUS  current
                   DESCRIPTION
                            "Chassis card table."
                   ::= { rdnChassis 11 }

               --
               -- start of card if table
               --

               rdnCardIfIndexEntry OBJECT-TYPE
                   SYNTAX      RdnCardIfIndexEntry
                   MAX-ACCESS  not-accessible
                   STATUS      current
                   DESCRIPTION
                            "Chassis card table."
                   INDEX { rdnCardIfIndex }
               ::= { rdnCardIfIndexTable 1 }

               RdnCardIfIndexEntry ::=
                   SEQUENCE {
                       rdnCardIfIndex                 Integer32,
                       rdnCardIfSlotNumber            Integer32,
                       rdnCardIfPortNumber            Integer32,
                       rdnCardIfCardIndex             Integer32,
                       rdnCardIfConnectorTypeEnabled  INTEGER,
                       rdnCardIfLinkUpDownEnable      INTEGER,
                       rdnCardIfPortType              INTEGER
                   }

               rdnCardIfIndex OBJECT-TYPE
                   SYNTAX      Integer32
                   MAX-ACCESS  read-only
                   STATUS      current
                   DESCRIPTION
                           "matches RFC1213 ifTable IfIndex"
                   ::= { rdnCardIfIndexEntry 1 }

               rdnCardIfSlotNumber OBJECT-TYPE
                   SYNTAX      Integer32
                   MAX-ACCESS  read-only
                   STATUS      current
                   DESCRIPTION
                           "Chassis slot number, or -1 if neither
                           applicable nor determinable."
                   ::= { rdnCardIfIndexEntry 2 }

               rdnCardIfPortNumber OBJECT-TYPE
                   SYNTAX      Integer32
                   MAX-ACCESS  read-only
                   STATUS      current
                   DESCRIPTION
                           "Chassis port number, unique per port on a
                            given card if available."
                   ::= { rdnCardIfIndexEntry 3 }

               rdnCardIfCardIndex OBJECT-TYPE
                   SYNTAX      Integer32
                   MAX-ACCESS  read-only
                   STATUS      current
                   DESCRIPTION
                           "cardIndex of the card in the Chassis cardTable
                            which contains this interface."
                   ::= { rdnCardIfIndexEntry 4 }

               rdnCardIfConnectorTypeEnabled OBJECT-TYPE
                   SYNTAX      INTEGER {
                                   not-specified(1),
                                   none (2),
                                   rj-45 (3),
                                   db-40 (4),
                                   db-15 (5)
                               }
                   MAX-ACCESS  read-only
                   STATUS      current
                   DESCRIPTION "Interface connector type currently enabled.
                                Value will be 1 if not known or not used,
                                or 2 if none of this ports' interface
                                connectors are enabled."
                   ::= { rdnCardIfIndexEntry 5 }

          rdnCardIfLinkUpDownEnable OBJECT-TYPE
                   SYNTAX      INTEGER { enabled(1),
                                         disabled(2) }
                   MAX-ACCESS  read-write
                   STATUS      current
                   DESCRIPTION "This enables and disables the sending of
                                the proprietary notifications 'rdnLinkUpTrap'
                                and 'rdnLinkDownTrap' that provide more
                                information than the standard link up and
                                link down notifications.  By default, these
                                traps are disabled."
                   DEFVAL { disabled }
                   ::= { rdnCardIfIndexEntry 6 }

               rdnCardIfPortType OBJECT-TYPE
                   SYNTAX      INTEGER {
                                   ethernet(1),
                                   gige(2),
                                   cmts(3),
                                   cmts-dn(4),
                                   cmts-up(5),
                                   cmts-up-log(6),
                                   pos(7),
                                   lag(8)
	                       }
                   MAX-ACCESS  read-only
                   STATUS      current
                   DESCRIPTION "This object is used to identify port types for a
                                given card. This object will report ethernet(1)
                                for SRM ports and HSIM FE ports, gige(2) for GigE
                                ports, cmts(3) for CMTS cards, cmts_dn(4) in case
                                of downstream ports for CMTS cards, cmts_up(5) in
                                case of upstream ports for CMTS cards, cmts_up_log(6)
                                in case of upstream logical channels for CMTS cards,
                                pos(7) for POS cards, lag(8) for Link Aggregation interfaces"
                   ::= { rdnCardIfIndexEntry 7 }


               -- end of card if table


               rdnSysUpTimeAtLastChassisChange OBJECT-TYPE
                   SYNTAX  TimeTicks
                   MAX-ACCESS  read-only
                   STATUS  current
                   DESCRIPTION
                           "Time in seconds/100 from the last cold
                           start to the last change in the chassis'
                           configuration. This value will be updated
                           whenever the chassis experiences a change
                           in the count, type, or slot position of
                           a card in cardTable."
                   ::= { rdnChassis 12 }

               rdnSysUpTimeAtLastConfigChange OBJECT-TYPE
                   SYNTAX  TimeTicks
                   MAX-ACCESS  read-only
                   STATUS  current
                   DESCRIPTION
                           "Time in seconds/100 from the last
						   configuration change in the system. This
						   value will be set back to zero whenever the system
						   experiences a change in the configuration."
                   ::= { rdnChassis 13 }

               rdnChassisPowerTrapEnable OBJECT-TYPE
                       SYNTAX     INTEGER { enabled(1), disabled(2) }
                       MAX-ACCESS read-write
                       STATUS     current
                       DESCRIPTION
                           "This object controls SNMP traps for chassis Power Failure.
                            If its value is set to enabled(1), then traps
                            are generated. If the value is disabled(2), then traps
                            are not generated.
                            By default, this object has the value enabled(1).
                           "
                       DEFVAL { enabled }

                       ::= { rdnChassis 14 }

               rdnChassisFanTrapEnable OBJECT-TYPE
                       SYNTAX     INTEGER { enabled(1), disabled(2) }
                       MAX-ACCESS read-write
                       STATUS     current
                       DESCRIPTION
                           "This object controls SNMP traps for chassis Fan Failure.
                            If its value is set to enabled(1), then traps
                            are generated. If the value is disabled(2), then traps
                            are not generated.
                            By default, this object has the value enabled(1).
                           "
                       DEFVAL { enabled }

                       ::= { rdnChassis 15 }

               rdnChassisBSRSrmSwitchoverTrapEnable OBJECT-TYPE
                       SYNTAX     INTEGER { enabled(1), disabled(2) }
                       MAX-ACCESS read-write
                       STATUS     current
                       DESCRIPTION
                           "This object controls SNMP traps for redundant SRM switchovers.
                            If its value is set to enabled(1), then traps
                            are generated. If the value is disabled(2), then traps
                            are not generated.
                            By default, this object has the value enabled(1).
                           "
                       DEFVAL { enabled }

                       ::= { rdnChassis 16 }


        -- traps

               chassisNotificationObject OBJECT IDENTIFIER ::= { rdnChassis 0 }

               chassisPowerFailureTrapInfo OBJECT-TYPE
               SYNTAX  INTEGER {
                          powerFailureA(1),
                          powerFailureB(2),
                          powerRestoredA(3),
                          powerRestoredB(4)
                       }
               MAX-ACCESS accessible-for-notify
               STATUS     current
               DESCRIPTION "Indicates the location of the Power Failure."
               ::= { chassisNotificationObject 1 }


               chassisPowerFailureTrap NOTIFICATION-TYPE
               OBJECTS { chassisPowerFailureTrapInfo }
               STATUS current
               DESCRIPTION "A chassisPowerFailureTrap is generated when a Power
                            Failure is detected in the system"
               ::= { chassisNotificationObject 2 }

               chassisFanFailureTrapInfo OBJECT-TYPE
               SYNTAX  INTEGER {
                          upperFanFailure(1),
                          lowerFanFailure(2)
                       }
               MAX-ACCESS accessible-for-notify
               STATUS     current
               DESCRIPTION "Indicates the location of the Fan Failure."
               ::= { chassisNotificationObject 3 }


               chassisFanFailureTrap NOTIFICATION-TYPE
               OBJECTS { chassisFanFailureTrapInfo }
               STATUS current
               DESCRIPTION "A chassisFanFailureTrap is generated when a Fan
                            Failure is detected in the system"
               ::= { chassisNotificationObject 4 }


               rdnRedundancyFailedSlotNumber OBJECT-TYPE
                 SYNTAX  Integer32 (0..2147483647)
                 MAX-ACCESS  accessible-for-notify
                 STATUS  current
                 DESCRIPTION "Chassis slot number that failed,
                              or -1 if neither applicable nor
                              determinable."
                  ::= { chassisNotificationObject 5 }


               rdnRedundancyBackupSlotNumber OBJECT-TYPE
                 SYNTAX  Integer32 (0..2147483647)
                 MAX-ACCESS  accessible-for-notify
                 STATUS  current
                 DESCRIPTION "Slot number of the backup card
                              that took over for the failed card,
                              or -1 if neither applicable nor
                              determinable."
                  ::= { chassisNotificationObject 6 }



               rdnBSRSrmSwitchoverTrap NOTIFICATION-TYPE
                              OBJECTS
                              {
                                rdnRedundancyFailedSlotNumber,
                                rdnRedundancyBackupSlotNumber
                              }
                              STATUS current
                              DESCRIPTION "An SRM Card has failed, and a
                                           switchover has
                                           occurred to a redundant SRM card."

                ::= { chassisNotificationObject 7 }


               rdnLinkUpTrap NOTIFICATION-TYPE
                             OBJECTS { ifIndex,
                                       ifDescr,
                                       ifType,
                                       ifAdminStatus,
                                       ifOperStatus }
                             STATUS current
                             DESCRIPTION
                                   "A proprietary Link Up Notification for all
                                   interfaces. This notification contains more details
                                   than the standard 'linkUp' notification in RFC 2863."
                            ::= { chassisNotificationObject 8 }


               rdnLinkDownTrap  NOTIFICATION-TYPE
                                OBJECTS   { ifIndex,
                                            ifDescr,
                                            ifType,
                                            ifAdminStatus,
                                            ifOperStatus }
                                STATUS    current
                                DESCRIPTION
                                    "A proprietary Link Down Notification for all
                                    interfaces. This notification contains more details
                                    than the standard 'linkDown' notification in RFC 2863."
                                ::= { chassisNotificationObject 9 }

               rdnBsrTestTrap NOTIFICATION-TYPE
                              OBJECTS
                              {
                                docsDevEvLevel,
                                sysDescr
                              }
                              STATUS current
                              DESCRIPTION
                                  "This is convenient test trap that Service personnel
                                   can generate manually, in debug mode, from the CLI,
                                   for diagnostic purposes ('generate snmp-trap [severity]').

                                   Varbinds are docsDevEvLevel = trap severity level,
                                   and sysDescr = system description.
                                  "

                ::= { chassisNotificationObject 10 }



        -- conformance information

        -- compliance statements


        -- units of conformance

    END
