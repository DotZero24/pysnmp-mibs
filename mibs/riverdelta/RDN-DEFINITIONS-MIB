-- *****************************************************************
-- RDN-DEFINITIONS-MIB.mib:
-- Motorola BSR's Definitions MIB
--
-- Copyright (C) 2001, 2008 by Motorola, Inc.
-- All rights reserved.
-- *****************************************************************
RDN-DEFINITIONS-MIB DEFINITIONS ::= BEGIN

    IMPORTS
        MODULE-IDENTITY
            FROM SNMPv2-SMI
        riverdelta
            FROM RDN-MIB;

    -- riverdelta definitions mib module

    rdnDefinitions MODULE-IDENTITY
        LAST-UPDATED "200808080000Z" -- August 8, 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola definitions.

		 Copyright (C) 2001, 2008 by Motorola, Inc.
	     	 All rights reserved."


 	REVISION    "200808080000Z" -- August 8, 2008
	DESCRIPTION
		"Added Copyright Statement into MIB modules's
	     	description."

        REVISION     "200311050000Z"
        DESCRIPTION
                "Updated the CONTACT-INFO."
        REVISION     "200212100000Z"
        DESCRIPTION
                "remove rdnSensorsSysAvg;
                 replace rdnSensorsFanTop and rdnSensorsFanBottom with
	         rdnSensorsFan"
        REVISION     "200104180000Z"
        DESCRIPTION
                "Initial creation."
        ::= { riverdelta 4 }

END
