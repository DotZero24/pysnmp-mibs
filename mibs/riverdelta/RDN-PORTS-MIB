-- *****************************************************************
-- RDN-PORTS-MIB.mib:
-- Motorola BSR's Ports Definitions MIB
--
-- Copyright (C) 2001, 2008 by Motorola, Inc.
-- All rights reserved.
-- *****************************************************************
RDN-PORTS-MIB DEFINITIONS ::= BEGIN

    IMPORTS
        MODULE-IDENTITY
            FROM SNMPv2-SMI
        rdnDefinitions
            FROM RDN-DEFINITIONS-MIB;

    -- riverdelta ports definitions mib module

    rdnPorts MODULE-IDENTITY
        LAST-UPDATED "200808080000Z" -- August 8, 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola Port
                definitions.

		Copyright (C) 2001, 2008 by Motorola, Inc.
	     	All rights reserved."


	REVISION "200808080000Z"  -- 08 August 2008
	DESCRIPTION
		"Added Copyright Statement into MIB modules's
	       	 description."
        REVISION     "200510200000Z"
        DESCRIPTION
                "Added definition for subinterface port"
        REVISION     "200311050000Z"
        DESCRIPTION
                "+ Updated the CONTACT-INFO.
	         + Reorder REVISION/DESCRIPTION in required
                   reverse chronological order."
        REVISION     "200304290000Z"
        DESCRIPTION
                "Clean up of CONTACT-INFO."
        REVISION     "200105080000Z"
        DESCRIPTION
                "Initial creation."
        ::= { rdnDefinitions 5 }


      --
      -- module definitions for all riverdelta modules
      --

      rdnPortsUnknown           OBJECT IDENTIFIER ::= { rdnPorts 0 }
      rdnPortsGige              OBJECT IDENTIFIER ::= { rdnPorts 1 }
      rdnPortsEthernet          OBJECT IDENTIFIER ::= { rdnPorts 2 }
      rdnPortsCableMac          OBJECT IDENTIFIER ::= { rdnPorts 3 }
      rdnPortsCableUpstream     OBJECT IDENTIFIER ::= { rdnPorts 4 }
      rdnPortsCableDownstream   OBJECT IDENTIFIER ::= { rdnPorts 5 }
      rdnPortsCableSubIf        OBJECT IDENTIFIER ::= { rdnPorts 6 }
      rdnPortsLoopback          OBJECT IDENTIFIER ::= { rdnPorts 7 }
      rdnPortsT1                OBJECT IDENTIFIER ::= { rdnPorts 8 }
      rdnPortsNull              OBJECT IDENTIFIER ::= { rdnPorts 9 }
      rdnPortsTunnel            OBJECT IDENTIFIER ::= { rdnPorts 10 }
      rdnPortsPOS               OBJECT IDENTIFIER ::= { rdnPorts 11 }
      rdnPortsATM               OBJECT IDENTIFIER ::= { rdnPorts 12 }

END
