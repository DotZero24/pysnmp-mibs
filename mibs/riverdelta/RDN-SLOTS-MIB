-- *****************************************************************
-- RDN-SLOTS-MIB.mib:
-- Motorola BSR's Slot Definitions MIB
--
-- Copyright (C) 2001, 2008 by Motorola, Inc.
-- All rights reserved.
-- *****************************************************************
RDN-SLOTS-MIB DEFINITIONS ::= BEGIN

    IMPORTS
        MODULE-IDENTITY
            FROM SNMPv2-SMI
        rdnDefinitions
            FROM RDN-DEFINITIONS-MIB;

    -- riverdelta slot definitions mib module

    rdnSlots MODULE-IDENTITY
        LAST-UPDATED "200808080000Z"  -- August 8, 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola Slot
                definitions.

		Copyright (C) 2001, 2008 by Motorola, Inc.
	     	All rights reserved."

	REVISION     "200808080000Z"  -- August 8, 2008
	DESCRIPTION
		"Added Copyright Statement into MIB modules's
	       	 description."
        REVISION     "200311050000Z"
        DESCRIPTION
                "+ Updated the CONTACT-INFO.
	         + Reorder REVISION/DESCRIPTION in required
                   reverse chronological order."
        REVISION     "200304290000Z"
        DESCRIPTION
                "Clean up of CONTACT-INFO."
        REVISION     "200104180000Z"
        DESCRIPTION
                "Initial creation."
        ::= { rdnDefinitions 3 }


      --
      -- slot definitions for all riverdelta chassis's
      --

      rdnSlotsUnknown         OBJECT IDENTIFIER ::= { rdnSlots 0 }
      rdnSlotsBSR64000Master  OBJECT IDENTIFIER ::= { rdnSlots 1 }
      rdnSlotsBSR64000IO      OBJECT IDENTIFIER ::= { rdnSlots 2 }
      rdnSlotsBSR1000         OBJECT IDENTIFIER ::= { rdnSlots 3 }
      rdnSlotsOSR2000         OBJECT IDENTIFIER ::= { rdnSlots 4 }

END
