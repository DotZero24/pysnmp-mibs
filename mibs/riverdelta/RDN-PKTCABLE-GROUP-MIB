-- *****************************************************************
-- RDN-PKTCABLE-GROUP-MIB
-- Motorola BSR's Packet Cable MIB
--
-- Copyright (C) 2002, 2008 by Motorola, Inc.
-- All rights reserved.
-- *****************************************************************
RDN-PKTCABLE-GROUP-MIB DEFINITIONS ::= BEGIN

  IMPORTS

        riverdelta
                FROM RDN-MIB
        MODULE-IDENTITY,
        NOTIFICATION-TYPE,
        OBJECT-TYPE,
        Integer32,
        IpAddress
                FROM SNMPv2-SMI
        TruthValue,
        MacAddress,
        TEXTUAL-CONVENTION,
        DisplayString
                FROM SNMPv2-TC;


rdnPacketCableGroup MODULE-IDENTITY
        LAST-UPDATED "200810060000Z" -- 06 October 2008
        ORGANIZATION "Motorola"
        CONTACT-INFO "Motorola
	              Customer Service
                      101 Tournament Drive
                      Horsham, PA 19044
                      US Tel: +1 888 944 4357
                      Int Tel: +1 215 323 0044
	              Fax: +1 215 323 1502
                      Email: CPSSupport@Motorola.com"


	DESCRIPTION
            "MIB module for Motorola PacketCable.

	    Copyright (C) 2002, 2008 by Motorola, Inc.
	    All rights reserved."

        REVISION    "200810060000Z" -- Oct 06, 2008
        DESCRIPTION
            "Added Differentiated Services Code Point(DSCP) to Motorola PacketCable.
             Added rdnPktDQoSDscp, rdnPktMMDscp, rdnPktEMDscp and rdnPktESCccDscp."

	REVISION    "200808080000Z" -- 08 August 2008
	DESCRIPTION
	    "Fixed this MIB MODULE'S description and
	    its revison history. Added Copyright Statement into
	    MIB modules's description."

	REVISION    "200710220000Z" -- Oct 22, 2007
	DESCRIPTION
            "Added rdnPktDQoSGateResReassign to rdnPktDQoSStatsEntry."

	REVISION    "200605240000Z" -- May 24, 2006
        DESCRIPTION
            "Added RKS trap support to Motorola PacketCable.
             Added rdnPktEMRKSFailureTrapEnable."

	REVISION    "200605240000Z" -- May 24, 2006
        DESCRIPTION
            "Corrected the comments for rdnPktDQoSEmergencyPreemptTrap
	    mib object."

        REVISION    "200602150000Z" -- Feb 15, 2006
        DESCRIPTION
            "Added rdnPktDQoSEmergencyPreemptTrap mib object."

	REVISION    "200601240000Z" -- January 24, 2006
        DESCRIPTION
            "Add Preemption mib object to Motorola PacketCable."

	REVISION    "200311050000Z" -- November 5, 2003
        DESCRIPTION
            "Updated the CONTACT-INFO."

        REVISION    "200310240000Z" -- October 24, 2003
        DESCRIPTION
            "Changed MAX-ACCESS of the following objects from
             read-only to not-accessible: rdnGateId,
             rdnGateDirection, rdnPktDQosCopsHandle. Removed
             object rdnGateID and replaced with rdnGateId.
             Value of rdnGateDirection downstream(2) added."

        REVISION    "200305120000Z" -- May 12, 2003
        DESCRIPTION
            "Imported NOTIFICATION-TYPE from SNMPv2-SMI."

        REVISION    "200209060000Z"
        DESCRIPTION
            "Initial Version. "

        ::= { riverdelta 7 }

-- Textual Conventions
BcidDataArray ::= TEXTUAL-CONVENTION
    STATUS       current
    DESCRIPTION
          "An array holds the Billing Correlation ID."
    SYNTAX       OCTET STRING (SIZE (0..24))

--
-- riverdelta PacketCable group
--
rdnPktDQoSConfigGroup OBJECT IDENTIFIER ::= { rdnPacketCableGroup 1 }

rdnPktDQoSCOPSStatus OBJECT-TYPE
        SYNTAX  TruthValue
        MAX-ACCESS  read-write
        STATUS  current
        DESCRIPTION
            "This object is used to enable/disable PacketCable DQoS feature.
             When this object is set to FALSE(2), DQoS will be disabled."
        ::= { rdnPktDQoSConfigGroup 1 }

rdnPktDQoSCMTSIp OBJECT-TYPE
        SYNTAX  IpAddress
        MAX-ACCESS  read-write
        STATUS  current
        DESCRIPTION
            "An IP address can be configured for the CMTS. If that IP address
             is configured, BSR will only accept a COPS connection destined
             to that IP address. Example, loop back, HFC or network IP address."
        ::= { rdnPktDQoSConfigGroup 2 }

rdnPktDQoSPEPID OBJECT-TYPE
        SYNTAX  DisplayString (SIZE (0..32))
        MAX-ACCESS  read-write
        STATUS  current
        DESCRIPTION
            "An ASCII string to identify the CMTS. Default - Motorola CMTS."
        ::= { rdnPktDQoSConfigGroup 3 }

rdnPktDQoSClientAccpTimer OBJECT-TYPE
        SYNTAX  Integer32 (1..3600000)
        MAX-ACCESS  read-write
        STATUS  current
        DESCRIPTION
            "This object specifies the Time that limits the CMTS to wait for
            the Client Accept from the CMS/GC in milliseconds."
        ::= { rdnPktDQoSConfigGroup 4 }

rdnPktDQoST0Timer OBJECT-TYPE
        SYNTAX  Integer32 (1..3600)
        MAX-ACCESS  read-write
        STATUS  current
        DESCRIPTION
            "This object specifies the period of time in seconds that a Gate
            may be allocated without being authorized."
        ::= { rdnPktDQoSConfigGroup 5 }

rdnPktDQoST1Timer OBJECT-TYPE
        SYNTAX  Integer32 (1..3600)
        MAX-ACCESS  read-write
        STATUS  current
        DESCRIPTION
            "This object specifies the time in seconds that may elapse between
            the authorization and commit. This provisioned value is only used
            if the T1 value is not provided by the GC/CMS."
        ::= { rdnPktDQoSConfigGroup 6 }

rdnPktDQoST3Timer OBJECT-TYPE
        SYNTAX  Integer32
        MAX-ACCESS  read-write
        STATUS  current
        DESCRIPTION
            "Place holder"
        ::= { rdnPktDQoSConfigGroup 7 }

rdnPktDQoST6Timer OBJECT-TYPE
        SYNTAX  Integer32
        MAX-ACCESS  read-write
        STATUS  current
        DESCRIPTION
            "Place holder."
        ::= { rdnPktDQoSConfigGroup 8 }

rdnPktDQoSCopsTrapEnable  OBJECT-TYPE
        SYNTAX       INTEGER { enabled(1), disabled(2) }
        MAX-ACCESS   read-write
        STATUS       current
        DESCRIPTION "Indicates whether the PacketCable COPS connection trap
                     should be generated. If its value is set to enabled(1),
                     then traps are generated. If the value is disabled(2),
                     then traps are not generated. By default, this object
                     has the value disabled(2).
                     "
        ::= { rdnPktDQoSConfigGroup 9 }

rdnPktDQoSResReqTrapEnable  OBJECT-TYPE
        SYNTAX       INTEGER { enabled(1), disabled(2) }
        MAX-ACCESS   read-write
        STATUS       current
        DESCRIPTION "Indicates whether the PacketCable Resource Request trap
                     should be generated. If its value is set to enabled(1),
                     then traps are generated. If the value is disabled(2),
                     then traps are not generated. By default, this object
                     has the value disabled(2).
                     "
        ::= { rdnPktDQoSConfigGroup 10 }

rdnPktESTrapEnable  OBJECT-TYPE
        SYNTAX       INTEGER { enabled(1), disabled(2) }
        MAX-ACCESS   read-write
        STATUS       current
        DESCRIPTION "Indicates whether the PacketCable ES status trap
                     should be generated. If its value is set to enabled(1),
                     then traps are generated. If the value is disabled(2),
                     then traps are not generated. By default, this object
                     has the value disabled(2).
                     "
        ::= { rdnPktDQoSConfigGroup 11 }

rdnPktESEnable  OBJECT-TYPE
        SYNTAX       INTEGER { enabled(1), disabled(2) }
        MAX-ACCESS   read-write
        STATUS       current
        DESCRIPTION "Indicates whether the PacketCable ES feature is
                     enabled. If its value is set to enabled(1),
                     then Packet Cable ES functionality will operate based
                     on the information received in the Gate-Set message
                     from the CMS. If the value is disabled(2),
                     then the Packet Cable ES functionality will not
                     function according to the information received in the
                     Gate-Set message from the CMS. By default, this object
                     has the value enabled(1).
                     "
        ::= { rdnPktDQoSConfigGroup 12 }

rdnPktDQoSEmergencyTrapEnable  OBJECT-TYPE
        SYNTAX       INTEGER { enabled(1), disabled(2) }
        MAX-ACCESS   read-write
        STATUS       current
        DESCRIPTION "Indicates whether the PacketCable Emergency Call trap
                     should be generated. If its value is set to enabled(1),
                     then traps are generated. If the value is disabled(2),
                     then traps are not generated. By default, this object
                     has the value disabled(2).
                     "
        ::= { rdnPktDQoSConfigGroup 13 }

rdnPktDQoSEmergencyPreemption  OBJECT-TYPE
        SYNTAX       INTEGER {
                     disabled (0),
                     most-recent(1),
                     oldest(2),
                     random(3)
                     }
        MAX-ACCESS   read-write
        STATUS       current
        DESCRIPTION "Indicates whether the PacketCable Emergency Preemption
                     is disabled or set to a specific option of dropping a
                     normal dqos voice call. If its value is set to most-recent(1),
                     the most-recent normal dqos voice call of that Service
                     Class is dropped when the bandwidth of the Emergency
                     Service Class has maxed out. The Preemption can only
                     occur if that Service Class has 'allowShared' turned
                     on. Otherwise, Preemption can not occur and thus, the
                     high priority call can not be completed. If the value
                     is oldest(2), the oldest normal dqos voice call is dropped.
                     If the value is random, random normal dqos voice call
                     is dropped. By default, this object has the value disabled(0).
                     "
        ::= { rdnPktDQoSConfigGroup 14 }

rdnPktEMRKSFailureTrapEnable  OBJECT-TYPE
        SYNTAX       INTEGER { enabled(1), disabled(2) }
        MAX-ACCESS   read-write
        STATUS       current
        DESCRIPTION "Indicates whether the PacketCable EM RKS Failure trap
                     should be generated. If its value is set to enabled(1),
                     then the trap is generated. If the value is disabled(2),
                     then the trap is not generated. By default, this object
                     has the value disabled(2).
                     "
        ::= { rdnPktDQoSConfigGroup 15 }

rdnPktDQoSDscp OBJECT-TYPE
        SYNTAX       Integer32 (0..63)
	MAX-ACCESS   read-write
	STATUS       current
	DESCRIPTION "The contents of the Differentiated Services Code Point(DSCP) for DQoS.
                     DSCP is intended to supersede the existing definitions
		     of the IPv4 TOS octet and the IPv6 Traffic Class octet.
		     By setting this value, DSCP will apply to all the DQoS
		     traffic IP header.
                     "
        DEFVAL { 0 }
	::= { rdnPktDQoSConfigGroup 16 }

rdnPktMMDscp OBJECT-TYPE
        SYNTAX       Integer32 (0..63)
	MAX-ACCESS   read-write
	STATUS       current
	DESCRIPTION "The contents of the Differentiated Services Code Point(DSCP) for Multimedia.
                     DSCP is intended to supersede the exsiting definitions
		     of the IPv4 TOS octet and the IPv6 Traffic Class octet.
		     By setting this value, DSCP will apply to all the Multimedia
		     traffic IP header.
                     "
        DEFVAL { 0 }
	::= { rdnPktDQoSConfigGroup 17 }

rdnPktEMDscp OBJECT-TYPE
        SYNTAX       Integer32 (0..63)
	MAX-ACCESS   read-write
	STATUS       current
	DESCRIPTION "The contents of the Differentiated Services Code Point(DSCP)
	             for Event Message and Electronic Surveillance Call
		     Data Connection(CDC).
                     DSCP is intended to supersede the existing definitions
		     of the IPv4 TOS octet and the IPv6 Traffic Class octet.
		     By setting this value, DSCP will apply to all the Event
		     Message traffic IP header and Electronic Surveillance
		     Call Data Connection traffic IP header.
                     "
        DEFVAL { 0 }
	::= { rdnPktDQoSConfigGroup 18 }

rdnPktESCccDscp OBJECT-TYPE
        SYNTAX       Integer32 (0..63)
	MAX-ACCESS   read-write
	STATUS       current
	DESCRIPTION "The contents of the Differentiated Services Code Point(DSCP)
	             for Electronic Surveillance Call Content Connection(CCC).
                     DSCP is intended to supersede the existing definitions
		     of the IPv4 TOS octet and the IPv6 Traffic Class octet.
		     By setting this value, DSCP will apply to all the Electronic
		     Surveillance Call Content Connection traffic IP header.
                     "
        DEFVAL { 0 }
	::= { rdnPktDQoSConfigGroup 19 }

rdnGateStatsTable OBJECT-TYPE
        SYNTAX  SEQUENCE OF RdnGateStatsEntry
        MAX-ACCESS  not-accessible
        STATUS  current
        DESCRIPTION
            "This table provide PacketCable statistics of DQoS gate."
        ::= { rdnPacketCableGroup 2 }

rdnGateStatsEntry OBJECT-TYPE
        SYNTAX  RdnGateStatsEntry
        MAX-ACCESS  not-accessible
        STATUS  current
        DESCRIPTION
            "Each entry provides a set of statistics objects for DQoS gate."
        INDEX { rdnGateId }
        ::= { rdnGateStatsTable 1 }

RdnGateStatsEntry ::= SEQUENCE
    {
        rdnGateId                         Integer32,
        rdnGateStatsState                 INTEGER,
        rdnGateStatsSubscriberIP          IpAddress,
        rdnGateStatsRKSPrimaryAddr        IpAddress,
        rdnGateStatsRKSPrimaryPort        Integer32,
        rdnGateStatsRKSSecondaryAddr      IpAddress,
        rdnGateStatsRKSSecondaryPort      Integer32,
        rdnGateStatsEventFlag             Integer32,
        rdnGateStatsBillingCorrelationID  BcidDataArray,
        rdnGateStatsDurationTime          DisplayString,
        rdnGateStatsSlotNum               Integer32,
        rdnGateStatsUpSfid                Integer32,
        rdnGateStatsDnSfid                Integer32,
        rdnGateStatsResourceID            Integer32,
        rdnGateStatsESCDCAddr             IpAddress,
        rdnGateStatsESCDCPort             Integer32,
        rdnGateStatsESFlag                Integer32,
        rdnGateStatsESCCCAddr             IpAddress,
        rdnGateStatsESCCCPort             Integer32,
        rdnGateStatsESCCCId               Integer32
   }

rdnGateId OBJECT-TYPE
        SYNTAX      Integer32
        MAX-ACCESS  not-accessible
        STATUS      current
        DESCRIPTION
            "This attribute is the identifier for allocated gate."
        ::= { rdnGateStatsEntry 1 }

rdnGateStatsState OBJECT-TYPE
        SYNTAX      INTEGER {
                idle(0),
                start(1),
                allocated(2),
                authorized(3),
                reserved(4),
--                remoteCommitted(5),
--                localCommitted(6),
                committed(7),
                committedRecovery(8),
                numOfStates(9)
        }
        MAX-ACCESS  read-only
        STATUS      current
        DESCRIPTION
            "This attribute describes current state
                Idle(0),
                Start(1),
                Allocated(2),
                Authorized(3),
                Reserved(4),
                RemoteCommitted(5),
                LocalCommitted(6),
                Committed(7)."
        ::= { rdnGateStatsEntry 2 }

rdnGateStatsSubscriberIP OBJECT-TYPE
        SYNTAX      IpAddress
        MAX-ACCESS  read-only
        STATUS      current
        DESCRIPTION
            "This attribute describes the IP address of MTA requesting the
            gate. Issue:(IPV4 ONLY)"
        ::= { rdnGateStatsEntry 3 }

rdnGateStatsRKSPrimaryAddr OBJECT-TYPE
        SYNTAX      IpAddress
        MAX-ACCESS  read-only
        STATUS      current
        DESCRIPTION
            "This attribute describes Primary Record Keeping Server's IP
            address, the record keeper to whom event records are sent."
        ::= { rdnGateStatsEntry 4 }

rdnGateStatsRKSPrimaryPort OBJECT-TYPE
        SYNTAX      Integer32
        MAX-ACCESS  read-only
        STATUS      current
        DESCRIPTION
            "This attribute describes Primary Record Keeping Server Port, the
             port number for event records to be sent."
        ::= { rdnGateStatsEntry 5 }

rdnGateStatsRKSSecondaryAddr OBJECT-TYPE
        SYNTAX      IpAddress
        MAX-ACCESS  read-only
        STATUS      current
        DESCRIPTION
            "This attribute describes Secondary Record Keeping Server's IP
            address, the record keeper to whom event records are sent."
        ::= { rdnGateStatsEntry 6 }

rdnGateStatsRKSSecondaryPort OBJECT-TYPE
        SYNTAX      Integer32
        MAX-ACCESS  read-only
        STATUS      current
        DESCRIPTION
            "This attribute describes Secondary Record Keeping Server Port,
            the port number for event records to be sent."
        ::= { rdnGateStatsEntry 7 }

rdnGateStatsEventFlag  OBJECT-TYPE
        SYNTAX      Integer32
        MAX-ACCESS  read-only
        STATUS      current
        DESCRIPTION
            "0x01 - Batch Processing. If set the CMTS MUST accumulate event
            records as part of a batch file and send to the Record Keeping
            Server at periodic intervals. If clear the CMTS MUST send the
            event records to the Record Keeping Serverin real-time."
        ::= { rdnGateStatsEntry 8 }

rdnGateStatsBillingCorrelationID OBJECT-TYPE
        SYNTAX      BcidDataArray
        MAX-ACCESS  read-only
        STATUS      current
        DESCRIPTION
            "This attribute is the identifier assigned by the CMS for all
            records related to the session."
        ::= { rdnGateStatsEntry 9 }

rdnGateStatsDurationTime OBJECT-TYPE
        SYNTAX      DisplayString
        MAX-ACCESS  read-only
        STATUS      current
        DESCRIPTION
            "This attribute describes the time that gate was commited."
        ::= { rdnGateStatsEntry 10 }

rdnGateStatsSlotNum OBJECT-TYPE
        SYNTAX      Integer32
        MAX-ACCESS  read-only
        STATUS      current
        DESCRIPTION
            "This attribute describes the CMTS slot number."
        ::= { rdnGateStatsEntry 11 }

rdnGateStatsUpSfid OBJECT-TYPE
        SYNTAX      Integer32
        MAX-ACCESS  read-only
        STATUS      current
        DESCRIPTION
            "This attribute describes the upstream SFID."
        ::= { rdnGateStatsEntry 12 }

rdnGateStatsDnSfid OBJECT-TYPE
        SYNTAX      Integer32
        MAX-ACCESS  read-only
        STATUS      current
        DESCRIPTION
            "This attribute describes the downstream SFID."
        ::= { rdnGateStatsEntry 13 }

rdnGateStatsResourceID OBJECT-TYPE
        SYNTAX      Integer32
        MAX-ACCESS  read-only
        STATUS      current
        DESCRIPTION
            "This attribute is an RSVP object that's used as an identifier
            for future resource changes."
        ::= { rdnGateStatsEntry 14 }

rdnGateStatsESCDCAddr OBJECT-TYPE
        SYNTAX      IpAddress
        MAX-ACCESS  read-only
        STATUS      current
        DESCRIPTION
            "This attribute describes the DF's IP address,
             the DF to whom duplicated event messages are sent."
        ::= { rdnGateStatsEntry 15 }

rdnGateStatsESCDCPort OBJECT-TYPE
        SYNTAX      Integer32
        MAX-ACCESS  read-only
        STATUS      current
        DESCRIPTION
            "This attribute describes the DF's Port for CDC, the
             port number for duplicated event messages to be sent."
        ::= { rdnGateStatsEntry 16 }

rdnGateStatsESFlag  OBJECT-TYPE
        SYNTAX      Integer32
        MAX-ACCESS  read-only
        STATUS      current
        DESCRIPTION
            "If bit 0 is set  - DUP-Event. If set the CMTS MUST send a duplicate copy
             of all event messages relate to this gate to the DF-IP-Address for
             CDC (rdnGateStatsESCDCAddr). If bit 1 is set the CMTS MUST
             send a duplicate copy of all packets matching the
             classifier(s) fo this gate to the DF-IP-Address-for-CCC (rdnGateStatsESCCCAddr)."
        ::= { rdnGateStatsEntry 17 }

rdnGateStatsESCCCAddr OBJECT-TYPE
        SYNTAX      IpAddress
        MAX-ACCESS  read-only
        STATUS      current
        DESCRIPTION
            "This attribute describes the DF's IP address for CCC,
             the DF to whom duplicated classifier matched packets  are sent."
        ::= { rdnGateStatsEntry 18 }

rdnGateStatsESCCCPort OBJECT-TYPE
        SYNTAX      Integer32
        MAX-ACCESS  read-only
        STATUS      current
        DESCRIPTION
            "This attribute describes the DF's Port for CCC, the
             port number for duplicated classifier matched packets to be sent."
        ::= { rdnGateStatsEntry 19 }

rdnGateStatsESCCCId OBJECT-TYPE
        SYNTAX      Integer32
        MAX-ACCESS  read-only
        STATUS      current
        DESCRIPTION
            "An Identifier used to identify the intercept order to the Law
             Enforcement Agency."
        ::= { rdnGateStatsEntry 20 }

rdnGateSpecTable OBJECT-TYPE
        SYNTAX  SEQUENCE OF RdnGateSpecEntry
        MAX-ACCESS  not-accessible
        STATUS  current
        DESCRIPTION
            "This table contains DQoS Gate Specification statistics of
            upstream and downstream."
        ::= { rdnPacketCableGroup 3 }

rdnGateSpecEntry OBJECT-TYPE
        SYNTAX  RdnGateSpecEntry
        MAX-ACCESS  not-accessible
        STATUS  current
        DESCRIPTION
            "Each entry contain DQoS Gate Specification statistics of
             the upstream  or downstream."
        INDEX { rdnGateId, rdnGateDirection }
        ::= { rdnGateSpecTable 1 }

RdnGateSpecEntry ::= SEQUENCE
    {
        rdnGateDirection           INTEGER,
        rdnGateSpecProtocol        Integer32,
        rdnGateSpecSourceIP        IpAddress,
        rdnGateSpecSourcePort      Integer32,
        rdnGateSpecDestIP          IpAddress,
        rdnGateSpecDestPort        Integer32,
        rdnGateSpecServiceFlowID   Integer32,
        rdnGateSpecFlags           INTEGER,
        rdnGateSpecSessionClass    INTEGER,
        rdnGateSpecDiffServCode    Integer32,
        rdnGateSpecT1Timer         Integer32,
        rdnGateSpecTokenBuckRate   Integer32,
        rdnGateSpecBuckSize        Integer32,
        rdnGateSpecPeakDataRate    Integer32,
        rdnGateSpecMinPoliceUnit   Integer32,
        rdnGateSpecMaxPacketSize   Integer32,
        rdnGateSpecReserveRate     Integer32,
        rdnGateSlackTerm           Integer32
    }

rdnGateDirection OBJECT-TYPE
        SYNTAX      INTEGER {
           upstream(1),
           downstream(2)
        }
        MAX-ACCESS  not-accessible
        STATUS      current
        DESCRIPTION
            "This attribute describes the direction of the gate specification."
        ::= { rdnGateSpecEntry 2 }

rdnGateSpecProtocol OBJECT-TYPE
        SYNTAX      Integer32
        MAX-ACCESS  read-only
        STATUS      current
        DESCRIPTION
            "This attribute describes the Protocol to match in the IP header."
        ::= { rdnGateSpecEntry 3 }

rdnGateSpecSourceIP OBJECT-TYPE
        SYNTAX     IpAddress
        MAX-ACCESS  read-only
        STATUS      current
        DESCRIPTION
            "This attribute describes the source IP V4 address, zero for no
             match."
        ::= { rdnGateSpecEntry 4 }

rdnGateSpecSourcePort OBJECT-TYPE
        SYNTAX      Integer32
        MAX-ACCESS  read-only
        STATUS      current
        DESCRIPTION
            "This attribute describes source port. Zero for no match."
        ::= { rdnGateSpecEntry 5 }

rdnGateSpecDestIP OBJECT-TYPE
        SYNTAX     IpAddress
        MAX-ACCESS  read-only
        STATUS      current
        DESCRIPTION
            "This attribute describes the destination IP V4 address, zero for
            no match."
        ::= { rdnGateSpecEntry 6 }

rdnGateSpecDestPort OBJECT-TYPE
        SYNTAX      Integer32
        MAX-ACCESS  read-only
        STATUS      current
        DESCRIPTION
            "This attribute describes destination port. Zero for no match."
        ::= { rdnGateSpecEntry 7 }

rdnGateSpecServiceFlowID OBJECT-TYPE
        SYNTAX      Integer32
        MAX-ACCESS  read-only
        STATUS      current
        DESCRIPTION
            "This attribute describes the service flow ID that maps to the
             Gate. This value could be zero if a Gate is viewed prior to a
             SFID being assigned to the Gate."
        ::= { rdnGateSpecEntry 8 }

rdnGateSpecFlags  OBJECT-TYPE
        SYNTAX      INTEGER {
           autoCommit(1),
           commitNotAllowed(2)
        }
        MAX-ACCESS  read-only
        STATUS      current
        DESCRIPTION
            "autoCommit(1), resources Commit immediately upon reservation.
             commitNotAllowed(2), CMTS ignores any COMMIT messages for the
             gate."
        ::= { rdnGateSpecEntry 9 }

        rdnGateSpecSessionClass OBJECT-TYPE
                SYNTAX      INTEGER {
           unspecified(255),
           normalPriority(1),
           highPriority(2)
        }
        MAX-ACCESS  read-only
        STATUS      current
        DESCRIPTION
            "This attribute identifies the proper admission control policy or
            parameters to be applied for the gate.
               unspecified (255),
               normalPriority (1),
               highPriority (2)."
        ::= { rdnGateSpecEntry 10 }

rdnGateSpecDiffServCode OBJECT-TYPE
        SYNTAX      Integer32
        MAX-ACCESS  read-only
        STATUS      current
        DESCRIPTION
            "This attribute describes Differentiated Services Code Point."
        ::= { rdnGateSpecEntry 11 }

rdnGateSpecT1Timer OBJECT-TYPE
        SYNTAX      Integer32
        MAX-ACCESS  read-only
        STATUS      current
        DESCRIPTION
            "This attribute describes Gate Transition timer in seconds, the
            time limit between authorization and a commit."
        ::= { rdnGateSpecEntry 12 }

rdnGateSpecTokenBuckRate OBJECT-TYPE
        SYNTAX      Integer32
        MAX-ACCESS  read-only
        STATUS      current
        DESCRIPTION
            "Token Bucket Rate, (r) 32 bit IEEE floating point number used in
            Bandwidth Calculations. Specifies the token bucket that the traffic
            conforms to. Part of TSpec."
        ::= { rdnGateSpecEntry 13 }

rdnGateSpecBuckSize OBJECT-TYPE
        SYNTAX      Integer32
        MAX-ACCESS  read-only
        STATUS      current
        DESCRIPTION
            "Token Bucket Size (b) 32 bit IEEE floating point number used in
            Bandwidth Calculations. Specifies the token bucket that the traffic
            conforms ot. Part of TSpec."
        ::= { rdnGateSpecEntry 14 }

rdnGateSpecPeakDataRate OBJECT-TYPE
        SYNTAX      Integer32
        MAX-ACCESS  read-only
        STATUS      current
        DESCRIPTION
            "Peak Data Rate (p) 32 bit IEEE floating point number used in
            Bandwidth Calculations. Specifies the Peak Data Rate at which
            the source sends traffic. Part of TSpec."
        ::= { rdnGateSpecEntry 15 }

rdnGateSpecMinPoliceUnit OBJECT-TYPE
        SYNTAX      Integer32
        MAX-ACCESS  read-only
        STATUS      current
        DESCRIPTION
            "Minimum Policed Unit (m) 32 bit integer. The smallest packet
            size that the source generates, if asmaller packet is sent, it
            will count as a packet of size m for the purpose fo policing.
            Part of TSpec."
        ::= { rdnGateSpecEntry 16 }

rdnGateSpecMaxPacketSize OBJECT-TYPE
        SYNTAX      Integer32
        MAX-ACCESS  read-only
        STATUS      current
        DESCRIPTION
            "Maximum Packet Size (M) 32 bit integer. Maximum packet size
            (including IP and higher layer headers) that are generated by
            the source. Part of TSpec."
        ::= { rdnGateSpecEntry 17 }

rdnGateSpecReserveRate OBJECT-TYPE
        SYNTAX      Integer32
        MAX-ACCESS  read-only
        STATUS      current
        DESCRIPTION
            "Rate (R) 32 bit IEEE floating point integer. The amount of
            bandwidth allocated to the flow. Must be greater than or equal
            to (r) from the TSpec. Part of RSpec."
        ::= { rdnGateSpecEntry 18 }

rdnGateSlackTerm OBJECT-TYPE
        SYNTAX      Integer32
        MAX-ACCESS  read-only
        STATUS      current
        DESCRIPTION
            "Slack Term (S) 32 bit integer. Delay Bound part of RSpec."
        ::= { rdnGateSpecEntry 19 }

rdnPktCMSIpConfigTable OBJECT-TYPE
        SYNTAX      SEQUENCE OF RdnPktCMSIpConfigEntry
        MAX-ACCESS  not-accessible
        STATUS      current
        DESCRIPTION
            "This table contain the IP address list of CMS/GC configuration."
        ::= { rdnPacketCableGroup 4 }

rdnPktCMSIpConfigEntry OBJECT-TYPE
        SYNTAX      RdnPktCMSIpConfigEntry
        MAX-ACCESS  not-accessible
        STATUS      current
        DESCRIPTION
            "List of IP addresses for CMS/GC."
        INDEX { rdnPktCMSIpAddressIndex }
        ::= {rdnPktCMSIpConfigTable 1 }

RdnPktCMSIpConfigEntry ::= SEQUENCE {
           rdnPktCMSIpAddressIndex    Integer32,
           rdnPktCMSIpAddress         IpAddress
        }

rdnPktCMSIpAddressIndex OBJECT-TYPE
        SYNTAX      Integer32
        MAX-ACCESS  not-accessible
        STATUS      current
        DESCRIPTION
            "Index to access rdnPktCMSIpAddress."
        ::= { rdnPktCMSIpConfigEntry 1 }

rdnPktCMSIpAddress OBJECT-TYPE
        SYNTAX      IpAddress
        MAX-ACCESS  read-write
        STATUS      current
        DESCRIPTION
            "Specifies an IP address of a CMS/GC: If not configured, CMTS
             accepts any CMS IP Address.
             NOTE: it is necessary to accept the TCP connection, and then
             determine if the IP address can be used. If not the connection
             is closed."
        ::= { rdnPktCMSIpConfigEntry 2 }

rdnPktDQoSStatsTable OBJECT-TYPE
        SYNTAX  SEQUENCE OF RdnPktDQoSStatsEntry
        MAX-ACCESS  not-accessible
        STATUS  current
        DESCRIPTION
            "This table contains DQoS Gate statistics.
             Note: Index is equal to COPS Handle plus one."
        ::= { rdnPacketCableGroup 6 }

rdnPktDQoSStatsEntry OBJECT-TYPE
        SYNTAX  RdnPktDQoSStatsEntry
        MAX-ACCESS  not-accessible
        STATUS  current
        DESCRIPTION
            "Each entry contains DQoS Gate statistic data.
             Note: Index is equal to COPS Handle plus one."
        INDEX { rdnPktDQoSCopsHandle }
        ::= { rdnPktDQoSStatsTable 1 }

RdnPktDQoSStatsEntry ::= SEQUENCE {
           rdnPktDQoSIpAddress          IpAddress,
           rdnPktDQoSCopsHandle         Integer32,
           rdnPktDQoSCopsStatus         INTEGER,
           rdnPktDQoSCopsConnected      Integer32,
           rdnPktDQoSCopsTerminated     Integer32,
           rdnPktDQoSCopsKASent         Integer32,
           rdnPktDQoSCopsKARcvd         Integer32,
           rdnPktDQoSKATimeout          Integer32,
           rdnPktDQoST0Timeout          Integer32,
           rdnPktDQoST1Timeout          Integer32,
           rdnPktDQoSGateAllocCount     Integer32,
           rdnPktDQoSGateAllocAckCount  Integer32,
           rdnPktDQoSGateAllocErrCount  Integer32,
           rdnPktDQoSGateSetCount       Integer32,
           rdnPktDQoSGateSetAckCount    Integer32,
           rdnPktDQoSGateSetErrCount    Integer32,
           rdnPktDQoSGateDeleteCount    Integer32,
           rdnPktDQoSGateDeleteAckCount Integer32,
           rdnPktDQoSGateDeleteErrCount Integer32,
           rdnPktDQoSGateInfoCount      Integer32,
           rdnPktDQoSGateInfoAckCount   Integer32,
           rdnPktDQoSGateInfoErrCount   Integer32,
           rdnPktDQoSGateOpenRcvd       Integer32,
           rdnPktDQoSGateOpenAckSent    Integer32,
           rdnPktDQoSGateOpenErrSent    Integer32,
           rdnPktDQoSGateCloseRcvd      Integer32,
           rdnPktDQoSGateCloseAckSent   Integer32,
           rdnPktDQoSGateCloseErrSent   Integer32,
           rdnPktDQoSGateOpenSent       Integer32,
           rdnPktDQoSGateOpenAckRcvd    Integer32,
           rdnPktDQoSGateOpenErrRcvd    Integer32,
           rdnPktDQoSGateCloseSent      Integer32,
           rdnPktDQoSGateCloseAckRcvd   Integer32,
           rdnPktDQoSGateCloseErrRcvd   Integer32,
           rdnPktDQoSGateOpenRetries    Integer32,
           rdnPktDQoSGateCloseRetries   Integer32,
           rdnPktDQoSGateOpenExhausted  Integer32,
           rdnPktDQoSGateCloseExhausted Integer32,
           rdnPktDQoSCliOpenSent           Integer32,
           rdnPktDQoSCliAcceptReceived  Integer32,
           rdnPktDQoSRequestSent           Integer32,
           rdnPktDQoSCliCloseReceived   Integer32,
           rdnPktDQoSCliCloseSent          Integer32,
           rdnPktDQoSSsqReceived         Integer32,
           rdnPktDQoSSscSent                 Integer32,
           rdnPktDQoSDrqSent                 Integer32,
           rdnPktDQoST7Timeout          Integer32,
           rdnPktDQoST8Timeout          Integer32,
           rdnPktDQoSGateCmDel            Integer32,
           rdnPktDQoSGateCmDereg      Integer32,
           rdnPktDQoSGateAdminDel      Integer32,
	   rdnPktDQoSGateResReassign   Integer32
-- Future PCMM support
--           rdnPktDQoSMMGateSetCount     Integer32,
--           rdnPktDQoSMMGateSetAckCount  Integer32,
--           rdnPktDQoSMMGateSetErrCount      Integer32,
--           rdnPktDQoSMMGateDeleteCount      Integer32,
--           rdnPktDQoSMMGateDeleteAckCount       Integer32,
--           rdnPktDQoSMMGateDeleteErrCount       Integer32,
--           rdnPktDQoSMMGateInfoCount        Integer32,
--           rdnPktDQoSMMGateInfoAckCount     Integer32,
--           rdnPktDQoSMMGateInfoErrCount     Integer32,
--           rdnPktDQoSMMGateReportStateCount     Integer32,
--           rdnPktDQoSMMT1Timeout        Integer32,
--           rdnPktDQoSMMT2Timeout        Integer32,
--           rdnPktDQoSMMT3Timeout        Integer32,
--           rdnPktDQoSMMT4Timeout        Integer32,
--           rdnPktDQoSMMVolLimit             Integer32,
--          rdnPktDQoSMMCmDereg          Integer32,
--           rdnPktDQoSMMAdminDel         Integer32
        }

rdnPktDQoSIpAddress OBJECT-TYPE
        SYNTAX      IpAddress
        MAX-ACCESS  read-only
        STATUS      current
        DESCRIPTION
            "This entry contains IP address of cms - used for debugging stats"
        ::= { rdnPktDQoSStatsEntry 1 }

rdnPktDQoSCopsHandle OBJECT-TYPE
        SYNTAX      Integer32
        MAX-ACCESS  not-accessible
        STATUS      current
        DESCRIPTION
            "This entry contains cms handle id."
        ::= { rdnPktDQoSStatsEntry 2 }

rdnPktDQoSCopsStatus OBJECT-TYPE
        SYNTAX      INTEGER {
           closed(0),
           opening(1),
           open(2)
        }
        MAX-ACCESS  read-only
        STATUS      current
        DESCRIPTION
            "This entry contains cm state."
        ::= { rdnPktDQoSStatsEntry 3 }

rdnPktDQoSCopsConnected OBJECT-TYPE
        SYNTAX      Integer32
        MAX-ACCESS  read-only
        STATUS      current
        DESCRIPTION
            "This entry contains statistics of CMS connections."
        ::= { rdnPktDQoSStatsEntry 4 }

rdnPktDQoSCopsTerminated OBJECT-TYPE
        SYNTAX      Integer32
        MAX-ACCESS  read-only
        STATUS      current
        DESCRIPTION
            "This entry contains statistics of the statistics of the CMS-CMTS
             session close."
        ::= { rdnPktDQoSStatsEntry 5 }

rdnPktDQoSCopsKASent OBJECT-TYPE
        SYNTAX      Integer32
        MAX-ACCESS  read-only
        STATUS      current
        DESCRIPTION
            "This entry contains the statistics of KA sending to the CMS."
        ::= { rdnPktDQoSStatsEntry 6 }

rdnPktDQoSCopsKARcvd OBJECT-TYPE
        SYNTAX      Integer32
        MAX-ACCESS  read-only
        STATUS      current
        DESCRIPTION
            "This entry contains the statistics of KA received ."
        ::= { rdnPktDQoSStatsEntry 7 }

rdnPktDQoSKATimeout OBJECT-TYPE
        SYNTAX      Integer32
        MAX-ACCESS  read-only
        STATUS      current
        DESCRIPTION
            "This entry contains the statistics of the expiration of the KA
             timer."
        ::= { rdnPktDQoSStatsEntry 8 }

rdnPktDQoST0Timeout OBJECT-TYPE
        SYNTAX      Integer32
        MAX-ACCESS  read-only
        STATUS      current
        DESCRIPTION
            "This entry contains the statistics of the expiration of T0 timer."
        ::= { rdnPktDQoSStatsEntry 9 }

rdnPktDQoST1Timeout OBJECT-TYPE
        SYNTAX      Integer32
        MAX-ACCESS  read-only
        STATUS      current
        DESCRIPTION
            "This entry contains the statistics of the expiration of T1 timer."
        ::= { rdnPktDQoSStatsEntry 10 }

rdnPktDQoSGateAllocCount OBJECT-TYPE
        SYNTAX      Integer32
        MAX-ACCESS  read-only
        STATUS      current
        DESCRIPTION
            "This entry contains the statistics of DGM_CCM_GATE_ALLOC_CMD
             message received."
        ::= { rdnPktDQoSStatsEntry 11 }

rdnPktDQoSGateAllocAckCount OBJECT-TYPE
        SYNTAX      Integer32
        MAX-ACCESS  read-only
        STATUS      current
        DESCRIPTION
            "This entry contains the statistics of DGM_CCM_GATE_ALLOC_ACK_CMD
             message sent."
        ::= { rdnPktDQoSStatsEntry 12 }

rdnPktDQoSGateAllocErrCount OBJECT-TYPE
        SYNTAX      Integer32
        MAX-ACCESS  read-only
        STATUS      current
        DESCRIPTION
            "This entry contains the statistics of gate allocation error
             message sent."
        ::= { rdnPktDQoSStatsEntry 13 }

rdnPktDQoSGateSetCount OBJECT-TYPE
        SYNTAX      Integer32
        MAX-ACCESS  read-only
        STATUS      current
        DESCRIPTION
            "This entry contains the statistics of DGM_CCM_GATE_SET_CMD
             message received."
        ::= { rdnPktDQoSStatsEntry 14 }

rdnPktDQoSGateSetAckCount OBJECT-TYPE
        SYNTAX      Integer32
        MAX-ACCESS  read-only
        STATUS      current
        DESCRIPTION
            "This entry contains the statistics of DGM_CCM_GATE_SET_ACK_CMD
             message sent."
        ::= { rdnPktDQoSStatsEntry 15 }

rdnPktDQoSGateSetErrCount OBJECT-TYPE
        SYNTAX      Integer32
        MAX-ACCESS  read-only
        STATUS      current
        DESCRIPTION
            "This entry contains the statistics of gate set error message
             sent."
        ::= { rdnPktDQoSStatsEntry 16 }

rdnPktDQoSGateDeleteCount OBJECT-TYPE
        SYNTAX      Integer32
        MAX-ACCESS  read-only
        STATUS      current
        DESCRIPTION
            "This entry contains the statistics of DGM_CCM_GATE_DELETE_CMD
             message received."
        ::= { rdnPktDQoSStatsEntry 17 }

rdnPktDQoSGateDeleteAckCount OBJECT-TYPE
        SYNTAX      Integer32
        MAX-ACCESS  read-only
        STATUS      current
        DESCRIPTION
            "This entry contains the statistics of DGM_CCM_GATE_DELETE_ACK_CMD
             message sent."
        ::= { rdnPktDQoSStatsEntry 18 }

rdnPktDQoSGateDeleteErrCount OBJECT-TYPE
        SYNTAX      Integer32
        MAX-ACCESS  read-only
        STATUS      current
        DESCRIPTION
            "This entry contains the statistics of gate delete error message
             sent."
        ::= { rdnPktDQoSStatsEntry 19 }

rdnPktDQoSGateInfoCount OBJECT-TYPE
        SYNTAX      Integer32
        MAX-ACCESS  read-only
        STATUS      current
        DESCRIPTION
            "This entry contains the statistics of DGM_CCM_GATE_INFO_CMD
             message received."
        ::= { rdnPktDQoSStatsEntry 20 }

rdnPktDQoSGateInfoAckCount OBJECT-TYPE
        SYNTAX      Integer32
        MAX-ACCESS  read-only
        STATUS      current
        DESCRIPTION
            "This entry contains the statistics of DGM_CCM_GATE_INFO_ACK_CMD
             message sent."
        ::= { rdnPktDQoSStatsEntry 21 }

rdnPktDQoSGateInfoErrCount OBJECT-TYPE
        SYNTAX      Integer32
        MAX-ACCESS  read-only
        STATUS      current
        DESCRIPTION
            "This entry contains the statistics of gate info error message
             sent."
        ::= { rdnPktDQoSStatsEntry 22 }

rdnPktDQoSGateOpenRcvd OBJECT-TYPE
        SYNTAX      Integer32
        MAX-ACCESS  read-only
        STATUS      obsolete
        DESCRIPTION
            "This entry contains the statistics of DGM_GSM_GATE_OPEN_MSG_TYPE
             message received."
        ::= { rdnPktDQoSStatsEntry 23 }

rdnPktDQoSGateOpenAckSent  OBJECT-TYPE
        SYNTAX      Integer32
        MAX-ACCESS  read-only
        STATUS      obsolete
        DESCRIPTION
            "This entry contains the statistics of DGM_GSM_GATE_OPEN_ACK_MSG
             message sent."
        ::= { rdnPktDQoSStatsEntry 24 }

rdnPktDQoSGateOpenErrSent OBJECT-TYPE
        SYNTAX      Integer32
        MAX-ACCESS  read-only
        STATUS      obsolete
        DESCRIPTION
            "This entry contains the statistics of gate open error message
             message sent."
        ::= { rdnPktDQoSStatsEntry 25 }

rdnPktDQoSGateCloseRcvd OBJECT-TYPE
        SYNTAX      Integer32
        MAX-ACCESS  read-only
        STATUS      obsolete
        DESCRIPTION
            "This entry contains the statistics of DGM_GSM_GATE_CLOSE_MSG
             received."
        ::= { rdnPktDQoSStatsEntry 26 }

rdnPktDQoSGateCloseAckSent OBJECT-TYPE
        SYNTAX      Integer32
        MAX-ACCESS  read-only
        STATUS      obsolete
        DESCRIPTION
            "This entry contains the statistics of DGM_GSM_GATE_CLOSE_ACK_MSG
             sent."
        ::= { rdnPktDQoSStatsEntry 27 }

rdnPktDQoSGateCloseErrSent  OBJECT-TYPE
        SYNTAX      Integer32
        MAX-ACCESS  read-only
        STATUS      obsolete
        DESCRIPTION
            "This entry contains the statistics of Gate Close Error message
             sent."
        ::= { rdnPktDQoSStatsEntry 28 }

rdnPktDQoSGateOpenSent OBJECT-TYPE
        SYNTAX      Integer32
        MAX-ACCESS  read-only
        STATUS      current
        DESCRIPTION
            "This entry contains the statistics of DGM_GSM_GATE_OPEN_MSG sent."
        ::= { rdnPktDQoSStatsEntry 29 }

rdnPktDQoSGateOpenAckRcvd OBJECT-TYPE
        SYNTAX      Integer32
        MAX-ACCESS  read-only
        STATUS      obsolete
        DESCRIPTION
            "This entry contains the statistics of DGM_GSM_GATE_OPEN_ACK_MSG
             received."
        ::= { rdnPktDQoSStatsEntry 30 }

rdnPktDQoSGateOpenErrRcvd OBJECT-TYPE
        SYNTAX      Integer32
        MAX-ACCESS  read-only
        STATUS      obsolete
        DESCRIPTION
            "This entry contains the statistics of Gate Open Error message
             received."
        ::= { rdnPktDQoSStatsEntry 31 }

rdnPktDQoSGateCloseSent OBJECT-TYPE
        SYNTAX      Integer32
        MAX-ACCESS  read-only
        STATUS      current
        DESCRIPTION
            "This entry contains the statistics of DGM_GSM_GATE_CLOSE_MSG
             sent."
        ::= { rdnPktDQoSStatsEntry 32 }

rdnPktDQoSGateCloseAckRcvd OBJECT-TYPE
        SYNTAX      Integer32
        MAX-ACCESS  read-only
        STATUS      obsolete
        DESCRIPTION
            "This entry contains the statistics of DGM_GSM_GATE_CLOSE_ACK_MSG
             received."
        ::= { rdnPktDQoSStatsEntry 33 }

rdnPktDQoSGateCloseErrRcvd OBJECT-TYPE
        SYNTAX      Integer32
        MAX-ACCESS  read-only
        STATUS      obsolete
        DESCRIPTION
            "This entry contains the statistics of Gate Close Error message
             received."
        ::= { rdnPktDQoSStatsEntry 34 }

rdnPktDQoSGateOpenRetries OBJECT-TYPE
        SYNTAX      Integer32
        MAX-ACCESS  read-only
        STATUS      obsolete
        DESCRIPTION
            "This entry contains the statistics of DGM_GSM_GATE_OPEN_MSG_TYPE
             sent when T5 expires."
        ::= { rdnPktDQoSStatsEntry 35 }

rdnPktDQoSGateCloseRetries OBJECT-TYPE
        SYNTAX      Integer32
        MAX-ACCESS  read-only
        STATUS      obsolete
        DESCRIPTION
            "This entry contains the statistics of DGM_GSM_GATE_CLOSE_MSG sent
             when T5 expires. "
        ::= { rdnPktDQoSStatsEntry 36 }

rdnPktDQoSGateOpenExhausted OBJECT-TYPE
        SYNTAX      Integer32
        MAX-ACCESS  read-only
        STATUS      obsolete
        DESCRIPTION
            "This entry contains the statistics of gate message retry exhausted
             with DGM_GSM_GATE_OPEN_MSG_TYPE."
        ::= { rdnPktDQoSStatsEntry 37 }

rdnPktDQoSGateCloseExhausted OBJECT-TYPE
        SYNTAX      Integer32
        MAX-ACCESS  read-only
        STATUS      obsolete
        DESCRIPTION
            "This entry contains the statistics of gate message retry exhausted
             with DGM_GSM_GATE_CLOSE_MSG. "
        ::= { rdnPktDQoSStatsEntry 38 }

rdnPktDQoSCliOpenSent OBJECT-TYPE
        SYNTAX      Integer32
        MAX-ACCESS  read-only
        STATUS      current
        DESCRIPTION
            "This entry contains the statistic for Client Opens sent."
        ::= { rdnPktDQoSStatsEntry 39 }

rdnPktDQoSCliAcceptReceived OBJECT-TYPE
        SYNTAX      Integer32
        MAX-ACCESS  read-only
        STATUS      current
        DESCRIPTION
            "This entry contains the statistic for Client Accepts received."
        ::= { rdnPktDQoSStatsEntry 40 }

rdnPktDQoSRequestSent OBJECT-TYPE
        SYNTAX      Integer32
        MAX-ACCESS  read-only
        STATUS      current
        DESCRIPTION
            "This entry contains the statistic for Requests sent."
        ::= { rdnPktDQoSStatsEntry 41 }

rdnPktDQoSCliCloseReceived OBJECT-TYPE
        SYNTAX      Integer32
        MAX-ACCESS  read-only
        STATUS      current
        DESCRIPTION
            "This entry contains the statistic for Client Close received."
        ::= { rdnPktDQoSStatsEntry 42 }

rdnPktDQoSCliCloseSent OBJECT-TYPE
        SYNTAX      Integer32
        MAX-ACCESS  read-only
        STATUS      current
        DESCRIPTION
            "This entry contains the statistic for Client Close sent."
        ::= { rdnPktDQoSStatsEntry 43 }

rdnPktDQoSSsqReceived OBJECT-TYPE
        SYNTAX      Integer32
        MAX-ACCESS  read-only
        STATUS      current
        DESCRIPTION
            "This entry contains the statistic for SSQs received."
        ::= { rdnPktDQoSStatsEntry 44 }

rdnPktDQoSSscSent OBJECT-TYPE
        SYNTAX      Integer32
        MAX-ACCESS  read-only
        STATUS      current
        DESCRIPTION
            "This entry contains the statistic for SSCs sent."
        ::= { rdnPktDQoSStatsEntry 45 }

rdnPktDQoSDrqSent OBJECT-TYPE
        SYNTAX      Integer32
        MAX-ACCESS  read-only
        STATUS      current
        DESCRIPTION
            "This entry contains the statistic for DRQs sent."
        ::= { rdnPktDQoSStatsEntry 46 }

rdnPktDQoST7Timeout OBJECT-TYPE
        SYNTAX      Integer32
        MAX-ACCESS  read-only
        STATUS      current
        DESCRIPTION
            "This entry contains the statistics of the expiration of T7 timer."
        ::= { rdnPktDQoSStatsEntry 47 }

rdnPktDQoST8Timeout OBJECT-TYPE
        SYNTAX      Integer32
        MAX-ACCESS  read-only
        STATUS      current
        DESCRIPTION
            "This entry contains the statistics of the expiration of T8 timer."
        ::= { rdnPktDQoSStatsEntry 48 }

rdnPktDQoSGateCmDel OBJECT-TYPE
        SYNTAX      Integer32
        MAX-ACCESS  read-only
        STATUS      current
        DESCRIPTION
            "This entry contains the statistic for Gate CM deleted."
        ::= { rdnPktDQoSStatsEntry 49 }

rdnPktDQoSGateCmDereg OBJECT-TYPE
        SYNTAX      Integer32
        MAX-ACCESS  read-only
        STATUS      current
        DESCRIPTION
            "This entry contains the statistic Gate CM de-registered."
        ::= { rdnPktDQoSStatsEntry 50 }

rdnPktDQoSGateAdminDel OBJECT-TYPE
        SYNTAX      Integer32
        MAX-ACCESS  read-only
        STATUS      current
        DESCRIPTION
            "This entry contains the statistic for Gate Administrator Delete."
        ::= { rdnPktDQoSStatsEntry 51 }

rdnPktDQoSGateResReassign OBJECT-TYPE
        SYNTAX      Integer32
        MAX-ACCESS  read-only
        STATUS      current
        DESCRIPTION
            "This entry contains the statistic for Gate Reservation Reassignment."
        ::= { rdnPktDQoSStatsEntry 52 }

--rdnPktDQoSMMGateSetCount OBJECT-TYPE
--        SYNTAX      Integer32
--        MAX-ACCESS  read-only
--        STATUS      current
--        DESCRIPTION
--            "This entry contains the statistic for PCMM Gate Set count."
--        ::= { rdnPktDQoSStatsEntry 52 }

--rdnPktDQoSMMGateSetAckCount OBJECT-TYPE
--        SYNTAX      Integer32
--        MAX-ACCESS  read-only
--        STATUS      current
--        DESCRIPTION
--            "This entry contains the statistic for PCMM Gate Set ACK count."
--        ::= { rdnPktDQoSStatsEntry 53 }

--rdnPktDQoSMMGateSetErrCount OBJECT-TYPE
--        SYNTAX      Integer32
--        MAX-ACCESS  read-only
--        STATUS      current
--        DESCRIPTION
--            "This entry contains the statistic for PCMM Gate Set Error count."
--        ::= { rdnPktDQoSStatsEntry 54 }

--rdnPktDQoSMMGateDeleteCount OBJECT-TYPE
--        SYNTAX      Integer32
--        MAX-ACCESS  read-only
--        STATUS      current
--        DESCRIPTION
--            "This entry contains the statistic for PCMM Gate Delete count."
--        ::= { rdnPktDQoSStatsEntry 55 }

--rdnPktDQoSMMGateDeleteAckCount OBJECT-TYPE
--        SYNTAX      Integer32
--        MAX-ACCESS  read-only
--        STATUS      current
--        DESCRIPTION
--            "This entry contains the statistic for PCMM Gate Delete ACK count."
--        ::= { rdnPktDQoSStatsEntry 56 }

--rdnPktDQoSMMGateDeleteErrCount OBJECT-TYPE
--        SYNTAX      Integer32
--        MAX-ACCESS  read-only
--        STATUS      current
--        DESCRIPTION
--            "This entry contains the statistic for PCMM Gate Delete Error count."
--        ::= { rdnPktDQoSStatsEntry 57 }

--rdnPktDQoSMMGateInfoCount OBJECT-TYPE
--        SYNTAX      Integer32
--        MAX-ACCESS  read-only
--        STATUS      current
--        DESCRIPTION
--            "This entry contains the statistic for PCMM Gate Info count."
--        ::= { rdnPktDQoSStatsEntry 58 }

--rdnPktDQoSMMGateInfoAckCount OBJECT-TYPE
--        SYNTAX      Integer32
--        MAX-ACCESS  read-only
--        STATUS      current
--        DESCRIPTION
--            "This entry contains the statistic for PCMM Gate Info ACK count."
--        ::= { rdnPktDQoSStatsEntry 59 }

--rdnPktDQoSMMGateInfoErrCount OBJECT-TYPE
--        SYNTAX      Integer32
--        MAX-ACCESS  read-only
--        STATUS      current
--        DESCRIPTION
--            "This entry contains the statistic for PCMM Gate Info Error count."
--        ::= { rdnPktDQoSStatsEntry 60 }

--rdnPktDQoSMMGateReportStateCount OBJECT-TYPE
--        SYNTAX      Integer32
--        MAX-ACCESS  read-only
--        STATUS      current
--        DESCRIPTION
--            "This entry contains the statistic for PCMM Gate Report State count."
--        ::= { rdnPktDQoSStatsEntry 61 }

--rdnPktDQoSMMT1Timeout OBJECT-TYPE
--        SYNTAX      Integer32
--        MAX-ACCESS  read-only
--        STATUS      current
--        DESCRIPTION
--            "This entry contains the statistic for PCMM T1 timeout."
--        ::= { rdnPktDQoSStatsEntry 62 }

--rdnPktDQoSMMT2Timeout OBJECT-TYPE
--        SYNTAX      Integer32
--        MAX-ACCESS  read-only
--        STATUS      current
--        DESCRIPTION
--            "This entry contains the statistic for PCMM T2 timeout."
--        ::= { rdnPktDQoSStatsEntry 63 }

--rdnPktDQoSMMT3Timeout OBJECT-TYPE
--        SYNTAX      Integer32
--        MAX-ACCESS  read-only
--        STATUS      current
--        DESCRIPTION
--            "This entry contains the statistic for PCMM T3 timeout."
--        ::= { rdnPktDQoSStatsEntry 64 }

--rdnPktDQoSMMT4Timeout OBJECT-TYPE
--        SYNTAX      Integer32
--        MAX-ACCESS  read-only
--        STATUS      current
--        DESCRIPTION
--            "This entry contains the statistic for PCMM T4 timeout."
--        ::= { rdnPktDQoSStatsEntry 65 }

--rdnPktDQoSMMVolLimit OBJECT-TYPE
--        SYNTAX      Integer32
--        MAX-ACCESS  read-only
--        STATUS      current
--        DESCRIPTION
--            "This entry contains the statistic for PCMM Volume Limit reached."
--        ::= { rdnPktDQoSStatsEntry 66 }

--rdnPktDQoSMMCmDereg OBJECT-TYPE
--        SYNTAX      Integer32
--        MAX-ACCESS  read-only
--        STATUS      current
--        DESCRIPTION
--            "This entry contains the statistic for PCMM CM deregisters."
--        ::= { rdnPktDQoSStatsEntry 67 }

--rdnPktDQoSMMAdminDel OBJECT-TYPE
--        SYNTAX      Integer32
--        MAX-ACCESS  read-only
--        STATUS      current
--        DESCRIPTION
--            "This entry contains the statistic for PCMM Administrator delete."
--        ::= { rdnPktDQoSStatsEntry 68 }

-- traps

rdnPktDQoSNotificationObject OBJECT IDENTIFIER ::= { rdnPacketCableGroup 7 }

rdnPktDQoSCopsReason OBJECT-TYPE
        SYNTAX      INTEGER {
           copsConnectionEstablished(1),
           cantEstablishCopsConnection(2),
           unauthorizedCms(3),
           copsConnectionClosed(4),
           copsConnectionDisconnected(5),
           keepAliveFailure(6)
        }
        MAX-ACCESS accessible-for-notify
        STATUS      current
        DESCRIPTION
            "This entry contains the rdnPktDQoSCopsTrap reason code
             1 = The CMTS COPS connection to the CMS/GC is established.
             specified in the rdnPktDQoSCopsCmsIpAddr field.
             2 = Can't establish the COPS connection with the IP address
             specified in the rdnPktDQoSCopsCmsIpAddr field.
             3 = The CMS attempting to make the COPS connection is not
             authorized to make the connection. The IP address is
             specified in the rdnPktDQoSCopsCmsIpAddr field.
             4 = The CMTS COPS connection to the CMS/GC is closed. The
             CMTS has received a ClientClose from the CMS/GC. The IP
             address of the CMS/GC is specified in the
             rdnPktDQoSCopsCmsIpAddr field.
             5 = The CMTS COPS connection to the CMS/GC is disconnected.
             The connection was administratively closed via a command
             from the console of the CMTS. The IP address of the CMS/GC
             is specified in the rdnPktDQoSCopsCmsIpAddr field.
             6 = The CMTS has not received a Keep-Alive message from
             the CMS/GC within the specified KA timer interval.
             The IP address of the CMS/GC is specified in the
             rdnPktDQoSCopsCmsIpAddr field."
        ::= { rdnPktDQoSNotificationObject 1 }

rdnPktDQoSCopsCmsIpAddr OBJECT-TYPE
        SYNTAX      IpAddress
        MAX-ACCESS accessible-for-notify
        STATUS      current
        DESCRIPTION
            "This entry contains the IP address of the CMS/GC associated with
             the reason code for the rdnPktDQoSCopsTrap."
        ::= { rdnPktDQoSNotificationObject 2 }

rdnPktDQoSCopsCmsPortNum OBJECT-TYPE
        SYNTAX      Integer32
        MAX-ACCESS accessible-for-notify
        STATUS      current
        DESCRIPTION
            "This entry contains the TCP port number that the CMS/GC
             is connected on. This is additional information associated
             with the reason code for the rdnPktDQoSCopsTrap."
        ::= { rdnPktDQoSNotificationObject 3 }

rdnPktDQoSCopsCmsHandleId OBJECT-TYPE
        SYNTAX      Integer32
        MAX-ACCESS accessible-for-notify
        STATUS      current
        DESCRIPTION
            "This entry contains the COPS handle ID associated with the
             connection to the CMS/GC. This is additional information
             associated with the reason code for the rdnPktDQoSCopsTrap."
        ::= { rdnPktDQoSNotificationObject 4 }


rdnPktDQoSResReqReason OBJECT-TYPE
           SYNTAX      INTEGER {
           dsaReqResourceGreaterThanAuth(1),
           dsaResReqWithoutGateId(2),
           dsaResReqWithInvalidGateId(3),
           dscReqResourceGreaterThanAuth(4),
           dscResReqWithoutGateId(5),
           dscResReqWithInvalidGateId(6)
        }
        MAX-ACCESS accessible-for-notify
        STATUS      current
        DESCRIPTION
            "This entry contains the rdnPktDQoSResReqTrap reason code
             1 = The MTA DSA-REQ has requested more resource than it has been
             authorized. The MTA is identified by the CM's Mac address
             as specified in the rdnPktDQoSResReqCmMacAddr field.
             2 = The MTA DSA-REQ is requesting resource with an unknown
             Gate ID.
             3 = The MTA DSA-REA is requesting resource without including
             a Gate ID.
             4 = The MTA DSC-REQ has requested more resource than it has been
             authorized. The MTA is identified by the CM's Mac address
             as specified in the rdnPktDQoSResReqCmMacAddr field.
             5 = The MTA DSC-REQ is requesting resource with an unknown
             Gate ID.
             6 = The MTA DSC-REA is requesting resource without including
             a Gate ID."
        ::= { rdnPktDQoSNotificationObject 5 }

rdnPktDQoSCmMacAddr OBJECT-TYPE
        SYNTAX      MacAddress
        MAX-ACCESS accessible-for-notify
        STATUS      current
        DESCRIPTION
            "This entry contains the CM's Mac address for the MTA it
             is associated with. The reason code and this Mac address
             provide the detailed information for the rdnPktDQoSResReqTrap."
        ::= { rdnPktDQoSNotificationObject 6 }

rdnPktDQoSEmergencyReason OBJECT-TYPE
           SYNTAX      INTEGER {
           emergencyCallBeingRejected(1)
        }
        MAX-ACCESS accessible-for-notify
        STATUS      current
        DESCRIPTION
            "This entry contains the rdnPktDQoSEmergencyTrap reason code
             1 = Emergency Call is rejected due to insufficient bandwidth."
        ::= { rdnPktDQoSNotificationObject 7 }

rdnPktDQoSClassName OBJECT-TYPE
        SYNTAX      DisplayString (SIZE (0..32))
        MAX-ACCESS  accessible-for-notify
        STATUS      current
        DESCRIPTION
            "An ASCII string to identify the Class Name"
        ::= { rdnPktDQoSNotificationObject 8 }

rdnPktDQoSGateId OBJECT-TYPE
        SYNTAX      Integer32
        MAX-ACCESS  accessible-for-notify
        STATUS      current
        DESCRIPTION
            "This attribute is the identifier for allocated gate.
             Refer to rdnGateId."
        ::= { rdnPktDQoSNotificationObject 9 }

rdnPktDQoSEmergencyPreemptReason OBJECT-TYPE
           SYNTAX      INTEGER {
           emergencyPreemptedMostRecentCall(1),
           emergencyPreemptedOldestCall(2),
           emergencyPreemptedRandomCall(3)
        }
        MAX-ACCESS accessible-for-notify
        STATUS      current
        DESCRIPTION
            "This entry contains the rdnPktDQoSEmergencyPreempTrap reason code
             1 = Emergency call preempted the most recent DQoS call.
             2 = Emergency call preempted the oldest DQoS call.
             3 = Emergency call preempted a random DQoS call."
        ::= { rdnPktDQoSNotificationObject 10 }

--
-- DQoS Notification Group
--
rdnPktDQoSNotificationTraps OBJECT IDENTIFIER ::= {rdnPacketCableGroup 8 }
rdnPktDQoSNotificationTrapsPrefix OBJECT IDENTIFIER ::= {rdnPktDQoSNotificationTraps 0 }

rdnPktDQoSCopsTrap NOTIFICATION-TYPE
    OBJECTS  { rdnPktDQoSCopsReason,
               rdnPktDQoSCopsCmsIpAddr }
    STATUS   current
    DESCRIPTION
             "A PacketCable COPS connection status change to the CMS/GC has
              occurred. The reason code and CMS/GC IP address provide
              the detailed information regarding this trap."
    ::= { rdnPktDQoSNotificationTrapsPrefix 1 }


rdnPktDQoSResReqTrap NOTIFICATION-TYPE
    OBJECTS  { rdnPktDQoSResReqReason,
               rdnPktDQoSCmMacAddr}
    STATUS   current
    DESCRIPTION
             "A PacketCable MTA resource request problem has occurred
              (e.g., a problem while processing the DSA-REQ or DSC-REQ
              was detected). The reason code, the Gate ID, and the CM
              Mac address, provide detailed information regarding
              this trap."
    ::= { rdnPktDQoSNotificationTrapsPrefix 2 }

rdnPktDQoSEmergencyTrap NOTIFICATION-TYPE
    OBJECTS  { rdnPktDQoSEmergencyReason,
               rdnPktDQoSCmMacAddr,
               rdnPktDQoSClassName,
               rdnPktDQoSGateId}
    STATUS   current
    DESCRIPTION
             "A PacketCable Emergency call is rejected.
              The reason code, and the CM Mac address, the gate direction,
              the Channel ID, and the Gate Id provide detailed information
              regarding this trap."
    ::= { rdnPktDQoSNotificationTrapsPrefix 3 }

rdnPktDQoSEmergencyPreemptTrap NOTIFICATION-TYPE
    OBJECTS  { rdnPktDQoSEmergencyPreemptReason,
               rdnPktDQoSCmMacAddr,
               rdnPktDQoSClassName,
               rdnPktDQoSGateId}
    STATUS   current
    DESCRIPTION
             "A PacketCable Emergency call is preempted successfully.
              The reason code, and the CM Mac address, the Service Class
              Name and the Gate Id provide detailed information regarding
              this trap."
    ::= { rdnPktDQoSNotificationTrapsPrefix 4 }

rdnPktESNotificationObject OBJECT IDENTIFIER ::= { rdnPacketCableGroup 9 }

rdnPktESReason OBJECT-TYPE
        SYNTAX      INTEGER {
           cdcFailure(1)
        }
        MAX-ACCESS accessible-for-notify
        STATUS      current
        DESCRIPTION
            "This entry contains the rdnPktESTrap reason code
             1 = Their was no reply from the DF when attempting to send
             Duplicated Event messages."
        ::= { rdnPktESNotificationObject 1 }

rdnPktESDFIpAddr OBJECT-TYPE
        SYNTAX      IpAddress
        MAX-ACCESS accessible-for-notify
        STATUS      current
        DESCRIPTION
            "This entry contains the IP address of the DF associated with
             the reason code for the rdnPktESTrap."
        ::= { rdnPktESNotificationObject 2 }

rdnPktESDFPortNum OBJECT-TYPE
        SYNTAX      Integer32
        MAX-ACCESS accessible-for-notify
        STATUS      current
        DESCRIPTION
            "This entry contains the port number that the DF
             is connected on. This is additional information associated
             with the reason code for the rdnPktESTrap."
        ::= { rdnPktESNotificationObject 3 }

--
-- ES Notification Group
--
rdnPktESNotificationTraps OBJECT IDENTIFIER ::= {rdnPacketCableGroup 10 }
rdnPktESNotificationTrapsPrefix OBJECT IDENTIFIER ::= {rdnPktESNotificationTraps 0 }

rdnPktESTrap NOTIFICATION-TYPE
    OBJECTS  { rdnPktESReason,
               rdnPktESDFIpAddr,
               rdnPktESDFPortNum}
    STATUS   current
    DESCRIPTION
             "A PacketCable ES failure has occurred.
              The reason code, DF IP address and port provide
              the detailed information regarding this trap."
    ::= { rdnPktESNotificationTrapsPrefix 1 }


rdnPktRKSNotificationObject OBJECT IDENTIFIER ::= { rdnPacketCableGroup 11 }

rdnPktRKSReason OBJECT-TYPE
           SYNTAX      INTEGER {
           retriesExhausted(1)
        }
        MAX-ACCESS accessible-for-notify
        STATUS      current
        DESCRIPTION
            "This entry contains the rdnPktRKSTrap reason code
             1 = RKS communications failure. Primary and secondary RKS retries exhausted."
        ::= { rdnPktRKSNotificationObject 1 }

rdnPktRKSTransID OBJECT-TYPE
        SYNTAX      Integer32
        MAX-ACCESS accessible-for-notify
        STATUS      current
        DESCRIPTION
            "This entry contains the event message Transaction ID.
             This is additional information associated with the reason code for
             the rdnPktRKSTrap."
        ::= { rdnPktRKSNotificationObject 2 }

rdnPktRKSIPPrimary OBJECT-TYPE
        SYNTAX      IpAddress
        MAX-ACCESS accessible-for-notify
        STATUS      current
        DESCRIPTION
            "This entry contains the IP address of the primary RKS.
             This is additional information associated with the reason code
             for the rdnPktRKSTrap."
        ::= { rdnPktRKSNotificationObject 3 }

rdnPktRKSPortPrimary OBJECT-TYPE
        SYNTAX      Integer32
        MAX-ACCESS accessible-for-notify
        STATUS      current
        DESCRIPTION
            "This entry contains the TCP port number of the primary RKS.
             This is additional information associated with the reason code
             for the rdnPktRKSTrap."
        ::= { rdnPktRKSNotificationObject 4 }

rdnPktRKSIPSecondary OBJECT-TYPE
        SYNTAX      IpAddress
        MAX-ACCESS accessible-for-notify
        STATUS      current
        DESCRIPTION
            "This entry contains the IP address of the secondary RKS.
             This is additional information associated with the reason code
             for the rdnPktRKSTrap."
        ::= { rdnPktRKSNotificationObject 5 }

rdnPktRKSPortSecondary OBJECT-TYPE
        SYNTAX      Integer32
        MAX-ACCESS accessible-for-notify
        STATUS      current
        DESCRIPTION
            "This entry contains the TCP port number of the secondary RKS.
             This is additional information associated with the reason code
             for the rdnPktRKSTrap."
        ::= { rdnPktRKSNotificationObject 6 }

rdnPktRKSVersionID OBJECT-TYPE
           SYNTAX      INTEGER {
           packetCable10(1),
           packetCable11(2),
           packetCableMultiMedia(3)
        }
        MAX-ACCESS accessible-for-notify
        STATUS      current
        DESCRIPTION
            "This entry contains the version ID of the RKS associated with the rdnPktRKSTrap.
             1 = Packet Cable 1.0
             2 = Packet Cable 1.1
             3 = Packet Cable MultiMedia"
        ::= { rdnPktRKSNotificationObject 7 }

--
-- RKS Notification Group
--
rdnPktRKSNotificationTraps OBJECT IDENTIFIER ::= {rdnPacketCableGroup 12 }
rdnPktRKSNotificationTrapsPrefix OBJECT IDENTIFIER ::= {rdnPktRKSNotificationTraps 0 }

rdnPktDQoSRKSTrap NOTIFICATION-TYPE
    OBJECTS  { rdnPktRKSReason,
               rdnPktRKSTransID,
               rdnPktRKSIPPrimary,
               rdnPktRKSPortPrimary,
               rdnPktRKSIPSecondary,
               rdnPktRKSPortSecondary,
               rdnPktRKSVersionID}
    STATUS   current
    DESCRIPTION
             "There has been a communication failure to both the primary
              and secondary Record Keeping Servers.
              The reason code, the ID of the failed Transaction, primary
              and secondary RKS IP address and port number, and the RKS
              version type is provided."
    ::= { rdnPktRKSNotificationTrapsPrefix 1}

END
