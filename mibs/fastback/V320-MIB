V320-MIB DEFINITIONS ::= BEGIN

-- *****************************************************************
-- Title:    Sub10 Systems - MIB
-- Version:  1.00
-- Date:     29/11/2011
-- Comments: This MIB is based on various MIB files
--           (RFC 3418, SNMPv2, Ethernet-like Interface, ...)
-- *****************************************************************


-- *****************************************************************
-- *      Sub10 Systems
-- *****************************************************************


IMPORTS
    MODULE-IDENTITY, OBJECT-TYPE, NOTIFICATION-TYPE,
    Integer32, mib-2, Counter32, enterprises FROM SNMPv2-SMI
    DisplayString FROM SNMPv2-TC
    NOTIFICATION-GROUP, OBJECT-GROUP FROM SNMPv2-CONF;

sub10OID MODULE-IDENTITY
    LAST-UPDATED "201111290000Z"
    ORGANIZATION "Sub10 Systems Ltd"
    CONTACT-INFO "support@sub10systems.com"
    DESCRIPTION "Sub10 MIB"
    REVISION "201111290000Z"
    DESCRIPTION "Initial Revision"
    ::= { enterprises 39003 }

-- Object IDs group
--
terminal2 OBJECT IDENTIFIER ::= { sub10OID 2 }

terminalLinkQuality OBJECT-TYPE
    SYNTAX INTEGER {
        green (1),
        yellow (2),
        red (3),
        unknown(10)
    }
    MAX-ACCESS read-only
    STATUS current
    DESCRIPTION
        "A measure for quality of the microwave link.
        Green: good signal level to withstand heavy rain
        Yellow: sufficient signal level but no margin
        Red: insufficient signal level, link not available
        Unknown: no signal level data available"
    ::= { terminal2 1 }


terminalReceivePower OBJECT-TYPE
    SYNTAX      Integer32
    MAX-ACCESS  read-only
    STATUS      current
    DESCRIPTION "Receive signal level in dBm"
    ::= { terminal2 10 }

terminalTemperature OBJECT-TYPE
    SYNTAX      Integer32
    MAX-ACCESS  read-only
    STATUS      current
    DESCRIPTION "Temperature within the unit in degree Celsius"
    ::= { terminal2 11 }

terminalLockDetector OBJECT-TYPE
    SYNTAX      Integer32
    MAX-ACCESS  read-only
    STATUS      current
    DESCRIPTION "Lock detection signal level"
    ::= { terminal2 12 }

terminalLinkQualityImproved OBJECT-TYPE
    SYNTAX INTEGER{
        red2green (1),
        red2yellow (2),
        yellow2green (3)
    }
    MAX-ACCESS read-only
    STATUS     current
    DESCRIPTION
        "Indicates a positive change of the received microwave signal
        and the quality change from red to green or from red to yellow."
    ::= { terminal2 13 }

terminalLinkQualityReduced OBJECT-TYPE
    SYNTAX INTEGER{
        green2yellow (1),
        green2red (2),
        yellow2red (3)
    }
    MAX-ACCESS read-only
    STATUS     current
    DESCRIPTION
        "Indicates a negative change of the received microwave signal
        and the quality change from red to green or from red to yellow."
    ::= { terminal2 14 }

terminalFirmwareversion OBJECT-TYPE
    SYNTAX OCTET STRING
    MAX-ACCESS read-only
    STATUS current
    DESCRIPTION
        "Installed Firmware Version."
    ::= { terminal2 21 }

terminalAuxVoltage OBJECT-TYPE
    SYNTAX OCTET STRING
    MAX-ACCESS read-only
    STATUS current
    DESCRIPTION
        "Actual Voltage at Auxilary Port"
    ::= { terminal2 25 }

terminalObjectGroup OBJECT-GROUP
    OBJECTS {
        terminalLinkQualityReduced,
        terminalLinkQualityImproved,
        terminalReceivePower,
        terminalLinkQuality,
        terminalTemperature,
        terminalLockDetector,
        terminalFirmwareversion,
        terminalAuxVoltage
    }
    STATUS current
    DESCRIPTION "Terminal object group"
    ::= { terminal2 24 }

-- *****************************************************************
-- *      Traps
-- *****************************************************************

terminalTraps OBJECT IDENTIFIER ::= { terminal2 22 }

terminalLinkQualityImprovedTrap NOTIFICATION-TYPE
    OBJECTS { terminalLinkQualityImproved }
    STATUS current
    DESCRIPTION "A trap indicating that the microwave signal quality did increase."
    ::= { terminalTraps 1 }

terminalLinkQualityReducedTrap NOTIFICATION-TYPE
    OBJECTS { terminalLinkQualityReduced }
    STATUS current
    DESCRIPTION "A trap indicating that the microwave signal quality did decrease."
    ::= { terminalTraps 2 }

terminalTemperatureHighTrap NOTIFICATION-TYPE
    OBJECTS { terminalTemperature }
    STATUS current
    DESCRIPTION "A trap indicating that the temperature within the unit
    is over or below 70 degree Celsius."
    ::= { terminalTraps 3 }

terminalTemperatureLowTrap NOTIFICATION-TYPE
    OBJECTS { terminalTemperature }
    STATUS current
    DESCRIPTION "A trap indicating that the temperature within the unit
    is over or below -40 degree Celsius."
    ::= { terminalTraps 4 }


terminalNotificationGroup NOTIFICATION-GROUP
    NOTIFICATIONS {
        terminalLinkQualityImprovedTrap,
        terminalLinkQualityReducedTrap,
        terminalTemperatureHighTrap,
        terminalTemperatureLowTrap
    }
    STATUS current
    DESCRIPTION "Terminal notification group"
    ::= { terminal2 23 }


END
