--
-- Copyright (c) 2017 by Ruckus Wireless, Inc.
-- All Rights Reserved
--

RUCKUS-TUNNEL-MIB DEFINITIONS ::= BEGIN

IMPORTS
    ruckusCommonTunnelModule
        FROM RUCKUS-ROOT-MIB
    DisplayString
        FROM SNMPv2-TC
    OBJECT-GROUP
        FROM SNMPv2-CONF
    MODULE-IDENTITY,
    OBJECT-TYPE,
    Counter32
        FROM SNMPv2-SMI;

ruckusTunnelMIB MODULE-IDENTITY
    LAST-UPDATED "201703060900Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus Tunnel Objects"
    ::= { ruckusCommonTunnelModule 1 }


-- Groups
--

ruckusTunnelObjects OBJECT IDENTIFIER     ::= { ruckusTunnelMIB 1 }

ruckusTunnelInfo OBJECT IDENTIFIER    ::= { ruckusTunnelObjects 1 }

ruckusTunnelSoftGREConfigInfo  OBJECT IDENTIFIER   ::= { ruckusTunnelInfo 3 }

ruckusTunnelSoftGREStatusInfo  OBJECT IDENTIFIER   ::= { ruckusTunnelInfo 5 }

ruckusTunnelSoftGREConfigTable OBJECT-TYPE
    SYNTAX  SEQUENCE OF RuckusTunnelSoftGREEntry
    MAX-ACCESS not-accessible
    STATUS current
    DESCRIPTION
        "SoftGRE Tunnel table."
    ::= { ruckusTunnelSoftGREConfigInfo 1 }

ruckusTunnelSoftGREEntry OBJECT-TYPE
    SYNTAX  RuckusTunnelSoftGREEntry
    MAX-ACCESS not-accessible
    STATUS current
    DESCRIPTION
        "Specifies each SoftGRE Tunnel entry."
    INDEX {
        ruckusTunnelSoftGREIndex }
    ::= { ruckusTunnelSoftGREConfigTable 1 }

RuckusTunnelSoftGREEntry ::= SEQUENCE {
    ruckusTunnelSoftGREIndex	   		 	Unsigned32,
    ruckusTunnelSoftGREAdminEnable                   	INTEGER,
    ruckusTunnelSoftGREPrimaryGatewayAddress     	OCTET STRING,
    ruckusTunnelSoftGRESecondaryGatewayAddress 	    	OCTET STRING}

RuckusTunnelSoftGREStatusEntry ::= SEQUENCE {
    ruckusTunnelSoftGREStatusIndex                      Unsigned32,
    ruckusTunnelSoftGRECurrentActivePeerIp     		OCTET STRING,
    ruckusTunnelSoftGREUptime     			DisplayString,
    ruckusTunnelSoftGREKeepAliveDropCounter           	Counter32,
    ruckusTunnelSoftGRETunnelChangeCounter           	Counter32}

ruckusTunnelSoftGREIndex OBJECT-TYPE
    SYNTAX  Unsigned32
    MAX-ACCESS read-only
    STATUS current
    DESCRIPTION
        "Tunnel index."
    ::= { ruckusTunnelSoftGREEntry 200 }

ruckusTunnelSoftGREAdminEnable OBJECT-TYPE
    SYNTAX INTEGER {
           enable(1),
           disable(2)
           }
    MAX-ACCESS read-write
    STATUS current
    DESCRIPTION
        "Specifies the SoftGRE is Enabled or Not-Enabled.
         enable(1):   SoftGRE Enable,
         disable(2):  SoftGRE Disable."
    DEFVAL { disable }
    ::= { ruckusTunnelSoftGREEntry 1 }

ruckusTunnelSoftGREPrimaryGatewayAddress OBJECT-TYPE
    SYNTAX  OCTET STRING  (SIZE (2..40))
    MAX-ACCESS read-write
    STATUS current
    DESCRIPTION
        "Specifies the SoftGRE Primary Gateway ip(v4 and v6) address,
        such as: 192.168.0.2, 2000:0:0:2."
    ::= { ruckusTunnelSoftGREEntry 2 }

ruckusTunnelSoftGRESecondaryGatewayAddress OBJECT-TYPE
    SYNTAX  OCTET STRING  (SIZE (2..40))
    MAX-ACCESS read-write
    STATUS current
    DESCRIPTION
        "Specifies the SoftGRE Secondary Gateway ip(v4 and v6) address,
        such as: 192.168.0.2, 2000:0:0:2."
    ::= { ruckusTunnelSoftGREEntry 3 }


ruckusTunnelSoftGREStatusTable OBJECT-TYPE
    SYNTAX  SEQUENCE OF RuckusTunnelSoftGREStatusEntry
    MAX-ACCESS not-accessible
    STATUS current
    DESCRIPTION
        "SoftGRE Tunnel Status table."
    ::= { ruckusTunnelSoftGREStatusInfo 1 }

ruckusTunnelSoftGREStatusEntry OBJECT-TYPE
    SYNTAX  RuckusTunnelSoftGREStatusEntry
    MAX-ACCESS not-accessible
    STATUS current
    DESCRIPTION
        "Specifies each SoftGRE Tunnel Status entry."
    INDEX {
        ruckusTunnelSoftGREStatusIndex }
    ::= { ruckusTunnelSoftGREStatusTable 1 }


ruckusTunnelSoftGREStatusIndex OBJECT-TYPE
    SYNTAX  Unsigned32
    MAX-ACCESS read-only
    STATUS current
    DESCRIPTION
        "Tunnel Status index."
    ::= { ruckusTunnelSoftGREStatusEntry 200 }


ruckusTunnelSoftGRECurrentActivePeerIp  OBJECT-TYPE
    SYNTAX OCTET STRING  (SIZE (2..40))
    MAX-ACCESS read-only
    STATUS current
    DESCRIPTION
        "show the SoftGRE Active Peer IP Address"
   ::= { ruckusTunnelSoftGREStatusEntry 1 }

ruckusTunnelSoftGREUptime OBJECT-TYPE
    SYNTAX DisplayString(SIZE(1..64))
    MAX-ACCESS read-only
    STATUS current
    DESCRIPTION
        "show the SoftGRE Uptime"
   ::= { ruckusTunnelSoftGREStatusEntry 2 }

ruckusTunnelSoftGREKeepAliveDropCounter OBJECT-TYPE
    SYNTAX Counter32
    MAX-ACCESS read-only
    STATUS current
    DESCRIPTION
        "show the SoftGRE Keep Alive Drop Counter"
   ::= { ruckusTunnelSoftGREStatusEntry 3 }

ruckusTunnelSoftGRETunnelChangeCounter OBJECT-TYPE
    SYNTAX Counter32
    MAX-ACCESS read-only
    STATUS current
    DESCRIPTION
        "show the SoftGRE Tunnel Change Counter"
   ::= { ruckusTunnelSoftGREStatusEntry 4 }


-- Conformance & Compliance
--

END
