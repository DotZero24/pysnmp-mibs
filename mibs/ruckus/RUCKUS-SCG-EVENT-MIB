-- Date      : Mon Mar 07 16:12:27 CST 2011
--
-- Copyright (c) 2011 by Ruckus Wireless, Inc.
-- All Rights Reserved
--

RUCKUS-SCG-EVENT-MIB	DEFINITIONS ::= BEGIN
	IMPORTS
		MacAddress, DisplayString
			FROM SNMPv2-TC
		OBJECT-GROUP, MODULE-COMPLIANCE
			FROM SNMPv2-CONF
		MODULE-IDENTITY, OBJECT-TYPE, Unsigned32, IpAddress, enterprises, NOTIFICATION-TYPE
			FROM SNMPv2-SMI
		ruckusEvents
			FROM RUCKUS-ROOT-MIB;

	ruckusSCGEventMIB	MODULE-IDENTITY
    	LAST-UPDATED "201508181000Z"
    	ORGANIZATION "Ruckus Wireless, Inc."
    	CONTACT-INFO
        	"Ruckus Wireless, Inc.

	        350 West Java Dr.
        	Sunnyvale, CA 94089
	        USA

	        T: +1 (650) 265-4200
    	    F: +1 (408) 738-2065
        	EMail: info@ruckuswireless.com
	        Web: www.ruckuswireless.com"

	DESCRIPTION		"Ruckus SCG event objects, including trap OID and trap payload."
		::=  {  ruckusEvents  10  }

	ruckusSCGEventTraps	OBJECT IDENTIFIER
		::=  {  ruckusSCGEventMIB  1  }

	ruckusSCGEventObjects	OBJECT IDENTIFIER
		::=  {  ruckusSCGEventMIB  2  }

	ruckusSCGSystemMiscEventTrap NOTIFICATION-TYPE
     OBJECTS     {ruckusSCGEventSeverity,ruckusSCGEventType,ruckusSCGEventDescription,ruckusSCGEventCode}
     STATUS      current
     DESCRIPTION
        "Generic trap triggered by admin specified miscellaneous event.
       The event severity, event type, event description and event code are enclosed."
		::= { ruckusSCGEventTraps 1 }

  ruckusSCGUpgradeSuccessTrap NOTIFICATION-TYPE
     OBJECTS{ruckusSCGEventSeverity,ruckusSCGEventType,ruckusSCGEventNodeName,ruckusSCGEventMacAddr,ruckusSCGEventNodeMgmtIp,ruckusSCGEventFirmwareVersion,ruckusSCGEventUpgradedFirmwareVersion,ruckusSCGEventCode}
     STATUS      current
     DESCRIPTION
        "Trigger when there is a SCG upgrade success event.
       The event severity, event type, node name, MAC address, management IP address, firmware version, upgraded firmware version and event code are enclosed."
		::= { ruckusSCGEventTraps 2 }

  ruckusSCGUpgradeFailedTrap NOTIFICATION-TYPE
     OBJECTS     {ruckusSCGEventSeverity,ruckusSCGEventType,ruckusSCGEventFirmwareVersion,ruckusSCGEventUpgradedFirmwareVersion,ruckusSCGEventCode}
     STATUS      current
     DESCRIPTION
        "Trigger when there is a SCG upgrade failed event.
       The event severity, event type, firmware version, upgraded firmware version and event code are enclosed."
		::= { ruckusSCGEventTraps 3 }

  ruckusSCGNodeRestartedTrap NOTIFICATION-TYPE
     OBJECTS     {ruckusSCGEventSeverity,ruckusSCGEventType,ruckusSCGEventNodeName,ruckusSCGEventMacAddr,ruckusSCGEventNodeMgmtIp,ruckusSCGEventReason,ruckusSCGEventCode}
     STATUS      current
     DESCRIPTION
        "Trigger when there is a SCG restarted event.
       The event severity, event type, node name, MAC address, management IP address, restart reason and event code are enclosed."
		::= { ruckusSCGEventTraps 4 }

  ruckusSCGNodeShutdownTrap NOTIFICATION-TYPE
     OBJECTS     {ruckusSCGEventSeverity,ruckusSCGEventType,ruckusSCGEventNodeName,ruckusSCGEventMacAddr,ruckusSCGEventNodeMgmtIp,ruckusSCGEventCode}
     STATUS      current
     DESCRIPTION
        "Trigger when there is a SCG shutdown event.
       The event severity, event type, node name, MAC address, management IP address and event code are enclosed."
		::= { ruckusSCGEventTraps 5 }

  ruckusSCGCPUUsageThresholdExceededTrap NOTIFICATION-TYPE
     OBJECTS     {ruckusSCGEventSeverity,ruckusSCGEventType,ruckusSCGEventNodeName,ruckusSCGEventMacAddr,ruckusSCGCPUPerc,ruckusSCGEventCode}
     STATUS      current
     DESCRIPTION
        "Trigger when there is a SCG CPU threshold exceeded event.
       The event severity, event type, node name, MAC address, CPU usage percent and event code are enclosed."
		::= { ruckusSCGEventTraps 6 }

  ruckusSCGMemoryUsageThresholdExceededTrap NOTIFICATION-TYPE
     OBJECTS     {ruckusSCGEventSeverity,ruckusSCGEventType,ruckusSCGEventNodeName,ruckusSCGEventMacAddr,ruckusSCGMemoryPerc,ruckusSCGEventCode}
     STATUS      current
     DESCRIPTION
        "Trigger when there is a SCG memory threshold exceeded event.
       The event severity, event type, node name, MAC address, memory usage percent and event code are enclosed."
		::= { ruckusSCGEventTraps 7 }

  ruckusSCGDiskUsageThresholdExceededTrap NOTIFICATION-TYPE
     OBJECTS     {ruckusSCGEventSeverity,ruckusSCGEventType,ruckusSCGEventNodeName,ruckusSCGEventMacAddr,ruckusSCGDiskPerc,ruckusSCGEventCode}
     STATUS      current
     DESCRIPTION
        "Trigger when there is a SCG disk usage threshold exceeded event.
       The event severity, event type, node name, MAC address, disk usage percent and event code are enclosed."
		::= { ruckusSCGEventTraps 8 }

  ruckusSCGLicenseUsageThresholdExceededTrap	NOTIFICATION-TYPE
     OBJECTS     {ruckusSCGEventSeverity,ruckusSCGEventType,ruckusSCGLicenseType,ruckusSCGLicenseUsagePerc,ruckusSCGEventCode}
     STATUS  current
     DESCRIPTION
        "Trigger when there is SCG license usage threshold exceeded event.
       The event severity, event type, license type, license usage percent and event code are enclosed."
		::= { ruckusSCGEventTraps 19 }

  ruckusSCGAPMiscEventTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventDescription,ruckusSCGEventZoneName,ruckusSCGEventCode,ruckusSCGEventAPIPv6}
     STATUS      current
     DESCRIPTION
        "Generic trap triggered by AP related miscellaneous event.
       The event severity, event type, AP name, AP MAC address, AP IP address, AP location, AP GPS coordinates, event description, AP description, zone name, event code and AP IPv6 address are enclosed."
    ::= { ruckusSCGEventTraps 20 }

  ruckusSCGAPConnectedTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventReason,ruckusSCGEventCode,ruckusSCGEventAPIPv6}
     STATUS      current
     DESCRIPTION
        "Trigger when there is an AP connected event.
       The event severity, event type, AP name, AP MAC address, AP IP address, AP location, AP description, AP GPS coordinates, zone name, join reason, event code and AP IPv6 address are enclosed."
    ::= { ruckusSCGEventTraps 21 }

  ruckusSCGAPDeletedTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS      current
     DESCRIPTION
        "Trigger when there is an AP deleted event.
       The event severity, event type, AP name, AP MAC address, AP IP address, AP location, AP description, AP GPS coordinates, zone name, event code and AP IPv6 address are enclosed."
    ::= { ruckusSCGEventTraps 22 }

  ruckusSCGAPDisconnectedTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS      current
     DESCRIPTION
        "Trigger when there is an AP connection lost event.
       The event severity, event type, AP name, AP MAC address, AP IP address, AP location, AP description, AP GPS coordinates, zone name, event code and AP IPv6 address are enclosed."
    ::= { ruckusSCGEventTraps 23 }

  ruckusSCGAPLostHeartbeatTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS      current
     DESCRIPTION
        "Trigger when there is a SCG lost AP heart beat event.
       The event severity, event type, AP name, AP MAC address, AP IP address, AP location, AP description, AP GPS coordinates, zone name, event code and AP IPv6 address are enclosed."
    ::= { ruckusSCGEventTraps 24 }

  ruckusSCGAPRebootTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventReason,ruckusSCGEventCode,ruckusSCGEventAPIPv6}
     STATUS      current
     DESCRIPTION
        "Trigger when there is an AP reboot event.
       The event severity, event type, AP name, AP MAC address, AP IP address, AP location, AP description, AP GPS coordinates, zone name, reboot reason, event code and AP IPv6 address are enclosed."
    ::= { ruckusSCGEventTraps 25 }

  ruckusSCGCriticalAPConnectedTrap NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventReason,ruckusSCGEventCode,ruckusSCGEventAPIPv6}
     STATUS      current
     DESCRIPTION
        "Trigger when there is a critical AP connected event.
	     The event severity, event type, AP name, AP MAC address, AP IP address, AP location, AP description, AP GPS coordinates, zone name, join reason, event code and AP IPv6 address are enclosed."
    ::= { ruckusSCGEventTraps 26 }

  ruckusSCGCriticalAPDisconnectedTrap NOTIFICATION-TYPE
     OBJECTS      {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS      current
     DESCRIPTION
        "Trigger when there is a critical AP connection lost event.
	     The event severity, event type, AP name, AP MAC address, AP IP address, AP location, AP description, AP GPS coordinates, zone name, event code and AP IPv6 address are enclosed."
    ::= { ruckusSCGEventTraps 27 }

  ruckusSCGAPRejectedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCtrlIP,ruckusSCGEventReason,ruckusSCGEventCode,ruckusSCGEventAPIPv6}
     STATUS  current
     DESCRIPTION
        "Trigger when there is an AP rejected event.
	     The event severity, event type, AP name, AP MAC address, AP IP address, AP location, AP description, AP GPS coordinates, zone name, SCG control IP address, reject reason, event code and AP IPv6 address are enclosed."
    ::= { ruckusSCGEventTraps 28 }

  ruckusSCGAPConfUpdateFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAPConfigID,ruckusSCGEventCode,ruckusSCGEventAPIPv6}
     STATUS  current
     DESCRIPTION
        "Trigger when there is an AP configuration update failed event.
	       The event severity, event type, AP name, AP MAC address, AP IP address, AP location, AP description, AP GPS coordinates, zone name, configure ID, event code and AP IPv6 address are enclosed."
			::= { ruckusSCGEventTraps 29 }

  ruckusSCGAPConfUpdatedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAPConfigID,ruckusSCGEventCode,ruckusSCGEventAPIPv6}
     STATUS   current
     DESCRIPTION
        "Trigger when there is an AP configuration updated event.
	       The event severity, event type, AP name, AP MAC address, AP IP address, AP location, AP description, AP GPS coordinates, zone name, configure ID, event code and AP IPv6 address are enclosed."
			::= { ruckusSCGEventTraps 30 }

  ruckusSCGAPSwapOutModelDiffTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAPModel,ruckusSCGConfigAPModel,ruckusSCGEventCode,ruckusSCGEventAPIPv6}
     STATUS   current
     DESCRIPTION
        "Trigger when there is an AP model is different from imported swap AP model.
	       The event severity, event type, AP name, AP MAC address, AP IP address, AP location, AP description, AP GPS coordinates, zone name,AP mode, configure AP model, event code and AP IPv6 address are enclosed."
			::= { ruckusSCGEventTraps 31 }

  ruckusSCGAPPreProvisionModelDiffTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAPModel,ruckusSCGConfigAPModel,ruckusSCGEventCode,ruckusSCGEventAPIPv6}
     STATUS   current
     DESCRIPTION
        "Trigger when there is an AP model is different from imported pre-provision AP model.
	       The event severity, event type, AP name, AP MAC address, AP IP address, AP location, AP description, AP GPS coordinates, zone name,AP mode, configure AP model, event code and AP IPv6 address are enclosed."
			::= { ruckusSCGEventTraps 32 }

  ruckusSCGAPDiscoveryFailTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCtrlIP,ruckusSCGEventCode,ruckusSCGEventAPIPv6}
     STATUS  current
     DESCRIPTION
        "Trigger when there is an AP discovery failed event.
	       The event severity, event type, AP name, AP MAC address, AP IP address, AP location, AP description, AP GPS coordinates, zone name, SCG control IP address, event code and AP IPv6 address are enclosed."
			::= { ruckusSCGEventTraps 33 }

	ruckusSCGAPFirmwareUpdateFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
        "Trigger when there is an AP firmware update failed event.
			   The event severity, event type, AP name, AP MAC address, AP IP address, AP location, AP description, AP GPS coordinates, zone name, event code and AP IPv6 address are enclosed."
			::= { ruckusSCGEventTraps 34 }

	ruckusSCGAPFirmwareUpdatedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
        "Trigger when there is an AP firmware update success event.
			   The event severity, event type, AP name, AP MAC address, AP IP address, AP location, AP description, AP GPS coordinates, zone name, event code and AP IPv6 address are enclosed."
			::= { ruckusSCGEventTraps 35 }

  ruckusSCGAPWlanOversubscribedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode}
     STATUS   current
     DESCRIPTION
        "Trigger when there is an AP WLAN oversubscribed event.
	       The event severity, event type, AP name, AP MAC address, AP IP address, AP location, AP description, AP GPS coordinates, zone name and event code are enclosed."
			::= { ruckusSCGEventTraps 36 }

  ruckusSCGAPFactoryResetTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
        "Trigger when there is an AP factory reset event.
	       The event severity, event type, AP name, AP MAC address, AP IP address, AP location, AP description, AP GPS coordinates, zone name, event code and AP IPv6 address are enclosed."
			::= { ruckusSCGEventTraps 37 }

  ruckusSCGCableModemDownTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
        "Trigger when there is an AP cable modem down event.
	       The event severity, event type, AP name, AP MAC address, AP IP address, AP location, AP description, AP GPS coordinates, zone name, event code and AP IPv6 address are enclosed."
			::= { ruckusSCGEventTraps 38 }

  ruckusSCGCableModemRebootTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is an AP cable modem reboot event.
			   The event severity, event type, AP name, AP MAC address, AP IP address, AP location, AP description, AP GPS coordinates, zone name, event code and AP IPv6 address are enclosed."
			 ::= { ruckusSCGEventTraps 39 }

  ruckusSCGAPJoinZoneFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventTargetZoneName,ruckusSCGEventReason,ruckusSCGEventCode,ruckusSCGEventAPIPv6}
     STATUS   current
     DESCRIPTION
			 "Trigger when there is an AP failed to join to a specify zone event.
			   The event severity, event type, AP name, AP MAC address, AP IP address, AP location, AP description, AP GPS coordinates, zone name, target zone name, failure reason, event code and AP IPv6 address are enclosed."
			 ::= { ruckusSCGEventTraps 40 }

  ruckusSCGAPManagedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCtrlIP,ruckusSCGEventCode}
     STATUS  current
     DESCRIPTION
        "Trigger when there is an AP managed event.
	     The event severity, event type, AP name, AP MAC address, AP IP address, AP location, AP description, AP GPS coordinates, zone name, SCG control IP address and event code are enclosed."
    ::= { ruckusSCGEventTraps 41 }

  ruckusSCGCPUUsageThresholdBackToNormalTrap NOTIFICATION-TYPE
     OBJECTS     {ruckusSCGEventSeverity,ruckusSCGEventType,ruckusSCGEventNodeName,ruckusSCGEventMacAddr,ruckusSCGCPUPerc,ruckusSCGEventCode}
     STATUS      current
     DESCRIPTION
        "Trigger when there is a SCG CPU threshold back to normal event.
       The event severity, event type, node name, MAC address, CPU usage percent and event code are enclosed."
		::= { ruckusSCGEventTraps 42 }

  ruckusSCGMemoryUsageThresholdBackToNormalTrap NOTIFICATION-TYPE
     OBJECTS     {ruckusSCGEventSeverity,ruckusSCGEventType,ruckusSCGEventNodeName,ruckusSCGEventMacAddr,ruckusSCGMemoryPerc,ruckusSCGEventCode}
     STATUS      current
     DESCRIPTION
        "Trigger when there is a SCG memory threshold back to normal event.
       The event severity, event type, node name, MAC address, memory usage percent and event code are enclosed."
		::= { ruckusSCGEventTraps 43 }

  ruckusSCGDiskUsageThresholdBackToNormalTrap NOTIFICATION-TYPE
     OBJECTS     {ruckusSCGEventSeverity,ruckusSCGEventType,ruckusSCGEventNodeName,ruckusSCGEventMacAddr,ruckusSCGDiskPerc,ruckusSCGEventCode}
     STATUS      current
     DESCRIPTION
        "Trigger when there is a SCG disk threshold back to normal event.
       The event severity, event type, node name, MAC address, disk usage percent and event code are enclosed."
		::= { ruckusSCGEventTraps 44 }

  ruckusSCGCableModemUpTrap NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
        "Trigger when there is an AP cable modem up event.
	       The event severity, event type, AP name, AP MAC address, AP IP address, AP location, AP description, AP GPS coordinates, zone name, event code and AP IPv6 address are enclosed."
			::= { ruckusSCGEventTraps 45 }

  ruckusSCGAPDiscoverySuccessTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventCtrlIP,ruckusSCGEventCode,ruckusSCGEventAPIPv6}
     STATUS  current
     DESCRIPTION
        "Trigger when there is an AP discovery success event.
	       The event severity, event type, AP name, AP MAC address, AP IP address, AP location, AP description, AP GPS coordinates, zone name, SCG control IP address, event code and AP IPv6 address are enclosed."
			::= { ruckusSCGEventTraps 46 }

  ruckusSCGCMResetByUserTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventReason,ruckusSCGEventCode,ruckusSCGEventAPIPv6}
     STATUS   current
     DESCRIPTION
        "Trigger when there is an AP cable modem soft-rebooted by user event.
	       The event severity, event type, AP name, AP MAC address, AP IP address, AP location, AP description, AP GPS coordinates, zone name, event reason, event code and AP IPv6 address are enclosed."
			::= { ruckusSCGEventTraps 47 }

  ruckusSCGCMResetFactoryByUserTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGEventReason,ruckusSCGEventCode,ruckusSCGEventAPIPv6}
     STATUS   current
     DESCRIPTION
        "Trigger when there is an AP cable modem set to factory default by user event.
	       The event severity, event type, AP name, AP MAC address, AP IP address, AP location, AP description, AP GPS coordinates, zone name, event reason, event code and AP IPv6 address are enclosed."
			::= { ruckusSCGEventTraps 48 }

  ruckusSCGSSIDSpoofingRogueAPDetectedTrap	NOTIFICATION-TYPE
     OBJECTS	{ruckusSCGEventSeverity,ruckusSCGEventType,ruckusSCGEventRogueMac,ruckusSCGEventSSID,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is an AP detects a rogue AP event.
			   The event severity, event type, rogue AP MAC address, ssid, AP name, AP MAC address, AP IP address, AP location, AP description, AP GPS coordinates, zone name, event code and AP IPv6 address are enclosed."
			 ::= { ruckusSCGEventTraps 50 }

  ruckusSCGMacSpoofingRogueAPDetectedTrap	NOTIFICATION-TYPE
     OBJECTS	{ruckusSCGEventSeverity,ruckusSCGEventType,ruckusSCGEventRogueMac,ruckusSCGEventSSID,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is an AP detects a rogue AP event.
			   The event severity, event type, rogue AP MAC address, ssid, AP name, AP MAC address, AP IP address, AP location, AP description, AP GPS coordinates, zone name, event code and AP IPv6 address are enclosed."
			 ::= { ruckusSCGEventTraps 51 }

  ruckusSCGSameNetworkRogueAPDetectedTrap	NOTIFICATION-TYPE
     OBJECTS	{ruckusSCGEventSeverity,ruckusSCGEventType,ruckusSCGEventRogueMac,ruckusSCGEventSSID,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is an AP detects a rogue AP which has the same bssid with detect AP event.
			   The event severity, event type, rogue AP MAC address, ssid, AP name, AP MAC address, AP IP address, AP location, AP description, AP GPS coordinates, zone name, event code and AP IPv6 address are enclosed."
			 ::= { ruckusSCGEventTraps 52 }

  ruckusSCGADHocNetworkRogueAPDetectedTrap	NOTIFICATION-TYPE
     OBJECTS	{ruckusSCGEventSeverity,ruckusSCGEventType,ruckusSCGEventRogueMac,ruckusSCGEventSSID,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is an AP detects a rogue AP which has the same network detecting AP event.
			   The event severity, event type, rogue AP MAC address, ssid, AP name, AP MAC address, AP IP address, AP location, AP description, AP GPS coordinates, zone name and event code are enclosed."
			 ::= { ruckusSCGEventTraps 53 }

  ruckusSCGMaliciousRogueAPTimeoutTrap	NOTIFICATION-TYPE
     OBJECTS	{ruckusSCGEventSeverity,ruckusSCGEventType,ruckusSCGEventRogueMac,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6}
     STATUS   current
     DESCRIPTION
			 "Trigger when there is a rogue AP disappears event.
			   The event severity, event type, rogue AP MAC address, AP name, AP MAC address, AP IP address, AP location, AP description, AP GPS coordinates, zone name, event code and AP IPv6 address are enclosed."
			 ::= { ruckusSCGEventTraps 54 }

  ruckusSCGAPLBSConnectSuccessTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLBSURL,ruckusSCGLBSPort,ruckusSCGEventCode,ruckusSCGEventAPIPv6}
     STATUS   current
     DESCRIPTION
			 "Trigger when there is AP successfully connect to LS event.
			   The event severity, event type,AP name, AP MAC address, AP IP address, AP location, AP description, AP GPS coordinates, zone name, LBS server URL, LBS port, event code and AP IPv6 address are enclosed."
			 ::= { ruckusSCGEventTraps 55 }

  ruckusSCGAPLBSNoResponsesTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLBSURL,ruckusSCGLBSPort,ruckusSCGEventCode,ruckusSCGEventAPIPv6}
     STATUS   current
     DESCRIPTION
			 "Trigger when there is an AP connect to LS no response event.
			    The event severity, event type,AP name, AP MAC address, AP IP address, AP location, AP description, AP GPS coordinates, zone name, LBS server URL, LBS port, event code and AP IPv6 address are enclosed."
			::= { ruckusSCGEventTraps 56 }

  ruckusSCGAPLBSAuthFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLBSURL,ruckusSCGLBSPort,ruckusSCGEventCode,ruckusSCGEventAPIPv6}
     STATUS   current
     DESCRIPTION
			 "Trigger when there is an AP connect LS authentication failure event.
			   The event severity, event type,AP name, AP MAC address, AP IP address, AP location, AP description, AP GPS coordinates, zone name, LBS server URL, LBS port, event code and AP IPv6 address are enclosed."
			::= { ruckusSCGEventTraps 57 }

  ruckusSCGAPLBSConnectFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLBSURL,ruckusSCGLBSPort,ruckusSCGEventCode,ruckusSCGEventAPIPv6}
     STATUS   current
     DESCRIPTION
			 "Trigger when there is an AP failed connect to LS event.
			    The event severity, event type,AP name, AP MAC address, AP IP address, AP location, AP description, AP GPS coordinates, zone name, LBS server URL, LBS port, event code and AP IPv6 address are enclosed."
			::= { ruckusSCGEventTraps 58 }

  ruckusSCGGeneralRogueAPTrap	NOTIFICATION-TYPE
     OBJECTS	{ruckusSCGEventSeverity,ruckusSCGEventType,ruckusSCGEventRogueMac,ruckusSCGEventSSID,ruckusSCGEventAPName,ruckusSCGEventAPMacAddr,ruckusSCGEventAPIP,ruckusSCGEventAPLocation,ruckusSCGEventAPDescription,ruckusSCGEventAPGPSCoordinates,ruckusSCGEventZoneName,ruckusSCGEventCode,ruckusSCGEventAPIPv6,ruckusSCGEventRoguePolicyName,ruckusSCGEventRogueRuleName,ruckusSCGEventRogueType}
     STATUS   current
     DESCRIPTION
			 "Trigger when there is an AP detects a rogue AP and classified by policy event.
			   The event severity, event type, rogue AP MAC address, ssid, AP name, AP MAC address, AP IP address, AP location, AP description, AP GPS coordinates, zone name, event code, policy name, rule name, rogue type and AP IPv6 address are enclosed."
			 ::= { ruckusSCGEventTraps 59 }

  ruckusSCGAPTunnelBuildFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDPIP,ruckusSCGEventReason,ruckusSCGEventCode,ruckusSCGEventAPIPv6}
     STATUS  current
     DESCRIPTION
        "Trigger when there is an AP build tunnel failed event.
	       The event severity, event type, AP name, AP MAC address, AP IP address, AP location, AP description, AP GPS coordinates, zone name, SCG DP IP address, failure reason, event code and AP IPv6 address are enclosed."
		::= { ruckusSCGEventTraps 60 }

  ruckusSCGAPTunnelBuildSuccessTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDPIP,ruckusSCGEventCode,ruckusSCGEventAPIPv6}
     STATUS  current
     DESCRIPTION
        "Trigger when there is an AP build tunnel success event.
	       The event severity, event type, AP name, AP MAC address, AP IP address, AP location, AP description, AP GPS coordinates,  zone name, SCG DP IP address, event code and AP IPv6 address are enclosed."
		::= { ruckusSCGEventTraps 61 }

  ruckusSCGAPTunnelDisconnectedTrap	NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDPIP,ruckusSCGEventReason,ruckusSCGEventCode,ruckusSCGEventAPIPv6}
     STATUS  current
     DESCRIPTION
        "Trigger when there is an AP tunnel disconnected event.
	       The event severity, event type, AP name, AP MAC address, AP IP address, AP location, AP description, AP GPS coordinates, zone name, SCG DP IP address, failure reason, event code and AP IPv6 address are enclosed."
		::= { ruckusSCGEventTraps 62 }

  ruckusSCGAPSoftGRETunnelFailoverPtoSTrap	NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusPrimaryGRE,ruckusSecondaryGRE,ruckusSCGEventCode,ruckusSCGEventAPIPv6}
     STATUS  current
     DESCRIPTION
        "Trigger when there is an AP softGRE tunnel fails over primary to secondary event.
	       The event severity, event type, AP name, AP MAC address, AP IP address, AP location, AP description, AP GPS coordinates, zone name, primary GRE gateway, secondary GRE gateway, event code and AP IPv6 address are enclosed."
		::= { ruckusSCGEventTraps 65 }

  ruckusSCGAPSoftGRETunnelFailoverStoPTrap	NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusPrimaryGRE,ruckusSecondaryGRE,ruckusSCGEventCode,ruckusSCGEventAPIPv6}
     STATUS  current
     DESCRIPTION
        "Trigger when there is an AP softGRE tunnel fails over secondary to primary event.
	       The event severity, event type, AP name, AP MAC address, AP IP address, AP location, AP description, AP GPS coordinates, zone name, primary GRE gateway, secondary GRE gateway, event code and AP IPv6 address are enclosed."
		::= { ruckusSCGEventTraps 66 }

 ruckusSCGAPSoftGREGatewayNotReachableTrap	NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSoftGREGatewayList,ruckusSCGEventCode,ruckusSCGEventAPIPv6}
     STATUS  current
     DESCRIPTION
        "Trigger when there is an AP softGRE gateway not reachable event.
	       The event severity, event type, AP name, AP MAC address, AP IP address, AP location, AP description, AP GPS coordinates, zone name, soft GRE gateway list, event code and AP IPv6 address are enclosed."
		::= { ruckusSCGEventTraps 67 }

  ruckusSCGAPSoftGREGatewayReachableTrap	NOTIFICATION-TYPE
     OBJECTS     {ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGSoftGREGWAddress,ruckusSCGEventCode}
     STATUS  current
     DESCRIPTION
        "Trigger when there is an AP softGRE gateway reachable event.
	       The event severity, event type, AP name, AP MAC address, AP IP address, AP location, AP description, AP GPS coordinates, zone name, soft GRE gateway IP address and event code are enclosed."
		::= { ruckusSCGEventTraps 68 }

  ruckusSCGDPConfUpdateFailedTrap	NOTIFICATION-TYPE
     OBJECTS     {ruckusSCGEventSeverity,ruckusSCGEventType,ruckusSCGDPKey,ruckusSCGDPConfigID,ruckusSCGEventCode}
     STATUS  current
     DESCRIPTION
        "Trigger when there is DP configuration update failed event.
       The event severity, event type, DP's identifier, configuration UUID and event code are enclosed."
		::= { ruckusSCGEventTraps 70 }

  ruckusSCGDPLostHeartbeatTrap	NOTIFICATION-TYPE
     OBJECTS     {ruckusSCGEventSeverity,ruckusSCGEventType,ruckusSCGDPKey,ruckusSCGEventCode}
     STATUS  current
     DESCRIPTION
        "Trigger when there is DP lost heart beat event.
       The event severity, event type, DP's identifier and event code are enclosed."
		::= { ruckusSCGEventTraps 71 }

  ruckusSCGDPDisconnectedTrap	NOTIFICATION-TYPE
     OBJECTS     {ruckusSCGEventSeverity,ruckusSCGEventType,ruckusSCGDPKey,ruckusSCGEventCtrlIP,ruckusSCGEventCode}
     STATUS  current
     DESCRIPTION
        "Trigger when there is DP disconnected event.
       The event severity, event code, event type , DP's identifier, SCG control IP address and event code are enclosed."
		::= { ruckusSCGEventTraps 72 }

  ruckusSCGDPPhyInterfaceDownTrap	NOTIFICATION-TYPE
     OBJECTS     {ruckusSCGEventSeverity,ruckusSCGEventType,ruckusSCGDPKey,ruckusSCGNetworkPortID,ruckusSCGEventCode}
     STATUS  current
     DESCRIPTION
        "Trigger when there is DP physical interface down event.
       The event severity, event type, DP's identifier, network port ID and event code are enclosed."
		::= { ruckusSCGEventTraps 73 }

  ruckusSCGDPStatusUpdateFailedTrap	NOTIFICATION-TYPE
     OBJECTS     {ruckusSCGEventSeverity,ruckusSCGEventType,ruckusSCGDPKey,ruckusSCGEventCode}
     STATUS  current
     DESCRIPTION
        "Trigger when there is DP update status failed event.
       The event severity, event type, DP's identifier and event code are enclosed."
		::= { ruckusSCGEventTraps 74 }

  ruckusSCGDPStatisticUpdateFaliedTrap	NOTIFICATION-TYPE
     OBJECTS     {ruckusSCGEventSeverity,ruckusSCGEventType,ruckusSCGDPKey,ruckusSCGEventCode}
     STATUS  current
     DESCRIPTION
        "Trigger when there is DP update statistical failed event.
       The event severity, event type, DP's identifier and event code are enclosed."
		::= { ruckusSCGEventTraps 75 }

  ruckusSCGDPConnectedTrap	NOTIFICATION-TYPE
     OBJECTS     {ruckusSCGEventSeverity,ruckusSCGEventType,ruckusSCGDPKey,ruckusSCGEventCtrlIP,ruckusSCGEventCode}
     STATUS  current
     DESCRIPTION
        "Trigger when there is DP connected event.
       The event severity, event type, DP's identifier, SCG control IP and event code are enclosed."
		::= { ruckusSCGEventTraps 76 }

  ruckusSCGDPPhyInterfaceUpTrap	NOTIFICATION-TYPE
     OBJECTS     {ruckusSCGEventSeverity,ruckusSCGEventType,ruckusSCGDPKey,ruckusSCGNetworkPortID,ruckusSCGEventCode}
     STATUS  current
     DESCRIPTION
        "Trigger when there is DP physical interface up event.
       The event severity, event type, DP's identifier, network port ID and event code are enclosed."
		::= { ruckusSCGEventTraps 77 }

  ruckusSCGDPConfUpdatedTrap	NOTIFICATION-TYPE
     OBJECTS     {ruckusSCGEventSeverity,ruckusSCGEventType,ruckusSCGDPKey,ruckusSCGDPConfigID,ruckusSCGEventCode}
     STATUS  current
     DESCRIPTION
        "Trigger when there is DP configuration updated event.
       The event severity, event type, DP's identifier, configuration UUID and event code are enclosed."
		::= { ruckusSCGEventTraps 78 }

  ruckusSCGDPTunnelTearDownTrap	NOTIFICATION-TYPE
     OBJECTS     {ruckusSCGEventSeverity,ruckusSCGEventType,ruckusSCGDPKey,ruckusSCGEventAPMacAddr,ruckusSCGEventReason,ruckusSCGEventCode}
     STATUS  current
     DESCRIPTION
        "Trigger when there is DP tear down tunnel event.
       The event severity, event type, DP's identifier, AP MAC address, event reason and event code are enclosed."
		::= { ruckusSCGEventTraps 79 }

  ruckusSCGDPRebootTrap	NOTIFICATION-TYPE
     OBJECTS     {ruckusSCGEventSeverity,ruckusSCGEventType,ruckusSCGDPKey,ruckusSCGEventCode}
     STATUS  current
     DESCRIPTION
        "Trigger when there is DP reboot event.
       The event severity, event type, DP's identifier and event code are enclosed."
		::= { ruckusSCGEventTraps 80 }

  ruckusSCGDPAcceptTunnelRequestTrap  NOTIFICATION-TYPE
     OBJECTS     {ruckusSCGEventSeverity,ruckusSCGEventType,ruckusSCGDPKey,ruckusSCGEventAPMacAddr,ruckusSCGEventCode}
     STATUS  current
     DESCRIPTION
        "Trigger when there is data plane accepts a tunnel request from the AP event.
       The event severity, event type, DP's identifier, AP MAC address and event code are enclosed."
		::= { ruckusSCGEventTraps 81 }

  ruckusSCGDPRejectTunnelRequestTrap  NOTIFICATION-TYPE
     OBJECTS     {ruckusSCGEventSeverity,ruckusSCGEventType,ruckusSCGDPKey,ruckusSCGEventAPMacAddr,ruckusSCGEventReason,ruckusSCGEventCode}
     STATUS  current
     DESCRIPTION
        "Trigger occurs where there is data plane rejects a tunnel request from the AP event.
       The event severity, event type, DP's identifier, AP MAC address, event reason and event code are enclosed."
		::= { ruckusSCGEventTraps 82 }

  ruckusSCGDPSgreGWUnreachableTrap NOTIFICATION-TYPE
     OBJECTS     {ruckusSCGEventSeverity,ruckusSCGEventType,ruckusSCGDPKey,ruckusSCGSoftGREGWAddress,ruckusSCGEventCode}
     STATUS  current
     DESCRIPTION
        "Trigger when there is data plane detects that a core network gateway is unreachable event.
       The event severity, event type, DP's identifier, core gateway address and event code are enclosed."
		::= { ruckusSCGEventTraps 83 }

  ruckusSCGDPSgreGWReachableTrap NOTIFICATION-TYPE
     OBJECTS     {ruckusSCGEventSeverity,ruckusSCGEventType,ruckusSCGDPKey,ruckusSCGSoftGREGWAddress,ruckusSCGEventCode}
     STATUS  current
     DESCRIPTION
        "Trigger when there is data plane detects that a core network gateway is reachable event.
       The event severity, event type, DP's identifier, core gateway address and event code are enclosed."
		::= { ruckusSCGEventTraps 84 }

  ruckusSCGDPTunnelSetUpTrap NOTIFICATION-TYPE
     OBJECTS     {ruckusSCGEventSeverity,ruckusSCGEventType,ruckusSCGDPKey,ruckusSCGEventAPMacAddr,ruckusSCGEventCode}
     STATUS  current
     DESCRIPTION
        "Trigger when there is DP set up tunnel event.
       The event severity, event type, DP's identifier, AP MAC address and event code are enclosed."
		::= { ruckusSCGEventTraps 85 }

  ruckusSCGDPDiscoverySuccessTrap NOTIFICATION-TYPE
     OBJECTS     {ruckusSCGEventSeverity,ruckusSCGEventType,ruckusSCGDPKey,ruckusSCGEventCtrlIP,ruckusSCGEventCode}
     STATUS  current
     DESCRIPTION
        "Trigger when there is a DP discovery success event.
       The event severity, event type, DP's identifier, SCG control IP address and event code are enclosed."
		::= { ruckusSCGEventTraps 86 }

  ruckusSCGDPDiscoveryFailTrap NOTIFICATION-TYPE
     OBJECTS     {ruckusSCGEventSeverity,ruckusSCGEventType,ruckusSCGDPKey,ruckusSCGEventCtrlIP,ruckusSCGEventCode}
     STATUS  current
     DESCRIPTION
        "Trigger when there is a DP discovery failed event.
       The event severity, event type, DP's identifier, SCG control IP address and event code are enclosed."
		::= { ruckusSCGEventTraps 87 }

  ruckusSCGDPSgreGWInactTrap NOTIFICATION-TYPE
     OBJECTS     {ruckusSCGEventSeverity,ruckusSCGEventType,ruckusSCGDPKey,ruckusSCGSoftGREGWAddress,ruckusSCGEventCode}
     STATUS  current
     DESCRIPTION
        "Trigger when there is data plane detects that a core network gateway is inactive event.
       The event severity, event type, DP's identifier, core gateway address and event code are enclosed."
		::= { ruckusSCGEventTraps 88 }

  ruckusSCGDPSgreGWActTrap NOTIFICATION-TYPE
     OBJECTS     {ruckusSCGEventSeverity,ruckusSCGEventType,ruckusSCGDPKey,ruckusSCGSoftGREGWAddress,ruckusSCGEventCode}
     STATUS  current
     DESCRIPTION
        "Trigger when there is data plane detects that a core network gateway is active event.
       The event severity, event type, DP's identifier, core gateway address and event code are enclosed."
		::= { ruckusSCGEventTraps 89 }

  ruckusSCGDPPktPoolLowTrap NOTIFICATION-TYPE
     OBJECTS     {ruckusSCGEventSeverity,ruckusSCGEventType,ruckusSCGDPKey,ruckusSCGDPPacketPoolID,ruckusSCGEventCode}
     STATUS  current
     DESCRIPTION
        "Trigger when there is data core's packet pool in under low water mark event.
       The event severity, event type, DP's identifier, DP's packet pool ID and event code are enclosed."
		::= { ruckusSCGEventTraps 90 }

  ruckusSCGDPPktPoolCriticalLowTrap NOTIFICATION-TYPE
     OBJECTS     {ruckusSCGEventSeverity,ruckusSCGEventType,ruckusSCGDPKey,ruckusSCGDPPacketPoolID,ruckusSCGEventCode}
     STATUS  current
     DESCRIPTION
        "Trigger when there is data core's packet pool in under critical low water mark event.
       The event severity, event type, DP's identifier, DP's packet pool ID and event code are enclosed."
		::= { ruckusSCGEventTraps 91 }

  ruckusSCGDPPktPoolRecoverTrap NOTIFICATION-TYPE
     OBJECTS     {ruckusSCGEventSeverity,ruckusSCGEventType,ruckusSCGDPKey,ruckusSCGDPPacketPoolID,ruckusSCGEventCode}
     STATUS  current
     DESCRIPTION
        "Trigger when there is when data core's packet pool in above high water mark event.
       The event severity, event type, DP's identifier, DP's packet pool ID and event code are enclosed."
		::= { ruckusSCGEventTraps 92 }

  ruckusSCGDPCoreDeadTrap NOTIFICATION-TYPE
     OBJECTS     {ruckusSCGEventSeverity,ruckusSCGEventType,ruckusSCGDPKey,ruckusSCGEventCode}
     STATUS  current
     DESCRIPTION
        "Trigger when there is one or more data core dead event.
       The event severity, event type, DP's identifier and event code are enclosed."
		::= { ruckusSCGEventTraps 93 }

  ruckusSCGDPDeletedTrap NOTIFICATION-TYPE
     OBJECTS     {ruckusSCGEventSeverity,ruckusSCGEventType,ruckusSCGDPKey,ruckusSCGEventCode}
     STATUS  current
     DESCRIPTION
        "Trigger when there is a DP is deleted event.
       The event severity, event type, DP's identifier and event code are enclosed."
		::= { ruckusSCGEventTraps 94 }

  ruckusSCGDPUpgradeStartTrap NOTIFICATION-TYPE
     OBJECTS     {ruckusSCGEventSeverity,ruckusSCGEventType,ruckusSCGDPKey,ruckusSCGEventCode}
     STATUS  current
     DESCRIPTION
        "Trigger when there is DP started the upgrade process event.
       The event severity, event type, DP's identifier and event code are enclosed."
		::= { ruckusSCGEventTraps 95}

  ruckusSCGDPUpgradingTrap NOTIFICATION-TYPE
     OBJECTS     {ruckusSCGEventSeverity,ruckusSCGEventType,ruckusSCGDPKey,ruckusSCGEventCode}
     STATUS  current
     DESCRIPTION
        "Trigger when there is DP has started to upgrade program and configuration event.
       The event severity, event type, DP's identifier and event code are enclosed."
		::= { ruckusSCGEventTraps 96}

  ruckusSCGDPUpgradeSuccessTrap NOTIFICATION-TYPE
     OBJECTS     {ruckusSCGEventSeverity,ruckusSCGEventType,ruckusSCGDPKey,ruckusSCGEventCode}
     STATUS  current
     DESCRIPTION
        "Trigger when there is DP has been upgraded successfully event.
       The event severity, event type, DP's identifier and event code are enclosed."
		::= { ruckusSCGEventTraps 97}

  ruckusSCGDPUpgradeFailedTrap NOTIFICATION-TYPE
     OBJECTS     {ruckusSCGEventSeverity,ruckusSCGEventType,ruckusSCGDPKey,ruckusSCGEventCode}
     STATUS  current
     DESCRIPTION
        "Trigger when there is DP failed to upgrade event.
       The event severity, event type, DP's identifier and event code are enclosed."
		::= { ruckusSCGEventTraps 98}

  ruckusSCGClientMiscEventTrap NOTIFICATION-TYPE
     OBJECTS     {ruckusSCGEventSeverity,ruckusSCGEventType,ruckusSCGEventClientMacAddr,ruckusSCGEventDescription,ruckusSCGEventCode}
     STATUS      current
     DESCRIPTION
        "Generic trap triggered by specified client related miscellaneous event.
         The event severity, event type, client MAC address, event description and event code are enclosed."
    ::= { ruckusSCGEventTraps 100 }

  ruckusSCGNodeJoinFailedTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is new node join failed event.
       The event severity, event type, node name, node MAC address, cluster name and event code are enclosed."
		::= { ruckusSCGEventTraps 200 }

  ruckusSCGNodeRemoveFailedTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is remove node failed event.
       The event severity, event type, node name,node MAC address, cluster name and event code are enclosed."
		::= { ruckusSCGEventTraps 201 }

  ruckusSCGNodeOutOfServiceTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is node out of service event.
       The event severity, event type, node name,node MAC address, cluster name and event code are enclosed."
		::= { ruckusSCGEventTraps 202 }

  ruckusSCGClusterInMaintenanceStateTrap	NOTIFICATION-TYPE
     OBJECTS     {ruckusSCGEventSeverity,ruckusSCGEventType,ruckusSCGClusterName,ruckusSCGEventCode}
     STATUS  current
     DESCRIPTION
        "Trigger when there is cluster in maintenance state event.
       The event severity, event type, cluster name and event code are enclosed."
		::= { ruckusSCGEventTraps 203 }

  ruckusSCGClusterBackupFailedTrap	NOTIFICATION-TYPE
     OBJECTS     {ruckusSCGEventSeverity,ruckusSCGEventType,ruckusSCGClusterName,ruckusSCGEventCode}
     STATUS  current
     DESCRIPTION
        "Trigger when there is backup cluster failed event.
       The event severity, event type, cluster name and event code are enclosed."
		::= { ruckusSCGEventTraps 204 }

  ruckusSCGClusterRestoreFailedTrap	NOTIFICATION-TYPE
     OBJECTS     {ruckusSCGEventSeverity,ruckusSCGEventType,ruckusSCGClusterName,ruckusSCGEventCode}
     STATUS  current
     DESCRIPTION
        "Trigger when there is restore cluster failed event.
       The event severity, event type, cluster name and event code are enclosed."
		::= { ruckusSCGEventTraps 205 }

  ruckusSCGClusterAppStoppedTrap	NOTIFICATION-TYPE
     OBJECTS     {ruckusSCGEventSeverity,ruckusSCGEventType,ruckusSCGProcessName,ruckusSCGEventNodeName,ruckusSCGEventMacAddr,ruckusSCGEventCode}
     STATUS  current
     DESCRIPTION
        "Trigger when there is cluster application stop event.
       The event severity, event type, application name, SCG node name, node MAC address and event code are enclosed."
		::= { ruckusSCGEventTraps 206 }

  ruckusSCGNodeBondInterfaceDownTrap	NOTIFICATION-TYPE
     OBJECTS     {ruckusSCGEventSeverity,ruckusSCGEventType,ruckusSCGNetworkInterface,ruckusSCGEventNodeName,ruckusSCGEventMacAddr,ruckusSCGEventCode}
     STATUS  current
     DESCRIPTION
        "Trigger when there is node bond interface down event.
       The event severity, event type, network interface, SCG node name, node MAC address and event code are enclosed."
		::= { ruckusSCGEventTraps 207 }

  ruckusSCGNodePhyInterfaceDownTrap	NOTIFICATION-TYPE
     OBJECTS     {ruckusSCGEventSeverity,ruckusSCGEventType,ruckusSCGNetworkInterface,ruckusSCGEventNodeName,ruckusSCGEventMacAddr,ruckusSCGEventCode}
     STATUS  current
     DESCRIPTION
        "Trigger when there is node physical interface down event.
       The event severity, event type, network interface, SCG node name, node MAC address and event code are enclosed."
		::= { ruckusSCGEventTraps 208 }

  ruckusSCGClusterLeaderChangedTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is cluster leader changed event.
       The event severity, event type, SCG node name, node MAC address, cluster name and event code are enclosed."
		::= { ruckusSCGEventTraps 209 }

  ruckusSCGClusterUpgradeSuccessTrap	NOTIFICATION-TYPE
     OBJECTS     {ruckusSCGEventSeverity,ruckusSCGEventType,ruckusSCGClusterName,ruckusSCGEventFirmwareVersion,ruckusSCGEventUpgradedFirmwareVersion,ruckusSCGEventCode}
     STATUS  current
     DESCRIPTION
        "Trigger when there is upgrade entire cluster success event.
       The event severity, event type, cluster name, firmware version, upgraded firmware version and event code are enclosed."
		::= { ruckusSCGEventTraps 210 }

  ruckusSCGNodeBondInterfaceUpTrap	NOTIFICATION-TYPE
     OBJECTS     {ruckusSCGEventSeverity,ruckusSCGEventType,ruckusSCGNetworkInterface,ruckusSCGEventNodeName,ruckusSCGEventMacAddr,ruckusSCGEventCode}
     STATUS  current
     DESCRIPTION
        "Trigger when there is node bond interface up event.
       The event severity, event type, network interface, SCG node name, SCG MAC address and event code are enclosed."
		::= { ruckusSCGEventTraps 211 }

  ruckusSCGNodePhyInterfaceUpTrap	NOTIFICATION-TYPE
     OBJECTS     {ruckusSCGEventSeverity,ruckusSCGEventType,ruckusSCGNetworkInterface,ruckusSCGEventNodeName,ruckusSCGEventMacAddr,ruckusSCGEventCode}
     STATUS  current
     DESCRIPTION
        "Trigger when there is node physical interface up event.
       The event severity, event type,network interface, SCG node name, SCG MAC address and event code are enclosed."
		::= { ruckusSCGEventTraps 212 }

  ruckusSCGClusterBackToInServiceTrap	NOTIFICATION-TYPE
     OBJECTS     {ruckusSCGEventSeverity,ruckusSCGEventType,ruckusSCGClusterName,ruckusSCGEventCode}
     STATUS  current
     DESCRIPTION
        "Trigger when there is cluster back to in service event.
       The event severity, event type, cluster name and event code are enclosed."
		::= { ruckusSCGEventTraps 216 }

  ruckusSCGBackupClusterSuccessTrap	NOTIFICATION-TYPE
     OBJECTS     {ruckusSCGEventSeverity,ruckusSCGEventType,ruckusSCGClusterName,ruckusSCGEventCode}
     STATUS  current
     DESCRIPTION
        "Trigger when there is backup cluster success event.
       The event severity, event type, cluster name and event code are enclosed."
		::= { ruckusSCGEventTraps 217 }

  ruckusSCGNodeJoinSuccessTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is new node join success event.
       The event severity, event type, SCG node name, node MAC address, cluster name and event code are enclosed."
		::= { ruckusSCGEventTraps 218 }

  ruckusSCGClusterAppStartTrap	NOTIFICATION-TYPE
     OBJECTS     {ruckusSCGEventSeverity,ruckusSCGEventType,ruckusSCGProcessName,ruckusSCGEventNodeName,ruckusSCGEventMacAddr,ruckusSCGEventCode}
     STATUS  current
     DESCRIPTION
        "Trigger when there is cluster application start event.
       The event severity, event type, application name, SCG node name, node MAC address and event code are enclosed."
		::= { ruckusSCGEventTraps 219 }

  ruckusSCGNodeRemoveSuccessTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is remove node success event.
       The event severity, event type, SCG node name, node MAC address, cluster name and event code are enclosed."
		::= { ruckusSCGEventTraps 220 }

  ruckusSCGClusterRestoreSuccessTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is restore cluster success event.
       The event severity, event type, SCG node name, node MAC address, cluster name and event code are enclosed."
		::= { ruckusSCGEventTraps 221 }

  ruckusSCGNodeBackToInServiceTrap	NOTIFICATION-TYPE
     OBJECTS     {ruckusSCGEventSeverity,ruckusSCGEventType,ruckusSCGEventNodeName,ruckusSCGEventMacAddr,ruckusSCGClusterName,ruckusSCGEventCode}
     STATUS  current
     DESCRIPTION
        "Trigger when there is node back to in service event.
       The event severity, event type, SCG node name, node MAC address, cluster name and event code are enclosed."
		::= { ruckusSCGEventTraps 222 }

  ruckusSCGSshTunnelSwitchedTrap	NOTIFICATION-TYPE
     OBJECTS     {ruckusSCGEventSeverity,ruckusSCGEventType,ruckusSCGEventNodeName,ruckusSCGEventMacAddr,ruckusSCGClusterName,ruckusSCGSwitchStatus,ruckusSCGEventCode}
     STATUS  current
     DESCRIPTION
        "Trigger when there is SSH tunnel switched event.
       The event severity, event type, SCG node name, node MAC address, cluster name, switch status and event code are enclosed."
		::= { ruckusSCGEventTraps 223 }

  ruckusSCGClusterCfgBackupStartTrap	NOTIFICATION-TYPE
     OBJECTS     {ruckusSCGEventSeverity,ruckusSCGEventType,ruckusSCGClusterName,ruckusSCGEventCode}
     STATUS  current
     DESCRIPTION
        "Trigger when there is a configuration backup start event.
       The event severity, event type, cluster name and event code are enclosed."
		::= { ruckusSCGEventTraps 224 }

  ruckusSCGClusterCfgBackupSuccessTrap	NOTIFICATION-TYPE
     OBJECTS     {ruckusSCGEventSeverity,ruckusSCGEventType,ruckusSCGClusterName,ruckusSCGEventCode}
     STATUS  current
     DESCRIPTION
        "Trigger when there is a configuration backup success event.
       The event severity, event type, cluster name and event code are enclosed."
		::= { ruckusSCGEventTraps 225 }

  ruckusSCGClusterCfgBackupFailedTrap	NOTIFICATION-TYPE
     OBJECTS     {ruckusSCGEventSeverity,ruckusSCGEventType,ruckusSCGClusterName,ruckusSCGEventCode}
     STATUS  current
     DESCRIPTION
        "Trigger when there is a configuration backup failed event.
       The event severity, event type, cluster name and event code are enclosed."
		::= { ruckusSCGEventTraps 226 }

  ruckusSCGClusterCfgRestoreSuccessTrap	NOTIFICATION-TYPE
     OBJECTS     {ruckusSCGEventSeverity,ruckusSCGEventType,ruckusSCGClusterName,ruckusSCGEventCode}
     STATUS  current
     DESCRIPTION
        "Trigger when there is a configuration restore success event.
       The event severity, event type, cluster name and event code are enclosed."
		::= { ruckusSCGEventTraps 227 }

  ruckusSCGClusterCfgRestoreFailedTrap	NOTIFICATION-TYPE
     OBJECTS     {ruckusSCGEventSeverity,ruckusSCGEventType,ruckusSCGClusterName,ruckusSCGEventCode}
     STATUS  current
     DESCRIPTION
        "Trigger when there is a configuration restore failed event.
       The event severity, event type, cluster name and event code are enclosed."
		::= { ruckusSCGEventTraps 228 }

  ruckusSCGClusterUploadSuccessTrap	NOTIFICATION-TYPE
     OBJECTS     {ruckusSCGEventSeverity,ruckusSCGEventType,ruckusSCGClusterName,ruckusSCGEventCode}
     STATUS  current
     DESCRIPTION
        "Trigger when there is a cluster upload success event.
       The event severity, event type, cluster name and event code are enclosed."
		::= { ruckusSCGEventTraps 229 }

  ruckusSCGClusterUploadFailedTrap	NOTIFICATION-TYPE
     OBJECTS     {ruckusSCGEventSeverity,ruckusSCGEventType,ruckusSCGClusterName,ruckusSCGEventReason,ruckusSCGEventCode}
     STATUS  current
     DESCRIPTION
        "Trigger when there is a cluster upload failed event.
       The event severity, event type, cluster name, failure reason and event code are enclosed."
		::= { ruckusSCGEventTraps 230 }

  ruckusSCGClusterOutOfServiceTrap	NOTIFICATION-TYPE
     OBJECTS     {ruckusSCGEventSeverity,ruckusSCGEventType,ruckusSCGClusterName,ruckusSCGEventCode}
     STATUS  current
     DESCRIPTION
        "Trigger when there is a cluster out of service event.
       The event severity, event type, cluster name and event code are enclosed."
		::= { ruckusSCGEventTraps 231 }

  ruckusSCGClusterUploadVDPFirmwareStartTrap  NOTIFICATION-TYPE
     OBJECTS     {ruckusSCGEventSeverity,ruckusSCGEventType,ruckusSCGClusterName,ruckusSCGEventCode}
     STATUS  current
     DESCRIPTION
        "Trigger when there is a cluster upload vDP firmware process starts event.
       The event severity, event type, cluster name and event code are enclosed."
		::= { ruckusSCGEventTraps 232 }

  ruckusSCGClusterUploadVDPFirmwareSuccessTrap	NOTIFICATION-TYPE
     OBJECTS     {ruckusSCGEventSeverity,ruckusSCGEventType,ruckusSCGClusterName,ruckusSCGEventCode}
     STATUS  current
     DESCRIPTION
        "Trigger when there is a cluster uploaded vDP firmware successfully event.
       The event severity, event type, cluster name and event code are enclosed."
		::= { ruckusSCGEventTraps 233 }

  ruckusSCGClusterUploadVDPFirmwareFailedTrap	NOTIFICATION-TYPE
     OBJECTS     {ruckusSCGEventSeverity,ruckusSCGEventType,ruckusSCGClusterName,ruckusSCGEventReason,ruckusSCGEventCode}
     STATUS  current
     DESCRIPTION
        "Trigger when there is a cluster failed to upload vDP firmware event.
       The event severity, event type, cluster name, failure reason and event code are enclosed."
		::= { ruckusSCGEventTraps 234 }

  ruckusSCGIpmiVotageTrap	NOTIFICATION-TYPE
     OBJECTS     {ruckusSCGEventSeverity,ruckusSCGEventType,ruckusSCGTemperatureStatus,ruckusSCGEventMacAddr,ruckusSCGEventCode}
     STATUS  current
     DESCRIPTION
        "Trigger when there is baseboard voltage event.
       The event severity, event type, temperature status, SCG node MAC address and event code are enclosed."
		::= { ruckusSCGEventTraps 250 }

  ruckusSCGIpmiTempBBTrap	NOTIFICATION-TYPE
     OBJECTS     {ruckusSCGEventSeverity,ruckusSCGEventType,ruckusSCGTemperatureStatus,ruckusSCGEventMacAddr,ruckusSCGEventCode}
     STATUS  current
     DESCRIPTION
        "Trigger when there is baseboard temperature event.
       The event severity, event type, temperature status, SCG node MAC address and event code are enclosed."
		::= { ruckusSCGEventTraps 251 }

  ruckusSCGIpmiTempFPTrap	NOTIFICATION-TYPE
     OBJECTS     {ruckusSCGEventSeverity,ruckusSCGEventType,ruckusSCGTemperatureStatus,ruckusSCGEventMacAddr,ruckusSCGEventCode}
     STATUS  current
     DESCRIPTION
        "Trigger when there is front panel temperature event.
       The event severity, event type, temperature status, SCG node MAC address and event code are enclosed."
		::= { ruckusSCGEventTraps 252 }

  ruckusSCGIpmiTempIOHTrap	NOTIFICATION-TYPE
     OBJECTS     {ruckusSCGEventSeverity,ruckusSCGEventType,ruckusSCGTemperatureStatus,ruckusSCGEventMacAddr,ruckusSCGEventCode}
     STATUS  current
     DESCRIPTION
        "Trigger when there is chip set temperature event.
       The event severity, event type, temperature status, SCG node MAC address and event code are enclosed."
		::= { ruckusSCGEventTraps 253 }

  ruckusSCGIpmiTempMemPTrap	NOTIFICATION-TYPE
     OBJECTS     {ruckusSCGEventSeverity,ruckusSCGEventType,ruckusSCGProcessorId,ruckusSCGTemperatureStatus,ruckusSCGEventMacAddr,ruckusSCGEventCode}
     STATUS  current
     DESCRIPTION
        "Trigger when there is processor memory temperature event.
       The event severity, event type, processor id, temperature status, SCG node MAC address and event code are enclosed."
		::= { ruckusSCGEventTraps 254 }

  ruckusSCGIpmiTempPSTrap	NOTIFICATION-TYPE
     OBJECTS     {ruckusSCGEventSeverity,ruckusSCGEventType,ruckusSCGPsId,ruckusSCGTemperatureStatus,ruckusSCGEventMacAddr,ruckusSCGEventCode}
     STATUS  current
     DESCRIPTION
        "Trigger when there is power supply temperature event.
       The event severity, event type, SCG node name,power supply id, temperature status, SCG node MAC address and event code are enclosed."
		::= { ruckusSCGEventTraps 255 }

  ruckusSCGIpmiTempPTrap	NOTIFICATION-TYPE
     OBJECTS     {ruckusSCGEventSeverity,ruckusSCGEventType,ruckusSCGProcessorId,ruckusSCGTemperatureStatus,ruckusSCGEventMacAddr,ruckusSCGEventCode}
     STATUS  current
     DESCRIPTION
        "Trigger when there is processor temperature event.
       The event severity, event type, processor id, temperature status, SCG node MAC address and event code are enclosed."
		::= { ruckusSCGEventTraps 256 }

  ruckusSCGIpmiTempHSBPTrap	NOTIFICATION-TYPE
     OBJECTS     {ruckusSCGEventSeverity,ruckusSCGEventType,ruckusSCGTemperatureStatus,ruckusSCGEventMacAddr,ruckusSCGEventCode}
     STATUS  current
     DESCRIPTION
        "Trigger when there is hot swap backplane temperature event.
       The event severity, event type, temperature status, SCG node MAC address and event code are enclosed."
		::= { ruckusSCGEventTraps 257 }

  ruckusSCGIpmiFanTrap	NOTIFICATION-TYPE
     OBJECTS     {ruckusSCGEventSeverity,ruckusSCGEventType,ruckusSCGFanId,ruckusSCGFanStatus,ruckusSCGEventMacAddr,ruckusSCGEventCode}
     STATUS  current
     DESCRIPTION
        "Trigger when there is system fan event.
       The event severity, event type, fan id, fan status, SCG node MAC address and event code are enclosed."
		::= { ruckusSCGEventTraps 258 }

  ruckusSCGIpmiPowerTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is power supply input event.
       The event severity, event type, power supply id,  power supply status, SCG node MAC address and event code are enclosed."
		::= { ruckusSCGEventTraps 259 }

  ruckusSCGIpmiCurrentTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is current power supply output event.
       The event severity, event type, power supply id, power supply status, SCG node MAC address and event code are enclosed."
		::= { ruckusSCGEventTraps 260 }

  ruckusSCGIpmiFanStatusTrap	NOTIFICATION-TYPE
     OBJECTS     {ruckusSCGEventSeverity,ruckusSCGEventType,ruckusSCGFanId,ruckusSCGFanStatus,ruckusSCGEventMacAddr,ruckusSCGEventCode}
     STATUS  current
     DESCRIPTION
        "Trigger when there is fan module event.
       The event severity, event type, fan id, fan status, SCG node MAC address and event code are enclosed."
		::= { ruckusSCGEventTraps 261 }

  ruckusSCGIpmiPsStatusTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is power supply event.
       The event severity, event type, power supply id, power supply status, SCG node MAC address and event code are enclosed."
		::= { ruckusSCGEventTraps 262 }

  ruckusSCGIpmiDrvStatusTrap	NOTIFICATION-TYPE
     OBJECTS     {ruckusSCGEventSeverity,ruckusSCGEventType,ruckusSCGDrvId,ruckusSCGDrvStatus,ruckusSCGEventMacAddr,ruckusSCGEventCode}
     STATUS  current
     DESCRIPTION
        "Trigger when there is disk drive event.
       The event severity, event type, disk drive id, disk drive status, SCG node MAC address and event code are enclosed."
		::= { ruckusSCGEventTraps 263 }

  ruckusSCGIpmiREVotageTrap	NOTIFICATION-TYPE
     OBJECTS     {ruckusSCGEventSeverity,ruckusSCGEventType,ruckusSCGTemperatureStatus,ruckusSCGEventMacAddr,ruckusSCGEventCode}
     STATUS  current
     DESCRIPTION
        "Trigger when there is voltage status recover from abnormal condition event.
       The event severity, event type, temperature status, SCG node MAC address and event code are enclosed."
		::= { ruckusSCGEventTraps 264 }

  ruckusSCGIpmiRETempBBTrap	NOTIFICATION-TYPE
     OBJECTS     {ruckusSCGEventSeverity,ruckusSCGEventType,ruckusSCGTemperatureStatus,ruckusSCGEventMacAddr,ruckusSCGEventCode}
     STATUS  current
     DESCRIPTION
        "Trigger when there is baseboard temperature status recover from abnormal condition event.
       The event severity, event type, temperature status, SCG node MAC address and event code are enclosed."
		::= { ruckusSCGEventTraps 265 }

  ruckusSCGIpmiRETempFPTrap	NOTIFICATION-TYPE
     OBJECTS     {ruckusSCGEventSeverity,ruckusSCGEventType,ruckusSCGTemperatureStatus,ruckusSCGEventMacAddr,ruckusSCGEventCode}
     STATUS  current
     DESCRIPTION
        "Trigger when there is front panel temperature status recover from abnormal condition event.
       The event severity, event type, temperature status, SCG node MAC address and event code are enclosed."
		::= { ruckusSCGEventTraps 266 }

  ruckusSCGIpmiRETempIOHTrap	NOTIFICATION-TYPE
     OBJECTS     {ruckusSCGEventSeverity,ruckusSCGEventType,ruckusSCGTemperatureStatus,ruckusSCGEventMacAddr,ruckusSCGEventCode}
     STATUS  current
     DESCRIPTION
        "Trigger when there is chip set temperature status recover from abnormal condition event.
       The event severity, event type, temperature status, SCG node MAC address and event code are enclosed."
		::= { ruckusSCGEventTraps 267 }

  ruckusSCGIpmiRETempMemPTrap	NOTIFICATION-TYPE
     OBJECTS     {ruckusSCGEventSeverity,ruckusSCGEventType,ruckusSCGProcessorId,ruckusSCGTemperatureStatus,ruckusSCGEventMacAddr,ruckusSCGEventCode}
     STATUS  current
     DESCRIPTION
        "Trigger when there is processor memory temperature status recover from abnormal condition event.
       The event severity, event type, processor id, temperature status, SCG node MAC address and event code are enclosed."
		::= { ruckusSCGEventTraps 268 }

  ruckusSCGIpmiRETempPSTrap	NOTIFICATION-TYPE
     OBJECTS     {ruckusSCGEventSeverity,ruckusSCGEventType,ruckusSCGPsId,ruckusSCGTemperatureStatus,ruckusSCGEventMacAddr,ruckusSCGEventCode}
     STATUS  current
     DESCRIPTION
        "Trigger when there is power supply temperature status recover from abnormal condition event.
       The event severity, event type, SCG node name,power supply id, temperature status, SCG node MAC address and event code are enclosed."
		::= { ruckusSCGEventTraps 269 }

  ruckusSCGIpmiRETempPTrap	NOTIFICATION-TYPE
     OBJECTS     {ruckusSCGEventSeverity,ruckusSCGEventType,ruckusSCGProcessorId,ruckusSCGTemperatureStatus,ruckusSCGEventMacAddr,ruckusSCGEventCode}
     STATUS  current
     DESCRIPTION
        "Trigger when there is processor temperature status recover from abnormal condition event.
       The event severity, event type, processor id, temperature status, SCG node MAC address and event code are enclosed."
		::= { ruckusSCGEventTraps 270 }

  ruckusSCGIpmiRETempHSBPTrap	NOTIFICATION-TYPE
     OBJECTS     {ruckusSCGEventSeverity,ruckusSCGEventType,ruckusSCGTemperatureStatus,ruckusSCGEventMacAddr,ruckusSCGEventCode}
     STATUS  current
     DESCRIPTION
        "Trigger when there is hot swap backplane temperature status recover from abnormal condition event.
       The event severity, event type, temperature status, SCG node MAC address and event code are enclosed."
		::= { ruckusSCGEventTraps 271 }

  ruckusSCGIpmiREFanTrap	NOTIFICATION-TYPE
     OBJECTS     {ruckusSCGEventSeverity,ruckusSCGEventType,ruckusSCGFanId,ruckusSCGFanStatus,ruckusSCGEventMacAddr,ruckusSCGEventCode}
     STATUS  current
     DESCRIPTION
        "Trigger when there is system fan module status recover from abnormal condition.
       The event severity, event type, fan id, fan status, SCG node MAC address and event code are enclosed."
		::= { ruckusSCGEventTraps 272 }

  ruckusSCGIpmiREPowerTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is power supply AC power input status recover from abnormal condition event.
       The event severity, event type, power supply id,  power supply status, SCG node MAC address and event code are enclosed."
		::= { ruckusSCGEventTraps 273 }

  ruckusSCGIpmiRECurrentTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is power supply and the maximum voltage output status recover from abnormal condition event.
       The event severity, event type, power supply id, power supply status, SCG node MAC address and event code are enclosed."
		::= { ruckusSCGEventTraps 274 }

  ruckusSCGIpmiREFanStatusTrap	NOTIFICATION-TYPE
     OBJECTS     {ruckusSCGEventSeverity,ruckusSCGEventType,ruckusSCGFanId,ruckusSCGFanStatus,ruckusSCGEventMacAddr,ruckusSCGEventCode}
     STATUS  current
     DESCRIPTION
        "Trigger when there is fan module status recover from abnormal condition event.
       The event severity, event type, fan id, fan status, SCG node MAC address and event code are enclosed."
		::= { ruckusSCGEventTraps 275 }

  ruckusSCGIpmiREPsStatusTrap	NOTIFICATION-TYPE
     OBJECTS     {ruckusSCGEventSeverity,ruckusSCGEventType,ruckusSCGPsId,ruckusSCGPsStatus,ruckusSCGEventMacAddr,ruckusSCGEventCode}
     STATUS  current
     DESCRIPTION
        "Trigger when there is power supply status recover from abnormal condition event.
       The event severity, event type, power supply id, power supply status, SCG node MAC address and event code are enclosed."
		::= { ruckusSCGEventTraps 276 }

  ruckusSCGIpmiREDrvStatusTrap	NOTIFICATION-TYPE
     OBJECTS     {ruckusSCGEventSeverity,ruckusSCGEventType,ruckusSCGDrvId,ruckusSCGDrvStatus,ruckusSCGEventMacAddr,ruckusSCGEventCode}
     STATUS  current
     DESCRIPTION
        "Trigger when there is disk drive status recover from abnormal condition event.
       The event severity, event type, disk drive id, disk drive status, SCG node MAC address and event code are enclosed."
		::= { ruckusSCGEventTraps 277 }

  ruckusSCGFtpTransferErrorTrap	NOTIFICATION-TYPE
     OBJECTS     {ruckusSCGEventSeverity,ruckusSCGEventType,ruckusSCGFtpIp,ruckusSCGFtpPort,ruckusSCGFileName,ruckusSCGEventMacAddr,ruckusSCGEventCode}
     STATUS  current
     DESCRIPTION
        "Trigger when there is FTP transfer error event.
       The event severity, event type, FTP server IP address, FTP server port, file name, SCG node MAC address and event code are enclosed."
		::= { ruckusSCGEventTraps 280 }

  ruckusSCGSystemLBSConnectSuccessTrap	NOTIFICATION-TYPE
     OBJECTS     {ruckusSCGEventSeverity,ruckusSCGEventType,ruckusSCGEventMacAddr,ruckusSCGEventNodeMgmtIp,ruckusSCGLBSURL,ruckusSCGLBSPort,ruckusSCGEventCode}
     STATUS  current
     DESCRIPTION
        "Trigger when there is SCG successfully connect to LS event.
       The event severity, event type, SCG node MAC address, management IP address, LBS server URL, LBS port and event code are enclosed."
		::= { ruckusSCGEventTraps 290 }

  ruckusSCGSystemLBSNoResponseTrap	NOTIFICATION-TYPE
     OBJECTS     {ruckusSCGEventSeverity,ruckusSCGEventType,ruckusSCGEventMacAddr,ruckusSCGEventNodeMgmtIp,ruckusSCGLBSURL,ruckusSCGLBSPort,ruckusSCGEventCode}
     STATUS  current
     DESCRIPTION
        "Trigger when there is SCG connect to LS no response event.
       The event severity, event type, SCG node MAC address, management IP address, LBS server URL, LBS port and event code are enclosed."
		::= { ruckusSCGEventTraps 291 }

  ruckusSCGSystemLBSAuthFailedTrap	NOTIFICATION-TYPE
     OBJECTS     {ruckusSCGEventSeverity,ruckusSCGEventType,ruckusSCGEventMacAddr,ruckusSCGEventNodeMgmtIp,ruckusSCGLBSURL,ruckusSCGLBSPort,ruckusSCGEventCode}
     STATUS  current
     DESCRIPTION
        "Trigger when there is SCG connect LS authentication failure event.
       The event severity, event type, SCG node MAC address, management IP address, LBS server URL, LBS port and event code are enclosed."
		::= { ruckusSCGEventTraps 292 }

  ruckusSCGSystemLBSConnectFailedTrap	NOTIFICATION-TYPE
     OBJECTS     {ruckusSCGEventSeverity,ruckusSCGEventType,ruckusSCGEventMacAddr,ruckusSCGEventNodeMgmtIp,ruckusSCGLBSURL,ruckusSCGLBSPort,ruckusSCGEventCode}
     STATUS  current
     DESCRIPTION
        "Trigger when there is SCG failed connect to LS event.
       The event severity, event type, SCG node MAC address, management IP address, LBS server URL, LBS port and event code are enclosed."
		::= { ruckusSCGEventTraps 293 }

  ruckusSCGProcessRestartTrap	NOTIFICATION-TYPE
     OBJECTS     {ruckusSCGEventSeverity,ruckusSCGEventType,ruckusSCGProcessName,ruckusSCGEventMacAddr,ruckusSCGEventNodeMgmtIp,ruckusSCGEventCode}
     STATUS  current
     DESCRIPTION
        "Trigger when there is process restart event.
       The event severity, event type, process name, SCG node MAC address, management IP address and event code are enclosed."
		::= { ruckusSCGEventTraps 300 }

  ruckusSCGServiceUnavailableTrap	NOTIFICATION-TYPE
     OBJECTS     {ruckusSCGEventSeverity,ruckusSCGEventType,ruckusSCGProcessName,ruckusSCGEventMacAddr,ruckusSCGEventNodeMgmtIp,ruckusSCGEventCode}
     STATUS  current
     DESCRIPTION
        "Trigger when there is service unavailable event.
       The event severity, event type, process name, SCG node MAC address, management IP address and event code are enclosed."
		::= { ruckusSCGEventTraps 301 }

  ruckusSCGKeepAliveFailureTrap	NOTIFICATION-TYPE
     OBJECTS     {ruckusSCGEventSeverity,ruckusSCGEventType,ruckusSCGSrcProcess,ruckusSCGProcessName,ruckusSCGEventMacAddr,ruckusSCGEventNodeMgmtIp,ruckusSCGEventCode}
     STATUS  current
     DESCRIPTION
        "Trigger when there is service keep alive failure event.
       The event severity, event type, source process name, process name, SCG node MAC address, management IP address and event code are enclosed."
		::= { ruckusSCGEventTraps 302 }

  ruckusSCGResourceUnavailableTrap	NOTIFICATION-TYPE
     OBJECTS     {ruckusSCGEventSeverity,ruckusSCGEventType,ruckusSCGSrcProcess,ruckusSCGEventMacAddr,ruckusSCGEventNodeMgmtIp,ruckusSCGEventReason,ruckusSCGEventCode}
     STATUS  current
     DESCRIPTION
        "Trigger when there is resource unavailable event.
       The event severity, event type, source process name, SCG node MAC address, management IP address, reason and event code are enclosed."
		::= { ruckusSCGEventTraps 304 }

  ruckusSCGSmfRegFailedTrap	NOTIFICATION-TYPE
     OBJECTS     {ruckusSCGEventSeverity,ruckusSCGEventType,ruckusSCGSrcProcess,ruckusSCGEventMacAddr,ruckusSCGEventNodeMgmtIp,ruckusSCGEventCode}
     STATUS  current
     DESCRIPTION
        "Trigger when there is SMF registration failed event.
       The event severity, event type, source process name, SCG node MAC address, management IP address and event code are enclosed."
		::= { ruckusSCGEventTraps 305 }

  ruckusSCGHipFailoverTrap	NOTIFICATION-TYPE
     OBJECTS     {ruckusSCGEventSeverity,ruckusSCGEventType,ruckusSCGSrcProcess,ruckusSCGEventMacAddr,ruckusSCGEventNodeMgmtIp,ruckusSCGEventCode}
     STATUS  current
     DESCRIPTION
        "Trigger when there is HIP failover event.
       The event severity, event type, source process name, SCG node MAC address, management IP address and event code are enclosed."
		::= { ruckusSCGEventTraps 306 }

  ruckusSCGConfUpdFailedTrap	NOTIFICATION-TYPE
     OBJECTS     {ruckusSCGEventSeverity,ruckusSCGEventType,ruckusSCGProcessName,ruckusSCGEventMacAddr,ruckusSCGEventNodeMgmtIp,ruckusSCGEventReason,ruckusSCGEventCode}
     STATUS  current
     DESCRIPTION
        "Trigger when there is configuration update failed event.
       The event severity, event type, process name, SCG node MAC address, management IP address, failure reason and event code are enclosed."
		::= { ruckusSCGEventTraps 307 }

  ruckusSCGConfRcvFailedTrap	NOTIFICATION-TYPE
     OBJECTS     {ruckusSCGEventSeverity,ruckusSCGEventType,ruckusSCGEventMacAddr,ruckusSCGEventNodeMgmtIp,ruckusSCGEventReason,ruckusSCGEventCode}
     STATUS  current
     DESCRIPTION
        "Trigger when there is SCG configuration receive failed event.
       The event severity, event type, SCG node MAC address, management IP address, failure reason and event code are enclosed."
		::= { ruckusSCGEventTraps 308 }

  ruckusSCGLostCnxnToDbladeTrap	NOTIFICATION-TYPE
     OBJECTS     {ruckusSCGEventSeverity,ruckusSCGEventType,ruckusSCGEventCtrlIP,ruckusSCGDPIP,ruckusSCGEventMacAddr,ruckusSCGEventNodeMgmtIp,ruckusSCGEventCode}
     STATUS  current
     DESCRIPTION
        "Trigger when there is lost connection to DP event.
       The event severity, event type, SCG control IP address, DP IP address, SCG node MAC address, management IP address and event code are enclosed."
		::= { ruckusSCGEventTraps 309 }

  ruckusSCGGgsnRestartedTrap	NOTIFICATION-TYPE
     OBJECTS     {ruckusSCGEventSeverity,ruckusSCGEventType,ruckusSCGGgsnIp,ruckusSCGGtpcIp,ruckusSCGEventMacAddr,ruckusSCGEventNodeMgmtIp,ruckusSCGEventCode}
     STATUS  current
     DESCRIPTION
        "Trigger when there is GGSN restarted event.
       The event severity, event type, GGSN IP address, GTP IP address, SCG node MAC address, management IP address and event code are enclosed."
		::= { ruckusSCGEventTraps 310 }

  ruckusSCGGgsnNotReachableTrap	NOTIFICATION-TYPE
     OBJECTS     {ruckusSCGEventSeverity,ruckusSCGEventType,ruckusSCGGgsnIp,ruckusSCGGtpcIp,ruckusSCGEventMacAddr,ruckusSCGEventCode}
     STATUS  current
     DESCRIPTION
        "Trigger when there is GGSN not reachable event.
       The event severity, event type, GGSN IP address, GTP IP address, SCG node MAC address and event code are enclosed."
		::= { ruckusSCGEventTraps 311 }

  ruckusSCGGgsnNotResolvedTrap	NOTIFICATION-TYPE
     OBJECTS     {ruckusSCGEventSeverity,ruckusSCGEventType,ruckusSCGApn,ruckusSCGUEImsi,ruckusSCGUEMsisdn,ruckusSCGEventMacAddr,ruckusSCGEventCode}
     STATUS  current
     DESCRIPTION
        "Trigger when there is GGSN not resolved event.
       The event severity, event type, APN, UE IMSI, UE msisdn, SCG node MAC address and event code are enclosed."
		::= { ruckusSCGEventTraps 312 }

  ruckusSCGUnknownUETrap	NOTIFICATION-TYPE
     OBJECTS     {ruckusSCGEventSeverity,ruckusSCGEventType,ruckusSCGEventClientMacAddr,ruckusSCGUEMsisdn,ruckusSCGEventMacAddr,ruckusSCGEventNodeMgmtIp,ruckusSCGEventCode}
     STATUS  current
     DESCRIPTION
        "Trigger when there is unknown UE event.
       The event severity, event type, client MAC address, UE msisdn, SCG node MAC address, management IP address and event code are enclosed."
		::= { ruckusSCGEventTraps 313 }

  ruckusSCGAuthSrvrNotReachableTrap	NOTIFICATION-TYPE
     OBJECTS     {ruckusSCGEventSeverity,ruckusSCGEventType,ruckusSCGAuthSrvrIp,ruckusSCGRadProxyIp,ruckusSCGEventMacAddr,ruckusSCGEventNodeMgmtIp,ruckusSCGEventCode}
     STATUS  current
     DESCRIPTION
        "Trigger when there is authentication server not reachable event.
       The event severity, event type, authentication server IP address, radius proxy IP address, SCG node MAC address, management IP address and event code are enclosed."
		::= { ruckusSCGEventTraps 314 }

  ruckusSCGAccSrvrNotReachableTrap	NOTIFICATION-TYPE
     OBJECTS     {ruckusSCGEventSeverity,ruckusSCGEventType,ruckusSCGAccSrvrIp,ruckusSCGRadProxyIp,ruckusSCGEventMacAddr,ruckusSCGEventNodeMgmtIp,ruckusSCGEventCode}
     STATUS  current
     DESCRIPTION
        "Trigger when there is accounting server not reachable event.
       The event severity, event type, accounting server IP address, radius proxy IP address, SCG node MAC address, management IP address and event code are enclosed."
		::= { ruckusSCGEventTraps 315 }

  ruckusSCGUnknownRealmTrap	NOTIFICATION-TYPE
     OBJECTS     {ruckusSCGEventSeverity,ruckusSCGEventType,ruckusSCGRealm,ruckusSCGEventMacAddr,ruckusSCGEventCode}
     STATUS  current
     DESCRIPTION
        "Trigger when there is unknown realm.
       The event severity, event type, realm name, SCG node MAC address and event code are enclosed."
		::= { ruckusSCGEventTraps 316 }

  ruckusSCGAuthFailedNonPermanentIDTrap	NOTIFICATION-TYPE
     OBJECTS     {ruckusSCGEventSeverity,ruckusSCGEventType,ruckusSCGUEImsi,ruckusSCGUEMsisdn,ruckusSCGEventMacAddr,ruckusSCGEventNodeMgmtIp,ruckusSCGEventReason,ruckusSCGEventCode}
     STATUS  current
     DESCRIPTION
        "Trigger when there is non-permanent ID authentication failed event.
       The event severity, event type, UE IMSI, UE msisdn, SCG node MAC address, management IP address, failure reason and event code are enclosed."
		::= { ruckusSCGEventTraps 317 }

  ruckusSCGCnxnToCgfFailedTrap	NOTIFICATION-TYPE
     OBJECTS     {ruckusSCGEventSeverity,ruckusSCGEventType,ruckusSCGCgfSrvrIp,ruckusSCGRadSrvrIp,ruckusSCGEventMacAddr,ruckusSCGEventNodeMgmtIp,ruckusSCGEventCode}
     STATUS  current
     DESCRIPTION
        "Trigger when there is connection to CGF failed.
       The event severity, event type, CGF sever IP address, radius server IP address, SCG node MAC address, management IP address and event code are enclosed."
		::= { ruckusSCGEventTraps 318 }

  ruckusSCGCdrTransferFailedTrap	NOTIFICATION-TYPE
     OBJECTS     {ruckusSCGEventSeverity,ruckusSCGEventType,ruckusSCGCgfSrvrIp,ruckusSCGRadSrvrIp,ruckusSCGEventMacAddr,ruckusSCGEventNodeMgmtIp,ruckusSCGEventCode}
     STATUS  current
     DESCRIPTION
        "Trigger when there is CDR transfer failed event.
       The event severity, event type, CGF sever IP address, radius server IP address, SCG node MAC address, management IP address and event code are enclosed."
		::= { ruckusSCGEventTraps 319 }

  ruckusSCGCdrGenerateFailedTrap	NOTIFICATION-TYPE
     OBJECTS     {ruckusSCGEventSeverity,ruckusSCGEventType,ruckusSCGRadSrvrIp,ruckusSCGEventMacAddr,ruckusSCGEventNodeMgmtIp,ruckusSCGEventCode}
     STATUS  current
     DESCRIPTION
        "Trigger when there is CDR generation failed event.
       The event severity, event type, radius server IP address,SCG node MAC address, management IP address and event code are enclosed."
		::= { ruckusSCGEventTraps 320 }

  ruckusSCGDestNotRecheableTrap	NOTIFICATION-TYPE
     OBJECTS     {ruckusSCGEventSeverity,ruckusSCGEventType,ruckusSCGPointCode,ruckusSCGEventMacAddr,ruckusSCGEventCode}
     STATUS  current
     DESCRIPTION
        "Trigger when there is destination not reachable.
       The event severity, event type, point code, SCG node MAC address and event code are enclosed."
		::= { ruckusSCGEventTraps 321 }

  ruckusSCGAppServerDownTrap	NOTIFICATION-TYPE
     OBJECTS     {ruckusSCGEventSeverity,ruckusSCGEventType,ruckusSCGRoutingContext,ruckusSCGPointCode,ruckusSCGSSN,ruckusSCGEventMacAddr,ruckusSCGEventCode}
     STATUS  current
     DESCRIPTION
        "Trigger when there is application server down event.
       The event severity, event type, routing context, local point code, local SSN, SCG node MAC address and event code are enclosed."
		::= { ruckusSCGEventTraps 324 }

  ruckusSCGAppServerInactiveTrap	NOTIFICATION-TYPE
     OBJECTS     {ruckusSCGEventSeverity,ruckusSCGEventType,ruckusSCGRoutingContext,ruckusSCGPointCode,ruckusSCGSSN,ruckusSCGEventMacAddr,ruckusSCGEventCode}
     STATUS  current
     DESCRIPTION
        "Trigger when there is application server inactive event.
       The event severity, event type, routing context, local point code, local SSN, SCG node MAC address and event code are enclosed."
		::= { ruckusSCGEventTraps 325 }

  ruckusSCGAssocCantStartTrap	NOTIFICATION-TYPE
     OBJECTS     {ruckusSCGEventSeverity,ruckusSCGEventType,ruckusSCGSrcIP,ruckusSCGSrcPort,ruckusSCGDestIP,ruckusSCGDestPort,ruckusSCGEventMacAddr,ruckusSCGEventCode}
     STATUS  current
     DESCRIPTION
        "Trigger when there is association can not start event.
       The event severity, event type, source IP address, source port, destination IP address, destination port, SCG node MAC address and event code are enclosed."
		::= { ruckusSCGEventTraps 326 }

  ruckusSCGAssocDownTrap	NOTIFICATION-TYPE
     OBJECTS     {ruckusSCGEventSeverity,ruckusSCGEventType,ruckusSCGSrcIP,ruckusSCGSrcPort,ruckusSCGDestIP,ruckusSCGDestPort,ruckusSCGEventMacAddr,ruckusSCGEventCode}
     STATUS  current
     DESCRIPTION
        "Trigger when there is association down event.
       The event severity, event type, source IP address, source port, destination IP address, destination port, SCG node MAC address and event code are enclosed."
		::= { ruckusSCGEventTraps 327 }

  ruckusSCGOutboundRoutingFailedTrap	NOTIFICATION-TYPE
     OBJECTS     {ruckusSCGEventSeverity,ruckusSCGEventType,ruckusSCGOperation,ruckusSCGUEImsi,ruckusSCGHlrInstance,ruckusSCGEventMacAddr,ruckusSCGEventCode}
     STATUS  current
     DESCRIPTION
        "Trigger when there is outbound routing failure event.
       The event severity, event type, route operation, UE IMSI, HLR instance, SCG node MAC address and event code are enclosed."
		::= { ruckusSCGEventTraps 328 }

  ruckusSCGDidAllocationFailureTrap	NOTIFICATION-TYPE
     OBJECTS     {ruckusSCGEventSeverity,ruckusSCGEventType,ruckusSCGEventMacAddr,ruckusSCGEventCode}
     STATUS  current
     DESCRIPTION
        "Trigger when there is did allocation failure event.
		 The event severity, event type, node MAC address and event code are enclosed."
		::= { ruckusSCGEventTraps 329 }

  ruckusSCGPdnGwUnresolvedTrap	NOTIFICATION-TYPE
     OBJECTS     {ruckusSCGEventSeverity,ruckusSCGEventType,ruckusSCGSrcProcess,ruckusSCGApn,ruckusSCGUEImsi,ruckusSCGUEMsisdn,ruckusSCGEventMacAddr,ruckusSCGEventNodeMgmtIp,ruckusSCGEventCode}
     STATUS  current
     DESCRIPTION
        "Trigger when there is PDN gateway could not be resolved.
       The event severity, event type, source process name, APN, UE IMSI, UE msisdn, SCG node MAC address, management IP address and event code are enclosed."
		::= { ruckusSCGEventTraps 331 }

  ruckusSCGPdnGwVersionUnsupportedTrap	NOTIFICATION-TYPE
     OBJECTS     {ruckusSCGEventSeverity,ruckusSCGEventType,ruckusSCGSrcProcess,ruckusSCGPgwIp,ruckusSCGEventMacAddr,ruckusSCGEventNodeMgmtIp,ruckusSCGEventCode}
     STATUS  current
     DESCRIPTION
        "Trigger when there is PDN gateway version not supported event.
		 The event severity, event type, source process name, PGW IP adress, SCG node MAC address, management IP address and event code are enclosed."
		::= { ruckusSCGEventTraps 332 }

  ruckusSCGPdnGwAssociationDownTrap	NOTIFICATION-TYPE
     OBJECTS     {ruckusSCGEventSeverity,ruckusSCGEventType,ruckusSCGSrcProcess,ruckusSCGPgwIp,ruckusSCGEventMacAddr,ruckusSCGEventNodeMgmtIp,ruckusSCGEventCode}
     STATUS  current
     DESCRIPTION
        "Trigger when there is association PDN gateway down.
       The event severity, event type, source process name, PGW IP address, SCG node MAC address, management IP address and event code are enclosed."
		::= { ruckusSCGEventTraps 333 }

  ruckusSCGCreateSessionResponseFailedTrap	NOTIFICATION-TYPE
     OBJECTS     {ruckusSCGEventSeverity,ruckusSCGEventType,ruckusSCGSrcProcess,ruckusSCGPgwIp,ruckusSCGUEImsi,ruckusSCGRealm,ruckusSCGEventMacAddr,ruckusSCGEventNodeMgmtIp,ruckusSCGEventReason,ruckusSCGEventCode}
     STATUS  current
     DESCRIPTION
        "Trigger when there is create session response failed event.
       The event severity, event type, source process name, PGW IP address, UE IMSI, realm name, SCG node MAC address, management IP address, failure reason and event code are enclosed."
		::= { ruckusSCGEventTraps 334 }

  ruckusSCGDecodeFailedTrap	NOTIFICATION-TYPE
     OBJECTS     {ruckusSCGEventSeverity,ruckusSCGEventType,ruckusSCGSrcProcess,ruckusSCGPgwIp,ruckusSCGEventMacAddr,ruckusSCGEventNodeMgmtIp,ruckusSCGEventCode}
     STATUS  current
     DESCRIPTION
        "Trigger when there is decode failed event.
	    The event severity, event type, source process name, PGW IP address, SCG node MAC address, management IP address and event code are enclosed."
			::= { ruckusSCGEventTraps 335 }

  ruckusSCGModifyBearerResponseFailedTrap	NOTIFICATION-TYPE
     OBJECTS	{ruckusSCGEventSeverity,ruckusSCGEventType,ruckusSCGSrcProcess,ruckusSCGPgwIp,ruckusSCGUEImsi,ruckusSCGRealm,ruckusSCGEventMacAddr,ruckusSCGEventNodeMgmtIp,ruckusSCGEventReason,ruckusSCGEventCode}
     STATUS  current
     DESCRIPTION
        "Trigger when there is modify bearer response failed event.
       The event severity, event type, source process name, PGW IP address, UE IMSI, realm name, SCG node MAC address, management IP address, failure reason and event code are enclosed."
			::= { ruckusSCGEventTraps 336 }

  ruckusSCGDeleteSessionResponseFailedTrap	NOTIFICATION-TYPE
     OBJECTS     {ruckusSCGEventSeverity,ruckusSCGEventType,ruckusSCGSrcProcess,ruckusSCGPgwIp,ruckusSCGUEImsi,ruckusSCGRealm,ruckusSCGEventMacAddr,ruckusSCGEventNodeMgmtIp,ruckusSCGEventReason,ruckusSCGEventCode}
     STATUS  current
     DESCRIPTION
        "Trigger when there is delete session response failed event.
       The event severity, event type, source process name, PGW IP address, UE IMSI, realm name, SCG node MAC address, management IP address, failure reason and event code are enclosed."
			::= { ruckusSCGEventTraps 337 }

  ruckusSCGDeleteBearerRequestFailedTrap	NOTIFICATION-TYPE
     OBJECTS     {ruckusSCGEventSeverity,ruckusSCGEventType,ruckusSCGSrcProcess,ruckusSCGPgwIp,ruckusSCGRealm,ruckusSCGEventMacAddr,ruckusSCGEventNodeMgmtIp,ruckusSCGEventReason,ruckusSCGEventCode}
     STATUS  current
     DESCRIPTION
        "Trigger when there is delete bearer request failed event.
        The event severity, event type, source process name, PGW IP address, realm name, SCG node MAC address, management IP address, failure reason and event code are enclosed."
			::= { ruckusSCGEventTraps 338 }

  ruckusSCGUpdateBearerRequestFailedTrap	NOTIFICATION-TYPE
     OBJECTS     {ruckusSCGEventSeverity,ruckusSCGEventType,ruckusSCGSrcProcess,ruckusSCGPgwIp,ruckusSCGRealm,ruckusSCGEventMacAddr,ruckusSCGEventNodeMgmtIp,ruckusSCGEventReason,ruckusSCGEventCode}
     STATUS  current
     DESCRIPTION
        "Trigger when there is update bearer request failed event.
        The event severity, event type, source process name, PGW IP address, realm name, SCG node MAC address, management IP address, failure reason and event code are enclosed."
		::= { ruckusSCGEventTraps 339 }

  ruckusSCGCgfServerNotConfiguredTrap	NOTIFICATION-TYPE
     OBJECTS     {ruckusSCGEventSeverity,ruckusSCGEventType,ruckusSCGCgfSrvrIp,ruckusSCGGgsnIp,ruckusSCGEventMacAddr,ruckusSCGEventNodeMgmtIp,ruckusSCGEventCode}
     STATUS  current
     DESCRIPTION
        "Trigger when there is CGF server IP received from GGSN or PDN gateway not configured event.
       The event severity, event type, CGF sever IP address, GGSN IP address, SCG node MAC address, management IP address and event code are enclosed."
		::= { ruckusSCGEventTraps 340 }

  ruckusSCGTtgSessionCriticalThresholdTrap	NOTIFICATION-TYPE
     OBJECTS	{ruckusSCGEventSeverity,ruckusSCGEventType,ruckusSCGEventMacAddr,ruckusSCGEventCode}
     STATUS  current
     DESCRIPTION
        "Trigger when there is TTG session critical threshold event.
       The event severity, event type, SCG node MAC address and event code are enclosed."
		::= { ruckusSCGEventTraps 342 }

  ruckusSCGTtgSessionLicenseInsufficientTrap	NOTIFICATION-TYPE
     OBJECTS     {ruckusSCGEventSeverity,ruckusSCGEventType,ruckusSCGEventMacAddr,ruckusSCGEventCode}
     STATUS  current
     DESCRIPTION
        "Trigger when there is TTG session license exhausted event.
       The event severity, event type, SCG node MAC address and event code are enclosed."
		::= { ruckusSCGEventTraps 343 }

  ruckusSCGAPAcctMsgMandatoryPrmMissingTrap	NOTIFICATION-TYPE
     OBJECTS     {ruckusSCGEventSeverity,ruckusSCGEventType,ruckusSCGSrcProcess,ruckusSCGEventAPIP,ruckusSCGUserName,ruckusSCGEventMacAddr,ruckusSCGEventNodeMgmtIp,ruckusSCGEventCode,ruckusSCGEventAPIPv6}
     STATUS  current
     DESCRIPTION
        "Trigger when there is AP accounting message mandatory parameter missing event.
       The event severity, event type, source process name,AP IP address, user name, SCG node MAC address, management IP address, event code and AP IPv6 address are enclosed."
		::= { ruckusSCGEventTraps 344 }

  ruckusSCGAcctUnknownRealmTrap	NOTIFICATION-TYPE
     OBJECTS     {ruckusSCGEventSeverity,ruckusSCGEventType,ruckusSCGSrcProcess,ruckusSCGEventAPIP,ruckusSCGUserName,ruckusSCGEventMacAddr,ruckusSCGEventNodeMgmtIp,ruckusSCGEventCode,ruckusSCGEventAPIPv6}
     STATUS  current
     DESCRIPTION
        "Trigger when there is unknown realm accounting event.
       The event severity, event type, source process name, AP IP address,user name, SCG node MAC address, management IP address, event code and AP IPv6 address are enclosed."
		::= { ruckusSCGEventTraps 345 }

  ruckusSCGAPAcctMsgDecodeFailedTrap	NOTIFICATION-TYPE
     OBJECTS     {ruckusSCGEventSeverity,ruckusSCGEventType,ruckusSCGSrcProcess,ruckusSCGEventAPIP,ruckusSCGEventMacAddr,ruckusSCGEventNodeMgmtIp,ruckusSCGEventCode,ruckusSCGEventAPIPv6}
     STATUS  current
     DESCRIPTION
        "Trigger when there is AP accounting message decode failed event.
       The event severity, event type, source process name, AP IP address, SCG node MAC address, management IP address, event code and AP IPv6 address are enclosed."
		::= { ruckusSCGEventTraps 346 }

  ruckusSCGAPAcctRespWhileInvalidConfigTrap	NOTIFICATION-TYPE
     OBJECTS     {ruckusSCGEventSeverity,ruckusSCGEventType,ruckusSCGSrcProcess,ruckusSCGEventAPIP,ruckusSCGUserName,ruckusSCGEventMacAddr,ruckusSCGEventNodeMgmtIp,ruckusSCGEventCode,ruckusSCGEventAPIPv6}
     STATUS  current
     DESCRIPTION
        "Trigger when there is SCG sends response to AP accounting message while configuration is incorrect in SCG to forward received message or to generate CDR event.
       The event severity, event type, source process name, AP IP address, user Name, SCG node MAC address, management IP address, event code and AP IPv6 address are enclosed."
		::= { ruckusSCGEventTraps 347 }

  ruckusSCGAPAcctMsgDropNoAcctStartMsgTrap	NOTIFICATION-TYPE
     OBJECTS     {ruckusSCGEventSeverity,ruckusSCGEventType,ruckusSCGSrcProcess,ruckusSCGEventAPIP,ruckusSCGUserName,ruckusSCGEventMacAddr,ruckusSCGEventNodeMgmtIp,ruckusSCGEventCode,ruckusSCGEventAPIPv6}
     STATUS  current
     DESCRIPTION
        "Trigger when there is accounting message from AP dropped Acct Interim/Stop message as Account Start no received from AP event.
       The event severity, event type, source process name, AP IP address, user Name, SCG node MAC address, management IP address, event code and AP IPv6 address are enclosed."
		::= { ruckusSCGEventTraps 348 }

  ruckusSCGUnauthorizedCoaDmMessageDroppedTrap	NOTIFICATION-TYPE
     OBJECTS     {ruckusSCGEventSeverity,ruckusSCGEventType,ruckusSCGSrcProcess,ruckusSCGRadSrvrIp,ruckusSCGEventMacAddr,ruckusSCGEventNodeMgmtIp,ruckusSCGEventCode}
     STATUS  current
     DESCRIPTION
        "Trigger when there is received COA/DM from unauthorized AAA server event.
		 The event severity, event type, source process name, AAA server IP address, SCG node MAC address, management IP address and event code are enclosed."
		::= { ruckusSCGEventTraps 349 }

  ruckusSCGConnectedToDbladeTrap	NOTIFICATION-TYPE
     OBJECTS     {ruckusSCGEventSeverity,ruckusSCGEventType,ruckusSCGEventCtrlIP,ruckusSCGDPIP,ruckusSCGEventMacAddr,ruckusSCGEventNodeMgmtIp,ruckusSCGEventCode}
     STATUS  current
     DESCRIPTION
        "Trigger when there is successful connection to DP event.
       The event severity, event type, SCG control IP address, DP IP address, SCG node MAC address, management IP address and event code are enclosed."
		::= { ruckusSCGEventTraps 350 }

  ruckusSCGDestAvailableTrap	NOTIFICATION-TYPE
     OBJECTS     {ruckusSCGEventSeverity,ruckusSCGEventType,ruckusSCGPointCode,ruckusSCGEventMacAddr,ruckusSCGEventCode}
     STATUS  current
     DESCRIPTION
        "Trigger when there is destination available event.
       The event severity, event type, point code, SCG node MAC address and event code are enclosed."
		::= { ruckusSCGEventTraps 351 }

  ruckusSCGAppServerActiveTrap	NOTIFICATION-TYPE
     OBJECTS     {ruckusSCGEventSeverity,ruckusSCGEventType,ruckusSCGRoutingContext,ruckusSCGPointCode,ruckusSCGSSN,ruckusSCGEventMacAddr,ruckusSCGEventCode}
     STATUS  current
     DESCRIPTION
        "Trigger when there is application server active event.
       The event severity, event type, routing context, local point code, local SSN, SCG node MAC address and event code are enclosed."
		::= { ruckusSCGEventTraps 352 }

  ruckusSCGAssocUpTrap	NOTIFICATION-TYPE
     OBJECTS     {ruckusSCGEventSeverity,ruckusSCGEventType,ruckusSCGSrcIP,ruckusSCGSrcPort,ruckusSCGDestIP,ruckusSCGDestPort,ruckusSCGEventMacAddr,ruckusSCGEventCode}
     STATUS  current
     DESCRIPTION
        "Trigger when there is association up event.
       The event severity, event type, source IP address, source port, destination IP address, destination port, SCG node MAC address and event code are enclosed."
		::= { ruckusSCGEventTraps 353 }

  ruckusSCGSessUpdatedAtDbladeTrap	NOTIFICATION-TYPE
     OBJECTS     {ruckusSCGEventSeverity,ruckusSCGEventType,ruckusSCGEventCtrlIP,ruckusSCGDPIP,ruckusSCGUEImsi,ruckusSCGUEMsisdn,ruckusSCGEventMacAddr,ruckusSCGEventNodeMgmtIp,ruckusSCGEventCode}
     STATUS  current
     DESCRIPTION
        "Trigger when there is session updates the request (C-D-SESS-UPD-REQ) successfully event.
       The event severity, event type, SCG control IP address, SCG DP IP address, UE IMSI, UE msisdn, SCG node MAC address, management IP address and event code are enclosed."
		::= { ruckusSCGEventTraps 354 }

  ruckusSCGSessUpdateErrAtDbladeTrap  NOTIFICATION-TYPE
     OBJECTS     {ruckusSCGEventSeverity,ruckusSCGEventType,ruckusSCGEventCtrlIP,ruckusSCGDPIP,ruckusSCGUEImsi,ruckusSCGUEMsisdn,ruckusSCGEventMacAddr,ruckusSCGEventNodeMgmtIp,ruckusSCGEventCode}
     STATUS  current
     DESCRIPTION
        "Trigger when there is session updates the request (C-D-SESS-UPD-REQ) failed event.
       The event severity, event type, SCG control IP address, SCG DP IP address, UE IMSI, UE msisdn, SCG node MAC address, management IP address and event code are enclosed."
		::= { ruckusSCGEventTraps 355 }

  ruckusSCGSessDeletedAtDbladeTrap  NOTIFICATION-TYPE
     OBJECTS     {ruckusSCGEventSeverity,ruckusSCGEventType,ruckusSCGEventCtrlIP,ruckusSCGDPIP,ruckusSCGUEImsi,ruckusSCGUEMsisdn,ruckusSCGEventMacAddr,ruckusSCGEventNodeMgmtIp,ruckusSCGEventCode}
     STATUS  current
     DESCRIPTION
        "Trigger when there is session deletes request (C-D-SESS-DEL-REQ) successfully event.
       The event severity, event type, SCG control IP address, SCG DP IP address, UE IMSI, UE msisdn, SCG node MAC address, management IP address and event code are enclosed."
		::= { ruckusSCGEventTraps 356 }

  ruckusSCGSessDeleteErrAtDbladeTrap  NOTIFICATION-TYPE
     OBJECTS     {ruckusSCGEventSeverity,ruckusSCGEventType,ruckusSCGEventCtrlIP,ruckusSCGDPIP,ruckusSCGUEImsi,ruckusSCGUEMsisdn,ruckusSCGEventMacAddr,ruckusSCGEventNodeMgmtIp,ruckusSCGEventCode}
     STATUS  current
     DESCRIPTION
        "Trigger when there is session deletes request (C-D-SESS-DEL-REQ) failed event.
       The event severity, event type, SCG control IP address, SCG DP IP address, UE IMSI, UE msisdn, SCG node MAC address, management IP address and event code are enclosed."
		::= { ruckusSCGEventTraps 357 }

  ruckusSCGLicenseSyncSuccessTrap  NOTIFICATION-TYPE
     OBJECTS     {ruckusSCGEventSeverity,ruckusSCGEventType,ruckusSCGEventNodeName,ruckusSCGLicenseServerName,ruckusSCGEventCode}
     STATUS      current
     DESCRIPTION
        "Trigger when there is license data syncs up with license server successfully event.
       The event severity, event type, node name, license server name and event code are enclosed."
		::= { ruckusSCGEventTraps 358 }

  ruckusSCGLicenseSyncFailedTrap  NOTIFICATION-TYPE
     OBJECTS     {ruckusSCGEventSeverity,ruckusSCGEventType,ruckusSCGEventNodeName,ruckusSCGLicenseServerName,ruckusSCGEventCode}
     STATUS      current
     DESCRIPTION
        "Trigger when there is license data syncs up with license server failed event.
       The event severity, event type, node name, license server name and event code are enclosed."
		::= { ruckusSCGEventTraps 359 }

  ruckusSCGLicenseImportSuccessTrap  NOTIFICATION-TYPE
     OBJECTS     {ruckusSCGEventSeverity,ruckusSCGEventType,ruckusSCGEventNodeName,ruckusSCGEventCode}
     STATUS      current
     DESCRIPTION
        "Trigger when there is license data import successfully event.
       The event severity, event type, node name and event code are enclosed."
		::= { ruckusSCGEventTraps 360 }

  ruckusSCGLicenseImportFailedTrap  NOTIFICATION-TYPE
     OBJECTS     {ruckusSCGEventSeverity,ruckusSCGEventType,ruckusSCGEventNodeName,ruckusSCGEventCode}
     STATUS      current
     DESCRIPTION
        "Trigger when there is license data import failed event.
       The event severity, event type, node name and event code are enclosed."
		::= { ruckusSCGEventTraps 361 }

  ruckusSCGSyslogServerReachableTrap  NOTIFICATION-TYPE
     OBJECTS     {ruckusSCGEventSeverity,ruckusSCGEventType,ruckusSCGSyslogServerAddress,ruckusSCGEventMacAddr,ruckusSCGEventCode}
     STATUS      current
     DESCRIPTION
        "Trigger when there is a syslog server reachable event.
       The event severity, event type, syslog server address, SCG node MAC address and event code are enclosed."
		::= { ruckusSCGEventTraps 370 }

  ruckusSCGSyslogServerUnreachableTrap  NOTIFICATION-TYPE
     OBJECTS     {ruckusSCGEventSeverity,ruckusSCGEventType,ruckusSCGSyslogServerAddress,ruckusSCGEventMacAddr,ruckusSCGEventCode}
     STATUS      current
     DESCRIPTION
        "Trigger when there is a syslog server unreachable event.
       The event severity, event type, syslog server address, SCG node MAC address and event code are enclosed."
		::= { ruckusSCGEventTraps 371 }

  ruckusSCGSyslogServerSwitchedTrap  NOTIFICATION-TYPE
     OBJECTS     {ruckusSCGEventSeverity,ruckusSCGEventType,ruckusSCGSrcSyslogServerAddress,ruckusSCGDestSyslogServerAddress,ruckusSCGEventMacAddr,ruckusSCGEventCode}
     STATUS      current
     DESCRIPTION
        "Trigger when there is a syslog server switched event.
       The event severity, event type, source syslog server address, destination syslog server address, SCG node MAC address and event code are enclosed."
		::= { ruckusSCGEventTraps 372 }

  ruckusSCGAPRadiusServerReachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGRadSrvrIp,ruckusSCGEventCode,ruckusSCGEventAPIPv6}
     STATUS   current
     DESCRIPTION
        "Trigger when there is an AP is able to reach radius server successfully event.
	       The event severity, event type, AP name, AP MAC address, AP IP address, AP location, AP description, AP GPS coordinates, zone name, radius server IP address, event code and AP IPv6 address are enclosed."
			::= { ruckusSCGEventTraps 400 }

  ruckusSCGAPRadiusServerUnreachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGRadSrvrIp,ruckusSCGEventCode,ruckusSCGEventAPIPv6}
     STATUS   current
     DESCRIPTION
        "Trigger when there is an AP is unable to reach radius server event.
	       The event severity, event type, AP name, AP MAC address, AP IP address, AP location, AP description, AP GPS coordinates, zone name, radius server IP address, event code and AP IPv6 address are enclosed."
			::= { ruckusSCGEventTraps 401 }

  ruckusSCGAPLDAPServerReachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLDAPSrvrIp,ruckusSCGEventCode,ruckusSCGEventAPIPv6}
     STATUS   current
     DESCRIPTION
        "Trigger when there is an AP is able to reach LDAP server successfully event.
	       The event severity, event type, AP name, AP MAC address, AP IP address, AP location, AP description, AP GPS coordinates, zone name, LDAP server IP address, event code and AP IPv6 address are enclosed."
			::= { ruckusSCGEventTraps 402 }

  ruckusSCGAPLDAPServerUnreachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGLDAPSrvrIp,ruckusSCGEventCode,ruckusSCGEventAPIPv6}
     STATUS   current
     DESCRIPTION
        "Trigger when there is an AP is unable to reach LDAP server event.
	       The event severity, event type, AP name, AP MAC address, AP IP address, AP location, AP description, AP GPS coordinates, zone name, LDAP server IP address, event code and AP IPv6 address are enclosed."
			::= { ruckusSCGEventTraps 403 }

  ruckusSCGAPADServerReachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGADSrvrIp,ruckusSCGEventCode,ruckusSCGEventAPIPv6}
     STATUS   current
     DESCRIPTION
        "Trigger when there is an AP is able to reach AD server successfully event.
	       The event severity, event type, AP name, AP MAC address, AP IP address, AP location, AP description, AP GPS coordinates, zone name, AD server IP address, event code and AP IPv6 address are enclosed."
			::= { ruckusSCGEventTraps 404 }

  ruckusSCGAPADServerUnreachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGADSrvrIp,ruckusSCGEventCode,ruckusSCGEventAPIPv6}
     STATUS   current
     DESCRIPTION
        "Trigger when there is an AP is unable to reach AD server event.
	       The event severity, event type, AP name, AP MAC address, AP IP address, AP location, AP description, AP GPS coordinates, zone name, AD server IP address, event code and AP IPv6 address are enclosed."
			::= { ruckusSCGEventTraps 405 }

  ruckusSCGAPUsbSoftwarePackageDownloadedTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGSoftwareName,ruckusSCGEventCode,ruckusSCGEventAPIPv6}
     STATUS   current
     DESCRIPTION
        "Trigger when there is an AP downloaded its USB software package successfully event.
	       The event severity, event type, AP name, AP MAC address, AP IP address, AP location, AP description, AP GPS coordinates, zone name, USB software name, event code and AP IPv6 address are enclosed."
			::= { ruckusSCGEventTraps 406 }

  ruckusSCGAPUsbSoftwarePackageDownloadFailedTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGSoftwareName,ruckusSCGEventCode,ruckusSCGEventAPIPv6}
     STATUS   current
     DESCRIPTION
        "Trigger when there is an AP failed to download its USB software package event.
	       The event severity, event type, AP name, AP MAC address, AP IP address, AP location, AP description, AP GPS coordinates, zone name, USB software name, event code and AP IPv6 address are enclosed."
			::= { ruckusSCGEventTraps 407 }

  ruckusSCGEspAuthServerReachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAuthSrvrIp,ruckusSCGEventCode,ruckusSCGEventAPIPv6}
     STATUS   current
     DESCRIPTION
        "Trigger when there is an AP is able to reach WeChat ESP authentication server successfully event.
	       The event severity, event type, AP name, AP MAC address, AP IP address, AP location, AP description, AP GPS coordinates, zone name, authentication server IP address, event code and AP IPv6 address are enclosed."
			::= { ruckusSCGEventTraps 408 }

  ruckusSCGEspAuthServerUnreachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGAuthSrvrIp,ruckusSCGEventCode,ruckusSCGEventAPIPv6}
     STATUS   current
     DESCRIPTION
        "Trigger when there is an AP is unable to reach WeChat ESP authentication server event.
	       The event severity, event type, AP name, AP MAC address, AP IP address, AP location, AP description, AP GPS coordinates, zone name, authentication server IP address, event code and AP IPv6 address are enclosed."
			::= { ruckusSCGEventTraps 409 }

  ruckusSCGEspAuthServerResolvableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDomainName,ruckusSCGEventCode,ruckusSCGEventAPIPv6}
     STATUS   current
     DESCRIPTION
        "Trigger when there is an AP is able to resolve WeChat ESP authentication server domain name successfully event.
	       The event severity, event type, AP name, AP MAC address, AP IP address, AP location, AP description, AP GPS coordinates, zone name, authentication server domain name, event code and AP IPv6 address are enclosed."
			::= { ruckusSCGEventTraps 410 }

  ruckusSCGEspAuthServerUnResolvableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDomainName,ruckusSCGEventCode,ruckusSCGEventAPIPv6}
     STATUS   current
     DESCRIPTION
        "Trigger when there is an AP is unable to resolve WeChat ESP authentication server domain name event.
	       The event severity, event type, AP name, AP MAC address, AP IP address, AP location, AP description, AP GPS coordinates, zone name, authentication server domain name, event code and AP IPv6 address are enclosed."
			::= { ruckusSCGEventTraps 411 }

  ruckusSCGEspDNATServerReachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDNATIp,ruckusSCGEventCode,ruckusSCGEventAPIPv6}
     STATUS   current
     DESCRIPTION
        "Trigger when there is an AP is able to reach WeChat ESP DNAT server successfully event.
	       The event severity, event type, AP name, AP MAC address, AP IP address, AP location, AP description, AP GPS coordinates, zone name, DNAT server IP address, event code and AP IPv6 address are enclosed."
			::= { ruckusSCGEventTraps 412 }

  ruckusSCGEspDNATServerUnreachableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDNATIp,ruckusSCGEventCode,ruckusSCGEventAPIPv6}
     STATUS   current
     DESCRIPTION
        "Trigger when there is an AP is unable to reach WeChat ESP DNAT server event.
	       The event severity, event type, AP name, AP MAC address, AP IP address, AP location, AP description, AP GPS coordinates, zone name, DNAT server IP address, event code and AP IPv6 address are enclosed."
			::= { ruckusSCGEventTraps 413 }

  ruckusSCGEspDNATServerResolvableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDomainName,ruckusSCGEventCode,ruckusSCGEventAPIPv6}
     STATUS   current
     DESCRIPTION
        "Trigger when there is an AP is able to resolve WeChat ESP DNAT server domain name successfully event.
	       The event severity, event type, AP name, AP MAC address, AP IP address, AP location, AP description, AP GPS coordinates, zone name, authentication server domain name, event code and AP IPv6 address are enclosed."
			::= { ruckusSCGEventTraps 414 }

  ruckusSCGEspDNATServerUnresolvableTrap  NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGDomainName,ruckusSCGEventCode,ruckusSCGEventAPIPv6}
     STATUS   current
     DESCRIPTION
        "Trigger when there is an AP is unable to resolve WeChat ESP DNAT server domain name event.
	       The event severity, event type, AP name, AP MAC address, AP IP address, AP location, AP description, AP GPS coordinates, zone name, authentication server domain name, event code and AP IPv6 address are enclosed."
			::= { ruckusSCGEventTraps 415 }

  ruckusRateLimitTORSurpassedTrap	NOTIFICATION-TYPE
     OBJECTS     {ruckusSCGEventSeverity,ruckusSCGEventType,ruckusSCGRadSrvrIp,ruckusSCGEventCode}
     STATUS  current
     DESCRIPTION
        "Trigger when there is received rate Limit for Total Outstanding Requests(TOR) Surpassed event.
		 The event severity, event type, AAA server IP address and event code are enclosed."
		::= { ruckusSCGEventTraps 500 }

  ruckusSCGIPSecTunnelAssociatedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGIPSecGWAddress,ruckusSCGEventCode,ruckusSCGEventAPIPv6}
     STATUS   current
     DESCRIPTION
        "Trigger when there is an AP is able to reach secure gateway successfully event.
	       The event severity, event type, AP name, AP MAC address, AP IP address, AP location, AP description, AP GPS coordinates, zone name, secure gateway address, event code and AP IPv6 address are enclosed."
			::= { ruckusSCGEventTraps 600 }

  ruckusSCGIPSecTunnelDisassociatedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGIPSecGWAddress,ruckusSCGEventCode,ruckusSCGEventAPIPv6}
     STATUS   current
     DESCRIPTION
        "Trigger when there is an AP is disconnected from secure gateway event.
	       The event severity, event type, AP name, AP MAC address, AP IP address, AP location, AP description, AP GPS coordinates, zone name, secure gateway address, event code and AP IPv6 address are enclosed."
			::= { ruckusSCGEventTraps 601 }

  ruckusSCGIPSecTunnelAssociateFailedTrap	NOTIFICATION-TYPE
     OBJECTS	{ruckusSCGEventSeverity,ruckusSCGEventType,ruckusSCGEventAPName,ruckusSCGEventAPMacAddr,ruckusSCGEventAPIP,ruckusSCGEventAPLocation,ruckusSCGEventAPDescription,ruckusSCGEventAPGPSCoordinates,ruckusSCGEventZoneName,ruckusSCGIPSecGWAddress,ruckusSCGEventCode,ruckusSCGEventAPIPv6}
     STATUS   current
     DESCRIPTION
        "Trigger when there is an AP is not able to reach secure gateway successfully event.
	       The event severity, event type, AP name, AP MAC address, AP IP address, AP location, AP description, AP GPS coordinates, zone name, secure gateway address, event code and AP IPv6 address are enclosed."
			::= { ruckusSCGEventTraps 602 }

  ruckusSCGPmipProcessInitTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received PMIPv6 process crashed, is restarted event.
		 The event severity, event type, SCG node MAC address, management IP address and event code are enclosed."
		::= { ruckusSCGEventTraps 700 }

  ruckusSCGPmipUnavailableTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received PMIPv6 process repeatedly restarts, could not become stable event.
		 The event severity, event type, SCG node MAC address, management IP address and event code are enclosed."
		::= { ruckusSCGEventTraps 701 }

  ruckusSCGPmipUnallocatedMemoryTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received memory allocation failed in PMIPv6 process event.
		 The event severity, event type, SCG node MAC address, management IP address and event code are enclosed."
		::= { ruckusSCGEventTraps 702 }

  ruckusSCGPmipUpdateCgfFailedTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received PMIPv6 failed to apply configuration event.
		 The event severity, event type, SCG node MAC address, management IP address and event code are enclosed."
		::= { ruckusSCGEventTraps 703 }

  ruckusSCGPmipLMAIcmpUnreachableTrap	NOTIFICATION-TYPE
     OBJECTS     {ruckusSCGEventSeverity,ruckusSCGEventType,ruckusSCGLMAIp,ruckusSCGEventMacAddr,ruckusSCGEventNodeMgmtIp,ruckusSCGEventCode}
     STATUS  current
     DESCRIPTION
        "Trigger when there is received PMIPv6 daemon cannot reach the LMA server by ICMP packet event.
		 The event severity, event type, LMA IP address, SCG node MAC address, management IP address and event code are enclosed."
		::= { ruckusSCGEventTraps 704 }

  ruckusSCGPmipLMAFailOverTrap	NOTIFICATION-TYPE
     OBJECTS     {ruckusSCGEventSeverity,ruckusSCGEventType,ruckusSCGLMAIp,ruckusSCGEventMacAddr,ruckusSCGEventNodeMgmtIp,ruckusSCGEventCode}
     STATUS  current
     DESCRIPTION
        "Trigger when there is received LMA failover event.
		 The event severity, event type, LMA IP address, SCG node MAC address, management IP address and event code are enclosed."
		::= { ruckusSCGEventTraps 705 }

  ruckusSCGPmipBindingFailureTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received MN binding failure from LMA server event.
		 The event severity, event type, SCG node MAC address, management IP address and event code are enclosed."
		::= { ruckusSCGEventTraps 706 }

  ruckusSCGPmiplostCnxnToDHCPTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received PMIPv6 process cannot connect to DHCP server event.
		 The event severity, event type, SCG node MAC address, management IP address and event code are enclosed."
		::= { ruckusSCGEventTraps 707 }

  ruckusSCGPmipLMAIcmpReachableTrap	NOTIFICATION-TYPE
     OBJECTS     {ruckusSCGEventSeverity,ruckusSCGEventType,ruckusSCGLMAIp,ruckusSCGEventMacAddr,ruckusSCGEventNodeMgmtIp,ruckusSCGEventCode}
     STATUS  current
     DESCRIPTION
        "Trigger when there is received PMIPv6 daemon successfully reaches the LMA server by ICMP packet event.
		 The event severity, event type, LMA IP address, SCG node MAC address, management IP address and event code are enclosed."
		::= { ruckusSCGEventTraps 708 }

  ruckusSCGPmipBindingSuccessTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received MN binding success from LMA server event.
		 The event severity, event type, SCG node MAC address, management IP address and event code are enclosed."
		::= { ruckusSCGEventTraps 709 }

  ruckusSCGPmipConnectedToDHCPTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is received PMIPv6 process successfully connects to DHCP server event.
		 The event severity, event type, SCG node MAC address, management IP address and event code are enclosed."
		::= { ruckusSCGEventTraps 710 }

  ruckusSCGPmipProcessStoppedTrap	NOTIFICATION-TYPE
     OBJECTS     {ruckusSCGEventSeverity,ruckusSCGEventType,ruckusSCGEventMacAddr,ruckusSCGEventNodeMgmtIp,ruckusSCGEventCode}
     STATUS  current
     DESCRIPTION
        "Trigger when there is PMIPv6 process stopped event.
		 The event severity, event type, SCG node MAC address, management IP address and event code are enclosed."
		::= { ruckusSCGEventTraps 711 }

  ruckusSCGEventDescription OBJECT-TYPE
	    SYNTAX      OCTET STRING
	    MAX-ACCESS  accessible-for-notify
	    STATUS      current
	    DESCRIPTION
             "The event's description."
	    ::= { ruckusSCGEventObjects 1 }

  ruckusSCGClusterName   OBJECT-TYPE
	    SYNTAX      OCTET STRING
	    MAX-ACCESS  accessible-for-notify
	    STATUS      current
	    DESCRIPTION
             "The SCG's cluster name."
	    ::= { ruckusSCGEventObjects 2 }

  ruckusSCGEventCode OBJECT-TYPE
	    SYNTAX      OCTET STRING
	    MAX-ACCESS  accessible-for-notify
	    STATUS      current
	    DESCRIPTION
	        "The event's code."
	    ::= { ruckusSCGEventObjects 10 }

  ruckusSCGProcessName  OBJECT-TYPE
     SYNTAX     OCTET STRING
     MAX-ACCESS  accessible-for-notify
     STATUS   current
     DESCRIPTION
			"The process name."
			::= { ruckusSCGEventObjects 11 }

  ruckusSCGEventCtrlIP  OBJECT-TYPE
     SYNTAX     OCTET STRING
     MAX-ACCESS  accessible-for-notify
     STATUS   current
     DESCRIPTION
			"The SCG's node control IP address."
			::= { ruckusSCGEventObjects 12 }

  ruckusSCGEventSeverity OBJECT-TYPE
	    SYNTAX      OCTET STRING
	    MAX-ACCESS  accessible-for-notify
	    STATUS      current
	    DESCRIPTION
	        "The event's severity."
	    ::= { ruckusSCGEventObjects 13 }

  ruckusSCGEventType OBJECT-TYPE
	    SYNTAX      OCTET STRING
	    MAX-ACCESS  accessible-for-notify
	    STATUS      current
	    DESCRIPTION
	        "The event's type."
	    ::= { ruckusSCGEventObjects 14 }

  ruckusSCGEventNodeMgmtIp OBJECT-TYPE
	    SYNTAX      OCTET STRING
	    MAX-ACCESS  accessible-for-notify
	    STATUS      current
	    DESCRIPTION
	        "The SCG's management IP address."
	    ::= { ruckusSCGEventObjects 15 }

  ruckusSCGEventNodeName OBJECT-TYPE
	    SYNTAX      OCTET STRING
	    MAX-ACCESS  accessible-for-notify
	    STATUS      current
	    DESCRIPTION
             "The SCG's node name."
	    ::= { ruckusSCGEventObjects 16 }

  ruckusSCGCPUPerc OBJECT-TYPE
	    SYNTAX      OCTET STRING
	    MAX-ACCESS  accessible-for-notify
	    STATUS      current
	    DESCRIPTION
             "The SCG's CPU usage percent."
	    ::= { ruckusSCGEventObjects 17 }

  ruckusSCGMemoryPerc OBJECT-TYPE
	    SYNTAX      OCTET STRING
	    MAX-ACCESS  accessible-for-notify
	    STATUS      current
	    DESCRIPTION
             "The SCG's memory usage percent."
	    ::= { ruckusSCGEventObjects 18 }

  ruckusSCGDiskPerc OBJECT-TYPE
	    SYNTAX      OCTET STRING
	    MAX-ACCESS  accessible-for-notify
	    STATUS      current
	    DESCRIPTION
             "The SCG's disk usage percent."
	    ::= { ruckusSCGEventObjects 19 }

  ruckusSCGEventMacAddr OBJECT-TYPE
	    SYNTAX      OCTET STRING
	    MAX-ACCESS  accessible-for-notify
	    STATUS      current
	    DESCRIPTION
             "The SCG's MAC address."
	    ::= { ruckusSCGEventObjects 20 }

  ruckusSCGEventFirmwareVersion OBJECT-TYPE
	    SYNTAX      OCTET STRING
	    MAX-ACCESS  accessible-for-notify
	    STATUS      current
	    DESCRIPTION
             "The SCG's firmware version."
	    ::= { ruckusSCGEventObjects 21 }

  ruckusSCGEventUpgradedFirmwareVersion OBJECT-TYPE
	    SYNTAX      OCTET STRING
	    MAX-ACCESS  accessible-for-notify
	    STATUS      current
	    DESCRIPTION
	        "The SCG's upgrade firmware version."
	    ::= { ruckusSCGEventObjects 22 }

  ruckusSCGEventAPMacAddr OBJECT-TYPE
	    SYNTAX      OCTET STRING
	    MAX-ACCESS  accessible-for-notify
	    STATUS      current
	    DESCRIPTION
	        "The AP's MAC address."
	    ::= { ruckusSCGEventObjects 23 }

  ruckusSCGEventReason OBJECT-TYPE
	    SYNTAX      OCTET STRING
	    MAX-ACCESS  accessible-for-notify
	    STATUS      current
	    DESCRIPTION
	        "The event's reason."
	    ::= { ruckusSCGEventObjects 24 }

  ruckusSCGEventAPName OBJECT-TYPE
	    SYNTAX      OCTET STRING
	    MAX-ACCESS  accessible-for-notify
	    STATUS      current
	    DESCRIPTION
	        "The AP's name."
	    ::= { ruckusSCGEventObjects 25 }

  ruckusSCGEventAPIP OBJECT-TYPE
	    SYNTAX      OCTET STRING
	    MAX-ACCESS  accessible-for-notify
	    STATUS      current
	    DESCRIPTION
	        "The AP's IP address."
	    ::= { ruckusSCGEventObjects 26 }

  ruckusSCGEventAPLocation OBJECT-TYPE
	    SYNTAX      OCTET STRING
	    MAX-ACCESS  accessible-for-notify
	    STATUS      current
	    DESCRIPTION
	        "The AP's location."
	    ::= { ruckusSCGEventObjects 27 }

  ruckusSCGEventAPGPSCoordinates OBJECT-TYPE
	    SYNTAX      OCTET STRING
	    MAX-ACCESS  accessible-for-notify
	    STATUS      current
	    DESCRIPTION
	        "The AP's GPS coordinates."
	    ::= { ruckusSCGEventObjects 28 }

  ruckusSCGEventAPDescription OBJECT-TYPE
	    SYNTAX      OCTET STRING
	    MAX-ACCESS  accessible-for-notify
	    STATUS      current
	    DESCRIPTION
	        "The AP's description."
	    ::= { ruckusSCGEventObjects 29 }

  ruckusSCGEventZoneName OBJECT-TYPE
	    SYNTAX      OCTET STRING
	    MAX-ACCESS  accessible-for-notify
	    STATUS      current
	    DESCRIPTION
	        "The zone name."
	    ::= { ruckusSCGEventObjects 30 }

  ruckusSCGAPModel  OBJECT-TYPE
     SYNTAX     OCTET STRING
     MAX-ACCESS  accessible-for-notify
     STATUS   current
     DESCRIPTION
			"The AP model"
			::= { ruckusSCGEventObjects 31 }

  ruckusSCGConfigAPModel  OBJECT-TYPE
     SYNTAX     OCTET STRING
     MAX-ACCESS  accessible-for-notify
     STATUS   current
     DESCRIPTION
			"The configured AP model"
			::= { ruckusSCGEventObjects 32 }

  ruckusSCGAPConfigID  OBJECT-TYPE
     SYNTAX     OCTET STRING
     MAX-ACCESS  accessible-for-notify
     STATUS   current
     DESCRIPTION
			"The AP's configuration UUID"
			::= { ruckusSCGEventObjects 33 }

  ruckusSCGEventTargetZoneName  OBJECT-TYPE
     SYNTAX     OCTET STRING
     MAX-ACCESS  accessible-for-notify
     STATUS   current
     DESCRIPTION
			"The AP's target zone name"
			::= { ruckusSCGEventObjects 34 }

  ruckusSCGEventAPIPv6 OBJECT-TYPE
	    SYNTAX      OCTET STRING
	    MAX-ACCESS  accessible-for-notify
	    STATUS      current
	    DESCRIPTION
	        "The AP's IPv6 address."
	    ::= { ruckusSCGEventObjects 35 }

  ruckusSCGLBSURL  OBJECT-TYPE
     SYNTAX     OCTET STRING
     MAX-ACCESS  accessible-for-notify
     STATUS   current
     DESCRIPTION
			"The LBS server's URL"
			::= { ruckusSCGEventObjects 38 }

  ruckusSCGLBSPort  OBJECT-TYPE
     SYNTAX     OCTET STRING
     MAX-ACCESS  accessible-for-notify
     STATUS   current
     DESCRIPTION
			"The LBS server's port"
			::= { ruckusSCGEventObjects 39 }

  ruckusSCGEventSSID  OBJECT-TYPE
     SYNTAX     OCTET STRING
     MAX-ACCESS  accessible-for-notify
     STATUS   current
     DESCRIPTION
			"The WLAN ssid"
			::= { ruckusSCGEventObjects 40 }

  ruckusSCGEventRogueMac  OBJECT-TYPE
     SYNTAX     OCTET STRING
     MAX-ACCESS  accessible-for-notify
     STATUS   current
     DESCRIPTION
			"The rogue MAC Address"
			::= { ruckusSCGEventObjects 45 }

  ruckusPrimaryGRE  OBJECT-TYPE
     SYNTAX     OCTET STRING
     MAX-ACCESS  accessible-for-notify
     STATUS   current
     DESCRIPTION
			"The primary GRE gateway."
			::= { ruckusSCGEventObjects 46 }

  ruckusSecondaryGRE  OBJECT-TYPE
     SYNTAX     OCTET STRING
     MAX-ACCESS  accessible-for-notify
     STATUS   current
     DESCRIPTION
			"The secondary GRE gateway."
			::= { ruckusSCGEventObjects 47 }

  ruckusSoftGREGatewayList  OBJECT-TYPE
     SYNTAX     OCTET STRING
     MAX-ACCESS  accessible-for-notify
     STATUS   current
     DESCRIPTION
			"The softGRE gateway list. It could be IP address or FQDN and must have only two IPs/DNs separated by semicolon (;)."
			::= { ruckusSCGEventObjects 48 }

  ruckusSCGSoftGREGWAddress  OBJECT-TYPE
     SYNTAX     OCTET STRING
     MAX-ACCESS  accessible-for-notify
     STATUS   current
     DESCRIPTION
			"The softGRE gateway IP address."
			::= { ruckusSCGEventObjects 49}

  ruckusSCGEventClientMacAddr OBJECT-TYPE
	    SYNTAX      OCTET STRING
	    MAX-ACCESS  accessible-for-notify
	    STATUS      current
	    DESCRIPTION
	        "The client's MAC address."
	    ::= { ruckusSCGEventObjects 50 }

  ruckusSCGDPKey OBJECT-TYPE
	    SYNTAX      OCTET STRING
	    MAX-ACCESS  accessible-for-notify
	    STATUS      current
	    DESCRIPTION
	        "The DP's identifier."
	    ::= { ruckusSCGEventObjects 80 }

  ruckusSCGDPConfigID  OBJECT-TYPE
     SYNTAX     OCTET STRING
     MAX-ACCESS  accessible-for-notify
     STATUS   current
     DESCRIPTION
			"The DP's configuration ID."
			::= { ruckusSCGEventObjects 81 }

  ruckusSCGDPIP  OBJECT-TYPE
     SYNTAX     OCTET STRING
     MAX-ACCESS  accessible-for-notify
     STATUS   current
     DESCRIPTION
			"The DP's IP address."
			::= { ruckusSCGEventObjects 82 }

  ruckusSCGDPPacketPoolID  OBJECT-TYPE
     SYNTAX     OCTET STRING
     MAX-ACCESS  accessible-for-notify
     STATUS   current
     DESCRIPTION
			"The DP's packet pool ID."
			::= { ruckusSCGEventObjects 83 }

  ruckusSCGNetworkPortID  OBJECT-TYPE
     SYNTAX     OCTET STRING
     MAX-ACCESS  accessible-for-notify
     STATUS   current
     DESCRIPTION
			"The network port ID."
			::= { ruckusSCGEventObjects 100 }

  ruckusSCGNetworkInterface  OBJECT-TYPE
     SYNTAX     OCTET STRING
     MAX-ACCESS  accessible-for-notify
     STATUS   current
     DESCRIPTION
			"The network interface."
			::= { ruckusSCGEventObjects 101 }

  ruckusSCGSwitchStatus  OBJECT-TYPE
     SYNTAX     OCTET STRING
     MAX-ACCESS  accessible-for-notify
     STATUS   current
     DESCRIPTION
			"The switch status."
			::= { ruckusSCGEventObjects 102 }

  ruckusSCGTemperatureStatus  OBJECT-TYPE
     SYNTAX     OCTET STRING
     MAX-ACCESS  accessible-for-notify
     STATUS   current
     DESCRIPTION
			"The temperature status."
			::= { ruckusSCGEventObjects 120 }

  ruckusSCGProcessorId  OBJECT-TYPE
     SYNTAX     OCTET STRING
     MAX-ACCESS  accessible-for-notify
     STATUS   current
     DESCRIPTION
			"The processor ID."
			::= { ruckusSCGEventObjects 121 }

  ruckusSCGFanId  OBJECT-TYPE
     SYNTAX     OCTET STRING
     MAX-ACCESS  accessible-for-notify
     STATUS   current
     DESCRIPTION
			"The fan module ID."
			::= { ruckusSCGEventObjects 122 }

  ruckusSCGFanStatus  OBJECT-TYPE
     SYNTAX     OCTET STRING
     MAX-ACCESS  accessible-for-notify
     STATUS   current
     DESCRIPTION
			"The fan module status."
			::= { ruckusSCGEventObjects 123 }

  ruckusSCGPsId  OBJECT-TYPE
     SYNTAX     OCTET STRING
     MAX-ACCESS  accessible-for-notify
     STATUS   current
     DESCRIPTION
			"The power supply ID."
			::= { ruckusSCGEventObjects 124 }

  ruckusSCGPsStatus  OBJECT-TYPE
     SYNTAX     OCTET STRING
     MAX-ACCESS  accessible-for-notify
     STATUS   current
     DESCRIPTION
			"The power supply status."
			::= { ruckusSCGEventObjects 125 }

  ruckusSCGDrvId  OBJECT-TYPE
     SYNTAX     OCTET STRING
     MAX-ACCESS  accessible-for-notify
     STATUS   current
     DESCRIPTION
			"The drive ID."
			::= { ruckusSCGEventObjects 126 }

  ruckusSCGDrvStatus  OBJECT-TYPE
     SYNTAX     OCTET STRING
     MAX-ACCESS  accessible-for-notify
     STATUS   current
     DESCRIPTION
			"The drive status."
			::= { ruckusSCGEventObjects 127 }

  ruckusSCGLicenseType  OBJECT-TYPE
     SYNTAX     OCTET STRING
     MAX-ACCESS  accessible-for-notify
     STATUS   current
     DESCRIPTION
			"The license type"
			::= { ruckusSCGEventObjects 150 }

  ruckusSCGLicenseUsagePerc  OBJECT-TYPE
     SYNTAX     OCTET STRING
     MAX-ACCESS  accessible-for-notify
     STATUS   current
     DESCRIPTION
			"The license usage percent."
			::= { ruckusSCGEventObjects 151 }

  ruckusSCGLicenseServerName  OBJECT-TYPE
     SYNTAX     OCTET STRING
     MAX-ACCESS  accessible-for-notify
     STATUS   current
     DESCRIPTION
			"The license server name."
			::= { ruckusSCGEventObjects 152 }

  ruckusSCGIPSecGWAddress  OBJECT-TYPE
     SYNTAX     OCTET STRING
     MAX-ACCESS  accessible-for-notify
     STATUS   current
     DESCRIPTION
			"The secure gateway address."
			::= { ruckusSCGEventObjects 153 }

  ruckusSCGSyslogServerAddress  OBJECT-TYPE
     SYNTAX     OCTET STRING
     MAX-ACCESS  accessible-for-notify
     STATUS   current
     DESCRIPTION
			"The syslog server address."
			::= { ruckusSCGEventObjects 154 }

  ruckusSCGSrcSyslogServerAddress  OBJECT-TYPE
     SYNTAX     OCTET STRING
     MAX-ACCESS  accessible-for-notify
     STATUS   current
     DESCRIPTION
			"The source syslog server address."
			::= { ruckusSCGEventObjects 155 }

  ruckusSCGDestSyslogServerAddress  OBJECT-TYPE
     SYNTAX     OCTET STRING
     MAX-ACCESS  accessible-for-notify
     STATUS   current
     DESCRIPTION
			"The destination syslog server address."
			::= { ruckusSCGEventObjects 156 }

  ruckusSCGFtpIp  OBJECT-TYPE
     SYNTAX     OCTET STRING
     MAX-ACCESS  accessible-for-notify
     STATUS   current
     DESCRIPTION
			"The FTP server IP address."
			::= { ruckusSCGEventObjects 200 }

  ruckusSCGFtpPort  OBJECT-TYPE
     SYNTAX     OCTET STRING
     MAX-ACCESS  accessible-for-notify
     STATUS   current
     DESCRIPTION
			"The FTP server port."
			::= { ruckusSCGEventObjects 201 }

  ruckusSCGSrcProcess  OBJECT-TYPE
     SYNTAX     OCTET STRING
     MAX-ACCESS  accessible-for-notify
     STATUS   current
     DESCRIPTION
			"The source process name."
			::= { ruckusSCGEventObjects 301 }

  ruckusSCGGgsnIp  OBJECT-TYPE
     SYNTAX     OCTET STRING
     MAX-ACCESS  accessible-for-notify
     STATUS   current
     DESCRIPTION
			"The GGSN IP address."
			::= { ruckusSCGEventObjects 302 }

  ruckusSCGGtpcIp  OBJECT-TYPE
     SYNTAX     OCTET STRING
     MAX-ACCESS  accessible-for-notify
     STATUS   current
     DESCRIPTION
			"The GTP IP address."
			::= { ruckusSCGEventObjects 303 }

  ruckusSCGApn  OBJECT-TYPE
     SYNTAX     OCTET STRING
     MAX-ACCESS  accessible-for-notify
     STATUS   current
     DESCRIPTION
			"The APN name."
			::= { ruckusSCGEventObjects 304 }

  ruckusSCGUEImsi  OBJECT-TYPE
     SYNTAX     OCTET STRING
     MAX-ACCESS  accessible-for-notify
     STATUS   current
     DESCRIPTION
			"The UE IMSI."
			::= { ruckusSCGEventObjects 305 }

  ruckusSCGUEMsisdn  OBJECT-TYPE
     SYNTAX     OCTET STRING
     MAX-ACCESS  accessible-for-notify
     STATUS   current
     DESCRIPTION
			"The UE MSISDN."
			::= { ruckusSCGEventObjects 306 }

  ruckusSCGAuthSrvrIp  OBJECT-TYPE
     SYNTAX     OCTET STRING
     MAX-ACCESS  accessible-for-notify
     STATUS   current
     DESCRIPTION
			"The authentication server IP address."
			::= { ruckusSCGEventObjects 307 }

  ruckusSCGRadProxyIp  OBJECT-TYPE
     SYNTAX     OCTET STRING
     MAX-ACCESS  accessible-for-notify
     STATUS   current
     DESCRIPTION
			"The radius proxy IP address."
			::= { ruckusSCGEventObjects 308 }

  ruckusSCGAccSrvrIp  OBJECT-TYPE
     SYNTAX     OCTET STRING
     MAX-ACCESS  accessible-for-notify
     STATUS   current
     DESCRIPTION
			"The accounting server IP address."
			::= { ruckusSCGEventObjects 309 }

  ruckusSCGRealm  OBJECT-TYPE
     SYNTAX     OCTET STRING
     MAX-ACCESS  accessible-for-notify
     STATUS   current
     DESCRIPTION
			"The Realm name."
			::= { ruckusSCGEventObjects 310 }

  ruckusSCGCgfSrvrIp  OBJECT-TYPE
     SYNTAX     OCTET STRING
     MAX-ACCESS  accessible-for-notify
     STATUS   current
     DESCRIPTION
			"The CGF IP address."
			::= { ruckusSCGEventObjects 311 }

  ruckusSCGRadSrvrIp  OBJECT-TYPE
     SYNTAX     OCTET STRING
     MAX-ACCESS  accessible-for-notify
     STATUS   current
     DESCRIPTION
			"The radius server IP address."
			::= { ruckusSCGEventObjects 312 }

  ruckusSCGCipIp  OBJECT-TYPE
     SYNTAX     OCTET STRING
     MAX-ACCESS  accessible-for-notify
     STATUS   current
     DESCRIPTION
			"The CIP IP address."
			::= { ruckusSCGEventObjects 313 }

  ruckusSCGPointCode  OBJECT-TYPE
     SYNTAX     OCTET STRING
     MAX-ACCESS  accessible-for-notify
     STATUS   current
     DESCRIPTION
			"The point code."
			::= { ruckusSCGEventObjects 314 }

  ruckusSCGCongLevel  OBJECT-TYPE
     SYNTAX     OCTET STRING
     MAX-ACCESS  accessible-for-notify
     STATUS   current
     DESCRIPTION
			"The level of congestion."
			::= { ruckusSCGEventObjects 315 }

  ruckusSCGSSN  OBJECT-TYPE
     SYNTAX     OCTET STRING
     MAX-ACCESS  accessible-for-notify
     STATUS   current
     DESCRIPTION
			"The SSN."
			::= { ruckusSCGEventObjects 316 }

  ruckusSCGRoutingContext  OBJECT-TYPE
     SYNTAX     OCTET STRING
     MAX-ACCESS  accessible-for-notify
     STATUS   current
     DESCRIPTION
			"The routing context."
			::= { ruckusSCGEventObjects 317 }

  ruckusSCGSrcIP  OBJECT-TYPE
     SYNTAX     OCTET STRING
     MAX-ACCESS  accessible-for-notify
     STATUS   current
     DESCRIPTION
			"The source IP address."
			::= { ruckusSCGEventObjects 318 }

  ruckusSCGSrcPort  OBJECT-TYPE
     SYNTAX     OCTET STRING
     MAX-ACCESS  accessible-for-notify
     STATUS   current
     DESCRIPTION
			"The source port."
			::= { ruckusSCGEventObjects 319 }

  ruckusSCGDestIP  OBJECT-TYPE
     SYNTAX     OCTET STRING
     MAX-ACCESS  accessible-for-notify
     STATUS   current
     DESCRIPTION
			"The destination IP address."
			::= { ruckusSCGEventObjects 320 }

  ruckusSCGDestPort  OBJECT-TYPE
     SYNTAX     OCTET STRING
     MAX-ACCESS  accessible-for-notify
     STATUS   current
     DESCRIPTION
			"The destination port."
			::= { ruckusSCGEventObjects 321 }

  ruckusSCGOperation  OBJECT-TYPE
     SYNTAX     OCTET STRING
     MAX-ACCESS  accessible-for-notify
     STATUS   current
     DESCRIPTION
			"The operation name."
			::= { ruckusSCGEventObjects 322 }

  ruckusSCGHlrInstance  OBJECT-TYPE
     SYNTAX     OCTET STRING
     MAX-ACCESS  accessible-for-notify
     STATUS   current
     DESCRIPTION
			"The HLR instance."
			::= { ruckusSCGEventObjects 323 }

  ruckusSCGUserName  OBJECT-TYPE
     SYNTAX     OCTET STRING
     MAX-ACCESS  accessible-for-notify
     STATUS   current
     DESCRIPTION
			"The user name."
			::= { ruckusSCGEventObjects 324 }

  ruckusSCGPgwIp  OBJECT-TYPE
     SYNTAX     OCTET STRING
     MAX-ACCESS  accessible-for-notify
     STATUS   current
     DESCRIPTION
			"The PGW IP address."
			::= { ruckusSCGEventObjects 325 }

  ruckusSCGFileName  OBJECT-TYPE
     SYNTAX     OCTET STRING
     MAX-ACCESS  accessible-for-notify
     STATUS   current
     DESCRIPTION
			"The file name."
			::= { ruckusSCGEventObjects 326 }

  ruckusSCGLDAPSrvrIp  OBJECT-TYPE
     SYNTAX     OCTET STRING
     MAX-ACCESS  accessible-for-notify
     STATUS   current
     DESCRIPTION
			"The LDAP server IP address."
			::= { ruckusSCGEventObjects 327 }

  ruckusSCGADSrvrIp  OBJECT-TYPE
     SYNTAX     OCTET STRING
     MAX-ACCESS  accessible-for-notify
     STATUS   current
     DESCRIPTION
			"The AD server IP address."
			::= { ruckusSCGEventObjects 328 }

  ruckusSCGSoftwareName  OBJECT-TYPE
     SYNTAX     OCTET STRING
     MAX-ACCESS  accessible-for-notify
     STATUS   current
     DESCRIPTION
			"The software name."
			::= { ruckusSCGEventObjects 329 }

  ruckusSCGDomainName  OBJECT-TYPE
     SYNTAX     OCTET STRING
     MAX-ACCESS  accessible-for-notify
     STATUS   current
     DESCRIPTION
			"The domain name."
			::= { ruckusSCGEventObjects 330 }

  ruckusSCGDNATIp  OBJECT-TYPE
     SYNTAX     OCTET STRING
     MAX-ACCESS  accessible-for-notify
     STATUS   current
     DESCRIPTION
			"The DNAT server IP address."
			::= { ruckusSCGEventObjects 331 }

  ruckusSCGLMAIp  OBJECT-TYPE
     SYNTAX     OCTET STRING
     MAX-ACCESS  accessible-for-notify
     STATUS   current
     DESCRIPTION
			"The LMA IP address."
			::= { ruckusSCGEventObjects 400 }

  ruckusSCGEventRoguePolicyName  OBJECT-TYPE
     SYNTAX     OCTET STRING
     MAX-ACCESS  accessible-for-notify
     STATUS   current
     DESCRIPTION
			"The rogue classified by which policy name."
			::= { ruckusSCGEventObjects 401 }

  ruckusSCGEventRogueRuleName  OBJECT-TYPE
     SYNTAX     OCTET STRING
     MAX-ACCESS  accessible-for-notify
     STATUS   current
     DESCRIPTION
			"The rogue rogue classified by which rule name."
			::= { ruckusSCGEventObjects 402 }

  ruckusSCGEventRogueType  OBJECT-TYPE
     SYNTAX     OCTET STRING
     MAX-ACCESS  accessible-for-notify
     STATUS   current
     DESCRIPTION
			"The rogue classified as type."
			::= { ruckusSCGEventObjects 403 }

END
