G6-LACP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

protocol MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 2 }

lacp  OBJECT IDENTIFIER ::= { protocol 54 }



-- *************************** CONFIGURATION SECTION ********************************


lacpEnableLacp OBJECT-TYPE   -- enable_lacp
	SYNTAX INTEGER {  disabled(0), enabled(1) }
	MAX-ACCESS read-write
	STATUS current
	DESCRIPTION
	"General enable of LACP function. "
	::= { lacp 1 }


-- ******************* Begin of configTable *************************

configTable	OBJECT-TYPE
	SYNTAX SEQUENCE OF ConfigEntry
	MAX-ACCESS not-accessible
	STATUS current
	DESCRIPTION
		""
	::= { lacp 2 }

configEntry	OBJECT-TYPE
	SYNTAX ConfigEntry
	MAX-ACCESS not-accessible
	STATUS current
	DESCRIPTION
		""
	INDEX { configIndex }
	::= { configTable 1 }


	ConfigEntry ::= SEQUENCE {
	configIndex INTEGER,
	configLinkAggregation INTEGER ,
	configSystemPriority Integer32 ,
	configMode INTEGER ,
	configTransmitInterval INTEGER
	}

configIndex	OBJECT-TYPE
	SYNTAX INTEGER (0)
	MAX-ACCESS not-accessible
	STATUS current
	DESCRIPTION
		"Automatically generated"
	::= { configEntry 1 }

configLinkAggregation OBJECT-TYPE   -- link_aggregation
	SYNTAX INTEGER
		{
		static (0),
		dynamic (1)
		}
	MAX-ACCESS read-write
	STATUS current
	DESCRIPTION
	"With static setting the link aggregation operates exactly on the ports defined via trunk configuration. Dynamic uses protocol between both endpoints to dynamically use as many or little links as currently available."
	::= { configEntry 2 }

configSystemPriority OBJECT-TYPE   -- system_priority
	SYNTAX Integer32 (0..65535)
	MAX-ACCESS read-write
	STATUS current
	DESCRIPTION
	"Priority associated with the system."
	::= { configEntry 3 }

configMode OBJECT-TYPE   -- mode
	SYNTAX INTEGER
		{
		passive (0),
		active (1)
		}
	MAX-ACCESS read-write
	STATUS current
	DESCRIPTION
	"Determines active or passive operational mode."
	::= { configEntry 4 }

configTransmitInterval OBJECT-TYPE   -- transmit_interval
	SYNTAX INTEGER
		{
		slow (0),
		fast (1)
		}
	MAX-ACCESS read-write
	STATUS current
	DESCRIPTION
	"Determine LACP PDU interval."
	::= { configEntry 5 }


-- ********************* End of configTable ***********************


-- ******************* Begin of portConfigTable *************************

portConfigTable	OBJECT-TYPE
	SYNTAX SEQUENCE OF PortConfigEntry
	MAX-ACCESS not-accessible
	STATUS current
	DESCRIPTION
		"Configuration parameter concerning the port specific LACP setttings"
	::= { lacp 3 }

portConfigEntry	OBJECT-TYPE
	SYNTAX PortConfigEntry
	MAX-ACCESS not-accessible
	STATUS current
	DESCRIPTION
		""
	INDEX { portConfigPortIndex }
	::= { portConfigTable 1 }


	PortConfigEntry ::= SEQUENCE {
	portConfigPortIndex INTEGER,
	portConfigTrunkId Integer32
	}

portConfigPortIndex	OBJECT-TYPE
	SYNTAX INTEGER (0..24)
	MAX-ACCESS not-accessible
	STATUS current
	DESCRIPTION
		"Automatically generated"
	::= { portConfigEntry 1 }

portConfigTrunkId OBJECT-TYPE   -- trunk_id
	SYNTAX Integer32 (0..255)
	MAX-ACCESS read-write
	STATUS current
	DESCRIPTION
	"All ports with the same trunk_id form a common trunk. Use trunk_id 0 for ports that do not belong to any LACP trunk. The trunk_id corresponds to the trunk_config[index]."
	::= { portConfigEntry 2 }


-- ********************* End of portConfigTable ***********************


-- ******************* Begin of trunkConfigTable *************************

trunkConfigTable	OBJECT-TYPE
	SYNTAX SEQUENCE OF TrunkConfigEntry
	MAX-ACCESS not-accessible
	STATUS current
	DESCRIPTION
		"Each trunk is referenced by its index number."
	::= { lacp 4 }

trunkConfigEntry	OBJECT-TYPE
	SYNTAX TrunkConfigEntry
	MAX-ACCESS not-accessible
	STATUS current
	DESCRIPTION
		""
	INDEX { trunkConfigIndex }
	::= { trunkConfigTable 1 }


	TrunkConfigEntry ::= SEQUENCE {
	trunkConfigIndex INTEGER,
	trunkConfigName DisplayString,
	trunkConfigTrunkEnable INTEGER
	}

trunkConfigIndex	OBJECT-TYPE
	SYNTAX INTEGER (0..15)
	MAX-ACCESS not-accessible
	STATUS current
	DESCRIPTION
		"Automatically generated"
	::= { trunkConfigEntry 1 }

trunkConfigName OBJECT-TYPE   -- name
	SYNTAX DisplayString
	MAX-ACCESS read-write
	STATUS current
	DESCRIPTION
	"Unique name used to identify the trunk Interface."
	::= { trunkConfigEntry 2 }

trunkConfigTrunkEnable OBJECT-TYPE   -- trunk_enable
	SYNTAX INTEGER {  disabled(0), enabled(1) }
	MAX-ACCESS read-write
	STATUS current
	DESCRIPTION
	"Enables the trunk for operation. When disabled, trunk is brought down."
	::= { trunkConfigEntry 3 }


-- ********************* End of trunkConfigTable ***********************



-- ****************************** STATUS SECTION ********************************


-- ******************* Begin of portStatusTable *************************

portStatusTable	OBJECT-TYPE
	SYNTAX SEQUENCE OF PortStatusEntry
	MAX-ACCESS not-accessible
	STATUS current
	DESCRIPTION
		"Displays the negotiated and active settings of LACP parameters."
	::= { lacp 100 }

portStatusEntry	OBJECT-TYPE
	SYNTAX PortStatusEntry
	MAX-ACCESS not-accessible
	STATUS current
	DESCRIPTION
		""
	INDEX { portStatusPortIndex }
	::= { portStatusTable 1 }


	PortStatusEntry ::= SEQUENCE {
	portStatusPortIndex INTEGER,
	portStatusTrunkName DisplayString,
	portStatusTrunkId Integer32 ,
	portStatusActivityMode INTEGER ,
	portStatusSynchronized INTEGER ,
	portStatusAggregationPossible INTEGER ,
	portStatusCollection INTEGER ,
	portStatusDistribution INTEGER ,
	portStatusExpiredState INTEGER ,
	portStatusDefaultedState INTEGER
	}

portStatusPortIndex	OBJECT-TYPE
	SYNTAX INTEGER (0..24)
	MAX-ACCESS not-accessible
	STATUS current
	DESCRIPTION
		"Automatically generated"
	::= { portStatusEntry 1 }

portStatusTrunkName OBJECT-TYPE   -- trunk_name
	SYNTAX DisplayString
	MAX-ACCESS read-only
	STATUS current
	DESCRIPTION
	"Name of the trunk to which port is associated."
	::= { portStatusEntry 2 }

portStatusTrunkId OBJECT-TYPE   -- trunk_id
	SYNTAX Integer32 (0..255)
	MAX-ACCESS read-only
	STATUS current
	DESCRIPTION
	"interface index value of the trunk to which port is attached."
	::= { portStatusEntry 3 }

portStatusActivityMode OBJECT-TYPE   -- activity_mode
	SYNTAX INTEGER
		{
		passive (0),
		active (1)
		}
	MAX-ACCESS read-only
	STATUS current
	DESCRIPTION
	""
	::= { portStatusEntry 4 }

portStatusSynchronized OBJECT-TYPE   -- synchronized
	SYNTAX INTEGER { false(0), true(1) }
	MAX-ACCESS read-only
	STATUS current
	DESCRIPTION
	"True when trunk is synchronized."
	::= { portStatusEntry 5 }

portStatusAggregationPossible OBJECT-TYPE   -- aggregation_possible
	SYNTAX INTEGER { false(0), true(1) }
	MAX-ACCESS read-only
	STATUS current
	DESCRIPTION
	"Indicates link is aggregatable or not."
	::= { portStatusEntry 6 }

portStatusCollection OBJECT-TYPE   -- collection
	SYNTAX INTEGER { false(0), true(1) }
	MAX-ACCESS read-only
	STATUS current
	DESCRIPTION
	"Collection of incoming frames on this link is enabled or disabled."
	::= { portStatusEntry 7 }

portStatusDistribution OBJECT-TYPE   -- distribution
	SYNTAX INTEGER { false(0), true(1) }
	MAX-ACCESS read-only
	STATUS current
	DESCRIPTION
	"Distribution of outgoing frames on this link is enabled or disabled."
	::= { portStatusEntry 8 }

portStatusExpiredState OBJECT-TYPE   -- expired_state
	SYNTAX INTEGER { false(0), true(1) }
	MAX-ACCESS read-only
	STATUS current
	DESCRIPTION
	"True indicates that the actor is in the EXPIRED state"
	::= { portStatusEntry 9 }

portStatusDefaultedState OBJECT-TYPE   -- defaulted_state
	SYNTAX INTEGER { false(0), true(1) }
	MAX-ACCESS read-only
	STATUS current
	DESCRIPTION
	"When true default configured operational partner information are used. If false the partner information in use has been received in a LACP PDU."
	::= { portStatusEntry 10 }


-- ********************* End of portStatusTable ***********************


-- ******************* Begin of actorStatusTable *************************

actorStatusTable	OBJECT-TYPE
	SYNTAX SEQUENCE OF ActorStatusEntry
	MAX-ACCESS not-accessible
	STATUS current
	DESCRIPTION
		"Actor specific status values."
	::= { lacp 101 }

actorStatusEntry	OBJECT-TYPE
	SYNTAX ActorStatusEntry
	MAX-ACCESS not-accessible
	STATUS current
	DESCRIPTION
		""
	INDEX { actorStatusPortIndex }
	::= { actorStatusTable 1 }


	ActorStatusEntry ::= SEQUENCE {
	actorStatusPortIndex INTEGER,
	actorStatusSystemPriority Integer32 ,
	actorStatusSystemId MacAddress,
	actorStatusPort Integer32 ,
	actorStatusPriority Integer32 ,
	actorStatusAdminKey Integer32 ,
	actorStatusOperKey Integer32 ,
	actorStatusTransmitInterval INTEGER
	}

actorStatusPortIndex	OBJECT-TYPE
	SYNTAX INTEGER (0..24)
	MAX-ACCESS not-accessible
	STATUS current
	DESCRIPTION
		"Automatically generated"
	::= { actorStatusEntry 1 }

actorStatusSystemPriority OBJECT-TYPE   -- system_priority
	SYNTAX Integer32 (0..65535)
	MAX-ACCESS read-only
	STATUS current
	DESCRIPTION
	"Priority associated with the system"
	::= { actorStatusEntry 2 }

actorStatusSystemId OBJECT-TYPE   -- system_id
	SYNTAX MacAddress
	MAX-ACCESS read-only
	STATUS current
	DESCRIPTION
	"Mac address of the switch"
	::= { actorStatusEntry 3 }

actorStatusPort OBJECT-TYPE   -- port
	SYNTAX Integer32 (0..65535)
	MAX-ACCESS read-only
	STATUS current
	DESCRIPTION
	"Port number assigned by lacp which is local to LACP. "
	::= { actorStatusEntry 4 }

actorStatusPriority OBJECT-TYPE   -- priority
	SYNTAX Integer32 (0..65535)
	MAX-ACCESS read-only
	STATUS current
	DESCRIPTION
	"Priority assigned to the port."
	::= { actorStatusEntry 5 }

actorStatusAdminKey OBJECT-TYPE   -- admin_key
	SYNTAX Integer32 (0..65535)
	MAX-ACCESS read-only
	STATUS current
	DESCRIPTION
	"current administration key value of the port."
	::= { actorStatusEntry 6 }

actorStatusOperKey OBJECT-TYPE   -- oper_key
	SYNTAX Integer32 (0..65535)
	MAX-ACCESS read-only
	STATUS current
	DESCRIPTION
	"current operational key value of the port."
	::= { actorStatusEntry 7 }

actorStatusTransmitInterval OBJECT-TYPE   -- transmit_interval
	SYNTAX INTEGER
		{
		slow (0),
		fast (1)
		}
	MAX-ACCESS read-only
	STATUS current
	DESCRIPTION
	"Indicates the link partners transmit interval."
	::= { actorStatusEntry 8 }


-- ********************* End of actorStatusTable ***********************


-- ******************* Begin of partnerStatusTable *************************

partnerStatusTable	OBJECT-TYPE
	SYNTAX SEQUENCE OF PartnerStatusEntry
	MAX-ACCESS not-accessible
	STATUS current
	DESCRIPTION
		"Partner specific status values."
	::= { lacp 102 }

partnerStatusEntry	OBJECT-TYPE
	SYNTAX PartnerStatusEntry
	MAX-ACCESS not-accessible
	STATUS current
	DESCRIPTION
		""
	INDEX { partnerStatusPortIndex }
	::= { partnerStatusTable 1 }


	PartnerStatusEntry ::= SEQUENCE {
	partnerStatusPortIndex INTEGER,
	partnerStatusSystemPriority Integer32 ,
	partnerStatusSystemId MacAddress,
	partnerStatusPort Integer32 ,
	partnerStatusPriority Integer32 ,
	partnerStatusAdminKey Integer32 ,
	partnerStatusOperKey Integer32 ,
	partnerStatusReceiveInterval INTEGER ,
	partnerStatusActivityMode INTEGER ,
	partnerStatusSynchronized INTEGER ,
	partnerStatusAggregationPossible INTEGER ,
	partnerStatusCollection INTEGER ,
	partnerStatusDistribution INTEGER ,
	partnerStatusExpiredState INTEGER ,
	partnerStatusDefaultedState INTEGER
	}

partnerStatusPortIndex	OBJECT-TYPE
	SYNTAX INTEGER (0..24)
	MAX-ACCESS not-accessible
	STATUS current
	DESCRIPTION
		"Automatically generated"
	::= { partnerStatusEntry 1 }

partnerStatusSystemPriority OBJECT-TYPE   -- system_priority
	SYNTAX Integer32 (0..65535)
	MAX-ACCESS read-only
	STATUS current
	DESCRIPTION
	"Priority associated with the system"
	::= { partnerStatusEntry 2 }

partnerStatusSystemId OBJECT-TYPE   -- system_id
	SYNTAX MacAddress
	MAX-ACCESS read-only
	STATUS current
	DESCRIPTION
	"Mac address of the switch"
	::= { partnerStatusEntry 3 }

partnerStatusPort OBJECT-TYPE   -- port
	SYNTAX Integer32 (0..65535)
	MAX-ACCESS read-only
	STATUS current
	DESCRIPTION
	"Port number assigned by lacp which is local to LACP. "
	::= { partnerStatusEntry 4 }

partnerStatusPriority OBJECT-TYPE   -- priority
	SYNTAX Integer32 (0..65535)
	MAX-ACCESS read-only
	STATUS current
	DESCRIPTION
	"Priority assigned to the port."
	::= { partnerStatusEntry 5 }

partnerStatusAdminKey OBJECT-TYPE   -- admin_key
	SYNTAX Integer32 (0..65535)
	MAX-ACCESS read-only
	STATUS current
	DESCRIPTION
	"current administration key value of the port."
	::= { partnerStatusEntry 6 }

partnerStatusOperKey OBJECT-TYPE   -- oper_key
	SYNTAX Integer32 (0..65535)
	MAX-ACCESS read-only
	STATUS current
	DESCRIPTION
	"current operational key value of the port."
	::= { partnerStatusEntry 7 }

partnerStatusReceiveInterval OBJECT-TYPE   -- receive_interval
	SYNTAX INTEGER
		{
		slow (0),
		fast (1)
		}
	MAX-ACCESS read-only
	STATUS current
	DESCRIPTION
	"Partner requesting transmission interval from actor. TRUE send PDUs for every 1 sec, FALSE every 30 secs."
	::= { partnerStatusEntry 8 }

partnerStatusActivityMode OBJECT-TYPE   -- activity_mode
	SYNTAX INTEGER
		{
		passive (0),
		active (1)
		}
	MAX-ACCESS read-only
	STATUS current
	DESCRIPTION
	""
	::= { partnerStatusEntry 9 }

partnerStatusSynchronized OBJECT-TYPE   -- synchronized
	SYNTAX INTEGER { false(0), true(1) }
	MAX-ACCESS read-only
	STATUS current
	DESCRIPTION
	"True when trunk is synchronized."
	::= { partnerStatusEntry 10 }

partnerStatusAggregationPossible OBJECT-TYPE   -- aggregation_possible
	SYNTAX INTEGER { false(0), true(1) }
	MAX-ACCESS read-only
	STATUS current
	DESCRIPTION
	"Indicates link is aggregatable or not."
	::= { partnerStatusEntry 11 }

partnerStatusCollection OBJECT-TYPE   -- collection
	SYNTAX INTEGER { false(0), true(1) }
	MAX-ACCESS read-only
	STATUS current
	DESCRIPTION
	"Collection of incoming frames on this link is enabled or disabled."
	::= { partnerStatusEntry 12 }

partnerStatusDistribution OBJECT-TYPE   -- distribution
	SYNTAX INTEGER { false(0), true(1) }
	MAX-ACCESS read-only
	STATUS current
	DESCRIPTION
	"Distribution of outgoing frames on this link is enabled or disabled."
	::= { partnerStatusEntry 13 }

partnerStatusExpiredState OBJECT-TYPE   -- expired_state
	SYNTAX INTEGER { false(0), true(1) }
	MAX-ACCESS read-only
	STATUS current
	DESCRIPTION
	"True indicates that the actor is in the EXPIRED state"
	::= { partnerStatusEntry 14 }

partnerStatusDefaultedState OBJECT-TYPE   -- defaulted_state
	SYNTAX INTEGER { false(0), true(1) }
	MAX-ACCESS read-only
	STATUS current
	DESCRIPTION
	"When true default configured operational partner information are used. If false the partner information in use has been received in a LACP PDU."
	::= { partnerStatusEntry 15 }


-- ********************* End of partnerStatusTable ***********************



END
