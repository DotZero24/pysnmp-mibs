G6-IP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

device MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 1 }

ip  OBJECT IDENTIFIER ::= { device 22 }



-- *************************** CONFIGURATION SECTION ********************************


ipPingTest OBJECT-TYPE   -- ping_test
	SYNTAX DisplayString
	MAX-ACCESS read-write
	STATUS current
	DESCRIPTION
	"Supply an IP address to ping for reachability testing."
	::= { ip 1 }


ipTraceRoute OBJECT-TYPE   -- trace_route
	SYNTAX DisplayString
	MAX-ACCESS read-write
	STATUS current
	DESCRIPTION
	"Supply an IP address to trace route testing."
	::= { ip 2 }


ipDnsLookup OBJECT-TYPE   -- dns_lookup
	SYNTAX DisplayString
	MAX-ACCESS read-write
	STATUS current
	DESCRIPTION
	"Supply a hostname or web address to query for its ip address."
	::= { ip 3 }


ipArpTable OBJECT-TYPE   -- arp_table
	SYNTAX DisplayString
	MAX-ACCESS read-write
	STATUS current
	DESCRIPTION
	"Displays the content of the ARP table used for management access."
	::= { ip 4 }


ipHostname OBJECT-TYPE   -- hostname
	SYNTAX DisplayString
	MAX-ACCESS read-write
	STATUS current
	DESCRIPTION
	"Defines the local hostname."
	::= { ip 5 }


ipLocalMtu OBJECT-TYPE   -- local_mtu
	SYNTAX Integer32 (0..65535)
	MAX-ACCESS read-write
	STATUS current
	DESCRIPTION
	"Defines MTU value for locally generated data."
	::= { ip 6 }


-- ******************* Begin of v4ConfigTable *************************

v4ConfigTable	OBJECT-TYPE
	SYNTAX SEQUENCE OF V4ConfigEntry
	MAX-ACCESS not-accessible
	STATUS current
	DESCRIPTION
		"This section configures IP version 4 fixed IP settings or enables use of DHCP alternatively."
	::= { ip 7 }

v4ConfigEntry	OBJECT-TYPE
	SYNTAX V4ConfigEntry
	MAX-ACCESS not-accessible
	STATUS current
	DESCRIPTION
		""
	INDEX { v4ConfigIndex }
	::= { v4ConfigTable 1 }


	V4ConfigEntry ::= SEQUENCE {
	v4ConfigIndex INTEGER,
	v4ConfigDhcpMode INTEGER ,
	v4ConfigStaticDeviceIp OCTET STRING ,
	v4ConfigStaticSubnetMask OCTET STRING ,
	v4ConfigStaticGateway OCTET STRING ,
	v4ConfigStaticDnsServer OCTET STRING ,
	v4ConfigSecondaryDeviceIp OCTET STRING ,
	v4ConfigSecondarySubnetMask OCTET STRING ,
	v4ConfigDefaultAddressSelection INTEGER
	}

v4ConfigIndex	OBJECT-TYPE
	SYNTAX INTEGER (0)
	MAX-ACCESS not-accessible
	STATUS current
	DESCRIPTION
		"Automatically generated"
	::= { v4ConfigEntry 1 }

v4ConfigDhcpMode OBJECT-TYPE   -- dhcp_mode
	SYNTAX INTEGER
		{
		disabled (0),
		useDhcp (1),
		dhcpWithScript (2)
		}
	MAX-ACCESS read-write
	STATUS current
	DESCRIPTION
	"Enable DHCP to automatically retrieve an IP address and subnet mask. Also DHCP may be used to supply a CLI script file reference to be used on assignment."
	::= { v4ConfigEntry 2 }

v4ConfigStaticDeviceIp OBJECT-TYPE   -- static_device_ip
	SYNTAX OCTET STRING (SIZE (0..20))
	MAX-ACCESS read-write
	STATUS current
	DESCRIPTION
	"Static device IP address. When DHCP is enabled, DHCP has preference over this setting."
	::= { v4ConfigEntry 3 }

v4ConfigStaticSubnetMask OBJECT-TYPE   -- static_subnet_mask
	SYNTAX OCTET STRING (SIZE (0..20))
	MAX-ACCESS read-write
	STATUS current
	DESCRIPTION
	"Static subnet mask. When DHCP is enabled, DHCP has preference over this setting."
	::= { v4ConfigEntry 4 }

v4ConfigStaticGateway OBJECT-TYPE   -- static_gateway
	SYNTAX OCTET STRING (SIZE (0..20))
	MAX-ACCESS read-write
	STATUS current
	DESCRIPTION
	"Static default gateway IP address. When DHCP is enabled, DHCP has preference over this setting."
	::= { v4ConfigEntry 5 }

v4ConfigStaticDnsServer OBJECT-TYPE   -- static_dns_server
	SYNTAX OCTET STRING (SIZE (0..20))
	MAX-ACCESS read-write
	STATUS current
	DESCRIPTION
	"Static domain name server IP address. When DHCP is enabled, DHCP has preference over this setting."
	::= { v4ConfigEntry 6 }

v4ConfigSecondaryDeviceIp OBJECT-TYPE   -- secondary_device_ip
	SYNTAX OCTET STRING (SIZE (0..20))
	MAX-ACCESS read-write
	STATUS current
	DESCRIPTION
	"Alternative IP address for management access. Not required in most installations."
	::= { v4ConfigEntry 7 }

v4ConfigSecondarySubnetMask OBJECT-TYPE   -- secondary_subnet_mask
	SYNTAX OCTET STRING (SIZE (0..20))
	MAX-ACCESS read-write
	STATUS current
	DESCRIPTION
	"This subnet mask applies to secondary ip address."
	::= { v4ConfigEntry 8 }

v4ConfigDefaultAddressSelection OBJECT-TYPE   -- default_address_selection
	SYNTAX INTEGER
		{
		primary (0),
		secondary (1)
		}
	MAX-ACCESS read-write
	STATUS current
	DESCRIPTION
	"This parameter defines which own ip address is used for outgoing packets generated by the device. This only applies when a secondary_device_ip is configured."
	::= { v4ConfigEntry 9 }


-- ********************* End of v4ConfigTable ***********************


-- ******************* Begin of v6ConfigTable *************************

v6ConfigTable	OBJECT-TYPE
	SYNTAX SEQUENCE OF V6ConfigEntry
	MAX-ACCESS not-accessible
	STATUS current
	DESCRIPTION
		"This section configures IP version 6 fixed IP settings or enables use of automatic configuration alternatively."
	::= { ip 8 }

v6ConfigEntry	OBJECT-TYPE
	SYNTAX V6ConfigEntry
	MAX-ACCESS not-accessible
	STATUS current
	DESCRIPTION
		""
	INDEX { v6ConfigIndex }
	::= { v6ConfigTable 1 }


	V6ConfigEntry ::= SEQUENCE {
	v6ConfigIndex INTEGER,
	v6ConfigEnableIpv6 INTEGER ,
	v6ConfigEnableIcmpAutoAddress INTEGER ,
	v6ConfigEnableDhcpAutoAddress INTEGER
	}

v6ConfigIndex	OBJECT-TYPE
	SYNTAX INTEGER (0)
	MAX-ACCESS not-accessible
	STATUS current
	DESCRIPTION
		"Automatically generated"
	::= { v6ConfigEntry 1 }

v6ConfigEnableIpv6 OBJECT-TYPE   -- enable_ipv6
	SYNTAX INTEGER {  disabled(0), enabled(1) }
	MAX-ACCESS read-write
	STATUS current
	DESCRIPTION
	"General enable of IPv6 management access functionality."
	::= { v6ConfigEntry 2 }

v6ConfigEnableIcmpAutoAddress OBJECT-TYPE   -- enable_icmp_auto_address
	SYNTAX INTEGER {  disabled(0), enabled(1) }
	MAX-ACCESS read-write
	STATUS current
	DESCRIPTION
	"Decides if an ICMP assigned IPv6 address is accepted."
	::= { v6ConfigEntry 3 }

v6ConfigEnableDhcpAutoAddress OBJECT-TYPE   -- enable_dhcp_auto_address
	SYNTAX INTEGER {  disabled(0), enabled(1) }
	MAX-ACCESS read-write
	STATUS current
	DESCRIPTION
	"Decides if an DHCP assigned IPv6 address is accepted."
	::= { v6ConfigEntry 4 }


-- ********************* End of v6ConfigTable ***********************


-- ******************* Begin of v6AddressTable *************************

v6AddressTable	OBJECT-TYPE
	SYNTAX SEQUENCE OF V6AddressEntry
	MAX-ACCESS not-accessible
	STATUS current
	DESCRIPTION
		"Defines as many static IPv6 address entries as desired."
	::= { ip 9 }

v6AddressEntry	OBJECT-TYPE
	SYNTAX V6AddressEntry
	MAX-ACCESS not-accessible
	STATUS current
	DESCRIPTION
		""
	INDEX { v6AddressIndex }
	::= { v6AddressTable 1 }


	V6AddressEntry ::= SEQUENCE {
	v6AddressIndex INTEGER,
	v6AddressIp DisplayString
	}

v6AddressIndex	OBJECT-TYPE
	SYNTAX INTEGER (0..7)
	MAX-ACCESS not-accessible
	STATUS current
	DESCRIPTION
		"Automatically generated"
	::= { v6AddressEntry 1 }

v6AddressIp OBJECT-TYPE   -- ip
	SYNTAX DisplayString
	MAX-ACCESS read-write
	STATUS current
	DESCRIPTION
	"IPv6 address"
	::= { v6AddressEntry 2 }


-- ********************* End of v6AddressTable ***********************



-- ****************************** STATUS SECTION ********************************


-- ******************* Begin of v4StatusTable *************************

v4StatusTable	OBJECT-TYPE
	SYNTAX SEQUENCE OF V4StatusEntry
	MAX-ACCESS not-accessible
	STATUS current
	DESCRIPTION
		"This section shows a summary of IPv4 settings as they are currently active. These may reflect the statically configured values or may be dynamically assigned using DHCP."
	::= { ip 100 }

v4StatusEntry	OBJECT-TYPE
	SYNTAX V4StatusEntry
	MAX-ACCESS not-accessible
	STATUS current
	DESCRIPTION
		""
	INDEX { v4StatusIndex }
	::= { v4StatusTable 1 }


	V4StatusEntry ::= SEQUENCE {
	v4StatusIndex INTEGER,
	v4StatusDynamicDeviceIp OCTET STRING ,
	v4StatusDynamicSubnetMask OCTET STRING ,
	v4StatusDynamicGateway OCTET STRING ,
	v4StatusDynamicDnsServer1 OCTET STRING ,
	v4StatusDynamicDnsServer2 OCTET STRING ,
	v4StatusDynamicDnsServer3 OCTET STRING ,
	v4StatusDynamicDnsServer4 OCTET STRING ,
	v4StatusOutgoingDeviceIp OCTET STRING
	}

v4StatusIndex	OBJECT-TYPE
	SYNTAX INTEGER (0)
	MAX-ACCESS not-accessible
	STATUS current
	DESCRIPTION
		"Automatically generated"
	::= { v4StatusEntry 1 }

v4StatusDynamicDeviceIp OBJECT-TYPE   -- dynamic_device_ip
	SYNTAX OCTET STRING (SIZE (0..20))
	MAX-ACCESS read-only
	STATUS current
	DESCRIPTION
	"Currently used device IP address."
	::= { v4StatusEntry 2 }

v4StatusDynamicSubnetMask OBJECT-TYPE   -- dynamic_subnet_mask
	SYNTAX OCTET STRING (SIZE (0..20))
	MAX-ACCESS read-only
	STATUS current
	DESCRIPTION
	"Currently used subnet mask."
	::= { v4StatusEntry 3 }

v4StatusDynamicGateway OBJECT-TYPE   -- dynamic_gateway
	SYNTAX OCTET STRING (SIZE (0..20))
	MAX-ACCESS read-only
	STATUS current
	DESCRIPTION
	"Currently used gateway IP address."
	::= { v4StatusEntry 4 }

v4StatusDynamicDnsServer1 OBJECT-TYPE   -- dynamic_dns_server_1
	SYNTAX OCTET STRING (SIZE (0..20))
	MAX-ACCESS read-only
	STATUS current
	DESCRIPTION
	"Currently used domain name server IP address."
	::= { v4StatusEntry 5 }

v4StatusDynamicDnsServer2 OBJECT-TYPE   -- dynamic_dns_server_2
	SYNTAX OCTET STRING (SIZE (0..20))
	MAX-ACCESS read-only
	STATUS current
	DESCRIPTION
	"Alternate currently used domain name server IP address."
	::= { v4StatusEntry 6 }

v4StatusDynamicDnsServer3 OBJECT-TYPE   -- dynamic_dns_server_3
	SYNTAX OCTET STRING (SIZE (0..20))
	MAX-ACCESS read-only
	STATUS current
	DESCRIPTION
	"Alternate currently used domain name server IP address."
	::= { v4StatusEntry 7 }

v4StatusDynamicDnsServer4 OBJECT-TYPE   -- dynamic_dns_server_4
	SYNTAX OCTET STRING (SIZE (0..20))
	MAX-ACCESS read-only
	STATUS current
	DESCRIPTION
	"Alternate currently used domain name server IP address."
	::= { v4StatusEntry 8 }

v4StatusOutgoingDeviceIp OBJECT-TYPE   -- outgoing_device_ip
	SYNTAX OCTET STRING (SIZE (0..20))
	MAX-ACCESS read-only
	STATUS current
	DESCRIPTION
	"Reflects the value v4_config.default_address_selection setting."
	::= { v4StatusEntry 9 }


-- ********************* End of v4StatusTable ***********************


-- ******************* Begin of v6StatusTable *************************

v6StatusTable	OBJECT-TYPE
	SYNTAX SEQUENCE OF V6StatusEntry
	MAX-ACCESS not-accessible
	STATUS current
	DESCRIPTION
		"This section shows a summary of IPv6 settings as they are currently active. These may reflect the statically configured values or may be dynamically assigned using DHCP or ICMP."
	::= { ip 101 }

v6StatusEntry	OBJECT-TYPE
	SYNTAX V6StatusEntry
	MAX-ACCESS not-accessible
	STATUS current
	DESCRIPTION
		""
	INDEX { v6StatusIndex }
	::= { v6StatusTable 1 }


	V6StatusEntry ::= SEQUENCE {
	v6StatusIndex INTEGER,
	v6StatusIp OCTET STRING ,
	v6StatusScope INTEGER ,
	v6StatusState INTEGER
	}

v6StatusIndex	OBJECT-TYPE
	SYNTAX INTEGER (0..7)
	MAX-ACCESS not-accessible
	STATUS current
	DESCRIPTION
		"Automatically generated"
	::= { v6StatusEntry 1 }

v6StatusIp OBJECT-TYPE   -- ip
	SYNTAX OCTET STRING (SIZE (0..50))
	MAX-ACCESS read-only
	STATUS current
	DESCRIPTION
	"IPv6 address."
	::= { v6StatusEntry 2 }

v6StatusScope OBJECT-TYPE   -- scope
	SYNTAX INTEGER
		{
		link (0),
		site (1),
		global (2),
		other (3)
		}
	MAX-ACCESS read-only
	STATUS current
	DESCRIPTION
	"Indicates the scope this IP is valid."
	::= { v6StatusEntry 3 }

v6StatusState OBJECT-TYPE   -- state
	SYNTAX INTEGER
		{
		stateless (0),
		stateful (1),
		both (2),
		other (3)
		}
	MAX-ACCESS read-only
	STATUS current
	DESCRIPTION
	"Indicates the state of this IP."
	::= { v6StatusEntry 4 }


-- ********************* End of v6StatusTable ***********************



END
