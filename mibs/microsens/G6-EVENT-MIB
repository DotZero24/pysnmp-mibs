G6-EVENT-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

event  OBJECT IDENTIFIER ::= { management 70 }



-- *************************** CONFIGURATION SECTION ********************************


-- ******************* Begin of eventListTable *************************

eventListTable	OBJECT-TYPE
	SYNTAX SEQUENCE OF EventListEntry
	MAX-ACCESS not-accessible
	STATUS current
	DESCRIPTION
		""
	::= { event 1 }

eventListEntry	OBJECT-TYPE
	SYNTAX EventListEntry
	MAX-ACCESS not-accessible
	STATUS current
	DESCRIPTION
		""
	INDEX { eventListIndex }
	::= { eventListTable 1 }


	EventListEntry ::= SEQUENCE {
	eventListIndex INTEGER,
	eventListName DisplayString,
	eventListGroup INTEGER ,
	eventListRelevance INTEGER ,
	eventListInternal INTEGER ,
	eventListSeverity INTEGER ,
	eventListSource INTEGER ,
	eventListTrap INTEGER ,
	eventListSyslogMessage DisplayString,
	eventListCustomMessage DisplayString,
	eventListIntegerElements DisplayString,
	eventListStringElements DisplayString,
	eventListCliScript DisplayString
	}

eventListIndex	OBJECT-TYPE
	SYNTAX INTEGER (0..127)
	MAX-ACCESS not-accessible
	STATUS current
	DESCRIPTION
		"Automatically generated"
	::= { eventListEntry 1 }

eventListName OBJECT-TYPE   -- name
	SYNTAX DisplayString
	MAX-ACCESS read-only
	STATUS current
	DESCRIPTION
	"Name of the event"
	::= { eventListEntry 2 }

eventListGroup OBJECT-TYPE   -- group
	SYNTAX INTEGER
		{
		internal (0),
		debug (2),
		test (3),
		reset (4),
		firmware (5),
		system (6),
		config (7),
		login (8),
		auth (9),
		power (10),
		temperature (11),
		link (12),
		sfp (13),
		poe (14),
		ring (15),
		ntp (16),
		signals (17),
		script (18),
		filter (19),
		lacp (20),
		app (21),
		cable (22),
		security (23),
		msp1000 (24),
		backup (25),
		fan (26),
		messaging (27),
		terminalServer (28),
		smartOffice (29)
		}
	MAX-ACCESS read-only
	STATUS current
	DESCRIPTION
	"Associated group of this event"
	::= { eventListEntry 3 }

eventListRelevance OBJECT-TYPE   -- relevance
	SYNTAX INTEGER
		{
		pos (0),
		neg (1),
		info (2)
		}
	MAX-ACCESS read-only
	STATUS current
	DESCRIPTION
	"Positive, negative or informational event"
	::= { eventListEntry 4 }

eventListInternal OBJECT-TYPE   -- internal
	SYNTAX INTEGER {  disabled(0), enabled(1) }
	MAX-ACCESS read-only
	STATUS current
	DESCRIPTION
	"If enabled this event cannot be used for syslog or traps"
	::= { eventListEntry 5 }

eventListSeverity OBJECT-TYPE   -- severity
	SYNTAX INTEGER
		{
		disabled (0),
		debug (1),
		info (2),
		notice (3),
		warning (4),
		error (5),
		critical (6),
		alert (7),
		emergency (8)
		}
	MAX-ACCESS read-write
	STATUS current
	DESCRIPTION
	"Severity level of this event. Can be modified if required"
	::= { eventListEntry 6 }

eventListSource OBJECT-TYPE   -- source
	SYNTAX INTEGER
		{
		unit (0),
		port (1)
		}
	MAX-ACCESS read-only
	STATUS current
	DESCRIPTION
	"Unit or port related event"
	::= { eventListEntry 7 }

eventListTrap OBJECT-TYPE   -- trap
	SYNTAX INTEGER {  disabled(0), enabled(1) }
	MAX-ACCESS read-write
	STATUS current
	DESCRIPTION
	"When enabled a trap may be generated for this event"
	::= { eventListEntry 8 }

eventListSyslogMessage OBJECT-TYPE   -- syslog_message
	SYNTAX DisplayString
	MAX-ACCESS read-only
	STATUS current
	DESCRIPTION
	"Fixed event text describing the cause of the event."
	::= { eventListEntry 9 }

eventListCustomMessage OBJECT-TYPE   -- custom_message
	SYNTAX DisplayString
	MAX-ACCESS read-write
	STATUS current
	DESCRIPTION
	"Here a custom or translated version of the event text may be inserted."
	::= { eventListEntry 10 }

eventListIntegerElements OBJECT-TYPE   -- integer_elements
	SYNTAX DisplayString
	MAX-ACCESS read-only
	STATUS current
	DESCRIPTION
	"Lists which integer value informations are available for the syslog message"
	::= { eventListEntry 11 }

eventListStringElements OBJECT-TYPE   -- string_elements
	SYNTAX DisplayString
	MAX-ACCESS read-only
	STATUS current
	DESCRIPTION
	"Lists which string type informations are available for the syslog message"
	::= { eventListEntry 12 }

eventListCliScript OBJECT-TYPE   -- cli_script
	SYNTAX DisplayString
	MAX-ACCESS read-write
	STATUS current
	DESCRIPTION
	"When a script name is present the script will be executed whenever this event occurs. Note: Internal events do not trigger scripts even though a script name may be entered. Several scripts may be assigned to a single event. Syntax: app/scriptfile:subroutine para1 para2, next script... All fields besides the scriptfile are optional."
	::= { eventListEntry 13 }


-- ********************* End of eventListTable ***********************



-- ****************************** STATUS SECTION ********************************



END
