G6-MSP1000-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

device MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 1 }

msp1000  OBJECT IDENTIFIER ::= { device 94 }



-- *************************** CONFIGURATION SECTION ********************************


-- ******************* Begin of systemConfigTable *************************

systemConfigTable	OBJECT-TYPE
	SYNTAX SEQUENCE OF SystemConfigEntry
	MAX-ACCESS not-accessible
	STATUS current
	DESCRIPTION
		""
	::= { msp1000 1 }

systemConfigEntry	OBJECT-TYPE
	SYNTAX SystemConfigEntry
	MAX-ACCESS not-accessible
	STATUS current
	DESCRIPTION
		""
	INDEX { systemConfigIndex }
	::= { systemConfigTable 1 }


	SystemConfigEntry ::= SEQUENCE {
	systemConfigIndex INTEGER,
	systemConfigNmsOperationMode INTEGER ,
	systemConfigCoreMode INTEGER ,
	systemConfigNodeId Unsigned32,
	systemConfigDisableLegacyAccess INTEGER
	}

systemConfigIndex	OBJECT-TYPE
	SYNTAX INTEGER (0)
	MAX-ACCESS not-accessible
	STATUS current
	DESCRIPTION
		"Automatically generated"
	::= { systemConfigEntry 1 }

systemConfigNmsOperationMode OBJECT-TYPE   -- nms_operation_mode
	SYNTAX INTEGER
		{
		passive (0),
		active (1)
		}
	MAX-ACCESS read-write
	STATUS current
	DESCRIPTION
	"Read and learn in PASSIVE mode or ACTIVE mode forcing configuration upon the other modules."
	::= { systemConfigEntry 2 }

systemConfigCoreMode OBJECT-TYPE   -- core_mode
	SYNTAX INTEGER
		{
		v1 (0),
		v2 (1)
		}
	MAX-ACCESS read-write
	STATUS current
	DESCRIPTION
	"Use V2 unless used with an older system running in V1 mode. Only change when instructed."
	::= { systemConfigEntry 3 }

systemConfigNodeId OBJECT-TYPE   -- node_id
	SYNTAX Unsigned32
	MAX-ACCESS read-write
	STATUS current
	DESCRIPTION
	"Node Id used when NMS is used in combination with SEEmiles V5 management software. When in doubt use default node id 60000."
	::= { systemConfigEntry 4 }

systemConfigDisableLegacyAccess OBJECT-TYPE   -- disable_legacy_access
	SYNTAX INTEGER {  disabled(0), enabled(1) }
	MAX-ACCESS read-write
	STATUS current
	DESCRIPTION
	"When set network access via SEEmiles is no longer possible."
	::= { systemConfigEntry 5 }


-- ********************* End of systemConfigTable ***********************


-- ******************* Begin of slotConfigTable *************************

slotConfigTable	OBJECT-TYPE
	SYNTAX SEQUENCE OF SlotConfigEntry
	MAX-ACCESS not-accessible
	STATUS current
	DESCRIPTION
		""
	::= { msp1000 2 }

slotConfigEntry	OBJECT-TYPE
	SYNTAX SlotConfigEntry
	MAX-ACCESS not-accessible
	STATUS current
	DESCRIPTION
		""
	INDEX { slotConfigIndex }
	::= { slotConfigTable 1 }


	SlotConfigEntry ::= SEQUENCE {
	slotConfigIndex INTEGER,
	slotConfigModule INTEGER ,
	slotConfigSparepartMode INTEGER ,
	slotConfigPort1Alias DisplayString,
	slotConfigPort2Alias DisplayString,
	slotConfigPort3Alias DisplayString,
	slotConfigPort4Alias DisplayString
	}

slotConfigIndex	OBJECT-TYPE
	SYNTAX INTEGER (0..11)
	MAX-ACCESS not-accessible
	STATUS current
	DESCRIPTION
		"Automatically generated"
	::= { slotConfigEntry 1 }

slotConfigModule OBJECT-TYPE   -- module
	SYNTAX INTEGER
		{
		undefined (0),
		empty (1),
		legacy (2),
		passive (3),
		x2g (61),
		txg (63),
		cxg (87),
		t4g (62),
		em2 (105),
		em3 (109),
		om1 (104),
		lp1 (106),
		os1 (72),
		m2g (56),
		cxgp (88),
		nm1 (65),
		nm2 (66),
		nm3 (108),
		nm3p (110),
		xcm1 (60),
		tdm4 (50),
		wcm2 (57),
		fc8Filter (10),
		fc8aFilter (11),
		fc8xFilter (12),
		b4sFilter (13),
		b4xFilter (14),
		b8mFilter (15),
		b8dFilter (16),
		fd4Filter (17),
		dc1Filter (18),
		se1 (19)
		}
	MAX-ACCESS read-write
	STATUS current
	DESCRIPTION
	"Defines which module is expected to be placed in this slot. This should be identical to the actual hardware. The value may be set prior to actual roll-out to preconfigure the system."
	::= { slotConfigEntry 2 }

slotConfigSparepartMode OBJECT-TYPE   -- sparepart_mode
	SYNTAX INTEGER {  disabled(0), enabled(1) }
	MAX-ACCESS read-write
	STATUS current
	DESCRIPTION
	"When enabled the module is operating normally but will not generate any alarms. This is useful for modules that are inserted but only used as spare and are not properly connected at this time. This way unnecassary alarms are avoided."
	::= { slotConfigEntry 3 }

slotConfigPort1Alias OBJECT-TYPE   -- port_1_alias
	SYNTAX DisplayString
	MAX-ACCESS read-write
	STATUS current
	DESCRIPTION
	"User defined port name for easier reference."
	::= { slotConfigEntry 4 }

slotConfigPort2Alias OBJECT-TYPE   -- port_2_alias
	SYNTAX DisplayString
	MAX-ACCESS read-write
	STATUS current
	DESCRIPTION
	"User defined port name for easier reference."
	::= { slotConfigEntry 5 }

slotConfigPort3Alias OBJECT-TYPE   -- port_3_alias
	SYNTAX DisplayString
	MAX-ACCESS read-write
	STATUS current
	DESCRIPTION
	"User defined port name for easier reference."
	::= { slotConfigEntry 6 }

slotConfigPort4Alias OBJECT-TYPE   -- port_4_alias
	SYNTAX DisplayString
	MAX-ACCESS read-write
	STATUS current
	DESCRIPTION
	"User defined port name for easier reference."
	::= { slotConfigEntry 7 }


-- ********************* End of slotConfigTable ***********************


-- ******************* Begin of x2gConfigTable *************************

x2gConfigTable	OBJECT-TYPE
	SYNTAX SEQUENCE OF X2gConfigEntry
	MAX-ACCESS not-accessible
	STATUS current
	DESCRIPTION
		"This table is used to define any X2G or OFX-3 modules in the system."
	::= { msp1000 3 }

x2gConfigEntry	OBJECT-TYPE
	SYNTAX X2gConfigEntry
	MAX-ACCESS not-accessible
	STATUS current
	DESCRIPTION
		""
	INDEX { x2gConfigIndex }
	::= { x2gConfigTable 1 }


	X2gConfigEntry ::= SEQUENCE {
	x2gConfigIndex INTEGER,
	x2gConfigPort1Datarate INTEGER ,
	x2gConfigPort2Datarate INTEGER ,
	x2gConfigPort3Datarate INTEGER ,
	x2gConfigPort4Datarate INTEGER ,
	x2gConfigCrossConnect INTEGER ,
	x2gConfigDeactivatePort1 INTEGER ,
	x2gConfigDeactivatePort2 INTEGER ,
	x2gConfigDeactivatePort3 INTEGER ,
	x2gConfigDeactivatePort4 INTEGER ,
	x2gConfigFrontPanelMode INTEGER ,
	x2gConfigLossOfSignalHandling INTEGER ,
	x2gConfigOptimizedFor8b10b INTEGER ,
	x2gConfigBertPattern INTEGER ,
	x2gConfigSfpDeltaInterval INTEGER ,
	x2gConfigSfpDeltaThreshold INTEGER ,
	x2gConfigBackupTrigger INTEGER ,
	x2gConfigStayWithLastLink INTEGER ,
	x2gConfigBackupEnd INTEGER ,
	x2gConfigPermitLinkOverride INTEGER
	}

x2gConfigIndex	OBJECT-TYPE
	SYNTAX INTEGER (0..11)
	MAX-ACCESS not-accessible
	STATUS current
	DESCRIPTION
		"Automatically generated"
	::= { x2gConfigEntry 1 }

x2gConfigPort1Datarate OBJECT-TYPE   -- port_1_datarate
	SYNTAX INTEGER
		{
		transparent (0),
		ms100mEth (2),
		ms1gEth (8),
		ms1xFc (7),
		ms2xFc (10),
		oc3 (3),
		oc12 (6),
		oc48 (11),
		otu1 (13),
		fix100 (1),
		escon (4),
		sdi (5),
		hdtv (9),
		m2g (12)
		}
	MAX-ACCESS read-write
	STATUS current
	DESCRIPTION
	"This parameter defines the data rate used to setup the internal retimer to provide 3R regeneration. Note that internally interconnected ports must be set to the same rate."
	::= { x2gConfigEntry 2 }

x2gConfigPort2Datarate OBJECT-TYPE   -- port_2_datarate
	SYNTAX INTEGER
		{
		transparent (0),
		ms100mEth (2),
		ms1gEth (8),
		ms1xFc (7),
		ms2xFc (10),
		oc3 (3),
		oc12 (6),
		oc48 (11),
		otu1 (13),
		fix100 (1),
		escon (4),
		sdi (5),
		hdtv (9),
		m2g (12)
		}
	MAX-ACCESS read-write
	STATUS current
	DESCRIPTION
	"This parameter defines the data rate used to setup the internal retimer to provide 3R regeneration. Note that internally interconnected ports must be set to the same rate."
	::= { x2gConfigEntry 3 }

x2gConfigPort3Datarate OBJECT-TYPE   -- port_3_datarate
	SYNTAX INTEGER
		{
		transparent (0),
		ms100mEth (2),
		ms1gEth (8),
		ms1xFc (7),
		ms2xFc (10),
		oc3 (3),
		oc12 (6),
		oc48 (11),
		otu1 (13),
		fix100 (1),
		escon (4),
		sdi (5),
		hdtv (9),
		m2g (12)
		}
	MAX-ACCESS read-write
	STATUS current
	DESCRIPTION
	"This parameter defines the data rate used to setup the internal retimer to provide 3R regeneration. Note that internally interconnected ports must be set to the same rate."
	::= { x2gConfigEntry 4 }

x2gConfigPort4Datarate OBJECT-TYPE   -- port_4_datarate
	SYNTAX INTEGER
		{
		transparent (0),
		ms100mEth (2),
		ms1gEth (8),
		ms1xFc (7),
		ms2xFc (10),
		oc3 (3),
		oc12 (6),
		oc48 (11),
		otu1 (13),
		fix100 (1),
		escon (4),
		sdi (5),
		hdtv (9),
		m2g (12)
		}
	MAX-ACCESS read-write
	STATUS current
	DESCRIPTION
	"This parameter defines the data rate used to setup the internal retimer to provide 3R regeneration. Note that internally interconnected ports must be set to the same rate."
	::= { x2gConfigEntry 5 }

x2gConfigCrossConnect OBJECT-TYPE   -- cross_connect
	SYNTAX INTEGER
		{
		disconnect (0),
		normal (20),
		alternate (1),
		backup (5),
		ringBackupWest (9),
		ringBackupEast (15),
		multicast (11),
		dropContinue (12),
		addDropWest (13),
		addDropEast (14),
		crossOver (16),
		switchP1P2 (17),
		switchP1P3 (18),
		switchP1P4 (19),
		bertPort4 (21)
		}
	MAX-ACCESS read-write
	STATUS current
	DESCRIPTION
	"This parameter defines the data path through the module. It is also used to setup a permanent bit error rate test."
	::= { x2gConfigEntry 6 }

x2gConfigDeactivatePort1 OBJECT-TYPE   -- deactivate_port_1
	SYNTAX INTEGER {  disabled(0), enabled(1) }
	MAX-ACCESS read-write
	STATUS current
	DESCRIPTION
	"When enabled, the optical interface is disabled and communication is cut."
	::= { x2gConfigEntry 7 }

x2gConfigDeactivatePort2 OBJECT-TYPE   -- deactivate_port_2
	SYNTAX INTEGER {  disabled(0), enabled(1) }
	MAX-ACCESS read-write
	STATUS current
	DESCRIPTION
	"When enabled, the optical interface is disabled and communication is cut."
	::= { x2gConfigEntry 8 }

x2gConfigDeactivatePort3 OBJECT-TYPE   -- deactivate_port_3
	SYNTAX INTEGER {  disabled(0), enabled(1) }
	MAX-ACCESS read-write
	STATUS current
	DESCRIPTION
	"When enabled, the optical interface is disabled and communication is cut."
	::= { x2gConfigEntry 9 }

x2gConfigDeactivatePort4 OBJECT-TYPE   -- deactivate_port_4
	SYNTAX INTEGER {  disabled(0), enabled(1) }
	MAX-ACCESS read-write
	STATUS current
	DESCRIPTION
	"When enabled, the optical interface is disabled and communication is cut."
	::= { x2gConfigEntry 10 }

x2gConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { x2gConfigEntry 11 }

x2gConfigLossOfSignalHandling OBJECT-TYPE   -- loss_of_signal_handling
	SYNTAX INTEGER
		{
		local (0),
		percolate (1)
		}
	MAX-ACCESS read-write
	STATUS current
	DESCRIPTION
	"When set to LOCAL a loss of input signal will not affect another port. When set to PERCOLATE, a loss of signal will turn off the transmitter of the currently associated port."
	::= { x2gConfigEntry 12 }

x2gConfigOptimizedFor8b10b OBJECT-TYPE   -- optimized_for_8b10b
	SYNTAX INTEGER {  disabled(0), enabled(1) }
	MAX-ACCESS read-write
	STATUS current
	DESCRIPTION
	"Enable this feature when Ethernet or FibreChannel is used. Do not set when SDH is used on any port."
	::= { x2gConfigEntry 13 }

x2gConfigBertPattern OBJECT-TYPE   -- bert_pattern
	SYNTAX INTEGER
		{
		ms27 (0),
		ms223 (2),
		ms231 (3),
		cjPat (4),
		crPat (5),
		ms8b10bCnt (6)
		}
	MAX-ACCESS read-write
	STATUS current
	DESCRIPTION
	"Defines the bit pattern with which the build-in bit error rate tester (BERT) operates when cross connect is set to BERT."
	::= { x2gConfigEntry 14 }

x2gConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP is read and compared to previous value."
	::= { x2gConfigEntry 15 }

x2gConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { x2gConfigEntry 16 }

x2gConfigBackupTrigger OBJECT-TYPE   -- backup_trigger
	SYNTAX INTEGER
		{
		disabled (0),
		signalLoss (1),
		clockLoss (2)
		}
	MAX-ACCESS read-write
	STATUS current
	DESCRIPTION
	"Defines under which optical signal condition an automated backup is initiated."
	::= { x2gConfigEntry 17 }

x2gConfigStayWithLastLink OBJECT-TYPE   -- stay_with_last_link
	SYNTAX INTEGER {  disabled(0), enabled(1) }
	MAX-ACCESS read-write
	STATUS current
	DESCRIPTION
	"When set the backup switch remains in last position even when signal returns. Still the backup warning turns off after the delay set under backup_end parameter expires."
	::= { x2gConfigEntry 18 }

x2gConfigBackupEnd OBJECT-TYPE   -- backup_end
	SYNTAX INTEGER
		{
		noDelay (0),
		ms15Seconds (1),
		ms15Minutes (2),
		manually (3)
		}
	MAX-ACCESS read-write
	STATUS current
	DESCRIPTION
	"Defines how long the signal must remain steady before proper operation is assumed and the backup is terminated."
	::= { x2gConfigEntry 19 }

x2gConfigPermitLinkOverride OBJECT-TYPE   -- permit_link_override
	SYNTAX INTEGER {  disabled(0), enabled(1) }
	MAX-ACCESS read-write
	STATUS current
	DESCRIPTION
	"Permits the manual selection of a failed link using the link selection. Defaults to false to safeguard against accidential link selection which would result in loss of connection."
	::= { x2gConfigEntry 20 }


-- ********************* End of x2gConfigTable ***********************


-- ******************* Begin of txgConfigTable *************************

txgConfigTable	OBJECT-TYPE
	SYNTAX SEQUENCE OF TxgConfigEntry
	MAX-ACCESS not-accessible
	STATUS current
	DESCRIPTION
		"This table is used to define any TXG or XCM-2 modules in the system."
	::= { msp1000 4 }

txgConfigEntry	OBJECT-TYPE
	SYNTAX TxgConfigEntry
	MAX-ACCESS not-accessible
	STATUS current
	DESCRIPTION
		""
	INDEX { txgConfigIndex }
	::= { txgConfigTable 1 }


	TxgConfigEntry ::= SEQUENCE {
	txgConfigIndex INTEGER,
	txgConfigTxgDatarate INTEGER ,
	txgConfigTxgOperationMode INTEGER ,
	txgConfigPort1ItuChannel INTEGER ,
	txgConfigPort2ItuChannel INTEGER ,
	txgConfigDeactivatePort1 INTEGER ,
	txgConfigDeactivatePort2 INTEGER ,
	txgConfigFrontPanelMode INTEGER ,
	txgConfigLossOfSignalHandling INTEGER ,
	txgConfigBertPattern INTEGER ,
	txgConfigSfpDeltaInterval INTEGER ,
	txgConfigSfpDeltaThreshold INTEGER
	}

txgConfigIndex	OBJECT-TYPE
	SYNTAX INTEGER (0..11)
	MAX-ACCESS not-accessible
	STATUS current
	DESCRIPTION
		"Automatically generated"
	::= { txgConfigEntry 1 }

txgConfigTxgDatarate OBJECT-TYPE   -- txg_datarate
	SYNTAX INTEGER
		{
		oc192 (1),
		oc192Fec (3),
		ms10gEth (2),
		ms10xFc (5),
		otu2 (4),
		otu1f (7),
		otu2e (6),
		otu2f (8)
		}
	MAX-ACCESS read-write
	STATUS current
	DESCRIPTION
	"This parameter defines the data rate used to setup the internal retimer to provide 3R regeneration. Note that internally interconnected ports must be set to the same rate."
	::= { txgConfigEntry 2 }

txgConfigTxgOperationMode OBJECT-TYPE   -- txg_operation_mode
	SYNTAX INTEGER
		{
		disabled (0),
		transponder (2),
		repeater (3),
		bertPort1 (4),
		bertPort2 (5)
		}
	MAX-ACCESS read-write
	STATUS current
	DESCRIPTION
	"This parameter defines the data path through the module when an internal cross connect is avalable. It is also used to setup a permanent bit error rate test.  (most settings apply to X2G, TXG, OFX-3, XCM-2 only)"
	::= { txgConfigEntry 3 }

txgConfigPort1ItuChannel OBJECT-TYPE   -- port_1_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { txgConfigEntry 4 }

txgConfigPort2ItuChannel OBJECT-TYPE   -- port_2_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { txgConfigEntry 5 }

txgConfigDeactivatePort1 OBJECT-TYPE   -- deactivate_port_1
	SYNTAX INTEGER {  disabled(0), enabled(1) }
	MAX-ACCESS read-write
	STATUS current
	DESCRIPTION
	"When enabled, the optical interface is disabled and communication is cut."
	::= { txgConfigEntry 6 }

txgConfigDeactivatePort2 OBJECT-TYPE   -- deactivate_port_2
	SYNTAX INTEGER {  disabled(0), enabled(1) }
	MAX-ACCESS read-write
	STATUS current
	DESCRIPTION
	"When enabled, the optical interface is disabled and communication is cut."
	::= { txgConfigEntry 7 }

txgConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { txgConfigEntry 8 }

txgConfigLossOfSignalHandling OBJECT-TYPE   -- loss_of_signal_handling
	SYNTAX INTEGER
		{
		local (0),
		percolate (1)
		}
	MAX-ACCESS read-write
	STATUS current
	DESCRIPTION
	"When set to LOCAL a loss of input signal will not affect another port. When set to PERCOLATE, a loss of signal will turn off the transmitter of the other port."
	::= { txgConfigEntry 9 }

txgConfigBertPattern OBJECT-TYPE   -- bert_pattern
	SYNTAX INTEGER
		{
		ms27 (0),
		ms223 (2),
		ms231 (3),
		cjPat (4),
		crPat (5),
		ms8b10bCnt (6)
		}
	MAX-ACCESS read-write
	STATUS current
	DESCRIPTION
	"Defines the bit pattern with which the build-in bit error rate tester (BERT) operates when cross connect is set to BERT."
	::= { txgConfigEntry 10 }

txgConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP/XFP is read and compared to previous value."
	::= { txgConfigEntry 11 }

txgConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { txgConfigEntry 12 }


-- ********************* End of txgConfigTable ***********************


-- ******************* Begin of cxgPlusConfigTable *************************

cxgPlusConfigTable	OBJECT-TYPE
	SYNTAX SEQUENCE OF CxgPlusConfigEntry
	MAX-ACCESS not-accessible
	STATUS current
	DESCRIPTION
		"This table is used to define any CXG+ or OFC-10 modules in the system."
	::= { msp1000 5 }

cxgPlusConfigEntry	OBJECT-TYPE
	SYNTAX CxgPlusConfigEntry
	MAX-ACCESS not-accessible
	STATUS current
	DESCRIPTION
		""
	INDEX { cxgPlusConfigIndex }
	::= { cxgPlusConfigTable 1 }


	CxgPlusConfigEntry ::= SEQUENCE {
	cxgPlusConfigIndex INTEGER,
	cxgPlusConfigCxgPort12Datarate INTEGER ,
	cxgPlusConfigCxgPort34Datarate INTEGER ,
	cxgPlusConfigPort1ItuChannel INTEGER ,
	cxgPlusConfigPort2ItuChannel INTEGER ,
	cxgPlusConfigPort3ItuChannel INTEGER ,
	cxgPlusConfigPort4ItuChannel INTEGER ,
	cxgPlusConfigDeactivatePort1 INTEGER ,
	cxgPlusConfigDeactivatePort2 INTEGER ,
	cxgPlusConfigDeactivatePort3 INTEGER ,
	cxgPlusConfigDeactivatePort4 INTEGER ,
	cxgPlusConfigFrontPanelMode INTEGER ,
	cxgPlusConfigLossOfSignalHandling INTEGER ,
	cxgPlusConfigSfpDeltaInterval INTEGER ,
	cxgPlusConfigSfpDeltaThreshold INTEGER
	}

cxgPlusConfigIndex	OBJECT-TYPE
	SYNTAX INTEGER (0..11)
	MAX-ACCESS not-accessible
	STATUS current
	DESCRIPTION
		"Automatically generated"
	::= { cxgPlusConfigEntry 1 }

cxgPlusConfigCxgPort12Datarate OBJECT-TYPE   -- cxg_port_1_2_datarate
	SYNTAX INTEGER
		{
		transparent (0),
		ms8xFc (1),
		ms10gEth (2),
		ms10xFc16xFc (3)
		}
	MAX-ACCESS read-write
	STATUS current
	DESCRIPTION
	"The CXG relies on the features of the XFP to define its datarate. Since various XFP offer different rates with the same settings, only a general setting is provided. Both ports must operate at the same rate."
	::= { cxgPlusConfigEntry 2 }

cxgPlusConfigCxgPort34Datarate OBJECT-TYPE   -- cxg_port_3_4_datarate
	SYNTAX INTEGER
		{
		transparent (0),
		ms8xFc (1),
		ms10gEth (2),
		ms10xFc16xFc (3)
		}
	MAX-ACCESS read-write
	STATUS current
	DESCRIPTION
	"The CXG relies on the features of the XFP to define its datarate. Since various XFP offer different rates with the same settings, only a general setting is provided. Both ports must operate at the same rate."
	::= { cxgPlusConfigEntry 3 }

cxgPlusConfigPort1ItuChannel OBJECT-TYPE   -- port_1_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgPlusConfigEntry 4 }

cxgPlusConfigPort2ItuChannel OBJECT-TYPE   -- port_2_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgPlusConfigEntry 5 }

cxgPlusConfigPort3ItuChannel OBJECT-TYPE   -- port_3_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgPlusConfigEntry 6 }

cxgPlusConfigPort4ItuChannel OBJECT-TYPE   -- port_4_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgPlusConfigEntry 7 }

cxgPlusConfigDeactivatePort1 OBJECT-TYPE   -- deactivate_port_1
	SYNTAX INTEGER {  disabled(0), enabled(1) }
	MAX-ACCESS read-write
	STATUS current
	DESCRIPTION
	"When enabled, the optical interface is disabled and communication is cut."
	::= { cxgPlusConfigEntry 8 }

cxgPlusConfigDeactivatePort2 OBJECT-TYPE   -- deactivate_port_2
	SYNTAX INTEGER {  disabled(0), enabled(1) }
	MAX-ACCESS read-write
	STATUS current
	DESCRIPTION
	"When enabled, the optical interface is disabled and communication is cut."
	::= { cxgPlusConfigEntry 9 }

cxgPlusConfigDeactivatePort3 OBJECT-TYPE   -- deactivate_port_3
	SYNTAX INTEGER {  disabled(0), enabled(1) }
	MAX-ACCESS read-write
	STATUS current
	DESCRIPTION
	"When enabled, the optical interface is disabled and communication is cut."
	::= { cxgPlusConfigEntry 10 }

cxgPlusConfigDeactivatePort4 OBJECT-TYPE   -- deactivate_port_4
	SYNTAX INTEGER {  disabled(0), enabled(1) }
	MAX-ACCESS read-write
	STATUS current
	DESCRIPTION
	"When enabled, the optical interface is disabled and communication is cut."
	::= { cxgPlusConfigEntry 11 }

cxgPlusConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { cxgPlusConfigEntry 12 }

cxgPlusConfigLossOfSignalHandling OBJECT-TYPE   -- loss_of_signal_handling
	SYNTAX INTEGER
		{
		local (0),
		percolate (1)
		}
	MAX-ACCESS read-write
	STATUS current
	DESCRIPTION
	"When set to LOCAL a loss of input signal will not affect another port. When set to PERCOLATE, a loss of signal will turn off the transmitter of the other port."
	::= { cxgPlusConfigEntry 13 }

cxgPlusConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP/XFP is read and compared to previous value."
	::= { cxgPlusConfigEntry 14 }

cxgPlusConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { cxgPlusConfigEntry 15 }


-- ********************* End of cxgPlusConfigTable ***********************


-- ******************* Begin of cxgConfigTable *************************

cxgConfigTable	OBJECT-TYPE
	SYNTAX SEQUENCE OF CxgConfigEntry
	MAX-ACCESS not-accessible
	STATUS current
	DESCRIPTION
		"This table is used to define any CXG or XCM-3 modules in the system."
	::= { msp1000 6 }

cxgConfigEntry	OBJECT-TYPE
	SYNTAX CxgConfigEntry
	MAX-ACCESS not-accessible
	STATUS current
	DESCRIPTION
		""
	INDEX { cxgConfigIndex }
	::= { cxgConfigTable 1 }


	CxgConfigEntry ::= SEQUENCE {
	cxgConfigIndex INTEGER,
	cxgConfigCxgPort12Datarate INTEGER ,
	cxgConfigPort1ItuChannel INTEGER ,
	cxgConfigPort2ItuChannel INTEGER ,
	cxgConfigDeactivatePort1 INTEGER ,
	cxgConfigDeactivatePort2 INTEGER ,
	cxgConfigFrontPanelMode INTEGER ,
	cxgConfigLossOfSignalHandling INTEGER ,
	cxgConfigSfpDeltaInterval INTEGER ,
	cxgConfigSfpDeltaThreshold INTEGER
	}

cxgConfigIndex	OBJECT-TYPE
	SYNTAX INTEGER (0..11)
	MAX-ACCESS not-accessible
	STATUS current
	DESCRIPTION
		"Automatically generated"
	::= { cxgConfigEntry 1 }

cxgConfigCxgPort12Datarate OBJECT-TYPE   -- cxg_port_1_2_datarate
	SYNTAX INTEGER
		{
		transparent (0),
		ms8xFc (1),
		ms10gEth (2),
		ms10xFc16xFc (3)
		}
	MAX-ACCESS read-write
	STATUS current
	DESCRIPTION
	"The CXG relies on the features of the XFP to define its datarate. Since various XFP offer different rates with the same settings, only a general setting is provided. Both ports must operate at the same rate."
	::= { cxgConfigEntry 2 }

cxgConfigPort1ItuChannel OBJECT-TYPE   -- port_1_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgConfigEntry 3 }

cxgConfigPort2ItuChannel OBJECT-TYPE   -- port_2_itu_channel
	SYNTAX INTEGER
		{
		fixed (0),
		ch11 (22),
		ch12 (24),
		ch13 (26),
		ch14 (28),
		ch15 (30),
		ch16 (32),
		ch17 (34),
		ch18 (36),
		ch19 (38),
		ch20 (40),
		ch21 (42),
		ch22 (44),
		ch23 (46),
		ch24 (48),
		ch25 (50),
		ch26 (52),
		ch27 (54),
		ch28 (56),
		ch29 (58),
		ch30 (60),
		ch31 (62),
		ch32 (64),
		ch33 (66),
		ch34 (68),
		ch35 (70),
		ch36 (72),
		ch37 (74),
		ch38 (76),
		ch39 (78),
		ch40 (80),
		ch41 (82),
		ch42 (84),
		ch43 (86),
		ch44 (88),
		ch45 (90),
		ch46 (92),
		ch47 (94),
		ch48 (96),
		ch49 (98),
		ch50 (100),
		ch51 (102),
		ch52 (104),
		ch53 (106),
		ch54 (108),
		ch55 (110),
		ch56 (112),
		ch57 (114),
		ch58 (116),
		ch59 (118),
		ch60 (120),
		ch61 (122),
		ch62 (124),
		ch63 (126)
		}
	MAX-ACCESS read-write
	STATUS current
	DESCRIPTION
	"Tunable laser are supported. Select the wavelength from the supplied 100GHZ ITU-T grid. If the wavelength is not supported by the XFP, a warning event will be received. "
	::= { cxgConfigEntry 4 }

cxgConfigDeactivatePort1 OBJECT-TYPE   -- deactivate_port_1
	SYNTAX INTEGER {  disabled(0), enabled(1) }
	MAX-ACCESS read-write
	STATUS current
	DESCRIPTION
	"When enabled, the optical interface is disabled and communication is cut."
	::= { cxgConfigEntry 5 }

cxgConfigDeactivatePort2 OBJECT-TYPE   -- deactivate_port_2
	SYNTAX INTEGER {  disabled(0), enabled(1) }
	MAX-ACCESS read-write
	STATUS current
	DESCRIPTION
	"When enabled, the optical interface is disabled and communication is cut."
	::= { cxgConfigEntry 6 }

cxgConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { cxgConfigEntry 7 }

cxgConfigLossOfSignalHandling OBJECT-TYPE   -- loss_of_signal_handling
	SYNTAX INTEGER
		{
		local (0),
		percolate (1)
		}
	MAX-ACCESS read-write
	STATUS current
	DESCRIPTION
	"When set to LOCAL a loss of input signal will not affect another port. When set to PERCOLATE, a loss of signal will turn off the transmitter of the other port."
	::= { cxgConfigEntry 8 }

cxgConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP/XFP is read and compared to previous value."
	::= { cxgConfigEntry 9 }

cxgConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { cxgConfigEntry 10 }


-- ********************* End of cxgConfigTable ***********************


-- ******************* Begin of t4gConfigTable *************************

t4gConfigTable	OBJECT-TYPE
	SYNTAX SEQUENCE OF T4gConfigEntry
	MAX-ACCESS not-accessible
	STATUS current
	DESCRIPTION
		"This table is used to define any T4G or OFC-4 modules in the system."
	::= { msp1000 7 }

t4gConfigEntry	OBJECT-TYPE
	SYNTAX T4gConfigEntry
	MAX-ACCESS not-accessible
	STATUS current
	DESCRIPTION
		""
	INDEX { t4gConfigIndex }
	::= { t4gConfigTable 1 }


	T4gConfigEntry ::= SEQUENCE {
	t4gConfigIndex INTEGER,
	t4gConfigT4gPort12Datarate INTEGER ,
	t4gConfigT4gPort34Datarate INTEGER ,
	t4gConfigT4gOperationMode INTEGER ,
	t4gConfigDeactivatePort1 INTEGER ,
	t4gConfigDeactivatePort2 INTEGER ,
	t4gConfigDeactivatePort3 INTEGER ,
	t4gConfigDeactivatePort4 INTEGER ,
	t4gConfigFrontPanelMode INTEGER ,
	t4gConfigLossOfSignalHandling INTEGER ,
	t4gConfigBertPattern INTEGER ,
	t4gConfigSfpDeltaInterval INTEGER ,
	t4gConfigSfpDeltaThreshold INTEGER
	}

t4gConfigIndex	OBJECT-TYPE
	SYNTAX INTEGER (0..11)
	MAX-ACCESS not-accessible
	STATUS current
	DESCRIPTION
		"Automatically generated"
	::= { t4gConfigEntry 1 }

t4gConfigT4gPort12Datarate OBJECT-TYPE   -- t4g_port_1_2_datarate
	SYNTAX INTEGER
		{
		transparent (0),
		ms100mEth (2),
		ms1gEth (8),
		escon (4),
		ms1xFc (7),
		ms2xFc (10),
		ms4xFc (14),
		infiniband (12),
		oc3 (3),
		oc12 (6),
		oc48 (11)
		}
	MAX-ACCESS read-write
	STATUS current
	DESCRIPTION
	"The CXG relies on the features of the XFP to define its datarate. Since various XFP offer different rates with the same settings, only a general setting is provided. Both ports must operate at the same rate."
	::= { t4gConfigEntry 2 }

t4gConfigT4gPort34Datarate OBJECT-TYPE   -- t4g_port_3_4_datarate
	SYNTAX INTEGER
		{
		transparent (0),
		ms100mEth (2),
		ms1gEth (8),
		escon (4),
		ms1xFc (7),
		ms2xFc (10),
		ms4xFc (14),
		infiniband (12),
		oc3 (3),
		oc12 (6),
		oc48 (11)
		}
	MAX-ACCESS read-write
	STATUS current
	DESCRIPTION
	"Tunable laser are supported. Select the wavelength from the supplied 100GHZ ITU-T grid. If the wavelength is not supported by the XFP, a warning event will be received. "
	::= { t4gConfigEntry 3 }

t4gConfigT4gOperationMode OBJECT-TYPE   -- t4g_operation_mode
	SYNTAX INTEGER
		{
		disabled (0),
		transponder (1),
		bertPort4 (2)
		}
	MAX-ACCESS read-write
	STATUS current
	DESCRIPTION
	"This parameter defines the data path through the module when an internal cross connect is avalable. It is also used to setup a permanent bit error rate test.  (most settings apply to X2G, TXG, OFX-3, XCM-2 only)"
	::= { t4gConfigEntry 4 }

t4gConfigDeactivatePort1 OBJECT-TYPE   -- deactivate_port_1
	SYNTAX INTEGER {  disabled(0), enabled(1) }
	MAX-ACCESS read-write
	STATUS current
	DESCRIPTION
	"When enabled, the optical interface is disabled and communication is cut."
	::= { t4gConfigEntry 5 }

t4gConfigDeactivatePort2 OBJECT-TYPE   -- deactivate_port_2
	SYNTAX INTEGER {  disabled(0), enabled(1) }
	MAX-ACCESS read-write
	STATUS current
	DESCRIPTION
	"When enabled, the optical interface is disabled and communication is cut."
	::= { t4gConfigEntry 6 }

t4gConfigDeactivatePort3 OBJECT-TYPE   -- deactivate_port_3
	SYNTAX INTEGER {  disabled(0), enabled(1) }
	MAX-ACCESS read-write
	STATUS current
	DESCRIPTION
	"When enabled, the optical interface is disabled and communication is cut."
	::= { t4gConfigEntry 7 }

t4gConfigDeactivatePort4 OBJECT-TYPE   -- deactivate_port_4
	SYNTAX INTEGER {  disabled(0), enabled(1) }
	MAX-ACCESS read-write
	STATUS current
	DESCRIPTION
	"When enabled, the optical interface is disabled and communication is cut."
	::= { t4gConfigEntry 8 }

t4gConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { t4gConfigEntry 9 }

t4gConfigLossOfSignalHandling OBJECT-TYPE   -- loss_of_signal_handling
	SYNTAX INTEGER
		{
		local (0),
		percolate (1)
		}
	MAX-ACCESS read-write
	STATUS current
	DESCRIPTION
	"When set to LOCAL a loss of input signal will not affect another port. When set to PERCOLATE, a loss of signal will turn off the transmitter of the other port."
	::= { t4gConfigEntry 10 }

t4gConfigBertPattern OBJECT-TYPE   -- bert_pattern
	SYNTAX INTEGER
		{
		ms27 (0),
		ms223 (2),
		ms231 (3),
		cjPat (4),
		crPat (5),
		ms8b10bCnt (6)
		}
	MAX-ACCESS read-write
	STATUS current
	DESCRIPTION
	"Defines the bit pattern with which the build-in bit error rate tester (BERT) operates when cross connect is set to BERT."
	::= { t4gConfigEntry 11 }

t4gConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP/XFP is read and compared to previous value."
	::= { t4gConfigEntry 12 }

t4gConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { t4gConfigEntry 13 }


-- ********************* End of t4gConfigTable ***********************


-- ******************* Begin of m2gConfigTable *************************

m2gConfigTable	OBJECT-TYPE
	SYNTAX SEQUENCE OF M2gConfigEntry
	MAX-ACCESS not-accessible
	STATUS current
	DESCRIPTION
		"This table is used to define any M2G or TDM-2 modules in the system."
	::= { msp1000 8 }

m2gConfigEntry	OBJECT-TYPE
	SYNTAX M2gConfigEntry
	MAX-ACCESS not-accessible
	STATUS current
	DESCRIPTION
		""
	INDEX { m2gConfigIndex }
	::= { m2gConfigTable 1 }


	M2gConfigEntry ::= SEQUENCE {
	m2gConfigIndex INTEGER,
	m2gConfigChannel1Datarate INTEGER ,
	m2gConfigChannel2Datarate INTEGER ,
	m2gConfigPort1CopperSfp INTEGER ,
	m2gConfigPort2CopperSfp INTEGER ,
	m2gConfigSfpDeltaInterval INTEGER ,
	m2gConfigSfpDeltaThreshold INTEGER ,
	m2gConfigLinkBackupTrigger INTEGER ,
	m2gConfigStayWithLastLink INTEGER ,
	m2gConfigBackupEnd INTEGER ,
	m2gConfigPermitLinkOverride INTEGER
	}

m2gConfigIndex	OBJECT-TYPE
	SYNTAX INTEGER (0..11)
	MAX-ACCESS not-accessible
	STATUS current
	DESCRIPTION
		"Automatically generated"
	::= { m2gConfigEntry 1 }

m2gConfigChannel1Datarate OBJECT-TYPE   -- channel_1_datarate
	SYNTAX INTEGER
		{
		disabled (0),
		ms1gEth (1),
		ms1xFc (2)
		}
	MAX-ACCESS read-write
	STATUS current
	DESCRIPTION
	"Devices the datarate of the first TDM channel (port 1)"
	::= { m2gConfigEntry 2 }

m2gConfigChannel2Datarate OBJECT-TYPE   -- channel_2_datarate
	SYNTAX INTEGER
		{
		disabled (0),
		ms1gEth (1),
		ms1xFc (2)
		}
	MAX-ACCESS read-write
	STATUS current
	DESCRIPTION
	"Devices the datarate of the second TDM channel (port 2)"
	::= { m2gConfigEntry 3 }

m2gConfigPort1CopperSfp OBJECT-TYPE   -- port_1_copper_sfp
	SYNTAX INTEGER {  disabled(0), enabled(1) }
	MAX-ACCESS read-write
	STATUS current
	DESCRIPTION
	"Set when local copper RJ45 SFP is used and connection cannot be established."
	::= { m2gConfigEntry 4 }

m2gConfigPort2CopperSfp OBJECT-TYPE   -- port_2_copper_sfp
	SYNTAX INTEGER {  disabled(0), enabled(1) }
	MAX-ACCESS read-write
	STATUS current
	DESCRIPTION
	"Set when local copper RJ45 SFP is used and connection cannot be established."
	::= { m2gConfigEntry 5 }

m2gConfigSfpDeltaInterval OBJECT-TYPE   -- sfp_delta_interval
	SYNTAX INTEGER
		{
		disabled (0),
		ms1Sec (1),
		ms5Sec (2),
		ms10Sec (3),
		ms30Sec (4),
		ms60Sec (5),
		ms240Sec (6)
		}
	MAX-ACCESS read-write
	STATUS current
	DESCRIPTION
	"This enables and defines the interval in which the optical receive power level of each SFP/XFP is read and compared to previous value."
	::= { m2gConfigEntry 6 }

m2gConfigSfpDeltaThreshold OBJECT-TYPE   -- sfp_delta_threshold
	SYNTAX INTEGER
		{
		ms05Db (0),
		ms1Db (1),
		ms15Db (2),
		ms2Db (3),
		ms3Db (4),
		ms5Db (5)
		}
	MAX-ACCESS read-write
	STATUS current
	DESCRIPTION
	"This defines how much the optical receive power level can differ between successive reads before a warning trap is generated."
	::= { m2gConfigEntry 7 }

m2gConfigLinkBackupTrigger OBJECT-TYPE   -- link_backup_trigger
	SYNTAX INTEGER
		{
		disabled (0),
		signalLoss (1),
		errorBurst (2)
		}
	MAX-ACCESS read-write
	STATUS current
	DESCRIPTION
	"Defines under which optical signal condition an automated backup is initiated."
	::= { m2gConfigEntry 8 }

m2gConfigStayWithLastLink OBJECT-TYPE   -- stay_with_last_link
	SYNTAX INTEGER {  disabled(0), enabled(1) }
	MAX-ACCESS read-write
	STATUS current
	DESCRIPTION
	"When set the backup switch remains in last position even when signal returns. Still the backup warning turns off after the delay set under backup_end parameter expires."
	::= { m2gConfigEntry 9 }

m2gConfigBackupEnd OBJECT-TYPE   -- backup_end
	SYNTAX INTEGER
		{
		noDelay (0),
		ms15Seconds (1),
		ms15Minutes (2),
		manually (3)
		}
	MAX-ACCESS read-write
	STATUS current
	DESCRIPTION
	"Defines how long the signal must remain steady before proper operation is assumed and the backup is terminated."
	::= { m2gConfigEntry 10 }

m2gConfigPermitLinkOverride OBJECT-TYPE   -- permit_link_override
	SYNTAX INTEGER {  disabled(0), enabled(1) }
	MAX-ACCESS read-write
	STATUS current
	DESCRIPTION
	"Permits the manual selection of a failed link using the link selection. Defaults to false to safeguard against accidential link selection which would result in loss of connection."
	::= { m2gConfigEntry 11 }


-- ********************* End of m2gConfigTable ***********************


-- ******************* Begin of om1ConfigTable *************************

om1ConfigTable	OBJECT-TYPE
	SYNTAX SEQUENCE OF Om1ConfigEntry
	MAX-ACCESS not-accessible
	STATUS current
	DESCRIPTION
		""
	::= { msp1000 9 }

om1ConfigEntry	OBJECT-TYPE
	SYNTAX Om1ConfigEntry
	MAX-ACCESS not-accessible
	STATUS current
	DESCRIPTION
		""
	INDEX { om1ConfigIndex }
	::= { om1ConfigTable 1 }


	Om1ConfigEntry ::= SEQUENCE {
	om1ConfigIndex INTEGER,
	om1ConfigWavelengthPortA INTEGER ,
	om1ConfigLowThresholdPortA DisplayString,
	om1ConfigHighThresholdPortA DisplayString,
	om1ConfigWavelengthPortB INTEGER ,
	om1ConfigLowThresholdPortB DisplayString,
	om1ConfigHighThresholdPortB DisplayString,
	om1ConfigFrontPanelMode INTEGER
	}

om1ConfigIndex	OBJECT-TYPE
	SYNTAX INTEGER (0..11)
	MAX-ACCESS not-accessible
	STATUS current
	DESCRIPTION
		"Automatically generated"
	::= { om1ConfigEntry 1 }

om1ConfigWavelengthPortA OBJECT-TYPE   -- wavelength_port_a
	SYNTAX INTEGER
		{
		ms1550nm (0),
		ms1310nm (1),
		disabled (3)
		}
	MAX-ACCESS read-write
	STATUS current
	DESCRIPTION
	"Defines which wavelength band is measured. Use 1550 setting when a WDM link is measured."
	::= { om1ConfigEntry 2 }

om1ConfigLowThresholdPortA OBJECT-TYPE   -- low_threshold_port_a
	SYNTAX DisplayString
	MAX-ACCESS read-write
	STATUS current
	DESCRIPTION
	"Defines the lower optical signal level in dBm. A signal level below this threshold will trigger an event."
	::= { om1ConfigEntry 3 }

om1ConfigHighThresholdPortA OBJECT-TYPE   -- high_threshold_port_a
	SYNTAX DisplayString
	MAX-ACCESS read-write
	STATUS current
	DESCRIPTION
	"Defines the upper optical signal level in dBm. A signal level above this threshold will trigger an event."
	::= { om1ConfigEntry 4 }

om1ConfigWavelengthPortB OBJECT-TYPE   -- wavelength_port_b
	SYNTAX INTEGER
		{
		ms1550nm (0),
		ms1310nm (1),
		disabled (3)
		}
	MAX-ACCESS read-write
	STATUS current
	DESCRIPTION
	"Defines which wavelength band is measured. Use 1550 setting when a WDM link is measured."
	::= { om1ConfigEntry 5 }

om1ConfigLowThresholdPortB OBJECT-TYPE   -- low_threshold_port_b
	SYNTAX DisplayString
	MAX-ACCESS read-write
	STATUS current
	DESCRIPTION
	"Defines the lower optical signal level in dBm. A signal level below this threshold will trigger an event."
	::= { om1ConfigEntry 6 }

om1ConfigHighThresholdPortB OBJECT-TYPE   -- high_threshold_port_b
	SYNTAX DisplayString
	MAX-ACCESS read-write
	STATUS current
	DESCRIPTION
	"Defines the upper optical signal level in dBm. A signal level above this threshold will trigger an event."
	::= { om1ConfigEntry 7 }

om1ConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { om1ConfigEntry 8 }


-- ********************* End of om1ConfigTable ***********************


-- ******************* Begin of lp1ConfigTable *************************

lp1ConfigTable	OBJECT-TYPE
	SYNTAX SEQUENCE OF Lp1ConfigEntry
	MAX-ACCESS not-accessible
	STATUS current
	DESCRIPTION
		""
	::= { msp1000 10 }

lp1ConfigEntry	OBJECT-TYPE
	SYNTAX Lp1ConfigEntry
	MAX-ACCESS not-accessible
	STATUS current
	DESCRIPTION
		""
	INDEX { lp1ConfigIndex }
	::= { lp1ConfigTable 1 }


	Lp1ConfigEntry ::= SEQUENCE {
	lp1ConfigIndex INTEGER,
	lp1ConfigWavelengthPortA INTEGER ,
	lp1ConfigLowThresholdPortA DisplayString,
	lp1ConfigHighThresholdPortA DisplayString,
	lp1ConfigWavelengthPortB INTEGER ,
	lp1ConfigLowThresholdPortB DisplayString,
	lp1ConfigHighThresholdPortB DisplayString,
	lp1ConfigBackupCriteria INTEGER ,
	lp1ConfigStayWithLastLink INTEGER ,
	lp1ConfigBackupEnd INTEGER ,
	lp1ConfigFrontPanelMode INTEGER
	}

lp1ConfigIndex	OBJECT-TYPE
	SYNTAX INTEGER (0..11)
	MAX-ACCESS not-accessible
	STATUS current
	DESCRIPTION
		"Automatically generated"
	::= { lp1ConfigEntry 1 }

lp1ConfigWavelengthPortA OBJECT-TYPE   -- wavelength_port_a
	SYNTAX INTEGER
		{
		ms1550nm (0),
		ms1310nm (1),
		disabled (3)
		}
	MAX-ACCESS read-write
	STATUS current
	DESCRIPTION
	"Defines which wavelength band is measured. Use 1550 setting when a WDM link is measured."
	::= { lp1ConfigEntry 2 }

lp1ConfigLowThresholdPortA OBJECT-TYPE   -- low_threshold_port_a
	SYNTAX DisplayString
	MAX-ACCESS read-write
	STATUS current
	DESCRIPTION
	"Defines the lower optical signal level in dBm. A signal level below this threshold will trigger an event and a backup when configured."
	::= { lp1ConfigEntry 3 }

lp1ConfigHighThresholdPortA OBJECT-TYPE   -- high_threshold_port_a
	SYNTAX DisplayString
	MAX-ACCESS read-write
	STATUS current
	DESCRIPTION
	"Defines the upper optical signal level in dBm. A signal level above this threshold will trigger an event and a backup when configured."
	::= { lp1ConfigEntry 4 }

lp1ConfigWavelengthPortB OBJECT-TYPE   -- wavelength_port_b
	SYNTAX INTEGER
		{
		ms1550nm (0),
		ms1310nm (1),
		disabled (3)
		}
	MAX-ACCESS read-write
	STATUS current
	DESCRIPTION
	"Defines which wavelength band is measured. Use 1550 setting when a WDM link is measured."
	::= { lp1ConfigEntry 5 }

lp1ConfigLowThresholdPortB OBJECT-TYPE   -- low_threshold_port_b
	SYNTAX DisplayString
	MAX-ACCESS read-write
	STATUS current
	DESCRIPTION
	"Defines the lower optical signal level in dBm. A signal level below this threshold will trigger an event and a backup when configured."
	::= { lp1ConfigEntry 6 }

lp1ConfigHighThresholdPortB OBJECT-TYPE   -- high_threshold_port_b
	SYNTAX DisplayString
	MAX-ACCESS read-write
	STATUS current
	DESCRIPTION
	"Defines the upper optical signal level in dBm. A signal level above this threshold will trigger an event and a backup when configured."
	::= { lp1ConfigEntry 7 }

lp1ConfigBackupCriteria OBJECT-TYPE   -- backup_criteria
	SYNTAX INTEGER
		{
		signalLow (0),
		signalHigh (1),
		manually (2)
		}
	MAX-ACCESS read-write
	STATUS current
	DESCRIPTION
	"Defines under which optical signal condition an automated backup is initiated."
	::= { lp1ConfigEntry 8 }

lp1ConfigStayWithLastLink OBJECT-TYPE   -- stay_with_last_link
	SYNTAX INTEGER {  disabled(0), enabled(1) }
	MAX-ACCESS read-write
	STATUS current
	DESCRIPTION
	"When set the backup switch remains in last position even when signal return. Still the backup warning turns off after the delay set under backup_end parameter  expires."
	::= { lp1ConfigEntry 9 }

lp1ConfigBackupEnd OBJECT-TYPE   -- backup_end
	SYNTAX INTEGER
		{
		noDelay (0),
		ms15Seconds (1),
		ms15Minutes (2),
		manually (3)
		}
	MAX-ACCESS read-write
	STATUS current
	DESCRIPTION
	"Defines how long the signal must remain steady before proper operation is assumed and the backup is terminated."
	::= { lp1ConfigEntry 10 }

lp1ConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { lp1ConfigEntry 11 }


-- ********************* End of lp1ConfigTable ***********************


-- ******************* Begin of emConfigTable *************************

emConfigTable	OBJECT-TYPE
	SYNTAX SEQUENCE OF EmConfigEntry
	MAX-ACCESS not-accessible
	STATUS current
	DESCRIPTION
		"Configuration for EDFA amplifier modules EM2 and EM3."
	::= { msp1000 11 }

emConfigEntry	OBJECT-TYPE
	SYNTAX EmConfigEntry
	MAX-ACCESS not-accessible
	STATUS current
	DESCRIPTION
		""
	INDEX { emConfigIndex }
	::= { emConfigTable 1 }


	EmConfigEntry ::= SEQUENCE {
	emConfigIndex INTEGER,
	emConfigEdfaOperationMode INTEGER ,
	emConfigLossOfSignalHandling INTEGER ,
	emConfigSignalGain DisplayString,
	emConfigMaxOutputPower DisplayString,
	emConfigLowThresholdEdfaIn DisplayString,
	emConfigHighThresholdEdfaIn DisplayString,
	emConfigLowThresholdPortB DisplayString,
	emConfigHighThresholdPortB DisplayString,
	emConfigFrontPanelMode INTEGER
	}

emConfigIndex	OBJECT-TYPE
	SYNTAX INTEGER (0..11)
	MAX-ACCESS not-accessible
	STATUS current
	DESCRIPTION
		"Automatically generated"
	::= { emConfigEntry 1 }

emConfigEdfaOperationMode OBJECT-TYPE   -- edfa_operation_mode
	SYNTAX INTEGER
		{
		pumpDisabled (3),
		preAmp (0),
		booster (1)
		}
	MAX-ACCESS read-write
	STATUS current
	DESCRIPTION
	"Defines which wavelength band is measured. Use 1550 setting when a WDM link is measured."
	::= { emConfigEntry 2 }

emConfigLossOfSignalHandling OBJECT-TYPE   -- loss_of_signal_handling
	SYNTAX INTEGER
		{
		local (0),
		percolate (1)
		}
	MAX-ACCESS read-write
	STATUS current
	DESCRIPTION
	"Defines if loss of input signal turns off the EDFA pump (PERCOLATE) or not (LOCAL)"
	::= { emConfigEntry 3 }

emConfigSignalGain OBJECT-TYPE   -- signal_gain
	SYNTAX DisplayString
	MAX-ACCESS read-write
	STATUS current
	DESCRIPTION
	"Desired signal gain in dB."
	::= { emConfigEntry 4 }

emConfigMaxOutputPower OBJECT-TYPE   -- max_output_power
	SYNTAX DisplayString
	MAX-ACCESS read-write
	STATUS current
	DESCRIPTION
	"Maximum output power permitted to exit the module."
	::= { emConfigEntry 5 }

emConfigLowThresholdEdfaIn OBJECT-TYPE   -- low_threshold_edfa_in
	SYNTAX DisplayString
	MAX-ACCESS read-write
	STATUS current
	DESCRIPTION
	"This corresponds to the unamplified input signal before entering the EDFA section. Defines the lower optical signal level in dBm. A signal level below this threshold will trigger an event."
	::= { emConfigEntry 6 }

emConfigHighThresholdEdfaIn OBJECT-TYPE   -- high_threshold_edfa_in
	SYNTAX DisplayString
	MAX-ACCESS read-write
	STATUS current
	DESCRIPTION
	"This corresponds to the unamplified input signal before entering the EDFA section. Defines the upper optical signal level in dBm. A signal level above this threshold will trigger an event."
	::= { emConfigEntry 7 }

emConfigLowThresholdPortB OBJECT-TYPE   -- low_threshold_port_b
	SYNTAX DisplayString
	MAX-ACCESS read-write
	STATUS current
	DESCRIPTION
	"Port B is the unamplified return path through the module. Defines the lower optical signal level in dBm. A signal level below this threshold will trigger an event."
	::= { emConfigEntry 8 }

emConfigHighThresholdPortB OBJECT-TYPE   -- high_threshold_port_b
	SYNTAX DisplayString
	MAX-ACCESS read-write
	STATUS current
	DESCRIPTION
	"Port B is the unamplified return path through the module. Defines the upper optical signal level in dBm. A signal level above this threshold will trigger an event."
	::= { emConfigEntry 9 }

emConfigFrontPanelMode OBJECT-TYPE   -- front_panel_mode
	SYNTAX INTEGER
		{
		normal (0),
		extended (1),
		normalLocked (4),
		extendedLocked (5),
		remote (7)
		}
	MAX-ACCESS read-write
	STATUS current
	DESCRIPTION
	"Determines what is displayed on the front panel, when available. Also controls the modules local buttons."
	::= { emConfigEntry 10 }


-- ********************* End of emConfigTable ***********************


-- ******************* Begin of moduleControlTable *************************

moduleControlTable	OBJECT-TYPE
	SYNTAX SEQUENCE OF ModuleControlEntry
	MAX-ACCESS not-accessible
	STATUS current
	DESCRIPTION
		""
	::= { msp1000 12 }

moduleControlEntry	OBJECT-TYPE
	SYNTAX ModuleControlEntry
	MAX-ACCESS not-accessible
	STATUS current
	DESCRIPTION
		""
	INDEX { moduleControlIndex }
	::= { moduleControlTable 1 }


	ModuleControlEntry ::= SEQUENCE {
	moduleControlIndex INTEGER,
	moduleControlEnterPassword DisplayString,
	moduleControlRebootModule DisplayString,
	moduleControlWarmStart DisplayString,
	moduleControlClearCounter DisplayString,
	moduleControlSwitchOffBackup DisplayString,
	moduleControlSwitchToBackup DisplayString,
	moduleControlAutomaticBackup DisplayString,
	moduleControlWriteDisplay DisplayString,
	moduleControlLedTest DisplayString,
	moduleControlLoopOff DisplayString,
	moduleControlLoopPort1 DisplayString,
	moduleControlLoopPort2 DisplayString,
	moduleControlLoopPort3 DisplayString,
	moduleControlLoopPort4 DisplayString,
	moduleControlBertRestart DisplayString,
	moduleControlBertInsertError DisplayString,
	moduleControlBertClearCounter DisplayString
	}

moduleControlIndex	OBJECT-TYPE
	SYNTAX INTEGER (0..11)
	MAX-ACCESS not-accessible
	STATUS current
	DESCRIPTION
		"Automatically generated"
	::= { moduleControlEntry 1 }

moduleControlEnterPassword OBJECT-TYPE   -- enter_password
	SYNTAX DisplayString
	MAX-ACCESS read-write
	STATUS current
	DESCRIPTION
	"This command will set the module password. Only required when the nms_operation_mode is set to passive mode. Enter the password before configuration or actions can be accepted by the module."
	::= { moduleControlEntry 2 }

moduleControlRebootModule OBJECT-TYPE   -- reboot_module
	SYNTAX DisplayString
	MAX-ACCESS read-write
	STATUS current
	DESCRIPTION
	"This command will restart the module. All communication will be disrupted! Syntax: reboot_module = CONFIRM."
	::= { moduleControlEntry 3 }

moduleControlWarmStart OBJECT-TYPE   -- warm_start
	SYNTAX DisplayString
	MAX-ACCESS read-write
	STATUS current
	DESCRIPTION
	"This command will warm start the module. Communication shall not be disrupted. (Firmware dependend) Syntax: warm_start = CONFIRM."
	::= { moduleControlEntry 4 }

moduleControlClearCounter OBJECT-TYPE   -- clear_counter
	SYNTAX DisplayString
	MAX-ACCESS read-write
	STATUS current
	DESCRIPTION
	"This command will clear all module and port related statistics counter."
	::= { moduleControlEntry 5 }

moduleControlSwitchOffBackup OBJECT-TYPE   -- switch_off_backup
	SYNTAX DisplayString
	MAX-ACCESS read-write
	STATUS current
	DESCRIPTION
	"For a module that supports backup and which currently is in backup condition this command will revert to normal operation. If this would disrupt traffic a warning is returned and nothing is executed. To override this warning and switch back nonetheless type switch_off_backup = CONFIRM"
	::= { moduleControlEntry 6 }

moduleControlSwitchToBackup OBJECT-TYPE   -- switch_to_backup
	SYNTAX DisplayString
	MAX-ACCESS read-write
	STATUS current
	DESCRIPTION
	"For a module that supports backup this command will switch to the backup link. If this would disrupt traffic because backup link is not available a warning is returned and nothing is executed. To override this warning and switch over nonetheless type switch_to_backup = CONFIRM"
	::= { moduleControlEntry 7 }

moduleControlAutomaticBackup OBJECT-TYPE   -- automatic_backup
	SYNTAX DisplayString
	MAX-ACCESS read-write
	STATUS current
	DESCRIPTION
	"This command returns a manually overridden backup module to normal automatic mode. No parameter are required."
	::= { moduleControlEntry 8 }

moduleControlWriteDisplay OBJECT-TYPE   -- write_display
	SYNTAX DisplayString
	MAX-ACCESS read-write
	STATUS current
	DESCRIPTION
	"Writes to the front panel display of the module. Only for modules that offer a front panel display."
	::= { moduleControlEntry 9 }

moduleControlLedTest OBJECT-TYPE   -- led_test
	SYNTAX DisplayString
	MAX-ACCESS read-write
	STATUS current
	DESCRIPTION
	"This will start the modules LED test and will return the LED back up automatic mode after a few seconds. May be also be used to identify a certain module."
	::= { moduleControlEntry 10 }

moduleControlLoopOff OBJECT-TYPE   -- loop_off
	SYNTAX DisplayString
	MAX-ACCESS read-write
	STATUS current
	DESCRIPTION
	"Turns all loops off"
	::= { moduleControlEntry 11 }

moduleControlLoopPort1 OBJECT-TYPE   -- loop_port_1
	SYNTAX DisplayString
	MAX-ACCESS read-write
	STATUS current
	DESCRIPTION
	"Tries to engage a loop at port 1. Note not all modules support loops. View port status to check success."
	::= { moduleControlEntry 12 }

moduleControlLoopPort2 OBJECT-TYPE   -- loop_port_2
	SYNTAX DisplayString
	MAX-ACCESS read-write
	STATUS current
	DESCRIPTION
	"Tries to engage a loop at port 2. Note not all modules support loops. View port status to check success."
	::= { moduleControlEntry 13 }

moduleControlLoopPort3 OBJECT-TYPE   -- loop_port_3
	SYNTAX DisplayString
	MAX-ACCESS read-write
	STATUS current
	DESCRIPTION
	"Tries to engage a loop at port 3. Note not all modules support loops. View port status to check success."
	::= { moduleControlEntry 14 }

moduleControlLoopPort4 OBJECT-TYPE   -- loop_port_4
	SYNTAX DisplayString
	MAX-ACCESS read-write
	STATUS current
	DESCRIPTION
	"Tries to engage a loop at port 4. Note not all modules support loops. View port status to check success."
	::= { moduleControlEntry 15 }

moduleControlBertRestart OBJECT-TYPE   -- bert_restart
	SYNTAX DisplayString
	MAX-ACCESS read-write
	STATUS current
	DESCRIPTION
	"Resynchronizes BERT. Only has an effect if a BERT is available on the module and configured to be active."
	::= { moduleControlEntry 16 }

moduleControlBertInsertError OBJECT-TYPE   -- bert_insert_error
	SYNTAX DisplayString
	MAX-ACCESS read-write
	STATUS current
	DESCRIPTION
	"Inserts an error in the data pattern. This can be used to confirm that a BERT is actually operating. Only has an effect if a BERT is available on the module and configured to be active."
	::= { moduleControlEntry 17 }

moduleControlBertClearCounter OBJECT-TYPE   -- bert_clear_counter
	SYNTAX DisplayString
	MAX-ACCESS read-write
	STATUS current
	DESCRIPTION
	"Clears the BERT counter. Only has an effect if a BERT is available on the module and configured to be active."
	::= { moduleControlEntry 18 }


-- ********************* End of moduleControlTable ***********************



-- ****************************** STATUS SECTION ********************************


-- ******************* Begin of systemStatusTable *************************

systemStatusTable	OBJECT-TYPE
	SYNTAX SEQUENCE OF SystemStatusEntry
	MAX-ACCESS not-accessible
	STATUS current
	DESCRIPTION
		""
	::= { msp1000 100 }

systemStatusEntry	OBJECT-TYPE
	SYNTAX SystemStatusEntry
	MAX-ACCESS not-accessible
	STATUS current
	DESCRIPTION
		""
	INDEX { systemStatusIndex }
	::= { systemStatusTable 1 }


	SystemStatusEntry ::= SEQUENCE {
	systemStatusIndex INTEGER,
	systemStatusAnyErrorCondition INTEGER ,
	systemStatusAnyTestMode INTEGER ,
	systemStatusAnySparePart INTEGER ,
	systemStatusUsedNodeId Unsigned32,
	systemStatusLocalRack Unsigned32,
	systemStatusLocalSlot Unsigned32
	}

systemStatusIndex	OBJECT-TYPE
	SYNTAX INTEGER (0)
	MAX-ACCESS not-accessible
	STATUS current
	DESCRIPTION
		"Automatically generated"
	::= { systemStatusEntry 1 }

systemStatusAnyErrorCondition OBJECT-TYPE   -- any_error_condition
	SYNTAX INTEGER { false(0), true(1) }
	MAX-ACCESS read-only
	STATUS current
	DESCRIPTION
	"True when any error condition is currently present in any module."
	::= { systemStatusEntry 2 }

systemStatusAnyTestMode OBJECT-TYPE   -- any_test_mode
	SYNTAX INTEGER { false(0), true(1) }
	MAX-ACCESS read-only
	STATUS current
	DESCRIPTION
	"True when any module is in loopback test or has a backup engaged."
	::= { systemStatusEntry 3 }

systemStatusAnySparePart OBJECT-TYPE   -- any_spare_part
	SYNTAX INTEGER { false(0), true(1) }
	MAX-ACCESS read-only
	STATUS current
	DESCRIPTION
	"True when any module is marked as spare part."
	::= { systemStatusEntry 4 }

systemStatusUsedNodeId OBJECT-TYPE   -- used_node_id
	SYNTAX Unsigned32
	MAX-ACCESS read-only
	STATUS current
	DESCRIPTION
	"Actually used node id as discovered from device"
	::= { systemStatusEntry 5 }

systemStatusLocalRack OBJECT-TYPE   -- local_rack
	SYNTAX Unsigned32
	MAX-ACCESS read-only
	STATUS current
	DESCRIPTION
	"Indicates in which rack the mangement module over which this information is retrieved is inserted."
	::= { systemStatusEntry 6 }

systemStatusLocalSlot OBJECT-TYPE   -- local_slot
	SYNTAX Unsigned32
	MAX-ACCESS read-only
	STATUS current
	DESCRIPTION
	"Indicates in which slot the mangement module over which this information is retrieved is inserted."
	::= { systemStatusEntry 7 }


-- ********************* End of systemStatusTable ***********************


-- ******************* Begin of moduleInventoryTable *************************

moduleInventoryTable	OBJECT-TYPE
	SYNTAX SEQUENCE OF ModuleInventoryEntry
	MAX-ACCESS not-accessible
	STATUS current
	DESCRIPTION
		""
	::= { msp1000 101 }

moduleInventoryEntry	OBJECT-TYPE
	SYNTAX ModuleInventoryEntry
	MAX-ACCESS not-accessible
	STATUS current
	DESCRIPTION
		""
	INDEX { moduleInventoryIndex }
	::= { moduleInventoryTable 1 }


	ModuleInventoryEntry ::= SEQUENCE {
	moduleInventoryIndex INTEGER,
	moduleInventoryExpectedModule DisplayString,
	moduleInventoryModule DisplayString,
	moduleInventoryType INTEGER ,
	moduleInventoryBoardCode Integer32 ,
	moduleInventoryAdditionalInfo DisplayString,
	moduleInventorySerialNumber DisplayString,
	moduleInventoryOccupiedSlots Unsigned32,
	moduleInventoryProjectNumber DisplayString,
	moduleInventoryBuildVersion DisplayString,
	moduleInventoryProductionDate DisplayString,
	moduleInventoryMfgTestInfo DisplayString,
	moduleInventoryNumberOfOpticalPorts Integer32 ,
	moduleInventoryNumberOfSfpPorts Integer32 ,
	moduleInventoryNumberOfXfpPorts Integer32 ,
	moduleInventoryCoreFirmwareVersion DisplayString,
	moduleInventoryCoreFirmwareDate DisplayString,
	moduleInventoryApplFirmwareVersion DisplayString,
	moduleInventoryApplFirmwareDate DisplayString
	}

moduleInventoryIndex	OBJECT-TYPE
	SYNTAX INTEGER (0..11)
	MAX-ACCESS not-accessible
	STATUS current
	DESCRIPTION
		"Automatically generated"
	::= { moduleInventoryEntry 1 }

moduleInventoryExpectedModule OBJECT-TYPE   -- expected_module
	SYNTAX DisplayString
	MAX-ACCESS read-only
	STATUS current
	DESCRIPTION
	"Name of module configured for this slot."
	::= { moduleInventoryEntry 2 }

moduleInventoryModule OBJECT-TYPE   -- module
	SYNTAX DisplayString
	MAX-ACCESS read-only
	STATUS current
	DESCRIPTION
	"Name of module actually discovered in this slot. This name should be equal to the above name otherwise configuration may not apply properly."
	::= { moduleInventoryEntry 3 }

moduleInventoryType OBJECT-TYPE   -- type
	SYNTAX INTEGER
		{
		empty (0),
		unknown (1),
		transponder (2),
		measurement (3),
		amplifier (4),
		management (5),
		passive (6),
		occupied (7)
		}
	MAX-ACCESS read-only
	STATUS current
	DESCRIPTION
	"General functional type of module inserted."
	::= { moduleInventoryEntry 4 }

moduleInventoryBoardCode OBJECT-TYPE   -- board_code
	SYNTAX Integer32 (0..255)
	MAX-ACCESS read-only
	STATUS current
	DESCRIPTION
	"Internal code of actually inserted module."
	::= { moduleInventoryEntry 5 }

moduleInventoryAdditionalInfo OBJECT-TYPE   -- additional_info
	SYNTAX DisplayString
	MAX-ACCESS read-only
	STATUS current
	DESCRIPTION
	"Additional information that may be saved in some modules during production."
	::= { moduleInventoryEntry 6 }

moduleInventorySerialNumber OBJECT-TYPE   -- serial_number
	SYNTAX DisplayString
	MAX-ACCESS read-only
	STATUS current
	DESCRIPTION
	"Serial number as stored within the hardware."
	::= { moduleInventoryEntry 7 }

moduleInventoryOccupiedSlots OBJECT-TYPE   -- occupied_slots
	SYNTAX Unsigned32
	MAX-ACCESS read-only
	STATUS current
	DESCRIPTION
	"Number of slots taken by this module. Usually 1."
	::= { moduleInventoryEntry 8 }

moduleInventoryProjectNumber OBJECT-TYPE   -- project_number
	SYNTAX DisplayString
	MAX-ACCESS read-only
	STATUS current
	DESCRIPTION
	"Internal hardware project number"
	::= { moduleInventoryEntry 9 }

moduleInventoryBuildVersion OBJECT-TYPE   -- build_version
	SYNTAX DisplayString
	MAX-ACCESS read-only
	STATUS current
	DESCRIPTION
	"Precise build code for hardware version tracking."
	::= { moduleInventoryEntry 10 }

moduleInventoryProductionDate OBJECT-TYPE   -- production_date
	SYNTAX DisplayString
	MAX-ACCESS read-only
	STATUS current
	DESCRIPTION
	"Production data of the module"
	::= { moduleInventoryEntry 11 }

moduleInventoryMfgTestInfo OBJECT-TYPE   -- mfg_test_info
	SYNTAX DisplayString
	MAX-ACCESS read-only
	STATUS current
	DESCRIPTION
	" Internal information for quality management. Manufacturing Site / Test Site / Test Person"
	::= { moduleInventoryEntry 12 }

moduleInventoryNumberOfOpticalPorts OBJECT-TYPE   -- number_of_optical_ports
	SYNTAX Integer32 (0..255)
	MAX-ACCESS read-only
	STATUS current
	DESCRIPTION
	"Indicates the number of actively monitored optical ports of this type of module."
	::= { moduleInventoryEntry 13 }

moduleInventoryNumberOfSfpPorts OBJECT-TYPE   -- number_of_sfp_ports
	SYNTAX Integer32 (0..255)
	MAX-ACCESS read-only
	STATUS current
	DESCRIPTION
	"Indicates the number of optical SFP or SFP+ ports of this type of module."
	::= { moduleInventoryEntry 14 }

moduleInventoryNumberOfXfpPorts OBJECT-TYPE   -- number_of_xfp_ports
	SYNTAX Integer32 (0..255)
	MAX-ACCESS read-only
	STATUS current
	DESCRIPTION
	"Indicates the number of optical XFP ports of this type of module."
	::= { moduleInventoryEntry 15 }

moduleInventoryCoreFirmwareVersion OBJECT-TYPE   -- core_firmware_version
	SYNTAX DisplayString
	MAX-ACCESS read-only
	STATUS current
	DESCRIPTION
	"Core operating system software version."
	::= { moduleInventoryEntry 16 }

moduleInventoryCoreFirmwareDate OBJECT-TYPE   -- core_firmware_date
	SYNTAX DisplayString
	MAX-ACCESS read-only
	STATUS current
	DESCRIPTION
	"Core operating system software creation date."
	::= { moduleInventoryEntry 17 }

moduleInventoryApplFirmwareVersion OBJECT-TYPE   -- appl_firmware_version
	SYNTAX DisplayString
	MAX-ACCESS read-only
	STATUS current
	DESCRIPTION
	"Application software version."
	::= { moduleInventoryEntry 18 }

moduleInventoryApplFirmwareDate OBJECT-TYPE   -- appl_firmware_date
	SYNTAX DisplayString
	MAX-ACCESS read-only
	STATUS current
	DESCRIPTION
	"Application software creation date."
	::= { moduleInventoryEntry 19 }


-- ********************* End of moduleInventoryTable ***********************


-- ******************* Begin of moduleStatusTable *************************

moduleStatusTable	OBJECT-TYPE
	SYNTAX SEQUENCE OF ModuleStatusEntry
	MAX-ACCESS not-accessible
	STATUS current
	DESCRIPTION
		"This table holds a record for each module in the system. Note that not all modules deliver every kind of status."
	::= { msp1000 102 }

moduleStatusEntry	OBJECT-TYPE
	SYNTAX ModuleStatusEntry
	MAX-ACCESS not-accessible
	STATUS current
	DESCRIPTION
		""
	INDEX { moduleStatusIndex }
	::= { moduleStatusTable 1 }


	ModuleStatusEntry ::= SEQUENCE {
	moduleStatusIndex INTEGER,
	moduleStatusModule DisplayString,
	moduleStatusSystemOk INTEGER ,
	moduleStatusErrorCondition INTEGER ,
	moduleStatusTestMode INTEGER ,
	moduleStatusSparePart INTEGER ,
	moduleStatusUptime Counter32,
	moduleStatusTimeSinceCounterReset Counter32,
	moduleStatusTemperature Integer32 ,
	moduleStatusTooHot INTEGER ,
	moduleStatusBackupState BITS ,
	moduleStatusBackupCounter Unsigned32,
	moduleStatusBackupDuration Counter32
	}

moduleStatusIndex	OBJECT-TYPE
	SYNTAX INTEGER (0..11)
	MAX-ACCESS not-accessible
	STATUS current
	DESCRIPTION
		"Automatically generated"
	::= { moduleStatusEntry 1 }

moduleStatusModule OBJECT-TYPE   -- module
	SYNTAX DisplayString
	MAX-ACCESS read-only
	STATUS current
	DESCRIPTION
	"Name of module actually discovered in this slot."
	::= { moduleStatusEntry 2 }

moduleStatusSystemOk OBJECT-TYPE   -- system_ok
	SYNTAX INTEGER { false(0), true(1) }
	MAX-ACCESS read-only
	STATUS current
	DESCRIPTION
	"True when the module has booted and appears ok."
	::= { moduleStatusEntry 3 }

moduleStatusErrorCondition OBJECT-TYPE   -- error_condition
	SYNTAX INTEGER { false(0), true(1) }
	MAX-ACCESS read-only
	STATUS current
	DESCRIPTION
	"True when any error condition is currently present."
	::= { moduleStatusEntry 4 }

moduleStatusTestMode OBJECT-TYPE   -- test_mode
	SYNTAX INTEGER { false(0), true(1) }
	MAX-ACCESS read-only
	STATUS current
	DESCRIPTION
	"True when module is in loopback test or a backup is engaged."
	::= { moduleStatusEntry 5 }

moduleStatusSparePart OBJECT-TYPE   -- spare_part
	SYNTAX INTEGER { false(0), true(1) }
	MAX-ACCESS read-only
	STATUS current
	DESCRIPTION
	"True when module is marked as spare part."
	::= { moduleStatusEntry 6 }

moduleStatusUptime OBJECT-TYPE   -- uptime
	SYNTAX Counter32
	MAX-ACCESS read-only
	STATUS current
	DESCRIPTION
	"Uptime since last reboot in seconds."
	::= { moduleStatusEntry 7 }

moduleStatusTimeSinceCounterReset OBJECT-TYPE   -- time_since_counter_reset
	SYNTAX Counter32
	MAX-ACCESS read-only
	STATUS current
	DESCRIPTION
	"How long ago have the statistics counter been restarted."
	::= { moduleStatusEntry 8 }

moduleStatusTemperature OBJECT-TYPE   -- temperature
	SYNTAX Integer32 (0..255)
	MAX-ACCESS read-only
	STATUS current
	DESCRIPTION
	"Temperature value in centigrade."
	::= { moduleStatusEntry 9 }

moduleStatusTooHot OBJECT-TYPE   -- too_hot
	SYNTAX INTEGER { false(0), true(1) }
	MAX-ACCESS read-only
	STATUS current
	DESCRIPTION
	"True when module is running too hot."
	::= { moduleStatusEntry 10 }

moduleStatusBackupState OBJECT-TYPE   -- backup_state
	SYNTAX BITS
		{
		disrupted (0),
		backup (1),
		awaitSwitchback (2),
		manual (3)
		}
	MAX-ACCESS read-only
	STATUS current
	DESCRIPTION
	"Indicates if a backup is active and in which state."
	::= { moduleStatusEntry 11 }

moduleStatusBackupCounter OBJECT-TYPE   -- backup_counter
	SYNTAX Unsigned32
	MAX-ACCESS read-only
	STATUS current
	DESCRIPTION
	"Counts the number of times this module has initiated a backup (if backup feature is available for this module type)."
	::= { moduleStatusEntry 12 }

moduleStatusBackupDuration OBJECT-TYPE   -- backup_duration
	SYNTAX Counter32
	MAX-ACCESS read-only
	STATUS current
	DESCRIPTION
	"How long the backup has been activated in total since last value reset."
	::= { moduleStatusEntry 13 }


-- ********************* End of moduleStatusTable ***********************


-- ******************* Begin of portStatusTable *************************

portStatusTable	OBJECT-TYPE
	SYNTAX SEQUENCE OF PortStatusEntry
	MAX-ACCESS not-accessible
	STATUS current
	DESCRIPTION
		"This table holds a record for each optical port of the system. Note that not all modules deliver every kind of statistic."
	::= { msp1000 103 }

portStatusEntry	OBJECT-TYPE
	SYNTAX PortStatusEntry
	MAX-ACCESS not-accessible
	STATUS current
	DESCRIPTION
		""
	INDEX { portStatusPortIndex }
	::= { portStatusTable 1 }


	PortStatusEntry ::= SEQUENCE {
	portStatusPortIndex INTEGER,
	portStatusModule DisplayString,
	portStatusLocation DisplayString,
	portStatusSnmpPort Unsigned32,
	portStatusAlias DisplayString,
	portStatusAdminStatus INTEGER ,
	portStatusOperStatus INTEGER ,
	portStatusDetailedStatus BITS ,
	portStatusPortDatarate INTEGER ,
	portStatusUpdateTimeStamp DisplayString,
	portStatusTimeSinceValueReset Counter32,
	portStatusTimeSinceLastError Counter32,
	portStatusTimeSignalTooLow Counter32,
	portStatusSignalTooLowCounter Unsigned32,
	portStatusTimeSignalTooHigh Counter32,
	portStatusSignalTooHighCounter Unsigned32,
	portStatusLowThreshold DisplayString,
	portStatusCurrentInputSignal DisplayString,
	portStatusHighThreshold DisplayString
	}

portStatusPortIndex	OBJECT-TYPE
	SYNTAX INTEGER (0..47)
	MAX-ACCESS not-accessible
	STATUS current
	DESCRIPTION
		"Automatically generated"
	::= { portStatusEntry 1 }

portStatusModule OBJECT-TYPE   -- module
	SYNTAX DisplayString
	MAX-ACCESS read-only
	STATUS current
	DESCRIPTION
	"Name of module in which this port is present."
	::= { portStatusEntry 2 }

portStatusLocation OBJECT-TYPE   -- location
	SYNTAX DisplayString
	MAX-ACCESS read-only
	STATUS current
	DESCRIPTION
	"Textual description of port location."
	::= { portStatusEntry 3 }

portStatusSnmpPort OBJECT-TYPE   -- snmp_port
	SYNTAX Unsigned32
	MAX-ACCESS read-only
	STATUS current
	DESCRIPTION
	"Slot and port representation as used in SNMP. Formula is Slot*10000 + Port*10."
	::= { portStatusEntry 4 }

portStatusAlias OBJECT-TYPE   -- alias
	SYNTAX DisplayString
	MAX-ACCESS read-only
	STATUS current
	DESCRIPTION
	"Configured alias nickname of this port."
	::= { portStatusEntry 5 }

portStatusAdminStatus OBJECT-TYPE   -- admin_status
	SYNTAX INTEGER
		{
		none (0),
		up (1),
		down (2),
		testing (3)
		}
	MAX-ACCESS read-only
	STATUS current
	DESCRIPTION
	"Reflects the administrative setting of this port."
	::= { portStatusEntry 6 }

portStatusOperStatus OBJECT-TYPE   -- oper_status
	SYNTAX INTEGER
		{
		none (0),
		up (1),
		down (2),
		testing (3)
		}
	MAX-ACCESS read-only
	STATUS current
	DESCRIPTION
	"Indicates the combined operation port status."
	::= { portStatusEntry 7 }

portStatusDetailedStatus OBJECT-TYPE   -- detailed_status
	SYNTAX BITS
		{
		disabled (0),
		sfpMissing (1),
		pllNotLocked (2),
		signalLow (3),
		tooHigh (4),
		laserOff (5),
		loop (6),
		reserved (7),
		unknown (8),
		none (9)
		}
	MAX-ACCESS read-only
	STATUS current
	DESCRIPTION
	"Indicates detailed issues related to the port."
	::= { portStatusEntry 8 }

portStatusPortDatarate OBJECT-TYPE   -- port_datarate
	SYNTAX INTEGER
		{
		none (0),
		txp (1),
		ms100mEth (2),
		ms1gEth (3),
		ms10gEth (4),
		ms1xFc (10),
		ms2xFc (11),
		ms4xFc (12),
		ms8xFc (13),
		ms10xFc (14),
		ms16xFc (15),
		oc3 (20),
		oc12 (21),
		oc48 (22),
		oc192 (23),
		otu1 (30),
		otu1e (31),
		otu1f (32),
		otu2 (33),
		otu2e (34),
		otu2f (35),
		fix100 (40),
		escon (41),
		sdi (42),
		hdtv (43),
		tdm2 (44),
		other (45)
		}
	MAX-ACCESS read-only
	STATUS current
	DESCRIPTION
	"Reflects the data rate setting of this port."
	::= { portStatusEntry 9 }

portStatusUpdateTimeStamp OBJECT-TYPE   -- update_time_stamp
	SYNTAX DisplayString
	MAX-ACCESS read-only
	STATUS current
	DESCRIPTION
	"Indicates the time when this record was last updated."
	::= { portStatusEntry 10 }

portStatusTimeSinceValueReset OBJECT-TYPE   -- time_since_value_reset
	SYNTAX Counter32
	MAX-ACCESS read-only
	STATUS current
	DESCRIPTION
	"Time since when the following statistics have been accumulated. They restart upon module power up or on forced value reset."
	::= { portStatusEntry 11 }

portStatusTimeSinceLastError OBJECT-TYPE   -- time_since_last_error
	SYNTAX Counter32
	MAX-ACCESS read-only
	STATUS current
	DESCRIPTION
	"Time since last input signal loss or input signal too high."
	::= { portStatusEntry 12 }

portStatusTimeSignalTooLow OBJECT-TYPE   -- time_signal_too_low
	SYNTAX Counter32
	MAX-ACCESS read-only
	STATUS current
	DESCRIPTION
	"Total time the input signal was below threshold."
	::= { portStatusEntry 13 }

portStatusSignalTooLowCounter OBJECT-TYPE   -- signal_too_low_counter
	SYNTAX Unsigned32
	MAX-ACCESS read-only
	STATUS current
	DESCRIPTION
	"Number of times a transition to signal too low has occured."
	::= { portStatusEntry 14 }

portStatusTimeSignalTooHigh OBJECT-TYPE   -- time_signal_too_high
	SYNTAX Counter32
	MAX-ACCESS read-only
	STATUS current
	DESCRIPTION
	"Total time the input signal was above high threshold."
	::= { portStatusEntry 15 }

portStatusSignalTooHighCounter OBJECT-TYPE   -- signal_too_high_counter
	SYNTAX Unsigned32
	MAX-ACCESS read-only
	STATUS current
	DESCRIPTION
	"Number of times a transition to signal too high has occured."
	::= { portStatusEntry 16 }

portStatusLowThreshold OBJECT-TYPE   -- low_threshold
	SYNTAX DisplayString
	MAX-ACCESS read-only
	STATUS current
	DESCRIPTION
	"Defined signal too low threshold."
	::= { portStatusEntry 17 }

portStatusCurrentInputSignal OBJECT-TYPE   -- current_input_signal
	SYNTAX DisplayString
	MAX-ACCESS read-only
	STATUS current
	DESCRIPTION
	"Actual current signal level."
	::= { portStatusEntry 18 }

portStatusHighThreshold OBJECT-TYPE   -- high_threshold
	SYNTAX DisplayString
	MAX-ACCESS read-only
	STATUS current
	DESCRIPTION
	"Defined signal too high threshold."
	::= { portStatusEntry 19 }


-- ********************* End of portStatusTable ***********************


-- ******************* Begin of emStatusTable *************************

emStatusTable	OBJECT-TYPE
	SYNTAX SEQUENCE OF EmStatusEntry
	MAX-ACCESS not-accessible
	STATUS current
	DESCRIPTION
		"Optical amplifier status"
	::= { msp1000 104 }

emStatusEntry	OBJECT-TYPE
	SYNTAX EmStatusEntry
	MAX-ACCESS not-accessible
	STATUS current
	DESCRIPTION
		""
	INDEX { emStatusIndex }
	::= { emStatusTable 1 }


	EmStatusEntry ::= SEQUENCE {
	emStatusIndex INTEGER,
	emStatusSystemOk INTEGER ,
	emStatusErrors BITS ,
	emStatusHardwareCode DisplayString,
	emStatusTimeSincePowerError Counter32,
	emStatusTimeWithPowerLoss Counter32,
	emStatusInputSignalLowCounter Unsigned32,
	emStatusInputPower DisplayString,
	emStatusSignalGain DisplayString,
	emStatusOptimalFlatGain DisplayString,
	emStatusBackReflection DisplayString,
	emStatusSignalOutputPower DisplayString,
	emStatusTotalOutputPower DisplayString,
	emStatusMinOutputPower DisplayString,
	emStatusMaxOutputPower DisplayString,
	emStatusCfgOutputPower DisplayString
	}

emStatusIndex	OBJECT-TYPE
	SYNTAX INTEGER (0..11)
	MAX-ACCESS not-accessible
	STATUS current
	DESCRIPTION
		"Automatically generated"
	::= { emStatusEntry 1 }

emStatusSystemOk OBJECT-TYPE   -- system_ok
	SYNTAX INTEGER { false(0), true(1) }
	MAX-ACCESS read-only
	STATUS current
	DESCRIPTION
	"True when no errors are present"
	::= { emStatusEntry 2 }

emStatusErrors OBJECT-TYPE   -- errors
	SYNTAX BITS
		{
		lossOfInput (0),
		lossOfOutput (1),
		tooHot (2),
		eyeSafetyShutdown (3),
		backReflection (4),
		powerLimit (5),
		overCurrent (6),
		pumpDown (7)
		}
	MAX-ACCESS read-only
	STATUS current
	DESCRIPTION
	"Indicates various optical error conditions."
	::= { emStatusEntry 3 }

emStatusHardwareCode OBJECT-TYPE   -- hardware_code
	SYNTAX DisplayString
	MAX-ACCESS read-only
	STATUS current
	DESCRIPTION
	"Details codes about the installed hardware components."
	::= { emStatusEntry 4 }

emStatusTimeSincePowerError OBJECT-TYPE   -- time_since_power_error
	SYNTAX Counter32
	MAX-ACCESS read-only
	STATUS current
	DESCRIPTION
	"How long ago since the last time the output power was in error condition."
	::= { emStatusEntry 5 }

emStatusTimeWithPowerLoss OBJECT-TYPE   -- time_with_power_loss
	SYNTAX Counter32
	MAX-ACCESS read-only
	STATUS current
	DESCRIPTION
	"Accumulated time the output power has been down."
	::= { emStatusEntry 6 }

emStatusInputSignalLowCounter OBJECT-TYPE   -- input_signal_low_counter
	SYNTAX Unsigned32
	MAX-ACCESS read-only
	STATUS current
	DESCRIPTION
	"Number of times a loss of signal has occured."
	::= { emStatusEntry 7 }

emStatusInputPower OBJECT-TYPE   -- input_power
	SYNTAX DisplayString
	MAX-ACCESS read-only
	STATUS current
	DESCRIPTION
	"Optical input power of port A."
	::= { emStatusEntry 8 }

emStatusSignalGain OBJECT-TYPE   -- signal_gain
	SYNTAX DisplayString
	MAX-ACCESS read-only
	STATUS current
	DESCRIPTION
	"Indicates how strong the input signal is amplified."
	::= { emStatusEntry 9 }

emStatusOptimalFlatGain OBJECT-TYPE   -- optimal_flat_gain
	SYNTAX DisplayString
	MAX-ACCESS read-only
	STATUS current
	DESCRIPTION
	"Indicates the best gain setting for an even amplification accross the wavelength channels"
	::= { emStatusEntry 10 }

emStatusBackReflection OBJECT-TYPE   -- back_reflection
	SYNTAX DisplayString
	MAX-ACCESS read-only
	STATUS current
	DESCRIPTION
	"The value should be low and indicates cable issues if not."
	::= { emStatusEntry 11 }

emStatusSignalOutputPower OBJECT-TYPE   -- signal_output_power
	SYNTAX DisplayString
	MAX-ACCESS read-only
	STATUS current
	DESCRIPTION
	"Indicated the actually achieved optical signal output power."
	::= { emStatusEntry 12 }

emStatusTotalOutputPower OBJECT-TYPE   -- total_output_power
	SYNTAX DisplayString
	MAX-ACCESS read-only
	STATUS current
	DESCRIPTION
	"Indicated the actually achieved optical output power leaving the module (including noise)."
	::= { emStatusEntry 13 }

emStatusMinOutputPower OBJECT-TYPE   -- min_output_power
	SYNTAX DisplayString
	MAX-ACCESS read-only
	STATUS current
	DESCRIPTION
	"Indicates the minimum optical output level that must be send out"
	::= { emStatusEntry 14 }

emStatusMaxOutputPower OBJECT-TYPE   -- max_output_power
	SYNTAX DisplayString
	MAX-ACCESS read-only
	STATUS current
	DESCRIPTION
	"Indicates the maximum optical output level that can be send out"
	::= { emStatusEntry 15 }

emStatusCfgOutputPower OBJECT-TYPE   -- cfg_output_power
	SYNTAX DisplayString
	MAX-ACCESS read-only
	STATUS current
	DESCRIPTION
	"Indicated the desired configured optical output power"
	::= { emStatusEntry 16 }


-- ********************* End of emStatusTable ***********************


-- ******************* Begin of bertStatusTable *************************

bertStatusTable	OBJECT-TYPE
	SYNTAX SEQUENCE OF BertStatusEntry
	MAX-ACCESS not-accessible
	STATUS current
	DESCRIPTION
		"Displays the results of the bit error rate tester (BERT) if it is present and enabled in a slot"
	::= { msp1000 105 }

bertStatusEntry	OBJECT-TYPE
	SYNTAX BertStatusEntry
	MAX-ACCESS not-accessible
	STATUS current
	DESCRIPTION
		""
	INDEX { bertStatusIndex }
	::= { bertStatusTable 1 }


	BertStatusEntry ::= SEQUENCE {
	bertStatusIndex INTEGER,
	bertStatusLocation DisplayString,
	bertStatusBertOperation INTEGER ,
	bertStatusTotalErrors Unsigned32,
	bertStatusTimeSinceLastError Counter32,
	bertStatusTotalTestTime Counter32,
	bertStatusErroredTime Counter32,
	bertStatusBitErrorRate DisplayString,
	bertStatusBerSinceLastError DisplayString,
	bertStatusTheoreticalBer DisplayString,
	bertStatusAvailability DisplayString
	}

bertStatusIndex	OBJECT-TYPE
	SYNTAX INTEGER (0..11)
	MAX-ACCESS not-accessible
	STATUS current
	DESCRIPTION
		"Automatically generated"
	::= { bertStatusEntry 1 }

bertStatusLocation OBJECT-TYPE   -- location
	SYNTAX DisplayString
	MAX-ACCESS read-only
	STATUS current
	DESCRIPTION
	"Textual description of BERT port location."
	::= { bertStatusEntry 2 }

bertStatusBertOperation OBJECT-TYPE   -- bert_operation
	SYNTAX INTEGER
		{
		unused (0),
		inSync (1),
		wasOutOfSync (2),
		outOfSync (3)
		}
	MAX-ACCESS read-only
	STATUS current
	DESCRIPTION
	"Indicates the general bit error rate tester operational status."
	::= { bertStatusEntry 3 }

bertStatusTotalErrors OBJECT-TYPE   -- total_errors
	SYNTAX Unsigned32
	MAX-ACCESS read-only
	STATUS current
	DESCRIPTION
	"Number of errored bits. Only valid when BERT is synchronized."
	::= { bertStatusEntry 4 }

bertStatusTimeSinceLastError OBJECT-TYPE   -- time_since_last_error
	SYNTAX Counter32
	MAX-ACCESS read-only
	STATUS current
	DESCRIPTION
	"Seconds elapsed since the last error was detected."
	::= { bertStatusEntry 5 }

bertStatusTotalTestTime OBJECT-TYPE   -- total_test_time
	SYNTAX Counter32
	MAX-ACCESS read-only
	STATUS current
	DESCRIPTION
	"Accumulated time how long the test was run since last value clear."
	::= { bertStatusEntry 6 }

bertStatusErroredTime OBJECT-TYPE   -- errored_time
	SYNTAX Counter32
	MAX-ACCESS read-only
	STATUS current
	DESCRIPTION
	"Accumulated seconds in which at least on errored bit was detected."
	::= { bertStatusEntry 7 }

bertStatusBitErrorRate OBJECT-TYPE   -- bit_error_rate
	SYNTAX DisplayString
	MAX-ACCESS read-only
	STATUS current
	DESCRIPTION
	"Averaged bit error rate during test interval."
	::= { bertStatusEntry 8 }

bertStatusBerSinceLastError OBJECT-TYPE   -- ber_since_last_error
	SYNTAX DisplayString
	MAX-ACCESS read-only
	STATUS current
	DESCRIPTION
	"Bit error rate since last error."
	::= { bertStatusEntry 9 }

bertStatusTheoreticalBer OBJECT-TYPE   -- theoretical_ber
	SYNTAX DisplayString
	MAX-ACCESS read-only
	STATUS current
	DESCRIPTION
	"Theoretical best possible error rate in the given time frame of the current test interval."
	::= { bertStatusEntry 10 }

bertStatusAvailability OBJECT-TYPE   -- availability
	SYNTAX DisplayString
	MAX-ACCESS read-only
	STATUS current
	DESCRIPTION
	"Relation of transmitted vs. Errored bits."
	::= { bertStatusEntry 11 }


-- ********************* End of bertStatusTable ***********************



END
