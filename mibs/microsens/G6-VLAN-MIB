G6-VLAN-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

protocol MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 2 }

vlan  OBJECT IDENTIFIER ::= { protocol 82 }



-- *************************** CONFIGURATION SECTION ********************************


vlanEnableVlanFiltering OBJECT-TYPE   -- enable_vlan_filtering
	SYNTAX INTEGER {  disabled(0), enabled(1) }
	MAX-ACCESS read-write
	STATUS current
	DESCRIPTION
	"Generally enable VLAN filtering function:"
	::= { vlan 1 }


-- ******************* Begin of vlanIdConfigTable *************************

vlanIdConfigTable	OBJECT-TYPE
	SYNTAX SEQUENCE OF VlanIdConfigEntry
	MAX-ACCESS not-accessible
	STATUS current
	DESCRIPTION
		"This section defines some default VLAN settings."
	::= { vlan 2 }

vlanIdConfigEntry	OBJECT-TYPE
	SYNTAX VlanIdConfigEntry
	MAX-ACCESS not-accessible
	STATUS current
	DESCRIPTION
		""
	INDEX { vlanIdConfigIndex }
	::= { vlanIdConfigTable 1 }


	VlanIdConfigEntry ::= SEQUENCE {
	vlanIdConfigIndex INTEGER,
	vlanIdConfigManagementVlanId Integer32 ,
	vlanIdConfigManagementPriority INTEGER ,
	vlanIdConfigVoiceVlanId Integer32 ,
	vlanIdConfigRstpVlanId Integer32 ,
	vlanIdConfigUnauthorizedVlanId Integer32 ,
	vlanIdConfigSmartofficeVlanId Integer32
	}

vlanIdConfigIndex	OBJECT-TYPE
	SYNTAX INTEGER (0)
	MAX-ACCESS not-accessible
	STATUS current
	DESCRIPTION
		"Automatically generated"
	::= { vlanIdConfigEntry 1 }

vlanIdConfigManagementVlanId OBJECT-TYPE   -- management_vlan_id
	SYNTAX Integer32 (0..65535)
	MAX-ACCESS read-write
	STATUS current
	DESCRIPTION
	"VLAN ID for internal management port. Packets sent by the management agent are tagged with this VLAN ID,"
	::= { vlanIdConfigEntry 2 }

vlanIdConfigManagementPriority OBJECT-TYPE   -- management_priority
	SYNTAX INTEGER
		{
		priority0 (0),
		priority1 (1),
		priority2 (2),
		priority3 (3),
		priority4 (4),
		priority5 (5),
		priority6 (6),
		priority7 (7)
		}
	MAX-ACCESS read-write
	STATUS current
	DESCRIPTION
	"VLAN Priority for internal management port. Packets sent by the internal management agent are tagged with this priority value."
	::= { vlanIdConfigEntry 3 }

vlanIdConfigVoiceVlanId OBJECT-TYPE   -- voice_vlan_id
	SYNTAX Integer32 (0..65535)
	MAX-ACCESS read-write
	STATUS current
	DESCRIPTION
	"Voice VLAN ID. Special VLAN for IP phones."
	::= { vlanIdConfigEntry 4 }

vlanIdConfigRstpVlanId OBJECT-TYPE   -- rstp_vlan_id
	SYNTAX Integer32 (0..65535)
	MAX-ACCESS read-write
	STATUS current
	DESCRIPTION
	"RSTP VLAN ID. When using single instance Spanning Tree (STP or RSTP) in combination with VLANs, all spanning tree messages are tagged with this VLAN ID. "
	::= { vlanIdConfigEntry 5 }

vlanIdConfigUnauthorizedVlanId OBJECT-TYPE   -- unauthorized_vlan_id
	SYNTAX Integer32 (0..65535)
	MAX-ACCESS read-write
	STATUS current
	DESCRIPTION
	"When using port access control with dynamic VLANs, unauthorized ports are attached to this VLAN."
	::= { vlanIdConfigEntry 6 }

vlanIdConfigSmartofficeVlanId OBJECT-TYPE   -- smartoffice_vlan_id
	SYNTAX Integer32 (0..65535)
	MAX-ACCESS read-write
	STATUS current
	DESCRIPTION
	"VLAN ID used for SmartOffice control traffic between director and controllers. Also used by the SmartOffice GUI."
	::= { vlanIdConfigEntry 7 }


-- ********************* End of vlanIdConfigTable ***********************


-- ******************* Begin of portConfigTable *************************

portConfigTable	OBJECT-TYPE
	SYNTAX SEQUENCE OF PortConfigEntry
	MAX-ACCESS not-accessible
	STATUS current
	DESCRIPTION
		"These settings define the default VLANs per port and defines how untagged data are treated."
	::= { vlan 3 }

portConfigEntry	OBJECT-TYPE
	SYNTAX PortConfigEntry
	MAX-ACCESS not-accessible
	STATUS current
	DESCRIPTION
		""
	INDEX { portConfigPortIndex }
	::= { portConfigTable 1 }


	PortConfigEntry ::= SEQUENCE {
	portConfigPortIndex INTEGER,
	portConfigVlanMode INTEGER ,
	portConfigDefaultVlanId Integer32 ,
	portConfigForceDefaultVlanId INTEGER ,
	portConfigDefaultPriority INTEGER ,
	portConfigPriorityOverride INTEGER ,
	portConfigUnauthorizedVlanId Integer32 ,
	portConfigFallbackVlanId Integer32 ,
	portConfigQInQEthertype INTEGER
	}

portConfigPortIndex	OBJECT-TYPE
	SYNTAX INTEGER (0..24)
	MAX-ACCESS not-accessible
	STATUS current
	DESCRIPTION
		"Automatically generated"
	::= { portConfigEntry 1 }

portConfigVlanMode OBJECT-TYPE   -- vlan_mode
	SYNTAX INTEGER
		{
		access (0),
		hybrid (1),
		trunk (2),
		qInQCustomer (3),
		qInQProvider (4)
		}
	MAX-ACCESS read-write
	STATUS current
	DESCRIPTION
	"Defines how the VLAN tag of incoming and outgoing packets shall be handled on port."
	::= { portConfigEntry 2 }

portConfigDefaultVlanId OBJECT-TYPE   -- default_vlan_id
	SYNTAX Integer32 (0..65535)
	MAX-ACCESS read-write
	STATUS current
	DESCRIPTION
	"Default VLAN ID for port. Incoming packets without VLAN tag are automatically tagged using the default VLAN ID and default priority values."
	::= { portConfigEntry 3 }

portConfigForceDefaultVlanId OBJECT-TYPE   -- force_default_vlan_id
	SYNTAX INTEGER {  disabled(0), enabled(1) }
	MAX-ACCESS read-write
	STATUS current
	DESCRIPTION
	"When enabled, incoming packets with existing VLAN tag are overwritten with the default port VLAN ID."
	::= { portConfigEntry 4 }

portConfigDefaultPriority OBJECT-TYPE   -- default_priority
	SYNTAX INTEGER
		{
		priority0 (0),
		priority1 (1),
		priority2 (2),
		priority3 (3),
		priority4 (4),
		priority5 (5),
		priority6 (6),
		priority7 (7)
		}
	MAX-ACCESS read-write
	STATUS current
	DESCRIPTION
	"Default priority value for port. Incoming packets without VLAN tag are automatically tagged using the default VLAN ID and default priority values."
	::= { portConfigEntry 5 }

portConfigPriorityOverride OBJECT-TYPE   -- priority_override
	SYNTAX INTEGER {  disabled(0), enabled(1) }
	MAX-ACCESS read-write
	STATUS current
	DESCRIPTION
	"When enabled, incoming packets with existing VLAN tag are overwritten with the default priority value."
	::= { portConfigEntry 6 }

portConfigUnauthorizedVlanId OBJECT-TYPE   -- unauthorized_vlan_id
	SYNTAX Integer32 (0..65535)
	MAX-ACCESS read-write
	STATUS current
	DESCRIPTION
	"When using port access control with dynamic VLANs, unauthorized ports are attached to this VLAN. When set to 0 the global vlan_id_config.unauthorized_vlan_id parameter applies. Use this parameter to set an independend port specific unauthorized vlan."
	::= { portConfigEntry 7 }

portConfigFallbackVlanId OBJECT-TYPE   -- fallback_vlan_id
	SYNTAX Integer32 (0..65535)
	MAX-ACCESS read-write
	STATUS current
	DESCRIPTION
	"When using port access control with dynamic VLANs and a RADIUS server, the fallback vlan is assigned when the RADIUS server is unavailable. If this parameter is set to 0 the unauthorized vlan is used instead. If this is also 0 then the global vlan_id_config.unauthorized_vlan_id parameter applies."
	::= { portConfigEntry 8 }

portConfigQInQEthertype OBJECT-TYPE   -- q_in_q_ethertype
	SYNTAX INTEGER
		{
		ox88a8 (0),
		ox9100 (1),
		ox9200 (2),
		ox8100 (3)
		}
	MAX-ACCESS read-write
	STATUS current
	DESCRIPTION
	"Ethertype configuration only applies for vlan_mode Q_IN_Q."
	::= { portConfigEntry 9 }


-- ********************* End of portConfigTable ***********************


-- ******************* Begin of filterConfigTable *************************

filterConfigTable	OBJECT-TYPE
	SYNTAX SEQUENCE OF FilterConfigEntry
	MAX-ACCESS not-accessible
	STATUS current
	DESCRIPTION
		"Defines the used VLANs and their associated ports."
	::= { vlan 4 }

filterConfigEntry	OBJECT-TYPE
	SYNTAX FilterConfigEntry
	MAX-ACCESS not-accessible
	STATUS current
	DESCRIPTION
		""
	INDEX { filterConfigIndex }
	::= { filterConfigTable 1 }


	FilterConfigEntry ::= SEQUENCE {
	filterConfigIndex INTEGER,
	filterConfigVlanId DisplayString,
	filterConfigEntryMode INTEGER ,
	filterConfigAlias DisplayString,
	filterConfigMstpGroup Integer32 ,
	filterConfigFabricAttachISid Unsigned32,
	filterConfigPortMembers INTEGER,
	filterConfigManagementMembers INTEGER ,
	filterConfigPriorityOverride INTEGER ,
	filterConfigNewPriority INTEGER
	}

filterConfigIndex	OBJECT-TYPE
	SYNTAX INTEGER (0..255)
	MAX-ACCESS not-accessible
	STATUS current
	DESCRIPTION
		"Automatically generated"
	::= { filterConfigEntry 1 }

filterConfigVlanId OBJECT-TYPE   -- vlan_id
	SYNTAX DisplayString
	MAX-ACCESS read-write
	STATUS current
	DESCRIPTION
	"Defines filter table entry for this VLAN ID. This is the key value for the table. Type '=:' to edit, use index '[*] = new_vlan:' to add an entry. Edit string to nothing to delete entry."
	::= { filterConfigEntry 2 }

filterConfigEntryMode OBJECT-TYPE   -- entry_mode
	SYNTAX INTEGER {  disabled(0), enabled(1) }
	MAX-ACCESS read-write
	STATUS current
	DESCRIPTION
	"When disabled, filtering for this VLAN ID is disabled without deleting the table entry. This can be used for testing and configuration. "
	::= { filterConfigEntry 3 }

filterConfigAlias OBJECT-TYPE   -- alias
	SYNTAX DisplayString
	MAX-ACCESS read-write
	STATUS current
	DESCRIPTION
	"User-definable name string for VLAN."
	::= { filterConfigEntry 4 }

filterConfigMstpGroup OBJECT-TYPE   -- mstp_group
	SYNTAX Integer32 (0..65535)
	MAX-ACCESS read-write
	STATUS current
	DESCRIPTION
	"All filter entries with the same mstp_group number will share an MSTP instance. A group may consist of one or many vlan entries. A value of 0 indicates that MSTP is not used for this VLAN."
	::= { filterConfigEntry 5 }

filterConfigFabricAttachISid OBJECT-TYPE   -- fabric_attach_i_sid
	SYNTAX Unsigned32
	MAX-ACCESS read-write
	STATUS current
	DESCRIPTION
	"This parameter defines the VLAN to I-SID binding when the shortest path bridging (SPB) fabric attach feature is used."
	::= { filterConfigEntry 6 }

filterConfigPortMembers OBJECT-TYPE   -- port_members
	SYNTAX INTEGER
	MAX-ACCESS read-write
	STATUS current
	DESCRIPTION
	"Defines port memberships for VLAN. Syntax: slot/port, slot/port or use hex value for quick setup = 0x3f (ports 1-6)"
	::= { filterConfigEntry 7 }

filterConfigManagementMembers OBJECT-TYPE   -- management_members
	SYNTAX INTEGER
		{
		none (0),
		cpu1 (1),
		cpu2 (2),
		all (3)
		}
	MAX-ACCESS read-write
	STATUS current
	DESCRIPTION
	"Defines the port membership for the internal management port(s)."
	::= { filterConfigEntry 8 }

filterConfigPriorityOverride OBJECT-TYPE   -- priority_override
	SYNTAX INTEGER {  disabled(0), enabled(1) }
	MAX-ACCESS read-write
	STATUS current
	DESCRIPTION
	"When enabled the priority value of packets tagged with this VLAN is overwritten with the new_priority value."
	::= { filterConfigEntry 9 }

filterConfigNewPriority OBJECT-TYPE   -- new_priority
	SYNTAX INTEGER
		{
		priority0 (0),
		priority1 (1),
		priority2 (2),
		priority3 (3),
		priority4 (4),
		priority5 (5),
		priority6 (6),
		priority7 (7)
		}
	MAX-ACCESS read-write
	STATUS current
	DESCRIPTION
	"VLAN priority value when priority_override is enabled."
	::= { filterConfigEntry 10 }


-- ********************* End of filterConfigTable ***********************


vlanEnableMvrp OBJECT-TYPE   -- enable_mvrp
	SYNTAX INTEGER {  disabled(0), enabled(1) }
	MAX-ACCESS read-write
	STATUS current
	DESCRIPTION
	"Generally enable MVRP (Multiple VLAN Reservation Protocol) function. MVRP is operational on 802.1q trunk ports only."
	::= { vlan 5 }


-- ******************* Begin of mvrpPortConfigTable *************************

mvrpPortConfigTable	OBJECT-TYPE
	SYNTAX SEQUENCE OF MvrpPortConfigEntry
	MAX-ACCESS not-accessible
	STATUS current
	DESCRIPTION
		"Configuration parameter concerning the port specific MVRP setttings."
	::= { vlan 6 }

mvrpPortConfigEntry	OBJECT-TYPE
	SYNTAX MvrpPortConfigEntry
	MAX-ACCESS not-accessible
	STATUS current
	DESCRIPTION
		""
	INDEX { mvrpPortConfigPortIndex }
	::= { mvrpPortConfigTable 1 }


	MvrpPortConfigEntry ::= SEQUENCE {
	mvrpPortConfigPortIndex INTEGER,
	mvrpPortConfigEnableMvrp INTEGER ,
	mvrpPortConfigRegistrationMode INTEGER ,
	mvrpPortConfigJoinTimer Unsigned32,
	mvrpPortConfigLeaveTimer Unsigned32,
	mvrpPortConfigLeaveallTimer Unsigned32
	}

mvrpPortConfigPortIndex	OBJECT-TYPE
	SYNTAX INTEGER (0..24)
	MAX-ACCESS not-accessible
	STATUS current
	DESCRIPTION
		"Automatically generated"
	::= { mvrpPortConfigEntry 1 }

mvrpPortConfigEnableMvrp OBJECT-TYPE   -- enable_mvrp
	SYNTAX INTEGER {  disabled(0), enabled(1) }
	MAX-ACCESS read-write
	STATUS current
	DESCRIPTION
	"Enable MVRP (Multiple VLAN Reservation Protocol) on this port."
	::= { mvrpPortConfigEntry 2 }

mvrpPortConfigRegistrationMode OBJECT-TYPE   -- registration_mode
	SYNTAX INTEGER
		{
		normal (0),
		fixed (1),
		forbidden (2)
		}
	MAX-ACCESS read-write
	STATUS current
	DESCRIPTION
	"Configuration of the MVRP registration mode."
	::= { mvrpPortConfigEntry 3 }

mvrpPortConfigJoinTimer OBJECT-TYPE   -- join_timer
	SYNTAX Unsigned32
	MAX-ACCESS read-write
	STATUS current
	DESCRIPTION
	"Number of milliseconds that the interface must wait before sending MVRP PDUs."
	::= { mvrpPortConfigEntry 4 }

mvrpPortConfigLeaveTimer OBJECT-TYPE   -- leave_timer
	SYNTAX Unsigned32
	MAX-ACCESS read-write
	STATUS current
	DESCRIPTION
	"Number of milliseconds that the switch retains a VLAN in the Leave state before the VLAN is unregistered. At a minimum, set the leave-timer interval at twice the join-timer interval."
	::= { mvrpPortConfigEntry 5 }

mvrpPortConfigLeaveallTimer OBJECT-TYPE   -- leaveall_timer
	SYNTAX Unsigned32
	MAX-ACCESS read-write
	STATUS current
	DESCRIPTION
	"Number of milliseconds between the sending of Leave All messages."
	::= { mvrpPortConfigEntry 6 }


-- ********************* End of mvrpPortConfigTable ***********************


-- ******************* Begin of fabricAttachPortConfigTable *************************

fabricAttachPortConfigTable	OBJECT-TYPE
	SYNTAX SEQUENCE OF FabricAttachPortConfigEntry
	MAX-ACCESS not-accessible
	STATUS current
	DESCRIPTION
		"Configuration parameter controling the fabric attach feature. Each port can be configured individually."
	::= { vlan 7 }

fabricAttachPortConfigEntry	OBJECT-TYPE
	SYNTAX FabricAttachPortConfigEntry
	MAX-ACCESS not-accessible
	STATUS current
	DESCRIPTION
		""
	INDEX { fabricAttachPortConfigPortIndex }
	::= { fabricAttachPortConfigTable 1 }


	FabricAttachPortConfigEntry ::= SEQUENCE {
	fabricAttachPortConfigPortIndex INTEGER,
	fabricAttachPortConfigEnableFabricAttach INTEGER ,
	fabricAttachPortConfigMsgAuthentication INTEGER ,
	fabricAttachPortConfigEnterFaAuthKey DisplayString,
	fabricAttachPortConfigEncryptedFaAuthKey DisplayString
	}

fabricAttachPortConfigPortIndex	OBJECT-TYPE
	SYNTAX INTEGER (0..24)
	MAX-ACCESS not-accessible
	STATUS current
	DESCRIPTION
		"Automatically generated"
	::= { fabricAttachPortConfigEntry 1 }

fabricAttachPortConfigEnableFabricAttach OBJECT-TYPE   -- enable_fabric_attach
	SYNTAX INTEGER {  disabled(0), enabled(1) }
	MAX-ACCESS read-write
	STATUS current
	DESCRIPTION
	"Shortest path bridging (SPB) fabric attach feature can be used to simplify configuration in an SBP enabled network. Please also generally enable the LLDP function to use this feature. When enabled the port will act as client to a fabric attach network."
	::= { fabricAttachPortConfigEntry 2 }

fabricAttachPortConfigMsgAuthentication OBJECT-TYPE   -- msg_authentication
	SYNTAX INTEGER {  disabled(0), enabled(1) }
	MAX-ACCESS read-write
	STATUS current
	DESCRIPTION
	"when enabled message authentication using the fa_auth key is used."
	::= { fabricAttachPortConfigEntry 3 }

fabricAttachPortConfigEnterFaAuthKey OBJECT-TYPE   -- enter_fa_auth_key
	SYNTAX DisplayString
	MAX-ACCESS read-write
	STATUS current
	DESCRIPTION
	"Enter the fabric attach authentication keys required to access the network. No spaces are permitted."
	::= { fabricAttachPortConfigEntry 4 }

fabricAttachPortConfigEncryptedFaAuthKey OBJECT-TYPE   -- encrypted_fa_auth_key
	SYNTAX DisplayString
	MAX-ACCESS read-write
	STATUS current
	DESCRIPTION
	"Encrypted form of the entered key. This is automatically filled in when the enter_fa_auth command is executed."
	::= { fabricAttachPortConfigEntry 5 }


-- ********************* End of fabricAttachPortConfigTable ***********************



-- ****************************** STATUS SECTION ********************************


vlanNumberOfEntries OBJECT-TYPE   -- number_of_entries
	SYNTAX Integer32 (0..65535)
	MAX-ACCESS read-only
	STATUS current
	DESCRIPTION
	"Number of VLAN entries in the table."
	::= { vlan 100 }


-- ******************* Begin of statusTable *************************

statusTable	OBJECT-TYPE
	SYNTAX SEQUENCE OF StatusEntry
	MAX-ACCESS not-accessible
	STATUS current
	DESCRIPTION
		"This table lists the status of all defined VLANs."
	::= { vlan 101 }

statusEntry	OBJECT-TYPE
	SYNTAX StatusEntry
	MAX-ACCESS not-accessible
	STATUS current
	DESCRIPTION
		""
	INDEX { statusVlanIndex }
	::= { statusTable 1 }


	StatusEntry ::= SEQUENCE {
	statusVlanIndex INTEGER,
	statusVlanId Integer32 ,
	statusTimeMark Unsigned32,
	statusAlias DisplayString,
	statusPortMembers INTEGER,
	statusFilterDatabase Unsigned32,
	statusEgressPorts INTEGER,
	statusUntaggedPorts INTEGER,
	statusFabricAttachState INTEGER ,
	statusCreationMode INTEGER ,
	statusCreationTime Counter32
	}

statusVlanIndex	OBJECT-TYPE
	SYNTAX INTEGER (0..255)
	MAX-ACCESS not-accessible
	STATUS current
	DESCRIPTION
		"Automatically generated"
	::= { statusEntry 1 }

statusVlanId OBJECT-TYPE   -- vlan_id
	SYNTAX Integer32 (0..65535)
	MAX-ACCESS read-only
	STATUS current
	DESCRIPTION
	"VLAN identifier"
	::= { statusEntry 2 }

statusTimeMark OBJECT-TYPE   -- time_mark
	SYNTAX Unsigned32
	MAX-ACCESS read-only
	STATUS current
	DESCRIPTION
	""
	::= { statusEntry 3 }

statusAlias OBJECT-TYPE   -- alias
	SYNTAX DisplayString
	MAX-ACCESS read-only
	STATUS current
	DESCRIPTION
	"Contains the alias name for static entries."
	::= { statusEntry 4 }

statusPortMembers OBJECT-TYPE   -- port_members
	SYNTAX INTEGER
	MAX-ACCESS read-only
	STATUS current
	DESCRIPTION
	"Lists all ports that belong to this VLAN."
	::= { statusEntry 5 }

statusFilterDatabase OBJECT-TYPE   -- filter_database
	SYNTAX Unsigned32
	MAX-ACCESS read-only
	STATUS current
	DESCRIPTION
	"filter data base"
	::= { statusEntry 6 }

statusEgressPorts OBJECT-TYPE   -- egress_ports
	SYNTAX INTEGER
	MAX-ACCESS read-only
	STATUS current
	DESCRIPTION
	"The set of ports which are transmitting traffic for this VLAN as either tagged or untagged frames."
	::= { statusEntry 7 }

statusUntaggedPorts OBJECT-TYPE   -- untagged_ports
	SYNTAX INTEGER
	MAX-ACCESS read-only
	STATUS current
	DESCRIPTION
	"The set of ports which are transmitting traffic for this VLAN as untagged frames."
	::= { statusEntry 8 }

statusFabricAttachState OBJECT-TYPE   -- fabric_attach_state
	SYNTAX INTEGER
		{
		disabled (0),
		active (1),
		rejected (2)
		}
	MAX-ACCESS read-only
	STATUS current
	DESCRIPTION
	"Indicates if auto attachment to the fabric was successful."
	::= { statusEntry 9 }

statusCreationMode OBJECT-TYPE   -- creation_mode
	SYNTAX INTEGER
		{
		filterTable (0),
		pacc (1),
		mvrp (2)
		}
	MAX-ACCESS read-only
	STATUS current
	DESCRIPTION
	"Indicates by which means this VLAN entry was created."
	::= { statusEntry 10 }

statusCreationTime OBJECT-TYPE   -- creation_time
	SYNTAX Counter32
	MAX-ACCESS read-only
	STATUS current
	DESCRIPTION
	"The value of system.uptime when this VLAN was created."
	::= { statusEntry 11 }


-- ********************* End of statusTable ***********************


-- ******************* Begin of portStatusTable *************************

portStatusTable	OBJECT-TYPE
	SYNTAX SEQUENCE OF PortStatusEntry
	MAX-ACCESS not-accessible
	STATUS current
	DESCRIPTION
		"Port related view of the currently active VLAN setup."
	::= { vlan 102 }

portStatusEntry	OBJECT-TYPE
	SYNTAX PortStatusEntry
	MAX-ACCESS not-accessible
	STATUS current
	DESCRIPTION
		""
	INDEX { portStatusPortIndex }
	::= { portStatusTable 1 }


	PortStatusEntry ::= SEQUENCE {
	portStatusPortIndex INTEGER,
	portStatusAssignedVlanIds DisplayString,
	portStatusDynamicDefaultVlanId Integer32 ,
	portStatusLastUpdateMethod INTEGER ,
	portStatusLastUpdatingMac MacAddress,
	portStatusLastUpdateTime Counter32
	}

portStatusPortIndex	OBJECT-TYPE
	SYNTAX INTEGER (0..24)
	MAX-ACCESS not-accessible
	STATUS current
	DESCRIPTION
		"Automatically generated"
	::= { portStatusEntry 1 }

portStatusAssignedVlanIds OBJECT-TYPE   -- assigned_vlan_ids
	SYNTAX DisplayString
	MAX-ACCESS read-only
	STATUS current
	DESCRIPTION
	"List of all VLAN ids that are configured or dynamically assigned to this port."
	::= { portStatusEntry 2 }

portStatusDynamicDefaultVlanId OBJECT-TYPE   -- dynamic_default_vlan_id
	SYNTAX Integer32 (0..65535)
	MAX-ACCESS read-only
	STATUS current
	DESCRIPTION
	"Indicates the current port default VLAN. The value may change due to port authentication or configuration."
	::= { portStatusEntry 3 }

portStatusLastUpdateMethod OBJECT-TYPE   -- last_update_method
	SYNTAX INTEGER
		{
		config (0),
		viaMacTable (1),
		macViaRadius (2),
		ms8021xViaRadius (3)
		}
	MAX-ACCESS read-only
	STATUS current
	DESCRIPTION
	"Indicates what caused the last  VLAN reconfiguration."
	::= { portStatusEntry 4 }

portStatusLastUpdatingMac OBJECT-TYPE   -- last_updating_mac
	SYNTAX MacAddress
	MAX-ACCESS read-only
	STATUS current
	DESCRIPTION
	"Indicates which MAC address, if any, was involve in changing the VLAN setting for this port last."
	::= { portStatusEntry 5 }

portStatusLastUpdateTime OBJECT-TYPE   -- last_update_time
	SYNTAX Counter32
	MAX-ACCESS read-only
	STATUS current
	DESCRIPTION
	"Indicates the time when the VLAN settings were last changed."
	::= { portStatusEntry 6 }


-- ********************* End of portStatusTable ***********************


-- ******************* Begin of mvrpStatusTable *************************

mvrpStatusTable	OBJECT-TYPE
	SYNTAX SEQUENCE OF MvrpStatusEntry
	MAX-ACCESS not-accessible
	STATUS current
	DESCRIPTION
		"This table lists MVRP status information."
	::= { vlan 103 }

mvrpStatusEntry	OBJECT-TYPE
	SYNTAX MvrpStatusEntry
	MAX-ACCESS not-accessible
	STATUS current
	DESCRIPTION
		""
	INDEX { mvrpStatusPortIndex }
	::= { mvrpStatusTable 1 }


	MvrpStatusEntry ::= SEQUENCE {
	mvrpStatusPortIndex INTEGER,
	mvrpStatusLastSourceMac MacAddress,
	mvrpStatusFailedRegistrations Unsigned32
	}

mvrpStatusPortIndex	OBJECT-TYPE
	SYNTAX INTEGER (0..24)
	MAX-ACCESS not-accessible
	STATUS current
	DESCRIPTION
		"Automatically generated"
	::= { mvrpStatusEntry 1 }

mvrpStatusLastSourceMac OBJECT-TYPE   -- last_source_mac
	SYNTAX MacAddress
	MAX-ACCESS read-only
	STATUS current
	DESCRIPTION
	"The Source MAC Address of the last MVRP message received on this port."
	::= { mvrpStatusEntry 2 }

mvrpStatusFailedRegistrations OBJECT-TYPE   -- failed_registrations
	SYNTAX Unsigned32
	MAX-ACCESS read-only
	STATUS current
	DESCRIPTION
	"The total number of failed MVRP registrations, for any reason, on this port."
	::= { mvrpStatusEntry 3 }


-- ********************* End of mvrpStatusTable ***********************



END
