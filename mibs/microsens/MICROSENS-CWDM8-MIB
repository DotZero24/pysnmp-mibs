MICROSENS-CWDM8-MIB --{ iso org(3) dod(6) internet(1) private(4) enterprises(1) microsens(3181) }

DEFINITIONS ::= BEGIN

IMPORTS
		DisplayString FROM SNMPv2-TC
		TRAP-TYPE FROM RFC-1215
   enterprises, OBJECT-TYPE, IpAddress, Counter, Gauge, TimeTicks
   FROM RFC1155-SMI;

-- Title:                Microsens MIB/ 8-Channel-CWDM
-- Version :             1.0
-- Date :                02.07.2002
-- By:                   Joerg Johann
-- File:                 miccwdm8.mib

microsens OBJECT IDENTIFIER ::= { enterprises 3181 }

cwdm     OBJECT IDENTIFIER ::= { microsens 6 }

eightChannelCwdm OBJECT IDENTIFIER ::= { cwdm 4 }


-- device status table

deviceTable OBJECT-TYPE
	SYNTAX	SEQUENCE OF DeviceList
	ACCESS	not-accessible
	STATUS	mandatory
	DESCRIPTION
	"This table describes the device-status of the CWDM-system."
	::= { eightChannelCwdm 1 }

deviceTableEntry OBJECT-TYPE
	SYNTAX	DeviceList
	ACCESS	not-accessible
	STATUS	mandatory
	DESCRIPTION
	"An entry in the port table."
	INDEX
	{ deviceId } ::= { deviceTable 1 }

DeviceList ::= SEQUENCE {
	deviceId			INTEGER,
	deviceArtNo			DisplayString,
	deviceSerNo			DisplayString,
	deviceDesc			DisplayString,
	deviceTemperature		INTEGER,
	deviceTempAlarmThreshold	INTEGER,
	deviceTempAlarm			INTEGER,
	deviceTempShutdown		INTEGER,
	deviceTrPowerFailureAlarm	INTEGER,
	deviceMinorAlarm		INTEGER,
	deviceMajorAlarm		INTEGER
}

deviceId OBJECT-TYPE
	SYNTAX	INTEGER
	ACCESS	read-only
	STATUS	mandatory
	DESCRIPTION
	"This entry describes the device id."
	::= { deviceTableEntry 1 }

deviceArtNo OBJECT-TYPE
	SYNTAX  DisplayString (SIZE (0..16))
	ACCESS	read-only
	STATUS	mandatory
	DESCRIPTION
	"This entry describes the article number of the device."
	::= { deviceTableEntry 2 }

deviceSerNo OBJECT-TYPE
        SYNTAX  DisplayString (SIZE (0..16))
        ACCESS  read-only
        STATUS  mandatory
        DESCRIPTION
        "This entry describes the serial number of the device."
        ::= {  deviceTableEntry 3  }

deviceDesc OBJECT-TYPE
        SYNTAX  DisplayString (SIZE (0..32))
        ACCESS  read-only
        STATUS  mandatory
        DESCRIPTION
        "This entry provides a detailed description of the device."
        ::= {  deviceTableEntry 4  }

deviceTemperature OBJECT-TYPE
	SYNTAX	INTEGER
        {
         unknown	(-255)
        }
	ACCESS	read-only
	STATUS	mandatory
	DESCRIPTION
	"This entry describes the temperature of the device in degree centigrade."
	::= { deviceTableEntry 5 }

deviceTempAlarmThreshold OBJECT-TYPE
	SYNTAX	INTEGER
        {
         unknown	(-255)
        }
	ACCESS	read-only
	STATUS	mandatory
	DESCRIPTION
	"This entry describes the current temperature-alarm threshold value of the device
         in degree centigrade."
	::= { deviceTableEntry 6 }

deviceTempAlarm OBJECT-TYPE
	SYNTAX	INTEGER
        {
         alarm		(1),
	 no-alarm	(0),
         unknown	(-255)
        }
	ACCESS	read-only
	STATUS	mandatory
	DESCRIPTION
	"This entry describes if a temperature-alarm condition has occurred or not."
	::= { deviceTableEntry 7 }

deviceTempShutdown OBJECT-TYPE
	SYNTAX	INTEGER
        {
         alarm		(1),
	 no-alarm	(0),
         unknown	(-255)
        }
	ACCESS	read-only
	STATUS	mandatory
	DESCRIPTION
	"This entry describes if a temperature-shutdown condition has occurred or not."
	::= { deviceTableEntry 8 }

deviceTrPowerFailureAlarm OBJECT-TYPE
	SYNTAX	INTEGER
        {
	 no-alarm		(0),
         alarm-channel-1-4	(1),
         alarm-channel-5-8	(2),
         alarm-channel-1-8	(3),
         unknown		(-255)
        }
	ACCESS	read-only
	STATUS	mandatory
	DESCRIPTION
	"This entry describes if a transceiver-board power-supply-alarm condition has occurred or not."
	::= { deviceTableEntry 9 }

deviceMinorAlarm OBJECT-TYPE
	SYNTAX	INTEGER
        {
         alarm		(1),
	 no-alarm	(0),
         unknown	(-255)
        }
	ACCESS	read-only
	STATUS	mandatory
	DESCRIPTION
	"This entry describes if a minor-alarm condition has occurred or not."
	::= { deviceTableEntry 10 }

deviceMajorAlarm OBJECT-TYPE
	SYNTAX	INTEGER
        {
         alarm		(1),
	 no-alarm	(0),
         unknown	(-255)
        }
	ACCESS	read-only
	STATUS	mandatory
	DESCRIPTION
	"This entry describes if a major-alarm condition has occurred or not."
	::= { deviceTableEntry 11 }



-- port information table

portTable OBJECT-TYPE
	SYNTAX	SEQUENCE OF PortList
	ACCESS	not-accessible
	STATUS	mandatory
	DESCRIPTION
	"This table describes the port-status of the CWDM-system."
	::= { eightChannelCwdm 2 }

portTableEntry OBJECT-TYPE
	SYNTAX	PortList
	ACCESS	not-accessible
	STATUS	mandatory
	DESCRIPTION
	"An entry in the port table."
	INDEX
	{ portId } ::= { portTable 1 }

PortList ::= SEQUENCE {
	portId				INTEGER,
	portChannelEnabled		INTEGER,
	portLinkThroughLocalLine	INTEGER,
	portLinkThroughLineLocal	INTEGER,
	portLocalModuleInstalled	INTEGER,
	portLineModuleInstalled		INTEGER,
	portLocalLink			INTEGER,
	portLineLink			INTEGER,
	portLocalTxFault		INTEGER,
	portLineTxFault			INTEGER,
	portLocalPowerFault		INTEGER,
	portLinePowerFault		INTEGER,
	portRateSelect			INTEGER
}

portId OBJECT-TYPE
	SYNTAX	INTEGER
	ACCESS	read-only
	STATUS	mandatory
	DESCRIPTION
	"This entry describes the port id. "
	::= { portTableEntry 1 }

portChannelEnabled OBJECT-TYPE
        SYNTAX  INTEGER
        {
         disabled           (0),
         enabled            (1),
         unknown            (-255)
        }
        ACCESS  read-only
        STATUS  mandatory
        DESCRIPTION
        "This entry describes the channel's status.
         A value of 1 indicates that the channel is enabled,
         a value of 0 indicates that the channel is not enabled."
        ::= {  portTableEntry 2  }

portLinkThroughLocalLine OBJECT-TYPE
        SYNTAX  INTEGER
        {
         disabled           (0),
         enabled            (1),
         unknown            (-255)
        }
        ACCESS  read-only
        STATUS  mandatory
        DESCRIPTION
        "This entry describes the local-line link-through-status of the port."
        ::= {  portTableEntry 3  }

portLinkThroughLineLocal OBJECT-TYPE
        SYNTAX  INTEGER
        {
         disabled           (0),
         enabled            (1),
         unknown            (-255)
        }
        ACCESS  read-only
        STATUS  mandatory
        DESCRIPTION
        "This entry describes the line-local link-through-status of the port."
        ::= {  portTableEntry 4  }

portLocalModuleInstalled OBJECT-TYPE
        SYNTAX  INTEGER
        {
         not-installed 	    (0),
         installed     	    (1),
         unknown 	    (-255)
        }
        ACCESS  read-only
        STATUS  mandatory
        DESCRIPTION
        "This entry describes if a local transceiver module is installed or not."
        ::= {  portTableEntry 5  }

portLineModuleInstalled OBJECT-TYPE
        SYNTAX  INTEGER
        {
         not-installed 	    (0),
         installed     	    (1),
         unknown 	    (-255)
        }
        ACCESS  read-only
        STATUS  mandatory
        DESCRIPTION
        "This entry describes if a line transceiver module is installed or not."
        ::= {  portTableEntry 6  }

portLocalLink OBJECT-TYPE
        SYNTAX  INTEGER
        {
         off     	    (0),
         on     	    (1),
         unknown 	    (-255)
        }
        ACCESS  read-only
        STATUS  mandatory
        DESCRIPTION
        "This entry describes the port's local link status."
        ::= {  portTableEntry 7  }

portLineLink OBJECT-TYPE
        SYNTAX  INTEGER
        {
         off    	    (0),
         on     	    (1),
         unknown 	    (-255)
        }
        ACCESS  read-only
        STATUS  mandatory
        DESCRIPTION
        "This entry describes the port's line link status."
        ::= {  portTableEntry 8  }

portLocalTxFault OBJECT-TYPE
        SYNTAX  INTEGER
        {
         no-error    	    (0),
         error     	    (1),
         unknown 	    (-255)
        }
        ACCESS  read-only
        STATUS  mandatory
        DESCRIPTION
        "This entry describes the port's local-tx-fault status."
        ::= {  portTableEntry 9  }

portLineTxFault OBJECT-TYPE
        SYNTAX  INTEGER
        {
         no-error    	    (0),
         error     	    (1),
         unknown 	    (-255)
        }
        ACCESS  read-only
        STATUS  mandatory
        DESCRIPTION
        "This entry describes the port's line-tx-fault status."
        ::= {  portTableEntry 10  }

portLocalPowerFault OBJECT-TYPE
        SYNTAX  INTEGER
        {
         no-error    	    (0),
         error     	    (1),
         unknown 	    (-255)
        }
        ACCESS  read-only
        STATUS  mandatory
        DESCRIPTION
        "This entry describes the port's local-power-fault status."
        ::= {  portTableEntry 11  }

portLinePowerFault OBJECT-TYPE
        SYNTAX  INTEGER
        {
         no-error    	    (0),
         error     	    (1),
         unknown 	    (-255)
        }
        ACCESS  read-only
        STATUS  mandatory
        DESCRIPTION
        "This entry describes the port's line-power-fault status."
        ::= {  portTableEntry 12  }

portRateSelect OBJECT-TYPE
        SYNTAX  INTEGER
        {
         reduced    	    (0),
         full     	    (1),
         unknown 	    (-255)
        }
        ACCESS  read-only
        STATUS  mandatory
        DESCRIPTION
        "This entry describes the port's local data rate.
         A value of 1 describes full data rate,
         a value of 0 describes reduced data rate."
        ::= {  portTableEntry 13  }

-- local module information table

localModuleTable OBJECT-TYPE
	SYNTAX	SEQUENCE OF LocalModuleList
	ACCESS	not-accessible
	STATUS	mandatory
	DESCRIPTION
	"This table describes the local module status of the CWDM-system."
	::= { eightChannelCwdm 3 }

localModuleTableEntry OBJECT-TYPE
	SYNTAX	LocalModuleList
	ACCESS	not-accessible
	STATUS	mandatory
	DESCRIPTION
	"An entry in the local module table."
	INDEX
	{ localModuleId } ::= { localModuleTable 1 }

LocalModuleList ::= SEQUENCE {
	localModuleId				INTEGER,
	localModuleConnector			INTEGER,
	localModuleTrCodeSonet			INTEGER,
	localModuleTrCodeGigabit  		INTEGER,
	localModuleTrCodeFbLinkLength		INTEGER,
	localModuleTrCodeFbTrTech		INTEGER,
	localModuleTrCodeFbTrMedia		INTEGER,
	localModuleTrCodeFbSpeed		INTEGER,
	localModuleBrNominal			INTEGER,
	localModuleLength9km			INTEGER,
	localModuleLength9m			INTEGER,
	localModuleLength50			INTEGER,
	localModuleLength62			INTEGER,
	localModuleLengthCopper			INTEGER,
	localModuleVendorSN			DisplayString,
	localModuleDateCode			DisplayString,
	localModuleLaserCurrent			INTEGER,
	localModuleTransmittedPower		INTEGER,
	localModuleReceivedPower		INTEGER,
	localModuleLaserTemperature		INTEGER,
	localModuleVoltage			INTEGER
}

localModuleId OBJECT-TYPE
	SYNTAX	INTEGER
	ACCESS	read-only
	STATUS	mandatory
	DESCRIPTION
	"This entry describes the local module id. "
	::= { localModuleTableEntry 1 }

localModuleConnector OBJECT-TYPE
        SYNTAX  INTEGER
        {
         unknown            (0),
         sc                 (1),
         style1-copper      (2),
         style2-copper      (3),
         bnc-tnc	    (4),
         coaxial-headers    (5),
         fiberjack          (6),
         lc                 (7),
         mt-rj              (8),
         mu                 (9),
         sg                 (10),
         opticalpigtail     (11),
         hssdc2             (32),
	 copperpigtail	    (33)
        }
        ACCESS  read-only
        STATUS  mandatory
        DESCRIPTION
        "This entry describes the connector-type of the port."
        ::= {  localModuleTableEntry 2  }

localModuleTrCodeSonet OBJECT-TYPE
        SYNTAX  INTEGER
        {
         unknown            			(0),
         oc3-multi-mode-short-reach  		(1),
         oc3-single-mode-intermediate-reach    	(2),
         oc3-single-mode-long-reach	    	(4),
         oc12-multi-mode-short-reach	    	(16),
         oc12-single-mode-intermediate-reach   	(32),
         oc12-single-mode-long-reach	   	(64),
         oc48-short-reach		   	(128),
         oc48-intermediate-reach	   	(256),
         oc48-long-reach		   	(512)
        }
        ACCESS  read-only
        STATUS  mandatory
        DESCRIPTION
        "This entry describes the SONET compliance of the transceiver."
        ::= {  localModuleTableEntry 3  }

localModuleTrCodeGigabit OBJECT-TYPE
        SYNTAX  INTEGER
        {
         unknown            			(0),
         base-1000-sx           			(1),
         base-1000-lx           			(2),
         base-1000-cx           			(4),
         base-1000-t           			(8)
        }
        ACCESS  read-only
        STATUS  mandatory
        DESCRIPTION
        "This entry describes the Gigabit Ethernet compliance of the transceiver."
        ::= {  localModuleTableEntry 4  }

localModuleTrCodeFbLinkLength OBJECT-TYPE
        SYNTAX  INTEGER
        {
         unknown            			(0),
         long-distance        			(1),
         intermediate-distance         		(2),
         short-distance           		(4)
        }
        ACCESS  read-only
        STATUS  mandatory
        DESCRIPTION
        "This entry describes the fibre channel link length of the transceiver."
        ::= {  localModuleTableEntry 5  }

localModuleTrCodeFbTrTech OBJECT-TYPE
        SYNTAX  INTEGER
        {
         unknown            			(0),
         longwave-laser-LL     			(1),
         shortwave-laser-OFC           		(2),
         shortwave-laser-no-OFC			(4),
	 electrical-intra-enclosure 		(8),
	 electrical-inter-enclosure 		(16),
         longwave-laser-LC     			(32)
        }
        ACCESS  read-only
        STATUS  mandatory
        DESCRIPTION
        "This entry describes the fibre channel transmitter technology of the transceiver."
        ::= {  localModuleTableEntry 6  }

localModuleTrCodeFbTrMedia OBJECT-TYPE
        SYNTAX  INTEGER
        {
         unknown            			(0),
         single-mode				(1),
         multi-mode-50				(4),
         multi-mode-62-5			(8),
         video-coax				(16),
         miniature-coax				(32),
         shielded-twisted-pair			(64),
         twin-axial-pair			(128)
        }
        ACCESS  read-only
        STATUS  mandatory
        DESCRIPTION
        "This entry describes the fibre channel transmission media of the transceiver."
        ::= {  localModuleTableEntry 7  }

localModuleTrCodeFbSpeed OBJECT-TYPE
        SYNTAX  INTEGER
        {
         unknown            			(0),
         speed-100MBytes-per-sec			(1),
         speed-200MBytes-per-sec			(4),
         speed-400MBytes-per-sec			(16)
        }
        ACCESS  read-only
        STATUS  mandatory
        DESCRIPTION
        "This entry describes the fibre channel speed of the transceiver."
        ::= {  localModuleTableEntry 8  }

localModuleBrNominal OBJECT-TYPE
        SYNTAX  INTEGER
        {
         unknown	(-255)
        }
        ACCESS  read-only
        STATUS  mandatory
        DESCRIPTION
        "This entry describes the nominal bit rate, specified in units of 100 Megabits per second."
        ::= {  localModuleTableEntry 9  }

localModuleLength9km OBJECT-TYPE
        SYNTAX  INTEGER
        {
         unknown	(-255)
        }
        ACCESS  read-only
        STATUS  mandatory
        DESCRIPTION
        "This entry describes the link length supported by the transceiver using single-mode fibers.
         The value is in units of kilometers. A value of 255 means that the transceiver supports a
         link length greater than 254 km. A value of zero means that the transceiver does not support
         single-mode fibers."
        ::= {  localModuleTableEntry 10  }

localModuleLength9m OBJECT-TYPE
        SYNTAX  INTEGER
        {
         unknown	(-255)
        }
        ACCESS  read-only
        STATUS  mandatory
        DESCRIPTION
        "This entry describes the link length supported by the transceiver using single-mode fibers.
         The value is in units of 100 meters. A value of 255 means that the transceiver supports a
         link length greater than 25.4 km. A value of zero means that the transceiver does not support
         single-mode fibers."
        ::= {  localModuleTableEntry 11  }

localModuleLength50 OBJECT-TYPE
        SYNTAX  INTEGER
        {
         unknown	(-255)
        }
        ACCESS  read-only
        STATUS  mandatory
        DESCRIPTION
        "This entry describes the link length supported by the transceiver using 50 micron
         multi-mode mode fibers. The value is in units of 10 meters.
         A value of 255 means that the transceiver supports a link length greater than 2.54 km.
         A value of zero means that the transceiver does not support 50 micron multi-mode fibers."
        ::= {  localModuleTableEntry 12  }

localModuleLength62 OBJECT-TYPE
        SYNTAX  INTEGER
        {
         unknown	(-255)
        }
        ACCESS  read-only
        STATUS  mandatory
        DESCRIPTION
        "This entry describes the link length supported by the transceiver using 62.5 micron
         multi-mode mode fibers. The value is in units of 10 meters.
         A value of 255 means that the transceiver supports a link length greater than 2.54 km.
         A value of zero means that the transceiver does not support 62.5 micron multi-mode fibers."
        ::= {  localModuleTableEntry 13  }

localModuleLengthCopper OBJECT-TYPE
        SYNTAX  INTEGER
        {
         unknown	(-255)
        }
        ACCESS  read-only
        STATUS  mandatory
        DESCRIPTION
        "This entry describes the link length supported by the transceiver using copper cables.
         The value is in units of 1 meter.
         A value of 255 means that the transceiver supports a link length greater than 254 m.
         A value of zero means that the transceiver does not support copper cables."
        ::= {  localModuleTableEntry 14  }

localModuleVendorSN OBJECT-TYPE
        SYNTAX  DisplayString (SIZE (0..16))
        ACCESS  read-only
        STATUS  mandatory
        DESCRIPTION
        "This entry describes the vendor's serial number of the transceiver."
        ::= {  localModuleTableEntry 15  }

localModuleDateCode OBJECT-TYPE
        SYNTAX  DisplayString (SIZE (0..8))
        ACCESS  read-only
        STATUS  mandatory
        DESCRIPTION
        "This entry describes the vendor's date code in the [yymmdd]-format."
        ::= {  localModuleTableEntry 16  }

localModuleLaserCurrent OBJECT-TYPE
        SYNTAX  INTEGER
        {
         unknown            			(-255)
        }
        ACCESS  read-only
        STATUS  optional
        DESCRIPTION
        "This entry describes the transmitter laser's bias current in milli ampere."
        ::= {  localModuleTableEntry 17  }

localModuleTransmittedPower OBJECT-TYPE
        SYNTAX  INTEGER
        {
         unknown            			(-255)
        }
        ACCESS  read-only
        STATUS  optional
        DESCRIPTION
        "This entry describes the transmitter optical output power in micro watt."
        ::= {  localModuleTableEntry 18  }

localModuleReceivedPower OBJECT-TYPE
        SYNTAX  INTEGER
        {
         unknown            			(-255)
        }
        ACCESS  read-only
        STATUS  optional
        DESCRIPTION
        "This entry describes the transmitter optical received power in micro watt."
        ::= {  localModuleTableEntry 19  }

localModuleLaserTemperature OBJECT-TYPE
        SYNTAX  INTEGER
        {
         unknown            			(-255)
        }
        ACCESS  read-only
        STATUS  optional
        DESCRIPTION
        "This entry describes the laser temperature in degree centigrade."
        ::= {  localModuleTableEntry 20  }

localModuleVoltage OBJECT-TYPE
        SYNTAX  INTEGER
        {
         unknown            			(-255)
        }
        ACCESS  read-only
        STATUS  optional
        DESCRIPTION
        "This entry describes the transceiver supply voltage in mV."
        ::= {  localModuleTableEntry 21  }

-- line module information table

lineModuleTable OBJECT-TYPE
	SYNTAX	SEQUENCE OF LineModuleList
	ACCESS	not-accessible
	STATUS	mandatory
	DESCRIPTION
	"This table describes the line module status of the CWDM-system."
	::= { eightChannelCwdm 4 }

lineModuleTableEntry OBJECT-TYPE
	SYNTAX	LineModuleList
	ACCESS	not-accessible
	STATUS	mandatory
	DESCRIPTION
	"An entry in the line module table."
	INDEX
	{ lineModuleId } ::= { lineModuleTable 1 }

LineModuleList ::= SEQUENCE {
	lineModuleId				INTEGER,
	lineModuleConnector			INTEGER,
	lineModuleTrCodeSonet			INTEGER,
	lineModuleTrCodeGigabit  		INTEGER,
	lineModuleTrCodeFbLinkLength		INTEGER,
	lineModuleTrCodeFbTrTech		INTEGER,
	lineModuleTrCodeFbTrMedia		INTEGER,
	lineModuleTrCodeFbSpeed			INTEGER,
	lineModuleBrNominal			INTEGER,
	lineModuleLength9km			INTEGER,
	lineModuleLength9m			INTEGER,
	lineModuleLength50			INTEGER,
	lineModuleLength62			INTEGER,
	lineModuleLengthCopper			INTEGER,
	lineModuleVendorSN			DisplayString,
	lineModuleDateCode			DisplayString,
	lineModuleLaserCurrent			INTEGER,
	lineModuleTransmittedPower		INTEGER,
	lineModuleReceivedPower			INTEGER,
	lineModuleLaserTemperature		INTEGER,
	lineModuleVoltage			INTEGER
}

lineModuleId OBJECT-TYPE
	SYNTAX	INTEGER
	ACCESS	read-only
	STATUS	mandatory
	DESCRIPTION
	"This entry describes the line module id. "
	::= { lineModuleTableEntry 1 }

lineModuleConnector OBJECT-TYPE
        SYNTAX  INTEGER
        {
         unknown            (0),
         sc                 (1),
         style1-copper      (2),
         style2-copper      (3),
         bnc-tnc	    (4),
         coaxial-headers    (5),
         fiberjack          (6),
         lc                 (7),
         mt-rj              (8),
         mu                 (9),
         sg                 (10),
         opticalpigtail     (11),
         hssdc2             (32),
	 copperpigtail	    (33)
        }
        ACCESS  read-only
        STATUS  mandatory
        DESCRIPTION
        "This entry describes the connector-type of the port."
        ::= {  lineModuleTableEntry 2  }

lineModuleTrCodeSonet OBJECT-TYPE
        SYNTAX  INTEGER
        {
         unknown            			(0),
         oc3-multi-mode-short-reach  		(1),
         oc3-single-mode-intermediate-reach    	(2),
         oc3-single-mode-long-reach	    	(4),
         oc12-multi-mode-short-reach	    	(16),
         oc12-single-mode-intermediate-reach   	(32),
         oc12-single-mode-long-reach	   	(64),
         oc48-short-reach		   	(128),
         oc48-intermediate-reach	   	(256),
         oc48-long-reach		   	(512)
        }
        ACCESS  read-only
        STATUS  mandatory
        DESCRIPTION
        "This entry describes the SONET compliance of the transceiver."
        ::= {  lineModuleTableEntry 3  }

lineModuleTrCodeGigabit OBJECT-TYPE
        SYNTAX  INTEGER
        {
         unknown            			(0),
         base-1000-SX           			(1),
         base-1000-LX           			(2),
         base-1000-CX           			(4),
         base-1000-T           			(8)
        }
        ACCESS  read-only
        STATUS  mandatory
        DESCRIPTION
        "This entry describes the Gigabit Ethernet compliance of the transceiver."
        ::= {  lineModuleTableEntry 4  }

lineModuleTrCodeFbLinkLength OBJECT-TYPE
        SYNTAX  INTEGER
        {
         unknown            			(0),
         long-distance        			(1),
         intermediate-distance         		(2),
         short-distance           		(4)
        }
        ACCESS  read-only
        STATUS  mandatory
        DESCRIPTION
        "This entry describes the fibre channel link length of the transceiver."
        ::= {  lineModuleTableEntry 5  }

lineModuleTrCodeFbTrTech OBJECT-TYPE
        SYNTAX  INTEGER
        {
         unknown            			(0),
         longwave-laser-LL     			(1),
         shortwave-laser-OFC           		(2),
         shortwave-laser-no-OFC			(4),
	 electrical-intra-enclosure 		(8),
	 electrical-inter-enclosure 		(16),
         longwave-laser-LC     			(32)
        }
        ACCESS  read-only
        STATUS  mandatory
        DESCRIPTION
        "This entry describes the fibre channel transmitter technology of the transceiver."
        ::= {  lineModuleTableEntry 6  }

lineModuleTrCodeFbTrMedia OBJECT-TYPE
        SYNTAX  INTEGER
        {
         unknown            			(0),
         single-mode				(1),
         multi-mode-50				(4),
         multi-mode-62-5			(8),
         video-coax				(16),
         miniature-coax				(32),
         shielded-twisted-pair			(64),
         twin-axial-pair			(128)
        }
        ACCESS  read-only
        STATUS  mandatory
        DESCRIPTION
        "This entry describes the fibre channel transmission media of the transceiver."
        ::= {  lineModuleTableEntry 7  }

lineModuleTrCodeFbSpeed OBJECT-TYPE
        SYNTAX  INTEGER
        {
         unknown            			(0),
         speed-100MBytes-per-sec			(1),
         speed-200MBytes-per-sec			(4),
         speed-400MBytes-per-sec			(16)
        }
        ACCESS  read-only
        STATUS  mandatory
        DESCRIPTION
        "This entry describes the fibre channel speed of the transceiver."
        ::= {  lineModuleTableEntry 8  }

lineModuleBrNominal OBJECT-TYPE
        SYNTAX  INTEGER
        {
         unknown	(-255)
        }
        ACCESS  read-only
        STATUS  mandatory
        DESCRIPTION
        "This entry describes the nominal bit rate, specified in units of 100 Megabits per second."
        ::= {  lineModuleTableEntry 9  }

lineModuleLength9km OBJECT-TYPE
        SYNTAX  INTEGER
        {
         unknown	(-255)
        }
        ACCESS  read-only
        STATUS  mandatory
        DESCRIPTION
        "This entry describes the link length supported by the transceiver using single-mode fibers.
         The value is in units of kilometers. A value of 255 means that the transceiver supports a
         link length greater than 254 km. A value of zero means that the transceiver does not support
         single-mode fibers."
        ::= {  lineModuleTableEntry 10  }

lineModuleLength9m OBJECT-TYPE
        SYNTAX  INTEGER
        {
         unknown	(-255)
        }
        ACCESS  read-only
        STATUS  mandatory
        DESCRIPTION
        "This entry describes the link length supported by the transceiver using single-mode fibers.
         The value is in units of 100 meters. A value of 255 means that the transceiver supports a
         link length greater than 25.4 km. A value of zero means that the transceiver does not support
         single-mode fibers."
        ::= {  lineModuleTableEntry 11  }

lineModuleLength50 OBJECT-TYPE
        SYNTAX  INTEGER
        {
         unknown	(-255)
        }
        ACCESS  read-only
        STATUS  mandatory
        DESCRIPTION
        "This entry describes the link length supported by the transceiver using 50 micron
         multi-mode mode fibers. The value is in units of 10 meters.
         A value of 255 means that the transceiver supports a link length greater than 2.54 km.
         A value of zero means that the transceiver does not support 50 micron multi-mode fibers."
        ::= {  lineModuleTableEntry 12  }

lineModuleLength62 OBJECT-TYPE
        SYNTAX  INTEGER
        {
         unknown	(-255)
        }
        ACCESS  read-only
        STATUS  mandatory
        DESCRIPTION
        "This entry describes the link length supported by the transceiver using 62.5 micron
         multi-mode mode fibers. The value is in units of 10 meters.
         A value of 255 means that the transceiver supports a link length greater than 2.54 km.
         A value of zero means that the transceiver does not support 62.5 micron multi-mode fibers."
        ::= {  lineModuleTableEntry 13  }

lineModuleLengthCopper OBJECT-TYPE
        SYNTAX  INTEGER
        {
         unknown	(-255)
        }
        ACCESS  read-only
        STATUS  mandatory
        DESCRIPTION
        "This entry describes the link length supported by the transceiver using copper cables.
         The value is in units of 1 meter.
         A value of 255 means that the transceiver supports a link length greater than 254 m.
         A value of zero means that the transceiver does not support copper cables."
        ::= {  lineModuleTableEntry 14  }

lineModuleVendorSN OBJECT-TYPE
        SYNTAX  DisplayString (SIZE (0..16))
        ACCESS  read-only
        STATUS  mandatory
        DESCRIPTION
        "This entry describes the vendor's serial number of the transceiver."
        ::= {  lineModuleTableEntry 15  }

lineModuleDateCode OBJECT-TYPE
        SYNTAX  DisplayString (SIZE (0..8))
        ACCESS  read-only
        STATUS  mandatory
        DESCRIPTION
        "This entry describes the vendor's date code in the [yymmdd]-format."
        ::= {  lineModuleTableEntry 16  }

lineModuleLaserCurrent OBJECT-TYPE
        SYNTAX  INTEGER
        {
         unknown	(-255)
        }
        ACCESS  read-only
        STATUS  mandatory
        DESCRIPTION
        "This entry describes the transmitter laser's bias current in milli ampere."
        ::= {  lineModuleTableEntry 17  }

lineModuleTransmittedPower OBJECT-TYPE
        SYNTAX  INTEGER
        {
         unknown	(-255)
        }
        ACCESS  read-only
        STATUS  mandatory
        DESCRIPTION
        "This entry describes the transmitter optical output power in micro watt."
        ::= {  lineModuleTableEntry 18  }

lineModuleReceivedPower OBJECT-TYPE
        SYNTAX  INTEGER
        {
         unknown	(-255)
        }
        ACCESS  read-only
        STATUS  mandatory
        DESCRIPTION
        "This entry describes the transmitter optical received power in micro watt."
        ::= {  lineModuleTableEntry 19  }

lineModuleLaserTemperature OBJECT-TYPE
        SYNTAX  INTEGER
        {
         unknown	(-255)
        }
        ACCESS  read-only
        STATUS  mandatory
        DESCRIPTION
        "This entry describes the laser temperature in degree centigrade."
        ::= {  lineModuleTableEntry 20  }

lineModuleVoltage OBJECT-TYPE
        SYNTAX  INTEGER
        {
         unknown	(-255)
        }
        ACCESS  read-only
        STATUS  mandatory
        DESCRIPTION
        "This entry describes the transceiver supply voltage in mV."
        ::= {  lineModuleTableEntry 21  }


-- power supply table

powerTable OBJECT-TYPE
	SYNTAX	SEQUENCE OF PowerList
	ACCESS	not-accessible
	STATUS	mandatory
	DESCRIPTION
	"This table describes the power-supply-status of the CWDM-system."
	::= { eightChannelCwdm 5 }

powerTableEntry OBJECT-TYPE
	SYNTAX	PowerList
	ACCESS	not-accessible
	STATUS	mandatory
	DESCRIPTION
	"An entry in the power-supply table."
	INDEX
	{ powerId } ::= { powerTable 1 }

PowerList ::= SEQUENCE {
	powerId			INTEGER,
	powerArtNo		DisplayString,
	powerSerNo		DisplayString,
	powerDesc		DisplayString,
	powerTemperature	INTEGER,
	powerStatus		INTEGER,
	powerSuppliedPower	INTEGER,
	powerLoad		INTEGER,
	powerFanStatus		INTEGER
}

powerId OBJECT-TYPE
	SYNTAX	INTEGER
	ACCESS	read-only
	STATUS	mandatory
	DESCRIPTION
	"This entry describes the power-supply module id. "
	::= { powerTableEntry 1 }

powerArtNo OBJECT-TYPE
        SYNTAX  DisplayString (SIZE (0..16))
        ACCESS  read-only
        STATUS  mandatory
        DESCRIPTION
        "This entry describes the article number of the power-supply module."
        ::= {  powerTableEntry 2  }

powerSerNo OBJECT-TYPE
        SYNTAX  DisplayString (SIZE (0..16))
        ACCESS  read-only
        STATUS  mandatory
        DESCRIPTION
        "This entry describes the serial number of the power-supply module."
        ::= {  powerTableEntry 3  }

powerDesc OBJECT-TYPE
        SYNTAX  DisplayString (SIZE (0..32))
        ACCESS  read-only
        STATUS  mandatory
        DESCRIPTION
        "This entry provides a detailed description of the power-supply module."
        ::= {  powerTableEntry 4  }

powerTemperature OBJECT-TYPE
	SYNTAX	INTEGER
        {
         unknown	(-255)
        }
	ACCESS	read-only
	STATUS	mandatory
	DESCRIPTION
	"This entry describes the temperature of the power-supply module."
	::= { powerTableEntry 5 }

powerStatus OBJECT-TYPE
	SYNTAX	INTEGER
        {
         unknown	(-255),
	 not-active	(0),
         active		(1)
        }
	ACCESS	read-only
	STATUS	mandatory
	DESCRIPTION
	"This entry describes the operational status of the power-supply module."
	::= { powerTableEntry 6 }

powerSuppliedPower OBJECT-TYPE
	SYNTAX	INTEGER
        {
         unknown	(-255)
        }
	ACCESS	read-only
	STATUS	mandatory
	DESCRIPTION
        "This entry describes the power output of the power-supply module in watt."
	::= { powerTableEntry 7 }

powerLoad OBJECT-TYPE
	SYNTAX	INTEGER
        {
         unknown	(-255)
        }
	ACCESS	read-only
	STATUS	mandatory
	DESCRIPTION
        "This entry describes the load level of the power-supply module in percent."
	::= { powerTableEntry 8 }

powerFanStatus OBJECT-TYPE
	SYNTAX	INTEGER
        {
         unknown	(-255),
	 not-active	(0),
         active		(1)
        }
	ACCESS	read-only
	STATUS	mandatory
	DESCRIPTION
	"This entry describes the fan status of the power-supply module."
	::= { powerTableEntry 9 }


-- line interface table

lineIfTable OBJECT-TYPE
	SYNTAX	SEQUENCE OF LineIfList
	ACCESS	not-accessible
	STATUS	mandatory
	DESCRIPTION
	"This table describes the line-interface status of the CWDM-system."
	::= { eightChannelCwdm 6 }

lineIfTableEntry OBJECT-TYPE
	SYNTAX	LineIfList
	ACCESS	not-accessible
	STATUS	mandatory
	DESCRIPTION
	"An entry in the line-interface table."
	INDEX
	{ lineIfId } ::= { lineIfTable 1 }

LineIfList ::= SEQUENCE {
	lineIfId			INTEGER,
	lineIfArtNo			DisplayString,
	lineIfSerNo			DisplayString,
	lineIfWestLinkStatus		INTEGER,
       	lineIfEastLinkStatus		INTEGER,
	lineIfWestChannelStatus		INTEGER,
	lineIfEastChannelStatus		INTEGER,
	lineIfWestLinkRcvPower		INTEGER,
	lineIfEastLinkRcvPower		INTEGER
}

lineIfId OBJECT-TYPE
	SYNTAX	INTEGER
	ACCESS	read-only
	STATUS	mandatory
	DESCRIPTION
	"This entry describes the power-supply module id. "
	::= { lineIfTableEntry 1 }

lineIfArtNo OBJECT-TYPE
        SYNTAX  DisplayString (SIZE (0..16))
        ACCESS  read-only
        STATUS  mandatory
        DESCRIPTION
        "This entry describes the article number of the power-supply module."
        ::= {  lineIfTableEntry 2  }

lineIfSerNo OBJECT-TYPE
        SYNTAX  DisplayString (SIZE (0..16))
        ACCESS  read-only
        STATUS  mandatory
        DESCRIPTION
        "This entry describes the serial number of the power-supply module."
        ::= {  lineIfTableEntry 3  }

lineIfWestLinkStatus OBJECT-TYPE
	SYNTAX	INTEGER
        {
         unknown	(-255),
         off		(0),
         on		(1)
        }
	ACCESS	read-only
	STATUS	optional
	DESCRIPTION
	"This entry describes the west-link status of the interface module."
	::= { lineIfTableEntry 4 }

lineIfEastLinkStatus OBJECT-TYPE
	SYNTAX	INTEGER
        {
         unknown	(-255),
         off		(0),
         on		(1)
        }
	ACCESS	read-only
	STATUS	optional
	DESCRIPTION
	"This entry describes the east-link status of the interface module."
	::= { lineIfTableEntry 5 }

lineIfWestChannelStatus OBJECT-TYPE
	SYNTAX	INTEGER
        {
         unknown	(-255),
         not-in-use	(0),
         in-use		(1)
        }
	ACCESS	read-only
	STATUS	optional
	DESCRIPTION
	"This entry describes the west-channel status of the interface module."
	::= { lineIfTableEntry 6 }

lineIfEastChannelStatus OBJECT-TYPE
	SYNTAX	INTEGER
        {
         unknown	(-255),
         not-in-use	(0),
         in-use		(1)
        }
	ACCESS	read-only
	STATUS	optional
	DESCRIPTION
	"This entry describes the east-channel status of the interface module."
	::= { lineIfTableEntry 7 }

lineIfWestLinkRcvPower OBJECT-TYPE
	SYNTAX	INTEGER
        {
         unknown	(-255)
        }
	ACCESS	read-only
	STATUS	optional
	DESCRIPTION
	"This entry describes the west-link receive power of the interface module in micro watts."
	::= { lineIfTableEntry 8 }

lineIfEastLinkRcvPower OBJECT-TYPE
	SYNTAX	INTEGER
        {
         unknown	(-255)
        }
	ACCESS	read-only
	STATUS	optional
	DESCRIPTION
	"This entry describes the east-link receive power of the interface module in micro watts."
	::= { lineIfTableEntry 9 }


-- passive optical module table

passiveTable OBJECT-TYPE
	SYNTAX	SEQUENCE OF PassiveList
	ACCESS	not-accessible
	STATUS	mandatory
	DESCRIPTION
	"This table describes the passive optical module status of the CWDM-system."
	::= { eightChannelCwdm 7 }

passiveTableEntry OBJECT-TYPE
	SYNTAX	PassiveList
	ACCESS	not-accessible
	STATUS	mandatory
	DESCRIPTION
	"An entry in the passive table."
	INDEX
	{ passiveId } ::= { passiveTable 1 }

PassiveList ::= SEQUENCE {
	passiveId			INTEGER,
	passiveArtNo			DisplayString,
	passiveSerNo			DisplayString
}

passiveId OBJECT-TYPE
	SYNTAX	INTEGER
	ACCESS	read-only
	STATUS	mandatory
	DESCRIPTION
	"This entry describes the passive optical module id. "
	::= { passiveTableEntry 1 }

passiveArtNo OBJECT-TYPE
        SYNTAX  DisplayString (SIZE (0..16))
        ACCESS  read-only
        STATUS  mandatory
        DESCRIPTION
        "This entry describes the article number of the power-supply module."
        ::= {  passiveTableEntry 2  }

passiveSerNo OBJECT-TYPE
        SYNTAX  DisplayString (SIZE (0..16))
        ACCESS  read-only
        STATUS  mandatory
        DESCRIPTION
        "This entry describes the serial number of the power-supply module."
        ::= {  passiveTableEntry 3  }


-- number of channel information :

channelCount OBJECT-TYPE
        SYNTAX  INTEGER
        ACCESS  read-only
        STATUS  mandatory
        DESCRIPTION
        "This entry describes the number of channels in the CWDM-system."
        ::= {  eightChannelCwdm 100  }


-- Trap Definitions :

minorAlarmRelayTrap TRAP-TYPE
	ENTERPRISE	eightChannelCwdm
	VARIABLES	{ deviceMinorAlarm }
        DESCRIPTION
        "Trap indicating a change in the minor alarm relay status."
        ::= 0

majorAlarmRelayTrap TRAP-TYPE
	ENTERPRISE	eightChannelCwdm
	VARIABLES	{ deviceMajorAlarm }
        DESCRIPTION
        "Trap indicating a change in the major alarm relay status."
        ::= 1

devicePowerSupplyTrap TRAP-TYPE
	ENTERPRISE	eightChannelCwdm
	VARIABLES	{ powerId, powerStatus }
        DESCRIPTION
        "Trap indicating a change in the power-supply redundancy status."
        ::= 2

deviceTemperatureAlarmTrap TRAP-TYPE
	ENTERPRISE	eightChannelCwdm
	VARIABLES	{ deviceTemperature,deviceTempAlarm }
        DESCRIPTION
        "Trap indicating a device temperature alarm event has occurred."
        ::= 3

deviceTemperatureShutdownTrap TRAP-TYPE
	ENTERPRISE	eightChannelCwdm
	VARIABLES	{ deviceTemperature,deviceTempShutdown }
        DESCRIPTION
        "Trap indicating a device temperature shutdown event has occurred."
        ::= 4

fanAlarmTrap TRAP-TYPE
	ENTERPRISE	eightChannelCwdm
	VARIABLES	{ powerId, powerFanStatus }
        DESCRIPTION
        "Trap indicating a fan alarm in a power supply module."
        ::= 5

portLocalLinkChangeTrap TRAP-TYPE
	ENTERPRISE	eightChannelCwdm
	VARIABLES	{ portId, portLocalLink }
        DESCRIPTION
        "Trap indicating that a port's local link status has changed.
         The port is identified by the portId variable."
        ::= 6

portLineLinkChangeTrap TRAP-TYPE
	ENTERPRISE	eightChannelCwdm
	VARIABLES	{ portId, portLineLink }
        DESCRIPTION
        "Trap indicating that a port's line link status has changed.
         The port is identified by the portId variable."
        ::= 7

END
