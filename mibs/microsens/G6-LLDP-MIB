G6-LLDP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

protocol MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 2 }

lldp  OBJECT IDENTIFIER ::= { protocol 43 }



-- *************************** CONFIGURATION SECTION ********************************


-- ******************* Begin of configTable *************************

configTable	OBJECT-TYPE
	SYNTAX SEQUENCE OF ConfigEntry
	MAX-ACCESS not-accessible
	STATUS current
	DESCRIPTION
		"General settings for LLDP (link layer discovery protocol). This protocol is used to identify the directly attached neighbor devices. This is useful to build a network topolgy. It is also used to identify voip telephones and to set them up."
	::= { lldp 1 }

configEntry	OBJECT-TYPE
	SYNTAX ConfigEntry
	MAX-ACCESS not-accessible
	STATUS current
	DESCRIPTION
		""
	INDEX { configIndex }
	::= { configTable 1 }


	ConfigEntry ::= SEQUENCE {
	configIndex INTEGER,
	configEnableLldp INTEGER ,
	configEnableCdp INTEGER ,
	configLldpEnabledPorts INTEGER,
	configReceiveOnly INTEGER ,
	configForwardToLink INTEGER ,
	configAdvertizedMedClass INTEGER ,
	configDisableMedInventory INTEGER ,
	configDisableVoiceVlanTlv INTEGER ,
	configCdpVersion INTEGER ,
	configVoiceVlanPrio Integer32 ,
	configVoiceVlanSignalPrio Integer32 ,
	configVoiceDscp Integer32 ,
	configSignalingDscp Integer32 ,
	configTimeToLive Integer32 ,
	configTxDelay Integer32 ,
	configMsgTxInterval Integer32 ,
	configForceLldpTransmission INTEGER ,
	configLldpResponsePreferred INTEGER
	}

configIndex	OBJECT-TYPE
	SYNTAX INTEGER (0)
	MAX-ACCESS not-accessible
	STATUS current
	DESCRIPTION
		"Automatically generated"
	::= { configEntry 1 }

configEnableLldp OBJECT-TYPE   -- enable_lldp
	SYNTAX INTEGER {  disabled(0), enabled(1) }
	MAX-ACCESS read-write
	STATUS current
	DESCRIPTION
	"This generally enables the link layer discovery protocol (LLDP)."
	::= { configEntry 2 }

configEnableCdp OBJECT-TYPE   -- enable_cdp
	SYNTAX INTEGER {  disabled(0), enabled(1) }
	MAX-ACCESS read-write
	STATUS current
	DESCRIPTION
	"This enables Cisco discovery protocol. Check cdp_version parameter to select CDP version."
	::= { configEntry 3 }

configLldpEnabledPorts OBJECT-TYPE   -- lldp_enabled_ports
	SYNTAX INTEGER
	MAX-ACCESS read-write
	STATUS current
	DESCRIPTION
	"This parameter permits port selective LLDP enabling. When empty all ports are enabled! Syntax: slot/port, slot/port or use hex value for quick setup. Example = 0x7 defines ports 1-3."
	::= { configEntry 4 }

configReceiveOnly OBJECT-TYPE   -- receive_only
	SYNTAX INTEGER {  disabled(0), enabled(1) }
	MAX-ACCESS read-write
	STATUS current
	DESCRIPTION
	"This enables receive only mode. LLDP will not send any frames. It will only listen to its neighbours.   "
	::= { configEntry 5 }

configForwardToLink OBJECT-TYPE   -- forward_to_link
	SYNTAX INTEGER {  disabled(0), enabled(1) }
	MAX-ACCESS read-write
	STATUS current
	DESCRIPTION
	"This mode forwards all received LLDP packets to the uplink port. In combination with receive_only option enabled this unit keeps quiet and all LLDP handling should be taken care off by the upstream device."
	::= { configEntry 6 }

configAdvertizedMedClass OBJECT-TYPE   -- advertized_med_class
	SYNTAX INTEGER
		{
		disableMed (0),
		genericEndpoint (1),
		mediaEndpoint (2),
		communicationEndpoint (3),
		networkDevice (4)
		}
	MAX-ACCESS read-write
	STATUS current
	DESCRIPTION
	"Enables emission of LLDP-MED frames of a certain class."
	::= { configEntry 7 }

configDisableMedInventory OBJECT-TYPE   -- disable_med_inventory
	SYNTAX INTEGER {  disabled(0), enabled(1) }
	MAX-ACCESS read-write
	STATUS current
	DESCRIPTION
	"Disable LLDP-MED inventory TLV transmission."
	::= { configEntry 8 }

configDisableVoiceVlanTlv OBJECT-TYPE   -- disable_voice_vlan_tlv
	SYNTAX INTEGER {  disabled(0), enabled(1) }
	MAX-ACCESS read-write
	STATUS current
	DESCRIPTION
	"Disable voice vlan indication TLV transmission."
	::= { configEntry 9 }

configCdpVersion OBJECT-TYPE   -- cdp_version
	SYNTAX INTEGER
		{
		v1AndV2 (0),
		v1 (1),
		v2 (2)
		}
	MAX-ACCESS read-write
	STATUS current
	DESCRIPTION
	"Determines which version CDP messages are used."
	::= { configEntry 10 }

configVoiceVlanPrio OBJECT-TYPE   -- voice_vlan_prio
	SYNTAX Integer32 (0..255)
	MAX-ACCESS read-write
	STATUS current
	DESCRIPTION
	"Layer 2 priority used for voice vlan in voip application."
	::= { configEntry 11 }

configVoiceVlanSignalPrio OBJECT-TYPE   -- voice_vlan_signal_prio
	SYNTAX Integer32 (0..255)
	MAX-ACCESS read-write
	STATUS current
	DESCRIPTION
	"Layer 2 priority used for voice vlan signaling in voip application."
	::= { configEntry 12 }

configVoiceDscp OBJECT-TYPE   -- voice_dscp
	SYNTAX Integer32 (0..255)
	MAX-ACCESS read-write
	STATUS current
	DESCRIPTION
	"DiffServ codepoint (0-63) for voip application"
	::= { configEntry 13 }

configSignalingDscp OBJECT-TYPE   -- signaling_dscp
	SYNTAX Integer32 (0..255)
	MAX-ACCESS read-write
	STATUS current
	DESCRIPTION
	"DiffServ codepoint (0-63) for voip signaling"
	::= { configEntry 14 }

configTimeToLive OBJECT-TYPE   -- time_to_live
	SYNTAX Integer32 (0..255)
	MAX-ACCESS read-write
	STATUS current
	DESCRIPTION
	"The time to live value defines the time for which the lldp transmitted details are valid and can be displayed in the status."
	::= { configEntry 15 }

configTxDelay OBJECT-TYPE   -- tx_delay
	SYNTAX Integer32 (0..255)
	MAX-ACCESS read-write
	STATUS current
	DESCRIPTION
	"Transmission delay in seconds between successive LLDP frame transmissions initiated by changes in the LLDP local configuration."
	::= { configEntry 16 }

configMsgTxInterval OBJECT-TYPE   -- msg_tx_interval
	SYNTAX Integer32 (0..65535)
	MAX-ACCESS read-write
	STATUS current
	DESCRIPTION
	"The interval at which LLDP frames are transmitted on behalf of this LLDP agent."
	::= { configEntry 17 }

configForceLldpTransmission OBJECT-TYPE   -- force_lldp_transmission
	SYNTAX INTEGER {  disabled(0), enabled(1) }
	MAX-ACCESS read-write
	STATUS current
	DESCRIPTION
	"Force to send LLDP packets even when there is no LLDP peer detected."
	::= { configEntry 18 }

configLldpResponsePreferred OBJECT-TYPE   -- lldp_response_preferred
	SYNTAX INTEGER {  disabled(0), enabled(1) }
	MAX-ACCESS read-write
	STATUS current
	DESCRIPTION
	"When enabled LLDP responses takes precende over CDP protocol responses."
	::= { configEntry 19 }


-- ********************* End of configTable ***********************


-- ******************* Begin of localCoordinatesTable *************************

localCoordinatesTable	OBJECT-TYPE
	SYNTAX SEQUENCE OF LocalCoordinatesEntry
	MAX-ACCESS not-accessible
	STATUS current
	DESCRIPTION
		"Detailed GPS information about the pysical location of this device may be entered here."
	::= { lldp 2 }

localCoordinatesEntry	OBJECT-TYPE
	SYNTAX LocalCoordinatesEntry
	MAX-ACCESS not-accessible
	STATUS current
	DESCRIPTION
		""
	INDEX { localCoordinatesIndex }
	::= { localCoordinatesTable 1 }


	LocalCoordinatesEntry ::= SEQUENCE {
	localCoordinatesIndex INTEGER,
	localCoordinatesLatitude DisplayString,
	localCoordinatesLatResolution Integer32 ,
	localCoordinatesLongitude DisplayString,
	localCoordinatesLongResolution Integer32 ,
	localCoordinatesAltitude DisplayString,
	localCoordinatesAltResolution Integer32 ,
	localCoordinatesAltType INTEGER ,
	localCoordinatesDatum DisplayString
	}

localCoordinatesIndex	OBJECT-TYPE
	SYNTAX INTEGER (0)
	MAX-ACCESS not-accessible
	STATUS current
	DESCRIPTION
		"Automatically generated"
	::= { localCoordinatesEntry 1 }

localCoordinatesLatitude OBJECT-TYPE   -- latitude
	SYNTAX DisplayString
	MAX-ACCESS read-write
	STATUS current
	DESCRIPTION
	"A value in degrees such as: 50,123"
	::= { localCoordinatesEntry 2 }

localCoordinatesLatResolution OBJECT-TYPE   -- lat_resolution
	SYNTAX Integer32 (0..255)
	MAX-ACCESS read-write
	STATUS current
	DESCRIPTION
	"A value in bits. Higher value is more accurate."
	::= { localCoordinatesEntry 3 }

localCoordinatesLongitude OBJECT-TYPE   -- longitude
	SYNTAX DisplayString
	MAX-ACCESS read-write
	STATUS current
	DESCRIPTION
	"A value in degrees such as: 50,123"
	::= { localCoordinatesEntry 4 }

localCoordinatesLongResolution OBJECT-TYPE   -- long_resolution
	SYNTAX Integer32 (0..255)
	MAX-ACCESS read-write
	STATUS current
	DESCRIPTION
	"A value in bits. Higher value is more accurate."
	::= { localCoordinatesEntry 5 }

localCoordinatesAltitude OBJECT-TYPE   -- altitude
	SYNTAX DisplayString
	MAX-ACCESS read-write
	STATUS current
	DESCRIPTION
	"A value in meters."
	::= { localCoordinatesEntry 6 }

localCoordinatesAltResolution OBJECT-TYPE   -- alt_resolution
	SYNTAX Integer32 (0..255)
	MAX-ACCESS read-write
	STATUS current
	DESCRIPTION
	"A value in bits. Higher value is more accurate."
	::= { localCoordinatesEntry 7 }

localCoordinatesAltType OBJECT-TYPE   -- alt_type
	SYNTAX INTEGER
		{
		meter (0),
		floor (1)
		}
	MAX-ACCESS read-write
	STATUS current
	DESCRIPTION
	"Defines in which way the altitude is interpreted."
	::= { localCoordinatesEntry 8 }

localCoordinatesDatum OBJECT-TYPE   -- datum
	SYNTAX DisplayString
	MAX-ACCESS read-write
	STATUS current
	DESCRIPTION
	"Name of the map the given coordinates are based upon."
	::= { localCoordinatesEntry 9 }


-- ********************* End of localCoordinatesTable ***********************


-- ******************* Begin of localCivicLocationTable *************************

localCivicLocationTable	OBJECT-TYPE
	SYNTAX SEQUENCE OF LocalCivicLocationEntry
	MAX-ACCESS not-accessible
	STATUS current
	DESCRIPTION
		"Detailed address information about the physical location of this device may be entered here. These data are forwarded using the LLDP-MED protocol. "
	::= { lldp 3 }

localCivicLocationEntry	OBJECT-TYPE
	SYNTAX LocalCivicLocationEntry
	MAX-ACCESS not-accessible
	STATUS current
	DESCRIPTION
		""
	INDEX { localCivicLocationIndex }
	::= { localCivicLocationTable 1 }


	LocalCivicLocationEntry ::= SEQUENCE {
	localCivicLocationIndex INTEGER,
	localCivicLocationCountryCode DisplayString,
	localCivicLocationLanguage DisplayString,
	localCivicLocationNationalSubdivision DisplayString,
	localCivicLocationCounty DisplayString,
	localCivicLocationTown DisplayString,
	localCivicLocationDistrict DisplayString,
	localCivicLocationBlock DisplayString,
	localCivicLocationStreet DisplayString,
	localCivicLocationLeadingStreetDirection DisplayString,
	localCivicLocationTrailingStreetSuffix DisplayString,
	localCivicLocationStreetSuffix DisplayString,
	localCivicLocationHouseNumber DisplayString,
	localCivicLocationHouseNumberSuffix DisplayString,
	localCivicLocationLandmark DisplayString,
	localCivicLocationAdditionalInfo DisplayString,
	localCivicLocationName DisplayString,
	localCivicLocationZipCode DisplayString,
	localCivicLocationBuilding DisplayString,
	localCivicLocationUnit DisplayString,
	localCivicLocationFloor DisplayString,
	localCivicLocationRoom DisplayString,
	localCivicLocationPlaceType DisplayString,
	localCivicLocationScript DisplayString,
	localCivicLocationElinNumber DisplayString
	}

localCivicLocationIndex	OBJECT-TYPE
	SYNTAX INTEGER (0)
	MAX-ACCESS not-accessible
	STATUS current
	DESCRIPTION
		"Automatically generated"
	::= { localCivicLocationEntry 1 }

localCivicLocationCountryCode OBJECT-TYPE   -- country_code
	SYNTAX DisplayString
	MAX-ACCESS read-write
	STATUS current
	DESCRIPTION
	"Two-letter ISO 3166 country code in capital ASCII letters. Use DE for Germany, etc."
	::= { localCivicLocationEntry 2 }

localCivicLocationLanguage OBJECT-TYPE   -- language
	SYNTAX DisplayString
	MAX-ACCESS read-write
	STATUS current
	DESCRIPTION
	"ISO 639 language code used for presenting the address information."
	::= { localCivicLocationEntry 3 }

localCivicLocationNationalSubdivision OBJECT-TYPE   -- national_subdivision
	SYNTAX DisplayString
	MAX-ACCESS read-write
	STATUS current
	DESCRIPTION
	"National subdivision: state, canton, region, province, or prefecture. Example: Hessen"
	::= { localCivicLocationEntry 4 }

localCivicLocationCounty OBJECT-TYPE   -- county
	SYNTAX DisplayString
	MAX-ACCESS read-write
	STATUS current
	DESCRIPTION
	"County / parish / district. Example: Landkreis Darmstadt"
	::= { localCivicLocationEntry 5 }

localCivicLocationTown OBJECT-TYPE   -- town
	SYNTAX DisplayString
	MAX-ACCESS read-write
	STATUS current
	DESCRIPTION
	"City / township. Example: Frankfurt"
	::= { localCivicLocationEntry 6 }

localCivicLocationDistrict OBJECT-TYPE   -- district
	SYNTAX DisplayString
	MAX-ACCESS read-write
	STATUS current
	DESCRIPTION
	"City district / division / borough / ward."
	::= { localCivicLocationEntry 7 }

localCivicLocationBlock OBJECT-TYPE   -- block
	SYNTAX DisplayString
	MAX-ACCESS read-write
	STATUS current
	DESCRIPTION
	"Neighborhood / block."
	::= { localCivicLocationEntry 8 }

localCivicLocationStreet OBJECT-TYPE   -- street
	SYNTAX DisplayString
	MAX-ACCESS read-write
	STATUS current
	DESCRIPTION
	"Name of the street without house number."
	::= { localCivicLocationEntry 9 }

localCivicLocationLeadingStreetDirection OBJECT-TYPE   -- leading_street_direction
	SYNTAX DisplayString
	MAX-ACCESS read-write
	STATUS current
	DESCRIPTION
	"Use any of these values or leave blank: N,E,W,S,NE,NW,SE,SW."
	::= { localCivicLocationEntry 10 }

localCivicLocationTrailingStreetSuffix OBJECT-TYPE   -- trailing_street_suffix
	SYNTAX DisplayString
	MAX-ACCESS read-write
	STATUS current
	DESCRIPTION
	"Use any of these values or leave blank: N,E,W,S,NE,NW,SE,SW."
	::= { localCivicLocationEntry 11 }

localCivicLocationStreetSuffix OBJECT-TYPE   -- street_suffix
	SYNTAX DisplayString
	MAX-ACCESS read-write
	STATUS current
	DESCRIPTION
	"Street suffix such as place or avenue."
	::= { localCivicLocationEntry 12 }

localCivicLocationHouseNumber OBJECT-TYPE   -- house_number
	SYNTAX DisplayString
	MAX-ACCESS read-write
	STATUS current
	DESCRIPTION
	"House number without a possible suffix."
	::= { localCivicLocationEntry 13 }

localCivicLocationHouseNumberSuffix OBJECT-TYPE   -- house_number_suffix
	SYNTAX DisplayString
	MAX-ACCESS read-write
	STATUS current
	DESCRIPTION
	"A modifier to the house number. It does not include parts of the house number. Example: a"
	::= { localCivicLocationEntry 14 }

localCivicLocationLandmark OBJECT-TYPE   -- landmark
	SYNTAX DisplayString
	MAX-ACCESS read-write
	STATUS current
	DESCRIPTION
	"Landmark or vanity address for easier reference. Example: Airport Frankfurt"
	::= { localCivicLocationEntry 15 }

localCivicLocationAdditionalInfo OBJECT-TYPE   -- additional_info
	SYNTAX DisplayString
	MAX-ACCESS read-write
	STATUS current
	DESCRIPTION
	"Additional location information without specified format."
	::= { localCivicLocationEntry 16 }

localCivicLocationName OBJECT-TYPE   -- name
	SYNTAX DisplayString
	MAX-ACCESS read-write
	STATUS current
	DESCRIPTION
	"Identifies the person or organization associated with the address. Example: Sunshine Airline Office"
	::= { localCivicLocationEntry 17 }

localCivicLocationZipCode OBJECT-TYPE   -- zip_code
	SYNTAX DisplayString
	MAX-ACCESS read-write
	STATUS current
	DESCRIPTION
	"Postal zip code for the address."
	::= { localCivicLocationEntry 18 }

localCivicLocationBuilding OBJECT-TYPE   -- building
	SYNTAX DisplayString
	MAX-ACCESS read-write
	STATUS current
	DESCRIPTION
	"The name of the building if this exists. Example: Terminal Building East"
	::= { localCivicLocationEntry 19 }

localCivicLocationUnit OBJECT-TYPE   -- unit
	SYNTAX DisplayString
	MAX-ACCESS read-write
	STATUS current
	DESCRIPTION
	"Unit / appartment / suite."
	::= { localCivicLocationEntry 20 }

localCivicLocationFloor OBJECT-TYPE   -- floor
	SYNTAX DisplayString
	MAX-ACCESS read-write
	STATUS current
	DESCRIPTION
	"Floor value. Example: 1 for first floor"
	::= { localCivicLocationEntry 21 }

localCivicLocationRoom OBJECT-TYPE   -- room
	SYNTAX DisplayString
	MAX-ACCESS read-write
	STATUS current
	DESCRIPTION
	"Room number or name."
	::= { localCivicLocationEntry 22 }

localCivicLocationPlaceType OBJECT-TYPE   -- place_type
	SYNTAX DisplayString
	MAX-ACCESS read-write
	STATUS current
	DESCRIPTION
	"Place type. Example: Office"
	::= { localCivicLocationEntry 23 }

localCivicLocationScript OBJECT-TYPE   -- script
	SYNTAX DisplayString
	MAX-ACCESS read-write
	STATUS current
	DESCRIPTION
	"The script (from ISO 15924 [14]) used to encode the address information. Default: Latn"
	::= { localCivicLocationEntry 24 }

localCivicLocationElinNumber OBJECT-TYPE   -- elin_number
	SYNTAX DisplayString
	MAX-ACCESS read-write
	STATUS current
	DESCRIPTION
	"Emergency Call Services (ECS) Emergency Location Identification Number (ELIN)."
	::= { localCivicLocationEntry 25 }


-- ********************* End of localCivicLocationTable ***********************



-- ****************************** STATUS SECTION ********************************


-- ******************* Begin of receivedOverviewTable *************************

receivedOverviewTable	OBJECT-TYPE
	SYNTAX SEQUENCE OF ReceivedOverviewEntry
	MAX-ACCESS not-accessible
	STATUS current
	DESCRIPTION
		""
	::= { lldp 100 }

receivedOverviewEntry	OBJECT-TYPE
	SYNTAX ReceivedOverviewEntry
	MAX-ACCESS not-accessible
	STATUS current
	DESCRIPTION
		""
	INDEX { receivedOverviewPortIndex }
	::= { receivedOverviewTable 1 }


	ReceivedOverviewEntry ::= SEQUENCE {
	receivedOverviewPortIndex INTEGER,
	receivedOverviewSysName DisplayString,
	receivedOverviewSysDesc DisplayString,
	receivedOverviewChassisIdSubtype INTEGER ,
	receivedOverviewChassisId DisplayString,
	receivedOverviewMgmtIp DisplayString,
	receivedOverviewMgmtOid DisplayString,
	receivedOverviewCapabilities BITS ,
	receivedOverviewCapabilitiesEnabled BITS ,
	receivedOverviewMedCapabilities BITS ,
	receivedOverviewPortIdSubtype INTEGER ,
	receivedOverviewPortIdentification DisplayString,
	receivedOverviewPortDescription DisplayString,
	receivedOverviewPortVlan Integer32
	}

receivedOverviewPortIndex	OBJECT-TYPE
	SYNTAX INTEGER (0..31)
	MAX-ACCESS not-accessible
	STATUS current
	DESCRIPTION
		"Automatically generated"
	::= { receivedOverviewEntry 1 }

receivedOverviewSysName OBJECT-TYPE   -- sys_name
	SYNTAX DisplayString
	MAX-ACCESS read-only
	STATUS current
	DESCRIPTION
	"System name."
	::= { receivedOverviewEntry 2 }

receivedOverviewSysDesc OBJECT-TYPE   -- sys_desc
	SYNTAX DisplayString
	MAX-ACCESS read-only
	STATUS current
	DESCRIPTION
	"System description."
	::= { receivedOverviewEntry 3 }

receivedOverviewChassisIdSubtype OBJECT-TYPE   -- chassis_id_subtype
	SYNTAX INTEGER
		{
		unknown (0),
		chassisComponent (1),
		interfaceAlias (2),
		portComponent (3),
		macAddress (4),
		networkAddress (5),
		interfaceName (6),
		local (7)
		}
	MAX-ACCESS read-only
	STATUS current
	DESCRIPTION
	"Type of chassis id."
	::= { receivedOverviewEntry 4 }

receivedOverviewChassisId OBJECT-TYPE   -- chassis_id
	SYNTAX DisplayString
	MAX-ACCESS read-only
	STATUS current
	DESCRIPTION
	"Chassis id of received frame."
	::= { receivedOverviewEntry 5 }

receivedOverviewMgmtIp OBJECT-TYPE   -- mgmt_ip
	SYNTAX DisplayString
	MAX-ACCESS read-only
	STATUS current
	DESCRIPTION
	"Management IP address."
	::= { receivedOverviewEntry 6 }

receivedOverviewMgmtOid OBJECT-TYPE   -- mgmt_oid
	SYNTAX DisplayString
	MAX-ACCESS read-only
	STATUS current
	DESCRIPTION
	"Management start OID for SNMP access."
	::= { receivedOverviewEntry 7 }

receivedOverviewCapabilities OBJECT-TYPE   -- capabilities
	SYNTAX BITS
		{
		other (0),
		repeater (1),
		bridge (2),
		wlan (3),
		router (4),
		telephone (5),
		docsis (6),
		station (7)
		}
	MAX-ACCESS read-only
	STATUS current
	DESCRIPTION
	"LLDP capabilities supported."
	::= { receivedOverviewEntry 8 }

receivedOverviewCapabilitiesEnabled OBJECT-TYPE   -- capabilities_enabled
	SYNTAX BITS
		{
		other (0),
		repeater (1),
		bridge (2),
		wlan (3),
		router (4),
		telephone (5),
		docsis (6),
		station (7)
		}
	MAX-ACCESS read-only
	STATUS current
	DESCRIPTION
	"LLDP capabilities enabled."
	::= { receivedOverviewEntry 9 }

receivedOverviewMedCapabilities OBJECT-TYPE   -- med_capabilities
	SYNTAX BITS
		{
		capability (0),
		policy (1),
		location (2),
		mdiPse (3),
		mdiPd (4),
		inventory (5)
		}
	MAX-ACCESS read-only
	STATUS current
	DESCRIPTION
	"LLDP_MED capabilities."
	::= { receivedOverviewEntry 10 }

receivedOverviewPortIdSubtype OBJECT-TYPE   -- port_id_subtype
	SYNTAX INTEGER
		{
		unknown (0),
		interfaceAlias (1),
		portComponent (2),
		macAddress (3),
		networkAddress (4),
		interfaceName (5),
		agentCircuitId (6),
		local (7)
		}
	MAX-ACCESS read-only
	STATUS current
	DESCRIPTION
	"Type of port id."
	::= { receivedOverviewEntry 11 }

receivedOverviewPortIdentification OBJECT-TYPE   -- port_identification
	SYNTAX DisplayString
	MAX-ACCESS read-only
	STATUS current
	DESCRIPTION
	"Port id."
	::= { receivedOverviewEntry 12 }

receivedOverviewPortDescription OBJECT-TYPE   -- port_description
	SYNTAX DisplayString
	MAX-ACCESS read-only
	STATUS current
	DESCRIPTION
	"Port description."
	::= { receivedOverviewEntry 13 }

receivedOverviewPortVlan OBJECT-TYPE   -- port_vlan
	SYNTAX Integer32 (0..65535)
	MAX-ACCESS read-only
	STATUS current
	DESCRIPTION
	"Port vlan identifier. Related to port_default_vlan_id."
	::= { receivedOverviewEntry 14 }


-- ********************* End of receivedOverviewTable ***********************


-- ******************* Begin of receivedCoordinatesTable *************************

receivedCoordinatesTable	OBJECT-TYPE
	SYNTAX SEQUENCE OF ReceivedCoordinatesEntry
	MAX-ACCESS not-accessible
	STATUS current
	DESCRIPTION
		"Detailed GPS information about the pysical location of the attached device for each port are visible here if provided through the LLDP-MED protocol. "
	::= { lldp 101 }

receivedCoordinatesEntry	OBJECT-TYPE
	SYNTAX ReceivedCoordinatesEntry
	MAX-ACCESS not-accessible
	STATUS current
	DESCRIPTION
		""
	INDEX { receivedCoordinatesPortIndex }
	::= { receivedCoordinatesTable 1 }


	ReceivedCoordinatesEntry ::= SEQUENCE {
	receivedCoordinatesPortIndex INTEGER,
	receivedCoordinatesLatitude DisplayString,
	receivedCoordinatesLatResolution Integer32 ,
	receivedCoordinatesLongitude DisplayString,
	receivedCoordinatesLongResolution Integer32 ,
	receivedCoordinatesAltitude DisplayString,
	receivedCoordinatesAltResolution Integer32 ,
	receivedCoordinatesAltUnit INTEGER ,
	receivedCoordinatesDatum DisplayString
	}

receivedCoordinatesPortIndex	OBJECT-TYPE
	SYNTAX INTEGER (0..31)
	MAX-ACCESS not-accessible
	STATUS current
	DESCRIPTION
		"Automatically generated"
	::= { receivedCoordinatesEntry 1 }

receivedCoordinatesLatitude OBJECT-TYPE   -- latitude
	SYNTAX DisplayString
	MAX-ACCESS read-only
	STATUS current
	DESCRIPTION
	"A value in degrees such as: 50,123"
	::= { receivedCoordinatesEntry 2 }

receivedCoordinatesLatResolution OBJECT-TYPE   -- lat_resolution
	SYNTAX Integer32 (0..255)
	MAX-ACCESS read-only
	STATUS current
	DESCRIPTION
	"A value in bits. Higher value is more accurate."
	::= { receivedCoordinatesEntry 3 }

receivedCoordinatesLongitude OBJECT-TYPE   -- longitude
	SYNTAX DisplayString
	MAX-ACCESS read-only
	STATUS current
	DESCRIPTION
	"A value in degrees such as: 50,123"
	::= { receivedCoordinatesEntry 4 }

receivedCoordinatesLongResolution OBJECT-TYPE   -- long_resolution
	SYNTAX Integer32 (0..255)
	MAX-ACCESS read-only
	STATUS current
	DESCRIPTION
	"A value in bits. Higher value is more accurate."
	::= { receivedCoordinatesEntry 5 }

receivedCoordinatesAltitude OBJECT-TYPE   -- altitude
	SYNTAX DisplayString
	MAX-ACCESS read-only
	STATUS current
	DESCRIPTION
	"A value in meters or the floor level depending on definition."
	::= { receivedCoordinatesEntry 6 }

receivedCoordinatesAltResolution OBJECT-TYPE   -- alt_resolution
	SYNTAX Integer32 (0..255)
	MAX-ACCESS read-only
	STATUS current
	DESCRIPTION
	"A value in bits. Higher value is more accurate."
	::= { receivedCoordinatesEntry 7 }

receivedCoordinatesAltUnit OBJECT-TYPE   -- alt_unit
	SYNTAX INTEGER
		{
		meter (0),
		floor (1)
		}
	MAX-ACCESS read-only
	STATUS current
	DESCRIPTION
	"Defines in which way the altitude is interpreted."
	::= { receivedCoordinatesEntry 8 }

receivedCoordinatesDatum OBJECT-TYPE   -- datum
	SYNTAX DisplayString
	MAX-ACCESS read-only
	STATUS current
	DESCRIPTION
	"Name of the map the given coordinates are based upon."
	::= { receivedCoordinatesEntry 9 }


-- ********************* End of receivedCoordinatesTable ***********************


-- ******************* Begin of receivedCivicLocationsTable *************************

receivedCivicLocationsTable	OBJECT-TYPE
	SYNTAX SEQUENCE OF ReceivedCivicLocationsEntry
	MAX-ACCESS not-accessible
	STATUS current
	DESCRIPTION
		"Detailed address information about the physical location of the attached device for each port are visible here if provided through the LLDP-MED protocol. "
	::= { lldp 102 }

receivedCivicLocationsEntry	OBJECT-TYPE
	SYNTAX ReceivedCivicLocationsEntry
	MAX-ACCESS not-accessible
	STATUS current
	DESCRIPTION
		""
	INDEX { receivedCivicLocationsPortIndex }
	::= { receivedCivicLocationsTable 1 }


	ReceivedCivicLocationsEntry ::= SEQUENCE {
	receivedCivicLocationsPortIndex INTEGER,
	receivedCivicLocationsCountryCode DisplayString,
	receivedCivicLocationsLanguage DisplayString,
	receivedCivicLocationsNationalSubdivision DisplayString,
	receivedCivicLocationsCounty DisplayString,
	receivedCivicLocationsTown DisplayString,
	receivedCivicLocationsDistrict DisplayString,
	receivedCivicLocationsBlock DisplayString,
	receivedCivicLocationsStreet DisplayString,
	receivedCivicLocationsLeadingStreetDirection DisplayString,
	receivedCivicLocationsTrailingStreetSuffix DisplayString,
	receivedCivicLocationsStreetSuffix DisplayString,
	receivedCivicLocationsHouseNumber DisplayString,
	receivedCivicLocationsHouseNumberSuffix DisplayString,
	receivedCivicLocationsLandmark DisplayString,
	receivedCivicLocationsAdditionalInfo DisplayString,
	receivedCivicLocationsName DisplayString,
	receivedCivicLocationsZipCode DisplayString,
	receivedCivicLocationsBuilding DisplayString,
	receivedCivicLocationsUnit DisplayString,
	receivedCivicLocationsFloor DisplayString,
	receivedCivicLocationsRoom DisplayString,
	receivedCivicLocationsPlaceType DisplayString,
	receivedCivicLocationsScript DisplayString,
	receivedCivicLocationsElinNumber DisplayString
	}

receivedCivicLocationsPortIndex	OBJECT-TYPE
	SYNTAX INTEGER (0..31)
	MAX-ACCESS not-accessible
	STATUS current
	DESCRIPTION
		"Automatically generated"
	::= { receivedCivicLocationsEntry 1 }

receivedCivicLocationsCountryCode OBJECT-TYPE   -- country_code
	SYNTAX DisplayString
	MAX-ACCESS read-only
	STATUS current
	DESCRIPTION
	"Two-letter ISO 3166 country code in capital ASCII letters. Use DE for Germany, etc."
	::= { receivedCivicLocationsEntry 2 }

receivedCivicLocationsLanguage OBJECT-TYPE   -- language
	SYNTAX DisplayString
	MAX-ACCESS read-only
	STATUS current
	DESCRIPTION
	"ISO 639 language code used for presenting the address information."
	::= { receivedCivicLocationsEntry 3 }

receivedCivicLocationsNationalSubdivision OBJECT-TYPE   -- national_subdivision
	SYNTAX DisplayString
	MAX-ACCESS read-only
	STATUS current
	DESCRIPTION
	"National subdivision: state, canton, region, province, or prefecture. Example: Hessen."
	::= { receivedCivicLocationsEntry 4 }

receivedCivicLocationsCounty OBJECT-TYPE   -- county
	SYNTAX DisplayString
	MAX-ACCESS read-only
	STATUS current
	DESCRIPTION
	"County / parish / district. Example: Landkreis Darmstadt"
	::= { receivedCivicLocationsEntry 5 }

receivedCivicLocationsTown OBJECT-TYPE   -- town
	SYNTAX DisplayString
	MAX-ACCESS read-only
	STATUS current
	DESCRIPTION
	"City / township. Example: Frankfurt"
	::= { receivedCivicLocationsEntry 6 }

receivedCivicLocationsDistrict OBJECT-TYPE   -- district
	SYNTAX DisplayString
	MAX-ACCESS read-only
	STATUS current
	DESCRIPTION
	"City district / division / borough / ward."
	::= { receivedCivicLocationsEntry 7 }

receivedCivicLocationsBlock OBJECT-TYPE   -- block
	SYNTAX DisplayString
	MAX-ACCESS read-only
	STATUS current
	DESCRIPTION
	"Neighborhood / block."
	::= { receivedCivicLocationsEntry 8 }

receivedCivicLocationsStreet OBJECT-TYPE   -- street
	SYNTAX DisplayString
	MAX-ACCESS read-only
	STATUS current
	DESCRIPTION
	"Name of the street without house number."
	::= { receivedCivicLocationsEntry 9 }

receivedCivicLocationsLeadingStreetDirection OBJECT-TYPE   -- leading_street_direction
	SYNTAX DisplayString
	MAX-ACCESS read-only
	STATUS current
	DESCRIPTION
	"Use any of these values or leave blank: N,E,W,S,NE,NW,SE,SW."
	::= { receivedCivicLocationsEntry 10 }

receivedCivicLocationsTrailingStreetSuffix OBJECT-TYPE   -- trailing_street_suffix
	SYNTAX DisplayString
	MAX-ACCESS read-only
	STATUS current
	DESCRIPTION
	"Use any of these values or leave blank: N,E,W,S,NE,NW,SE,SW."
	::= { receivedCivicLocationsEntry 11 }

receivedCivicLocationsStreetSuffix OBJECT-TYPE   -- street_suffix
	SYNTAX DisplayString
	MAX-ACCESS read-only
	STATUS current
	DESCRIPTION
	"Street suffix such as place or avenue."
	::= { receivedCivicLocationsEntry 12 }

receivedCivicLocationsHouseNumber OBJECT-TYPE   -- house_number
	SYNTAX DisplayString
	MAX-ACCESS read-only
	STATUS current
	DESCRIPTION
	"House number without a possible suffix."
	::= { receivedCivicLocationsEntry 13 }

receivedCivicLocationsHouseNumberSuffix OBJECT-TYPE   -- house_number_suffix
	SYNTAX DisplayString
	MAX-ACCESS read-only
	STATUS current
	DESCRIPTION
	"A modifier to the house number. It does not include parts of the house number. Example: a"
	::= { receivedCivicLocationsEntry 14 }

receivedCivicLocationsLandmark OBJECT-TYPE   -- landmark
	SYNTAX DisplayString
	MAX-ACCESS read-only
	STATUS current
	DESCRIPTION
	"Landmark or vanity address for easier reference. Example: Airport Frankfurt"
	::= { receivedCivicLocationsEntry 15 }

receivedCivicLocationsAdditionalInfo OBJECT-TYPE   -- additional_info
	SYNTAX DisplayString
	MAX-ACCESS read-only
	STATUS current
	DESCRIPTION
	"Additional location information without specified format."
	::= { receivedCivicLocationsEntry 16 }

receivedCivicLocationsName OBJECT-TYPE   -- name
	SYNTAX DisplayString
	MAX-ACCESS read-only
	STATUS current
	DESCRIPTION
	"Identifies the person or organization associated with the address. Example: Sunshine Airline Office"
	::= { receivedCivicLocationsEntry 17 }

receivedCivicLocationsZipCode OBJECT-TYPE   -- zip_code
	SYNTAX DisplayString
	MAX-ACCESS read-only
	STATUS current
	DESCRIPTION
	"Postal zip code for the address."
	::= { receivedCivicLocationsEntry 18 }

receivedCivicLocationsBuilding OBJECT-TYPE   -- building
	SYNTAX DisplayString
	MAX-ACCESS read-only
	STATUS current
	DESCRIPTION
	"The name of the building if this exists. Example: Terminal Building East"
	::= { receivedCivicLocationsEntry 19 }

receivedCivicLocationsUnit OBJECT-TYPE   -- unit
	SYNTAX DisplayString
	MAX-ACCESS read-only
	STATUS current
	DESCRIPTION
	"Unit / appartment / suite."
	::= { receivedCivicLocationsEntry 20 }

receivedCivicLocationsFloor OBJECT-TYPE   -- floor
	SYNTAX DisplayString
	MAX-ACCESS read-only
	STATUS current
	DESCRIPTION
	"Floor value. Example: 1 for first floor."
	::= { receivedCivicLocationsEntry 21 }

receivedCivicLocationsRoom OBJECT-TYPE   -- room
	SYNTAX DisplayString
	MAX-ACCESS read-only
	STATUS current
	DESCRIPTION
	"Room number or name."
	::= { receivedCivicLocationsEntry 22 }

receivedCivicLocationsPlaceType OBJECT-TYPE   -- place_type
	SYNTAX DisplayString
	MAX-ACCESS read-only
	STATUS current
	DESCRIPTION
	"Place type. Example: Office."
	::= { receivedCivicLocationsEntry 23 }

receivedCivicLocationsScript OBJECT-TYPE   -- script
	SYNTAX DisplayString
	MAX-ACCESS read-only
	STATUS current
	DESCRIPTION
	"The script (from ISO 15924 [14]) used to encode the address information. Default: Latn"
	::= { receivedCivicLocationsEntry 24 }

receivedCivicLocationsElinNumber OBJECT-TYPE   -- elin_number
	SYNTAX DisplayString
	MAX-ACCESS read-only
	STATUS current
	DESCRIPTION
	"Emergency Call Services (ECS) Emergency Location Identification Number (ELIN)."
	::= { receivedCivicLocationsEntry 25 }


-- ********************* End of receivedCivicLocationsTable ***********************


-- ******************* Begin of receivedPoliciesTable *************************

receivedPoliciesTable	OBJECT-TYPE
	SYNTAX SEQUENCE OF ReceivedPoliciesEntry
	MAX-ACCESS not-accessible
	STATUS current
	DESCRIPTION
		"Detailed information about the attached applications. "
	::= { lldp 103 }

receivedPoliciesEntry	OBJECT-TYPE
	SYNTAX ReceivedPoliciesEntry
	MAX-ACCESS not-accessible
	STATUS current
	DESCRIPTION
		""
	INDEX { receivedPoliciesPortIndex }
	::= { receivedPoliciesTable 1 }


	ReceivedPoliciesEntry ::= SEQUENCE {
	receivedPoliciesPortIndex INTEGER,
	receivedPoliciesApplicationType INTEGER ,
	receivedPoliciesPolicyDefined INTEGER ,
	receivedPoliciesTaggedVlan INTEGER ,
	receivedPoliciesVlanId Unsigned32,
	receivedPoliciesLayer2Priority INTEGER ,
	receivedPoliciesDscp Integer32
	}

receivedPoliciesPortIndex	OBJECT-TYPE
	SYNTAX INTEGER (0..31)
	MAX-ACCESS not-accessible
	STATUS current
	DESCRIPTION
		"Automatically generated"
	::= { receivedPoliciesEntry 1 }

receivedPoliciesApplicationType OBJECT-TYPE   -- application_type
	SYNTAX INTEGER
		{
		unknown (0),
		voice (1),
		voiceSignaling (2),
		guestVoice (3),
		guestVoiceSignaling (4),
		softphoneVoice (5),
		videoConferencing (6),
		streamingVideo (7),
		videoSignaling (8)
		}
	MAX-ACCESS read-only
	STATUS current
	DESCRIPTION
	"Valid application types."
	::= { receivedPoliciesEntry 2 }

receivedPoliciesPolicyDefined OBJECT-TYPE   -- policy_defined
	SYNTAX INTEGER { false(0), true(1) }
	MAX-ACCESS read-only
	STATUS current
	DESCRIPTION
	"False indicates policy is unknown. True indicates policy is defined."
	::= { receivedPoliciesEntry 3 }

receivedPoliciesTaggedVlan OBJECT-TYPE   -- tagged_vlan
	SYNTAX INTEGER { false(0), true(1) }
	MAX-ACCESS read-only
	STATUS current
	DESCRIPTION
	"When set VLAN tagging is used."
	::= { receivedPoliciesEntry 4 }

receivedPoliciesVlanId OBJECT-TYPE   -- vlan_id
	SYNTAX Unsigned32
	MAX-ACCESS read-only
	STATUS current
	DESCRIPTION
	"0 - only the priority level is significant. / IEEE 802.1q VLAN ID (VID) value. Related to voice vlan."
	::= { receivedPoliciesEntry 5 }

receivedPoliciesLayer2Priority OBJECT-TYPE   -- layer_2_priority
	SYNTAX INTEGER
		{
		unknown (0),
		background (1),
		spare (2),
		bestEffort (3),
		excellentEffort (4),
		controlledLoad (5),
		video (6),
		voice (7),
		networkControl (8)
		}
	MAX-ACCESS read-only
	STATUS current
	DESCRIPTION
	"IEEE 802.1d / IEEE 802.1p Layer 2 Priority."
	::= { receivedPoliciesEntry 6 }

receivedPoliciesDscp OBJECT-TYPE   -- dscp
	SYNTAX Integer32 (0..255)
	MAX-ACCESS read-only
	STATUS current
	DESCRIPTION
	"DiffServ/Differentiated Services Code Point (DSCP) value as defined in IETF RFC 2474 for the specified application type."
	::= { receivedPoliciesEntry 7 }


-- ********************* End of receivedPoliciesTable ***********************


-- ******************* Begin of receivedInventoryInfosTable *************************

receivedInventoryInfosTable	OBJECT-TYPE
	SYNTAX SEQUENCE OF ReceivedInventoryInfosEntry
	MAX-ACCESS not-accessible
	STATUS current
	DESCRIPTION
		"This table lists general inventory data of the attached equipment."
	::= { lldp 104 }

receivedInventoryInfosEntry	OBJECT-TYPE
	SYNTAX ReceivedInventoryInfosEntry
	MAX-ACCESS not-accessible
	STATUS current
	DESCRIPTION
		""
	INDEX { receivedInventoryInfosPortIndex }
	::= { receivedInventoryInfosTable 1 }


	ReceivedInventoryInfosEntry ::= SEQUENCE {
	receivedInventoryInfosPortIndex INTEGER,
	receivedInventoryInfosHardwareRevision DisplayString,
	receivedInventoryInfosFirmwareRevision DisplayString,
	receivedInventoryInfosSoftwareRevision DisplayString,
	receivedInventoryInfosSerialNumber DisplayString,
	receivedInventoryInfosManufacturer DisplayString,
	receivedInventoryInfosModelName DisplayString,
	receivedInventoryInfosAssetId DisplayString
	}

receivedInventoryInfosPortIndex	OBJECT-TYPE
	SYNTAX INTEGER (0..31)
	MAX-ACCESS not-accessible
	STATUS current
	DESCRIPTION
		"Automatically generated"
	::= { receivedInventoryInfosEntry 1 }

receivedInventoryInfosHardwareRevision OBJECT-TYPE   -- hardware_revision
	SYNTAX DisplayString
	MAX-ACCESS read-only
	STATUS current
	DESCRIPTION
	"Hardware version"
	::= { receivedInventoryInfosEntry 2 }

receivedInventoryInfosFirmwareRevision OBJECT-TYPE   -- firmware_revision
	SYNTAX DisplayString
	MAX-ACCESS read-only
	STATUS current
	DESCRIPTION
	"Firmware version"
	::= { receivedInventoryInfosEntry 3 }

receivedInventoryInfosSoftwareRevision OBJECT-TYPE   -- software_revision
	SYNTAX DisplayString
	MAX-ACCESS read-only
	STATUS current
	DESCRIPTION
	"Software version"
	::= { receivedInventoryInfosEntry 4 }

receivedInventoryInfosSerialNumber OBJECT-TYPE   -- serial_number
	SYNTAX DisplayString
	MAX-ACCESS read-only
	STATUS current
	DESCRIPTION
	"Serial number"
	::= { receivedInventoryInfosEntry 5 }

receivedInventoryInfosManufacturer OBJECT-TYPE   -- manufacturer
	SYNTAX DisplayString
	MAX-ACCESS read-only
	STATUS current
	DESCRIPTION
	"Manufacturer name"
	::= { receivedInventoryInfosEntry 6 }

receivedInventoryInfosModelName OBJECT-TYPE   -- model_name
	SYNTAX DisplayString
	MAX-ACCESS read-only
	STATUS current
	DESCRIPTION
	"Vendor-specific model name"
	::= { receivedInventoryInfosEntry 7 }

receivedInventoryInfosAssetId OBJECT-TYPE   -- asset_id
	SYNTAX DisplayString
	MAX-ACCESS read-only
	STATUS current
	DESCRIPTION
	"Vendor-specific asset tracking identifier"
	::= { receivedInventoryInfosEntry 8 }


-- ********************* End of receivedInventoryInfosTable ***********************


-- ******************* Begin of receivedPoeInfosTable *************************

receivedPoeInfosTable	OBJECT-TYPE
	SYNTAX SEQUENCE OF ReceivedPoeInfosEntry
	MAX-ACCESS not-accessible
	STATUS current
	DESCRIPTION
		"Detailed PoE information about the attached applications. "
	::= { lldp 105 }

receivedPoeInfosEntry	OBJECT-TYPE
	SYNTAX ReceivedPoeInfosEntry
	MAX-ACCESS not-accessible
	STATUS current
	DESCRIPTION
		""
	INDEX { receivedPoeInfosPortIndex }
	::= { receivedPoeInfosTable 1 }


	ReceivedPoeInfosEntry ::= SEQUENCE {
	receivedPoeInfosPortIndex INTEGER,
	receivedPoeInfosType INTEGER ,
	receivedPoeInfosSource INTEGER ,
	receivedPoeInfosPriority INTEGER ,
	receivedPoeInfosValue Unsigned32
	}

receivedPoeInfosPortIndex	OBJECT-TYPE
	SYNTAX INTEGER (0..31)
	MAX-ACCESS not-accessible
	STATUS current
	DESCRIPTION
		"Automatically generated"
	::= { receivedPoeInfosEntry 1 }

receivedPoeInfosType OBJECT-TYPE   -- type
	SYNTAX INTEGER
		{
		unknown (0),
		pse (1),
		pd (2),
		noPoe (3)
		}
	MAX-ACCESS read-only
	STATUS current
	DESCRIPTION
	"Type of PoE equipment."
	::= { receivedPoeInfosEntry 2 }

receivedPoeInfosSource OBJECT-TYPE   -- source
	SYNTAX INTEGER
		{
		unknown (0),
		pdPsePrimary (1),
		pdLocalBackup (2),
		pdPseLocal (3)
		}
	MAX-ACCESS read-only
	STATUS current
	DESCRIPTION
	"Describes the power source."
	::= { receivedPoeInfosEntry 3 }

receivedPoeInfosPriority OBJECT-TYPE   -- priority
	SYNTAX INTEGER
		{
		unknown (0),
		critical (1),
		high (2),
		low (3)
		}
	MAX-ACCESS read-only
	STATUS current
	DESCRIPTION
	"Indicates priority of this device."
	::= { receivedPoeInfosEntry 4 }

receivedPoeInfosValue OBJECT-TYPE   -- value
	SYNTAX Unsigned32
	MAX-ACCESS read-only
	STATUS current
	DESCRIPTION
	"Indicates the power available from the PSE via this port expressed in units of 0.1 watts on the remote device."
	::= { receivedPoeInfosEntry 5 }


-- ********************* End of receivedPoeInfosTable ***********************


-- ******************* Begin of receivedPoeControlTable *************************

receivedPoeControlTable	OBJECT-TYPE
	SYNTAX SEQUENCE OF ReceivedPoeControlEntry
	MAX-ACCESS not-accessible
	STATUS current
	DESCRIPTION
		""
	::= { lldp 106 }

receivedPoeControlEntry	OBJECT-TYPE
	SYNTAX ReceivedPoeControlEntry
	MAX-ACCESS not-accessible
	STATUS current
	DESCRIPTION
		""
	INDEX { receivedPoeControlPortIndex }
	::= { receivedPoeControlTable 1 }


	ReceivedPoeControlEntry ::= SEQUENCE {
	receivedPoeControlPortIndex INTEGER,
	receivedPoeControlType INTEGER ,
	receivedPoeControlPoePowerSupported INTEGER ,
	receivedPoeControlPoePowerEnabled INTEGER ,
	receivedPoeControlPairControl INTEGER ,
	receivedPoeControlPowerPairs INTEGER ,
	receivedPoeControlPowerClass INTEGER ,
	receivedPoeControlDeviceType Integer32 ,
	receivedPoeControlSource INTEGER ,
	receivedPoeControlPriority INTEGER ,
	receivedPoeControlPdRequestedPower Integer32 ,
	receivedPoeControlPseAllocatedPower Integer32
	}

receivedPoeControlPortIndex	OBJECT-TYPE
	SYNTAX INTEGER (0..31)
	MAX-ACCESS not-accessible
	STATUS current
	DESCRIPTION
		"Automatically generated"
	::= { receivedPoeControlEntry 1 }

receivedPoeControlType OBJECT-TYPE   -- type
	SYNTAX INTEGER
		{
		unknown (0),
		pse (1),
		pd (2),
		noPoe (3)
		}
	MAX-ACCESS read-only
	STATUS current
	DESCRIPTION
	"Indicates device type."
	::= { receivedPoeControlEntry 2 }

receivedPoeControlPoePowerSupported OBJECT-TYPE   -- poe_power_supported
	SYNTAX INTEGER { false(0), true(1) }
	MAX-ACCESS read-only
	STATUS current
	DESCRIPTION
	"Indicates if PoE is supported by the interface."
	::= { receivedPoeControlEntry 3 }

receivedPoeControlPoePowerEnabled OBJECT-TYPE   -- poe_power_enabled
	SYNTAX INTEGER { false(0), true(1) }
	MAX-ACCESS read-only
	STATUS current
	DESCRIPTION
	"Indicates if PoE is enabled for this interface."
	::= { receivedPoeControlEntry 4 }

receivedPoeControlPairControl OBJECT-TYPE   -- pair_control
	SYNTAX INTEGER { false(0), true(1) }
	MAX-ACCESS read-only
	STATUS current
	DESCRIPTION
	"Indicates if the pair selection can be controlled on the given port"
	::= { receivedPoeControlEntry 5 }

receivedPoeControlPowerPairs OBJECT-TYPE   -- power_pairs
	SYNTAX INTEGER
		{
		signal (1),
		spare (2)
		}
	MAX-ACCESS read-only
	STATUS current
	DESCRIPTION
	"Indicates which pins of the plug are used for power."
	::= { receivedPoeControlEntry 6 }

receivedPoeControlPowerClass OBJECT-TYPE   -- power_class
	SYNTAX INTEGER
		{
		noClass (0),
		class0 (1),
		class1 (2),
		class2 (3),
		class3 (4),
		class4 (5)
		}
	MAX-ACCESS read-only
	STATUS current
	DESCRIPTION
	"Required PoE class."
	::= { receivedPoeControlEntry 7 }

receivedPoeControlDeviceType OBJECT-TYPE   -- device_type
	SYNTAX Integer32 (0..255)
	MAX-ACCESS read-only
	STATUS current
	DESCRIPTION
	"Type of PoE equipment."
	::= { receivedPoeControlEntry 8 }

receivedPoeControlSource OBJECT-TYPE   -- source
	SYNTAX INTEGER
		{
		unknown (0),
		pdPsePrimary (1),
		pdLocalBackup (2),
		pdPseLocal (3)
		}
	MAX-ACCESS read-only
	STATUS current
	DESCRIPTION
	"Indicates the power source."
	::= { receivedPoeControlEntry 9 }

receivedPoeControlPriority OBJECT-TYPE   -- priority
	SYNTAX INTEGER
		{
		unknown (0),
		critical (1),
		high (2),
		low (3)
		}
	MAX-ACCESS read-only
	STATUS current
	DESCRIPTION
	"Priority of the attached port."
	::= { receivedPoeControlEntry 10 }

receivedPoeControlPdRequestedPower OBJECT-TYPE   -- pd_requested_power
	SYNTAX Integer32 (0..255)
	MAX-ACCESS read-only
	STATUS current
	DESCRIPTION
	"PD requested power value"
	::= { receivedPoeControlEntry 11 }

receivedPoeControlPseAllocatedPower OBJECT-TYPE   -- pse_allocated_power
	SYNTAX Integer32 (0..255)
	MAX-ACCESS read-only
	STATUS current
	DESCRIPTION
	"PSE allocated power value"
	::= { receivedPoeControlEntry 12 }


-- ********************* End of receivedPoeControlTable ***********************



END
