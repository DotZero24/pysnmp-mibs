G6-RMON-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

device MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 1 }

rmon  OBJECT IDENTIFIER ::= { device 85 }



-- *************************** CONFIGURATION SECTION ********************************


rmonClearAllCounter OBJECT-TYPE   -- clear_all_counter
	SYNTAX DisplayString
	MAX-ACCESS read-write
	STATUS current
	DESCRIPTION
	"When executed all rmon counters of all ports are reset to 0. This has no service implications."
	::= { rmon 1 }



-- ****************************** STATUS SECTION ********************************


-- ******************* Begin of ingressTable *************************

ingressTable	OBJECT-TYPE
	SYNTAX SEQUENCE OF IngressEntry
	MAX-ACCESS not-accessible
	STATUS current
	DESCRIPTION
		"Statistics regarding inbound traffic"
	::= { rmon 100 }

ingressEntry	OBJECT-TYPE
	SYNTAX IngressEntry
	MAX-ACCESS not-accessible
	STATUS current
	DESCRIPTION
		""
	INDEX { ingressPortIndex }
	::= { ingressTable 1 }


	IngressEntry ::= SEQUENCE {
	ingressPortIndex INTEGER,
	ingressEntryStatus INTEGER ,
	ingressInGoodOctetsLo Unsigned32,
	ingressInGoodOctetsHi Unsigned32,
	ingressInBadOctets Unsigned32,
	ingressInTotalPackets Unsigned32,
	ingressInUnicasts Unsigned32,
	ingressInNonUnicasts Unsigned32,
	ingressInBroadcasts Unsigned32,
	ingressInMulticasts Unsigned32,
	ingressInPause Unsigned32,
	ingressInTotalReceiveErrors Unsigned32,
	ingressInUndersize Unsigned32,
	ingressInOversize Unsigned32,
	ingressInFragments Unsigned32,
	ingressInJabber Unsigned32,
	ingressInFcsErrors Unsigned32,
	ingressInDiscarded Unsigned32
	}

ingressPortIndex	OBJECT-TYPE
	SYNTAX INTEGER (0..31)
	MAX-ACCESS not-accessible
	STATUS current
	DESCRIPTION
		"Automatically generated"
	::= { ingressEntry 1 }

ingressEntryStatus OBJECT-TYPE   -- entry_status
	SYNTAX INTEGER
		{
		invalid (0),
		valid (1)
		}
	MAX-ACCESS read-only
	STATUS current
	DESCRIPTION
	"Indicated whether this ports table is updated and valid."
	::= { ingressEntry 2 }

ingressInGoodOctetsLo OBJECT-TYPE   -- in_good_octets_lo
	SYNTAX Unsigned32
	MAX-ACCESS read-only
	STATUS current
	DESCRIPTION
	"Number of bytes received without error (low)"
	::= { ingressEntry 3 }

ingressInGoodOctetsHi OBJECT-TYPE   -- in_good_octets_hi
	SYNTAX Unsigned32
	MAX-ACCESS read-only
	STATUS current
	DESCRIPTION
	"Number of bytes received without error (high)"
	::= { ingressEntry 4 }

ingressInBadOctets OBJECT-TYPE   -- in_bad_octets
	SYNTAX Unsigned32
	MAX-ACCESS read-only
	STATUS current
	DESCRIPTION
	"Number of bytes received with error."
	::= { ingressEntry 5 }

ingressInTotalPackets OBJECT-TYPE   -- in_total_packets
	SYNTAX Unsigned32
	MAX-ACCESS read-only
	STATUS current
	DESCRIPTION
	"Number of packets on any type received."
	::= { ingressEntry 6 }

ingressInUnicasts OBJECT-TYPE   -- in_unicasts
	SYNTAX Unsigned32
	MAX-ACCESS read-only
	STATUS current
	DESCRIPTION
	"Number of unicast packets received."
	::= { ingressEntry 7 }

ingressInNonUnicasts OBJECT-TYPE   -- in_non_unicasts
	SYNTAX Unsigned32
	MAX-ACCESS read-only
	STATUS current
	DESCRIPTION
	"Number of packets which are non unicast type."
	::= { ingressEntry 8 }

ingressInBroadcasts OBJECT-TYPE   -- in_broadcasts
	SYNTAX Unsigned32
	MAX-ACCESS read-only
	STATUS current
	DESCRIPTION
	"Number of broadcast packets received."
	::= { ingressEntry 9 }

ingressInMulticasts OBJECT-TYPE   -- in_multicasts
	SYNTAX Unsigned32
	MAX-ACCESS read-only
	STATUS current
	DESCRIPTION
	"Number of multicast packets received."
	::= { ingressEntry 10 }

ingressInPause OBJECT-TYPE   -- in_pause
	SYNTAX Unsigned32
	MAX-ACCESS read-only
	STATUS current
	DESCRIPTION
	"Number of pause frames received."
	::= { ingressEntry 11 }

ingressInTotalReceiveErrors OBJECT-TYPE   -- in_total_receive_errors
	SYNTAX Unsigned32
	MAX-ACCESS read-only
	STATUS current
	DESCRIPTION
	"Number of packets received with any kind of error."
	::= { ingressEntry 12 }

ingressInUndersize OBJECT-TYPE   -- in_undersize
	SYNTAX Unsigned32
	MAX-ACCESS read-only
	STATUS current
	DESCRIPTION
	"Number of undersized frames received."
	::= { ingressEntry 13 }

ingressInOversize OBJECT-TYPE   -- in_oversize
	SYNTAX Unsigned32
	MAX-ACCESS read-only
	STATUS current
	DESCRIPTION
	"Number of oversizeded frames received."
	::= { ingressEntry 14 }

ingressInFragments OBJECT-TYPE   -- in_fragments
	SYNTAX Unsigned32
	MAX-ACCESS read-only
	STATUS current
	DESCRIPTION
	"Number of fragmented frames received."
	::= { ingressEntry 15 }

ingressInJabber OBJECT-TYPE   -- in_jabber
	SYNTAX Unsigned32
	MAX-ACCESS read-only
	STATUS current
	DESCRIPTION
	"Number of jabbers received."
	::= { ingressEntry 16 }

ingressInFcsErrors OBJECT-TYPE   -- in_fcs_errors
	SYNTAX Unsigned32
	MAX-ACCESS read-only
	STATUS current
	DESCRIPTION
	"Number of checksum errors."
	::= { ingressEntry 17 }

ingressInDiscarded OBJECT-TYPE   -- in_discarded
	SYNTAX Unsigned32
	MAX-ACCESS read-only
	STATUS current
	DESCRIPTION
	"Number of frames discard due to lack of internal buffer space."
	::= { ingressEntry 18 }


-- ********************* End of ingressTable ***********************


-- ******************* Begin of egressTable *************************

egressTable	OBJECT-TYPE
	SYNTAX SEQUENCE OF EgressEntry
	MAX-ACCESS not-accessible
	STATUS current
	DESCRIPTION
		"Statistics regarding outbound traffic"
	::= { rmon 101 }

egressEntry	OBJECT-TYPE
	SYNTAX EgressEntry
	MAX-ACCESS not-accessible
	STATUS current
	DESCRIPTION
		""
	INDEX { egressPortIndex }
	::= { egressTable 1 }


	EgressEntry ::= SEQUENCE {
	egressPortIndex INTEGER,
	egressOutGoodOctetsLo Unsigned32,
	egressOutGoodOctetsHi Unsigned32,
	egressOutUnicasts Unsigned32,
	egressOutNonUnicasts Unsigned32,
	egressOutBroadcasts Unsigned32,
	egressOutMulticasts Unsigned32,
	egressOutPause Unsigned32,
	egressOutDeferred Unsigned32,
	egressOutTotalCollisions Unsigned32,
	egressOutSingleCollisions Unsigned32,
	egressOutMultipleCollisions Unsigned32,
	egressOutExcessiveCollisions Unsigned32,
	egressOutLateCollisions Unsigned32,
	egressOutFcsErrors Unsigned32,
	egressOutDroppedPackets Unsigned32
	}

egressPortIndex	OBJECT-TYPE
	SYNTAX INTEGER (0..31)
	MAX-ACCESS not-accessible
	STATUS current
	DESCRIPTION
		"Automatically generated"
	::= { egressEntry 1 }

egressOutGoodOctetsLo OBJECT-TYPE   -- out_good_octets_lo
	SYNTAX Unsigned32
	MAX-ACCESS read-only
	STATUS current
	DESCRIPTION
	"Number of bytes transmitted without error (low)"
	::= { egressEntry 2 }

egressOutGoodOctetsHi OBJECT-TYPE   -- out_good_octets_hi
	SYNTAX Unsigned32
	MAX-ACCESS read-only
	STATUS current
	DESCRIPTION
	"Number of bytes transmitted without error (high)"
	::= { egressEntry 3 }

egressOutUnicasts OBJECT-TYPE   -- out_unicasts
	SYNTAX Unsigned32
	MAX-ACCESS read-only
	STATUS current
	DESCRIPTION
	"Number of unicast packets transmitted"
	::= { egressEntry 4 }

egressOutNonUnicasts OBJECT-TYPE   -- out_non_unicasts
	SYNTAX Unsigned32
	MAX-ACCESS read-only
	STATUS current
	DESCRIPTION
	"Number of packets which are non unicast type"
	::= { egressEntry 5 }

egressOutBroadcasts OBJECT-TYPE   -- out_broadcasts
	SYNTAX Unsigned32
	MAX-ACCESS read-only
	STATUS current
	DESCRIPTION
	"Number of broadcast packets transmitted"
	::= { egressEntry 6 }

egressOutMulticasts OBJECT-TYPE   -- out_multicasts
	SYNTAX Unsigned32
	MAX-ACCESS read-only
	STATUS current
	DESCRIPTION
	"Number of multicast packets transmitted"
	::= { egressEntry 7 }

egressOutPause OBJECT-TYPE   -- out_pause
	SYNTAX Unsigned32
	MAX-ACCESS read-only
	STATUS current
	DESCRIPTION
	"Number of pause frames transmitted"
	::= { egressEntry 8 }

egressOutDeferred OBJECT-TYPE   -- out_deferred
	SYNTAX Unsigned32
	MAX-ACCESS read-only
	STATUS current
	DESCRIPTION
	"Number of deferred frames due to a busy condition. This is not an error condition."
	::= { egressEntry 9 }

egressOutTotalCollisions OBJECT-TYPE   -- out_total_collisions
	SYNTAX Unsigned32
	MAX-ACCESS read-only
	STATUS current
	DESCRIPTION
	"Number of all collisions that have occurred on that port. A collision may occure on a half-duplex interface detecting an incoming packet at the time it was trying to transmit a packet."
	::= { egressEntry 10 }

egressOutSingleCollisions OBJECT-TYPE   -- out_single_collisions
	SYNTAX Unsigned32
	MAX-ACCESS read-only
	STATUS current
	DESCRIPTION
	"Number of times the port has experienced a single collision when attempting to transmit a packet."
	::= { egressEntry 11 }

egressOutMultipleCollisions OBJECT-TYPE   -- out_multiple_collisions
	SYNTAX Unsigned32
	MAX-ACCESS read-only
	STATUS current
	DESCRIPTION
	"Number of times the port has experienced a multiple collision when attempting to transmit a packet."
	::= { egressEntry 12 }

egressOutExcessiveCollisions OBJECT-TYPE   -- out_excessive_collisions
	SYNTAX Unsigned32
	MAX-ACCESS read-only
	STATUS current
	DESCRIPTION
	"Number of times a packet could not be sent due to repeated collisions on the same packet.."
	::= { egressEntry 13 }

egressOutLateCollisions OBJECT-TYPE   -- out_late_collisions
	SYNTAX Unsigned32
	MAX-ACCESS read-only
	STATUS current
	DESCRIPTION
	"Number of times a late collision has occured. A late collision occurs when the switch detects an incoming packet after it has already transmitted more than 64 bytes of its current outgoing packet. This indicates a half duplex - full duplex mismatch."
	::= { egressEntry 14 }

egressOutFcsErrors OBJECT-TYPE   -- out_fcs_errors
	SYNTAX Unsigned32
	MAX-ACCESS read-only
	STATUS current
	DESCRIPTION
	"Number of checksum errors"
	::= { egressEntry 15 }

egressOutDroppedPackets OBJECT-TYPE   -- out_dropped_packets
	SYNTAX Unsigned32
	MAX-ACCESS read-only
	STATUS current
	DESCRIPTION
	"Number of good outgoing frames that were dropped due to outgoing policies"
	::= { egressEntry 16 }


-- ********************* End of egressTable ***********************


-- ******************* Begin of histogramTable *************************

histogramTable	OBJECT-TYPE
	SYNTAX SEQUENCE OF HistogramEntry
	MAX-ACCESS not-accessible
	STATUS current
	DESCRIPTION
		"The histogram indicates the packet size distribution for incoming data per port."
	::= { rmon 102 }

histogramEntry	OBJECT-TYPE
	SYNTAX HistogramEntry
	MAX-ACCESS not-accessible
	STATUS current
	DESCRIPTION
		""
	INDEX { histogramPortIndex }
	::= { histogramTable 1 }


	HistogramEntry ::= SEQUENCE {
	histogramPortIndex INTEGER,
	histogramIn64Octets Unsigned32,
	histogramIn65To127Octets Unsigned32,
	histogramIn128To255Octets Unsigned32,
	histogramIn256To511Octets Unsigned32,
	histogramIn512To1023Octets Unsigned32,
	histogramIn1024ToMaxOctets Unsigned32
	}

histogramPortIndex	OBJECT-TYPE
	SYNTAX INTEGER (0..31)
	MAX-ACCESS not-accessible
	STATUS current
	DESCRIPTION
		"Automatically generated"
	::= { histogramEntry 1 }

histogramIn64Octets OBJECT-TYPE   -- in_64_octets
	SYNTAX Unsigned32
	MAX-ACCESS read-only
	STATUS current
	DESCRIPTION
	"Number of minimum size frames received"
	::= { histogramEntry 2 }

histogramIn65To127Octets OBJECT-TYPE   -- in_65_to_127_octets
	SYNTAX Unsigned32
	MAX-ACCESS read-only
	STATUS current
	DESCRIPTION
	"Number of frames with size between 65 and 127 bytes received"
	::= { histogramEntry 3 }

histogramIn128To255Octets OBJECT-TYPE   -- in_128_to_255_octets
	SYNTAX Unsigned32
	MAX-ACCESS read-only
	STATUS current
	DESCRIPTION
	"Number of frames with size between 128 and 255 bytes received"
	::= { histogramEntry 4 }

histogramIn256To511Octets OBJECT-TYPE   -- in_256_to_511_octets
	SYNTAX Unsigned32
	MAX-ACCESS read-only
	STATUS current
	DESCRIPTION
	"Number of frames with size between 256 and 511 bytes received"
	::= { histogramEntry 5 }

histogramIn512To1023Octets OBJECT-TYPE   -- in_512_to_1023_octets
	SYNTAX Unsigned32
	MAX-ACCESS read-only
	STATUS current
	DESCRIPTION
	"Number of frames with size between 512 and 1023 bytes received"
	::= { histogramEntry 6 }

histogramIn1024ToMaxOctets OBJECT-TYPE   -- in_1024_to_max_octets
	SYNTAX Unsigned32
	MAX-ACCESS read-only
	STATUS current
	DESCRIPTION
	"Number of frames with size above 1023 bytes received"
	::= { histogramEntry 7 }


-- ********************* End of histogramTable ***********************


-- ******************* Begin of utilizationTable *************************

utilizationTable	OBJECT-TYPE
	SYNTAX SEQUENCE OF UtilizationEntry
	MAX-ACCESS not-accessible
	STATUS current
	DESCRIPTION
		"Calculates averaged data utilization values for each port."
	::= { rmon 103 }

utilizationEntry	OBJECT-TYPE
	SYNTAX UtilizationEntry
	MAX-ACCESS not-accessible
	STATUS current
	DESCRIPTION
		""
	INDEX { utilizationPortIndex }
	::= { utilizationTable 1 }


	UtilizationEntry ::= SEQUENCE {
	utilizationPortIndex INTEGER,
	utilizationIngressNow Integer32 ,
	utilizationIngress30s Integer32 ,
	utilizationIngress5min Integer32 ,
	utilizationEgressNow Integer32 ,
	utilizationEgress30s Integer32 ,
	utilizationEgress5min Integer32
	}

utilizationPortIndex	OBJECT-TYPE
	SYNTAX INTEGER (0..31)
	MAX-ACCESS not-accessible
	STATUS current
	DESCRIPTION
		"Automatically generated"
	::= { utilizationEntry 1 }

utilizationIngressNow OBJECT-TYPE   -- ingress_now
	SYNTAX Integer32 (0..255)
	MAX-ACCESS read-only
	STATUS current
	DESCRIPTION
	"Percentage of received utilization in the last second."
	::= { utilizationEntry 2 }

utilizationIngress30s OBJECT-TYPE   -- ingress_30s
	SYNTAX Integer32 (0..255)
	MAX-ACCESS read-only
	STATUS current
	DESCRIPTION
	"Percentage of received utilization averaged over last 30s."
	::= { utilizationEntry 3 }

utilizationIngress5min OBJECT-TYPE   -- ingress_5min
	SYNTAX Integer32 (0..255)
	MAX-ACCESS read-only
	STATUS current
	DESCRIPTION
	"Percentage of received utilization averaged over last 5 minutes."
	::= { utilizationEntry 4 }

utilizationEgressNow OBJECT-TYPE   -- egress_now
	SYNTAX Integer32 (0..255)
	MAX-ACCESS read-only
	STATUS current
	DESCRIPTION
	"Percentage of outgoing utilization in the last second."
	::= { utilizationEntry 5 }

utilizationEgress30s OBJECT-TYPE   -- egress_30s
	SYNTAX Integer32 (0..255)
	MAX-ACCESS read-only
	STATUS current
	DESCRIPTION
	"Percentage of outgoing utilization averaged over last 30s."
	::= { utilizationEntry 6 }

utilizationEgress5min OBJECT-TYPE   -- egress_5min
	SYNTAX Integer32 (0..255)
	MAX-ACCESS read-only
	STATUS current
	DESCRIPTION
	"Percentage of outgoing utilization averaged over last 5 minutes."
	::= { utilizationEntry 7 }


-- ********************* End of utilizationTable ***********************



END
