G6-NTP-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

ntp  OBJECT IDENTIFIER ::= { management 73 }



-- *************************** CONFIGURATION SECTION ********************************


ntpEnableNtp OBJECT-TYPE   -- enable_ntp
	SYNTAX INTEGER {  disabled(0), enabled(1) }
	MAX-ACCESS read-write
	STATUS current
	DESCRIPTION
	"When enabled the local clock will be synchronized with the time provided by a time server."
	::= { ntp 1 }


ntpSyncNow OBJECT-TYPE   -- sync_now
	SYNTAX DisplayString
	MAX-ACCESS read-write
	STATUS current
	DESCRIPTION
	"Action command to read time server now and setup the internal clock."
	::= { ntp 2 }


ntpDhcpProvidesNtpServer OBJECT-TYPE   -- dhcp_provides_ntp_server
	SYNTAX INTEGER {  disabled(0), enabled(1) }
	MAX-ACCESS read-write
	STATUS current
	DESCRIPTION
	"Enable DHCP to automatically retrieve NTP server address(es). When disabled, the locally defined addresses are used instead."
	::= { ntp 3 }


ntpMainNtpServer OBJECT-TYPE   -- main_ntp_server
	SYNTAX DisplayString
	MAX-ACCESS read-write
	STATUS current
	DESCRIPTION
	"This is the preferred NTP server address. IP address or symbolic name may be used."
	::= { ntp 4 }


ntpBackupNtpServer OBJECT-TYPE   -- backup_ntp_server
	SYNTAX DisplayString
	MAX-ACCESS read-write
	STATUS current
	DESCRIPTION
	"This defines an optional alternate ntp server address. IP address or symbolic name may be used."
	::= { ntp 5 }


ntpTrustedServer OBJECT-TYPE   -- trusted_server
	SYNTAX INTEGER {  disabled(0), enabled(1) }
	MAX-ACCESS read-write
	STATUS current
	DESCRIPTION
	"Some NTP server (Windows) indicate a too large deviation or indicate they are unreliable when they are not externally synchronized. To be able to still use such a server set this option to true."
	::= { ntp 6 }


ntpSyncInterval OBJECT-TYPE   -- sync_interval
	SYNTAX Integer32 (0..65535)
	MAX-ACCESS read-write
	STATUS current
	DESCRIPTION
	"Resynchronization interval (minutes), default once per day."
	::= { ntp 7 }


ntpShowTimeDate OBJECT-TYPE   -- show_time_date
	SYNTAX DisplayString
	MAX-ACCESS read-write
	STATUS current
	DESCRIPTION
	"Show system time and date."
	::= { ntp 8 }


ntpListTimeZones OBJECT-TYPE   -- list_time_zones
	SYNTAX DisplayString
	MAX-ACCESS read-write
	STATUS current
	DESCRIPTION
	"Displays a long list of available timezones. Pick the timezone that matches your location and use this name for the time_zone parameter."
	::= { ntp 9 }


ntpTimeZone OBJECT-TYPE   -- time_zone
	SYNTAX DisplayString
	MAX-ACCESS read-write
	STATUS current
	DESCRIPTION
	"Enter a string exactly as obtained via list_time_zones command. Note that a change of the time zone if only effective after a system reboot."
	::= { ntp 10 }


ntpTimeFormat OBJECT-TYPE   -- time_format
	SYNTAX DisplayString
	MAX-ACCESS read-write
	STATUS current
	DESCRIPTION
	"This parameter permits definition of the time format displayed under ntp.local_time. When left blank the default format hrs:min:sec is used. The parameter follows the Linux date command syntax. Please refer to external documentation for details. Use %k:%M for time without seconds. Use %P to add AM/PM where is applies. There are more options."
	::= { ntp 11 }


ntpDateFormat OBJECT-TYPE   -- date_format
	SYNTAX DisplayString
	MAX-ACCESS read-write
	STATUS current
	DESCRIPTION
	"This parameter permits definition of the data format displayed under ntp.local_date. When left blank the default format year-month-date is used. The parameter follows the Linux date command syntax. Please refer to external documentation for details. It is also possible to add weekday %A or month %B or week of year %V, etc."
	::= { ntp 12 }



-- ****************************** STATUS SECTION ********************************


ntpStatus OBJECT-TYPE   -- status
	SYNTAX INTEGER
		{
		unset (0),
		manuallySet (1),
		synchronized (2),
		syncFailed (4),
		dayLightSavingTime (16)
		}
	MAX-ACCESS read-only
	STATUS current
	DESCRIPTION
	"Indicates by which means the clock was last set. "
	::= { ntp 100 }


ntpLocalTime OBJECT-TYPE   -- local_time
	SYNTAX DisplayString
	MAX-ACCESS read-only
	STATUS current
	DESCRIPTION
	"Displays the current local date according to selected time zone in the format defined user ntp.time_format."
	::= { ntp 101 }


ntpLocalDate OBJECT-TYPE   -- local_date
	SYNTAX DisplayString
	MAX-ACCESS read-only
	STATUS current
	DESCRIPTION
	"Displays the current local date according to selected time zone in the format defined user ntp.date_format."
	::= { ntp 102 }


ntpUsedNtpServer OBJECT-TYPE   -- used_ntp_server
	SYNTAX DisplayString
	MAX-ACCESS read-only
	STATUS current
	DESCRIPTION
	"Actually used ntp server IP address or name"
	::= { ntp 103 }


ntpDynamicNtpServer1 OBJECT-TYPE   -- dynamic_ntp_server_1
	SYNTAX OCTET STRING (SIZE (0..20))
	MAX-ACCESS read-only
	STATUS current
	DESCRIPTION
	"Main dynamically assigned ntp server IP address."
	::= { ntp 104 }


ntpDynamicNtpServer2 OBJECT-TYPE   -- dynamic_ntp_server_2
	SYNTAX OCTET STRING (SIZE (0..20))
	MAX-ACCESS read-only
	STATUS current
	DESCRIPTION
	"Alternate dynamically assigned ntp server IP address."
	::= { ntp 105 }


ntpDynamicNtpServer3 OBJECT-TYPE   -- dynamic_ntp_server_3
	SYNTAX OCTET STRING (SIZE (0..20))
	MAX-ACCESS read-only
	STATUS current
	DESCRIPTION
	"Alternate dynamically assigned ntp server IP address."
	::= { ntp 106 }


ntpDynamicNtpServer4 OBJECT-TYPE   -- dynamic_ntp_server_4
	SYNTAX OCTET STRING (SIZE (0..20))
	MAX-ACCESS read-only
	STATUS current
	DESCRIPTION
	"Alternate dynamically assigned ntp server IP address."
	::= { ntp 107 }



END
