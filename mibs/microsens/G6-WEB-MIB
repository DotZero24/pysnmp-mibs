G6-WEB-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

web  OBJECT IDENTIFIER ::= { management 63 }



-- *************************** CONFIGURATION SECTION ********************************


webProtocol OBJECT-TYPE   -- protocol
	SYNTAX INTEGER
		{
		disabled (0),
		httpUnsecure (1),
		httpsSecure (2)
		}
	MAX-ACCESS read-write
	STATUS current
	DESCRIPTION
	"Define which web client access protocol is used"
	::= { web 1 }


webWebTimeout OBJECT-TYPE   -- web_timeout
	SYNTAX Integer32 (0..65535)
	MAX-ACCESS read-write
	STATUS current
	DESCRIPTION
	"Inactivity time out in seconds"
	::= { web 2 }


webHttpPortWeb OBJECT-TYPE   -- http_port_web
	SYNTAX Integer32 (0..65535)
	MAX-ACCESS read-write
	STATUS current
	DESCRIPTION
	"Port used for http protocol acccess. Standard port is 80. Can be changed when non-standard port shall be used for Web management traffic."
	::= { web 3 }


webHttpsPortWeb OBJECT-TYPE   -- https_port_web
	SYNTAX Integer32 (0..65535)
	MAX-ACCESS read-write
	STATUS current
	DESCRIPTION
	"Port used for https protocol acccess. Standard port is 443. Can be changed when non-standard port shall be used for Web management traffic."
	::= { web 4 }


webCertificateSource OBJECT-TYPE   -- certificate_source
	SYNTAX INTEGER
		{
		intern (0),
		custom (1)
		}
	MAX-ACCESS read-write
	STATUS current
	DESCRIPTION
	"Determines if internal default certificate is used or a customer downloaded certificate is used. The custom certificate needs to be specified after selecting the CUSTOM option using the Management.files.certificate.activate_for_web command."
	::= { web 5 }


webLoginMessage OBJECT-TYPE   -- login_message
	SYNTAX DisplayString
	MAX-ACCESS read-write
	STATUS current
	DESCRIPTION
	"This message is displayed during login to the management web server."
	::= { web 6 }


-- ******************* Begin of guiPageTable *************************

guiPageTable	OBJECT-TYPE
	SYNTAX SEQUENCE OF GuiPageEntry
	MAX-ACCESS not-accessible
	STATUS current
	DESCRIPTION
		"Define the look and feel of the SmartOffice graphical user interface."
	::= { web 7 }

guiPageEntry	OBJECT-TYPE
	SYNTAX GuiPageEntry
	MAX-ACCESS not-accessible
	STATUS current
	DESCRIPTION
		""
	INDEX { guiPageIndex }
	::= { guiPageTable 1 }


	GuiPageEntry ::= SEQUENCE {
	guiPageIndex INTEGER,
	guiPageName DisplayString,
	guiPageGuiMode INTEGER ,
	guiPageColorScheme INTEGER ,
	guiPageLimitedToUsers DisplayString,
	guiPageOptions DisplayString
	}

guiPageIndex	OBJECT-TYPE
	SYNTAX INTEGER (0..31)
	MAX-ACCESS not-accessible
	STATUS current
	DESCRIPTION
		"Automatically generated"
	::= { guiPageEntry 1 }

guiPageName OBJECT-TYPE   -- name
	SYNTAX DisplayString
	MAX-ACCESS read-write
	STATUS current
	DESCRIPTION
	"Unique name under which the page is reference a in the web gui."
	::= { guiPageEntry 2 }

guiPageGuiMode OBJECT-TYPE   -- gui_mode
	SYNTAX INTEGER
		{
		disabled (0),
		displayOnly (1),
		normal (2),
		remoteOnly (3)
		}
	MAX-ACCESS read-write
	STATUS current
	DESCRIPTION
	"Permits limiting of gui functionality for example in public places."
	::= { guiPageEntry 3 }

guiPageColorScheme OBJECT-TYPE   -- color_scheme
	SYNTAX INTEGER
		{
		gray (0),
		blue (1),
		red (2),
		lime (3),
		yellow (4),
		pink (5),
		cyan (6),
		green (7),
		orange (8),
		purple (9),
		teal (10)
		}
	MAX-ACCESS read-write
	STATUS current
	DESCRIPTION
	"Select desired look of the page. Different pages may use different color schemes even if the same elements are placed on them."
	::= { guiPageEntry 4 }

guiPageLimitedToUsers OBJECT-TYPE   -- limited_to_users
	SYNTAX DisplayString
	MAX-ACCESS read-write
	STATUS current
	DESCRIPTION
	"When left blank, every user has access to the gui page and its associated elements. When one or more comma separated user names are defined, then local or remote access to the page and its elements is limited to the listed users."
	::= { guiPageEntry 5 }

guiPageOptions OBJECT-TYPE   -- options
	SYNTAX DisplayString
	MAX-ACCESS read-write
	STATUS current
	DESCRIPTION
	"Optional additional parameter may be defined here is a comma separated list. Rendering options defined here, will be applied to all elements placed on the page, unless overridden with options defined at element level."
	::= { guiPageEntry 6 }


-- ********************* End of guiPageTable ***********************


-- ******************* Begin of guiElementTable *************************

guiElementTable	OBJECT-TYPE
	SYNTAX SEQUENCE OF GuiElementEntry
	MAX-ACCESS not-accessible
	STATUS current
	DESCRIPTION
		"Defines a single element of the user interface gui. Defines position as well as content and function."
	::= { web 8 }

guiElementEntry	OBJECT-TYPE
	SYNTAX GuiElementEntry
	MAX-ACCESS not-accessible
	STATUS current
	DESCRIPTION
		""
	INDEX { guiElementIndex }
	::= { guiElementTable 1 }


	GuiElementEntry ::= SEQUENCE {
	guiElementIndex INTEGER,
	guiElementName DisplayString,
	guiElementType INTEGER ,
	guiElementPage DisplayString,
	guiElementVisibility INTEGER ,
	guiElementAutoSave INTEGER ,
	guiElementRemoteAccessible INTEGER ,
	guiElementSensorAttribute DisplayString,
	guiElementScriptName DisplayString,
	guiElementWatchedElement DisplayString,
	guiElementOrder Unsigned32,
	guiElementHeight DisplayString,
	guiElementWidth DisplayString,
	guiElementTopMargin DisplayString,
	guiElementLeftMargin DisplayString,
	guiElementHeader DisplayString,
	guiElementText DisplayString,
	guiElementValue DisplayString,
	guiElementStartValue DisplayString,
	guiElementImage DisplayString,
	guiElementOptions DisplayString
	}

guiElementIndex	OBJECT-TYPE
	SYNTAX INTEGER (0..255)
	MAX-ACCESS not-accessible
	STATUS current
	DESCRIPTION
		"Automatically generated"
	::= { guiElementEntry 1 }

guiElementName OBJECT-TYPE   -- name
	SYNTAX DisplayString
	MAX-ACCESS read-write
	STATUS current
	DESCRIPTION
	"Unique name of the element."
	::= { guiElementEntry 2 }

guiElementType OBJECT-TYPE   -- type
	SYNTAX INTEGER
		{
		label (10),
		image (11),
		hyperLink (12),
		space (13),
		line (14),
		frame (15),
		button (30),
		selectBox (31),
		slider (32),
		radioButton (33),
		toggle (34),
		textBox (50),
		barGraph (51),
		gauge (52),
		symbol (53),
		diagram (54),
		input (55)
		}
	MAX-ACCESS read-write
	STATUS current
	DESCRIPTION
	"Predefined type of element. Choose to suit the functionality needed."
	::= { guiElementEntry 3 }

guiElementPage OBJECT-TYPE   -- page
	SYNTAX DisplayString
	MAX-ACCESS read-write
	STATUS current
	DESCRIPTION
	"Name of gui page(s) on which this element is placed on. Use comma to specify several pages."
	::= { guiElementEntry 4 }

guiElementVisibility OBJECT-TYPE   -- visibility
	SYNTAX INTEGER
		{
		normal (0),
		hidden (1),
		disabled (2)
		}
	MAX-ACCESS read-write
	STATUS current
	DESCRIPTION
	"Defines if an element is rendered on the gui."
	::= { guiElementEntry 5 }

guiElementAutoSave OBJECT-TYPE   -- auto_save
	SYNTAX INTEGER {  disabled(0), enabled(1) }
	MAX-ACCESS read-write
	STATUS current
	DESCRIPTION
	"When enabled, this gui element saves the current setting as the default value to be used should the system restart."
	::= { guiElementEntry 6 }

guiElementRemoteAccessible OBJECT-TYPE   -- remote_accessible
	SYNTAX INTEGER {  disabled(0), enabled(1) }
	MAX-ACCESS read-write
	STATUS current
	DESCRIPTION
	"When enabled, this gui element may be accessed via the the remote access interface. Use this parameter to restrict the remote interface to the required elements only."
	::= { guiElementEntry 7 }

guiElementSensorAttribute OBJECT-TYPE   -- sensor_attribute
	SYNTAX DisplayString
	MAX-ACCESS read-write
	STATUS current
	DESCRIPTION
	"Indicates which type of sensor this gui element simulates when being operated. If left blank the element will register with its type as default."
	::= { guiElementEntry 8 }

guiElementScriptName OBJECT-TYPE   -- script_name
	SYNTAX DisplayString
	MAX-ACCESS read-write
	STATUS current
	DESCRIPTION
	"When this element is updated the script specified in this parameter is executed. If the parameter is left blank, the standard MS_SmartOfficeControl.ms  script is executed. The specified script should not contain any time consuming functions."
	::= { guiElementEntry 9 }

guiElementWatchedElement OBJECT-TYPE   -- watched_element
	SYNTAX DisplayString
	MAX-ACCESS read-write
	STATUS current
	DESCRIPTION
	"Here a valid CLI command may be entered to display any system parameter. Status or config values may be specified. Alternatively, the content of a persistent variable may be watched. Such variables can be maintained by microScript. Syntax: $varname."
	::= { guiElementEntry 10 }

guiElementOrder OBJECT-TYPE   -- order
	SYNTAX Unsigned32
	MAX-ACCESS read-write
	STATUS current
	DESCRIPTION
	"Elements are displayed in this order. Elements with same index appear in the order they are configured. There may be gaps in the order of elements."
	::= { guiElementEntry 11 }

guiElementHeight OBJECT-TYPE   -- height
	SYNTAX DisplayString
	MAX-ACCESS read-write
	STATUS current
	DESCRIPTION
	"Height of element in percent of container height."
	::= { guiElementEntry 12 }

guiElementWidth OBJECT-TYPE   -- width
	SYNTAX DisplayString
	MAX-ACCESS read-write
	STATUS current
	DESCRIPTION
	"Width of element in percent of container width."
	::= { guiElementEntry 13 }

guiElementTopMargin OBJECT-TYPE   -- top_margin
	SYNTAX DisplayString
	MAX-ACCESS read-write
	STATUS current
	DESCRIPTION
	"Defines the distance of element in percent of container height below the above element. Can be used to position element in relation to others."
	::= { guiElementEntry 14 }

guiElementLeftMargin OBJECT-TYPE   -- left_margin
	SYNTAX DisplayString
	MAX-ACCESS read-write
	STATUS current
	DESCRIPTION
	"Defines the distance of element in percent of container width from the end of the previous element to the left. Can be used to position element in relation to others."
	::= { guiElementEntry 15 }

guiElementHeader OBJECT-TYPE   -- header
	SYNTAX DisplayString
	MAX-ACCESS read-write
	STATUS current
	DESCRIPTION
	"Title to be displayed above the element, doesn't preserve space if left empty."
	::= { guiElementEntry 16 }

guiElementText OBJECT-TYPE   -- text
	SYNTAX DisplayString
	MAX-ACCESS read-write
	STATUS current
	DESCRIPTION
	"Comma separated list of texts. Appearance depends on the type of element."
	::= { guiElementEntry 17 }

guiElementValue OBJECT-TYPE   -- value
	SYNTAX DisplayString
	MAX-ACCESS read-write
	STATUS current
	DESCRIPTION
	"Comma separated list of values. Usage depends on the type of element."
	::= { guiElementEntry 18 }

guiElementStartValue OBJECT-TYPE   -- start_value
	SYNTAX DisplayString
	MAX-ACCESS read-write
	STATUS current
	DESCRIPTION
	"Default or start value which is used when the element is first created. This value is automatically updated to reflect the last setting when the auto_save parameter is enabled. This value only applies to active elements."
	::= { guiElementEntry 19 }

guiElementImage OBJECT-TYPE   -- image
	SYNTAX DisplayString
	MAX-ACCESS read-write
	STATUS current
	DESCRIPTION
	"Comma separated list of images to display on the element."
	::= { guiElementEntry 20 }

guiElementOptions OBJECT-TYPE   -- options
	SYNTAX DisplayString
	MAX-ACCESS read-write
	STATUS current
	DESCRIPTION
	"Optional element specific additional parameter may be placed here."
	::= { guiElementEntry 21 }


-- ********************* End of guiElementTable ***********************



-- ****************************** STATUS SECTION ********************************



END
