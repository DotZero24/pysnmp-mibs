G6-SCRIPTDATA-MIB DEFINITIONS ::= BEGIN

IMPORTS
	MODULE-IDENTITY, OBJECT-TYPE, Integer32, Unsigned32, Counter32, enterprises,NOTIFICATION-TYPE
		FROM SNMPv2-SMI
	DisplayString, MacAddress
		FROM SNMPv2-TC
	g6	FROM MICROSENS-G6-MIB
	;

management MODULE-IDENTITY --Category
	LAST-UPDATED "201802121619Z"
	ORGANIZATION "MICROSENS GmbH & Co. KG"
	CONTACT-INFO
		"Kueferstrasse 16
		D-59067 Hamm
		Germany
		support@microsens.de
		http://www.microsens.de"
	DESCRIPTION
		"Microsens private MIB for Generation 6 Ethernet Switches"

	REVISION "201802121619Z"
	DESCRIPTION
		"File creation"
	::= { g6 3 }

scriptdata  OBJECT IDENTIFIER ::= { management 77 }



-- *************************** CONFIGURATION SECTION ********************************


-- ******************* Begin of parameterTable *************************

parameterTable	OBJECT-TYPE
	SYNTAX SEQUENCE OF ParameterEntry
	MAX-ACCESS not-accessible
	STATUS current
	DESCRIPTION
		"This table is used to define script specific configuration parameter. The parameter list is  created by scripts using the register parameter command."
	::= { scriptdata 1 }

parameterEntry	OBJECT-TYPE
	SYNTAX ParameterEntry
	MAX-ACCESS not-accessible
	STATUS current
	DESCRIPTION
		""
	INDEX { parameterIndex }
	::= { parameterTable 1 }


	ParameterEntry ::= SEQUENCE {
	parameterIndex INTEGER,
	parameterName DisplayString,
	parameterValue DisplayString
	}

parameterIndex	OBJECT-TYPE
	SYNTAX INTEGER (0..99)
	MAX-ACCESS not-accessible
	STATUS current
	DESCRIPTION
		"Automatically generated"
	::= { parameterEntry 1 }

parameterName OBJECT-TYPE   -- name
	SYNTAX DisplayString
	MAX-ACCESS read-write
	STATUS current
	DESCRIPTION
	"Unique script specific parameter name. At least 3 character are required. THIS NAME SHOULD NOT BE MODIFIED BY USERS."
	::= { parameterEntry 2 }

parameterValue OBJECT-TYPE   -- value
	SYNTAX DisplayString
	MAX-ACCESS read-write
	STATUS current
	DESCRIPTION
	"Customer entered parameter value. This may be a string or a number depending of the script requirement."
	::= { parameterEntry 3 }


-- ********************* End of parameterTable ***********************



-- ****************************** STATUS SECTION ********************************


-- ******************* Begin of variablesTable *************************

variablesTable	OBJECT-TYPE
	SYNTAX SEQUENCE OF VariablesEntry
	MAX-ACCESS not-accessible
	STATUS current
	DESCRIPTION
		"Array of string variables that can be written and read by scripts. Several scripts may share data in these variables. The variables may also be accessed via SNMP."
	::= { scriptdata 100 }

variablesEntry	OBJECT-TYPE
	SYNTAX VariablesEntry
	MAX-ACCESS not-accessible
	STATUS current
	DESCRIPTION
		""
	INDEX { variablesIndex }
	::= { variablesTable 1 }


	VariablesEntry ::= SEQUENCE {
	variablesIndex INTEGER,
	variablesName DisplayString,
	variablesValue DisplayString
	}

variablesIndex	OBJECT-TYPE
	SYNTAX INTEGER (0..99)
	MAX-ACCESS not-accessible
	STATUS current
	DESCRIPTION
		"Automatically generated"
	::= { variablesEntry 1 }

variablesName OBJECT-TYPE   -- name
	SYNTAX DisplayString
	MAX-ACCESS read-only
	STATUS current
	DESCRIPTION
	"Script specific variable name for programmatic output of string variables. Format scriptname/varname. When the /(slash) is missing this is a general script variable."
	::= { variablesEntry 2 }

variablesValue OBJECT-TYPE   -- value
	SYNTAX DisplayString
	MAX-ACCESS read-only
	STATUS current
	DESCRIPTION
	"The value can only be written via script."
	::= { variablesEntry 3 }


-- ********************* End of variablesTable ***********************



END
