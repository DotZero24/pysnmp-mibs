TERADICI-PCOIPv2-MIB DEFINITIONS ::= BEGIN

    IMPORTS
        MODULE-IDENTITY,
        OBJECT-TYPE,
        OBJECT-IDENTITY,
        Integer32,
        Counter32,
        Counter64
           FROM SNMPv2-SMI

        enterprises
            FROM RFC1155-SMI;

teraMibModule MODULE-IDENTITY
    LAST-UPDATED "201201281000Z"
    ORGANIZATION "Teradici Corporation"
    CONTACT-INFO
        "       Chris Topp

        Postal: 101-4621 Canada Way
        Burnaby, BC  V5G 4X8
        Canada

        Tel: +1 604 451 5800
        Fax: +1 604 451 5818

        E-mail: ctopp@teradici.com"

    DESCRIPTION "MIB describing PC-over-IP (tm) statistics."
    REVISION "201201281000Z"    -- 28 January, 2012
    DESCRIPTION "Version 2 of the PCoIP MIB."

    ::= { enterprises 25071 }

    teraProducts            OBJECT IDENTIFIER ::= { teraMibModule 1 }
    teraPcoipV2             OBJECT IDENTIFIER ::= { teraProducts 2 }

    teraPcoipGenStats       OBJECT IDENTIFIER ::= { teraPcoipV2 1 }
    teraPcoipNetStats       OBJECT IDENTIFIER ::= { teraPcoipV2 2 }
    teraPcoipAudioStats     OBJECT IDENTIFIER ::= { teraPcoipV2 3 }
    teraPcoipImagingStats   OBJECT IDENTIFIER ::= { teraPcoipV2 4 }
    teraPcoipUSBStats       OBJECT IDENTIFIER ::= { teraPcoipV2 5 }
    teraPcoipGenDevices     OBJECT IDENTIFIER ::= { teraPcoipV2 6 }
    teraPcoipImagingDevices OBJECT IDENTIFIER ::= { teraPcoipV2 7 }
    teraPcoipUSBDevices     OBJECT IDENTIFIER ::= { teraPcoipV2 8 }

-- Teradici PCoIP General Statistics Definitions
    pcoipGenStatsTable OBJECT-TYPE
        SYNTAX      SEQUENCE OF PcoipGenStatsEntry
        MAX-ACCESS  not-accessible
        STATUS      current
        DESCRIPTION "The PCoIP General statistics table."
            ::= { teraPcoipGenStats 1 }

    pcoipGenStatsEntry OBJECT-TYPE
        SYNTAX      PcoipGenStatsEntry
        MAX-ACCESS  not-accessible
        STATUS      current
        DESCRIPTION "An entry in the PCoIP general statistics table."
        INDEX   { pcoipGenStatsSessionNumber }
            ::= { pcoipGenStatsTable 1 }

    PcoipGenStatsEntry ::=
        SEQUENCE {
            pcoipGenStatsSessionNumber          Integer32,
            pcoipGenStatsPacketsSent            Counter64,
            pcoipGenStatsBytesSent              Counter64,
            pcoipGenStatsPacketsReceived        Counter64,
            pcoipGenStatsBytesReceived          Counter64,
            pcoipGenStatsTxPacketsLost          Counter64,
            pcoipGenStatsSessionDuration        Counter64
        }

   pcoipGenStatsSessionNumber OBJECT-TYPE
       SYNTAX      Integer32 (1..1) -- currently only one PCoIP session per target
       MAX-ACCESS  read-only
       STATUS      current
       DESCRIPTION
               "PCoIP session number used to link PCoIP statistics to session."
           ::= { pcoipGenStatsEntry 1 }

   pcoipGenStatsPacketsSent OBJECT-TYPE
       SYNTAX      Counter64
       MAX-ACCESS  read-only
       STATUS      current
       DESCRIPTION
               "Total number of packets that have been transmitted since the PCoIP session started."
           ::= { pcoipGenStatsEntry 2 }

   pcoipGenStatsBytesSent OBJECT-TYPE
       SYNTAX      Counter64
       MAX-ACCESS  read-only
       STATUS      current
       DESCRIPTION
               "Total number of bytes that have been transmitted since the PCoIP session started."
           ::= { pcoipGenStatsEntry 3 }

   pcoipGenStatsPacketsReceived OBJECT-TYPE
       SYNTAX      Counter64
       MAX-ACCESS  read-only
       STATUS      current
       DESCRIPTION
               "Total number of packets that have been received since the PCoIP session started."
           ::= { pcoipGenStatsEntry 4 }

   pcoipGenStatsBytesReceived OBJECT-TYPE
       SYNTAX      Counter64
       MAX-ACCESS  read-only
       STATUS      current
       DESCRIPTION
               "Total number of bytes that have been received since the PCoIP session started."
           ::= { pcoipGenStatsEntry 5 }

   pcoipGenStatsTxPacketsLost OBJECT-TYPE
       SYNTAX      Counter64
       MAX-ACCESS  read-only
       STATUS      current
       DESCRIPTION
               "Total number of transmit packets that have been lost since the PCoIP session started."
           ::= { pcoipGenStatsEntry 6 }

   pcoipGenStatsSessionDuration OBJECT-TYPE
       SYNTAX      Counter64
       MAX-ACCESS  read-only
       STATUS      current
       DESCRIPTION
               "An incrementing number that represents the total number of seconds the PCoIP session has been open."
           ::= { pcoipGenStatsEntry 7 }

-- Teradici PCoIP Session Network Statistics Definitions
    pcoipNetStatsTable OBJECT-TYPE
        SYNTAX      SEQUENCE OF PcoipNetStatsEntry
        MAX-ACCESS  not-accessible
        STATUS      current
        DESCRIPTION "The PCoIP Network statistics table."
            ::= { teraPcoipNetStats 1 }

    pcoipNetStatsEntry OBJECT-TYPE
        SYNTAX      PcoipNetStatsEntry
        MAX-ACCESS  not-accessible
        STATUS      current
        DESCRIPTION "An entry in the PCoIP network statistics table."
        INDEX   { pcoipNetStatsSessionNumber }
            ::= { pcoipNetStatsTable 1 }

    PcoipNetStatsEntry ::=
        SEQUENCE {
            pcoipNetStatsSessionNumber               Integer32,
            pcoipNetStatsRoundTripLatencyMs          Counter64,
            pcoipNetStatsRXBWkbitPersec              Counter64,
            pcoipNetStatsRXBWPeakkbitPersec          Integer32,
            pcoipNetStatsRXPacketLossPercent         Integer32,
            pcoipNetStatsTXBWkbitPersec              Counter64,
            pcoipNetStatsTXBWActiveLimitkbitPersec   Integer32,
            pcoipNetStatsTXBWLimitkbitPersec         Integer32,
            pcoipNetStatsTXPacketLossPercent         Integer32
        }

    pcoipNetStatsSessionNumber      OBJECT-TYPE
       SYNTAX      Integer32 (1..1)
       MAX-ACCESS  read-only
       STATUS      current
       DESCRIPTION
           "PCoIP session number used to link statistics to session."
           ::={ pcoipNetStatsEntry 1 }

    pcoipNetStatsRoundTripLatencyMs OBJECT-TYPE
       SYNTAX      Counter64
       MAX-ACCESS  read-only
       STATUS      current
       DESCRIPTION "Round trip latency (in milliseconds) between server and client."
           ::={ pcoipNetStatsEntry 2 }

    pcoipNetStatsRXBWkbitPersec    OBJECT-TYPE
       SYNTAX      Counter64
       MAX-ACCESS  read-only
       STATUS      current
       DESCRIPTION "Average number of kilobits per second that have been received by this device."
           ::={ pcoipNetStatsEntry 3 }

    pcoipNetStatsRXBWPeakkbitPersec OBJECT-TYPE
       SYNTAX      Integer32       (0..1000)
       MAX-ACCESS  read-only
       STATUS      current
       DESCRIPTION "Peak bandwidth for incoming PCoIP packets within a one second sampling period."
           ::={ pcoipNetStatsEntry 4 }

    pcoipNetStatsRXPacketLossPercent OBJECT-TYPE
       SYNTAX      Integer32       (0..100)
       MAX-ACCESS  read-only
       STATUS      current
       DESCRIPTION "Percentage of received packets lost during a one second sampling period."
           ::={ pcoipNetStatsEntry 5 }

    pcoipNetStatsTXBWkbitPersec    OBJECT-TYPE
       SYNTAX         Counter64
       MAX-ACCESS  read-only
       STATUS      current
       DESCRIPTION "Average number of kilobits per second that have been transmitted by this device."
           ::={ pcoipNetStatsEntry 6 }

    pcoipNetStatsTXBWActiveLimitkbitPersec  OBJECT-TYPE
       SYNTAX      Integer32       (0..1000)
       MAX-ACCESS  read-only
       STATUS      current
       DESCRIPTION "The current estimate of the available network bandwidth, updated every second."
           ::={ pcoipNetStatsEntry 7 }

    pcoipNetStatsTXBWLimitkbitPersec OBJECT-TYPE
       SYNTAX      Integer32       (0..1000)
       MAX-ACCESS  read-only
       STATUS      current
       DESCRIPTION "Transmit bandwidth limit for outgoing packets."
           ::={ pcoipNetStatsEntry 8 }

    pcoipNetStatsTXPacketLossPercent OBJECT-TYPE
       SYNTAX      Integer32       (0..100)
       MAX-ACCESS  read-only
       STATUS      current
       DESCRIPTION "Percentage of transmitted packets lost during the one second sampling period."
           ::={ pcoipNetStatsEntry 9 }

-- Terdici PCoIP Session Audio Statistics Definitions
    pcoipAudioStatsTable OBJECT-TYPE
        SYNTAX      SEQUENCE OF PcoipAudioStatsEntry
        MAX-ACCESS  not-accessible
        STATUS      current
        DESCRIPTION "The PCoIP Audio statistics table."
            ::= { teraPcoipAudioStats 1 }

    pcoipAudioStatsEntry OBJECT-TYPE
        SYNTAX      PcoipAudioStatsEntry
        MAX-ACCESS  not-accessible
        STATUS      current
        DESCRIPTION "An entry in the PCoIP audio statistics table."
        INDEX   { pcoipAudioStatsSessionNumber }
            ::= { pcoipAudioStatsTable 1 }

    PcoipAudioStatsEntry ::=
        SEQUENCE {
            pcoipAudioStatsSessionNumber         Integer32,
            pcoipAudioStatsBytesReceived         Counter64,
            pcoipAudioStatsBytesSent             Counter64,
            pcoipAudioStatsRXBWkbitPersec        Counter64,
            pcoipAudioStatsTXBWkbitPersec        Counter64,
            pcoipAudioStatsTXBWLimitkbitPersec   Integer32
        }

    pcoipAudioStatsSessionNumber   OBJECT-TYPE
       SYNTAX      Integer32       (1..1)
       MAX-ACCESS  read-only
       STATUS      current
       DESCRIPTION "PCoIP session number used to link statistics to session."
           ::={ pcoipAudioStatsEntry    1 }

    pcoipAudioStatsBytesReceived   OBJECT-TYPE
       SYNTAX      Counter64
       MAX-ACCESS  read-only
       STATUS      current
       DESCRIPTION "Total number of audio bytes that have been received since the PCoIP session started."
           ::={ pcoipAudioStatsEntry    2 }

    pcoipAudioStatsBytesSent OBJECT-TYPE
       SYNTAX      Counter64
       MAX-ACCESS  read-only
       STATUS      current
       DESCRIPTION "Total number of audio bytes that have been sent since the PCoIP session started."
           ::={ pcoipAudioStatsEntry    3 }

    pcoipAudioStatsRXBWkbitPersec  OBJECT-TYPE
       SYNTAX      Counter64
       MAX-ACCESS  read-only
       STATUS      current
       DESCRIPTION "Average number of kilobits per second that have been received by the audio channel of this device."
           ::={ pcoipAudioStatsEntry    4 }

    pcoipAudioStatsTXBWkbitPersec  OBJECT-TYPE
       SYNTAX      Counter64
       MAX-ACCESS  read-only
       STATUS      current
       DESCRIPTION "Total number of audio kilobits that have been transmitted since the PCoIP session started."
           ::={ pcoipAudioStatsEntry    5 }

    pcoipAudioStatsTXBWLimitkbitPersec     OBJECT-TYPE
       SYNTAX      Integer32       (0..1000)
       MAX-ACCESS  read-only
       STATUS      current
       DESCRIPTION "Transmit bandwidth limit for outgoing audio packets."
           ::={ pcoipAudioStatsEntry    6 }

--- Teradici PCoIP Session Imaging Statistics Definitions
    pcoipImagingStatsTable OBJECT-TYPE
        SYNTAX      SEQUENCE OF PcoipImagingStatsEntry
        MAX-ACCESS  not-accessible
        STATUS      current
        DESCRIPTION "The PCoIP Imaging statistics table."
            ::= { teraPcoipImagingStats 1 }

    pcoipImagingStatsEntry OBJECT-TYPE
        SYNTAX      PcoipImagingStatsEntry
        MAX-ACCESS  not-accessible
        STATUS      current
        DESCRIPTION "An entry in the PCoIP imaging statistics table."
        INDEX   { pcoipImagingStatsSessionNumber }
            ::= { pcoipImagingStatsTable 1 }

    PcoipImagingStatsEntry ::=
        SEQUENCE {
            pcoipImagingStatsSessionNumber                 Integer32,
            pcoipImagingStatsBytesReceived                 Counter64,
            pcoipImagingStatsBytesSent                     Counter64,
            pcoipImagingStatsRXBWkbitPersec                Counter64,
            pcoipImagingStatsTXBWkbitPersec                Counter64,
            pcoipImagingStatsEncodedFramesPersec           Integer32,
            pcoipImagingStatsActiveMinimumQuality          Integer32,
            pcoipImagingStatsDecoderCapabilitykbitPersec   Integer32,
            pcoipImagingStatsPipelineProcRate              Integer32
        }

    pcoipImagingStatsSessionNumber  OBJECT-TYPE
       SYNTAX      Integer32       (1..1)
       MAX-ACCESS  read-only
       STATUS      current
       DESCRIPTION "PCoIP session number used to link statistics to session."
           ::={ pcoipImagingStatsEntry  1 }

    pcoipImagingStatsBytesReceived  OBJECT-TYPE
       SYNTAX      Counter64
       MAX-ACCESS  read-only
       STATUS      current
       DESCRIPTION "Total number of imaging bytes that have been received since the PCoIP session started."
           ::={ pcoipImagingStatsEntry  2 }

    pcoipImagingStatsBytesSent     OBJECT-TYPE
       SYNTAX      Counter64
       MAX-ACCESS  read-only
       STATUS      current
       DESCRIPTION "Total number of imaging bytes that have been sent since the PCoIP session started."
           ::={ pcoipImagingStatsEntry  3 }

    pcoipImagingStatsRXBWkbitPersec OBJECT-TYPE
       SYNTAX      Counter64
       MAX-ACCESS  read-only
       STATUS      current
       DESCRIPTION "Average number of kilobits per second that have been received by the imaging channel of this device."
           ::={ pcoipImagingStatsEntry  4 }

    pcoipImagingStatsTXBWkbitPersec OBJECT-TYPE
       SYNTAX      Counter64
       MAX-ACCESS  read-only
       STATUS      current
       DESCRIPTION "Average number of kilobits per second that have been received by the imaging channel of this device."
           ::={ pcoipImagingStatsEntry  5 }

    pcoipImagingStatsEncodedFramesPersec   OBJECT-TYPE
       SYNTAX      Integer32       (0..2400)
       MAX-ACCESS  read-only
       STATUS      current
       DESCRIPTION "The number of imaging frames which were encoded over a one second sampling period."
           ::={ pcoipImagingStatsEntry  6 }

    pcoipImagingStatsActiveMinimumQuality  OBJECT-TYPE
       SYNTAX      Integer32       (0..100)
       MAX-ACCESS  read-only
       STATUS      current
       DESCRIPTION "The lowest encoded quality, updated every second."
           ::={ pcoipImagingStatsEntry  7 }

    pcoipImagingStatsDecoderCapabilitykbitPersec   OBJECT-TYPE
       SYNTAX      Integer32       (0..100000)
       MAX-ACCESS  read-only
       STATUS      current
       DESCRIPTION "The current estimate of the decoder processing capability."
           ::={ pcoipImagingStatsEntry  8 }

    pcoipImagingStatsPipelineProcRate      OBJECT-TYPE
       SYNTAX      Integer32       (0..300)
       MAX-ACCESS  read-only
       STATUS      current
       DESCRIPTION "The current pipeline processing rate."
           ::={ pcoipImagingStatsEntry  9 }

-- Teradici PCoIP Session USB Statistics Definitions
    pcoipUSBStatsTable OBJECT-TYPE
        SYNTAX      SEQUENCE OF PcoipUSBStatsEntry
        MAX-ACCESS  not-accessible
        STATUS      current
        DESCRIPTION "The PCoIP USB statistics table."
            ::= { teraPcoipUSBStats 1 }

    pcoipUSBStatsEntry OBJECT-TYPE
        SYNTAX      PcoipUSBStatsEntry
        MAX-ACCESS  not-accessible
        STATUS      current
        DESCRIPTION "An entry in the PCoIP USB statistics table."
        INDEX   { pcoipUSBStatsSessionNumber }
            ::= { pcoipUSBStatsTable 1 }

    PcoipUSBStatsEntry ::=
        SEQUENCE {
            pcoipUSBStatsSessionNumber  Integer32,
            pcoipUSBStatsBytesReceived  Counter64,
            pcoipUSBStatsBytesSent      Counter64,
            pcoipUSBStatsRXBWkbitPersec Counter64,
            pcoipUSBStatsTXBWkbitPersec Counter64
        }

    pcoipUSBStatsSessionNumber     OBJECT-TYPE
       SYNTAX      Integer32       (1..1)
       MAX-ACCESS  read-only
       STATUS      current
       DESCRIPTION "PCoIP session number used to link statistics to session."
           ::={ pcoipUSBStatsEntry 1 }

    pcoipUSBStatsBytesReceived     OBJECT-TYPE
       SYNTAX      Counter64
       MAX-ACCESS  read-only
       STATUS      current
       DESCRIPTION "Total number of USB bytes that have been received since the PCoIP session started."
           ::={ pcoipUSBStatsEntry 2 }

    pcoipUSBStatsBytesSent  OBJECT-TYPE
       SYNTAX      Counter64
       MAX-ACCESS  read-only
       STATUS      current
       DESCRIPTION "Total number of USB bytes that have been sent since the PCoIP session started."
           ::={ pcoipUSBStatsEntry 3 }

    pcoipUSBStatsRXBWkbitPersec    OBJECT-TYPE
       SYNTAX      Counter64
       MAX-ACCESS  read-only
       STATUS      current
       DESCRIPTION "Average number of kilobits per second that have been received by the USB channel of this device."
           ::={ pcoipUSBStatsEntry 4 }

    pcoipUSBStatsTXBWkbitPersec    OBJECT-TYPE
       SYNTAX      Counter64
       MAX-ACCESS  read-only
       STATUS      current
       DESCRIPTION "Average number of kilobits per second that have been received by the USB channel of this device."
           ::={ pcoipUSBStatsEntry 5 }

-- Teradici PCoIP General Devices Definitions
    pcoipGenDevicesTable OBJECT-TYPE
        SYNTAX      SEQUENCE OF PcoipGenDevicesEntry
        MAX-ACCESS  not-accessible
        STATUS      current
        DESCRIPTION "The PCoIP General Devices table."
            ::= { teraPcoipGenDevices 1 }

    pcoipGenDevicesEntry OBJECT-TYPE
        SYNTAX      PcoipGenDevicesEntry
        MAX-ACCESS  not-accessible
        STATUS      current
        DESCRIPTION "An entry in the PCoIP general devices table."
        INDEX   { pcoipGenDevicesSessionNumber }
            ::= { pcoipGenDevicesTable 1 }

    PcoipGenDevicesEntry ::=
        SEQUENCE {
            pcoipGenDevicesSessionNumber        Integer32,
            pcoipGenDevicesName                 OCTET STRING,
            pcoipGenDevicesDescription          OCTET STRING,
            pcoipGenDevicesGenericTag           OCTET STRING,
            pcoipGenDevicesPartNumber           OCTET STRING,
            pcoipGenDevicesSerialNumber         OCTET STRING,
            pcoipGenDevicesHardwareVersion      OCTET STRING,
            pcoipGenDevicesFirmwareVersion      OCTET STRING,
            pcoipGenDevicesUniqueID             OCTET STRING,
            pcoipGenDevicesMAC                  OCTET STRING,
            pcoipGenDevicesUptime               Counter64
        }

    pcoipGenDevicesSessionNumber OBJECT-TYPE
       SYNTAX      Integer32    (1..1)
       MAX-ACCESS  read-only
       STATUS      current
       DESCRIPTION "PCoIP session number used to link imaging devices to statistics."
           ::={ pcoipGenDevicesEntry 1 }

    pcoipGenDevicesName OBJECT-TYPE
       SYNTAX      OCTET STRING
       MAX-ACCESS  read-only
       STATUS      current
       DESCRIPTION "String containing the PCoIP device name."
           ::={ pcoipGenDevicesEntry 2 }

    pcoipGenDevicesDescription OBJECT-TYPE
       SYNTAX      OCTET STRING
       MAX-ACCESS  read-only
       STATUS      current
       DESCRIPTION "String describing the processor."
           ::={ pcoipGenDevicesEntry 3 }

    pcoipGenDevicesGenericTag OBJECT-TYPE
       SYNTAX      OCTET STRING
       MAX-ACCESS  read-only
       STATUS      current
       DESCRIPTION "String describing device generic tag. "
           ::={ pcoipGenDevicesEntry 4 }

    pcoipGenDevicesPartNumber OBJECT-TYPE
       SYNTAX      OCTET STRING
       MAX-ACCESS  read-only
       STATUS      current
       DESCRIPTION "String describing the silicon part number of the device."
           ::={ pcoipGenDevicesEntry 5 }

    pcoipGenDevicesFwPartNumber OBJECT-TYPE
       SYNTAX      OCTET STRING
       MAX-ACCESS  read-only
       STATUS      current
       DESCRIPTION "String describing the product ID of the device."
           ::={ pcoipGenDevicesEntry 6 }

    pcoipGenDevicesSerialNumber OBJECT-TYPE
       SYNTAX      OCTET STRING
       MAX-ACCESS  read-only
       STATUS      current
       DESCRIPTION "String describing device serial number."
           ::={ pcoipGenDevicesEntry 7 }

    pcoipGenDevicesHardwareVersion OBJECT-TYPE
       SYNTAX      OCTET STRING
       MAX-ACCESS  read-only
       STATUS      current
       DESCRIPTION "String describing the silicon version."
           ::={ pcoipGenDevicesEntry 8 }

    pcoipGenDevicesFirmwareVersion OBJECT-TYPE
       SYNTAX      OCTET STRING
       MAX-ACCESS  read-only
       STATUS      current
       DESCRIPTION "String describing the currently running firmware revision."
           ::={ pcoipGenDevicesEntry 9 }

    pcoipGenDevicesUniqueID OBJECT-TYPE
       SYNTAX      OCTET STRING
       MAX-ACCESS  read-only
       STATUS      current
       DESCRIPTION "String describing the device unique identifier."
           ::={ pcoipGenDevicesEntry 10 }

    pcoipGenDevicesMAC OBJECT-TYPE
       SYNTAX      OCTET STRING
       MAX-ACCESS  read-only
       STATUS      current
       DESCRIPTION "String describing the device MAC address."
           ::={ pcoipGenDevicesEntry 11 }

    pcoipGenDevicesUptime OBJECT-TYPE
       SYNTAX      Counter64
       MAX-ACCESS  read-only
       STATUS      current
       DESCRIPTION "Integer containing the number of seconds since boot."
           ::={ pcoipGenDevicesEntry 12 }

-- Teradici PCoIP Imaging Devices Definitions
    pcoipImagingDevicesTable OBJECT-TYPE
        SYNTAX      SEQUENCE OF PcoipImagingDevicesEntry
        MAX-ACCESS  not-accessible
        STATUS      current
        DESCRIPTION "The PCoIP Imaging Devices table."
            ::= { teraPcoipImagingDevices 1 }

    pcoipImagingDevicesEntry OBJECT-TYPE
        SYNTAX      PcoipImagingDevicesEntry
        MAX-ACCESS  not-accessible
        STATUS      current
        DESCRIPTION "An entry in the PCoIP imaging devices table."
        INDEX   { pcoipImagingDevicesIndex }
            ::= { pcoipImagingDevicesTable 1 }

    PcoipImagingDevicesEntry ::=
        SEQUENCE {
            pcoipImagingDevicesIndex               Integer32,
            pcoipImagingDevicesSessionNumber       Integer32,
            pcoipImagingDevicesDisplayWidth        Integer32,
            pcoipImagingDevicesDisplayHeight       Integer32,
            pcoipImagingDevicesDisplayRefreshRate  Integer32,
            pcoipImagingDevicesDisplayRefreshRate  Integer32,
            pcoipImagingDevicesDisplayChangeRate   Integer32,
            pcoipImagingDevicesDisplayProcessRate  Integer32,
            pcoipImagingDevicesLimitReason         OCTET STRING,
            pcoipImagingDevicesModel               OCTET STRING,
            pcoipImagingDevicesStatus              OCTET STRING,
            pcoipImagingDevicesMode                OCTET STRING,
            pcoipImagingDevicesSerial              OCTET STRING,
            pcoipImagingDevicesVID                 OCTET STRING,
            pcoipImagingDevicesPID                 OCTET STRING,
            pcoipImagingDevicesDate                OCTET STRING
                }

    pcoipImagingDevicesIndex OBJECT-TYPE
       SYNTAX      Integer32       (1..4)
       MAX-ACCESS  read-only
       STATUS      current
       DESCRIPTION "The auxiliary variable used for identifying instances of the columnar objects in the devices table."
           ::={ pcoipImagingDevicesEntry 1 }

    pcoipImagingDevicesSessionNumber OBJECT-TYPE
       SYNTAX      Integer32       (1..1)
       MAX-ACCESS  read-only
       STATUS      current
       DESCRIPTION "PCoIP session number used to link imaging devices to statistics."
           ::={ pcoipImagingDevicesEntry 2 }

    pcoipImagingDevicesDisplayWidth OBJECT-TYPE
       SYNTAX      Integer32       (0..4096)
       MAX-ACCESS  read-only
       STATUS      current
       DESCRIPTION "Display width in pixels."
           ::={ pcoipImagingDevicesEntry 3 }

    pcoipImagingDevicesDisplayHeight OBJECT-TYPE
       SYNTAX      Integer32       (0..4096)
       MAX-ACCESS  read-only
       STATUS      current
       DESCRIPTION "Display height in lines."
           ::={ pcoipImagingDevicesEntry 4 }

    pcoipImagingDevicesDisplayRefreshRate  OBJECT-TYPE
       SYNTAX      Integer32       (0..600)
       MAX-ACCESS  read-only
       STATUS      current
       DESCRIPTION "Display refresh rate in Hz."
           ::={ pcoipImagingDevicesEntry 5 }

    pcoipImagingDevicesDisplayChangeRate  OBJECT-TYPE
       SYNTAX      Integer32       (0..600)
       MAX-ACCESS  read-only
       STATUS      current
       DESCRIPTION "Display input change rate in Hz over a 1 second sample."
           ::={ pcoipImagingDevicesEntry 6 }

    pcoipImagingDevicesDisplayProcessRate  OBJECT-TYPE
       SYNTAX      Integer32       (0..600)
       MAX-ACCESS  read-only
       STATUS      current
       DESCRIPTION "Display process frame rate in Hz over a 1 second sample."
           ::={ pcoipImagingDevicesEntry 7 }

    pcoipImagingDevicesLimitReason      OBJECT-TYPE
       SYNTAX      OCTET STRING
       MAX-ACCESS  read-only
       STATUS      current
       DESCRIPTION "String describing the reason for limiting the frame rate of this display."
           ::={ pcoipImagingDevicesEntry 8 }

    pcoipImagingDevicesModel      OBJECT-TYPE
       SYNTAX      OCTET STRING
       MAX-ACCESS  read-only
       STATUS      current
       DESCRIPTION "String describing the display model name."
           ::={ pcoipImagingDevicesEntry 9 }

    pcoipImagingDevicesStatus      OBJECT-TYPE
       SYNTAX      OCTET STRING
       MAX-ACCESS  read-only
       STATUS      current
       DESCRIPTION "String describing the display device status."
           ::={ pcoipImagingDevicesEntry 10 }

    pcoipImagingDevicesMode      OBJECT-TYPE
       SYNTAX      OCTET STRING
       MAX-ACCESS  read-only
       STATUS      current
       DESCRIPTION "String describing the display mode."
           ::={ pcoipImagingDevicesEntry 11 }

    pcoipImagingDevicesSerial      OBJECT-TYPE
       SYNTAX      OCTET STRING
       MAX-ACCESS  read-only
       STATUS      current
       DESCRIPTION "String describing the display serial number."
           ::={ pcoipImagingDevicesEntry 12 }

    pcoipImagingDevicesVID      OBJECT-TYPE
       SYNTAX      OCTET STRING
       MAX-ACCESS  read-only
       STATUS      current
       DESCRIPTION "String describing the display vendor ID."
           ::={ pcoipImagingDevicesEntry 13 }

    pcoipImagingDevicesPID      OBJECT-TYPE
       SYNTAX      OCTET STRING
       MAX-ACCESS  read-only
       STATUS      current
       DESCRIPTION "String describing the display product ID."
           ::={ pcoipImagingDevicesEntry 14 }

    pcoipImagingDevicesDate      OBJECT-TYPE
       SYNTAX      OCTET STRING
       MAX-ACCESS  read-only
       STATUS      current
       DESCRIPTION "String describing the display date of manufacture."
           ::={ pcoipImagingDevicesEntry 15 }

-- Teradici PCoIP USB Devices  Definitions
    pcoipUSBDevicesTable OBJECT-TYPE
        SYNTAX      SEQUENCE OF PcoipUSBDevicesEntry
        MAX-ACCESS  not-accessible
        STATUS      current
        DESCRIPTION "The PCoIP USB Devices table."
            ::= { teraPcoipUSBDevices 1 }

    pcoipUSBDevicesEntry OBJECT-TYPE
        SYNTAX      PcoipUSBDevicesEntry
        MAX-ACCESS  not-accessible
        STATUS      current
        DESCRIPTION "An entry in the PCoIP USB devices table."
        INDEX   { pcoipUSBDevicesIndex }
            ::= { pcoipUSBDevicesTable 1 }

    PcoipUSBDevicesEntry ::=
        SEQUENCE {
            pcoipUSBDevicesIndex           Integer32,
            pcoipUSBDevicesSessionNumber   Integer32,
            pcoipUSBDevicesPort            OCTET STRING,
            pcoipUSBDevicesModel           OCTET STRING,
            pcoipUSBDevicesStatus          OCTET STRING,
            pcoipUSBDevicesDeviceClass     OCTET STRING,
            pcoipUSBDevicesSubClass        OCTET STRING,
            pcoipUSBDevicesProtocol        OCTET STRING,
            pcoipUSBDevicesSerial          OCTET STRING,
            pcoipUSBDevicesVID             OCTET STRING,
            pcoipUSBDevicesPID             OCTET STRING
        }

    pcoipUSBDevicesIndex   OBJECT-TYPE
       SYNTAX      Integer32       (1..127)
       MAX-ACCESS  read-only
       STATUS      current
       DESCRIPTION "The auxiliary variable used for identifying instances of the columnar objects in the devices table."
           ::={ pcoipUSBDevicesEntry    1 }

    pcoipUSBDevicesSessionNumber   OBJECT-TYPE
       SYNTAX      Integer32       (1..1)
       MAX-ACCESS  read-only
       STATUS      current
       DESCRIPTION "PCoIP session number used to link USB devices to statistics."
           ::={ pcoipUSBDevicesEntry    2 }

    pcoipUSBDevicesPort   OBJECT-TYPE
       SYNTAX      OCTET STRING
       MAX-ACCESS  read-only
       STATUS      current
       DESCRIPTION "USB device port: OHCI or EHCI."
           ::={ pcoipUSBDevicesEntry    3 }

    pcoipUSBDevicesModel   OBJECT-TYPE
       SYNTAX      OCTET STRING
       MAX-ACCESS  read-only
       STATUS      current
       DESCRIPTION "String describing the model name of the connected device."
           ::={ pcoipUSBDevicesEntry    4 }

    pcoipUSBDevicesStatus   OBJECT-TYPE
       SYNTAX      OCTET STRING
       MAX-ACCESS  read-only
       STATUS      current
       DESCRIPTION "String describing the USB device status."
           ::={ pcoipUSBDevicesEntry    5 }

    pcoipUSBDevicesDeviceClass   OBJECT-TYPE
       SYNTAX      OCTET STRING
       MAX-ACCESS  read-only
       STATUS      current
       DESCRIPTION "String describing the USB device class."
           ::={ pcoipUSBDevicesEntry    6 }

    pcoipUSBDevicesSubClass   OBJECT-TYPE
       SYNTAX      OCTET STRING
       MAX-ACCESS  read-only
       STATUS      current
       DESCRIPTION "String describing the USB sub device class."
           ::={ pcoipUSBDevicesEntry    7 }

    pcoipUSBDevicesProtocol   OBJECT-TYPE
       SYNTAX      OCTET STRING
       MAX-ACCESS  read-only
       STATUS      current
       DESCRIPTION "String describing the USB protocol used."
           ::={ pcoipUSBDevicesEntry    8 }

    pcoipUSBDevicesSerial   OBJECT-TYPE
       SYNTAX      OCTET STRING
       MAX-ACCESS  read-only
       STATUS      current
       DESCRIPTION "String describing the USB device serial number."
           ::={ pcoipUSBDevicesEntry    9 }

    pcoipUSBDevicesVID   OBJECT-TYPE
       SYNTAX      OCTET STRING
       MAX-ACCESS  read-only
       STATUS      current
       DESCRIPTION "String describing the USB device vendor ID."
           ::={ pcoipUSBDevicesEntry    10 }

    pcoipUSBDevicesPID   OBJECT-TYPE
       SYNTAX      OCTET STRING
       MAX-ACCESS  read-only
       STATUS      current
       DESCRIPTION "String describing the USB device product ID."
           ::={ pcoipUSBDevicesEntry    11 }

END
