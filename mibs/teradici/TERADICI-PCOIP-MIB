TERADICI-PCOIP-MIB DEFINITIONS ::= BEGIN

    IMPORTS
        MODULE-IDENTITY,
        OBJECT-TYPE,
        OBJECT-IDENTITY,
        Integer32,
        Counter32,
        Counter64
           FROM SNMPv2-SMI

        enterprises
            FROM RFC1155-SMI;

teraMibModule MODULE-IDENTITY
    LAST-UPDATED "200801281000Z"
    ORGANIZATION "Teradici Corporation"
    CONTACT-INFO
        "       Ken Unger

        Postal: 500-4400 Dominion St.
        Burnaby, BC  V5G 4G3
        Canada

        Tel: +1 604 451 5800
        Fax: +1 604 451 5818

        E-mail: kunger@teradici.com"

    DESCRIPTION
        "MIB describing PC-over-IP (tm) statistics."
    REVISION "200801281000Z"    -- 28 January, 2008
    DESCRIPTION
        "Original version of this MIB."

    ::= { enterprises 25071 }

    teraProducts            OBJECT IDENTIFIER ::= { teraMibModule 1 }
    teraPcoip               OBJECT IDENTIFIER ::= { teraProducts 1 }

    teraPcoipStatistics     OBJECT IDENTIFIER ::= { teraPcoip 1 }
    teraImagingStatistics   OBJECT IDENTIFIER ::= { teraPcoip 2 }

-- Teradici PCoIP Statistics Definitions
    pcoipStatisticsTable OBJECT-TYPE
        SYNTAX      SEQUENCE OF PcoipStatisticsEntry
        MAX-ACCESS  not-accessible
        STATUS      current
        DESCRIPTION
                "The (conceptual) PCoIP statistics table."
        ::= { teraPcoipStatistics 1 }

    pcoipStatisticsEntry OBJECT-TYPE
        SYNTAX      PcoipStatisticsEntry
        MAX-ACCESS  not-accessible
        STATUS      current
        DESCRIPTION
                "An entry (conceptual row) in the PCoIP statistics table."
        INDEX   { pcoipStatisticsIndex }
        ::= { pcoipStatisticsTable 1 }

    PcoipStatisticsEntry ::=
        SEQUENCE {
            pcoipStatisticsIndex                    Integer32,
            pcoipStatisticsSessionNumber            Integer32,
            pcoipStatisticsPcoipPacketsTransmitted  Counter64,
            pcoipStatisticsPcoipBytesTransmitted    Counter64,
            pcoipStatisticsPcoipPacketsReceived     Counter64,
            pcoipStatisticsPcoipBytesReceived       Counter64,
            pcoipStatisticsPcoipLostPackets         Counter64,
            pcoipStatisticsPcoipLatency             Integer32
        }

   pcoipStatisticsIndex OBJECT-TYPE
       SYNTAX      Integer32 (1..1) --only one PCoIP instance per target
       MAX-ACCESS  read-only
       STATUS      current
       DESCRIPTION
               "The auxiliary variable used for identifying instances of
               the columnar objects in the statistics table."
           ::= { pcoipStatisticsEntry 1 }

   pcoipStatisticsSessionNumber OBJECT-TYPE
       SYNTAX      Integer32 (1..1) --only one PCoIP session per target
       MAX-ACCESS  read-only
       STATUS      current
       DESCRIPTION
               "PCoIP session number used to link PCoIP statistics to imaging
               statistics."
           ::= { pcoipStatisticsEntry 2 }

   pcoipStatisticsPcoipPacketsTransmitted OBJECT-TYPE
       SYNTAX      Counter64
       MAX-ACCESS  read-only
       STATUS      current
       DESCRIPTION
               "PCoIP packets transmitted during the current or most recent
               session."
           ::= { pcoipStatisticsEntry 3 }

   pcoipStatisticsPcoipBytesTransmitted OBJECT-TYPE
       SYNTAX      Counter64
       MAX-ACCESS  read-only
       STATUS      current
       DESCRIPTION
               "PCoIP bytes transmitted during the current or most recent
               session."
           ::= { pcoipStatisticsEntry 4 }

   pcoipStatisticsPcoipPacketsReceived OBJECT-TYPE
       SYNTAX      Counter64
       MAX-ACCESS  read-only
       STATUS      current
       DESCRIPTION
               "PCoIP packets received during the current or most recent
               session."
           ::= { pcoipStatisticsEntry 5 }

   pcoipStatisticsPcoipBytesReceived OBJECT-TYPE
       SYNTAX      Counter64
       MAX-ACCESS  read-only
       STATUS      current
       DESCRIPTION
               "PCoIP bytes received during the current or most recent
               session."
           ::= { pcoipStatisticsEntry 6 }

   pcoipStatisticsPcoipLostPackets OBJECT-TYPE
       SYNTAX      Counter64
       MAX-ACCESS  read-only
       STATUS      current
       DESCRIPTION
               "Detected lost PCoIP during the current or most recent session."
           ::= { pcoipStatisticsEntry 7 }

   pcoipStatisticsPcoipLatency OBJECT-TYPE
       SYNTAX      Integer32 (0..2147483647)
       MAX-ACCESS  read-only
       STATUS      current
       DESCRIPTION
               "Measured PCoIP latency in ms."
           ::= { pcoipStatisticsEntry 8 }

-- Teradici Imaging Statistics Definitions
    imagingStatisticsTable OBJECT-TYPE
        SYNTAX      SEQUENCE OF ImagingStatisticsEntry
        MAX-ACCESS  not-accessible
        STATUS      current
        DESCRIPTION
                "The (conceptual) imaging statistics table."
        ::= { teraImagingStatistics 1 }

    imagingStatisticsEntry OBJECT-TYPE
        SYNTAX      ImagingStatisticsEntry
        MAX-ACCESS  not-accessible
        STATUS      current
        DESCRIPTION
                "An entry (conceptual row) in the imaging statistics table."
        INDEX   { imagingStatisticsIndex }
        ::= { imagingStatisticsTable 1 }

    ImagingStatisticsEntry ::=
        SEQUENCE {
            imagingStatisticsIndex                      Integer32,
            imagingStatisticsSessionNumber              Integer32,
            imagingStatisticsSessionActive              INTEGER,
            imagingStatisticsDisplayActive              INTEGER,
            imagingStatisticsDisplayWidth               Integer32,
            imagingStatisticsDisplayHeight              Integer32,
            imagingStatisticsDisplayRefreshRate         Integer32,
            imagingStatisticsFrameCount                 Counter64
        }

   imagingStatisticsIndex OBJECT-TYPE
       SYNTAX      Integer32 (1..2) --maximum two displays per PCoIP session
       MAX-ACCESS  read-only
       STATUS      current
       DESCRIPTION
               "The auxiliary variable used for identifying instances of
               the columnar objects in the statistics table."
           ::= { imagingStatisticsEntry 1 }

   imagingStatisticsSessionNumber OBJECT-TYPE
       SYNTAX      Integer32 (1..1) --only one PCoIP session per target
       MAX-ACCESS  read-only
       STATUS      current
       DESCRIPTION
               "PCoIP session number used to link imaging statistics to PCoIP
               statistics."
           ::= { imagingStatisticsEntry 2 }

   imagingStatisticsSessionActive OBJECT-TYPE
       SYNTAX      INTEGER { inActive(0), active(1) }
       MAX-ACCESS  read-only
       STATUS      current
       DESCRIPTION
               "Whether the imaging session is active or inactive."
           ::= { imagingStatisticsEntry 3 }

   imagingStatisticsDisplayActive OBJECT-TYPE
       SYNTAX      INTEGER { inActive(0), active(1) }
       MAX-ACCESS  read-only
       STATUS      current
       DESCRIPTION
               "Whether display is active or inactive."
           ::= { imagingStatisticsEntry 4 }

   imagingStatisticsDisplayWidth OBJECT-TYPE
       SYNTAX      Integer32 (0..1600)
       MAX-ACCESS  read-only
       STATUS      current
       DESCRIPTION
               "Number of pixels the display is wide."
           ::= { imagingStatisticsEntry 5 }

   imagingStatisticsDisplayHeight OBJECT-TYPE
       SYNTAX      Integer32 (0..1600)
       MAX-ACCESS  read-only
       STATUS      current
       DESCRIPTION
               "Number of pixels the display is tall."
           ::= { imagingStatisticsEntry 6 }

   imagingStatisticsDisplayRefreshRate OBJECT-TYPE
       SYNTAX      Integer32 (0..500)
       MAX-ACCESS  read-only
       STATUS      current
       DESCRIPTION
               "Display refresh rate in Hz"
           ::= { imagingStatisticsEntry 7 }

   imagingStatisticsFrameCount OBJECT-TYPE
       SYNTAX      Counter64
       MAX-ACCESS  read-only
       STATUS      current
       DESCRIPTION
               "Encoded frame count per display."
           ::= { imagingStatisticsEntry 8 }

END
