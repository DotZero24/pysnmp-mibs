ALCATEL-ENT1-AUTO-CONFIG-MIB DEFINITIONS ::= BEGIN

IMPORTS
        NOTIFICATION-TYPE,
        OBJECT-TYPE,
        OBJECT-IDENTITY,
        MODULE-IDENTITY,
        Counter32, Integer32, Unsigned32, Counter64
		FROM SNMPv2-SMI
	    OBJECT-GROUP, MODULE-COMPLIANCE, NOTIFICATION-GROUP
		FROM SNMPv2-CONF
	    RowStatus
		FROM SNMPv2-TC
	    softentIND1AutoConfig
		FROM ALCATEL-ENT1-BASE;

alaAUTOCONFIGMIB MODULE-IDENTITY
	LAST-UPDATED  "201205040000Z"
	ORGANIZATION  "Alcatel-Lucent"
	CONTACT-INFO
			"Please consult with the Customer Service to ensure the most appropriate
			version of this document is used with the products in question:

	Alcatel-Lucent, Enterprise Solutions Division
	(Formerly Alcatel Internetworking, Incorporated)
	26801 West Agoura Road
	Agoura Hills, CA  91301-5122
	United States Of America

	Telephone:
	North America  +1 800 995 2696
	Latin America  +1 877 919 9526
	Europe         +31 23 556 0100
	Asia           +65 394 7933
	All Other      +1 818 878 4507

	Electronic Mail:         support@ind.alcatel.com
	World Wide Web:          http://alcatel-lucent.com/wps/portal/enterprise
	File Transfer Protocol:  ftp://ftp.ind.alcatel.com/pub/products/mibs"

	DESCRIPTION
		"This module describes an authoritative enterprise-specific Simple
		Network Management Protocol (SNMP) Management Information Base (MIB):

		The right to make changes in specification and other information
		contained in this document without prior notice is reserved.

		No liability shall be assumed for any incidental, indirect, special, or
		consequential damages whatsoever arising from or related to this
		document or the information contained herein.

		Vendors, end-users, and other interested parties are granted
		non-exclusive license to use this specification in connection with
		management of the products for which it is intended to be used.

		Copyright (C) 1995-2008 Alcatel-Lucent, Incorporated
		ALL RIGHTS RESERVED WORLDWIDE"

    REVISION      "201205040000Z"
    DESCRIPTION
        "The latest version of this MIB Module."

::= { softentIND1AutoConfig 1}

-- xxxxxxxxxxxxxxxxxxxxxxxxxxxxxxxxxxxxxxxxxxxxxxxxxxxxxxxxxxxxxxxxx

alaAUTOCONFIGMIBNotifications	OBJECT IDENTIFIER ::= { alaAUTOCONFIGMIB 0 }

alaAUTOCONFIGMIBObjects OBJECT-IDENTITY
	STATUS 			current
	DESCRIPTION 	"Branch for AUTO-CONFIG sub-system managed objects."
::= { alaAUTOCONFIGMIB 1 }

alaAUTOCONFIGMIBConformance OBJECT-IDENTITY
	STATUS 			current
	DESCRIPTION 	"Branch for AUTO-CONFIG sub-system conformance information."
::= { alaAUTOCONFIGMIB 2 }

alaAUTOCONFIGMIBGroups OBJECT-IDENTITY
	  STATUS          current
        DESCRIPTION
                                "Branch for AUTO-CONFIG subsystem
                                units of conformance."
        ::= { alaAUTOCONFIGMIBConformance 1 }

alaAUTOCONFIGMIBCompliances OBJECT-IDENTITY
        STATUS          current
        DESCRIPTION
                                "Branch for AUTO-CONFIG subsystem
                                compliance statements."
        ::= { alaAUTOCONFIGMIBConformance 2 }


-- xxxxxxxxxxxxxxxxxxxxxxxxxxxxxxxxxxxxxxxxxxxxxxxxxxxxxxxxxxxxxxxxx

alaAUTOCONFIGGlobal  OBJECT	IDENTIFIER ::= { alaAUTOCONFIGMIBObjects 1 }

-- xxxxxxxxxxxxxxxxxxxxxxxxxxxxxxxxxxxxxxxxxxxxxxxxxxxxxxxxxxxxxxxxx


alaAutoConfigAbort OBJECT-TYPE
  SYNTAX     INTEGER {
				 yes(1),
 				 no(2)
				 }
  MAX-ACCESS  read-write
  STATUS      current
  DESCRIPTION "Abort Auto-Config on the device."
  DEFVAL      { no }
  ::= { alaAUTOCONFIGGlobal 1}

-- xxxxxxxxxxxxxxxxxxxxxxxxxxxxxxxxxxxxxxxxxxxxxxxxxxxxxxxxxxxxxxxxx

alaAUTOCONFIGNotificationObjects 	OBJECT	IDENTIFIER ::= {  alaAUTOCONFIGMIBObjects 2}

-- xxxxxxxxxxxxxxxxxxxxxxxxxxxxxxxxxxxxxxxxxxxxxxxxxxxxxxxxxxxxxxxxx
--
-- trap description
--
alaAutoConfigTrapsObj OBJECT IDENTIFIER ::= { alaAUTOCONFIGMIBObjects 3}

 -- Notifications

 alaAutoConfigTrap NOTIFICATION-TYPE
 OBJECTS  {
                 alaAutoConfigAutoFabricEnableTrap
          }

    STATUS        current
    DESCRIPTION
       " This trap is sent after sending msg to Auto Fabric..."
::= { alaAUTOCONFIGMIBNotifications 1 }

-- Notification Objects

alaAutoConfigAutoFabricEnableTrap OBJECT-TYPE
        SYNTAX  INTEGER
                {
                    yes(1),
                    no(2)
                }
    MAX-ACCESS  accessible-for-notify
    STATUS  current
    DESCRIPTION
            "This object specifies the threshold status of subnet utilization."
    ::= { alaAutoConfigTrapsObj 1 }


-- xxxxxxxxxxxxxxxxxxxxxxxxxxxxxxxxxxxxxxxxxxxxxxxxxxxxxxxxxxxxxxxxxxxxxxxxxxxx
-- Compliance
-- xxxxxxxxxxxxxxxxxxxxxxxxxxxxxxxxxxxxxxxxxxxxxxxxxxxxxxxxxxxxxxxxxxxxxxxxxxxx

alaAUTOCONFIGMIBCompliance MODULE-COMPLIANCE
        STATUS          current
        DESCRIPTION
                                "Compliance statement for AUTO-CONFIG"
        MODULE
                MANDATORY-GROUPS
                {
                        alaAUTOCONFIGNotificationGroup
                }
        ::= { alaAUTOCONFIGMIBCompliances 1 }


-- xxxxxxxxxxxxxxxxxxxxxxxxxxxxxxxxxxxxxxxxxxxxxxxxxxxxxxxxxxxxxxxxxxxxxxxxxxxx
-- Units of Conformance
-- xxxxxxxxxxxxxxxxxxxxxxxxxxxxxxxxxxxxxxxxxxxxxxxxxxxxxxxxxxxxxxxxxxxxxxxxxxxx

    alaAUTOCONFIGNotificationGroup NOTIFICATION-GROUP
        NOTIFICATIONS
        {
               alaAutoConfigTrap
        }
        STATUS  current
        DESCRIPTION
            "AUTO-CONFIG Notification Group."
        ::= { alaAUTOCONFIGMIBGroups 1 }

    alaAutoConfigGlobalGroup     OBJECT-GROUP
        OBJECTS  {
            alaAutoConfigAbort,
            alaAutoConfigAutoFabricEnableTrap
        }
        STATUS  current
        DESCRIPTION
            "AUTO-CONFIG global configuration Group."
        ::= { alaAUTOCONFIGMIBGroups 2 }

END
