ALCATEL-ENT1-EVENT-SCRIPTING-MIB DEFINITIONS ::= BEGIN

IMPORTS
        OBJECT-TYPE,
        MODULE-IDENTITY,
        OBJECT-IDENTITY,
        IpAddress,
        Integer32, Unsigned32,
        Counter32,
        NOTIFICATION-TYPE       FROM SNMPv2-SMI
        DateAndTime,
        RowStatus               FROM SNMPv2-TC
        SnmpAdminString         FROM SNMP-FRAMEWORK-MIB
        MODULE-COMPLIANCE,
        OBJECT-GROUP,
        NOTIFICATION-GROUP              FROM SNMPv2-CONF
        softentIND1EventScripting       FROM ALCATEL-ENT1-BASE
        InetAddressType, InetAddress    FROM INET-ADDRESS-MIB;


alcatelIND1EventScriptingMIB  MODULE-IDENTITY
        LAST-UPDATED  "201412030000Z"
        ORGANIZATION "Alcatel-Lucent"
        CONTACT-INFO
            "Please consult with Customer Service to ensure the most appropriate
             version of this document is used with the products in question:

                        Alcatel-Lucent, Enterprise Solutions Division
                       (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"
        DESCRIPTION
            "This module describes CLI Event Scripting Subsystem Managed Objects.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2014 Alcatel-Lucent
                             ALL RIGHTS RESERVED WORLDWIDE"

        ::= { softentIND1EventScripting 1 }


    alcatelIND1EventScriptingObjects OBJECT-IDENTITY
        STATUS current
        DESCRIPTION
            "Branch For CLI Event Scripting Subsystem Managed Objects."
        ::= { alcatelIND1EventScriptingMIB 1 }


    alcatelIND1EventScriptingMIBConformance OBJECT-IDENTITY
        STATUS current
        DESCRIPTION
            "Branch For Event Scripting Subsystem Conformance Information."
        ::= { alcatelIND1EventScriptingMIB 2 }


    alcatelIND1EventScriptingMIBGroups OBJECT-IDENTITY
        STATUS current
        DESCRIPTION
            "Branch For Event Scripting Subsystem Units Of Conformance."
        ::= { alcatelIND1EventScriptingMIBConformance 1 }


    alcatelIND1EventScriptingMIBCompliances OBJECT-IDENTITY
        STATUS current
        DESCRIPTION
            "Branch For SNMP Agent Subsystem Compliance Statements."
        ::= { alcatelIND1EventScriptingMIBConformance 2 }


--
--  Event action scripting description
--

alaEventActionGlobalConfigObjects OBJECT IDENTIFIER ::= { alcatelIND1EventScriptingObjects 1 }

alaEventActionGlobalScriptTimeLimit OBJECT-TYPE
        SYNTAX  Unsigned32 (30..600)
        MAX-ACCESS  read-write
        STATUS  current
        DESCRIPTION
                "The maximum amount of time (in seconds) a script
                will be allowed to run before being killed."
        DEFVAL { 60 }
        ::= { alaEventActionGlobalConfigObjects 1 }

alaEventActionTable  OBJECT-TYPE
        SYNTAX  SEQUENCE OF AlaEventActionEntry
        MAX-ACCESS  not-accessible
        STATUS  current
        DESCRIPTION
                "The trap python script configuration table."
        ::= { alaEventActionGlobalConfigObjects 2 }

alaEventActionEntry  OBJECT-TYPE
        SYNTAX  AlaEventActionEntry
        MAX-ACCESS  not-accessible
        STATUS  current
        DESCRIPTION
                "A trap Python action-script configuration entry."
        INDEX { alaEventActionType, alaEventActionName }
        ::= { alaEventActionTable 1 }

AlaEventActionEntry ::= SEQUENCE {
        alaEventActionType                  INTEGER,
        alaEventActionName                  SnmpAdminString,
        alaEventActionScriptPath            SnmpAdminString,
        alaEventActionScriptLastChanged     DateAndTime,
        alaEventActionScriptLastLaunched    DateAndTime,
        alaEventActionScriptLaunchCount     Counter32,
        alaEventActionRowStatus             RowStatus
        }

alaEventActionType  OBJECT-TYPE
        SYNTAX  INTEGER {
                trap (1)
        }
        MAX-ACCESS  not-accessible
        STATUS  current
        DESCRIPTION
                "Enumeration indicating the event type for the row."
        ::= { alaEventActionEntry 1 }

alaEventActionName  OBJECT-TYPE
        SYNTAX  SnmpAdminString (SIZE (1..64))
        MAX-ACCESS  not-accessible
        STATUS  current
        DESCRIPTION
                "Event name. For traps, this is the trap name."
        ::= { alaEventActionEntry 2 }

alaEventActionScriptPath  OBJECT-TYPE
        SYNTAX  SnmpAdminString (SIZE (1..64))
        MAX-ACCESS  read-create
        STATUS  current
        DESCRIPTION
                "Script to launch when the event is matched. This script
                must be under the directory /flash/python/"
        ::= { alaEventActionEntry 3 }

alaEventActionScriptLastChanged  OBJECT-TYPE
        SYNTAX DateAndTime
        MAX-ACCESS  read-only
        STATUS  current
        DESCRIPTION
                "The last time alaEventActionScriptPath was modified this event."
        ::= { alaEventActionEntry 4 }

alaEventActionScriptLastLaunched  OBJECT-TYPE
        SYNTAX DateAndTime
        MAX-ACCESS  read-only
        STATUS  current
        DESCRIPTION
                "The last time the script was launched for this event.
                If no actions have been mached, this value will be all zeros
                (0-0-0,0:0:0.0).
                This value resets when alaEventActionScriptPath is modified as
                reported by alaEventActionScriptLastChanged."
        ::= { alaEventActionEntry 5 }

alaEventActionScriptLaunchCount  OBJECT-TYPE
        SYNTAX Counter32
        MAX-ACCESS  read-only
        STATUS  current
        DESCRIPTION
                "The number of times this event has been detected and the script
                has been launched.
                This value resets when alaEventActionScriptPath is modified as
                reported by alaEventActionScriptLastChanged."
        ::= { alaEventActionEntry 6 }

alaEventActionRowStatus  OBJECT-TYPE
        SYNTAX  RowStatus
        MAX-ACCESS  read-create
        STATUS  current
        DESCRIPTION
                "Row status to create/delete entries."
        ::= { alaEventActionEntry 7 }

--
-- Compliance Statements
--

    alcatelIND1EventScriptingMIBCompliance MODULE-COMPLIANCE
        STATUS  current
        DESCRIPTION
            "Compliance statement for CLI event scripting Subsystem."
        MODULE  -- this module

            MANDATORY-GROUPS
            {
                eventActionGlobalsGroup,
                eventActionGroup
            }

        ::= { alcatelIND1EventScriptingMIBCompliances 1 }

--
-- Units Of Conformance
--

     eventActionGlobalsGroup OBJECT-GROUP
        OBJECTS
        {
            alaEventActionGlobalScriptTimeLimit
        }
        STATUS  current
        DESCRIPTION
            "Collection of objects
             for Event Action Global Management."
        ::= { alcatelIND1EventScriptingMIBGroups 1 }


     eventActionGroup OBJECT-GROUP
        OBJECTS
        {
            alaEventActionScriptPath,
            alaEventActionScriptLastChanged,
            alaEventActionScriptLastLaunched,
            alaEventActionScriptLaunchCount,
            alaEventActionRowStatus
        }
        STATUS  current
        DESCRIPTION
            "Collection of objects
             for Event Action Management."
        ::= { alcatelIND1EventScriptingMIBGroups 2 }

END
