ALCATEL-ENT1-SIP-SNOOPING-MIB DEFINITIONS ::= BEGIN

IMPORTS
	NOTIFICATION-TYPE, OBJECT-TYPE, OBJECT-IDENTITY, MODULE-IDENTITY, Counter64, Integer32,
        Counter32
		FROM SNMPv2-SMI
          InetAddress,InetAddressType
                  	FROM INET-ADDRESS-MIB
	OBJECT-GROUP, MODULE-COMPLIANCE, NOTIFICATION-GROUP
		FROM SNMPv2-CONF
	RowStatus, DateAndTime
		FROM SNMPv2-TC
	softentIND1SIPSnooping
		FROM ALCATEL-ENT1-BASE
          SnmpAdminString
                    FROM SNMP-FRAMEWORK-MIB
        physicalIndex      FROM ALCATEL-ENT1-CHASSIS-MIB
        InterfaceIndex
    	FROM IF-MIB;

aluSIPSnoopingMIB MODULE-IDENTITY
	LAST-UPDATED  "201205040000Z"
	ORGANIZATION  "Alcatel-Lucent"
	CONTACT-INFO
			"Please consult with the Customer Service to ensure the most appropriate
			version of this document is used with the products in question:

	Alcatel-Lucent, Enterprise Solutions Division
	(Formerly Alcatel Internetworking, Incorporated)
	26801 West Agoura Road
	Agoura Hills, CA  91301-5122
	United States Of America

	Telephone:
	North America  +1 800 995 2696
	Latin America  +1 877 919 9526
	Europe         +31 23 556 0100
	Asia           +65 394 7933
	All Other      +1 818 878 4507

	Electronic Mail:         support@ind.alcatel.com
	World Wide Web:          http://alcatel-lucent.com/wps/portal/enterprise
	File Transfer Protocol:  ftp://ftp.ind.alcatel.com/pub/products/mibs"

	DESCRIPTION
		"This module describes an authoritative enterprise-specific Simple
		Network Management Protocol (SNMP) Management Information Base (MIB):

		For the Birds Of Prey Product Line
		SIP Snooping feature is provided to address the key challenge of real
	   	time delivery and monitoring requirements for media streams from SIP devices.

		The right to make changes in specification and other information
		contained in this document without prior notice is reserved.

		No liability shall be assumed for any incidental, indirect, special, or
		consequential damages whatsoever arising from or related to this
		document or the information contained herein.

		Vendors, end-users, and other interested parties are granted
		non-exclusive license to use this specification in connection with
		management of the products for which it is intended to be used.

		Copyright (C) 1995-2008 Alcatel-Lucent, Incorporated
		ALL RIGHTS RESERVED WORLDWIDE"

    REVISION      "201205040000Z"
    DESCRIPTION
        "The latest version of this MIB Module."

::= { softentIND1SIPSnooping 1}

-- xxxxxxxxxxxxxxxxxxxxxxxxxxxxxxxxxxxxxxxxxxxxxxxxxxxxxxxxxxxxxxxxx

aluSIPSnoopingMIBNotifications	OBJECT IDENTIFIER ::= { aluSIPSnoopingMIB 0 }

aluSIPSnoopingMIBObjects OBJECT-IDENTITY
	STATUS 			current
	DESCRIPTION 	"Branch for SIP Snooping sub-system managed objects."
::= { aluSIPSnoopingMIB	1 }

aluSIPSnoopingMIBConformance OBJECT-IDENTITY
	STATUS 			current
	DESCRIPTION 	"Branch for SIP Snooping sub-system conformance information."
::= { aluSIPSnoopingMIB	2 }

aluSIPSnoopingMIBGroups OBJECT-IDENTITY
        STATUS          current
        DESCRIPTION
                                "Branch for SIP Snooping subsystem
                                units of conformance."
        ::= { aluSIPSnoopingMIBConformance 1 }

aluSIPSnoopingMIBCompliances OBJECT-IDENTITY
        STATUS          current
        DESCRIPTION
                                "Branch for SIP Snooping subsystem
                                compliance statements."
        ::= { aluSIPSnoopingMIBConformance 2 }


-- xxxxxxxxxxxxxxxxxxxxxxxxxxxxxxxxxxxxxxxxxxxxxxxxxxxxxxxxxxxxxxxxx

aluSIPSnoopingConfig 	OBJECT	IDENTIFIER ::= { aluSIPSnoopingMIBObjects 1 }

-- xxxxxxxxxxxxxxxxxxxxxxxxxxxxxxxxxxxxxxxxxxxxxxxxxxxxxxxxxxxxxxxxx



aluSIPSnoopingStatus OBJECT-TYPE
  SYNTAX	INTEGER {
                enable (1),
                disable (2)
              }
  MAX-ACCESS  read-write
  STATUS      current
  DESCRIPTION "Enable/Disable SIP Snooping on the device."
  DEFVAL      { disable }
  ::= { aluSIPSnoopingConfig 1}

aluSIPSnoopingSIPTrustedServerIPAddress1Type OBJECT-TYPE
  SYNTAX      	    InetAddressType { ipv4(1) }
  MAX-ACCESS	  	read-write
  STATUS     	 	current
  DESCRIPTION 		"First SIP Snooping trusted call server IP address Type "
  ::= { aluSIPSnoopingConfig 2 }

aluSIPSnoopingSIPTrustedServerIPAddress1 OBJECT-TYPE
  SYNTAX      	    InetAddress
  MAX-ACCESS	  	read-write
  STATUS     	 	current
  DESCRIPTION 		"First SIP Snooping trusted call server IP address"
  DEFVAL      		{ '00000000'h }
  ::= { aluSIPSnoopingConfig 3 }

aluSIPSnoopingSIPTrustedServerIPAddress2Type OBJECT-TYPE
  SYNTAX      	    InetAddressType { ipv4(1) }
  MAX-ACCESS  		read-write
  STATUS      		current
  DESCRIPTION 		"Second SIP Snooping trusted call server IP address Type"
   DEFVAL                              { ipv4 }
  ::= { aluSIPSnoopingConfig 4 }

aluSIPSnoopingSIPTrustedServerIPAddress2 OBJECT-TYPE
  SYNTAX      	    InetAddress
  MAX-ACCESS  		read-write
  STATUS      		current
  DESCRIPTION 		"Second SIP Snooping trusted call server IP address"
  DEFVAL      		{ '00000000'h }
  ::= { aluSIPSnoopingConfig 5 }

aluSIPSnoopingSIPTrustedServerIPAddress3Type OBJECT-TYPE
  SYNTAX      	    InetAddressType { ipv4(1) }
  MAX-ACCESS  		read-write
  STATUS      		current
  DESCRIPTION 		"Third SIP Snooping trusted call server IP address Type"
  DEFVAL         { ipv4 }
  ::= { aluSIPSnoopingConfig 6 }

aluSIPSnoopingSIPTrustedServerIPAddress3 OBJECT-TYPE
  SYNTAX      	    InetAddress
  MAX-ACCESS  		read-write
  STATUS      		current
  DESCRIPTION 		"Third SIP Snooping trusted call server IP address"
  DEFVAL      		{ '00000000'h }
  ::= { aluSIPSnoopingConfig 7 }

aluSIPSnoopingSIPTrustedServerIPAddress4Type OBJECT-TYPE
  SYNTAX      	    InetAddressType { ipv4(1) }
  MAX-ACCESS  		read-write
  STATUS      		current
  DESCRIPTION 		"Fourth SIP Snooping trusted call server IP address Type"
  DEFVAL         { ipv4 }
  ::= { aluSIPSnoopingConfig 8 }

aluSIPSnoopingSIPTrustedServerIPAddress4 OBJECT-TYPE
  SYNTAX      	    InetAddress
  MAX-ACCESS  		read-write
  STATUS      		current
  DESCRIPTION 		"Fourth SIP Snooping trusted call server IP address"
  DEFVAL      		{ '00000000'h }
  ::= { aluSIPSnoopingConfig 9 }

aluSIPSnoopingSIPTrustedServerIPAddress5Type OBJECT-TYPE
  SYNTAX      	    InetAddressType { ipv4(1) }
  MAX-ACCESS  		read-write
  STATUS      		current
  DESCRIPTION 		"Fifth SIP Snooping trusted call server IP address Type"
  DEFVAL         { ipv4 }
  ::= { aluSIPSnoopingConfig 10 }

aluSIPSnoopingSIPTrustedServerIPAddress5 OBJECT-TYPE
  SYNTAX      	    InetAddress
  MAX-ACCESS  		read-write
  STATUS      		current
  DESCRIPTION 		"Fifth SIP Snooping trusted call server IP address"
  DEFVAL      		{ '00000000'h }
  ::= { aluSIPSnoopingConfig 11 }

aluSIPSnoopingSIPTrustedServerIPAddress6Type OBJECT-TYPE
  SYNTAX      	    InetAddressType { ipv4(1) }
  MAX-ACCESS  		read-write
  STATUS      		current
  DESCRIPTION 		"Sixth SIP Snooping trusted call server IP address Type"
  DEFVAL         { ipv4 }
  ::= { aluSIPSnoopingConfig 12 }

aluSIPSnoopingSIPTrustedServerIPAddress6 OBJECT-TYPE
  SYNTAX      	    InetAddress
  MAX-ACCESS  		read-write
  STATUS      		current
  DESCRIPTION 		"Sixth SIP Snooping trusted call server IP address"
  DEFVAL      		{ '00000000'h }
  ::= { aluSIPSnoopingConfig 13 }

aluSIPSnoopingSIPTrustedServerIPAddress7Type OBJECT-TYPE
  SYNTAX      	    InetAddressType { ipv4(1) }
  MAX-ACCESS  		read-write
  STATUS      		current
  DESCRIPTION 		"Seventh SIP Snooping trusted call server IP address Type"
  DEFVAL         { ipv4 }
  ::= { aluSIPSnoopingConfig 14 }

aluSIPSnoopingSIPTrustedServerIPAddress7 OBJECT-TYPE
  SYNTAX      	    InetAddress
  MAX-ACCESS  		read-write
  STATUS      		current
  DESCRIPTION 		"Seventh SIP Snooping trusted call server IP address"
  DEFVAL      		{ '00000000'h }
  ::= { aluSIPSnoopingConfig 15 }

aluSIPSnoopingSIPTrustedServerIPAddress8Type OBJECT-TYPE
  SYNTAX      	    InetAddressType { ipv4(1) }
  MAX-ACCESS  		read-write
  STATUS      		current
  DESCRIPTION 		"Eight SIP Snooping trusted call server IP address Type"
  DEFVAL         { ipv4 }
  ::= { aluSIPSnoopingConfig 16 }

aluSIPSnoopingSIPTrustedServerIPAddress8 OBJECT-TYPE
  SYNTAX      	    InetAddress
  MAX-ACCESS  		read-write
  STATUS      		current
  DESCRIPTION 		"Eight SIP Snooping trusted call server IP address"
  DEFVAL      		{ '00000000'h }
  ::= { aluSIPSnoopingConfig 17 }

aluSIPSnoopingSIPControlDSCP OBJECT-TYPE
  SYNTAX			Integer32 (0..63)
  MAX-ACCESS  		read-write
  STATUS      		current
  DESCRIPTION 		"SIP Snooping DSCP number."
  DEFVAL      		{ 0 }
  ::= { aluSIPSnoopingConfig 18 }

aluSIPSnoopingSOSCallNumber1 OBJECT-TYPE
  SYNTAX      		SnmpAdminString (SIZE(0..31))
  MAX-ACCESS  		read-write
  STATUS      		current
  DESCRIPTION 		"First SIP Snooping SOS Call number"
  ::= { aluSIPSnoopingConfig 19 }

aluSIPSnoopingSOSCallNumber2 OBJECT-TYPE
  SYNTAX      		SnmpAdminString (SIZE(0..31))
  MAX-ACCESS  		read-write
  STATUS      		current
  DESCRIPTION 		"Second SIP Snooping SOS Call number "
  ::= { aluSIPSnoopingConfig 20 }

aluSIPSnoopingSOSCallNumber3 OBJECT-TYPE
  SYNTAX      		SnmpAdminString (SIZE(0..31))
  MAX-ACCESS  		read-write
  STATUS      		current
  DESCRIPTION 		"Third SIP Snooping SOS Call number "
  ::= { aluSIPSnoopingConfig 21 }

aluSIPSnoopingSOSCallNumber4 OBJECT-TYPE
  SYNTAX      		SnmpAdminString (SIZE(0..31))
  MAX-ACCESS  		read-write
  STATUS      		current
  DESCRIPTION 		"Fourth SIP Snooping SOS Call number "
  ::= { aluSIPSnoopingConfig 22 }

aluSIPSnoopingSOSCallRTPDSCP OBJECT-TYPE
  SYNTAX			Integer32 (0..63)
  MAX-ACCESS  		read-write
  STATUS      		current
  DESCRIPTION	 	"SIP Snooping RTP DSCP number."
  DEFVAL      		{ 46 }
  ::= { aluSIPSnoopingConfig 23 }


aluSIPSnoopingThresholdNumberOfCalls OBJECT-TYPE
 SYNTAX      		Integer32 (50..500)
  MAX-ACCESS 		read-write
  STATUS      		current
  DESCRIPTION 	          "Number of call records that can be stored onto the device."
  DEFVAL      		{ 200 }
  ::= { aluSIPSnoopingConfig  24 }

aluSIPSnoopingClearStats OBJECT-TYPE
  SYNTAX      INTEGER {
                yes (1),
                no (2)
              }
  MAX-ACCESS  	read-write
  STATUS      	current
  DESCRIPTION  	"Clear the SIP Snooping statistics."
  DEFVAL      	{ no }
  ::= { aluSIPSnoopingConfig 25 }

aluSIPSnoopingSIPUdpPort1 OBJECT-TYPE
  SYNTAX      		Integer32 (0..65535)
  MAX-ACCESS	  	read-write
  STATUS     	 	current
  DESCRIPTION 		"First SIP Snooping UDP Port."
  ::= { aluSIPSnoopingConfig 26 }

aluSIPSnoopingSIPUdpPort2 OBJECT-TYPE
  SYNTAX      		Integer32 (0..65535)
  MAX-ACCESS	  	read-write
  STATUS     	 	current
  DESCRIPTION 		"Second SIP Snooping UDP Port."
  ::= { aluSIPSnoopingConfig 27 }

aluSIPSnoopingSIPUdpPort3 OBJECT-TYPE
  SYNTAX      		Integer32 (0..65535)
  MAX-ACCESS	  	read-write
  STATUS     	 	current
  DESCRIPTION 		"Third SIP Snooping UDP Port."
  ::= { aluSIPSnoopingConfig 28 }

aluSIPSnoopingSIPUdpPort4 OBJECT-TYPE
  SYNTAX      		Integer32 (0..65535)
  MAX-ACCESS	  	read-write
  STATUS     	 	current
  DESCRIPTION 		"Fourth SIP Snooping UDP Port."
  ::= { aluSIPSnoopingConfig 29 }

aluSIPSnoopingSIPUdpPort5 OBJECT-TYPE
  SYNTAX      		Integer32 (0..65535)
  MAX-ACCESS	  	read-write
  STATUS     	 	current
  DESCRIPTION 		"Fifth  SIP Snooping UDP Port."
  ::= { aluSIPSnoopingConfig 30 }

aluSIPSnoopingSIPUdpPort6 OBJECT-TYPE
  SYNTAX      		Integer32 (0..65535)
  MAX-ACCESS	  	read-write
  STATUS     	 	current
  DESCRIPTION 		"Sixth  SIP Snooping UDP Port."
  ::= { aluSIPSnoopingConfig 31 }

aluSIPSnoopingSIPUdpPort7 OBJECT-TYPE
  SYNTAX      		Integer32 (0..65535)
  MAX-ACCESS	  	read-write
  STATUS     	 	current
  DESCRIPTION 		"Seventh SIP Snooping UDP Port."
  ::= { aluSIPSnoopingConfig 32 }

aluSIPSnoopingSIPUdpPort8 OBJECT-TYPE
  SYNTAX      		Integer32 (0..65535)
  MAX-ACCESS	  	read-write
  STATUS     	 	current
  DESCRIPTION 		"Eighth SIP Snooping UDP Port."
  ::= { aluSIPSnoopingConfig 33 }

aluSIPSnoopingTotalCallsProcessed OBJECT-TYPE
  SYNTAX      		Counter64
  MAX-ACCESS 		read-only
  STATUS      		current
  DESCRIPTION 		"Total calls processed for SIP Snooping."
  ::= { aluSIPSnoopingConfig 34 }

aluSIPSnoopingTotalAudioStreams OBJECT-TYPE
 SYNTAX      	    Counter64
  MAX-ACCESS 		read-only
  STATUS      		current
  DESCRIPTION 		"Total audio streams."
  ::= { aluSIPSnoopingConfig 35 }

aluSIPSnoopingTotalVideoStreams OBJECT-TYPE
 SYNTAX      		Counter64
  MAX-ACCESS 		read-only
  STATUS      		current
  DESCRIPTION 		"Total video streams."
  ::= { aluSIPSnoopingConfig 36 }

aluSIPSnoopingTotalOtherStreams OBJECT-TYPE
 SYNTAX      		Counter64
  MAX-ACCESS 		read-only
  STATUS      		current
  DESCRIPTION 		"Total other streams."
  ::= { aluSIPSnoopingConfig 37 }

aluSIPSnoopingAudioStreamsBeyondThreshold OBJECT-TYPE
 SYNTAX      		Counter64
  MAX-ACCESS 		read-only
  STATUS      		current
  DESCRIPTION 		"Total audio streams that have exceeded threshold."
  ::= { aluSIPSnoopingConfig 38 }

aluSIPSnoopingVideoStreamsBeyondThreshold OBJECT-TYPE
 SYNTAX      		Counter64
  MAX-ACCESS 		read-only
  STATUS      		current
  DESCRIPTION 		"Total video streams that have exceeded threshold."
  ::= { aluSIPSnoopingConfig 39 }

aluSIPSnoopingOtherStreamsBeyondThreshold OBJECT-TYPE
 SYNTAX      		Counter64
  MAX-ACCESS 		read-only
  STATUS      		current
  DESCRIPTION 		"Total other streams that have exceeded threshold."
  ::= { aluSIPSnoopingConfig 40 }

aluSIPSnoopingActiveStreamsBeyondThreshold OBJECT-TYPE
 SYNTAX      		Counter64
  MAX-ACCESS 		read-only
  STATUS      		current
  DESCRIPTION 		"Total active streams that have exceeded threshold."
  ::= { aluSIPSnoopingConfig 41 }

aluSIPSnoopingActiveAudioStreams OBJECT-TYPE
 SYNTAX      		Counter64
  MAX-ACCESS 		read-only
  STATUS      		current
  DESCRIPTION 		"Active audio streams."
  ::= { aluSIPSnoopingConfig 42 }

aluSIPSnoopingActiveVideoStreams OBJECT-TYPE
 SYNTAX      		Counter64
  MAX-ACCESS 		read-only
  STATUS      		current
  DESCRIPTION 		"Active video streams."
  ::= { aluSIPSnoopingConfig 43 }

aluSIPSnoopingActiveOtherStreams OBJECT-TYPE
 SYNTAX      		Counter64
  MAX-ACCESS 		read-only
  STATUS      		current
  DESCRIPTION 		"Active other streams."
  ::= { aluSIPSnoopingConfig 44 }

aluSIPSnoopingHardwareSIPPackets OBJECT-TYPE
 SYNTAX      		Counter64
  MAX-ACCESS 		read-only
  STATUS      		current
  DESCRIPTION 		"Total SIP packet received by hardware."
  ::= { aluSIPSnoopingConfig 45 }

aluSIPSnoopingSoftwareSIPPackets OBJECT-TYPE
 SYNTAX      		Counter64
  MAX-ACCESS 		read-only
  STATUS      		current
  DESCRIPTION 		"Total SIP packet received by software."
  ::= { aluSIPSnoopingConfig 46 }

aluSIPSnoopingSIPInvitePackets OBJECT-TYPE
 SYNTAX      		Counter64
  MAX-ACCESS 		read-only
  STATUS      		current
  DESCRIPTION 		"Total SIP packet received with INVITE method."
  ::= { aluSIPSnoopingConfig 47 }

aluSIPSnoopingSIPAckPackets OBJECT-TYPE
 SYNTAX      		Counter64
  MAX-ACCESS 		read-only
  STATUS      		current
  DESCRIPTION 		"Total SIP packet received with ACK method."
  ::= { aluSIPSnoopingConfig 48 }

aluSIPSnoopingSIPByePackets OBJECT-TYPE
 SYNTAX      		Counter64
  MAX-ACCESS 		read-only
  STATUS      		current
  DESCRIPTION 		"Total SIP packet received with BYE method."
  ::= { aluSIPSnoopingConfig 49 }

aluSIPSnoopingSIPUpdatePackets OBJECT-TYPE
 SYNTAX      		Counter64
  MAX-ACCESS 		read-only
  STATUS      		current
  DESCRIPTION 		"Total SIP packet received with UPDATE method."
  ::= { aluSIPSnoopingConfig 50 }

aluSIPSnoopingSIPPrackPackets OBJECT-TYPE
 SYNTAX      		Counter64
  MAX-ACCESS 		read-only
  STATUS      		current
  DESCRIPTION 		"Total SIP packet received with PRACK method."
  ::= { aluSIPSnoopingConfig 51 }

aluSIPSnoopingSIPRecvdResponsePackets OBJECT-TYPE
 SYNTAX      		Counter64
  MAX-ACCESS 		read-only
  STATUS      		current
  DESCRIPTION 		"Total number of SIP response packet received."
  ::= { aluSIPSnoopingConfig 52 }

aluSIPSnoopingSIPDiscardedPackets OBJECT-TYPE
 SYNTAX      		Counter64
  MAX-ACCESS 		read-only
  STATUS      		current
  DESCRIPTION 		"Total number of discarded/malformed/unsupported SIP packets."
  ::= { aluSIPSnoopingConfig 53 }

aluSIPSnoopingSIPDiscardedNoTrustServerPackets OBJECT-TYPE
 SYNTAX      		Counter64
  MAX-ACCESS 		read-only
  STATUS      		current
  DESCRIPTION 		"Total number of discarded SIP packets not from/to trusted servers."
  ::= { aluSIPSnoopingConfig 54 }

aluSIPSnoopingSIPDroppedSWErrorPackets OBJECT-TYPE
 SYNTAX      		Counter64
  MAX-ACCESS 		read-only
  STATUS      		current
  DESCRIPTION 		"Total number of SIP packets dropped due the software error
  					(i.e. NI overflow, NI/CMM, CMM overflow etc.)."
  ::= { aluSIPSnoopingConfig 55 }

aluSIPSnoopingTotalEmergencyCalls OBJECT-TYPE
 SYNTAX      		Counter64
  MAX-ACCESS 		read-only
  STATUS      		current
  DESCRIPTION 		"Total number of Emergency Calls."
  ::= { aluSIPSnoopingConfig 56 }

aluSIPSnoopingSIPTcpPort1 OBJECT-TYPE
  SYNTAX      		Integer32 (0..65535)
  MAX-ACCESS	  	read-write
  STATUS     	 	current
  DESCRIPTION 		"First SIP Snooping TCP Port."
  ::= { aluSIPSnoopingConfig 57 }

aluSIPSnoopingSIPTcpPort2 OBJECT-TYPE
  SYNTAX      		Integer32 (0..65535)
  MAX-ACCESS	  	read-write
  STATUS     	 	current
  DESCRIPTION 		"Second SIP Snooping TCP Port."
  ::= { aluSIPSnoopingConfig 58 }

aluSIPSnoopingSIPTcpPort3 OBJECT-TYPE
  SYNTAX      		Integer32 (0..65535)
  MAX-ACCESS	  	read-write
  STATUS     	 	current
  DESCRIPTION 		"Third SIP Snooping TCP Port."
  ::= { aluSIPSnoopingConfig 59 }

aluSIPSnoopingSIPTcpPort4 OBJECT-TYPE
  SYNTAX      		Integer32 (0..65535)
  MAX-ACCESS	  	read-write
  STATUS     	 	current
  DESCRIPTION 		"Fourth SIP Snooping TCP Port."
  ::= { aluSIPSnoopingConfig 60 }

aluSIPSnoopingSIPTcpPort5 OBJECT-TYPE
  SYNTAX      		Integer32 (0..65535)
  MAX-ACCESS	  	read-write
  STATUS     	 	current
  DESCRIPTION 		"Fifth  SIP Snooping TCP Port."
  ::= { aluSIPSnoopingConfig 61 }

aluSIPSnoopingSIPTcpPort6 OBJECT-TYPE
  SYNTAX      		Integer32 (0..65535)
  MAX-ACCESS	  	read-write
  STATUS     	 	current
  DESCRIPTION 		"Sixth  SIP Snooping TCP Port."
  ::= { aluSIPSnoopingConfig 62 }

aluSIPSnoopingSIPTcpPort7 OBJECT-TYPE
  SYNTAX      		Integer32 (0..65535)
  MAX-ACCESS	  	read-write
  STATUS     	 	current
  DESCRIPTION 		"Seventh SIP Snooping TCP Port."
  ::= { aluSIPSnoopingConfig 63 }

aluSIPSnoopingSIPTcpPort8 OBJECT-TYPE
  SYNTAX      		Integer32 (0..65535)
  MAX-ACCESS	  	read-write
  STATUS     	 	current
  DESCRIPTION 		"Eighth SIP Snooping TCP Port."
  ::= { aluSIPSnoopingConfig 64 }

aluSIPSnoopingClearEndedCalls OBJECT-TYPE
  SYNTAX      INTEGER {
                yes (1),
                no (2)
              }
  MAX-ACCESS  	read-write
  STATUS      	current
  DESCRIPTION  	"Clear the SIP Snooping Ended Calls."
  DEFVAL      	{ no }
  ::= { aluSIPSnoopingConfig 65 }

alaSIPSnoopingRsvdHwResources OBJECT-TYPE
  SYNTAX      INTEGER {
                oneX (1),
                twoX (2),
       	        threeX (3),
	        fourX (4)
              }
  MAX-ACCESS  	read-write
  STATUS      	current
  DESCRIPTION  	"This reserves hardware resources required to program ACLs for media entries. Each value is a multiple of the default reserved hardware resources."
  DEFVAL      	{ oneX }
  ::= { aluSIPSnoopingConfig 66 }

alaSIPSnoopingSIPCpuRateLimit OBJECT-TYPE
  SYNTAX      INTEGER {
                oneMbps (1),
                twoMbps (2),
	  	threeMbps (3),
	        fourMbps (4)
              }
  MAX-ACCESS  	read-write
  STATUS      	current
  DESCRIPTION  	"Rate limit of SIP PDU trapping towards CPU, not applicable to SIP PDU going towards network port."
  DEFVAL      	{ oneMbps }
  ::= { aluSIPSnoopingConfig 67 }


aluSIPSnoopingPortConfigTable  OBJECT-TYPE
  SYNTAX                SEQUENCE OF SIPSnoopingPortConfigEntry
  MAX-ACCESS            not-accessible
  STATUS                current
  DESCRIPTION           "A table containing SIP Snooping port configuration information."
  ::= { aluSIPSnoopingMIBObjects 2 }

aluSIPSnoopingPortConfigEntry  OBJECT-TYPE
  SYNTAX                SIPSnoopingPortConfigEntry
  MAX-ACCESS            not-accessible
  STATUS                current
  DESCRIPTION           "SIP snooping port configuration entry."
  INDEX { aluSIPSnoopingPortConfigSlotPortIndex }
  ::= { aluSIPSnoopingPortConfigTable 1 }

SIPSnoopingPortConfigEntry	::=
	SEQUENCE
	{
		aluSIPSnoopingPortConfigSlotPortIndex 		InterfaceIndex,
		aluSIPSnoopingPortConfigPortStatus		    INTEGER,
		aluSIPSnoopingPortConfigPortMode			INTEGER
	}

aluSIPSnoopingPortConfigSlotPortIndex	OBJECT-TYPE
  SYNTAX		InterfaceIndex
  MAX-ACCESS  		not-accessible
  STATUS  		current
  DESCRIPTION   "The physical identification number for this port."
  ::= { aluSIPSnoopingPortConfigEntry 1 }


aluSIPSnoopingPortConfigPortStatus OBJECT-TYPE
  SYNTAX      INTEGER {
                enable (1),
                disable (2)
			}
  MAX-ACCESS  	read-write
  STATUS      	current
  DESCRIPTION  	"This is the sip snooping status on the port."
  DEFVAL      	{ enable }
  ::= { aluSIPSnoopingPortConfigEntry 2}

aluSIPSnoopingPortConfigPortMode OBJECT-TYPE
  SYNTAX      INTEGER {
                forceEdge (1),
                forceNonEdge (2),
                automatic (3)
				}
  MAX-ACCESS  	read-write
  STATUS      	current
  DESCRIPTION  	"This is the sip snooping Port Mode."
  DEFVAL      	{ automatic }
  ::= { aluSIPSnoopingPortConfigEntry 3}

aluSIPSnoopingThresholdTable  OBJECT-TYPE
  SYNTAX                SEQUENCE OF SIPSnoopingThresholdEntry
  MAX-ACCESS            not-accessible
  STATUS                current
  DESCRIPTION           "A table containing SIP Snooping threshold information."
  ::= { aluSIPSnoopingMIBObjects 3 }

aluSIPSnoopingThresholdEntry  OBJECT-TYPE
  SYNTAX                SIPSnoopingThresholdEntry
  MAX-ACCESS            not-accessible
  STATUS                current
  DESCRIPTION           "SIP snooping threshold entry."
  INDEX { aluSIPSnoopingThresholdMediumIndex }
  ::= { aluSIPSnoopingThresholdTable 1 }

SIPSnoopingThresholdEntry	::=
	SEQUENCE
	{
		aluSIPSnoopingThresholdMediumIndex 		INTEGER,
		aluSIPSnoopingThresholdJitter		        Integer32,
		aluSIPSnoopingThresholdPacketLost 		Integer32,
		aluSIPSnoopingThresholdRoundTripDelay 		Integer32,
		aluSIPSnoopingThresholdRFactor			Integer32,
		aluSIPSnoopingThresholdMOS 			Integer32
	}


aluSIPSnoopingThresholdMediumIndex OBJECT-TYPE
  SYNTAX      INTEGER {
                other (1),
                audio (2),
                video (3)     }
  MAX-ACCESS 		not-accessible
  STATUS      		current
  DESCRIPTION 		"Threshold medium for SIP Snooping."
  ::= { aluSIPSnoopingThresholdEntry 1 }

aluSIPSnoopingThresholdJitter OBJECT-TYPE
  SYNTAX      		Integer32 (0..300)
  MAX-ACCESS 		read-write
  STATUS      		current
  DESCRIPTION 	    "Jitter threshold in millisec for SIP Snooping."
  ::= { aluSIPSnoopingThresholdEntry 2 }

aluSIPSnoopingThresholdPacketLost OBJECT-TYPE
 SYNTAX      		Integer32 (0..99)
  MAX-ACCESS 		read-write
  STATUS      		current
  DESCRIPTION 	    "Packet Loss in percentage for SIP Snooping."
  ::= { aluSIPSnoopingThresholdEntry 3 }

aluSIPSnoopingThresholdRoundTripDelay OBJECT-TYPE
 SYNTAX      		Integer32 (0..500)
  MAX-ACCESS 		read-write
  STATUS      		current
  DESCRIPTION 	    "Round trip delay in millisec for SIP Snooping."
  ::= { aluSIPSnoopingThresholdEntry 4 }

aluSIPSnoopingThresholdRFactor OBJECT-TYPE
 SYNTAX      		Integer32 (0..100)
  MAX-ACCESS 		read-write
  STATUS      		current
  DESCRIPTION 		"R-Factor in millisec for SIP Snooping."
  ::= { aluSIPSnoopingThresholdEntry 5 }

aluSIPSnoopingThresholdMOS OBJECT-TYPE
 SYNTAX     		Integer32 (0..50)
 UNITS                  "tenths of value"
  MAX-ACCESS 		read-write
  STATUS      		current
  DESCRIPTION 		"MOS for SIP Snooping multiplied by a factor of 10."
  ::= { aluSIPSnoopingThresholdEntry 6 }


aluSIPSnoopingActiveCallSummaryTable  OBJECT-TYPE
  SYNTAX                SEQUENCE OF SIPSnoopingActiveCallSummaryEntry
  MAX-ACCESS            not-accessible
  STATUS                current
  DESCRIPTION           "A table containing SIP Snooping active Call summary information."
  ::= { aluSIPSnoopingMIBObjects 4 }

aluSIPSnoopingActiveCallSummaryEntry  OBJECT-TYPE
  SYNTAX                SIPSnoopingActiveCallSummaryEntry
  MAX-ACCESS            not-accessible
  STATUS                current
  DESCRIPTION           "SIP snooping active CallSummary entry."
  INDEX { aluSIPSnoopingActiveCallIndex }
  ::= { aluSIPSnoopingActiveCallSummaryTable 1 }

SIPSnoopingActiveCallSummaryEntry	::=
	SEQUENCE
	{
              aluSIPSnoopingActiveCallIndex  Integer32,
              aluSIPSnoopingActiveCallTagA SnmpAdminString,
              aluSIPSnoopingActiveCallTagB SnmpAdminString,
              aluSIPSnoopingActiveCallIpAddrAType InetAddressType,
              aluSIPSnoopingActiveCallIpAddrA InetAddress,
              aluSIPSnoopingActiveCallIpAddrBType InetAddressType,
              aluSIPSnoopingActiveCallIpAddrB InetAddress,
              aluSIPSnoopingActiveCallL4portA Integer32,
              aluSIPSnoopingActiveCallL4portB Integer32,
              aluSIPSnoopingActiveCallSipMediaType SnmpAdminString,
              aluSIPSnoopingActiveCallStart DateAndTime,
              aluSIPSnoopingActiveCallRtpCountA Counter64,
              aluSIPSnoopingActiveCallRtcpCountA  Counter64,
              aluSIPSnoopingActiveCallRuleNameA SnmpAdminString,
              aluSIPSnoopingActiveCallRtpCountB Counter64,
              aluSIPSnoopingActiveCallRtcpCountB Counter64,
              aluSIPSnoopingActiveCallRuleNameB SnmpAdminString,
              aluSIPSnoopingActiveCallId  SnmpAdminString,
              aluSIPSnoopingActiveCallTrustDSCPStatusA INTEGER,
              aluSIPSnoopingActiveCallTrustDSCPStatusB INTEGER,
              aluSIPSnoopingActiveCallPacketCountA Counter64,
              aluSIPSnoopingActiveCallPacketCountB Counter64

	}


aluSIPSnoopingActiveCallIndex   OBJECT-TYPE
SYNTAX         Integer32 (0..8000)
MAX-ACCESS     not-accessible
STATUS         current
DESCRIPTION    " aluSIPSnoopingActiveCallIndex  "
::= { aluSIPSnoopingActiveCallSummaryEntry 1 }



aluSIPSnoopingActiveCallTagA OBJECT-TYPE
SYNTAX         SnmpAdminString (SIZE (0..64))
MAX-ACCESS     read-only
STATUS         current
DESCRIPTION    "Active call tag for call direction A to B"
::= { aluSIPSnoopingActiveCallSummaryEntry   2 }


aluSIPSnoopingActiveCallTagB  OBJECT-TYPE
SYNTAX         SnmpAdminString (SIZE (0..64))
MAX-ACCESS     read-only
STATUS         current
DESCRIPTION    "Active call tag for call direction B to A"
::= { aluSIPSnoopingActiveCallSummaryEntry   3 }


aluSIPSnoopingActiveCallIpAddrAType  OBJECT-TYPE
SYNTAX         InetAddressType { ipv4(1) }
MAX-ACCESS     read-only
STATUS         current
DESCRIPTION    "Active call ip address for call direction A to B Type"
DEFVAL         { ipv4 }
::= { aluSIPSnoopingActiveCallSummaryEntry   4 }

aluSIPSnoopingActiveCallIpAddrA  OBJECT-TYPE
SYNTAX         InetAddress
MAX-ACCESS     read-only
STATUS         current
DESCRIPTION    "Active call ip address for call direction A to B"
::= { aluSIPSnoopingActiveCallSummaryEntry   5 }


aluSIPSnoopingActiveCallIpAddrBType  OBJECT-TYPE
SYNTAX         InetAddressType {ipv4(1) }
MAX-ACCESS     read-only
STATUS         current
DESCRIPTION    "Active call ip address for call direction B to A Type"
DEFVAL         { ipv4 }
::= { aluSIPSnoopingActiveCallSummaryEntry   6 }

aluSIPSnoopingActiveCallIpAddrB  OBJECT-TYPE
SYNTAX         InetAddress
MAX-ACCESS     read-only
STATUS         current
DESCRIPTION    " Active call ip address for call direction B to A"
::= { aluSIPSnoopingActiveCallSummaryEntry   7 }


aluSIPSnoopingActiveCallL4portA  OBJECT-TYPE
SYNTAX         Integer32 (0..65535)
MAX-ACCESS     read-only
STATUS         current
DESCRIPTION    " Active call L4 port for call direction A to B"
::= { aluSIPSnoopingActiveCallSummaryEntry   8 }


aluSIPSnoopingActiveCallL4portB  OBJECT-TYPE
SYNTAX         Integer32 (0..65535)
MAX-ACCESS     read-only
STATUS         current
DESCRIPTION    " Active call L4 port for call direction B to A"
::= { aluSIPSnoopingActiveCallSummaryEntry   9 }


aluSIPSnoopingActiveCallSipMediaType  OBJECT-TYPE
SYNTAX         SnmpAdminString
MAX-ACCESS     read-only
STATUS         current
DESCRIPTION    " Active call SipMediaType"
::= { aluSIPSnoopingActiveCallSummaryEntry   10 }


aluSIPSnoopingActiveCallStart  OBJECT-TYPE
SYNTAX         DateAndTime
MAX-ACCESS     read-only
STATUS         current
DESCRIPTION    " Active call CallStart DateAndTime"
::= { aluSIPSnoopingActiveCallSummaryEntry   11 }


aluSIPSnoopingActiveCallRtpCountA  OBJECT-TYPE
SYNTAX         Counter64
MAX-ACCESS     read-only
STATUS         current
DESCRIPTION    " Active call RtpCount for call direction A to B"
::= { aluSIPSnoopingActiveCallSummaryEntry   12 }


aluSIPSnoopingActiveCallRtcpCountA  OBJECT-TYPE
SYNTAX         Counter64
MAX-ACCESS     read-only
STATUS         current
DESCRIPTION    " Active call RtcpCount for call direction A to B"
::= { aluSIPSnoopingActiveCallSummaryEntry   13 }


aluSIPSnoopingActiveCallRuleNameA  OBJECT-TYPE
SYNTAX         SnmpAdminString
MAX-ACCESS     read-only
STATUS         current
DESCRIPTION    " Active call QoS RuleName for call direction A to B"
::= { aluSIPSnoopingActiveCallSummaryEntry   14 }


aluSIPSnoopingActiveCallRtpCountB  OBJECT-TYPE
SYNTAX         Counter64
MAX-ACCESS     read-only
STATUS         current
DESCRIPTION    " Active call RtpCount for call direction B to A"
::= { aluSIPSnoopingActiveCallSummaryEntry   15 }


aluSIPSnoopingActiveCallRtcpCountB  OBJECT-TYPE
SYNTAX         Counter64
MAX-ACCESS     read-only
STATUS         current
DESCRIPTION    " Active call RtcpCount for call direction B to A"
::= { aluSIPSnoopingActiveCallSummaryEntry   16 }


aluSIPSnoopingActiveCallRuleNameB  OBJECT-TYPE
SYNTAX         SnmpAdminString
MAX-ACCESS     read-only
STATUS         current
DESCRIPTION    " Active call QoS RuleName for call dirction B to A"
::= { aluSIPSnoopingActiveCallSummaryEntry   17 }

aluSIPSnoopingActiveCallId  OBJECT-TYPE
SYNTAX         SnmpAdminString (SIZE (0..128))
MAX-ACCESS     read-only
STATUS         current
DESCRIPTION    " Active call CallId"
::= { aluSIPSnoopingActiveCallSummaryEntry   18 }


aluSIPSnoopingActiveCallTrustDSCPStatusA OBJECT-TYPE
SYNTAX      INTEGER {
                enable (1),
                disable (2)
			}
MAX-ACCESS     read-only
STATUS         current
DESCRIPTION    "Indicates whether trusted dscp is enabled for the call in direction A to B"
::= { aluSIPSnoopingActiveCallSummaryEntry 19}

aluSIPSnoopingActiveCallTrustDSCPStatusB OBJECT-TYPE
SYNTAX      INTEGER {
                enable (1),
                disable (2)
			}
MAX-ACCESS     read-only
STATUS         current
DESCRIPTION    "Indicates whether trusted dscp is enabled for the call in direction B to A"
::= { aluSIPSnoopingActiveCallSummaryEntry 20}


aluSIPSnoopingActiveCallPacketCountA OBJECT-TYPE
SYNTAX     Counter64
MAX-ACCESS     read-only
STATUS         current
DESCRIPTION    "Total number of RTP packets from A to B"
::= { aluSIPSnoopingActiveCallSummaryEntry 21}

aluSIPSnoopingActiveCallPacketCountB OBJECT-TYPE
SYNTAX     Counter64
MAX-ACCESS     read-only
STATUS         current
DESCRIPTION    "Total number of RTP packets from B to A"
::= { aluSIPSnoopingActiveCallSummaryEntry 22}



aluSIPSnoopingActiveCallStatsTable  OBJECT-TYPE
  SYNTAX                SEQUENCE OF SIPSnoopingActiveCallStatsEntry
  MAX-ACCESS            not-accessible
  STATUS                current
  DESCRIPTION           "A table containing SIP Snooping Call statistics information."
  ::= { aluSIPSnoopingMIBObjects 5 }

aluSIPSnoopingActiveCallStatsEntry  OBJECT-TYPE
  SYNTAX                SIPSnoopingActiveCallStatsEntry
  MAX-ACCESS            not-accessible
  STATUS                current
  DESCRIPTION           "SIP snooping CallStats entry."
  INDEX { aluSIPSnoopingActiveCallIndex }
  ::= { aluSIPSnoopingActiveCallStatsTable 1 }

SIPSnoopingActiveCallStatsEntry	::=
	SEQUENCE
	{
              aluSIPSnoopingActiveCallStatsJitterViolationsA  Integer32,
              aluSIPSnoopingActiveCallStatsJitterViolationsB  Integer32,
              aluSIPSnoopingActiveCallStatsRtdViolationsA  Integer32,
              aluSIPSnoopingActiveCallStatsRtdViolationsB  Integer32,
              aluSIPSnoopingActiveCallStatsPktLossViolationsA  Integer32,
              aluSIPSnoopingActiveCallStatsPktLossViolationsB  Integer32,
              aluSIPSnoopingActiveCallStatsMosViolationsA  Integer32,
              aluSIPSnoopingActiveCallStatsMosViolationsB  Integer32,
              aluSIPSnoopingActiveCallStatsRfactorViolationsA  Integer32,
              aluSIPSnoopingActiveCallStatsRfactorViolationsB  Integer32,
              aluSIPSnoopingActiveCallStatsJitterMaxA  Integer32,
              aluSIPSnoopingActiveCallStatsJitterMinA  Integer32,
              aluSIPSnoopingActiveCallStatsJitterAvgA  Integer32,
              aluSIPSnoopingActiveCallStatsJitterMaxB  Integer32,
              aluSIPSnoopingActiveCallStatsJitterMinB  Integer32,
              aluSIPSnoopingActiveCallStatsJitterAvgB  Integer32,
              aluSIPSnoopingActiveCallStatsRtdMaxA  Integer32,
              aluSIPSnoopingActiveCallStatsRtdMinA  Integer32,
              aluSIPSnoopingActiveCallStatsRtdAvgA  Integer32,
              aluSIPSnoopingActiveCallStatsRtdMaxB  Integer32,
              aluSIPSnoopingActiveCallStatsRtdMinB  Integer32,
              aluSIPSnoopingActiveCallStatsRtdAvgB  Integer32,
              aluSIPSnoopingActiveCallStatsPktLossMaxA  Integer32,
              aluSIPSnoopingActiveCallStatsPktLossMinA  Integer32,
              aluSIPSnoopingActiveCallStatsPktLossAvgA  Integer32,
              aluSIPSnoopingActiveCallStatsPktLossMaxB  Integer32,
              aluSIPSnoopingActiveCallStatsPktLossMinB  Integer32,
              aluSIPSnoopingActiveCallStatsPktLossAvgB  Integer32,
              aluSIPSnoopingActiveCallStatsRfactorMaxA  Integer32,
              aluSIPSnoopingActiveCallStatsRfactorMinA  Integer32,
              aluSIPSnoopingActiveCallStatsRfactorAvgA  Integer32,
              aluSIPSnoopingActiveCallStatsRfactorMaxB  Integer32,
              aluSIPSnoopingActiveCallStatsRfactorMinB  Integer32,
              aluSIPSnoopingActiveCallStatsRfactorAvgB  Integer32,
              aluSIPSnoopingActiveCallStatsMosMaxA  Integer32,
              aluSIPSnoopingActiveCallStatsMosMinA  Integer32,
              aluSIPSnoopingActiveCallStatsMosAvgA  Integer32,
              aluSIPSnoopingActiveCallStatsMosMaxB  Integer32,
              aluSIPSnoopingActiveCallStatsMosMinB  Integer32,
              aluSIPSnoopingActiveCallStatsMosAvgB  Integer32
	}

aluSIPSnoopingActiveCallStatsJitterViolationsA  OBJECT-TYPE
SYNTAX         Integer32 (0..100)
MAX-ACCESS     read-only
STATUS         current
DESCRIPTION    "Active call Rtcp jitter violation (%) for call direction A to B"
::= { aluSIPSnoopingActiveCallStatsEntry   1 }


aluSIPSnoopingActiveCallStatsJitterViolationsB  OBJECT-TYPE
SYNTAX         Integer32 (0..100)
MAX-ACCESS     read-only
STATUS         current
DESCRIPTION    "Active call Rtcp jitter violation (%) for call direction B to A"
::= { aluSIPSnoopingActiveCallStatsEntry   2 }


aluSIPSnoopingActiveCallStatsRtdViolationsA  OBJECT-TYPE
SYNTAX         Integer32 (0..100)
MAX-ACCESS     read-only
STATUS         current
DESCRIPTION    "Active call round trip delay violation (%) for call direction A to B"
::= { aluSIPSnoopingActiveCallStatsEntry   3 }


aluSIPSnoopingActiveCallStatsRtdViolationsB  OBJECT-TYPE
SYNTAX         Integer32 (0..100)
MAX-ACCESS     read-only
STATUS         current
DESCRIPTION    "Active call round trip delay violation (%) for call direction B to A"
::= { aluSIPSnoopingActiveCallStatsEntry   4 }


aluSIPSnoopingActiveCallStatsPktLossViolationsA  OBJECT-TYPE
SYNTAX         Integer32 (0..100)
MAX-ACCESS     read-only
STATUS         current
DESCRIPTION    "Active call packet loss Violations (%) for call direction A to B"
::= { aluSIPSnoopingActiveCallStatsEntry   5 }

aluSIPSnoopingActiveCallStatsPktLossViolationsB  OBJECT-TYPE
SYNTAX         Integer32 (0..100)
MAX-ACCESS     read-only
STATUS         current
DESCRIPTION    "Active call packet loss Violations (%) for call direction B to A"
::= { aluSIPSnoopingActiveCallStatsEntry   6 }


aluSIPSnoopingActiveCallStatsMosViolationsA  OBJECT-TYPE
SYNTAX         Integer32 (0..100)
MAX-ACCESS     read-only
STATUS         current
DESCRIPTION    "Active call Mos Violations (%) for call direciton A to B"
::= { aluSIPSnoopingActiveCallStatsEntry   7 }


aluSIPSnoopingActiveCallStatsMosViolationsB  OBJECT-TYPE
SYNTAX         Integer32 (0..100)
MAX-ACCESS     read-only
STATUS         current
DESCRIPTION    "Active call Mos Violation (%) for call direction B to A"
::= { aluSIPSnoopingActiveCallStatsEntry   8 }


aluSIPSnoopingActiveCallStatsRfactorViolationsA  OBJECT-TYPE
SYNTAX         Integer32 (0..100)
MAX-ACCESS     read-only
STATUS         current
DESCRIPTION    "Active call Rfactor Violation (%) for call direction A to B"
::= { aluSIPSnoopingActiveCallStatsEntry   9 }


aluSIPSnoopingActiveCallStatsRfactorViolationsB  OBJECT-TYPE
SYNTAX         Integer32 (0..100)
MAX-ACCESS     read-only
STATUS         current
DESCRIPTION    "Active call Rfactor Violations for direction B to A"
::= { aluSIPSnoopingActiveCallStatsEntry   10 }


aluSIPSnoopingActiveCallStatsJitterMaxA  OBJECT-TYPE
SYNTAX         Integer32 (0..300)
MAX-ACCESS     read-only
STATUS         current
DESCRIPTION    "Active call Max jitter for call direction A to B"
::= { aluSIPSnoopingActiveCallStatsEntry   11 }

aluSIPSnoopingActiveCallStatsJitterMinA  OBJECT-TYPE
SYNTAX         Integer32 (0..300)
MAX-ACCESS     read-only
STATUS         current
DESCRIPTION    "Active call min Jitter for call direction A to B"
::= { aluSIPSnoopingActiveCallStatsEntry   12 }


aluSIPSnoopingActiveCallStatsJitterAvgA  OBJECT-TYPE
SYNTAX         Integer32 (0..300)
MAX-ACCESS     read-only
STATUS         current
DESCRIPTION    "Active call Avg jitter for call direction A to B"
::= { aluSIPSnoopingActiveCallStatsEntry   13 }


aluSIPSnoopingActiveCallStatsJitterMaxB  OBJECT-TYPE
SYNTAX         Integer32 (0..300)
MAX-ACCESS     read-only
STATUS         current
DESCRIPTION    "Active call Max jitter for call direction B to A"
::= { aluSIPSnoopingActiveCallStatsEntry   14 }


aluSIPSnoopingActiveCallStatsJitterMinB  OBJECT-TYPE
SYNTAX         Integer32 (0..300)
MAX-ACCESS     read-only
STATUS         current
DESCRIPTION    "Active call min Jitter for call direciton B to A"
::= { aluSIPSnoopingActiveCallStatsEntry   15 }


aluSIPSnoopingActiveCallStatsJitterAvgB  OBJECT-TYPE
SYNTAX         Integer32 (0..300)
MAX-ACCESS     read-only
STATUS         current
DESCRIPTION    "Active call avg Jitter for call direction B to A"
::= { aluSIPSnoopingActiveCallStatsEntry   16 }

aluSIPSnoopingActiveCallStatsRtdMaxA  OBJECT-TYPE
SYNTAX         Integer32 (0..500)
MAX-ACCESS     read-only
STATUS         current
DESCRIPTION    "Active call max round trip delay for direction A to B"
::= { aluSIPSnoopingActiveCallStatsEntry   17 }


aluSIPSnoopingActiveCallStatsRtdMinA  OBJECT-TYPE
SYNTAX         Integer32 (0..500)
MAX-ACCESS     read-only
STATUS         current
DESCRIPTION    "Active call min round trip delay for call direction A to B"
::= { aluSIPSnoopingActiveCallStatsEntry   18 }


aluSIPSnoopingActiveCallStatsRtdAvgA  OBJECT-TYPE
SYNTAX         Integer32 (0..500)
MAX-ACCESS     read-only
STATUS         current
DESCRIPTION    "Active call avg round trip delay for call direction A to B"
::= { aluSIPSnoopingActiveCallStatsEntry   19 }


aluSIPSnoopingActiveCallStatsRtdMaxB  OBJECT-TYPE
SYNTAX         Integer32 (0..500)
MAX-ACCESS     read-only
STATUS         current
DESCRIPTION    "Active call max round trip delay for call direction B to A"
::= { aluSIPSnoopingActiveCallStatsEntry   20 }


aluSIPSnoopingActiveCallStatsRtdMinB  OBJECT-TYPE
SYNTAX         Integer32 (0..500)
MAX-ACCESS     read-only
STATUS         current
DESCRIPTION    "Active call min round trip delay for call direction B to A"
::= { aluSIPSnoopingActiveCallStatsEntry   21 }


aluSIPSnoopingActiveCallStatsRtdAvgB  OBJECT-TYPE
SYNTAX         Integer32 (0..500)
MAX-ACCESS     read-only
STATUS         current
DESCRIPTION    "Active call Avg round trip delay for call direciton B to A"
::= { aluSIPSnoopingActiveCallStatsEntry   22 }


aluSIPSnoopingActiveCallStatsPktLossMaxA  OBJECT-TYPE
SYNTAX         Integer32 (0..99)
MAX-ACCESS     read-only
STATUS         current
DESCRIPTION    "Active call max packet loss (%) for call direciton A to B"
::= { aluSIPSnoopingActiveCallStatsEntry   23 }


aluSIPSnoopingActiveCallStatsPktLossMinA  OBJECT-TYPE
SYNTAX         Integer32 (0..99)
MAX-ACCESS     read-only
STATUS         current
DESCRIPTION    "Active call min packet loss (%) for call direction A to B"
::= { aluSIPSnoopingActiveCallStatsEntry   24 }


aluSIPSnoopingActiveCallStatsPktLossAvgA  OBJECT-TYPE
SYNTAX         Integer32 (0..99)
MAX-ACCESS     read-only
STATUS         current
DESCRIPTION    "Active call avg packet loss (%) for call direction A to B"
::= { aluSIPSnoopingActiveCallStatsEntry   25 }


aluSIPSnoopingActiveCallStatsPktLossMaxB  OBJECT-TYPE
SYNTAX         Integer32 (0..99)
MAX-ACCESS     read-only
STATUS         current
DESCRIPTION    "Active call max packet loss (%) for call direction B to A"
::= { aluSIPSnoopingActiveCallStatsEntry   26 }


aluSIPSnoopingActiveCallStatsPktLossMinB  OBJECT-TYPE
SYNTAX         Integer32 (0..99)
MAX-ACCESS     read-only
STATUS         current
DESCRIPTION    "Active call min packet loss (%) for call direction B to A"
::= { aluSIPSnoopingActiveCallStatsEntry   27 }


aluSIPSnoopingActiveCallStatsPktLossAvgB  OBJECT-TYPE
SYNTAX         Integer32 (0..99)
MAX-ACCESS     read-only
STATUS         current
DESCRIPTION    "Active call Avg packet loss (%) for call direction B to A"
::= { aluSIPSnoopingActiveCallStatsEntry   28 }


aluSIPSnoopingActiveCallStatsRfactorMaxA  OBJECT-TYPE
SYNTAX         Integer32 (0..100)
MAX-ACCESS     read-only
STATUS         current
DESCRIPTION    "Active call max Rfactor for call direction A to B"
::= { aluSIPSnoopingActiveCallStatsEntry   29 }


aluSIPSnoopingActiveCallStatsRfactorMinA  OBJECT-TYPE
SYNTAX         Integer32 (0..100)
MAX-ACCESS     read-only
STATUS         current
DESCRIPTION    "Active call min Rfactor for call direction A to B"
::= { aluSIPSnoopingActiveCallStatsEntry   30 }


aluSIPSnoopingActiveCallStatsRfactorAvgA  OBJECT-TYPE
SYNTAX         Integer32 (0..100)
MAX-ACCESS     read-only
STATUS         current
DESCRIPTION    "Active call avg Rfactor for call direction A to B"
::= { aluSIPSnoopingActiveCallStatsEntry   31 }


aluSIPSnoopingActiveCallStatsRfactorMaxB  OBJECT-TYPE
SYNTAX         Integer32 (0..100)
MAX-ACCESS     read-only
STATUS         current
DESCRIPTION    "Active call Max Rfactor for call direction B to A"
::= { aluSIPSnoopingActiveCallStatsEntry   32 }


aluSIPSnoopingActiveCallStatsRfactorMinB  OBJECT-TYPE
SYNTAX         Integer32 (0..100)
MAX-ACCESS     read-only
STATUS         current
DESCRIPTION    "Active call min Rfactor for call direction B to A"
::= { aluSIPSnoopingActiveCallStatsEntry   33 }


aluSIPSnoopingActiveCallStatsRfactorAvgB  OBJECT-TYPE
SYNTAX         Integer32 (0..100)
MAX-ACCESS     read-only
STATUS         current
DESCRIPTION    "Active call avg Rfactor for call direction B to A"
::= { aluSIPSnoopingActiveCallStatsEntry   34 }


aluSIPSnoopingActiveCallStatsMosMaxA  OBJECT-TYPE
SYNTAX         Integer32 (0..50)
UNITS          "tenths of value"
MAX-ACCESS     read-only
STATUS         current
DESCRIPTION    "Displays the Active call Max Mos for call direction A to B, multiplied by a factor of 10"
::= { aluSIPSnoopingActiveCallStatsEntry   35 }


aluSIPSnoopingActiveCallStatsMosMinA  OBJECT-TYPE
SYNTAX         Integer32 (0..50)
UNITS          "tenths of value"
MAX-ACCESS     read-only
STATUS         current
DESCRIPTION    "Displays the Active call min Mos for call direction A to B, multiplied by a factor of 10"
::= { aluSIPSnoopingActiveCallStatsEntry   36 }


aluSIPSnoopingActiveCallStatsMosAvgA  OBJECT-TYPE
SYNTAX         Integer32 (0..50)
UNITS          "tenths of value"
MAX-ACCESS     read-only
STATUS         current
DESCRIPTION    "Displays the Active call Avg Mos for call direction A to B, multiplied by a factor of 10"
::= { aluSIPSnoopingActiveCallStatsEntry   37 }


aluSIPSnoopingActiveCallStatsMosMaxB  OBJECT-TYPE
SYNTAX         Integer32 (0..50)
UNITS          "tenths of value"
MAX-ACCESS     read-only
STATUS         current
DESCRIPTION    "Displays the Active call max Mos for call direction B to A, multiplied by a factor of 10"
::= { aluSIPSnoopingActiveCallStatsEntry   38 }


aluSIPSnoopingActiveCallStatsMosMinB  OBJECT-TYPE
SYNTAX         Integer32 (0..50)
UNITS          "tenths of value"
MAX-ACCESS     read-only
STATUS         current
DESCRIPTION    "Displays the Active call min Mos for call direction B to A, multiplied by a factor of 10"
::= { aluSIPSnoopingActiveCallStatsEntry   39 }


aluSIPSnoopingActiveCallStatsMosAvgB  OBJECT-TYPE
SYNTAX         Integer32 (0..50)
UNITS          "tenths of value"
MAX-ACCESS     read-only
STATUS         current
DESCRIPTION    "Displays the Active call avg Mos for call direction B to A, multiplied by a factor of 10"
::= { aluSIPSnoopingActiveCallStatsEntry   40 }


aluSIPSnoopingEndedCallSummaryTable  OBJECT-TYPE
  SYNTAX                SEQUENCE OF SIPSnoopingEndedCallSummaryEntry
  MAX-ACCESS            not-accessible
  STATUS                current
  DESCRIPTION           "A table containing SIP Snooping ended Call summary information."
  ::= { aluSIPSnoopingMIBObjects 6 }

aluSIPSnoopingEndedCallSummaryEntry  OBJECT-TYPE
  SYNTAX                SIPSnoopingEndedCallSummaryEntry
  MAX-ACCESS            not-accessible
  STATUS                current
  DESCRIPTION           "SIP snooping CallSummary entry."
  INDEX { aluSIPSnoopingEndedCallIndex }
  ::= { aluSIPSnoopingEndedCallSummaryTable 1 }

SIPSnoopingEndedCallSummaryEntry	::=
	SEQUENCE
	{
              aluSIPSnoopingEndedCallIndex  Integer32,
              aluSIPSnoopingEndedCallId  SnmpAdminString,
              aluSIPSnoopingEndedCallTagA SnmpAdminString,
              aluSIPSnoopingEndedCallTagB SnmpAdminString,
              aluSIPSnoopingEndedCallIpAddrAType InetAddressType,
              aluSIPSnoopingEndedCallIpAddrA InetAddress,
              aluSIPSnoopingEndedCallIpAddrBType InetAddressType,
              aluSIPSnoopingEndedCallIpAddrB InetAddress,
              aluSIPSnoopingEndedCallL4portA Integer32,
              aluSIPSnoopingEndedCallL4portB Integer32,
              aluSIPSnoopingEndedCallSipMediaType SnmpAdminString,
              aluSIPSnoopingEndedCallStart DateAndTime,
              aluSIPSnoopingEndedCallEnd DateAndTime,
              aluSIPSnoopingEndedCallRtpCountA Counter64,
              aluSIPSnoopingEndedCallRtcpCountA  Counter64,
              aluSIPSnoopingEndedCallRuleNameA SnmpAdminString,
              aluSIPSnoopingEndedCallRtpCountB Counter64,
              aluSIPSnoopingEndedCallRtcpCountB Counter64,
              aluSIPSnoopingEndedCallRuleNameB SnmpAdminString,
	          aluSIPSnoopingEndedCallEndReason SnmpAdminString,
              aluSIPSnoopingEndedCallTrustDSCPStatusA INTEGER,
              aluSIPSnoopingEndedCallTrustDSCPStatusB INTEGER,
              aluSIPSnoopingEndedCallPacketCountA Counter64,
              aluSIPSnoopingEndedCallPacketCountB Counter64
	}

aluSIPSnoopingEndedCallIndex   OBJECT-TYPE
SYNTAX         Integer32 (0..8000)
MAX-ACCESS     not-accessible
STATUS         current
DESCRIPTION    " aluSIPSnoopingEndedCallIndex  "
::= { aluSIPSnoopingEndedCallSummaryEntry 1 }


aluSIPSnoopingEndedCallId  OBJECT-TYPE
SYNTAX         SnmpAdminString (SIZE (0..128))
MAX-ACCESS     read-only
STATUS         current
DESCRIPTION    " Ended call CallId"
::= { aluSIPSnoopingEndedCallSummaryEntry   2 }


aluSIPSnoopingEndedCallTagA OBJECT-TYPE
SYNTAX         SnmpAdminString (SIZE (0..64))
MAX-ACCESS     read-only
STATUS         current
DESCRIPTION    " Ended call TagA"
::= { aluSIPSnoopingEndedCallSummaryEntry   3 }


aluSIPSnoopingEndedCallTagB  OBJECT-TYPE
SYNTAX         SnmpAdminString (SIZE (0..64))
MAX-ACCESS     read-only
STATUS         current
DESCRIPTION    " Ended call tag for direction A to B"
::= { aluSIPSnoopingEndedCallSummaryEntry   4 }


aluSIPSnoopingEndedCallIpAddrAType  OBJECT-TYPE
SYNTAX         InetAddressType {ipv4(1)}
MAX-ACCESS     read-only
STATUS         current
DESCRIPTION    " Ended call ip address for direction A to B Type"
DEFVAL         { ipv4 }
::= { aluSIPSnoopingEndedCallSummaryEntry   5 }

aluSIPSnoopingEndedCallIpAddrA  OBJECT-TYPE
SYNTAX         InetAddress
MAX-ACCESS     read-only
STATUS         current
DESCRIPTION    " Ended call ip address for direction A to B"
::= { aluSIPSnoopingEndedCallSummaryEntry   6 }


aluSIPSnoopingEndedCallIpAddrBType  OBJECT-TYPE
SYNTAX         InetAddressType { ipv4(1) }
MAX-ACCESS     read-only
STATUS         current
DESCRIPTION    " Ended call ip address for direction B to A Type"
DEFVAL         { ipv4 }
::= { aluSIPSnoopingEndedCallSummaryEntry   7 }

aluSIPSnoopingEndedCallIpAddrB  OBJECT-TYPE
SYNTAX         InetAddress
MAX-ACCESS     read-only
STATUS         current
DESCRIPTION    " Ended call ip address for direction B to A"
::= { aluSIPSnoopingEndedCallSummaryEntry   8 }

aluSIPSnoopingEndedCallL4portA  OBJECT-TYPE
SYNTAX         Integer32 (0..65535)
MAX-ACCESS     read-only
STATUS         current
DESCRIPTION    " Ended call L4port for call direction A to B"
::= { aluSIPSnoopingEndedCallSummaryEntry   9 }


aluSIPSnoopingEndedCallL4portB  OBJECT-TYPE
SYNTAX         Integer32 (0..65535)
MAX-ACCESS     read-only
STATUS         current
DESCRIPTION    " Ended call L4port for call direction B to A"
::= { aluSIPSnoopingEndedCallSummaryEntry   10 }


aluSIPSnoopingEndedCallSipMediaType  OBJECT-TYPE
SYNTAX         SnmpAdminString
MAX-ACCESS     read-only
STATUS         current
DESCRIPTION    " Ended call SipMediaType"
::= { aluSIPSnoopingEndedCallSummaryEntry  11 }


aluSIPSnoopingEndedCallStart  OBJECT-TYPE
SYNTAX         DateAndTime
MAX-ACCESS     read-only
STATUS         current
DESCRIPTION    " Ended call CallStart DateAndTime"
::= { aluSIPSnoopingEndedCallSummaryEntry   12 }


aluSIPSnoopingEndedCallEnd  OBJECT-TYPE
SYNTAX         DateAndTime
MAX-ACCESS     read-only
STATUS         current
DESCRIPTION    " Ended call CallEnd DateAndTime"
::= { aluSIPSnoopingEndedCallSummaryEntry   13 }


aluSIPSnoopingEndedCallRtpCountA  OBJECT-TYPE
SYNTAX         Counter64
MAX-ACCESS     read-only
STATUS         current
DESCRIPTION    " Ended call RtpCount for call direction A to B"
::= { aluSIPSnoopingEndedCallSummaryEntry   14 }


aluSIPSnoopingEndedCallRtcpCountA  OBJECT-TYPE
SYNTAX         Counter64
MAX-ACCESS     read-only
STATUS         current
DESCRIPTION    " Ended call RtcpCount for call direction A to B"
::= { aluSIPSnoopingEndedCallSummaryEntry   15 }


aluSIPSnoopingEndedCallRuleNameA  OBJECT-TYPE
SYNTAX         SnmpAdminString
MAX-ACCESS     read-only
STATUS         current
DESCRIPTION    " Ended call RuleName for call direction A to B"
::= { aluSIPSnoopingEndedCallSummaryEntry   16 }


aluSIPSnoopingEndedCallRtpCountB  OBJECT-TYPE
SYNTAX         Counter64
MAX-ACCESS     read-only
STATUS         current
DESCRIPTION    " Ended call RtpCount for call direction B to A"
::= { aluSIPSnoopingEndedCallSummaryEntry   17 }


aluSIPSnoopingEndedCallRtcpCountB  OBJECT-TYPE
SYNTAX         Counter64
MAX-ACCESS     read-only
STATUS         current
DESCRIPTION    " Ended call RtcpCount for call direction B to A"
::= { aluSIPSnoopingEndedCallSummaryEntry   18 }


aluSIPSnoopingEndedCallRuleNameB  OBJECT-TYPE
SYNTAX         SnmpAdminString
MAX-ACCESS     read-only
STATUS         current
DESCRIPTION    " Ended call RuleName for call direction B to A"
::= { aluSIPSnoopingEndedCallSummaryEntry   19 }

aluSIPSnoopingEndedCallEndReason  OBJECT-TYPE
SYNTAX         SnmpAdminString
MAX-ACCESS     read-only
STATUS         current
DESCRIPTION    "Ended call reason"
::= { aluSIPSnoopingEndedCallSummaryEntry   20 }

aluSIPSnoopingEndedCallTrustDSCPStatusA OBJECT-TYPE
SYNTAX      INTEGER {
                enable (1),
                disable (2)
			}
MAX-ACCESS     read-only
STATUS         current
DESCRIPTION    "Indicates whether trusted dscp was enabled for the call in direction A to B"
::= { aluSIPSnoopingEndedCallSummaryEntry   21 }

aluSIPSnoopingEndedCallTrustDSCPStatusB OBJECT-TYPE
SYNTAX      INTEGER {
                enable (1),
                disable (2)
			}
MAX-ACCESS     read-only
STATUS         current
DESCRIPTION    "Indicates whether trusted dscp was enabled for the call in direction B to A"
::= { aluSIPSnoopingEndedCallSummaryEntry   22 }

aluSIPSnoopingEndedCallPacketCountA OBJECT-TYPE
SYNTAX         Counter64
MAX-ACCESS     read-only
STATUS         current
DESCRIPTION    "Total Number of RTP packets from A to B for Ended Calls"
::= { aluSIPSnoopingEndedCallSummaryEntry   23 }

aluSIPSnoopingEndedCallPacketCountB OBJECT-TYPE
SYNTAX         Counter64
MAX-ACCESS     read-only
STATUS         current
DESCRIPTION    "Total Number of RTP packets from B to A for Ended Calls"
::= { aluSIPSnoopingEndedCallSummaryEntry   24 }


aluSIPSnoopingEndedCallStatsTable  OBJECT-TYPE
  SYNTAX                SEQUENCE OF SIPSnoopingEndedCallStatsEntry
  MAX-ACCESS            not-accessible
  STATUS                current
  DESCRIPTION           "A table containing SIP Snooping Call statistics information."
  ::= { aluSIPSnoopingMIBObjects 7 }

aluSIPSnoopingEndedCallStatsEntry  OBJECT-TYPE
  SYNTAX                SIPSnoopingEndedCallStatsEntry
  MAX-ACCESS            not-accessible
  STATUS                current
  DESCRIPTION           "SIP snooping CallStats entry."
  INDEX { aluSIPSnoopingEndedCallIndex }
  ::= { aluSIPSnoopingEndedCallStatsTable 1 }

SIPSnoopingEndedCallStatsEntry	::=
	SEQUENCE
	{
              aluSIPSnoopingEndedCallStatsJitterViolationsA  Integer32,
              aluSIPSnoopingEndedCallStatsJitterViolationsB  Integer32,
              aluSIPSnoopingEndedCallStatsRtdViolationsA  Integer32,
              aluSIPSnoopingEndedCallStatsRtdViolationsB  Integer32,
              aluSIPSnoopingEndedCallStatsPktLossViolationsA  Integer32,
              aluSIPSnoopingEndedCallStatsPktLossViolationsB  Integer32,
              aluSIPSnoopingEndedCallStatsMosViolationsA  Integer32,
              aluSIPSnoopingEndedCallStatsMosViolationsB  Integer32,
              aluSIPSnoopingEndedCallStatsRfactorViolationsA  Integer32,
              aluSIPSnoopingEndedCallStatsRfactorViolationsB  Integer32,
              aluSIPSnoopingEndedCallStatsJitterMaxA  Integer32,
              aluSIPSnoopingEndedCallStatsJitterMinA  Integer32,
              aluSIPSnoopingEndedCallStatsJitterAvgA  Integer32,
              aluSIPSnoopingEndedCallStatsJitterMaxB  Integer32,
              aluSIPSnoopingEndedCallStatsJitterMinB  Integer32,
              aluSIPSnoopingEndedCallStatsJitterAvgB  Integer32,
              aluSIPSnoopingEndedCallStatsRtdMaxA  Integer32,
              aluSIPSnoopingEndedCallStatsRtdMinA  Integer32,
              aluSIPSnoopingEndedCallStatsRtdAvgA  Integer32,
              aluSIPSnoopingEndedCallStatsRtdMaxB  Integer32,
              aluSIPSnoopingEndedCallStatsRtdMinB  Integer32,
              aluSIPSnoopingEndedCallStatsRtdAvgB  Integer32,
              aluSIPSnoopingEndedCallStatsPktLossMaxA  Integer32,
              aluSIPSnoopingEndedCallStatsPktLossMinA  Integer32,
              aluSIPSnoopingEndedCallStatsPktLossAvgA  Integer32,
              aluSIPSnoopingEndedCallStatsPktLossMaxB  Integer32,
              aluSIPSnoopingEndedCallStatsPktLossMinB  Integer32,
              aluSIPSnoopingEndedCallStatsPktLossAvgB  Integer32,
              aluSIPSnoopingEndedCallStatsRfactorMaxA  Integer32,
              aluSIPSnoopingEndedCallStatsRfactorMinA  Integer32,
              aluSIPSnoopingEndedCallStatsRfactorAvgA  Integer32,
              aluSIPSnoopingEndedCallStatsRfactorMaxB  Integer32,
              aluSIPSnoopingEndedCallStatsRfactorMinB  Integer32,
              aluSIPSnoopingEndedCallStatsRfactorAvgB  Integer32,
              aluSIPSnoopingEndedCallStatsMosMaxA  Integer32,
              aluSIPSnoopingEndedCallStatsMosMinA  Integer32,
              aluSIPSnoopingEndedCallStatsMosAvgA  Integer32,
              aluSIPSnoopingEndedCallStatsMosMaxB  Integer32,
              aluSIPSnoopingEndedCallStatsMosMinB  Integer32,
              aluSIPSnoopingEndedCallStatsMosAvgB  Integer32
	}

aluSIPSnoopingEndedCallStatsJitterViolationsA  OBJECT-TYPE
SYNTAX         Integer32 (0..100)
MAX-ACCESS     read-only
STATUS         current
DESCRIPTION    "Ended call Rtcp jitter violation (%) for call direction A to B"
::= { aluSIPSnoopingEndedCallStatsEntry   1 }


aluSIPSnoopingEndedCallStatsJitterViolationsB  OBJECT-TYPE
SYNTAX         Integer32 (0..100)
MAX-ACCESS     read-only
STATUS         current
DESCRIPTION    "Ended call Rtcp jitter violation (%) for call direction B to A"
::= { aluSIPSnoopingEndedCallStatsEntry   2 }


aluSIPSnoopingEndedCallStatsRtdViolationsA  OBJECT-TYPE
SYNTAX         Integer32 (0..100)
MAX-ACCESS     read-only
STATUS         current
DESCRIPTION    "Ended call round trip delay violation (%) for call direction A to B"
::= { aluSIPSnoopingEndedCallStatsEntry   3 }


aluSIPSnoopingEndedCallStatsRtdViolationsB  OBJECT-TYPE
SYNTAX         Integer32 (0..100)
MAX-ACCESS     read-only
STATUS         current
DESCRIPTION    "Ended call round trip delay violation (%) for call direction B to A"
::= { aluSIPSnoopingEndedCallStatsEntry   4 }


aluSIPSnoopingEndedCallStatsPktLossViolationsA  OBJECT-TYPE
SYNTAX         Integer32 (0..100)
MAX-ACCESS     read-only
STATUS         current
DESCRIPTION    "Ended call packet loss Violations (%) for call direction A to B"
::= { aluSIPSnoopingEndedCallStatsEntry   5 }

aluSIPSnoopingEndedCallStatsPktLossViolationsB  OBJECT-TYPE
SYNTAX         Integer32 (0..100)
MAX-ACCESS     read-only
STATUS         current
DESCRIPTION    "Ended call packet loss Violations (%) for call direction B to A"
::= { aluSIPSnoopingEndedCallStatsEntry   6 }


aluSIPSnoopingEndedCallStatsMosViolationsA  OBJECT-TYPE
SYNTAX         Integer32 (0..100)
MAX-ACCESS     read-only
STATUS         current
DESCRIPTION    "Ended call Mos Violation (%) for call direction A to B"
::= { aluSIPSnoopingEndedCallStatsEntry   7 }


aluSIPSnoopingEndedCallStatsMosViolationsB  OBJECT-TYPE
SYNTAX         Integer32 (0..100)
MAX-ACCESS     read-only
STATUS         current
DESCRIPTION    "Ended call Mos Violation (%) for call direction B to A"
::= { aluSIPSnoopingEndedCallStatsEntry   8 }


aluSIPSnoopingEndedCallStatsRfactorViolationsA  OBJECT-TYPE
SYNTAX         Integer32 (0..100)
MAX-ACCESS     read-only
STATUS         current
DESCRIPTION    "Ended calls Rfactor Violations (%) for direction A to B"
::= { aluSIPSnoopingEndedCallStatsEntry   9 }


aluSIPSnoopingEndedCallStatsRfactorViolationsB  OBJECT-TYPE
SYNTAX         Integer32 (0..100)
MAX-ACCESS     read-only
STATUS         current
DESCRIPTION    "Ended calls Rfactor Violations (%) for direction B to A"
::= { aluSIPSnoopingEndedCallStatsEntry   10 }


aluSIPSnoopingEndedCallStatsJitterMaxA  OBJECT-TYPE
SYNTAX         Integer32 (0..300)
MAX-ACCESS     read-only
STATUS         current
DESCRIPTION    "Ended call max Jitter for call direction A to B"
::= { aluSIPSnoopingEndedCallStatsEntry   11 }

aluSIPSnoopingEndedCallStatsJitterMinA  OBJECT-TYPE
SYNTAX         Integer32 (0..300)
MAX-ACCESS     read-only
STATUS         current
DESCRIPTION    "Ended call min Jitter for call direction A to B"
::= { aluSIPSnoopingEndedCallStatsEntry   12 }


aluSIPSnoopingEndedCallStatsJitterAvgA  OBJECT-TYPE
SYNTAX         Integer32 (0..300)
MAX-ACCESS     read-only
STATUS         current
DESCRIPTION    "Ended call avg Jitter for call direction A to B"
::= { aluSIPSnoopingEndedCallStatsEntry   13 }


aluSIPSnoopingEndedCallStatsJitterMaxB  OBJECT-TYPE
SYNTAX         Integer32 (0..300)
MAX-ACCESS     read-only
STATUS         current
DESCRIPTION    "Ended call max Jitter for call direction B to A"
::= { aluSIPSnoopingEndedCallStatsEntry   14 }


aluSIPSnoopingEndedCallStatsJitterMinB  OBJECT-TYPE
SYNTAX         Integer32 (0..300)
MAX-ACCESS     read-only
STATUS         current
DESCRIPTION    "Ended call min Jitter for call direction B to A"
::= { aluSIPSnoopingEndedCallStatsEntry   15 }


aluSIPSnoopingEndedCallStatsJitterAvgB  OBJECT-TYPE
SYNTAX         Integer32 (0..300)
MAX-ACCESS     read-only
STATUS         current
DESCRIPTION    "Ended call avg Jitter for call direction B to A"
::= { aluSIPSnoopingEndedCallStatsEntry   16 }

aluSIPSnoopingEndedCallStatsRtdMaxA  OBJECT-TYPE
SYNTAX         Integer32 (0..500)
MAX-ACCESS     read-only
STATUS         current
DESCRIPTION    "Active call max round trip delay for call direciton A to B"
::= { aluSIPSnoopingEndedCallStatsEntry   17 }


aluSIPSnoopingEndedCallStatsRtdMinA  OBJECT-TYPE
SYNTAX         Integer32 (0..500)
MAX-ACCESS     read-only
STATUS         current
DESCRIPTION    "Active call min round trip delay for call direciton A to B"
::= { aluSIPSnoopingEndedCallStatsEntry   18 }


aluSIPSnoopingEndedCallStatsRtdAvgA  OBJECT-TYPE
SYNTAX         Integer32 (0..500)
MAX-ACCESS     read-only
STATUS         current
DESCRIPTION    "Active call Avg round trip delay for call direciton A to B"
::= { aluSIPSnoopingEndedCallStatsEntry   19 }


aluSIPSnoopingEndedCallStatsRtdMaxB  OBJECT-TYPE
SYNTAX         Integer32 (0..500)
MAX-ACCESS     read-only
STATUS         current
DESCRIPTION    "Active call max round trip delay for call direciton B to A"
::= { aluSIPSnoopingEndedCallStatsEntry   20 }


aluSIPSnoopingEndedCallStatsRtdMinB  OBJECT-TYPE
SYNTAX         Integer32 (0..500)
MAX-ACCESS     read-only
STATUS         current
DESCRIPTION    "Active call min round trip delay for call direciton B to A"
::= { aluSIPSnoopingEndedCallStatsEntry   21 }


aluSIPSnoopingEndedCallStatsRtdAvgB  OBJECT-TYPE
SYNTAX         Integer32 (0..500)
MAX-ACCESS     read-only
STATUS         current
DESCRIPTION    "Active call Avg round trip delay for call direciton B to A"
::= { aluSIPSnoopingEndedCallStatsEntry   22 }


aluSIPSnoopingEndedCallStatsPktLossMaxA  OBJECT-TYPE
SYNTAX         Integer32 (0..99)
MAX-ACCESS     read-only
STATUS         current
DESCRIPTION    "Ended call max packet loss (%) for call direction A to B"
::= { aluSIPSnoopingEndedCallStatsEntry   23 }


aluSIPSnoopingEndedCallStatsPktLossMinA  OBJECT-TYPE
SYNTAX         Integer32 (0..99)
MAX-ACCESS     read-only
STATUS         current
DESCRIPTION    "Ended call min packet loss (%) for call direction A to B"
::= { aluSIPSnoopingEndedCallStatsEntry   24 }


aluSIPSnoopingEndedCallStatsPktLossAvgA  OBJECT-TYPE
SYNTAX         Integer32 (0..99)
MAX-ACCESS     read-only
STATUS         current
DESCRIPTION    "Ended call Avg packet loss (%) for call direction A to B"
::= { aluSIPSnoopingEndedCallStatsEntry   25 }


aluSIPSnoopingEndedCallStatsPktLossMaxB  OBJECT-TYPE
SYNTAX         Integer32 (0..99)
MAX-ACCESS     read-only
STATUS         current
DESCRIPTION    "Ended call max packet loss (%) for call direction B to A"
::= { aluSIPSnoopingEndedCallStatsEntry   26 }


aluSIPSnoopingEndedCallStatsPktLossMinB  OBJECT-TYPE
SYNTAX         Integer32 (0..99)
MAX-ACCESS     read-only
STATUS         current
DESCRIPTION    "Ended call min packet loss (%) for call direction B to A"
::= { aluSIPSnoopingEndedCallStatsEntry   27 }


aluSIPSnoopingEndedCallStatsPktLossAvgB  OBJECT-TYPE
SYNTAX         Integer32 (0..99)
MAX-ACCESS     read-only
STATUS         current
DESCRIPTION    "Ended call Avg packet loss (%) for call direction B to A"
::= { aluSIPSnoopingEndedCallStatsEntry   28 }


aluSIPSnoopingEndedCallStatsRfactorMaxA  OBJECT-TYPE
SYNTAX         Integer32 (0..100)
MAX-ACCESS     read-only
STATUS         current
DESCRIPTION    "Ended call max Rfactor for call direction A to B"
::= { aluSIPSnoopingEndedCallStatsEntry   29 }


aluSIPSnoopingEndedCallStatsRfactorMinA  OBJECT-TYPE
SYNTAX         Integer32 (0..100)
MAX-ACCESS     read-only
STATUS         current
DESCRIPTION    "Ended call min Rfactor for call direction A to B"
::= { aluSIPSnoopingEndedCallStatsEntry   30 }


aluSIPSnoopingEndedCallStatsRfactorAvgA  OBJECT-TYPE
SYNTAX         Integer32 (0..100)
MAX-ACCESS     read-only
STATUS         current
DESCRIPTION    "Ended call avg Rfactor for call direction A to B"
::= { aluSIPSnoopingEndedCallStatsEntry   31 }


aluSIPSnoopingEndedCallStatsRfactorMaxB  OBJECT-TYPE
SYNTAX         Integer32 (0..100)
MAX-ACCESS     read-only
STATUS         current
DESCRIPTION    "Ended call max Rfactor for call direction B to A"
::= { aluSIPSnoopingEndedCallStatsEntry   32 }


aluSIPSnoopingEndedCallStatsRfactorMinB  OBJECT-TYPE
SYNTAX         Integer32 (0..100)
MAX-ACCESS     read-only
STATUS         current
DESCRIPTION    "Ended call min Rfactor for call direction B to A"
::= { aluSIPSnoopingEndedCallStatsEntry   33 }


aluSIPSnoopingEndedCallStatsRfactorAvgB  OBJECT-TYPE
SYNTAX         Integer32 (0..100)
MAX-ACCESS     read-only
STATUS         current
DESCRIPTION    "Ended call avg Rfactor for call direction B to A"
::= { aluSIPSnoopingEndedCallStatsEntry   34 }


aluSIPSnoopingEndedCallStatsMosMaxA  OBJECT-TYPE
SYNTAX         Integer32 (0..50)
UNITS          "tenths of value"
MAX-ACCESS     read-only
STATUS         current
DESCRIPTION    "Displays the Ended call max Mos for direction A to B, multiplied by a factor of 10"
::= { aluSIPSnoopingEndedCallStatsEntry   35 }


aluSIPSnoopingEndedCallStatsMosMinA  OBJECT-TYPE
SYNTAX         Integer32 (0..50)
UNITS          "tenths of value"
MAX-ACCESS     read-only
STATUS         current
DESCRIPTION    "Displays the Ended call min Mos for direction A to B, multiplied by a factor of 10"
::= { aluSIPSnoopingEndedCallStatsEntry   36 }


aluSIPSnoopingEndedCallStatsMosAvgA  OBJECT-TYPE
SYNTAX         Integer32 (0..50)
UNITS          "tenths of value"
MAX-ACCESS     read-only
STATUS         current
DESCRIPTION    "Displays the Ended call Avg Mos for direction A to B, multiplied by a factor of 10"
::= { aluSIPSnoopingEndedCallStatsEntry   37 }


aluSIPSnoopingEndedCallStatsMosMaxB  OBJECT-TYPE
SYNTAX         Integer32 (0..50)
UNITS          "tenths of value"
MAX-ACCESS     read-only
STATUS         current
DESCRIPTION    "Displays the Ended call max Mos for direction B to A, multiplied by a factor of 10"
::= { aluSIPSnoopingEndedCallStatsEntry   38 }


aluSIPSnoopingEndedCallStatsMosMinB  OBJECT-TYPE
SYNTAX         Integer32 (0..50)
UNITS          "tenths of value"
MAX-ACCESS     read-only
STATUS         current
DESCRIPTION    "Displays the Ended call min Mos for direction B to A, multiplied by a factor of 10"
::= { aluSIPSnoopingEndedCallStatsEntry   39 }


aluSIPSnoopingEndedCallStatsMosAvgB  OBJECT-TYPE
SYNTAX         Integer32 (0..50)
UNITS          "tenths of value"
MAX-ACCESS     read-only
STATUS         current
DESCRIPTION    "Displays the Ended call Avg Mos for direction B to A, multiplied by a factor of 10"
::= { aluSIPSnoopingEndedCallStatsEntry   40 }

alaSIPSnoopingRegisteredClientsTable  OBJECT-TYPE
  SYNTAX                SEQUENCE OF SIPSnoopingRegisteredClientsEntry
  MAX-ACCESS            not-accessible
  STATUS                current
  DESCRIPTION           "A table containing SIP Snooping Registered Clients information."
  ::= { aluSIPSnoopingMIBObjects 9 }

alaSIPSnoopingRegisteredClientsEntry  OBJECT-TYPE
  SYNTAX                SIPSnoopingRegisteredClientsEntry
  MAX-ACCESS            not-accessible
  STATUS                current
  DESCRIPTION           "SIP snooping Registered Clients entry."
  INDEX { alaSIPSnoopingRegisteredClientNumber }
  ::= { alaSIPSnoopingRegisteredClientsTable 1 }

SIPSnoopingRegisteredClientsEntry	::=
	SEQUENCE
	{
	      alaSIPSnoopingRegisteredClientNumber Integer32,
              alaSIPSnoopingRegisteredClientAddrType  InetAddressType,
              alaSIPSnoopingRegisteredClientAddr  InetAddress
	}

alaSIPSnoopingRegisteredClientNumber OBJECT-TYPE
SYNTAX         Integer32(1..9999)
MAX-ACCESS     not-accessible
STATUS         current
DESCRIPTION    "Registered Client Number"
::= { alaSIPSnoopingRegisteredClientsEntry  1 }

alaSIPSnoopingRegisteredClientAddrType  OBJECT-TYPE
SYNTAX         InetAddressType { ipv4(1) }
MAX-ACCESS     read-only
STATUS         current
DESCRIPTION    "Registered SIP Client Address Type"
::= { alaSIPSnoopingRegisteredClientsEntry  2 }

alaSIPSnoopingRegisteredClientAddr  OBJECT-TYPE
SYNTAX         InetAddress
MAX-ACCESS     read-only
STATUS         current
DESCRIPTION    "Registered SIP Client Address"
::= { alaSIPSnoopingRegisteredClientsEntry  3 }
-- xxxxxxxxxxxxxxxxxxxxxxxxxxxxxxxxxxxxxxxxxxxxxxxxxxxxxxxxxxxxxxxxx

aluSIPSnoopingNotificationObjects 	OBJECT	IDENTIFIER ::= { aluSIPSnoopingMIBObjects 8 }

-- xxxxxxxxxxxxxxxxxxxxxxxxxxxxxxxxxxxxxxxxxxxxxxxxxxxxxxxxxxxxxxxxx
alaSIPSnoopingCallViolationType OBJECT-TYPE
    SYNTAX      INTEGER {
        jitterViolation (1), --jitter violation
        rtdViolation (2), --rtd violation
        mosViolation (3), --mos violation
        rFactorViolation (4), -- Rfactor violation
        pktLossViolation (5) -- Packet loss violation
    }
MAX-ACCESS     accessible-for-notify
STATUS         current
DESCRIPTION    "Indicates type of the active call violation"
::= { aluSIPSnoopingNotificationObjects 1 }



alaSIPSnoopingRTCPOverThreshold NOTIFICATION-TYPE
OBJECTS  {
	aluSIPSnoopingActiveCallIpAddrA,
        aluSIPSnoopingActiveCallIpAddrB,
        aluSIPSnoopingActiveCallL4portB,
        aluSIPSnoopingActiveCallSipMediaType,
        alaSIPSnoopingCallViolationType
}
STATUS   current
DESCRIPTION
"This trap is sent in the event of one or more RTCP parameters exceeding the threshold limit"
::= { aluSIPSnoopingMIBNotifications 1 }

alaSIPSnoopingSignallingLost NOTIFICATION-TYPE
OBJECTS  {
           physicalIndex
        }
STATUS   current
DESCRIPTION
"This trap is sent in the event of SIP signalling messages getting lost due to rate-limiting"
::= { aluSIPSnoopingMIBNotifications 2 }

alaSIPSnoopingRTCPPktsLost NOTIFICATION-TYPE
OBJECTS  {
        physicalIndex
}
STATUS   current
DESCRIPTION
"This trap is sent in the event of RTCP packets lost due to rate-limiting"
::= { aluSIPSnoopingMIBNotifications 3 }

alaSIPSnoopingACLPreemptedBySOSCall NOTIFICATION-TYPE
OBJECTS  {
        physicalIndex,
        aluSIPSnoopingEndedCallIpAddrA,
        aluSIPSnoopingEndedCallIpAddrB,
        aluSIPSnoopingEndedCallL4portA,
        aluSIPSnoopingEndedCallL4portB
}
STATUS   current
DESCRIPTION
"This trap is sent in the event of SIP snooping RTP/RTCP ACL entry is preempted by SOS call"
::= { aluSIPSnoopingMIBNotifications 4 }

alaSIPSnoopingCallRecordsFileMoved NOTIFICATION-TYPE
OBJECTS  {
    aluSIPSnoopingThresholdNumberOfCalls
}
STATUS   current
DESCRIPTION
"This notification is generated when SIP SNOOPING ended call records flash file is moved from /flash/switch/sip_call_record.txt to /flash/switch/sip_call_record.txt.old. This happens when the configured call record storage limit is reached and possibly at boot-up if /flash/switch/sip_call_record.txt from previous run exists at the first check. Please configure aluSIPSnoopingThresholdNumberOfCalls appropriately to control frequency of file movement and this notification."
::= { aluSIPSnoopingMIBNotifications 5 }

-- xxxxxxxxxxxxxxxxxxxxxxxxxxxxxxxxxxxxxxxxxxxxxxxxxxxxxxxxxxxxxxxxxxxxxxxxxxxx
-- Compliance
-- xxxxxxxxxxxxxxxxxxxxxxxxxxxxxxxxxxxxxxxxxxxxxxxxxxxxxxxxxxxxxxxxxxxxxxxxxxxx

aluSIPSnoopingMIBCompliance MODULE-COMPLIANCE
        STATUS          current
        DESCRIPTION
                                "Compliance statement for SIP Snooping."
        MODULE
                MANDATORY-GROUPS
                {
                        aluSIPSnoopingPortConfigGroup,
                        aluSIPSnoopingThresholdGroup,
                        aluSIPSnoopingConfigGroup,
                        aluSIPSnoopingSummaryGroup,
                        aluSIPSnoopingStatsGroup,
                        alaSIPSnoopingNotificationGroup,
			alaSIPSnoopingRegisteredClientsGroup
                }
        ::= { aluSIPSnoopingMIBCompliances 1 }


-- xxxxxxxxxxxxxxxxxxxxxxxxxxxxxxxxxxxxxxxxxxxxxxxxxxxxxxxxxxxxxxxxxxxxxxxxxxxx
-- Units of Conformance
-- xxxxxxxxxxxxxxxxxxxxxxxxxxxxxxxxxxxxxxxxxxxxxxxxxxxxxxxxxxxxxxxxxxxxxxxxxxxx

aluSIPSnoopingPortConfigGroup      OBJECT-GROUP
        OBJECTS
        {
            aluSIPSnoopingPortConfigPortStatus,
            aluSIPSnoopingPortConfigPortMode
        }
        STATUS current
        DESCRIPTION
                                "Collection of objects for Port configurations for SIP Snooping applications."
        ::= { aluSIPSnoopingMIBGroups 1 }

aluSIPSnoopingThresholdGroup      OBJECT-GROUP
        OBJECTS
        {
                aluSIPSnoopingThresholdJitter,
		aluSIPSnoopingThresholdPacketLost,
		aluSIPSnoopingThresholdRoundTripDelay,
		aluSIPSnoopingThresholdRFactor,
		aluSIPSnoopingThresholdMOS
        }
        STATUS current
        DESCRIPTION
                                "Collection of objects for Threshold configfurations for SIP Snooping applications."
        ::= { aluSIPSnoopingMIBGroups 2 }

aluSIPSnoopingConfigGroup      OBJECT-GROUP
        OBJECTS
        {
               aluSIPSnoopingStatus,
               aluSIPSnoopingSIPTrustedServerIPAddress1,
	     aluSIPSnoopingSIPTrustedServerIPAddress1Type,
               aluSIPSnoopingSIPTrustedServerIPAddress2,
	     aluSIPSnoopingSIPTrustedServerIPAddress2Type,
               aluSIPSnoopingSIPTrustedServerIPAddress3,
	     aluSIPSnoopingSIPTrustedServerIPAddress3Type,
               aluSIPSnoopingSIPTrustedServerIPAddress4,
	     aluSIPSnoopingSIPTrustedServerIPAddress4Type,
               aluSIPSnoopingSIPTrustedServerIPAddress5,
	     aluSIPSnoopingSIPTrustedServerIPAddress5Type,
               aluSIPSnoopingSIPTrustedServerIPAddress6,
	     aluSIPSnoopingSIPTrustedServerIPAddress6Type,
               aluSIPSnoopingSIPTrustedServerIPAddress7,
	     aluSIPSnoopingSIPTrustedServerIPAddress7Type,
               aluSIPSnoopingSIPTrustedServerIPAddress8,
	     aluSIPSnoopingSIPTrustedServerIPAddress8Type,
               aluSIPSnoopingSIPControlDSCP,
               aluSIPSnoopingSOSCallNumber1,
               aluSIPSnoopingSOSCallNumber2,
               aluSIPSnoopingSOSCallNumber3,
               aluSIPSnoopingSOSCallNumber4,
               aluSIPSnoopingSOSCallRTPDSCP,
               aluSIPSnoopingThresholdNumberOfCalls,
               aluSIPSnoopingClearStats,
               aluSIPSnoopingTotalCallsProcessed,
               aluSIPSnoopingTotalAudioStreams,
               aluSIPSnoopingTotalVideoStreams,
               aluSIPSnoopingTotalOtherStreams,
               aluSIPSnoopingAudioStreamsBeyondThreshold,
               aluSIPSnoopingVideoStreamsBeyondThreshold,
               aluSIPSnoopingOtherStreamsBeyondThreshold,
               aluSIPSnoopingActiveStreamsBeyondThreshold,
               aluSIPSnoopingActiveAudioStreams,
               aluSIPSnoopingActiveVideoStreams,
               aluSIPSnoopingActiveOtherStreams,
               aluSIPSnoopingHardwareSIPPackets,
               aluSIPSnoopingSoftwareSIPPackets,
               aluSIPSnoopingSIPInvitePackets,
               aluSIPSnoopingSIPAckPackets,
               aluSIPSnoopingSIPByePackets,
               aluSIPSnoopingSIPUpdatePackets,
               aluSIPSnoopingSIPPrackPackets,
               aluSIPSnoopingSIPRecvdResponsePackets,
               aluSIPSnoopingSIPDiscardedPackets,
               aluSIPSnoopingSIPDiscardedNoTrustServerPackets,
               aluSIPSnoopingSIPDroppedSWErrorPackets,
               aluSIPSnoopingTotalEmergencyCalls,
               aluSIPSnoopingThresholdJitter,
               aluSIPSnoopingThresholdPacketLost,
               aluSIPSnoopingThresholdRoundTripDelay,
               aluSIPSnoopingThresholdRFactor,
               aluSIPSnoopingThresholdMOS,
               aluSIPSnoopingSIPUdpPort1,
               aluSIPSnoopingSIPUdpPort2,
               aluSIPSnoopingSIPUdpPort3,
               aluSIPSnoopingSIPUdpPort4,
               aluSIPSnoopingSIPUdpPort5,
               aluSIPSnoopingSIPUdpPort6,
               aluSIPSnoopingSIPUdpPort7,
               aluSIPSnoopingSIPUdpPort8,
               aluSIPSnoopingSIPTcpPort1,
               aluSIPSnoopingSIPTcpPort2,
               aluSIPSnoopingSIPTcpPort3,
               aluSIPSnoopingSIPTcpPort4,
               aluSIPSnoopingSIPTcpPort5,
               aluSIPSnoopingSIPTcpPort6,
               aluSIPSnoopingSIPTcpPort7,
               aluSIPSnoopingSIPTcpPort8,
               aluSIPSnoopingClearEndedCalls,
               alaSIPSnoopingRsvdHwResources,
               alaSIPSnoopingCallViolationType,
	       alaSIPSnoopingSIPCpuRateLimit
        }
        STATUS current
        DESCRIPTION
                                "Collection of objects for Port configurations for SIP Snooping applications."
        ::= { aluSIPSnoopingMIBGroups 3 }

aluSIPSnoopingSummaryGroup OBJECT-GROUP
        OBJECTS
          {
              aluSIPSnoopingActiveCallId,
              aluSIPSnoopingActiveCallTagA,
              aluSIPSnoopingActiveCallTagB,
              aluSIPSnoopingActiveCallIpAddrA,
              aluSIPSnoopingActiveCallIpAddrAType,
              aluSIPSnoopingActiveCallIpAddrB,
              aluSIPSnoopingActiveCallIpAddrBType,
              aluSIPSnoopingActiveCallL4portA,
              aluSIPSnoopingActiveCallL4portB,
              aluSIPSnoopingActiveCallSipMediaType,
              aluSIPSnoopingActiveCallStart,
              aluSIPSnoopingActiveCallRtpCountA,
              aluSIPSnoopingActiveCallRtcpCountA,
              aluSIPSnoopingActiveCallRuleNameA,
              aluSIPSnoopingActiveCallRtpCountB,
              aluSIPSnoopingActiveCallRtcpCountB,
              aluSIPSnoopingActiveCallRuleNameB,
              aluSIPSnoopingActiveCallTrustDSCPStatusA,
              aluSIPSnoopingActiveCallTrustDSCPStatusB,
              aluSIPSnoopingActiveCallPacketCountA,
              aluSIPSnoopingActiveCallPacketCountB,
              aluSIPSnoopingEndedCallTagA,
              aluSIPSnoopingEndedCallTagB,
              aluSIPSnoopingEndedCallIpAddrA,
              aluSIPSnoopingEndedCallIpAddrAType,
              aluSIPSnoopingEndedCallIpAddrB,
              aluSIPSnoopingEndedCallIpAddrBType,
              aluSIPSnoopingEndedCallL4portA,
              aluSIPSnoopingEndedCallL4portB,
              aluSIPSnoopingEndedCallSipMediaType,
              aluSIPSnoopingEndedCallStart,
              aluSIPSnoopingEndedCallEnd,
              aluSIPSnoopingEndedCallRtpCountA,
              aluSIPSnoopingEndedCallRtcpCountA,
              aluSIPSnoopingEndedCallRuleNameA,
              aluSIPSnoopingEndedCallRtpCountB,
              aluSIPSnoopingEndedCallRtcpCountB,
              aluSIPSnoopingEndedCallRuleNameB,
	          aluSIPSnoopingEndedCallEndReason,
              aluSIPSnoopingEndedCallId,
              aluSIPSnoopingEndedCallTrustDSCPStatusA,
              aluSIPSnoopingEndedCallTrustDSCPStatusB,
              aluSIPSnoopingEndedCallPacketCountA,
              aluSIPSnoopingEndedCallPacketCountB
          }
        STATUS current
        DESCRIPTION
                                "Collection of objects for SIP snooping call summary."
        ::= { aluSIPSnoopingMIBGroups 4}

aluSIPSnoopingStatsGroup      OBJECT-GROUP
        OBJECTS
        {
              aluSIPSnoopingActiveCallStatsJitterViolationsA,
              aluSIPSnoopingActiveCallStatsJitterViolationsB,
              aluSIPSnoopingActiveCallStatsRtdViolationsA,
              aluSIPSnoopingActiveCallStatsRtdViolationsB,
              aluSIPSnoopingActiveCallStatsPktLossViolationsA,
              aluSIPSnoopingActiveCallStatsPktLossViolationsB,
              aluSIPSnoopingActiveCallStatsMosViolationsA,
              aluSIPSnoopingActiveCallStatsMosViolationsB,
              aluSIPSnoopingActiveCallStatsRfactorViolationsA,
              aluSIPSnoopingActiveCallStatsRfactorViolationsB,
              aluSIPSnoopingActiveCallStatsJitterMaxA,
              aluSIPSnoopingActiveCallStatsJitterMinA,
              aluSIPSnoopingActiveCallStatsJitterAvgA,
              aluSIPSnoopingActiveCallStatsJitterMaxB,
              aluSIPSnoopingActiveCallStatsJitterMinB,
              aluSIPSnoopingActiveCallStatsJitterAvgB,
              aluSIPSnoopingActiveCallStatsRtdMaxA,
              aluSIPSnoopingActiveCallStatsRtdMinA,
              aluSIPSnoopingActiveCallStatsRtdAvgA,
              aluSIPSnoopingActiveCallStatsRtdMaxB,
              aluSIPSnoopingActiveCallStatsRtdMinB,
              aluSIPSnoopingActiveCallStatsRtdAvgB,
              aluSIPSnoopingActiveCallStatsPktLossMaxA,
              aluSIPSnoopingActiveCallStatsPktLossMinA,
              aluSIPSnoopingActiveCallStatsPktLossAvgA,
              aluSIPSnoopingActiveCallStatsPktLossMaxB,
              aluSIPSnoopingActiveCallStatsPktLossMinB,
              aluSIPSnoopingActiveCallStatsPktLossAvgB,
              aluSIPSnoopingActiveCallStatsRfactorMaxA,
              aluSIPSnoopingActiveCallStatsRfactorMinA,
              aluSIPSnoopingActiveCallStatsRfactorAvgA,
              aluSIPSnoopingActiveCallStatsRfactorMaxB,
              aluSIPSnoopingActiveCallStatsRfactorMinB,
              aluSIPSnoopingActiveCallStatsRfactorAvgB,
              aluSIPSnoopingActiveCallStatsMosMaxA,
              aluSIPSnoopingActiveCallStatsMosMinA,
              aluSIPSnoopingActiveCallStatsMosAvgA,
              aluSIPSnoopingActiveCallStatsMosMaxB,
              aluSIPSnoopingActiveCallStatsMosMinB,
              aluSIPSnoopingActiveCallStatsMosAvgB,
              aluSIPSnoopingEndedCallStatsJitterViolationsA,
              aluSIPSnoopingEndedCallStatsJitterViolationsB,
              aluSIPSnoopingEndedCallStatsRtdViolationsA,
              aluSIPSnoopingEndedCallStatsRtdViolationsB,
              aluSIPSnoopingEndedCallStatsPktLossViolationsA,
              aluSIPSnoopingEndedCallStatsPktLossViolationsB,
              aluSIPSnoopingEndedCallStatsMosViolationsA,
              aluSIPSnoopingEndedCallStatsMosViolationsB,
              aluSIPSnoopingEndedCallStatsRfactorViolationsA,
              aluSIPSnoopingEndedCallStatsRfactorViolationsB,
              aluSIPSnoopingEndedCallStatsJitterMaxA,
              aluSIPSnoopingEndedCallStatsJitterMinA,
              aluSIPSnoopingEndedCallStatsJitterAvgA,
              aluSIPSnoopingEndedCallStatsJitterMaxB,
              aluSIPSnoopingEndedCallStatsJitterMinB,
              aluSIPSnoopingEndedCallStatsJitterAvgB,
              aluSIPSnoopingEndedCallStatsRtdMaxA,
              aluSIPSnoopingEndedCallStatsRtdMinA,
              aluSIPSnoopingEndedCallStatsRtdAvgA,
              aluSIPSnoopingEndedCallStatsRtdMaxB,
              aluSIPSnoopingEndedCallStatsRtdMinB,
              aluSIPSnoopingEndedCallStatsRtdAvgB,
              aluSIPSnoopingEndedCallStatsPktLossMaxA,
              aluSIPSnoopingEndedCallStatsPktLossMinA,
              aluSIPSnoopingEndedCallStatsPktLossAvgA,
              aluSIPSnoopingEndedCallStatsPktLossMaxB,
              aluSIPSnoopingEndedCallStatsPktLossMinB,
              aluSIPSnoopingEndedCallStatsPktLossAvgB,
              aluSIPSnoopingEndedCallStatsRfactorMaxA,
              aluSIPSnoopingEndedCallStatsRfactorMinA,
              aluSIPSnoopingEndedCallStatsRfactorAvgA,
              aluSIPSnoopingEndedCallStatsRfactorMaxB,
              aluSIPSnoopingEndedCallStatsRfactorMinB,
              aluSIPSnoopingEndedCallStatsRfactorAvgB,
              aluSIPSnoopingEndedCallStatsMosMaxA,
              aluSIPSnoopingEndedCallStatsMosMinA,
              aluSIPSnoopingEndedCallStatsMosAvgA,
              aluSIPSnoopingEndedCallStatsMosMaxB,
              aluSIPSnoopingEndedCallStatsMosMinB,
              aluSIPSnoopingEndedCallStatsMosAvgB
        }
        STATUS current
        DESCRIPTION
                                "Collection of objects for SIP snooping call statistics."
        ::= { aluSIPSnoopingMIBGroups 5}

alaSIPSnoopingNotificationGroup NOTIFICATION-GROUP
   NOTIFICATIONS
   {
     alaSIPSnoopingRTCPOverThreshold,
     alaSIPSnoopingSignallingLost,
     alaSIPSnoopingRTCPPktsLost,
     alaSIPSnoopingACLPreemptedBySOSCall,
     alaSIPSnoopingCallRecordsFileMoved
   }
   STATUS  current
   DESCRIPTION
        "Collection of notifications for SIP Snooping."
   ::= { aluSIPSnoopingMIBGroups 6 }

alaSIPSnoopingRegisteredClientsGroup OBJECT-GROUP
   OBJECTS
   {
     alaSIPSnoopingRegisteredClientAddrType,
     alaSIPSnoopingRegisteredClientAddr
   }
   STATUS  current
   DESCRIPTION
        "Collection of registered client information for SIP Snooping."
   ::= { aluSIPSnoopingMIBGroups 7 }

END
