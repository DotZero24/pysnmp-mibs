ALCATEL-ENT1-TIMETRA-SAP-MIB DEFINITIONS ::= BEGIN

IMPORTS
    MODULE-IDENTITY, OBJECT-TYPE,
    NOTIFICATION-TYPE, Gauge32,
    Integer32, Unsigned32, IpAddress,
    Counter64, Counter32                        FROM SNMPv2-SMI

    MODULE-COMPLIANCE, OBJECT-GROUP,
    NOTIFICATION-GROUP                          FROM SNMPv2-CONF

    DisplayString,
    RowStatus, MacAddress, TimeStamp,
    TruthValue                                  FROM SNMPv2-TC

    InterfaceIndexOrZero                        FROM IF-MIB

    InetAddressType, InetAddress                FROM INET-ADDRESS-MIB

    AtmTrafficDescrParamIndex                   FROM ATM-TC-MIB

    ServiceAdminStatus,
    TmnxPortID, TmnxEncapVal, TmnxServId, TmnxCustId, TNamedItem,
    TIngressQueueId, TEgressQueueId, TNamedItemOrEmpty, TPortSchedulerPIR,
    TmnxActionType, TmnxOperState, TmnxIgmpVersion,
    TCpmProtPolicyID, TCIRRate, TPIRRate, TmnxEnabledDisabled, TItemDescription,
    TPolicyStatementNameOrEmpty, TSapIngressPolicyID, TSapEgressPolicyID
                                                FROM ALCATEL-ENT1-TIMETRA-TC-MIB

    tmnxServObjs, tmnxServConformance, tmnxServNotifications,
    custId, svcId, svcVpnId, tlsMstiInstanceId, tstpTraps,
    tmnxOtherBridgeId, tmnxCustomerBridgeId, tmnxCustomerRootBridgeId,
    protectedMacForNotify, tlsDhcpLseStateNewCiAddr,
    tlsDhcpLseStateNewChAddr, tlsDHCPClientLease, tlsDhcpLseStateOldCiAddr,
    tlsDhcpLseStateOldChAddr, hostConnectivityCiAddrType,
    hostConnectivityCiAddr, hostConnectivityChAddr,
    staticHostDynamicMacIpAddress, staticHostDynamicMacConflict,
    svcTlsMacMoveMaxRate, svcDhcpProxyError,
    svcDhcpCoAError, svcDhcpSubAuthError,
    tlsDhcpPacketProblem, svcDhcpLseStateNewCiAddr,
    svcDhcpLseStateNewChAddr, svcDhcpClientLease,
    svcDhcpLseStateOldCiAddr, svcDhcpLseStateOldChAddr, svcDhcpPacketProblem,
    svcDhcpLseStatePopulateError,
    ServObjName, ServObjDesc, ServType, VpnId,
    TlsLimitMacMoveLevel, TlsLimitMacMove, StpExceptionCondition,
    BridgeId, TSapIngQueueId, TSapEgrQueueId, TStpPortState, StpPortRole,
    StpProtocol, MvplsPruneState, TQosQueueAttribute, TVirtSchedAttribute,
    MstiInstanceIdOrZero, TdmOptionsCasTrunkFraming, CemSapReportAlarm,
    CemSapEcid, L2ptProtocols, ConfigStatus     FROM ALCATEL-ENT1-TIMETRA-SERV-MIB
    timetraSRMIBModules                         FROM ALCATEL-ENT1-TIMETRA-GLOBAL-MIB

    TBurstSize, TBurstPercentOrDefault,
    TAdaptationRule,
    tVirtualSchedulerName, tSchedulerPolicyName FROM ALCATEL-ENT1-TIMETRA-QOS-MIB

    TFilterID                                   FROM ALCATEL-ENT1-TIMETRA-FILTER-MIB;

timetraSvcSapMIBModule   MODULE-IDENTITY
    LAST-UPDATED    "0710010000Z"
    ORGANIZATION    "Alcatel"
    CONTACT-INFO
        "Alcatel 7x50 Support
         Web: http://www.alcatel.com/comps/pages/carrier_support.jhtml"
    DESCRIPTION
        "This  document  is the SNMP MIB module to manage and provision
        the various services of the Alcatel 7x50 SR system.

        Copyright  2003-2008 Alcatel-Lucent. All rights reserved. Reproduction
        of  this  document  is  authorized  on  the  condition that the
        foregoing copyright notice is included.

        This   SNMP   MIB  module  (Specification)  embodies  Alcatel's
        proprietary  intellectual  property.  Alcatel retains all title
        and ownership in the Specification, including any revisions.

        Alcatel  grants  all interested parties a non-exclusive license
        to  use and distribute an unmodified copy of this Specification
        in  connection with management of Alcatel products, and without
        fee,  provided  this copyright notice and license appear on all
        copies.

        This  Specification  is  supplied `as is', and Alcatel makes no
        warranty,  either express or implied, as to the use, operation,
        condition, or performance of the Specification."

--
--  Revision History
--
    REVISION        "0710010000Z"
    DESCRIPTION     "Rev 1.0                01 OCT 2007 00:00
                     1.0 release of the TIMETRA-SAP-MIB from TIMETRA-SERV-MIB."

    ::= { timetraSRMIBModules 55 }

-- --------------------------------------------------------------------
--      ALCATEL-ENT1-TIMETRA-SAP-MIB organisation
-- --------------------------------------------------------------------
tmnxSapObjs             OBJECT IDENTIFIER ::= { tmnxServObjs 3 }
    tmnxSapNotifyObjs       OBJECT IDENTIFIER ::= { tmnxSapObjs 100 }

tmnxSapConformance      OBJECT IDENTIFIER ::= { tmnxServConformance 3 }

sapTrapsPrefix          OBJECT IDENTIFIER ::= { tmnxServNotifications 3 }
    sapTraps                OBJECT IDENTIFIER ::= { sapTrapsPrefix 0 }

-- --------------------------------------------------------------------
-- tmnxSapObjs group
-- --------------------------------------------------------------------
sapNumEntries OBJECT-TYPE
    SYNTAX          Integer32
    MAX-ACCESS      read-only
    STATUS          current
    DESCRIPTION     "The current number of SAPs configured in this
                     device."
    ::= { tmnxSapObjs 1 }

-- ----------------------------------
-- Base SAP Table
-- ----------------------------------
sapBaseInfoTable OBJECT-TYPE
    SYNTAX          SEQUENCE OF SapBaseInfoEntry
    MAX-ACCESS      not-accessible
    STATUS          current
    DESCRIPTION     "A table that contains basic SAP information."
    ::= { tmnxSapObjs 2 }

sapBaseInfoEntry OBJECT-TYPE
    SYNTAX          SapBaseInfoEntry
    MAX-ACCESS      not-accessible
    STATUS          current
    DESCRIPTION     "Information about a specific SAP."
    INDEX           { svcId, sapPortId, sapEncapValue }
    ::= { sapBaseInfoTable 1 }

SapBaseInfoEntry ::=
    SEQUENCE {
        sapPortId                       TmnxPortID,
        sapEncapValue                   TmnxEncapVal,
        sapRowStatus                    RowStatus,
        sapType                         ServType,
        sapDescription                  ServObjDesc,
        sapAdminStatus                  ServiceAdminStatus,
        sapOperStatus                   INTEGER,
        sapIngressQosPolicyId           TSapIngressPolicyID,
        sapIngressMacFilterId           TFilterID,
        sapIngressIpFilterId            TFilterID,
        sapEgressQosPolicyId            TSapEgressPolicyID,
        sapEgressMacFilterId            TFilterID,
        sapEgressIpFilterId             TFilterID,
        sapMirrorStatus                 INTEGER,
        sapIesIfIndex                   InterfaceIndexOrZero,
        sapLastMgmtChange               TimeStamp,
        sapCollectAcctStats             TruthValue,
        sapAccountingPolicyId           Unsigned32,
        sapVpnId                        VpnId,
        sapCustId                       TmnxCustId,
        sapCustMultSvcSite              ServObjName,
        sapIngressQosSchedulerPolicy    ServObjName,
        sapEgressQosSchedulerPolicy     ServObjName,
        sapSplitHorizonGrp              ServObjName,
        sapIngressSharedQueuePolicy     ServObjName,
        sapIngressMatchQinQDot1PBits    INTEGER,
        sapOperFlags                    BITS,
        sapLastStatusChange             TimeStamp,
        sapAntiSpoofing                 INTEGER,
        sapIngressIpv6FilterId          TFilterID,
        sapEgressIpv6FilterId           TFilterID,
        sapTodSuite                     TNamedItemOrEmpty,
        sapIngUseMultipointShared       TruthValue,
        sapEgressQinQMarkTopOnly        TruthValue,
        sapEgressAggRateLimit           TPortSchedulerPIR,
        sapEndPoint                     ServObjName,
        sapIngressVlanTranslation       INTEGER,
        sapIngressVlanTranslationId     Integer32,
        sapSubType                      INTEGER,
        sapCpmProtPolicyId              TCpmProtPolicyID,
        sapCpmProtMonitorMac            TruthValue,
        sapEgressFrameBasedAccounting   TruthValue
    }

sapPortId OBJECT-TYPE
    SYNTAX          TmnxPortID
    MAX-ACCESS      read-only
    STATUS          current
    DESCRIPTION     "The ID of the access port where this SAP
                     is defined."
    ::= { sapBaseInfoEntry 1 }

sapEncapValue OBJECT-TYPE
    SYNTAX          TmnxEncapVal
    MAX-ACCESS      read-only
    STATUS          current
    DESCRIPTION     "The value of the label used to identify this
                     SAP on the access port specified by sapPortId."
    ::= { sapBaseInfoEntry 2 }

sapRowStatus OBJECT-TYPE
    SYNTAX          RowStatus
    MAX-ACCESS      read-create
    STATUS          current
    DESCRIPTION     "This object indicates the status of this row. The
                     only values supported during a set operation are
                     'createAndGo' and 'destroy'."
    ::= { sapBaseInfoEntry 3 }

sapType OBJECT-TYPE
    SYNTAX          ServType
    MAX-ACCESS      read-only
    STATUS          current
    DESCRIPTION     "This object indicates the type of service where
                     this SAP is defined."
    ::= { sapBaseInfoEntry 4 }

sapDescription OBJECT-TYPE
    SYNTAX          ServObjDesc
    MAX-ACCESS      read-create
    STATUS          current
    DESCRIPTION     "Generic information about this SAP."
    DEFVAL          { "" }
    ::= { sapBaseInfoEntry 5 }

sapAdminStatus OBJECT-TYPE
    SYNTAX          ServiceAdminStatus
    MAX-ACCESS      read-create
    STATUS          current
    DESCRIPTION     "The desired state of this SAP."
    DEFVAL          { down }
    ::= { sapBaseInfoEntry 6 }

sapOperStatus OBJECT-TYPE
    SYNTAX          INTEGER {
                        up                 (1),
                        down               (2),
                        ingressQosMismatch (3),
                        egressQosMismatch  (4),
                        portMtuTooSmall    (5),
                        svcAdminDown       (6),
                        iesIfAdminDown     (7)
                    }
    MAX-ACCESS      read-only
    STATUS          current
    DESCRIPTION     "The value of the object sapOperStatus indicates the
                     operating state of this SAP."
    ::= { sapBaseInfoEntry 7 }

sapIngressQosPolicyId OBJECT-TYPE
    SYNTAX          TSapIngressPolicyID
    MAX-ACCESS      read-create
    STATUS          current
    DESCRIPTION     "The value of the object sapIngressQosPolicyId specifies
                     the row index in the tSapIngressTable corresponding to this
                     ingress QoS policy, or one if no policy is specified.
                     The value 0 is needed for mirror SAPs that
                     cannot have a qos policy assigned."
    DEFVAL          { 1 }
    ::= { sapBaseInfoEntry 8 }

sapIngressMacFilterId OBJECT-TYPE
    SYNTAX          TFilterID
    MAX-ACCESS      read-create
    STATUS          current
    DESCRIPTION     "The value of the object sapIngressMacFilterId specifies
                     the row index in the tMacFilterTable corresponding to this
                     ingress filter, or zero if no filter is specified."
    DEFVAL          { 0 }
    ::= { sapBaseInfoEntry 9 }

sapIngressIpFilterId OBJECT-TYPE
    SYNTAX          TFilterID
    MAX-ACCESS      read-create
    STATUS          current
    DESCRIPTION     "The value of the object sapIngressIpFilterId specifies the
                     row index in the tIPFilterTable corresponding to this
                     ingress filter, or zero if no filter is specified."
    DEFVAL          { 0 }
    ::= { sapBaseInfoEntry 10 }

sapEgressQosPolicyId OBJECT-TYPE
    SYNTAX          TSapEgressPolicyID
    MAX-ACCESS      read-create
    STATUS          current
    DESCRIPTION     "The row index in the tSapEgressTable
                     corresponding to this egress QoS policy,
                     or one if no policy is specified."
    DEFVAL          { 1 }
    ::= { sapBaseInfoEntry 11 }

sapEgressMacFilterId OBJECT-TYPE
    SYNTAX          TFilterID
    MAX-ACCESS      read-create
    STATUS          current
    DESCRIPTION     "The row index in the tMacFilterTable
                     corresponding to this egress filter,
                     or zero if no filter is specified."
    DEFVAL          { 0 }
    ::= { sapBaseInfoEntry 12 }

sapEgressIpFilterId OBJECT-TYPE
    SYNTAX          TFilterID
    MAX-ACCESS      read-create
    STATUS          current
    DESCRIPTION     "The row index in the tIPFilterTable
                     corresponding to this egress filter,
                     or zero if no filter is specified."
    DEFVAL          { 0 }
    ::= { sapBaseInfoEntry 13 }

sapMirrorStatus OBJECT-TYPE
    SYNTAX          INTEGER {
                        ingress          (1),
                        egress           (2),
                        ingressAndEgress (3),
                        disabled         (4)
                    }
    MAX-ACCESS      read-only
    STATUS          current
    DESCRIPTION     "This object specifies whether traffic
                     mirroring has been enabled on this SAP."
    ::= { sapBaseInfoEntry 14 }

sapIesIfIndex OBJECT-TYPE
    SYNTAX          InterfaceIndexOrZero
    MAX-ACCESS      read-create
    STATUS          current
    DESCRIPTION     "When the value of sapType is 'ies' this
                     object specifies the index of the IES interface
                     where this SAP is defined. The value of this object
                     can be set only when the row is created and cannot
                     be changed while the row status is 'active'. This
                     object is otherwise not significant and should have
                     the value zero."
    ::= { sapBaseInfoEntry 15 }

sapLastMgmtChange OBJECT-TYPE
    SYNTAX          TimeStamp
    MAX-ACCESS      read-only
    STATUS          current
    DESCRIPTION     "The value of sysUpTime at the time of the
                     most recent management-initiated change to
                     this SAP."
    ::= { sapBaseInfoEntry 16 }

sapCollectAcctStats OBJECT-TYPE
    SYNTAX          TruthValue
    MAX-ACCESS      read-create
    STATUS          current
    DESCRIPTION     "When the value of this object is 'true' the agent
                     collects accounting statistics on this SAP."
    DEFVAL          { false }
    ::= { sapBaseInfoEntry 17 }

sapAccountingPolicyId OBJECT-TYPE
    SYNTAX          Unsigned32
    MAX-ACCESS      read-create
    STATUS          current
    DESCRIPTION     "This object specifies the policy to use to collect
                     accounting statistics on this SAP. The value zero
                     indicates that the agent should use the default
                     accounting policy, if one exists."
    DEFVAL          { 0 }
    ::= { sapBaseInfoEntry 18 }

sapVpnId OBJECT-TYPE
    SYNTAX          VpnId
    MAX-ACCESS      read-only
    STATUS          current
    DESCRIPTION     "The VPN ID of the associated service."
    ::= { sapBaseInfoEntry 19 }

sapCustId OBJECT-TYPE
    SYNTAX          TmnxCustId
    MAX-ACCESS      read-only
    STATUS          current
    DESCRIPTION     "The Customer ID of the associated service."
    ::= { sapBaseInfoEntry 20 }

sapCustMultSvcSite OBJECT-TYPE
    SYNTAX          ServObjName
    MAX-ACCESS      read-create
    STATUS          current
    DESCRIPTION     "The value of this object, when not null, indicates
                     the Multi-Service Site this SAP is a member of. This
                     information is used to configure the ingress and
                     egress QoS schedulers for this SAP."
    DEFVAL          { "" }
    ::= { sapBaseInfoEntry 21 }

sapIngressQosSchedulerPolicy OBJECT-TYPE
    SYNTAX          ServObjName
    MAX-ACCESS      read-create
    STATUS          current
    DESCRIPTION     "This object can be set only when sapCustMultSvcSite
                     is null. It indicates the ingress QoS scheduler for
                     this SAP."
    DEFVAL          { "" }
    ::= { sapBaseInfoEntry 22 }

sapEgressQosSchedulerPolicy OBJECT-TYPE
    SYNTAX          ServObjName
    MAX-ACCESS      read-create
    STATUS          current
    DESCRIPTION     "This object can be set only when sapCustMultSvcSite
                     is null. It indicates the egress QoS scheduler for
                     this SAP."
    DEFVAL          { "" }
    ::= { sapBaseInfoEntry 23 }

sapSplitHorizonGrp OBJECT-TYPE
    SYNTAX          ServObjName
    MAX-ACCESS      read-create
    STATUS          current
    DESCRIPTION     "This object specifies the name of the split-horizon
                     group where the SAP belongs to. This object can be
                     set only at the time the row is created. Per default
                     a SAP does not belong to any split-horizon group. The
                     name specified must correspond to an existing split-
                     horizon group in the TLS service where this SAP is
                     defined."
    DEFVAL          { "" }
    ::= { sapBaseInfoEntry 24 }

sapIngressSharedQueuePolicy OBJECT-TYPE
    SYNTAX          ServObjName
    MAX-ACCESS      read-create
    STATUS          current
    DESCRIPTION     "This object indicates the ingress shared queue policy
                     used by this SAP. When the value of this object is null
                     it means that the SAP will use individual ingress QoS
                     queues, instead of the shared ones."
    DEFVAL          { "" }
    ::= { sapBaseInfoEntry 25 }

sapIngressMatchQinQDot1PBits OBJECT-TYPE
    SYNTAX          INTEGER {
                        default (1),
                        top     (2),
                        bottom  (3)
                    }
    MAX-ACCESS      read-create
    STATUS          current
    DESCRIPTION     "This object applies only to SAP's defined on a port
                     configured for qinq service encapsulation. It indicates
                     which 802.1P bits will be used to match a QoS or a MAC
                     filter policy when a double-tagged frame is received on
                     this SAP."
    DEFVAL          { default }
    ::= { sapBaseInfoEntry 26 }

sapOperFlags OBJECT-TYPE
    SYNTAX          BITS {
                        sapAdminDown         (0),  -- SAP is admin down
                        svcAdminDown         (1),  -- Service is admin down
                        iesIfAdminDown       (2),  -- IP interface is admin down
                                                   -- (IES and VPRN only)
                        portOperDown         (3),  -- Access port is oper down
                        portMtuTooSmall      (4),  -- Access port's MTU is less
                                                   -- than Service MTU
                        l2OperDown           (5),  -- L2 PVC/PVP is oper down
                                                   -- (FR and ATM only)
                        ingressQosMismatch   (6),  -- Mismatch between ingress
                                                   -- QoS and Scheduler policies
                        egressQosMismatch    (7),  -- Mismatch between egress
                                                   -- QoS and Scheduler policies
                        relearnLimitExceeded (8),  -- MAC relearn limit was
                                                   -- exceeded (TLS only)
                        recProtSrcMac        (9),  -- Received a packet with a
                                                   -- protected source MAC
                                                   -- (TLS only)
                        subIfAdminDown       (10), -- Subscriber interface is
                                                   -- admin down (group-interface
                                                   -- SAP only)
                        sapIpipeNoCeIpAddr   (11), -- CE IP Address not
                                                   -- configured for Ipipe SAP
                                                   -- (IPIPE SAP only)
                        sapTodResourceUnavail (12),-- SAP with ToD had
                                                   -- insufficient resources
                                                   -- at boot time and got
                                                   -- default policies.
                        sapTodMssResourceUnavail (13), -- MSS of this SAP uses
                                                       -- ToD and due to
                                                       -- insufficient resources
                                                       -- at boot time got
                                                       -- default scheduler
                                                       -- policies.
                        sapParamMismatch      (14),    -- Service specific local
                                                       -- parameter mismatch
                        sapCemNoEcidOrMacAddr (15),    -- ECID or MAC address not
                                                       -- configured (CEM SAP
                                                       -- only)
                        sapStandbyForMcRing   (16),    -- mc-ring keeps this SAP
                                                       -- standby for the
                                                       -- corresponding SAP on
                                                       -- peer
                        sapSvcMtuTooSmall     (17),    -- Service MTU is less
                                                       -- than the SAP payload
                        ingressNamedPoolMismatch (18), -- Invalid named-pool
                                                       -- on the ingress side
                        egressNamedPoolMismatch  (19), -- Invalid named-pool
                                                       -- on the egress side
                        ipMirrorNoMacAddr     (20),    -- No MAC Address configured
                                                       -- for the ip-mirror
                        sapEpipeNoRingNode (21) -- No TIMETRA-MC-REDUNDANCY-MIB
                                                -- ::tmnxMcEpipeSapEntry object
                                                -- configured for Epipe SAP
                                                -- (EPIPE SAP only)
                    }
    MAX-ACCESS      read-only
    STATUS          current
    DESCRIPTION     "This object specifies all the conditions that
                     affect the operating status of this SAP."
    ::= { sapBaseInfoEntry 27 }

sapLastStatusChange OBJECT-TYPE
    SYNTAX          TimeStamp
    MAX-ACCESS      read-only
    STATUS          current
    DESCRIPTION     "The value of sysUpTime at the time of the
                     most recent operating status change to this
                     SAP."
    ::= { sapBaseInfoEntry 28 }

sapAntiSpoofing OBJECT-TYPE
    SYNTAX          INTEGER {
                        disabled            (0),
                        sourceIpAddr        (1),
                        sourceMacAddr       (2),
                        sourceIpAndMacAddr  (3),
                        nextHopIpAndMacAddr (4)
                    }
    MAX-ACCESS      read-create
    STATUS          current
    DESCRIPTION     "The value of the object sapAntiSpoofing specifies
                     the type of anti-spoof filtering applicable on this SAP.

                     'nextHopIpAndMacAddr (4)' is not supported on SR-1, where
                     the value of ALCATEL-IND1-TIMETRA-CHASSIS-MIB::tmnxChassisType is '5'."
    DEFVAL { disabled }
    ::= { sapBaseInfoEntry 29 }

sapIngressIpv6FilterId OBJECT-TYPE
    SYNTAX          TFilterID
    MAX-ACCESS      read-create
    STATUS          current
    DESCRIPTION     "The value of the object sapIngressIpv6FilterId specifies
                     the row index in the tIPv6FilterTable corresponding to
                     this ingress ipv6 filter, or zero if no ipv6 filter is
                     specified."
    DEFVAL          { 0 }
    ::= { sapBaseInfoEntry 30 }

sapEgressIpv6FilterId OBJECT-TYPE
    SYNTAX          TFilterID
    MAX-ACCESS      read-create
    STATUS          current
    DESCRIPTION     "The value of the object sapEgressIpv6FilterId specifies
                     the row index in the tIPv6FilterTable corresponding to
                     this egress ipv6 filter, or zero if no ipv6 filter is
                     specified."
    DEFVAL          { 0 }
    ::= { sapBaseInfoEntry 31 }

sapTodSuite OBJECT-TYPE
    SYNTAX          TNamedItemOrEmpty
    MAX-ACCESS      read-create
    STATUS          current
    DESCRIPTION     "The value of the object sapTodSuite specifies the Time of
                     Day (ToD) suite to be applied on this SAP.
                     An empty string indicates that no ToD suite is applied
                     on this SAP.
                     A set request will only be allowed, if the indicated suite
                     is defined in TIMETRA-SCHEDULER-MIB::tmnxTodSuiteTable."
    DEFVAL          { ''H }
    ::= { sapBaseInfoEntry 32 }

sapIngUseMultipointShared       OBJECT-TYPE
    SYNTAX          TruthValue
    MAX-ACCESS      read-create
    STATUS          current
    DESCRIPTION     "When the value of sapIngressSharedQueuePolicy is not null,
                     the value of the object sapIngUseMultipointShared
                     specifies whether this SAP uses the multipoint-shared
                     queues of the shared policy."
    DEFVAL          { false }
    ::= { sapBaseInfoEntry 33 }

sapEgressQinQMarkTopOnly OBJECT-TYPE
    SYNTAX          TruthValue
    MAX-ACCESS      read-create
    STATUS          current
    DESCRIPTION     "When the encapsulation type of the access port where
                     this SAP is defined is qinq, the value of the object
                     sapEgressQinQMarkTopOnly specifies which P-bits to mark
                     during packet egress. When the value is false both set
                     of P-bits are marked. When the value is true, only the
                     P-bits in the top Q-tag are marked."
    DEFVAL          { false }
    ::= { sapBaseInfoEntry 34 }

sapEgressAggRateLimit   OBJECT-TYPE
    SYNTAX          TPortSchedulerPIR
    UNITS           "kbps"
    MAX-ACCESS      read-create
    STATUS          current
    DESCRIPTION     "The value of the object sapEgressAggRateLimit
                     specifies the maximum total rate of all egress queues for
                     this SAP. The value '-1' means that there
                     is no limit."
    DEFVAL          { -1 }
    ::= { sapBaseInfoEntry 35 }

sapEndPoint         OBJECT-TYPE
    SYNTAX          ServObjName
    MAX-ACCESS      read-create
    STATUS          current
    DESCRIPTION     "The value of the object sapEndPoint specifies the service
                     endpoint to which this SAP is attached. The svcId of the
                     SAP MUST match the svcId of the service endpoint."
    DEFVAL          { "" }
    ::= { sapBaseInfoEntry 36 }

sapIngressVlanTranslation OBJECT-TYPE
    SYNTAX          INTEGER {
                        none        (1),
                        vlanId      (2),
                        copyOuter   (3)
                        }
    MAX-ACCESS      read-create
    STATUS          current
    DESCRIPTION     "The value of sapIngressVlanTranslation specifies the
                     desired Ingress Vlan Translation.

                     A value of 'vlanId' specifies that the value of
                     sapIngressVlanTranslationId is to be used to overwrite
                     the preserved VLAN id in the packet.

                     A value of 'copyOuter' specifies that the outer VLAN
                     id should be used to overwrite the preserved VLAN id in
                     the packet.

                     An 'inconsistentValue' error is returned when an attempt
                     is made to set the value of sapIngressVlanTranslation
                     to 'vlanId' and sapIngressVlanTranslationId is
                     set to '-1'."
    DEFVAL          { none }
    ::= { sapBaseInfoEntry 37 }

sapIngressVlanTranslationId OBJECT-TYPE
    SYNTAX          Integer32  (-1|0..4094)
    MAX-ACCESS      read-create
    STATUS          current
    DESCRIPTION     "The value of sapIngressVlanTranslationId specifies the
                     VLAN id to be used to overwrite the preserved VLAN id
                     in the packet.

                     An 'inconsistentValue' error is returned when an
                     attempt is made to set the value of
                     sapIngressVlanTranslationId to other than '-1' and
                     sapIngressVlanTranslation is not set to 'vlanId'."
    DEFVAL          { -1 }
    ::= { sapBaseInfoEntry 38 }

sapSubType          OBJECT-TYPE
    SYNTAX          INTEGER {
                        regular  (0),
                        capture  (1),
                        managed  (2)
                    }
    MAX-ACCESS      read-create
    STATUS          current
    DESCRIPTION     "The value of the object sapSubType indicates the
                     sub-type for this SAP.

                     A value of 'regular' indicates a standard SAP.

                     A value of 'capture' specifies a capturing SAP
                     in which triggering packets will be sent to the CPM.
                     Non-triggering packets captured by the 'capture' SAP
                     will be dropped.

                     A value of 'managed' indicates a managed SAP which
                     was created dynamically after receiving triggering
                     packets on a SAP with a sapSubType value of
                     'capture'. Entries with a value of 'managed'
                     are not user editable and are not maintained
                     in the configuration file.

                     Whereas any of the three values may be returned in
                     in response to an SNMP GET request, only two values
                     may be specified in an SNMP SET request: 'regular'
                     and 'capture'. An attempt to specify a value
                     of 'managed' in an SNMP SET request will fail
                     with an error of 'wrongValue'.

                     The value of this object cannot be changed after creation."
    DEFVAL          { regular }
    ::= { sapBaseInfoEntry 39 }

sapCpmProtPolicyId  OBJECT-TYPE
    SYNTAX          TCpmProtPolicyID
    MAX-ACCESS      read-create
    STATUS          current
    DESCRIPTION
        "The value of sapCpmProtPolicyId associates a CPM Protection policy
         with a SAP.

         A value of zero (0) specifies that no CPM Protection policy is
         associated with this SAP.

         A value of one (1) specifies that the default CPM Protection policy is
         associated with this SAP.

         If no value for sapCpmProtPolicyId is specified when the
         sapBaseInfoEntry is created, the system assigns a default value
         as follows: if the system creates a corresponding entry
         in the sapSubMgmtInfoTable, the default value is 'one'; otherwise,
         the default value is 'zero'. This means that all SAP's that
         support Enhanced Subscriber Management get a default value of 'one'.

         If a SAP would get a default value of 'one', it is not
         allowed to set the value of sapCpmProtPolicyId to 'zero'.

         If a SAP would get a default value of 'zero', it is not
         allowed to modify the value of sapCpmProtPolicyId.

         This object is not supported on SR-1 and ESS-1, where the
         value of ALCATEL-IND1-TIMETRA-CHASSIS-MIB::tmnxChassisType is '5',
         and 7710, where the value of ALCATEL-IND1-TIMETRA-CHASSIS-MIB::tmnxChassisType is
         '7' or '9'."
    ::= { sapBaseInfoEntry 40 }

sapCpmProtMonitorMac OBJECT-TYPE
    SYNTAX          TruthValue
    MAX-ACCESS      read-create
    STATUS          current
    DESCRIPTION
         "The value of sapCpmProtMonitorMac specifies whether the
         tmnxCpmProtPolPerSrcRateLimit of the CPM Protection policy must be applied.

         If the value of sapCpmProtMonitorMac is 'true', the per-source rate limit
         must be applied.

         If the value of sapCpmProtPolicyId is equal to zero (0), the value of
         sapCpmProtMonitorMac is irrelevant and will be ignored.

         This object is not supported on SR-1 and ESS-1, where the
         value of ALCATEL-IND1-TIMETRA-CHASSIS-MIB::tmnxChassisType is '5',
         and 7710, where the value of ALCATEL-IND1-TIMETRA-CHASSIS-MIB::tmnxChassisType is
         '7' or '9'."
    DEFVAL          { false }
    ::= { sapBaseInfoEntry 41 }

sapEgressFrameBasedAccounting OBJECT-TYPE
    SYNTAX       TruthValue
    MAX-ACCESS   read-create
    STATUS       current
    DESCRIPTION
        "The value of sapEgressFrameBasedAccounting specifies whether
         to use frame-based accounting when evaluating
         sapEgressAggRateLimit for all egress queues for this SAP.

         If the value is 'false', the default packet-based accounting
         method will be used."
    DEFVAL { false }
    ::= { sapBaseInfoEntry 42 }

-- -------------------------------------
-- TLS SAP Table
-- -------------------------------------
sapTlsInfoTable OBJECT-TYPE
    SYNTAX          SEQUENCE OF SapTlsInfoEntry
    MAX-ACCESS      not-accessible
    STATUS          current
    DESCRIPTION     "A table that contains TLS SAP information."
    ::= { tmnxSapObjs 3 }

sapTlsInfoEntry OBJECT-TYPE
    SYNTAX          SapTlsInfoEntry
    MAX-ACCESS      not-accessible
    STATUS          current
    DESCRIPTION     "TLS specific information about a SAP."
    INDEX           { svcId, sapPortId, sapEncapValue }
    ::= { sapTlsInfoTable 1 }

SapTlsInfoEntry ::=
    SEQUENCE {
        sapTlsStpAdminStatus            TmnxEnabledDisabled,
        sapTlsStpPriority               INTEGER,
        sapTlsStpPortNum                INTEGER,
        sapTlsStpPathCost               INTEGER,
        sapTlsStpRapidStart             TmnxEnabledDisabled,
        sapTlsStpBpduEncap              INTEGER,
        sapTlsStpPortState              TStpPortState,
        sapTlsStpDesignatedBridge       BridgeId,
        sapTlsStpDesignatedPort         Integer32,
        sapTlsStpForwardTransitions     Gauge32,
        sapTlsStpInConfigBpdus          Gauge32,
        sapTlsStpInTcnBpdus             Gauge32,
        sapTlsStpInBadBpdus             Gauge32,
        sapTlsStpOutConfigBpdus         Gauge32,
        sapTlsStpOutTcnBpdus            Gauge32,
        sapTlsStpOperBpduEncap          INTEGER,
        sapTlsVpnId                     VpnId,
        sapTlsCustId                    TmnxCustId,
        sapTlsMacAddressLimit           Integer32,
        sapTlsNumMacAddresses           Integer32,
        sapTlsNumStaticMacAddresses     Integer32,
        sapTlsMacLearning               TmnxEnabledDisabled,
        sapTlsMacAgeing                 TmnxEnabledDisabled,
        sapTlsStpOperEdge               TruthValue,
        sapTlsStpAdminPointToPoint      INTEGER,
        sapTlsStpPortRole               StpPortRole,
        sapTlsStpAutoEdge               TmnxEnabledDisabled,
        sapTlsStpOperProtocol           StpProtocol,
        sapTlsStpInRstBpdus             Gauge32,
        sapTlsStpOutRstBpdus            Gauge32,
        sapTlsLimitMacMove              TlsLimitMacMove,
        sapTlsDhcpSnooping              TmnxEnabledDisabled,
        sapTlsMacPinning                TmnxEnabledDisabled,
        sapTlsDiscardUnknownSource      TmnxEnabledDisabled,
        sapTlsMvplsPruneState           MvplsPruneState,
        sapTlsMvplsMgmtService          TmnxServId,
        sapTlsMvplsMgmtPortId           TmnxPortID,
        sapTlsMvplsMgmtEncapValue       TmnxEncapVal,
        sapTlsArpReplyAgent             INTEGER,
        sapTlsStpException              StpExceptionCondition,
        sapTlsAuthenticationPolicy      TPolicyStatementNameOrEmpty,
        sapTlsL2ptTermination           TmnxEnabledDisabled,
        sapTlsBpduTranslation           INTEGER,
        sapTlsStpRootGuard              TruthValue,
        sapTlsStpInsideRegion           TruthValue,
        sapTlsEgressMcastGroup          TNamedItemOrEmpty,
        sapTlsStpInMstBpdus             Gauge32,
        sapTlsStpOutMstBpdus            Gauge32,
        sapTlsRestProtSrcMac            TruthValue,
        sapTlsRestUnprotDstMac          TruthValue,
        sapTlsStpRxdDesigBridge         BridgeId,
        sapTlsStpRootGuardViolation     TruthValue,
        sapTlsShcvAction                INTEGER,
        sapTlsShcvSrcIp                 IpAddress,
        sapTlsShcvSrcMac                MacAddress,
        sapTlsShcvInterval              Unsigned32,
        sapTlsMvplsMgmtMsti             MstiInstanceIdOrZero,
        sapTlsMacMoveNextUpTime         Unsigned32,
        sapTlsMacMoveRateExcdLeft       Unsigned32,
        sapTlsRestProtSrcMacAction      INTEGER,
        sapTlsL2ptForceBoundary         TruthValue,
        sapTlsLimitMacMoveLevel         TlsLimitMacMoveLevel,
        sapTlsBpduTransOper             INTEGER,
        sapTlsDefMsapPolicy             TPolicyStatementNameOrEmpty,
        sapTlsL2ptProtocols             L2ptProtocols,
        sapTlsL2ptForceProtocols        L2ptProtocols,
        sapTlsPppoeMsapTrigger          TruthValue,
        sapTlsDhcpMsapTrigger           TruthValue,
        sapTlsMrpJoinTime               Unsigned32,
        sapTlsMrpLeaveTime              Unsigned32,
        sapTlsMrpLeaveAllTime           Unsigned32,
        sapTlsMrpPeriodicTime           Unsigned32,
        sapTlsMrpPeriodicEnabled        TruthValue
    }

sapTlsStpAdminStatus OBJECT-TYPE
    SYNTAX          TmnxEnabledDisabled
    MAX-ACCESS      read-write
    STATUS          current
    DESCRIPTION     "The value of the object sapTlsStpAdminStatus specifies
                     whether this SAP participates in the TLS's Spanning Tree
                     Protocol."
    DEFVAL          { enabled }
    ::= { sapTlsInfoEntry 1 }

sapTlsStpPriority OBJECT-TYPE
    SYNTAX          INTEGER (0..255)
    MAX-ACCESS      read-write
    STATUS          current
    DESCRIPTION     "The value of the object sapTlsStpPriority specifies
                     the value of the port priority field which is contained in
                     the most significant 4 bits of the 16-bit Port ID
                     associated with this SAP. As only the most significant 4
                     bits of the value are used, the actual value of this object
                     is limited to multiples of 16: e.g. the agent rounds down
                     the value to one of: 0, 16, 32, .. , 224, 240."
    DEFVAL          { 128 }
    ::= { sapTlsInfoEntry 2 }

sapTlsStpPortNum OBJECT-TYPE
    SYNTAX          INTEGER (0..4094)
    MAX-ACCESS      read-write
    STATUS          current
    DESCRIPTION     "The value of the object sapTlsStpPortNum specifies the
                     value of the port number field which is contained in the
                     least significant 12 bits of the 16-bit Port ID associated
                     with this SAP. Values in the range 2048..4094 are
                     automatically assigned by the agent when the SAP is
                     created or when the value of this object is set to zero
                     via management. Values in the range 1..2047 can be set
                     via management, to allow this object to have a
                     deterministic value across system reboots."
    ::= { sapTlsInfoEntry 3 }

sapTlsStpPathCost OBJECT-TYPE
    SYNTAX          INTEGER (1..200000000)
    MAX-ACCESS      read-write
    STATUS          current
    DESCRIPTION     "The value of the object  sapTlsStpPathCost specifies the
                     contribution of this port to the path cost of paths
                     towards the spanning tree root which include this port."
    DEFVAL          { 10 }
    ::= { sapTlsInfoEntry 4 }

sapTlsStpRapidStart OBJECT-TYPE
    SYNTAX          TmnxEnabledDisabled
    MAX-ACCESS      read-write
    STATUS          current
    DESCRIPTION     "The value of the object sapTlsStpRapidStart specifies
                     whether Rapid Start is enabled on this SAP. When the value
                     is 'enabled' the Spanning Tree Protocol state transitions
                     on this SAP are driven by the value of the 'HelloTime'
                     instead of the value of 'ForwardDelay', thus allowing a
                     faster transition into the forwarding state. This
                     parameter is also referred to as 'adminEdge'. "
    DEFVAL          { disabled }
    ::= { sapTlsInfoEntry 5 }

sapTlsStpBpduEncap OBJECT-TYPE
    SYNTAX          INTEGER {
                        dynamic (1),
                        dot1d   (2),
                        pvst    (3)
                    }
    MAX-ACCESS      read-write
    STATUS          current
    DESCRIPTION     "The value of the object sapTlsStpBpduEncap specifies the
                     type of encapsulation used on BPDUs sent out and received
                     on this SAP."
    DEFVAL          { dynamic }
    ::= { sapTlsInfoEntry 6 }

sapTlsStpPortState OBJECT-TYPE
    SYNTAX          TStpPortState
    MAX-ACCESS      read-only
    STATUS          current
    DESCRIPTION     "The value of the object sapTlsStpPortState indicates the
                     port's current state as defined by application of the
                     Spanning Tree Protocol. This state controls what action a
                     port takes on reception of a frame. If the bridge has
                     detected a port that is malfunctioning it will
                     place that port into the 'broken' state."
    ::= { sapTlsInfoEntry 7 }

sapTlsStpDesignatedBridge OBJECT-TYPE
    SYNTAX          BridgeId
    MAX-ACCESS      read-only
    STATUS          current
    DESCRIPTION     "The value of the object sapTlsStpDesignatedBridge
                     indicates  the Bridge Identifier of the bridge which this
                     port considers to be the Designated Bridge for this port's
                     segment."
    ::= { sapTlsInfoEntry 8 }

sapTlsStpDesignatedPort OBJECT-TYPE
    SYNTAX          Integer32
    MAX-ACCESS      read-only
    STATUS          current
    DESCRIPTION     "The value of the object sapTlsStpDesignatedPort indicates
                     the Port Identifier of the port on the Designated Bridge
                     for this port's segment."
    ::= { sapTlsInfoEntry 9 }

sapTlsStpForwardTransitions OBJECT-TYPE
    SYNTAX          Gauge32
    MAX-ACCESS      read-only
    STATUS          current
    DESCRIPTION     "The value of the object sapTlsStpForwardTransitions
                     indicates the number of times this port has transitioned
                     from the Learning state to the Forwarding state."
    ::= { sapTlsInfoEntry 10 }

sapTlsStpInConfigBpdus OBJECT-TYPE
    SYNTAX          Gauge32
    MAX-ACCESS      read-only
    STATUS          current
    DESCRIPTION     "The value of the object sapTlsStpInConfigBpdus indicates
                     the number of Configuration BPDUs received on this SAP."
    ::= { sapTlsInfoEntry 11 }

sapTlsStpInTcnBpdus OBJECT-TYPE
    SYNTAX          Gauge32
    MAX-ACCESS      read-only
    STATUS          current
    DESCRIPTION     "The value of the object  sapTlsStpInTcnBpdus indicates the
                     number of Topology Change Notification BPDUs received on
                     this SAP."
    ::= { sapTlsInfoEntry 12 }

sapTlsStpInBadBpdus OBJECT-TYPE
    SYNTAX          Gauge32
    MAX-ACCESS      read-only
    STATUS          current
    DESCRIPTION     "This object specifies the number of bad
                     BPDUs received on this SAP."
    ::= { sapTlsInfoEntry 13 }

sapTlsStpOutConfigBpdus OBJECT-TYPE
    SYNTAX          Gauge32
    MAX-ACCESS      read-only
    STATUS          current
    DESCRIPTION     "The value of the object sapTlsStpOutConfigBpdus indicates
                     the number of Configuration BPDUs sent out this SAP."
    ::= { sapTlsInfoEntry 14 }

sapTlsStpOutTcnBpdus OBJECT-TYPE
    SYNTAX          Gauge32
    MAX-ACCESS      read-only
    STATUS          current
    DESCRIPTION     "This object specifies the number of Topology
                     Change Notification BPDUs sent out this SAP."
    ::= { sapTlsInfoEntry 15 }

sapTlsStpOperBpduEncap OBJECT-TYPE
    SYNTAX          INTEGER {
                        dynamic (1),
                        dot1d   (2),
                        pvst    (3)
                    }
    MAX-ACCESS      read-only
    STATUS          current
    DESCRIPTION     "The value of the object sapTlsStpOperBpduEncap indicates
                     the operating encapsulation  type used on BPDUs sent out
                     and received on this SAP."
    ::= { sapTlsInfoEntry 16 }

sapTlsVpnId OBJECT-TYPE
    SYNTAX          VpnId
    MAX-ACCESS      read-only
    STATUS          current
    DESCRIPTION     "The value of the object sapTlsVpnId indicates the VPN ID
                     of the associated service."
    ::= { sapTlsInfoEntry 17 }

sapTlsCustId OBJECT-TYPE
    SYNTAX          TmnxCustId
    MAX-ACCESS      read-only
    STATUS          current
    DESCRIPTION     "The Customer ID of the associated service."
    ::= { sapTlsInfoEntry 18 }

sapTlsMacAddressLimit OBJECT-TYPE
    SYNTAX          Integer32(0..196607)
    MAX-ACCESS      read-write
    STATUS          current
    DESCRIPTION     "The value of the object sapTlsMacAddressLimit specifies
                     the maximum number of learned and static entries allowed
                     in the FDB of this SAP. The value 0 means: no limit for
                     this SAP. When the value of
                     ALCATEL-IND1-TIMETRA-CHASSIS-MIB::tmnxChassisOperMode is not 'c', the
                     maximum value of sapTlsMacAddressLimit is '131071'."
    DEFVAL          { 0 }
    ::= { sapTlsInfoEntry 19 }

sapTlsNumMacAddresses OBJECT-TYPE
    SYNTAX          Integer32
    MAX-ACCESS      read-only
    STATUS          current
    DESCRIPTION     "The value of the object sapTlsNumMacAddresses indicates
                     the number of MAC addresses  currently present in the FDB
                     that belong to this  SAP  (Both  learned and static MAC
                     addresses are counted)."
    ::= { sapTlsInfoEntry 20 }

sapTlsNumStaticMacAddresses OBJECT-TYPE
    SYNTAX          Integer32
    MAX-ACCESS      read-only
    STATUS          current
    DESCRIPTION     "The value of the object sapTlsNumStaticMacAddresses
                     indicates the number of static MAC addresses currently
                     present in the FDB that belong to this SAP."
    ::= { sapTlsInfoEntry 21 }

sapTlsMacLearning OBJECT-TYPE
    SYNTAX          TmnxEnabledDisabled
    MAX-ACCESS      read-write
    STATUS          current
    DESCRIPTION     "The value of the object sapTlsMacLearning specifies
                     whether the MAC learning process  is enabled for this SAP.
                     The value is ignored if MAC learning is disabled on
                     service level."
    DEFVAL          { enabled }
    ::= { sapTlsInfoEntry 22 }

sapTlsMacAgeing OBJECT-TYPE
    SYNTAX          TmnxEnabledDisabled
    MAX-ACCESS      read-write
    STATUS          current
    DESCRIPTION     "The value of the object sapTlsMacAgeing specifies whether
                     the MAC aging process  is enabled for this SAP. the value
                     is ignored if MAC aging is disabled on service level."
    DEFVAL          { enabled }
    ::= { sapTlsInfoEntry 23 }

sapTlsStpOperEdge OBJECT-TYPE
    SYNTAX          TruthValue
    MAX-ACCESS      read-only
    STATUS          current
    DESCRIPTION     "The value of the object sapTlsStpOperEdge indicates the
                     operational value of the Edge Port parameter. The object
                     is initialized to the value of sapTlsStpRapidStart and is
                     set FALSE on reception of a BPDU."
    REFERENCE
                    "IEEE 802.1t clause 14.8.2, 18.3.4"
    ::= { sapTlsInfoEntry 24 }

sapTlsStpAdminPointToPoint OBJECT-TYPE
    SYNTAX          INTEGER {
                        forceTrue  (0),
                        forceFalse (1)
                    }
    MAX-ACCESS      read-write
    STATUS          current
    DESCRIPTION     "The value of the object sapTlsStpAdminPointToPoint
                     specifies the administrative point-to-point  status  of
                     the LAN segment attached to this  sap. The value
                     'forceTrue' means that this port should  always  be
                     treated as if it is connected to a point-to-point link.
                     The value of 'forceFalse' means that this port should
                     be treated as having a shared media connection."
    REFERENCE
                    "IEEE 802.1w clause 6.4.3, 6.5, 14.8.2"
    DEFVAL          { forceTrue }
    ::= { sapTlsInfoEntry 25 }

sapTlsStpPortRole OBJECT-TYPE
    SYNTAX          StpPortRole
    MAX-ACCESS      read-only
    STATUS          current
    DESCRIPTION     "sapTlsStpPortRole indicates the current role of the
                     sap as defined by the Rapid Spanning Tree Protocol."
    ::= { sapTlsInfoEntry 26 }

sapTlsStpAutoEdge OBJECT-TYPE
    SYNTAX          TmnxEnabledDisabled
    MAX-ACCESS      read-write
    STATUS          current
    DESCRIPTION     "sapTlsStpAutoEdge specifies whether this SAP
                     is enabled for auto-edge detection as defined by Rapid
                     Spanning Tree Protocol."
    DEFVAL          { enabled }
    ::= { sapTlsInfoEntry 27 }

sapTlsStpOperProtocol OBJECT-TYPE
    SYNTAX          StpProtocol
    MAX-ACCESS      read-only
    STATUS          current
    DESCRIPTION     "sapTlsStpOperProtocol indicates whether stp, rstp or
                     mstp is  running  on this SAP. If the protocol is not
                     enabled  on  this  SAP,  the  value  notApplicable  is
                     returned."
    ::= { sapTlsInfoEntry 28 }

sapTlsStpInRstBpdus OBJECT-TYPE
    SYNTAX          Gauge32
    MAX-ACCESS      read-only
    STATUS          current
    DESCRIPTION     "The value of the object  sapTlsStpInRstBpdus indicates
                     the number of Rapid Spanning Tree (RST) BPDUs received on
                     this SAP."
    ::= { sapTlsInfoEntry 29 }

sapTlsStpOutRstBpdus OBJECT-TYPE
    SYNTAX          Gauge32
    MAX-ACCESS      read-only
    STATUS          current
    DESCRIPTION     "The value of the  object sapTlsStpOutRstBpdus indicates
                     the number of Rapid Spanning Tree (RST) BPDUs sent out on
                     this SAP."
    ::= { sapTlsInfoEntry 30 }

sapTlsLimitMacMove OBJECT-TYPE
    SYNTAX          TlsLimitMacMove
    MAX-ACCESS      read-write
    STATUS          current
    DESCRIPTION     "When sapTlsLimitMacMove value is set  to  'blockable'
                     the  agent will monitor the MAC relearn rate on this
                     SAP,  and it will  block  it  when the re-learn rate
                     specified  by  svcTlsMacMoveMaxRate  is exceeded. When
                     the  value is  'nonBlockable'  this  SAP will not be
                     blocked,  and  another  blockable  SAP will be blocked
                     instead."
    DEFVAL          { blockable }
    ::= { sapTlsInfoEntry 31 }

sapTlsDhcpSnooping OBJECT-TYPE
    SYNTAX          TmnxEnabledDisabled
    MAX-ACCESS      read-write
    STATUS          obsolete
    DESCRIPTION     "The value of the object sapTlsDhcpSnooping specifies
                     whether or not DHCP packets received on this SAP will be
                     snooped. This object was made obsolete in the 3.0 release."
    DEFVAL          { disabled }
    ::= { sapTlsInfoEntry 32 }

sapTlsMacPinning OBJECT-TYPE
    SYNTAX          TmnxEnabledDisabled
    MAX-ACCESS      read-write
    STATUS          current
    DESCRIPTION     "The value of the object sapTlsMacPinning specifies whether
                     or not MAC address pinning is active on this SAP. The
                     value will be set by default to disabled. However for a
                     SAP that belongs to a residential SHG, the value is set to
                     enabled by the system, and cannot be altered by the
                     operator. Setting the value to enable disables
                     re-learning of MAC addresses on other SAPs or
                     spoke-SDPs within the same VPLS; the MAC address will
                     hence remain attached to the SAP for the duration of
                     its age-timer. This object has effect only for MAC
                     addresses learned via the normal MAC learning
                     process, and not for entries learned via DHCP."
    ::= { sapTlsInfoEntry 33 }

sapTlsDiscardUnknownSource OBJECT-TYPE
    SYNTAX          TmnxEnabledDisabled
    MAX-ACCESS      read-write
    STATUS          current
    DESCRIPTION     "with   the object sapTlsMacAddressLimit a limit can be
                     configured  for  the  max number of MAC addresses that
                     will  be learned on this  SAP.  When  this limit is
                     reached, packets with unknown source MAC address are
                     forwarded by default. By setting
                     sapTlsDiscardUnknownSource  to enabled, packets with
                     unknown source MAC will be dropped in stead."
    DEFVAL          { disabled }
    ::= { sapTlsInfoEntry 34 }

sapTlsMvplsPruneState OBJECT-TYPE
    SYNTAX          MvplsPruneState
    MAX-ACCESS      read-only
    STATUS          current
    DESCRIPTION     "The value of sapTlsMvplsPruneState indicates the mVPLS
                     prune state of the SAP. The object will be set to
                     notApplicable if the SAP is not managed by a mVPLS. If
                     the SAP is managed the state reflects whether or not
                     the SAP is pruned by the STP instance running in the
                     mVPLS instance."
    ::= { sapTlsInfoEntry 35 }

sapTlsMvplsMgmtService OBJECT-TYPE
    SYNTAX          TmnxServId
    MAX-ACCESS      read-only
    STATUS          current
    DESCRIPTION     "The value of sapTlsMvplsMgmtService indicates the
                     service Id of the service where the STP instance is
                     running that is managing this SAP. This object is
                     only valid if sapTlsMvplsPruneState is different from
                     notApplicable."
    ::= { sapTlsInfoEntry 36 }

sapTlsMvplsMgmtPortId OBJECT-TYPE
    SYNTAX          TmnxPortID
    MAX-ACCESS      read-only
    STATUS          current
    DESCRIPTION     "The value of sapTlsMvplsMgmtPortId indicates the SAP
                     port Id of the SAP in the mVPLS instance specified in
                     sapTlsMvplsMgmtService that is controlling this SAP.
                     This object is only valid if sapTlsMvplsPruneState is
                     different from notApplicable."
    ::= { sapTlsInfoEntry 37 }

sapTlsMvplsMgmtEncapValue OBJECT-TYPE
    SYNTAX          TmnxEncapVal
    MAX-ACCESS      read-only
    STATUS          current
    DESCRIPTION     "The value of sapTlsMvplsMgmtEncapValue indicates the
                     SAP Encap value of the SAP in the mVPLS instance
                     specified in sapTlsMvplsMgmtService that is
                     controlling this SAP. This object is only valid if
                     sapTlsMvplsPruneState is different from notApplicable."
    ::= { sapTlsInfoEntry 38 }

sapTlsArpReplyAgent OBJECT-TYPE
    SYNTAX          INTEGER {
                        disabled               (1),
                        enabled                (2),
                        enabledWithSubscrIdent (3)
                    }
    MAX-ACCESS      read-write
    STATUS          current
    DESCRIPTION     "The value of the object sapTlsArpReplyAgent specifies
                     the status of the special ARP response mechanism in the
                     system for ARP requests destined to static or dynamic hosts
                     associated with this SAP.
                     disabled: the ARP reply function is not operational
                     enabled: the ARP reply function is enabled without
                              subscriber identification.
                     enabledWithSubscrIdent: the ARP reply function is enabled
                                             with subscriber identification."
    DEFVAL { disabled }
    ::= { sapTlsInfoEntry 39 }

sapTlsStpException OBJECT-TYPE
    SYNTAX          StpExceptionCondition
    MAX-ACCESS      read-only
    STATUS          current
    DESCRIPTION     "The value of the object sapTlsStpException indicates
                     whether an STP exception condition is present on this
                     Sap.
                     - none : no exception condition found.
                     - oneWayCommuniation : The neighbor RSTP peer on this link
                                            is not able to detect our presence.
                     - downstreamLoopDetected :A loop is detected on this link."
    ::= { sapTlsInfoEntry 40 }

sapTlsAuthenticationPolicy OBJECT-TYPE
    SYNTAX      TPolicyStatementNameOrEmpty
    MAX-ACCESS  read-write
    STATUS      current
    DESCRIPTION  "The value of the object sapTlsAuthenticationPolicy specifies
                  which subscriber authentication policy  must  be applied when
                  a DHCP msg is received on the interface.  The  authentication
                  policies  must be defined  in  tmnxSubAuthPlcyTable. The policy
                  will only be applied when sapTlsDhcpSnoop is enabled."
    DEFVAL { ''H }
    ::= { sapTlsInfoEntry 41 }

sapTlsL2ptTermination OBJECT-TYPE
    SYNTAX          TmnxEnabledDisabled
    MAX-ACCESS      read-write
    STATUS          current
    DESCRIPTION     "The value of the object sapTlsL2ptTermination specifies
                     whether received L2 Protocol Tunnel pdu's are terminated
                     on this port or sap"
    DEFVAL          { disabled }
    ::= { sapTlsInfoEntry 42 }

sapTlsBpduTranslation OBJECT-TYPE
    SYNTAX          INTEGER {
                        auto     (1),
                        disabled (2),
                        pvst     (3),
                        stp      (4)
                    }
    MAX-ACCESS      read-write
    STATUS          current
    DESCRIPTION     "The value of the object sapTlsBpduTranslation specifies
                     whether received L2 Protocol Tunnel pdu's are
                     translated before being sent out on this port or sap"
    DEFVAL          { disabled }
    ::= { sapTlsInfoEntry 43 }

sapTlsStpRootGuard OBJECT-TYPE
    SYNTAX          TruthValue
    MAX-ACCESS      read-write
    STATUS          current
    DESCRIPTION     "The value of the object sapTlsStpRootGuard specifies
                     whether this port is allowed to become STP root port.
                     It corresponds to the parameter 'restrictedRole' in 802.1Q.
                     If set, it can cause lack of spanning tree connectivity."
    DEFVAL          { false }
    ::= { sapTlsInfoEntry 44 }

sapTlsStpInsideRegion OBJECT-TYPE
    SYNTAX          TruthValue
    MAX-ACCESS      read-only
    STATUS          current
    DESCRIPTION     "The value of the object sapTlsStpInsideRegion indicates
                     whether the network connected to the SAP is in the same
                     MST region. It corresponds to the parameter 'infoInternal'
                     in 802.1Q."
    ::= { sapTlsInfoEntry 45 }

sapTlsEgressMcastGroup OBJECT-TYPE
    SYNTAX          TNamedItemOrEmpty
    MAX-ACCESS      read-write
    STATUS          current
    DESCRIPTION     "The value of the object sapTlsEgressMcastGroup specifies
                     the Egress Multicast Group this SAP belongs to."
    DEFVAL          { "" }
    ::= { sapTlsInfoEntry 46 }

sapTlsStpInMstBpdus OBJECT-TYPE
    SYNTAX          Gauge32
    MAX-ACCESS      read-only
    STATUS          current
    DESCRIPTION     "The value of the object sapTlsStpInMstBpdus indicates
                     the number of Multiple Spanning Tree (MST) BPDUs received
                     on this SAP."
    ::= { sapTlsInfoEntry 47 }

sapTlsStpOutMstBpdus OBJECT-TYPE
    SYNTAX          Gauge32
    MAX-ACCESS      read-only
    STATUS          current
    DESCRIPTION     "The value of the object sapTlsStpOutMstBpdus indicates
                     the number of Multiple Spanning Tree (MST) BPDUs sent out
                     on this SAP."
    ::= { sapTlsInfoEntry 48 }

sapTlsRestProtSrcMac OBJECT-TYPE
    SYNTAX          TruthValue
    MAX-ACCESS      read-write
    STATUS          current
    DESCRIPTION     "The value of the object sapTlsRestProtSrcMac specifies
                     how the agent will handle relearn requests for protected
                     MAC addresses. When the value of this object is 'true'
                     requests to relearn a protected MAC address will be
                     ignored.
                     In addition, if the value of sapTlsRestProtSrcMacAction
                     is 'disable', then the SAP where the protected source
                     MAC was seen will be brought operationally down."
    DEFVAL          { false }
    ::= { sapTlsInfoEntry 49 }

sapTlsRestUnprotDstMac OBJECT-TYPE
    SYNTAX          TruthValue
    MAX-ACCESS      read-write
    STATUS          current
    DESCRIPTION     "The value of the object sapTlsRestUnprotDstMac specifies
                     how the system will forward packets destined to an
                     unprotected MAC address. When the value of this object is
                     'true' packets destined to an unprotected MAC address
                     will be dropped."
    DEFVAL          { false }
    ::= { sapTlsInfoEntry 50 }

sapTlsStpRxdDesigBridge OBJECT-TYPE
    SYNTAX          BridgeId
    MAX-ACCESS      read-only
    STATUS          current
    DESCRIPTION     "The value of the object sapTlsStpRxdDesigBridge
                     indicates  the designated Bridge Identifier in the last
                     BPDU which was received on this SAP. It identifies
                     which bridge is connected to the SAP."
    ::= { sapTlsInfoEntry 51 }

sapTlsStpRootGuardViolation OBJECT-TYPE
    SYNTAX          TruthValue
    MAX-ACCESS      read-only
    STATUS          current
    DESCRIPTION     "The value of the object sapTlsStpRootGuardViolation
                     indicates whether there is a root-guard violation at the
                     present time. This can only happen when sapTlsStpRootGuard
                     is set to true."
    ::= { sapTlsInfoEntry 52 }


sapTlsShcvAction OBJECT-TYPE
    SYNTAX          INTEGER {
                         alarm  (1),
                         remove (2)
                    }
    MAX-ACCESS      read-write
    STATUS          current
    DESCRIPTION     "The value of the object sapTlsShcvAction
                     indicates whether any action should be triggered when
                     the connectivity check fails."
    DEFVAL          { alarm }
    ::= { sapTlsInfoEntry 53 }


sapTlsShcvSrcIp OBJECT-TYPE
    SYNTAX          IpAddress
    MAX-ACCESS      read-write
    STATUS          current
    DESCRIPTION     "The value of the object sapTlsShcvSrcIp
                     specifies the source IP address used when doing the
                     connectivity check. The value 0.0.0.0 indicates that
                     no host IP address is specified."
    ::= { sapTlsInfoEntry 54 }

sapTlsShcvSrcMac OBJECT-TYPE
    SYNTAX          MacAddress
    MAX-ACCESS      read-write
    STATUS          current
    DESCRIPTION     "The value of the object sapTlsShcvSrcMac
                     specifies the MAC address used when doing the connectivity
                     check. The value 0:0:0:0:0:0 indicates that no host MAC
                     address is specified."
    ::= { sapTlsInfoEntry 55 }

sapTlsShcvInterval OBJECT-TYPE
    SYNTAX          Unsigned32 (0..6000)
    UNITS           "minutes"
    MAX-ACCESS      read-write
    STATUS          current
    DESCRIPTION     "The value of the object sapTlsShcvInterval specifies
                     the interval in minutes between connectivity checks.
                     Zero means no connectivity checking."
    DEFVAL          { 0 }
    ::= { sapTlsInfoEntry 56 }

sapTlsMvplsMgmtMsti OBJECT-TYPE
    SYNTAX          MstiInstanceIdOrZero
    MAX-ACCESS      read-only
    STATUS          current
    DESCRIPTION     "The value of the object sapTlsMvplsMgmtMsti indicates the
                     MST-instance in the mVPLS instance specified in
                     sapTlsMvplsMgmtService that is controlling this SAP. A
                     value of 0 indicates the CIST.
                     This object is only valid if sapTlsMvplsPruneState is
                     different from notApplicable."
    ::= { sapTlsInfoEntry 57 }

sapTlsMacMoveNextUpTime OBJECT-TYPE
    SYNTAX          Unsigned32
    UNITS           "seconds"
    MAX-ACCESS      read-only
    STATUS          current
    DESCRIPTION     "The value of the object sapTlsMacMoveNextUpTime counts down
                     the time in seconds until a SAP that has been brought down
                     due to exceeding the TLS svcTlsMacMoveMaxRate, sapOperFlags
                     'relearnLimitExceeded', is automatically brought up again.
                     When this value is 0xffff, the SAP will never be
                     automatically brought up. The value is zero when
                     sapOperStatus is 'up'."
    ::= { sapTlsInfoEntry 58 }

sapTlsMacMoveRateExcdLeft   OBJECT-TYPE
    SYNTAX          Unsigned32
    MAX-ACCESS      read-only
    STATUS          current
    DESCRIPTION     "The value of the object sapTlsMacMoveRateExcdLeft
                     counts down the number of times this SAP can exceed the
                     TLS svcTlsMacMoveMaxRate and still be automatically
                     brought up."
    ::= { sapTlsInfoEntry 59 }

sapTlsRestProtSrcMacAction OBJECT-TYPE
    SYNTAX          INTEGER {
                        disable    (1),
                        alarm-only (2)
                    }
    MAX-ACCESS      read-write
    STATUS          current
    DESCRIPTION     "The value of the object sapTlsRestProtSrcMacAction
                     indicates the action to take whenever a relearn request
                     for a protected MAC is received on a restricted SAP.
                     When the value of this object is 'disable' the SAP
                     will be placed in the operational down state, with the
                     operating flag 'recProtSrcMac' set. When the value of
                     this object is 'alarm-only', the SAP will be left up
                     and only a notification, sapReceivedProtSrcMac,  will be
                     generated."
    DEFVAL          { disable }
    ::= { sapTlsInfoEntry 60 }

sapTlsL2ptForceBoundary OBJECT-TYPE
    SYNTAX          TruthValue
    MAX-ACCESS      read-write
    STATUS          current
    DESCRIPTION     "The value of sapTlsL2ptForceBoundary specifies if
                     sapTlsL2ptTermination is enforced for its managed SAP's.
                     Setting the value of the object sapTlsL2ptForceBoundary of
                     a SAP in a Management VPLS to `true' forces all its
                     managed SAP's to have sapTlsL2ptTermination enabled. This
                     value can only be `true' if the SAP belongs to a
                     management VPLS.
                     If this SAP has managed SAP's already with
                     sapTlsL2ptTermination disabled, it is not allowed
                     to set sapTlsL2ptForceBoundary to `true'."
    DEFVAL          { false }
    ::= { sapTlsInfoEntry 61 }

sapTlsLimitMacMoveLevel OBJECT-TYPE
    SYNTAX          TlsLimitMacMoveLevel
    MAX-ACCESS      read-write
    STATUS          current
    DESCRIPTION     "The value of the object sapTlsLimitMacMoveLevel
                     specifies the hierarchy in which SAPs are
                     blocked when a MAC-move limit is exceeded. When a MAC is
                     moving among multiple SAPs or spoke-SDPs, the SAP bind
                     or spoke-SDP bind with the lower level is blocked first.
                     (tertiary is the lowest)"
    DEFVAL          { tertiary }
    ::= { sapTlsInfoEntry 62 }

sapTlsBpduTransOper OBJECT-TYPE
    SYNTAX          INTEGER {
                        undefined (1),
                        disabled  (2),
                        pvst      (3),
                        stp       (4)
                    }
    MAX-ACCESS      read-only
    STATUS          current
    DESCRIPTION     "The value of the object sapTlsBpduTransOper indicates
                     the operational bpdu encapsulation used for BPDU
                     translated frames."
    ::= { sapTlsInfoEntry 63 }

sapTlsDefMsapPolicy OBJECT-TYPE
    SYNTAX          TPolicyStatementNameOrEmpty
    MAX-ACCESS      read-write
    STATUS          current
    DESCRIPTION     "The value of sapTlsDefMsapPolicy specifies the
                     default Managed SAP policy to use to create
                     Managed SAPs when the response from the Radius
                     server does not specify a Managed SAP policy.

                     The value of sapTlsDefMsapPolicy is only valid for
                     a SAP with a sapSubType value of 'capture'.
                     If the value is set to a non-empty string for a
                     SAP with a sapSubType value other than 'capture',
                     an 'inconsistentValue' error will be returned.

                     The Managed SAP policy must be defined in
                     msapPlcyTable, otherwise an 'inconsistentValue'
                     error will be returned."
    DEFVAL         { "" }
    ::= { sapTlsInfoEntry 64 }

sapTlsL2ptProtocols OBJECT-TYPE
    SYNTAX          L2ptProtocols
    MAX-ACCESS      read-write
    STATUS          current
    DESCRIPTION     "The value of the object sapTlsL2ptTermination specifies
                     which L2 Protocol Tunnel pdu's are terminated
                     on this port or sap"
    DEFVAL          { { stp } }
    ::= { sapTlsInfoEntry 65 }

sapTlsL2ptForceProtocols OBJECT-TYPE
    SYNTAX          L2ptProtocols
    MAX-ACCESS      read-write
    STATUS          current
    DESCRIPTION     "The value of the object sapTlsL2ptForceProtocols specifies
                     which L2 Protocol Tunnel pdu's must be terminated by
                     SAP's managed by this SAP.
                     This object is only relevant if the value of the object
                     sapTlsL2ptForceBoundary is 'true'.
                     For every SAP managed by this SAP, each L2 protocol
                     specified by sapTlsL2ptForceProtocols must be terminated,
                     while other L2 protocols may or may not be terminated,
                     depending on the value of sapTlsL2ptProtocols of that
                     managed SAP."
    DEFVAL          { { stp } }
    ::= { sapTlsInfoEntry 66 }

sapTlsPppoeMsapTrigger OBJECT-TYPE
    SYNTAX          TruthValue
    MAX-ACCESS      read-write
    STATUS          current
    DESCRIPTION     "The value of sapTlsPppoeMsapTrigger specifies whether
                     the receipt of PPPoE trigger packets on a VPLS SAP
                     with a sapSubType value of 'capture' will result in
                     a Radius authentication that will provide a service
                     context and the creation of a SAP with a sapSubType
                     value of 'managed'.

                     An attempt to set the value sapTlsPppoeMsapTrigger to
                     'true' on a SAP with sapSubType other than 'capture'
                     will return an 'inconsistentValue' error."
    DEFVAL         { false }
    ::= { sapTlsInfoEntry 67 }

sapTlsDhcpMsapTrigger OBJECT-TYPE
    SYNTAX          TruthValue
    MAX-ACCESS      read-write
    STATUS          current
    DESCRIPTION     "The value of sapTlsDhcpMsapTrigger specifies whether
                     the receipt of DHCP trigger packets on this VPLS SAP
                     with a sapSubType value of 'capture' will result in
                     a Radius authentication that will provide a service
                     context and the creation of a SAP with a sapSubType
                     value of 'managed'.

                     An attempt to set the value sapTlsDhcpMsapTrigger to
                     'true' on a SAP with sapSubType other than 'capture'
                     will return an 'inconsistentValue' error."
    DEFVAL         { false }
    ::= { sapTlsInfoEntry 68 }

sapTlsMrpJoinTime OBJECT-TYPE
    SYNTAX          Unsigned32 (1..10)
    UNITS           "deci-seconds"
    MAX-ACCESS      read-write
    STATUS          current
    DESCRIPTION     "The value of sapTlsMrpJoinTime specifies a timer value in
                    10ths of seconds which determines the maximum rate at
                    which attribute join messages can be sent on the SAP."
    DEFVAL         { 2 }
    ::= { sapTlsInfoEntry 69 }

sapTlsMrpLeaveTime OBJECT-TYPE
    SYNTAX          Unsigned32 (30..60)
    UNITS           "deci-seconds"
    MAX-ACCESS      read-write
    STATUS          current
    DESCRIPTION     "The value of sapTlsMrpLeaveTime specifies a timer value in
                    10ths of seconds which determines the amount of time a
                    registered attribute is held in leave state before the
                    registration is removed."
    DEFVAL         { 30 }
    ::= { sapTlsInfoEntry 70 }

sapTlsMrpLeaveAllTime OBJECT-TYPE
    SYNTAX          Unsigned32 (60..300)
    UNITS           "deci-seconds"
    MAX-ACCESS      read-write
    STATUS          current
    DESCRIPTION     "The value of sapTlsMrpLeaveAllTime specifies the a timer
                    value in 10ths of seconds which determines the frequency
                    where all attribute declarations on the SAP are all
                    refreshed."
    DEFVAL         { 100 }
    ::= { sapTlsInfoEntry 71 }

sapTlsMrpPeriodicTime OBJECT-TYPE
    SYNTAX          Unsigned32 (10..100)
    UNITS           "deci-seconds"
    MAX-ACCESS      read-write
    STATUS          current
    DESCRIPTION     "The value of sapTlsMrpPeriodicTime specifies a timer value
                    in 10ths of seconds which determines the frequency of
                    re-transmission of attribute declarations."
    DEFVAL         { 10 }
    ::= { sapTlsInfoEntry 72 }

sapTlsMrpPeriodicEnabled OBJECT-TYPE
    SYNTAX          TruthValue
    MAX-ACCESS      read-write
    STATUS          current
    DESCRIPTION     "The value of sapTlsMrpPeriodicEnabled specifies whether
                    re-transmission of attribute declarations is enabled."
    DEFVAL         { false }
    ::= { sapTlsInfoEntry 73 }


-- ---------------------------------------------------------------------
-- ATM SAP Table
--
--
--  Sparse Dependent Extention of the sapBaseInfoTable.
--
--  The same indexes are used for both the base table, sapBaseInfoTable,
--  and the sparse dependent table, sapAtmInfoTable.
--
--  This in effect extends the sapBaseInfoTable with additional columns.
--  Rows are created in the sapAtmInfoTable only for those entries
--  in the sapBaseInfoTable that are created on a port that 'atmEncap' set
--- for port encapsulation.
--
--  Deletion of a row in the sapBaseInfoTable results in the
--  same fate for the row in the sapAtmInfoTable.
-- ---------------------------------------------------------------------
sapAtmInfoTable OBJECT-TYPE
    SYNTAX          SEQUENCE OF SapAtmInfoEntry
    MAX-ACCESS      not-accessible
    STATUS          current
    DESCRIPTION     "A table that contains ATM SAP information."
    ::= { tmnxSapObjs 4 }

sapAtmInfoEntry OBJECT-TYPE
    SYNTAX          SapAtmInfoEntry
    MAX-ACCESS      not-accessible
    STATUS          current
    DESCRIPTION     "Information about a specific ATM SAP."
    INDEX           { svcId, sapPortId, sapEncapValue }
    ::= { sapAtmInfoTable 1 }

SapAtmInfoEntry ::=
    SEQUENCE {
        sapAtmEncapsulation             INTEGER,
        sapAtmIngressTrafficDescIndex   AtmTrafficDescrParamIndex,
        sapAtmEgressTrafficDescIndex    AtmTrafficDescrParamIndex,
        sapAtmOamAlarmCellHandling      ServiceAdminStatus,
        sapAtmOamTerminate              ServiceAdminStatus,
        sapAtmOamPeriodicLoopback       ServiceAdminStatus
  }

sapAtmEncapsulation OBJECT-TYPE
    SYNTAX          INTEGER {
                         vcMultiplexRoutedProtocol      (1),
                         vcMultiplexBridgedProtocol8023 (2),
                         llcSnapRoutedProtocol          (7),
                         multiprotocolFrameRelaySscs    (8),
                         unknown                        (10),
                         llcSnapBridgedProtocol8023     (11)
                     }
    MAX-ACCESS       read-write
    STATUS           current
    DESCRIPTION      "This object specifies the data encapsulation used
                      over the AAL5 SSCS layer.  The definition references
                      RFC 2684 Multiprotocol Encapsulation over ATM AAL5
                      and to the ATM Forum LAN Emulation specification."
    DEFVAL           { llcSnapRoutedProtocol }
    ::= { sapAtmInfoEntry 1 }

sapAtmIngressTrafficDescIndex OBJECT-TYPE
    SYNTAX           AtmTrafficDescrParamIndex(1..1000)
    MAX-ACCESS       read-write
    STATUS           current
    DESCRIPTION      "This object specifies the index of the ATM traffic
                      descriptor in the ATM traffic data encapsulation used
                      in for the ingress direction over the AAL5 SSCS layer.
                      The definition references RFC 2684 Multiprotocol
                      Encapsulation over ATM AAL5 and to the ATM Forum LAN
                      Emulation specification."
    DEFVAL           { 1 }
    ::= { sapAtmInfoEntry 2 }

sapAtmEgressTrafficDescIndex OBJECT-TYPE
    SYNTAX           AtmTrafficDescrParamIndex(1..1000)
    MAX-ACCESS       read-write
    STATUS           current
    DESCRIPTION      "This object specifies the index of the ATM traffic
                      descriptor in the ATM traffic data encapsulation used
                      in for the egress direction over the AAL5 SSCS layer.
                      The definition references RFC 2684 Multiprotocol
                      Encapsulation over ATM AAL5 and to the ATM Forum LAN
                      Emulation specification."
    DEFVAL           { 1 }
    ::= { sapAtmInfoEntry 3 }

sapAtmOamAlarmCellHandling OBJECT-TYPE
    SYNTAX           ServiceAdminStatus
    MAX-ACCESS       read-write
    STATUS           current
    DESCRIPTION      "A value of up specifies that the OAM status of a pvc
                      affects  the  sap  operational  status and OAM AIS/RDI
                      cell generation upon a sap operational status of down.
                      A value of down specifies that the OAM status of a pvc
                      will   not   affect  the  operational  status  of  the
                      associated   sap   and   no   OAM  AIS/RDI  cells  are
                      generated."
    DEFVAL          { up }
    ::= { sapAtmInfoEntry 4 }

sapAtmOamTerminate OBJECT-TYPE
    SYNTAX           ServiceAdminStatus
    MAX-ACCESS       read-write
    STATUS           current
    DESCRIPTION      "The sapAtmOamTerminate object specifies whether this
                      SAP will act as an OAM termination point.
                      If enabled, OAM cells will be sunk by the SAP and can
                      affect the SAP's operational status (if
                      sapAtmOamAlarmCellHandling is also enabled). Otherwise
                      the OAM cells will be passed into the APIPE service.
                      This object is only configurable for ATM SAPs that are
                      part of an APIPE service SDU or VCC mode. If the
                      sapPortId belongs to an Multi-Chassis APS port, the
                      default value is up."
    DEFVAL           { down }
    ::= { sapAtmInfoEntry 5 }

sapAtmOamPeriodicLoopback OBJECT-TYPE
    SYNTAX           ServiceAdminStatus
    MAX-ACCESS       read-write
    STATUS           current
    DESCRIPTION      "The sapAtmOamPeriodicLoopback object specifies whether
                      this SAP will run periodic OAM loopbacks or not.  If
                      enabled, an ATM OAM loopback cell will be transmitted
                      every period as configured in tAtmSysOamLoopbackPeriod.
                      If a response is not received and tAtmSysOamRetryDown
                      consecutive retries also result in failure, the endpoint
                      will transition to the eteAisLoc state.  Once in the
                      eteAisLoc state, an ATM OAM loopback cell will be
                      transmitted every period as configured in
                      tAtmSysOamLoopbackPeriod. If a response is received for
                      the periodic loopback and tAtmSysOamRetryUp consecutive
                      retries also each receive a response, the endpoint will
                      transition back to the up state.  This object is only
                      configurable on IES or VPRN service endpoints."
    DEFVAL           { down }
    ::= { sapAtmInfoEntry 6 }


-- ---------------------------------
-- Base SAP Statistics Table
-- ---------------------------------
sapBaseStatsTable OBJECT-TYPE
    SYNTAX          SEQUENCE OF SapBaseStatsEntry
    MAX-ACCESS      not-accessible
    STATUS          current
    DESCRIPTION     "A table that contains basic SAP statistics.
                     In the descriptions below 'Pchip' refers
                     to the Alcatel 7x50 SR series Packet Processing
                     chip, while 'Qchip' refers to the Alcatel 7x50
                     SR series QoS Queueing Engine chip."
    ::= { tmnxSapObjs 6 }

sapBaseStatsEntry OBJECT-TYPE
    SYNTAX          SapBaseStatsEntry
    MAX-ACCESS      not-accessible
    STATUS          current
    DESCRIPTION     "Basic statistics about a specific SAP."
    INDEX           { svcId, sapPortId, sapEncapValue }
    ::= { sapBaseStatsTable 1 }

SapBaseStatsEntry ::=
    SEQUENCE {
        sapBaseStatsIngressPchipDroppedPackets          Counter64,
        sapBaseStatsIngressPchipDroppedOctets           Counter64,
        sapBaseStatsIngressPchipOfferedHiPrioPackets    Counter64,
        sapBaseStatsIngressPchipOfferedHiPrioOctets     Counter64,
        sapBaseStatsIngressPchipOfferedLoPrioPackets    Counter64,
        sapBaseStatsIngressPchipOfferedLoPrioOctets     Counter64,
        sapBaseStatsIngressQchipDroppedHiPrioPackets    Counter64,
        sapBaseStatsIngressQchipDroppedHiPrioOctets     Counter64,
        sapBaseStatsIngressQchipDroppedLoPrioPackets    Counter64,
        sapBaseStatsIngressQchipDroppedLoPrioOctets     Counter64,
        sapBaseStatsIngressQchipForwardedInProfPackets  Counter64,
        sapBaseStatsIngressQchipForwardedInProfOctets   Counter64,
        sapBaseStatsIngressQchipForwardedOutProfPackets Counter64,
        sapBaseStatsIngressQchipForwardedOutProfOctets  Counter64,
        sapBaseStatsEgressQchipDroppedInProfPackets     Counter64,
        sapBaseStatsEgressQchipDroppedInProfOctets      Counter64,
        sapBaseStatsEgressQchipDroppedOutProfPackets    Counter64,
        sapBaseStatsEgressQchipDroppedOutProfOctets     Counter64,
        sapBaseStatsEgressQchipForwardedInProfPackets   Counter64,
        sapBaseStatsEgressQchipForwardedInProfOctets    Counter64,
        sapBaseStatsEgressQchipForwardedOutProfPackets  Counter64,
        sapBaseStatsEgressQchipForwardedOutProfOctets   Counter64,
        sapBaseStatsCustId                              TmnxCustId,
        sapBaseStatsIngressPchipOfferedUncoloredPackets Counter64,
        sapBaseStatsIngressPchipOfferedUncoloredOctets  Counter64,
        sapBaseStatsAuthenticationPktsDiscarded         Counter32,
        sapBaseStatsAuthenticationPktsSuccess           Counter32,
        sapBaseStatsLastClearedTime                     TimeStamp
    }

sapBaseStatsIngressPchipDroppedPackets OBJECT-TYPE
    SYNTAX          Counter64
    MAX-ACCESS      read-only
    STATUS          current
    DESCRIPTION     "The number of packets dropped by the
                     ingress Pchip due to: SAP state,
                     ingress MAC, IP or IPv6 filter, same segment
                     discard, bad checksum, etc."
    ::= { sapBaseStatsEntry 1 }

sapBaseStatsIngressPchipDroppedOctets OBJECT-TYPE
    SYNTAX          Counter64
    MAX-ACCESS      read-only
    STATUS          current
    DESCRIPTION     "The number of octets dropped by the
                     ingress Pchip due to: SAP state,
                     ingress MAC, IP or IPv6 filter, same segment
                     discard, bad checksum, etc."
    ::= { sapBaseStatsEntry 2 }

sapBaseStatsIngressPchipOfferedHiPrioPackets OBJECT-TYPE
    SYNTAX          Counter64
    MAX-ACCESS      read-only
    STATUS          current
    DESCRIPTION     "The number of high priority packets,
                     as determined by the SAP ingress QoS
                     policy, offered by the Pchip to the
                     Qchip."
    ::= { sapBaseStatsEntry 3 }

sapBaseStatsIngressPchipOfferedHiPrioOctets OBJECT-TYPE
    SYNTAX          Counter64
    MAX-ACCESS      read-only
    STATUS          current
    DESCRIPTION     "The number of high priority octets,
                     as determined by the SAP ingress QoS
                     policy, offered by the Pchip to the
                     Qchip."
    ::= { sapBaseStatsEntry 4 }

sapBaseStatsIngressPchipOfferedLoPrioPackets OBJECT-TYPE
    SYNTAX          Counter64
    MAX-ACCESS      read-only
    STATUS          current
    DESCRIPTION     "The number of low priority packets,
                     as determined by the SAP ingress QoS
                     policy, offered by the Pchip to the
                     Qchip."
    ::= { sapBaseStatsEntry 5 }

sapBaseStatsIngressPchipOfferedLoPrioOctets OBJECT-TYPE
    SYNTAX          Counter64
    MAX-ACCESS      read-only
    STATUS          current
    DESCRIPTION     "The number of low priority octets,
                     as determined by the SAP ingress QoS
                     policy, offered by the Pchip to the
                     Qchip."
    ::= { sapBaseStatsEntry 6 }

sapBaseStatsIngressQchipDroppedHiPrioPackets OBJECT-TYPE
    SYNTAX          Counter64
    MAX-ACCESS      read-only
    STATUS          current
    DESCRIPTION     "The number of high priority packets,
                     as determined by the SAP ingress QoS
                     policy, dropped by the Qchip due to:
                     MBS exceeded, buffer pool limit
                     exceeded, etc."
    ::= { sapBaseStatsEntry 7 }

sapBaseStatsIngressQchipDroppedHiPrioOctets OBJECT-TYPE
    SYNTAX          Counter64
    MAX-ACCESS      read-only
    STATUS          current
    DESCRIPTION     "The number of high priority octets,
                     as determined by the SAP ingress QoS
                     policy, dropped by the Qchip due to:
                     MBS exceeded, buffer pool limit
                     exceeded, etc."
    ::= { sapBaseStatsEntry 8 }

sapBaseStatsIngressQchipDroppedLoPrioPackets OBJECT-TYPE
    SYNTAX          Counter64
    MAX-ACCESS      read-only
    STATUS          current
    DESCRIPTION     "The number of low priority packets,
                     as determined by the SAP ingress QoS
                     policy, dropped by the Qchip due to:
                     MBS exceeded, buffer pool limit
                     exceeded, etc."
    ::= { sapBaseStatsEntry 9 }

sapBaseStatsIngressQchipDroppedLoPrioOctets OBJECT-TYPE
    SYNTAX          Counter64
    MAX-ACCESS      read-only
    STATUS          current
    DESCRIPTION     "The number of low priority octets,
                     as determined by the SAP ingress QoS
                     policy, dropped by the Qchip due to:
                     MBS exceeded, buffer pool limit
                     exceeded, etc."
    ::= { sapBaseStatsEntry 10 }

sapBaseStatsIngressQchipForwardedInProfPackets OBJECT-TYPE
    SYNTAX          Counter64
    MAX-ACCESS      read-only
    STATUS          current
    DESCRIPTION     "The number of in-profile packets
                     (rate below CIR) forwarded by the
                     ingress Qchip."
    ::= { sapBaseStatsEntry 11 }

sapBaseStatsIngressQchipForwardedInProfOctets OBJECT-TYPE
    SYNTAX          Counter64
    MAX-ACCESS      read-only
    STATUS          current
    DESCRIPTION     "The number of in-profile octets
                     (rate below CIR) forwarded by the
                     ingress Qchip."
    ::= { sapBaseStatsEntry 12 }

sapBaseStatsIngressQchipForwardedOutProfPackets OBJECT-TYPE
    SYNTAX          Counter64
    MAX-ACCESS      read-only
    STATUS          current
    DESCRIPTION     "The number of out-of-profile packets
                     (rate above CIR) forwarded by the
                     ingress Qchip."
    ::= { sapBaseStatsEntry 13 }

sapBaseStatsIngressQchipForwardedOutProfOctets OBJECT-TYPE
    SYNTAX          Counter64
    MAX-ACCESS      read-only
    STATUS          current
    DESCRIPTION     "The number of out-of-profile octets
                     (rate above CIR) forwarded by the
                     ingress Qchip."
    ::= { sapBaseStatsEntry 14 }

sapBaseStatsEgressQchipDroppedInProfPackets OBJECT-TYPE
    SYNTAX          Counter64
    MAX-ACCESS      read-only
    STATUS          current
    DESCRIPTION     "The number of in-profile packets
                     discarded by the egress Qchip due
                     to: MBS exceeded, buffer pool limit
                     exceeded, etc."
    ::= { sapBaseStatsEntry 15 }

sapBaseStatsEgressQchipDroppedInProfOctets OBJECT-TYPE
    SYNTAX          Counter64
    MAX-ACCESS      read-only
    STATUS          current
    DESCRIPTION     "The number of in-profile octets
                     discarded by the egress Qchip due
                     to: MBS exceeded, buffer pool limit
                     exceeded, etc."
    ::= { sapBaseStatsEntry 16 }

sapBaseStatsEgressQchipDroppedOutProfPackets OBJECT-TYPE
    SYNTAX          Counter64
    MAX-ACCESS      read-only
    STATUS          current
    DESCRIPTION     "The number of out-of-profile packets
                     discarded by the egress Qchip due
                     to: MBS exceeded, buffer pool limit
                     exceeded, etc."
    ::= { sapBaseStatsEntry 17 }

sapBaseStatsEgressQchipDroppedOutProfOctets OBJECT-TYPE
    SYNTAX          Counter64
    MAX-ACCESS      read-only
    STATUS          current
    DESCRIPTION     "The number of out-of-profile packets
                     discarded by the egress Qchip due
                     to: MBS exceeded, buffer pool limit
                     exceeded, etc."
    ::= { sapBaseStatsEntry 18 }

sapBaseStatsEgressQchipForwardedInProfPackets OBJECT-TYPE
    SYNTAX          Counter64
    MAX-ACCESS      read-only
    STATUS          current
    DESCRIPTION     "The number of in-profile packets
                     (rate below CIR) forwarded by the
                     egress Qchip."
    ::= { sapBaseStatsEntry 19 }

sapBaseStatsEgressQchipForwardedInProfOctets OBJECT-TYPE
    SYNTAX          Counter64
    MAX-ACCESS      read-only
    STATUS          current
    DESCRIPTION     "The number of in-profile octets
                     (rate below CIR) forwarded by the
                     egress Qchip."
    ::= { sapBaseStatsEntry 20 }

sapBaseStatsEgressQchipForwardedOutProfPackets OBJECT-TYPE
    SYNTAX          Counter64
    MAX-ACCESS      read-only
    STATUS          current
    DESCRIPTION     "The number of out-of-profile packets
                     (rate above CIR) forwarded by the
                     egress Qchip."
    ::= { sapBaseStatsEntry 21 }

sapBaseStatsEgressQchipForwardedOutProfOctets OBJECT-TYPE
    SYNTAX          Counter64
    MAX-ACCESS      read-only
    STATUS          current
    DESCRIPTION     "The number of out-of-profile octets
                     (rate above CIR) forwarded by the
                     egress Qchip."
    ::= { sapBaseStatsEntry 22 }

sapBaseStatsCustId OBJECT-TYPE
    SYNTAX          TmnxCustId
    MAX-ACCESS      read-only
    STATUS          current
    DESCRIPTION     "The Customer ID for the associated service."
    ::= { sapBaseStatsEntry 23 }

sapBaseStatsIngressPchipOfferedUncoloredPackets OBJECT-TYPE
    SYNTAX          Counter64
    MAX-ACCESS      read-only
    STATUS          current
    DESCRIPTION     "The number of uncolored packets,
                     as determined by the SAP ingress QoS
                     policy, offered by the Pchip to the
                     Qchip."
    ::= { sapBaseStatsEntry 24 }

sapBaseStatsIngressPchipOfferedUncoloredOctets OBJECT-TYPE
    SYNTAX          Counter64
    MAX-ACCESS      read-only
    STATUS          current
    DESCRIPTION     "The number of uncolored octets,
                     as determined by the SAP ingress QoS
                     policy, offered by the Pchip to the
                     Qchip."
    ::= { sapBaseStatsEntry 25 }

sapBaseStatsAuthenticationPktsDiscarded OBJECT-TYPE
    SYNTAX          Counter32
    MAX-ACCESS      read-only
    STATUS          current
    DESCRIPTION     "The number of DHCP packets discarded
                     as result of authentication."
    ::= { sapBaseStatsEntry 26 }

sapBaseStatsAuthenticationPktsSuccess OBJECT-TYPE
    SYNTAX          Counter32
    MAX-ACCESS      read-only
    STATUS          current
    DESCRIPTION     "The number of DHCP packets successfully authenticated."
    ::= { sapBaseStatsEntry 27 }

sapBaseStatsLastClearedTime OBJECT-TYPE
    SYNTAX          TimeStamp
    MAX-ACCESS      read-only
    STATUS          current
    DESCRIPTION     "The value of sapBaseStatsLastClearedTime indicates
                     the sysUpTime when the counters in this table were
                     last cleared."
    ::= { sapBaseStatsEntry 28 }

-- ----------------------------------------
-- Ingress QoS Queue SAP Statistics Table
-- ----------------------------------------
sapIngQosQueueStatsTable OBJECT-TYPE
    SYNTAX          SEQUENCE OF SapIngQosQueueStatsEntry
    MAX-ACCESS      not-accessible
    STATUS          current
    DESCRIPTION     "A table that contains ingress QoS queue SAP
                     statistics."
    ::= { tmnxSapObjs 7 }

sapIngQosQueueStatsEntry OBJECT-TYPE
    SYNTAX          SapIngQosQueueStatsEntry
    MAX-ACCESS      not-accessible
    STATUS          current
    DESCRIPTION     "Ingress statistics about a specific SAP's
                     QoS queue."
    INDEX           { svcId, sapPortId, sapEncapValue, sapIngQosQueueId }
    ::= { sapIngQosQueueStatsTable 1 }

SapIngQosQueueStatsEntry ::=
    SEQUENCE {
        sapIngQosQueueId                           TSapIngQueueId,
        sapIngQosQueueStatsOfferedHiPrioPackets    Counter64,
        sapIngQosQueueStatsDroppedHiPrioPackets    Counter64,
        sapIngQosQueueStatsOfferedLoPrioPackets    Counter64,
        sapIngQosQueueStatsDroppedLoPrioPackets    Counter64,
        sapIngQosQueueStatsOfferedHiPrioOctets     Counter64,
        sapIngQosQueueStatsDroppedHiPrioOctets     Counter64,
        sapIngQosQueueStatsOfferedLoPrioOctets     Counter64,
        sapIngQosQueueStatsDroppedLoPrioOctets     Counter64,
        sapIngQosQueueStatsForwardedInProfPackets  Counter64,
        sapIngQosQueueStatsForwardedOutProfPackets Counter64,
        sapIngQosQueueStatsForwardedInProfOctets   Counter64,
        sapIngQosQueueStatsForwardedOutProfOctets  Counter64,
        sapIngQosCustId                            TmnxCustId,
        sapIngQosQueueStatsUncoloredPacketsOffered Counter64,
        sapIngQosQueueStatsUncoloredOctetsOffered  Counter64
    }

sapIngQosQueueId OBJECT-TYPE
    SYNTAX          TSapIngQueueId
    MAX-ACCESS      read-only
    STATUS          current
    DESCRIPTION     "The index of the ingress QoS queue of
                     this SAP."
    ::= { sapIngQosQueueStatsEntry 1 }

sapIngQosQueueStatsOfferedHiPrioPackets OBJECT-TYPE
    SYNTAX          Counter64
    MAX-ACCESS      read-only
    STATUS          current
    DESCRIPTION     "The number of high priority packets,
                     as determined by the SAP ingress QoS
                     policy, offered by the Pchip to the
                     Qchip."
    ::= { sapIngQosQueueStatsEntry 2 }

sapIngQosQueueStatsDroppedHiPrioPackets OBJECT-TYPE
    SYNTAX          Counter64
    MAX-ACCESS      read-only
    STATUS          current
    DESCRIPTION     "The number of high priority packets,
                     as determined by the SAP ingress QoS
                     policy, dropped by the Qchip due to:
                     MBS exceeded, buffer pool limit
                     exceeded, etc."
    ::= { sapIngQosQueueStatsEntry 3 }

sapIngQosQueueStatsOfferedLoPrioPackets OBJECT-TYPE
    SYNTAX          Counter64
    MAX-ACCESS      read-only
    STATUS          current
    DESCRIPTION     "The number of low priority packets,
                     as determined by the SAP ingress QoS
                     policy, offered by the Pchip to the
                     Qchip."
    ::= { sapIngQosQueueStatsEntry 4 }

sapIngQosQueueStatsDroppedLoPrioPackets OBJECT-TYPE
    SYNTAX          Counter64
    MAX-ACCESS      read-only
    STATUS          current
    DESCRIPTION     "The number of low priority packets,
                     as determined by the SAP ingress QoS
                     policy, dropped by the Qchip due to:
                     MBS exceeded, buffer pool limit
                     exceeded, etc."
    ::= { sapIngQosQueueStatsEntry 5 }

sapIngQosQueueStatsOfferedHiPrioOctets OBJECT-TYPE
    SYNTAX          Counter64
    MAX-ACCESS      read-only
    STATUS          current
    DESCRIPTION     "The number of high priority octets,
                     as determined by the SAP ingress QoS
                     policy, offered by the Pchip to the
                     Qchip."
    ::= { sapIngQosQueueStatsEntry 6 }

sapIngQosQueueStatsDroppedHiPrioOctets OBJECT-TYPE
    SYNTAX          Counter64
    MAX-ACCESS      read-only
    STATUS          current
    DESCRIPTION     "The number of high priority octets,
                     as determined by the SAP ingress QoS
                     policy, dropped by the Qchip due to:
                     MBS exceeded, buffer pool limit
                     exceeded, etc."
    ::= { sapIngQosQueueStatsEntry 7 }

sapIngQosQueueStatsOfferedLoPrioOctets OBJECT-TYPE
    SYNTAX          Counter64
    MAX-ACCESS      read-only
    STATUS          current
    DESCRIPTION     "The number of low priority octets,
                     as determined by the SAP ingress QoS
                     policy, offered by the Pchip to the
                     Qchip."
    ::= { sapIngQosQueueStatsEntry 8 }

sapIngQosQueueStatsDroppedLoPrioOctets OBJECT-TYPE
    SYNTAX          Counter64
    MAX-ACCESS      read-only
    STATUS          current
    DESCRIPTION     "The number of low priority octets,
                     as determined by the SAP ingress QoS
                     policy, dropped by the Qchip due to:
                     MBS exceeded, buffer pool limit
                     exceeded, etc."
    ::= { sapIngQosQueueStatsEntry 9 }

sapIngQosQueueStatsForwardedInProfPackets OBJECT-TYPE
    SYNTAX          Counter64
    MAX-ACCESS      read-only
    STATUS          current
    DESCRIPTION     "The number of in-profile packets
                     (rate below CIR) forwarded by the
                     ingress Qchip."
    ::= { sapIngQosQueueStatsEntry 10 }

sapIngQosQueueStatsForwardedOutProfPackets OBJECT-TYPE
    SYNTAX          Counter64
    MAX-ACCESS      read-only
    STATUS          current
    DESCRIPTION     "The number of out-of-profile packets
                     (rate above CIR) forwarded by the
                     ingress Qchip."
    ::= { sapIngQosQueueStatsEntry 11 }

sapIngQosQueueStatsForwardedInProfOctets OBJECT-TYPE
    SYNTAX          Counter64
    MAX-ACCESS      read-only
    STATUS          current
    DESCRIPTION     "The number of in-profile octets
                     (rate below CIR) forwarded by the
                     ingress Qchip."
    ::= { sapIngQosQueueStatsEntry 12 }

sapIngQosQueueStatsForwardedOutProfOctets OBJECT-TYPE
    SYNTAX          Counter64
    MAX-ACCESS      read-only
    STATUS          current
    DESCRIPTION     "The number of out-of-profile octets
                     (rate above CIR) forwarded by the
                     ingress Qchip."
    ::= { sapIngQosQueueStatsEntry 13 }

sapIngQosCustId OBJECT-TYPE
    SYNTAX          TmnxCustId
    MAX-ACCESS      read-only
    STATUS          current
    DESCRIPTION     "The Customer ID for the associated service."
    ::= { sapIngQosQueueStatsEntry 14 }

sapIngQosQueueStatsUncoloredPacketsOffered OBJECT-TYPE
    SYNTAX          Counter64
    MAX-ACCESS      read-only
    STATUS          current
    DESCRIPTION     "The number of uncolored packets offered to
                     the ingress Qchip."
    ::= { sapIngQosQueueStatsEntry 15 }

sapIngQosQueueStatsUncoloredOctetsOffered OBJECT-TYPE
    SYNTAX          Counter64
    MAX-ACCESS      read-only
    STATUS          current
    DESCRIPTION     "The number of uncolored octets offered to
                     the ingress Qchip."
    ::= { sapIngQosQueueStatsEntry 16 }

-- ----------------------------------------
-- Egress QoS Queue SAP Statistics Table
-- ----------------------------------------
sapEgrQosQueueStatsTable OBJECT-TYPE
    SYNTAX          SEQUENCE OF SapEgrQosQueueStatsEntry
    MAX-ACCESS      not-accessible
    STATUS          current
    DESCRIPTION     "A table that contains egress QoS queue SAP
                     statistics."
    ::= { tmnxSapObjs 8 }

sapEgrQosQueueStatsEntry OBJECT-TYPE
    SYNTAX          SapEgrQosQueueStatsEntry
    MAX-ACCESS      not-accessible
    STATUS          current
    DESCRIPTION     "Egress statistics about a specific SAP's
                     QoS queue."
    INDEX           { svcId, sapPortId, sapEncapValue, sapEgrQosQueueId }
    ::= { sapEgrQosQueueStatsTable 1 }

SapEgrQosQueueStatsEntry ::=
    SEQUENCE {
        sapEgrQosQueueId                           TSapEgrQueueId,
        sapEgrQosQueueStatsForwardedInProfPackets  Counter64,
        sapEgrQosQueueStatsDroppedInProfPackets    Counter64,
        sapEgrQosQueueStatsForwardedOutProfPackets Counter64,
        sapEgrQosQueueStatsDroppedOutProfPackets   Counter64,
        sapEgrQosQueueStatsForwardedInProfOctets   Counter64,
        sapEgrQosQueueStatsDroppedInProfOctets     Counter64,
        sapEgrQosQueueStatsForwardedOutProfOctets  Counter64,
        sapEgrQosQueueStatsDroppedOutProfOctets    Counter64,
        sapEgrQosCustId                            TmnxCustId
    }

sapEgrQosQueueId OBJECT-TYPE
    SYNTAX          TSapEgrQueueId
    MAX-ACCESS      read-only
    STATUS          current
    DESCRIPTION     "The index of the egress QoS queue of
                     this SAP."
    ::= { sapEgrQosQueueStatsEntry 1 }

sapEgrQosQueueStatsForwardedInProfPackets OBJECT-TYPE
    SYNTAX          Counter64
    MAX-ACCESS      read-only
    STATUS          current
    DESCRIPTION     "The number of in-profile packets
                     (rate below CIR) forwarded by the
                     egress Qchip."
    ::= { sapEgrQosQueueStatsEntry 2 }

sapEgrQosQueueStatsDroppedInProfPackets OBJECT-TYPE
    SYNTAX          Counter64
    MAX-ACCESS      read-only
    STATUS          current
    DESCRIPTION     "The number of in-profile packets
                     discarded by the egress Qchip due
                     to: MBS exceeded, buffer pool limit
                     exceeded, etc."
    ::= { sapEgrQosQueueStatsEntry 3 }

sapEgrQosQueueStatsForwardedOutProfPackets OBJECT-TYPE
    SYNTAX          Counter64
    MAX-ACCESS      read-only
    STATUS          current
    DESCRIPTION     "The number of out-of-profile packets
                     (rate above CIR) forwarded by the
                     egress Qchip."
    ::= { sapEgrQosQueueStatsEntry 4 }

sapEgrQosQueueStatsDroppedOutProfPackets OBJECT-TYPE
    SYNTAX          Counter64
    MAX-ACCESS      read-only
    STATUS          current
    DESCRIPTION     "The number of out-of-profile packets
                     discarded by the egress Qchip due
                     to: MBS exceeded, buffer pool limit
                     exceeded, etc."
    ::= { sapEgrQosQueueStatsEntry 5 }

sapEgrQosQueueStatsForwardedInProfOctets OBJECT-TYPE
    SYNTAX          Counter64
    MAX-ACCESS      read-only
    STATUS          current
    DESCRIPTION     "The number of in-profile octets
                     (rate below CIR) forwarded by the
                     egress Qchip."
    ::= { sapEgrQosQueueStatsEntry 6 }

sapEgrQosQueueStatsDroppedInProfOctets OBJECT-TYPE
    SYNTAX          Counter64
    MAX-ACCESS      read-only
    STATUS          current
    DESCRIPTION     "The number of in-profile octets
                     discarded by the egress Qchip due
                     to: MBS exceeded, buffer pool limit
                     exceeded, etc."
    ::= { sapEgrQosQueueStatsEntry 7 }

sapEgrQosQueueStatsForwardedOutProfOctets OBJECT-TYPE
    SYNTAX          Counter64
    MAX-ACCESS      read-only
    STATUS          current
    DESCRIPTION     "The number of out-of-profile octets
                     (rate above CIR) forwarded by the
                     egress Qchip."
    ::= { sapEgrQosQueueStatsEntry 8 }

sapEgrQosQueueStatsDroppedOutProfOctets OBJECT-TYPE
    SYNTAX          Counter64
    MAX-ACCESS      read-only
    STATUS          current
    DESCRIPTION     "The number of out-of-profile octets
                     discarded by the egress Qchip due
                     to: MBS exceeded, buffer pool limit
                     exceeded, etc."
    ::= { sapEgrQosQueueStatsEntry 9 }

sapEgrQosCustId OBJECT-TYPE
    SYNTAX          TmnxCustId
    MAX-ACCESS      read-only
    STATUS          current
    DESCRIPTION     "The Customer ID for the associated service."
    ::= { sapEgrQosQueueStatsEntry 10 }

-- -------------------------------------------------
-- Ingress QoS Scheduler SAP Statistics Table
-- -------------------------------------------------
sapIngQosSchedStatsTable OBJECT-TYPE
    SYNTAX          SEQUENCE OF SapIngQosSchedStatsEntry
    MAX-ACCESS      not-accessible
    STATUS          current
    DESCRIPTION     "A table that contains ingress QoS queue SAP
                     statistics."
    ::= { tmnxSapObjs 9 }

sapIngQosSchedStatsEntry OBJECT-TYPE
    SYNTAX          SapIngQosSchedStatsEntry
    MAX-ACCESS      not-accessible
    STATUS          current
    DESCRIPTION     "Ingress statistics about a specific SAP's
                     QoS queue."
    INDEX           { svcId, sapPortId, sapEncapValue,
                      IMPLIED sapIngQosSchedName }
    ::= { sapIngQosSchedStatsTable 1 }

SapIngQosSchedStatsEntry ::=
    SEQUENCE {
        sapIngQosSchedName                     TNamedItem,
        sapIngQosSchedStatsForwardedPackets    Counter64,
        sapIngQosSchedStatsForwardedOctets     Counter64,
        sapIngQosSchedCustId                   TmnxCustId
    }

sapIngQosSchedName OBJECT-TYPE
    SYNTAX          TNamedItem
    MAX-ACCESS      not-accessible
    STATUS          current
    DESCRIPTION     "The index of the ingress QoS scheduler of
                     this SAP."
    ::= { sapIngQosSchedStatsEntry 1 }

sapIngQosSchedStatsForwardedPackets OBJECT-TYPE
    SYNTAX          Counter64
    MAX-ACCESS      read-only
    STATUS          current
    DESCRIPTION     "The number of forwarded packets, as
                     determined by the SAP ingress scheduler
                     policy, offered by the Pchip to the
                     Qchip."
    ::= { sapIngQosSchedStatsEntry 2 }

sapIngQosSchedStatsForwardedOctets OBJECT-TYPE
    SYNTAX          Counter64
    MAX-ACCESS      read-only
    STATUS          current
    DESCRIPTION     "The number of forwarded octets, as
                     determined by the SAP ingress scheduler
                     policy, offered by the Pchip to the
                     Qchip."
    ::= { sapIngQosSchedStatsEntry 3 }

sapIngQosSchedCustId OBJECT-TYPE
    SYNTAX          TmnxCustId
    MAX-ACCESS      read-only
    STATUS          current
    DESCRIPTION     "The Customer ID for the associated service."
    ::= { sapIngQosSchedStatsEntry 4 }

-- ---------------------------------------------
-- Egress QoS Scheduler SAP Statistics Table
-- ---------------------------------------------
sapEgrQosSchedStatsTable OBJECT-TYPE
    SYNTAX          SEQUENCE OF SapEgrQosSchedStatsEntry
    MAX-ACCESS      not-accessible
    STATUS          current
    DESCRIPTION     "A table that contains ingress QoS queue SAP
                     statistics."
    ::= { tmnxSapObjs 10 }

sapEgrQosSchedStatsEntry OBJECT-TYPE
    SYNTAX          SapEgrQosSchedStatsEntry
    MAX-ACCESS      not-accessible
    STATUS          current
    DESCRIPTION     "Egress statistics about a specific SAP's
                     QoS queue."
    INDEX           { svcId, sapPortId, sapEncapValue,
                      IMPLIED sapEgrQosSchedName }
    ::= { sapEgrQosSchedStatsTable 1 }

SapEgrQosSchedStatsEntry ::=
    SEQUENCE {
        sapEgrQosSchedName                     TNamedItem,
        sapEgrQosSchedStatsForwardedPackets    Counter64,
        sapEgrQosSchedStatsForwardedOctets     Counter64,
        sapEgrQosSchedCustId                   TmnxCustId
    }

sapEgrQosSchedName OBJECT-TYPE
    SYNTAX          TNamedItem
    MAX-ACCESS      not-accessible
    STATUS          current
    DESCRIPTION     "The index of the egress QoS scheduler of
                     this SAP."
    ::= { sapEgrQosSchedStatsEntry 1 }

sapEgrQosSchedStatsForwardedPackets OBJECT-TYPE
    SYNTAX          Counter64
    MAX-ACCESS      read-only
    STATUS          current
    DESCRIPTION     "The number of forwarded packets by the
                     egress Qchip, as determined by the SAP
                     egress scheduler policy."
    ::= { sapEgrQosSchedStatsEntry 2 }

sapEgrQosSchedStatsForwardedOctets OBJECT-TYPE
    SYNTAX          Counter64
    MAX-ACCESS      read-only
    STATUS          current
    DESCRIPTION     "The number of forwarded octets by the
                     egress Qchip, as determined by the SAP
                     egress scheduler policy."
    ::= { sapEgrQosSchedStatsEntry 3 }

sapEgrQosSchedCustId OBJECT-TYPE
    SYNTAX          TmnxCustId
    MAX-ACCESS      read-only
    STATUS          current
    DESCRIPTION     "The Customer ID for the associated service."
    ::= { sapEgrQosSchedStatsEntry 4 }

-- -----------------------------------------
-- TLS SAP Managed VLAN List Table
-- -----------------------------------------
sapTlsManagedVlanListTable OBJECT-TYPE
    SYNTAX          SEQUENCE OF SapTlsManagedVlanListEntry
    MAX-ACCESS      not-accessible
    STATUS          current
    DESCRIPTION     "This table is used only for SAPs that are part
                     of a management VPLS. It indicates for each SAP the
                     ranges of associated VLANs that will be affected when
                     the SAP changes state."
    ::= { tmnxSapObjs 11 }

sapTlsManagedVlanListEntry OBJECT-TYPE
    SYNTAX          SapTlsManagedVlanListEntry
    MAX-ACCESS      not-accessible
    STATUS          current
    DESCRIPTION     "Each row specifies a range of VLANS associated
                     with a SAP of a MVPLS. Ranges may contains overlapping
                     sections only for Mvpls SAPs that belong to the same
                     service."
    INDEX           { svcId,
                      sapPortId,
                      sapEncapValue,
                      sapTlsMvplsMinVlanTag,
                      sapTlsMvplsMaxVlanTag }
    ::= { sapTlsManagedVlanListTable 1 }

SapTlsManagedVlanListEntry ::=
    SEQUENCE {
        sapTlsMvplsMinVlanTag     Unsigned32,
        sapTlsMvplsMaxVlanTag     Unsigned32,
        sapTlsMvplsRowStatus      RowStatus
    }

sapTlsMvplsMinVlanTag OBJECT-TYPE
    SYNTAX          Unsigned32(0 .. 4095)
    MAX-ACCESS      not-accessible
    STATUS          current
    DESCRIPTION     "The value of sapTlsMvplsMinVlanTag specifies
                     the left bound (i.e. min. value) of a range of VLANs
                     that are associated with the Mvpls SAP.
                     sapTlsMvplsMinVlanTag must be smaller than (or equal
                     to) sapTlsMvplsMaxVlanTag.
                     Special values are:
                     0: this value is reserved for the null tag.
                     4095: this value denotes the default SAP."
    ::= { sapTlsManagedVlanListEntry 1 }

sapTlsMvplsMaxVlanTag OBJECT-TYPE
    SYNTAX          Unsigned32(0 .. 4095)
    MAX-ACCESS      not-accessible
    STATUS          current
    DESCRIPTION     "The value of sapTlsMvplsMaxVlanTag specifies the
                     right bound (i.e. max. value) of a range of VLANs that
                     are associated with the Mvpls SAP.
                     Special values are:
                     0: this value is reserved for the null tag.
                     4095: this value denotes the default SAP."
    ::= { sapTlsManagedVlanListEntry 2 }

sapTlsMvplsRowStatus OBJECT-TYPE
    SYNTAX           RowStatus
    MAX-ACCESS       read-create
    STATUS           current
    DESCRIPTION      "The value of sapTlsMvplsRowStatus specifies
                      the status of this row. The only values supported
                      during a set operation are 'createAndGo' and
                      'destroy'. A row (i.e. a range of VLAN tags) can be
                      destroyed only if there are no SAPs defined in
                      regular VPLSses in this range."
    ::= { sapTlsManagedVlanListEntry 3 }

-- ----------------------------------------------------
-- SAP Anti-spoof Table
-- ----------------------------------------------------
sapAntiSpoofTable OBJECT-TYPE
    SYNTAX          SEQUENCE OF SapAntiSpoofEntry
    MAX-ACCESS      not-accessible
    STATUS          current
    DESCRIPTION     "The sapAntiSpoofTable contains information about
                     anti-spoofing filters on a SAP."
    ::= { tmnxSapObjs 12 }

sapAntiSpoofEntry OBJECT-TYPE
    SYNTAX          SapAntiSpoofEntry
    MAX-ACCESS      not-accessible
    STATUS          current
    DESCRIPTION     "An entry in the sapAntiSpoofTable."
    INDEX           { sapPortId,
                      sapEncapValue,
                      sapAntiSpoofIpAddress,
                      sapAntiSpoofMacAddress }
    ::= { sapAntiSpoofTable 1 }

SapAntiSpoofEntry ::=
    SEQUENCE {
        sapAntiSpoofIpAddress  IpAddress,
        sapAntiSpoofMacAddress MacAddress
    }

sapAntiSpoofIpAddress OBJECT-TYPE
    SYNTAX          IpAddress
    MAX-ACCESS      read-only
    STATUS          current
    DESCRIPTION     "The value of sapAntiSpoofIpAddress indicates the IP
                     address for which this table entry contains information."
    ::= { sapAntiSpoofEntry 1 }

sapAntiSpoofMacAddress OBJECT-TYPE
    SYNTAX          MacAddress
    MAX-ACCESS      read-only
    STATUS          current
    DESCRIPTION     "The value of sapAntiSpoofMacAddress indicates the MAC
                     address for which this table entry contains information."
    ::= { sapAntiSpoofEntry 2 }

-- -----------------------------------------
-- SAP Static Host Table
-- -----------------------------------------
sapStaticHostTable OBJECT-TYPE
    SYNTAX          SEQUENCE OF SapStaticHostEntry
    MAX-ACCESS      not-accessible
    STATUS          current
    DESCRIPTION     "The sapStaticHostTable is used to configure static hosts
                     on a SAP."
    ::= { tmnxSapObjs 13 }

sapStaticHostEntry OBJECT-TYPE
    SYNTAX          SapStaticHostEntry
    MAX-ACCESS      not-accessible
    STATUS          current
    DESCRIPTION     "Each row entry represents information on a statically
                     configured host. Entries can be created and deleted via
                     SNMP SET operations."
    INDEX           { svcId,
                      sapPortId,
                      sapEncapValue,
                      sapStaticHostIpAddress,
                      sapStaticHostMacAddress }
    ::= { sapStaticHostTable 1 }

SapStaticHostEntry ::=
    SEQUENCE {
        sapStaticHostRowStatus          RowStatus,
        sapStaticHostIpAddress          IpAddress,
        sapStaticHostMacAddress         MacAddress,
        sapStaticHostSubscrIdent        DisplayString,
        sapStaticHostSubProfile         ServObjName,
        sapStaticHostSlaProfile         ServObjName,
        sapStaticHostShcvOperState      INTEGER,
        sapStaticHostShcvChecks         Unsigned32,
        sapStaticHostShcvReplies        Unsigned32,
        sapStaticHostShcvReplyTime      TimeStamp,
        sapStaticHostDynMacAddress      MacAddress,
        sapStaticHostRetailerSvcId      TmnxServId,
        sapStaticHostRetailerIf         InterfaceIndexOrZero,
        sapStaticHostFwdingState        TmnxOperState,
        sapStaticHostAncpString         DisplayString,
        sapStaticHostSubIdIsSapId       TruthValue,
        sapStaticHostAppProfile         ServObjName,
        sapStaticHostIntermediateDestId DisplayString
    }

sapStaticHostRowStatus OBJECT-TYPE
    SYNTAX          RowStatus
    MAX-ACCESS      read-create
    STATUS          current
    DESCRIPTION     "The value of the object sapStaticHostRowStatus controls
                     the creation and deletion of rows in this table."
    ::= { sapStaticHostEntry 1 }

sapStaticHostIpAddress OBJECT-TYPE
    SYNTAX          IpAddress
    MAX-ACCESS      not-accessible
    STATUS          current
    DESCRIPTION     "The value of the object sapStaticHostIpAddress specifies
                     the IP address associated with this static host. The value
                     0.0.0.0 indicates that no host IP address is specified."
    ::= { sapStaticHostEntry 2 }

sapStaticHostMacAddress OBJECT-TYPE
    SYNTAX          MacAddress
    MAX-ACCESS      not-accessible
    STATUS          current
    DESCRIPTION     "The value of the object sapStaticHostMacAddress specifies
                     the MAC address associated with this static host. The
                     value 0:0:0:0:0:0 indicates that no host MAC address is
                     specified."
    ::= { sapStaticHostEntry 3 }

sapStaticHostSubscrIdent OBJECT-TYPE
    SYNTAX          DisplayString (SIZE (0..32))
    MAX-ACCESS      read-create
    STATUS          current
    DESCRIPTION     "The value of the object sapStaticHostSubscrIdent specifies
                     the subscriber identification for this static host."
    DEFVAL          { "" }
    ::= { sapStaticHostEntry 4 }

sapStaticHostSubProfile OBJECT-TYPE
    SYNTAX          ServObjName
    MAX-ACCESS      read-create
    STATUS          current
    DESCRIPTION     "The value of the object sapStaticHostSubProfile specifies
                     the subscriber profile for this static host. The specified
                     subscriber profile needs to exists in the
                     TIMETRA-SUBSCRIBER-MGMT-MIB::tmnxSubProfileTable."
    DEFVAL          { "" }
    ::= { sapStaticHostEntry 5 }

sapStaticHostSlaProfile OBJECT-TYPE
    SYNTAX          ServObjName
    MAX-ACCESS      read-create
    STATUS          current
    DESCRIPTION     "The value of the object sapStaticHostSlaProfile specifies
                     the SLA profile for this static host. The specified
                     SLA profile needs to exists in the
                     TIMETRA-SUBSCRIBER-MGMT-MIB::tmnxSLAProfileTable."
    DEFVAL          { "" }
    ::= { sapStaticHostEntry 6 }

sapStaticHostShcvOperState OBJECT-TYPE
    SYNTAX          INTEGER {
                        disabled  (1),
                        undefined (2),
                        down      (3),
                        up        (4)
                    }
    MAX-ACCESS      read-only
    STATUS          current
    DESCRIPTION     "The value of the object sapStaticHostShcvOperState
                     gives the state of the subscriber host connectivity
                     check for this static host."
    ::= { sapStaticHostEntry 7 }

sapStaticHostShcvChecks OBJECT-TYPE
    SYNTAX          Unsigned32
    MAX-ACCESS      read-only
    STATUS          current
    DESCRIPTION     "The value of the object sapStaticHostShcvChecks specifies
                     the number of connectivity checks for this static host."
    ::= { sapStaticHostEntry 8 }

sapStaticHostShcvReplies OBJECT-TYPE
    SYNTAX          Unsigned32
    MAX-ACCESS      read-only
    STATUS          current
    DESCRIPTION     "The value of the object sapStaticHostShcvReplies specifies
                     the number of host replies for this static host."
    ::= { sapStaticHostEntry 9 }

sapStaticHostShcvReplyTime OBJECT-TYPE
    SYNTAX          TimeStamp
    MAX-ACCESS      read-only
    STATUS          current
    DESCRIPTION     "The value of the object sapStaticHostShcvReplyTime
                     gives the timestamp of the last successful connectivity
                     check for this static host."
    ::= { sapStaticHostEntry 10 }

sapStaticHostDynMacAddress OBJECT-TYPE
    SYNTAX          MacAddress
    MAX-ACCESS      read-only
    STATUS          current
    DESCRIPTION     "The value of the object sapStaticHostDynMacAddress gives
                     the MAC address learned via ARP in case this is an IP-only
                     static host (sapStaticHostMacAddress is set to
                     0:0:0:0:0:0).
                     The value 0:0:0:0:0:0 indicates that no MAC address is
                     learned yet."
    ::= { sapStaticHostEntry 11 }

sapStaticHostRetailerSvcId OBJECT-TYPE
    SYNTAX          TmnxServId
    MAX-ACCESS      read-only
    STATUS          current
    DESCRIPTION     "The value of the object sapStaticHostRetailerSvcId
                     indicates the service ID of the retailer VPRN service
                     to which this static host belongs. When this object is
                     non zero, the static host belongs to a retailer VPRN."
    ::= { sapStaticHostEntry 12 }

sapStaticHostRetailerIf OBJECT-TYPE
    SYNTAX          InterfaceIndexOrZero
    MAX-ACCESS      read-only
    STATUS          current
    DESCRIPTION     "The value of the object sapStaticHostRetailerIf indicates
                     the interface index of the retailer VPRN interface to which
                     this static host belongs. When this object is non zero,
                     the static host belongs to a retailer VPRN."
    ::= { sapStaticHostEntry 13 }

sapStaticHostFwdingState OBJECT-TYPE
    SYNTAX          TmnxOperState
    MAX-ACCESS      read-only
    STATUS          current
    DESCRIPTION     "The value of sapStaticHostFwdingState indicates the
                     forwarding state of this static host. When the value
                     is 'outOfService', host traffic is not forwarded.
                     When it is 'inService', host traffic is forwarded."
    ::= { sapStaticHostEntry 14 }

sapStaticHostAncpString OBJECT-TYPE
    SYNTAX          DisplayString (SIZE (0..63))
    MAX-ACCESS      read-create
    STATUS          current
    DESCRIPTION     "The value of sapStaticHostAncpString specifies
                     the ancp-string associated to this SAP host."
    DEFVAL          { "" }
    ::= { sapStaticHostEntry 15 }

sapStaticHostSubIdIsSapId OBJECT-TYPE
    SYNTAX          TruthValue
    MAX-ACCESS      read-create
    STATUS          current
    DESCRIPTION     "The value of the object sapStaticHostSubIdIsSapId
                     specifies whether the SAP-id is taken as subscriber
                     identification for this static host."
    DEFVAL          { false }
    ::= { sapStaticHostEntry 16 }

sapStaticHostAppProfile OBJECT-TYPE
    SYNTAX          ServObjName
    MAX-ACCESS      read-create
    STATUS          current
    DESCRIPTION     "The value of sapStaticHostAppProfile specifies
                     the application profile for this static host. The
                     specified application profile needs to exist in the
                     TIMETRA-BSX-MIB::tmnxBsxAppProfTable."
    DEFVAL          { "" }
    ::= { sapStaticHostEntry 17 }

sapStaticHostIntermediateDestId OBJECT-TYPE
    SYNTAX          DisplayString (SIZE (0..32))
    MAX-ACCESS      read-create
    STATUS          current
    DESCRIPTION     "The value of sapStaticHostIntermediateDestId specifies
                     to which intermediate destination (for example a DSLAM)
                     this host belongs."
    DEFVAL          { "" }
    ::= { sapStaticHostEntry 18 }

-- ----------------------------------------
-- SAP Tls DHCP Information Table
-- ----------------------------------------
sapTlsDhcpInfoTable OBJECT-TYPE
    SYNTAX          SEQUENCE OF SapTlsDhcpInfoEntry
    MAX-ACCESS      not-accessible
    STATUS          current
    DESCRIPTION     "sapTlsDhcpInfoTable  contains  DHCP information related
                     to a TLS  SAP.  This table complements sapTlsInfoTable,
                     and contains an entry for each Tls SAP. Rows in this
                     table are created and deleted automatically by the system."
    ::= { tmnxSapObjs 14 }

sapTlsDhcpInfoEntry OBJECT-TYPE
    SYNTAX          SapTlsDhcpInfoEntry
    MAX-ACCESS      not-accessible
    STATUS          current
    DESCRIPTION     " DHCP specific information for a TLS SAP."
    INDEX           { svcId, sapPortId, sapEncapValue }
    ::= { sapTlsDhcpInfoTable 1 }

SapTlsDhcpInfoEntry ::=
    SEQUENCE {
        sapTlsDhcpAdminState            TmnxEnabledDisabled,
        sapTlsDhcpDescription           ServObjDesc,
        sapTlsDhcpSnoop                 TmnxEnabledDisabled,
        sapTlsDhcpLeasePopulate         Unsigned32,
        sapTlsDhcpOperLeasePopulate     Unsigned32,
        sapTlsDhcpInfoAction            INTEGER,
        sapTlsDhcpCircuitId             INTEGER,
        sapTlsDhcpRemoteId              INTEGER,
        sapTlsDhcpRemoteIdString        DisplayString,
        sapTlsDhcpProxyAdminState       TmnxEnabledDisabled,
        sapTlsDhcpProxyServerAddr       IpAddress,
        sapTlsDhcpProxyLeaseTime        Unsigned32,
        sapTlsDhcpProxyLTRadiusOverride TruthValue,
        sapTlsDhcpVendorIncludeOptions  BITS,
        sapTlsDhcpVendorOptionString    DisplayString
        }

sapTlsDhcpAdminState OBJECT-TYPE
    SYNTAX          TmnxEnabledDisabled
    MAX-ACCESS      read-write
    STATUS          current
    DESCRIPTION     "The value of the object sapTlsDhcpAdminState specifies
                     the overall enable/disable state of all DHCP related
                     actions  on  this  Sap. The value 'disabled' allows
                     the user to configure  individual DHCP commands but
                     administratively disable them."
    DEFVAL          { disabled }
    ::= { sapTlsDhcpInfoEntry 1 }

sapTlsDhcpDescription OBJECT-TYPE
    SYNTAX          ServObjDesc
    MAX-ACCESS      read-write
    STATUS          current
    DESCRIPTION     "The value of the object sapTlsDhcpDescription specifies
                     a user provided description for DHCP on this Sap.
                     It consists of any printable, seven-bit ASCII characters
                     up to 80 characters in length."
    DEFVAL          { ''H }
    ::= { sapTlsDhcpInfoEntry 2 }

sapTlsDhcpSnoop OBJECT-TYPE
    SYNTAX          TmnxEnabledDisabled
    MAX-ACCESS      read-write
    STATUS          current
    DESCRIPTION     "The value of the object sapTlsDhcpSnoop specifies
                     the enable/disable state for DHCP snooping on this Sap.
                     Note that in order for snooping to be enabled
                     the object sapTlsDhcpAdminState must also have the
                     value enabled."
    DEFVAL          { disabled }
    ::= { sapTlsDhcpInfoEntry 3 }

sapTlsDhcpLeasePopulate OBJECT-TYPE
    SYNTAX          Unsigned32 (0..8000)
    MAX-ACCESS      read-write
    STATUS          current
    DESCRIPTION     "The value of the object sapTlsDhcpLeasePopulate specifies
                     the maximum number of DHCP lease states allowed on this
                     SAP."
    DEFVAL { 0 }
    ::= { sapTlsDhcpInfoEntry 4 }

sapTlsDhcpOperLeasePopulate OBJECT-TYPE
    SYNTAX          Unsigned32 (0..8000)
    MAX-ACCESS      read-only
    STATUS          current
    DESCRIPTION     "The value of the object sapTlsDhcpOperLeasePopulate
                     indicates the number of DHCP lease states currently
                     allocated on this SAP."
    ::= { sapTlsDhcpInfoEntry 5 }

sapTlsDhcpInfoAction OBJECT-TYPE
    SYNTAX          INTEGER {
                        replace (1),
                        drop    (2),
                        keep    (3)
                    }
    MAX-ACCESS      read-write
    STATUS          current
    DESCRIPTION     "The value of the object sapTlsDhcpInfoAction specifies
                     the DHCP option reforwarding policy:
                     'replace' - replace existing information with
                                 configured information
                     'drop'    - discard messages with existing relay
                                 information if the option-82 information
                                 is also present.
                     'keep'    - retain the existing relay information."
    DEFVAL { keep }
    ::= { sapTlsDhcpInfoEntry 6 }

sapTlsDhcpCircuitId OBJECT-TYPE
    SYNTAX          INTEGER {
                        none           (0),
                        asciiTuple     (1),
                        vlanAsciiTuple (2)
                    }
    MAX-ACCESS      read-write
    STATUS          current
    DESCRIPTION     "The value of the object sapTlsDhcpCircuitId specifies
                     whether or not the circuit-id suboption is present, and if
                     it is present what information goes in it:
                     - 'none'          the circuit-id suboption will not be part
                                       of the information option (Option 82).
                     - 'asciiTuple'    the ASCII-encoded  concatenated tuple
                                       consisting of the
                                          - access-node-identifier
                                          - service-id
                                          - interface-name
                                       is used.
                    - 'vlanAsciiTuple' the format will include VLAN-id and dot1p
                                       bits in addition to what is included in
                                       ascii-tuple already.  The format is
                                       supported on dot1q and qinq encapsulated
                                       ports only.  Thus, when the option 82
                                       bits are stripped, dot1p bits will be
                                       copied to the Ethernet header of an
                                       outgoing packet."
    DEFVAL { asciiTuple }
    ::= { sapTlsDhcpInfoEntry 7 }

sapTlsDhcpRemoteId OBJECT-TYPE
    SYNTAX          INTEGER {
                        none      (1),
                        mac       (2),
                        remote-id (3)
                    }
    MAX-ACCESS      read-write
    STATUS          current
    DESCRIPTION     "The value of the object sapTlsDhcpRemoteId specifies
                     what information goes into the remote-id suboption in
                     the DHCP Relay packet.
                     If the value of this object is set to 'none',
                     the remote-id suboption will not be part of the
                     information option (Option 82).
                     If the value of this object is set to 'mac',
                     the MAC address of the remote end is encoded in the
                     suboption.
                     If the value of this object is set to 'remote-id',
                     sapTlsDhcpRemoteIdString will represent the remote-id.
                     By default, the remote-id value is none."
    DEFVAL { none }
    ::= { sapTlsDhcpInfoEntry 8 }

sapTlsDhcpRemoteIdString OBJECT-TYPE
    SYNTAX          DisplayString (SIZE (0..32))
    MAX-ACCESS      read-write
    STATUS          current
    DESCRIPTION     "The value of the object sapTlsDhcpRemoteIdString specifies
                     the remote-id.  This object exists only if
                     sapTlsDhcpRemoteId has a value of 'remote-id'."
    DEFVAL { "" }
    ::= { sapTlsDhcpInfoEntry 9 }

sapTlsDhcpProxyAdminState   OBJECT-TYPE
    SYNTAX          TmnxEnabledDisabled
    MAX-ACCESS      read-write
    STATUS          current
    DESCRIPTION     "The value of sapTlsDhcpProxyAdminState specifies the
                     desired administrative state of the proxy server on this
                     interface.

                     Note that in order for the proxy server to be enabled,
                     the value of sapTlsDhcpAdminState must also be 'enabled'."
    DEFVAL { disabled }
    ::= { sapTlsDhcpInfoEntry 10 }

sapTlsDhcpProxyServerAddr   OBJECT-TYPE
    SYNTAX          IpAddress
    MAX-ACCESS      read-write
    STATUS          current
    DESCRIPTION     "The value of sapTlsDhcpProxyServerAddr specifies
                     the IP address which will be used as the source address
                     of the emulated DHCP server in the context of
                     this VPLS SAP.

                     This address is mandatory for the proxy server capability
                     and it should be in the context of the subnet represented
                     by this VPLS."
    DEFVAL { '00000000'H }
    ::= { sapTlsDhcpInfoEntry 11 }

sapTlsDhcpProxyLeaseTime    OBJECT-TYPE
    SYNTAX          Unsigned32 (0|300..315446399)
    UNITS           "seconds"
    MAX-ACCESS      read-write
    STATUS          current
    DESCRIPTION     "The value of sapTlsDhcpProxyLeaseTime specifies in seconds
                     how long a DHCP client is allowed to use the offered IP
                     address.

                     Value 0 means the lease time provided by a RADIUS or
                     an upstream DHCP server will not be overridden. A lease
                     time of 7 days is used when RADIUS does not provide
                     a lease time."
    DEFVAL { 0 }
    ::= { sapTlsDhcpInfoEntry 12 }

sapTlsDhcpProxyLTRadiusOverride OBJECT-TYPE
    SYNTAX          TruthValue
    MAX-ACCESS      read-write
    STATUS          current
    DESCRIPTION     "The value of sapTlsDhcpProxyLTRadiusOverride specifies
                     whether or not the lease time provided by the RADIUS
                     server is presented to the DHCP client.

                     By default the proxy-server will always make use of
                     sapTlsDhcpProxyLeaseTime, regardless of what lease time
                     information is provided from the RADIUS server.
                     When sapTlsDhcpProxyLTRadiusOverride is set to 'true', the
                     proxy-server will use the lease time information provided
                     by the RADIUS server, regardless of the configured one."
    DEFVAL { false }
    ::= { sapTlsDhcpInfoEntry 13 }

sapTlsDhcpVendorIncludeOptions OBJECT-TYPE
    SYNTAX          BITS {
                        systemId  (0),
                        clientMac (1),
                        serviceId (2),
                        sapId     (3)
                    }
    MAX-ACCESS      read-write
    STATUS          current
    DESCRIPTION     "The value of sapTlsDhcpVendorIncludeOptions specifies
                     what is encoded in the Alcatel vendor specific
                     sub-option of option 82.

                     The value of this object is only used when
                     sapTlsDhcpInfoAction is 'replace'."
    DEFVAL { { systemId } }
    ::= { sapTlsDhcpInfoEntry 14 }

sapTlsDhcpVendorOptionString OBJECT-TYPE
    SYNTAX          DisplayString (SIZE (0..32))
    MAX-ACCESS      read-write
    STATUS          current
    DESCRIPTION     "The value of sapTlsDhcpVendorOptionString specifies the
                     string that goes into the Alcatel vendor specific
                     sub-option of option 82.

                     This string is only used when sapTlsDhcpInfoAction is set
                     to 'replace'."
    DEFVAL { "" }
    ::= { sapTlsDhcpInfoEntry 15 }

-- --------------------------------------
-- SAP Tls Dhcp Stats Table
-- --------------------------------------
sapTlsDhcpStatsTable OBJECT-TYPE
    SYNTAX          SEQUENCE OF SapTlsDhcpStatsEntry
    MAX-ACCESS      not-accessible
    STATUS          current
    DESCRIPTION     "sapTlsDhcpStatsTable contains DHCP statistics related
                     to  a TLS SAP. This table complements sapTlsInfoTable,
                     and  contains  an entry for each Tls SAP. Rows in this
                     table  are  created  and  deleted automatically by the
                     system."
    ::= { tmnxSapObjs 15 }

sapTlsDhcpStatsEntry OBJECT-TYPE
    SYNTAX          SapTlsDhcpStatsEntry
    MAX-ACCESS      not-accessible
    STATUS          current
    DESCRIPTION     " DHCP statistics for a TLS SAP."
    INDEX           { svcId, sapPortId, sapEncapValue }
    ::= { sapTlsDhcpStatsTable 1 }

SapTlsDhcpStatsEntry ::=
    SEQUENCE {
        sapTlsDhcpStatsClntSnoopdPckts      Counter32,
        sapTlsDhcpStatsSrvrSnoopdPckts      Counter32,
        sapTlsDhcpStatsClntForwdPckts       Counter32,
        sapTlsDhcpStatsSrvrForwdPckts       Counter32,
        sapTlsDhcpStatsClntDropdPckts       Counter32,
        sapTlsDhcpStatsSrvrDropdPckts       Counter32,
        sapTlsDhcpStatsClntProxRadPckts     Counter32,
        sapTlsDhcpStatsClntProxLSPckts      Counter32,
        sapTlsDhcpStatsGenReleasePckts      Counter32,
        sapTlsDhcpStatsGenForceRenPckts     Counter32
    }

sapTlsDhcpStatsClntSnoopdPckts OBJECT-TYPE
    SYNTAX          Counter32
    MAX-ACCESS      read-only
    STATUS          current
    DESCRIPTION     "The value of the object sapTlsDhcpStatsClntSnoopdPckts
                     indicates the number of  DHCP client packets that have
                     been snooped on this SAP."
    ::= { sapTlsDhcpStatsEntry 1 }

sapTlsDhcpStatsSrvrSnoopdPckts OBJECT-TYPE
    SYNTAX          Counter32
    MAX-ACCESS      read-only
    STATUS          current
    DESCRIPTION     "The value of the object sapTlsDhcpStatsSrvrSnoopdPckts
                     indicates the number of  DHCP server packets that have
                     been snooped on this SAP."
    ::= { sapTlsDhcpStatsEntry 2 }

sapTlsDhcpStatsClntForwdPckts OBJECT-TYPE
    SYNTAX          Counter32
    MAX-ACCESS      read-only
    STATUS          current
    DESCRIPTION     "The value of the object sapTlsDhcpStatsClntForwdPckts
                     indicates the number  of  DHCP  client  packets  that
                     have been forwarded on this SAP."
    ::= { sapTlsDhcpStatsEntry 3 }

sapTlsDhcpStatsSrvrForwdPckts OBJECT-TYPE
    SYNTAX          Counter32
    MAX-ACCESS      read-only
    STATUS          current
    DESCRIPTION     "The value of the object sapTlsDhcpStatsSrvrForwdPckts
                     indicates the number of  DHCP  server  packets  that have
                     been forwarded on this SAP."
    ::= { sapTlsDhcpStatsEntry 4 }

sapTlsDhcpStatsClntDropdPckts OBJECT-TYPE
    SYNTAX          Counter32
    MAX-ACCESS      read-only
    STATUS          current
    DESCRIPTION     "The value of the object sapTlsDhcpStatsClntDropdPckts
                     indicates the number of  DHCP client packets that have
                     been dropped on this SAP."
    ::= { sapTlsDhcpStatsEntry 5 }

sapTlsDhcpStatsSrvrDropdPckts OBJECT-TYPE
    SYNTAX          Counter32
    MAX-ACCESS      read-only
    STATUS          current
    DESCRIPTION     "The value of the object sapTlsDhcpStatsSrvrDropdPckts
                     indicates the number of  DHCP server packets that have
                     been dropped on this SAP."
    ::= { sapTlsDhcpStatsEntry 6 }

sapTlsDhcpStatsClntProxRadPckts OBJECT-TYPE
    SYNTAX          Counter32
    MAX-ACCESS      read-only
    STATUS          current
    DESCRIPTION     "The value of the object sapTlsDhcpStatsClntProxRadPckts
                     indicates the number of DHCP client packets that have
                     been proxied on this SAP based on data received from a
                     RADIUS server."
    ::= { sapTlsDhcpStatsEntry 7 }

sapTlsDhcpStatsClntProxLSPckts OBJECT-TYPE
    SYNTAX          Counter32
    MAX-ACCESS      read-only
    STATUS          current
    DESCRIPTION     "The value of the object sapTlsDhcpStatsClntProxLSPckts
                     indicates the number of DHCP client packets that have
                     been proxied on this SAP based on a lease state. The
                     lease itself can have been obtained from a DHCP or RADIUS
                     server. This is the so called lease split functionality."
    ::= { sapTlsDhcpStatsEntry 8 }

sapTlsDhcpStatsGenReleasePckts OBJECT-TYPE
    SYNTAX          Counter32
    MAX-ACCESS      read-only
    STATUS          current
    DESCRIPTION     "The value of the object sapTlsDhcpStatsGenReleasePckts
                     indicates the number of DHCP RELEASE messages spoofed on
                     this SAP to the DHCP server."
    ::= { sapTlsDhcpStatsEntry 9 }

sapTlsDhcpStatsGenForceRenPckts OBJECT-TYPE
    SYNTAX          Counter32
    MAX-ACCESS      read-only
    STATUS          current
    DESCRIPTION     "The value of the object sapTlsDhcpStatsGenForceRenPckts
                     indicates the number of DHCP FORCERENEW messages spoofed
                     on this SAP to the DHCP clients."
    ::= { sapTlsDhcpStatsEntry 10 }

-- ----------------------------------------
-- SAP Tls Dhcp Lease State Table
-- ----------------------------------------
sapTlsDhcpLeaseStateTable OBJECT-TYPE
    SYNTAX          SEQUENCE OF SapTlsDhcpLeaseStateEntry
    MAX-ACCESS      not-accessible
    STATUS          obsolete
    DESCRIPTION     "sapTlsDhcpLeaseStateTable contains DHCP lease state info
                     for a TLS SAP. This table complements sapTlsInfoTable,
                     and contains an entry for each Tls SAP. Rows in this table
                     are created and deleted automatically by the system.
                     The content of this table is moved to the
                     svcDhcpLeaseStateTable."
    ::= { tmnxSapObjs 16 }

sapTlsDhcpLeaseStateEntry OBJECT-TYPE
    SYNTAX          SapTlsDhcpLeaseStateEntry
    MAX-ACCESS      not-accessible
    STATUS          obsolete
    DESCRIPTION     "DHCP Lease State information on a TLS SAP."
    INDEX           { svcId,
                      sapPortId,
                      sapEncapValue,
                      sapTlsDhcpLseStateCiAddr,
                      sapTlsDhcpLseStateChAddr }
    ::= { sapTlsDhcpLeaseStateTable 1 }

SapTlsDhcpLeaseStateEntry ::=
    SEQUENCE {
        sapTlsDhcpLseStateCiAddr        IpAddress,
        sapTlsDhcpLseStateChAddr        MacAddress,
        sapTlsDhcpLseStateRemainLseTime Unsigned32,
        sapTlsDhcpLseStateOption82      OCTET STRING,
        sapTlsDhcpLseStatePersistKey    Unsigned32
    }

sapTlsDhcpLseStateCiAddr OBJECT-TYPE
    SYNTAX          IpAddress
    MAX-ACCESS      not-accessible
    STATUS          obsolete
    DESCRIPTION     "The value of the object sapTlsDhcpLseStateCiAddr indicates
                     the IP address of the DHCP lease state."
    ::= { sapTlsDhcpLeaseStateEntry 1 }

sapTlsDhcpLseStateChAddr OBJECT-TYPE
    SYNTAX          MacAddress
    MAX-ACCESS      not-accessible
    STATUS          obsolete
    DESCRIPTION     "The value of the object sapTlsDhcpLseStateChAddr indicates
                     the MAC address of the DHCP lease state."
    ::= { sapTlsDhcpLeaseStateEntry 2 }

sapTlsDhcpLseStateRemainLseTime OBJECT-TYPE
    SYNTAX          Unsigned32
    MAX-ACCESS      read-only
    STATUS          obsolete
    DESCRIPTION     "The value of the object sapTlsDhcpLseStateRemainLseTime
                     indicates the remaining lease time of the Ip address of
                     the DHCP lease state.
                     This object was made obsolete in the 4.0 release."
    ::= { sapTlsDhcpLeaseStateEntry 3 }

sapTlsDhcpLseStateOption82 OBJECT-TYPE
    SYNTAX          OCTET STRING
    MAX-ACCESS      read-only
    STATUS          obsolete
    DESCRIPTION     "The value of the object sapTlsDhcpLseStateOption82
                     indicates the content of the Option82 for this DHCP
                     lease state.
                     This object was made obsolete in the 4.0 release."
    ::= { sapTlsDhcpLeaseStateEntry 4 }

sapTlsDhcpLseStatePersistKey OBJECT-TYPE
    SYNTAX          Unsigned32
    MAX-ACCESS      read-only
    STATUS          obsolete
    DESCRIPTION     "The value of the object sapTlsDhcpLseStatePersistKey
                     indicates a key value that can be used to track this lease
                     state in the persistence file.
                     This object was made obsolete in the 4.0 release."
    ::= { sapTlsDhcpLeaseStateEntry 5 }

-- --------------------------------------------
-- Ingress QoS Scheduler SAP Statistics Table
-- --------------------------------------------
sapPortIdIngQosSchedStatsTable OBJECT-TYPE
    SYNTAX          SEQUENCE OF SapPortIdIngQosSchedStatsEntry
    MAX-ACCESS      not-accessible
    STATUS          current
    DESCRIPTION
        "The sapPortIdIngQosSchedStatsTable contains ingress QoS
         queue SAP statistics. This table is used when the SAP
         is  a CCAG or LAG in 'link' mode, or an APS."
    ::= { tmnxSapObjs 17 }

sapPortIdIngQosSchedStatsEntry OBJECT-TYPE
    SYNTAX          SapPortIdIngQosSchedStatsEntry
    MAX-ACCESS      not-accessible
    STATUS          current
    DESCRIPTION     "Each entry represents the ingress statistics about a
                     specific SAP's QoS queue. Entries are created when
                     a scheduler policy is applied to a SAP."
    INDEX           { svcId, sapPortId, sapEncapValue,
                      sapPortIdIngQosSchedName, sapPortIdIngPortId }
    ::= { sapPortIdIngQosSchedStatsTable 1 }

SapPortIdIngQosSchedStatsEntry ::=
    SEQUENCE {
        sapPortIdIngQosSchedName      TNamedItem,
        sapPortIdIngPortId            TmnxPortID,
        sapPortIdIngQosSchedFwdPkts   Counter64,
        sapPortIdIngQosSchedFwdOctets Counter64,
        sapPortIdIngQosSchedCustId    TmnxCustId
    }

sapPortIdIngQosSchedName OBJECT-TYPE
    SYNTAX          TNamedItem
    MAX-ACCESS      not-accessible
    STATUS          current
    DESCRIPTION     "The value of sapPortIdIngQosSchedName is used as an index
                     of the ingress QoS scheduler of this SAP."
    ::= { sapPortIdIngQosSchedStatsEntry 1 }

sapPortIdIngPortId OBJECT-TYPE
    SYNTAX          TmnxPortID
    MAX-ACCESS      not-accessible
    STATUS          current
    DESCRIPTION     "The value of sapPortIdIngPortId is used
                     as an index of the ingress QoS scheduler of this SAP. When
                     the SAP is an aps/ccag/lag in 'link' mode, this object is
                     the TmnxPortID of the member-port on which the scheduler is
                     applied."
    ::= {sapPortIdIngQosSchedStatsEntry 2 }

sapPortIdIngQosSchedFwdPkts OBJECT-TYPE
    SYNTAX          Counter64
    MAX-ACCESS      read-only
    STATUS          current
    DESCRIPTION     "The value of sapPortIdIngQosSchedFwdPkts indicates
                     the number of forwarded packets, as determined by the SAP
                     ingress scheduler policy, offered by the Pchip to the
                     Qchip."
    ::= { sapPortIdIngQosSchedStatsEntry 3 }

sapPortIdIngQosSchedFwdOctets OBJECT-TYPE
    SYNTAX          Counter64
    MAX-ACCESS      read-only
    STATUS          current
    DESCRIPTION     "The value of sapPortIdIngQosSchedFwdOctets indicates
                     the number of forwarded octets,as determined by the SAP
                     ingress scheduler policy, offered by the Pchip to the
                     Qchip."
    ::= { sapPortIdIngQosSchedStatsEntry 4 }

sapPortIdIngQosSchedCustId OBJECT-TYPE
    SYNTAX          TmnxCustId
    MAX-ACCESS      read-only
    STATUS          current
    DESCRIPTION     "The value of sapPortIdIngQosSchedCustId indicates the
                     Customer ID for the associated service."
    ::= { sapPortIdIngQosSchedStatsEntry 5 }

-- ------------------------------------------------------------
-- Egress QoS Scheduler SAP Statistics Table for Link mode SAPs
-- ------------------------------------------------------------
sapPortIdEgrQosSchedStatsTable OBJECT-TYPE
    SYNTAX          SEQUENCE OF SapPortIdEgrQosSchedStatsEntry
    MAX-ACCESS      not-accessible
    STATUS          current
    DESCRIPTION     "The sapPortIdEgrQosSchedStatsTable contains egress QoS
                     queue SAP statistics. This table is used when the SAP
                     is  a CCAG or LAG in 'link' mode, or an APS."
    ::= { tmnxSapObjs 18 }

sapPortIdEgrQosSchedStatsEntry OBJECT-TYPE
    SYNTAX          SapPortIdEgrQosSchedStatsEntry
    MAX-ACCESS      not-accessible
    STATUS          current
    DESCRIPTION     "Each entry represents the egress statistics about a
                     specific SAP's QoS queue. Entries are created when
                     a scheduler policy is applied to a SAP."
    INDEX           { svcId, sapPortId, sapEncapValue,
                      sapPortIdEgrQosSchedName, sapPortIdEgrPortId }
    ::= { sapPortIdEgrQosSchedStatsTable 1 }

SapPortIdEgrQosSchedStatsEntry ::=
    SEQUENCE {
        sapPortIdEgrQosSchedName        TNamedItem,
        sapPortIdEgrPortId              TmnxPortID,
        sapPortIdEgrQosSchedFwdPkts     Counter64,
        sapPortIdEgrQosSchedFwdOctets   Counter64,
        sapPortIdEgrQosSchedCustId      TmnxCustId
    }

sapPortIdEgrQosSchedName OBJECT-TYPE
    SYNTAX          TNamedItem
    MAX-ACCESS      not-accessible
    STATUS          current
    DESCRIPTION     "The value of sapPortIdEgrQosSchedName is used as an index
                     of the egress QoS scheduler of this SAP."
    ::= { sapPortIdEgrQosSchedStatsEntry 1 }

sapPortIdEgrPortId OBJECT-TYPE
    SYNTAX          TmnxPortID
    MAX-ACCESS      not-accessible
    STATUS          current
    DESCRIPTION     "The value of sapPortIdEgrPortId is used
                     as an index of the egress QoS scheduler of this SAP. When
                     the SAP is an aps/ccag/lag in 'link' mode, this object is
                     the TmnxPortID of the member-port on which the scheduler is
                     applied."
    ::= {sapPortIdEgrQosSchedStatsEntry 2 }

sapPortIdEgrQosSchedFwdPkts OBJECT-TYPE
    SYNTAX          Counter64
    MAX-ACCESS      read-only
    STATUS          current
    DESCRIPTION     "The value of sapPortIdEgrQosSchedFwdPkts indicates
                     the number of forwarded packets, as determined by the SAP
                     egress scheduler policy, offered by the Pchip to the
                     Qchip."
    ::= { sapPortIdEgrQosSchedStatsEntry 3 }

sapPortIdEgrQosSchedFwdOctets OBJECT-TYPE
    SYNTAX          Counter64
    MAX-ACCESS      read-only
    STATUS          current
    DESCRIPTION     "The value of sapPortIdEgrQosSchedFwdOctets indicates
                     the number of forwarded octets,as determined by the SAP
                     egress scheduler policy, offered by the Pchip to the
                     Qchip."
    ::= { sapPortIdEgrQosSchedStatsEntry 4 }

sapPortIdEgrQosSchedCustId OBJECT-TYPE
    SYNTAX          TmnxCustId
    MAX-ACCESS      read-only
    STATUS          current
    DESCRIPTION     "The value of sapPortIdEgrQosSchedCustId indicates the
                     Customer ID for the associated service."
    ::= { sapPortIdEgrQosSchedStatsEntry 5 }


-- ------------------------------------------
-- SAP Ingress QoS Queue Table
-- ------------------------------------------
sapIngQosQueueInfoTable OBJECT-TYPE
    SYNTAX          SEQUENCE OF SapIngQosQueueInfoEntry
    MAX-ACCESS      not-accessible
    STATUS          current
    DESCRIPTION     "This table is used to override the base parameters
                     of a queue, as defined in the associated SAP
                     ingress QoS policy."
    ::= { tmnxSapObjs 19 }

sapIngQosQueueInfoEntry OBJECT-TYPE
    SYNTAX          SapIngQosQueueInfoEntry
    MAX-ACCESS      not-accessible
    STATUS          current
    DESCRIPTION     "Override values for the specified SAP ingress QoS
                     queue. These values override the corresponding ones
                     specified in the associated SAP ingress QoS policy."
    INDEX           { svcId,
                      sapPortId,
                      sapEncapValue,
                      sapIngQosQId }
    ::= { sapIngQosQueueInfoTable 1 }

SapIngQosQueueInfoEntry ::=
    SEQUENCE {
        sapIngQosQId                TIngressQueueId,
        sapIngQosQRowStatus         RowStatus,
        sapIngQosQLastMgmtChange    TimeStamp,
        sapIngQosQOverrideFlags     TQosQueueAttribute,
        sapIngQosQCBS               TBurstSize,
        sapIngQosQMBS               TBurstSize,
        sapIngQosQHiPrioOnly        TBurstPercentOrDefault,
        sapIngQosQCIRAdaptation     TAdaptationRule,
        sapIngQosQPIRAdaptation     TAdaptationRule,
        sapIngQosQAdminPIR          TPIRRate,
        sapIngQosQAdminCIR          TCIRRate
    }

sapIngQosQId OBJECT-TYPE
    SYNTAX          TIngressQueueId
    MAX-ACCESS      not-accessible
    STATUS          current
    DESCRIPTION     "The value of sapIngQosQId indicates the ID of the
                     queue whose parameters are to be overridden."
    ::= { sapIngQosQueueInfoEntry 1 }

sapIngQosQRowStatus OBJECT-TYPE
    SYNTAX          RowStatus
    MAX-ACCESS      read-create
    STATUS          current
    DESCRIPTION     "The value of sapIngQosQRowStatus controls the creation
                     and deletion of rows in this table."
    ::= { sapIngQosQueueInfoEntry 2 }

sapIngQosQLastMgmtChange OBJECT-TYPE
    SYNTAX          TimeStamp
    MAX-ACCESS      read-only
    STATUS          current
    DESCRIPTION     "The value of sapIngQosQLastMgmtChange indicates the
                     value of sysUpTime at the time of the last management
                     change of any writable object of this row."
    ::= { sapIngQosQueueInfoEntry 3 }

sapIngQosQOverrideFlags OBJECT-TYPE
    SYNTAX          TQosQueueAttribute
    MAX-ACCESS      read-create
    STATUS          current
    DESCRIPTION     "The value of sapIngQosQOverrideFlags specifies the
                     set of attributes whose values have been overridden
                     via management on this queue. Clearing a given flag
                     will return the corresponding overridden attribute
                     to the value defined on the SAP's ingress QoS policy."
    ::= { sapIngQosQueueInfoEntry 4 }

sapIngQosQCBS OBJECT-TYPE
    SYNTAX          TBurstSize
    UNITS           "kilo bytes"
    MAX-ACCESS      read-create
    STATUS          current
    DESCRIPTION     "The value of sapIngQosQCBS specifies the amount of
                     reserved buffer space (in kilo bytes) for this queue."
    DEFVAL { -1 }
    ::= { sapIngQosQueueInfoEntry 5 }

sapIngQosQMBS OBJECT-TYPE
    SYNTAX          TBurstSize
    UNITS           "kilo bytes"
    MAX-ACCESS      read-create
    STATUS          current
    DESCRIPTION     "The value of sapIngQosQMBS specifies the maximum
                     amount of buffer space (in kilo bytes) allowed for
                     this queue."
    DEFVAL { -1 }
    ::= { sapIngQosQueueInfoEntry 6 }

sapIngQosQHiPrioOnly OBJECT-TYPE
    SYNTAX          TBurstPercentOrDefault
    UNITS           "percent"
    MAX-ACCESS      read-create
    STATUS          current
    DESCRIPTION     "The value of sapIngQosQHiPrioOnly specifies the
                     percentage of buffer space for this queue, used
                     exclusively by high priority packets."
    DEFVAL { -1 }
    ::= { sapIngQosQueueInfoEntry 7 }

sapIngQosQCIRAdaptation OBJECT-TYPE
    SYNTAX          TAdaptationRule
    MAX-ACCESS      read-create
    STATUS          current
    DESCRIPTION     "The value of sapIngQosQCIRAdaptation specifies the
                     criteria to use to compute the operational CIR value
                     for this queue, while maintaining a minimum offset."
    DEFVAL { closest }
    ::= { sapIngQosQueueInfoEntry 8 }

sapIngQosQPIRAdaptation OBJECT-TYPE
    SYNTAX          TAdaptationRule
    MAX-ACCESS      read-create
    STATUS          current
    DESCRIPTION     "The value of sapIngQosQPIRAdaptation specifies the
                     criteria to use to compute the operational PIR value
                     for this queue, while maintaining a minimum offset."
    DEFVAL { closest }
    ::= { sapIngQosQueueInfoEntry 9 }

sapIngQosQAdminPIR OBJECT-TYPE
    SYNTAX          TPIRRate
    UNITS           "kilo bits per second"
    MAX-ACCESS      read-create
    STATUS          current
    DESCRIPTION     "The value of sapIngQosQAdminPIR specifies the desired
                     PIR value for this queue."
    DEFVAL { -1 }
    ::= { sapIngQosQueueInfoEntry 10 }

sapIngQosQAdminCIR OBJECT-TYPE
    SYNTAX          TCIRRate
    UNITS           "kilo bits per second"
    MAX-ACCESS      read-create
    STATUS          current
    DESCRIPTION     "The value of sapIngQosQAdminCIR specifies the desired
                     CIR value for this queue."
    DEFVAL { -1 }
    ::= { sapIngQosQueueInfoEntry 11 }

-- ----------------------------
-- SAP Egress QoS Queue Table
-- ----------------------------
sapEgrQosQueueInfoTable OBJECT-TYPE
    SYNTAX          SEQUENCE OF SapEgrQosQueueInfoEntry
    MAX-ACCESS      not-accessible
    STATUS          current
    DESCRIPTION     "This table is used to override the base parameters
                     of a queue, as defined in the associated SAP
                     egress QoS policy."
    ::= { tmnxSapObjs 20 }

sapEgrQosQueueInfoEntry OBJECT-TYPE
    SYNTAX          SapEgrQosQueueInfoEntry
    MAX-ACCESS      not-accessible
    STATUS          current
    DESCRIPTION     "Override values for the specified SAP egress QoS
                     queue. These values override the corresponding ones
                     specified in the associated SAP egress QoS policy."
    INDEX           { svcId,
                      sapPortId,
                      sapEncapValue,
                      sapEgrQosQId }
    ::= { sapEgrQosQueueInfoTable 1 }

SapEgrQosQueueInfoEntry ::=
    SEQUENCE {
        sapEgrQosQId                TEgressQueueId,
        sapEgrQosQRowStatus         RowStatus,
        sapEgrQosQLastMgmtChange    TimeStamp,
        sapEgrQosQOverrideFlags     TQosQueueAttribute,
        sapEgrQosQCBS               TBurstSize,
        sapEgrQosQMBS               TBurstSize,
        sapEgrQosQHiPrioOnly        TBurstPercentOrDefault,
        sapEgrQosQCIRAdaptation     TAdaptationRule,
        sapEgrQosQPIRAdaptation     TAdaptationRule,
        sapEgrQosQAdminPIR          TPIRRate,
        sapEgrQosQAdminCIR          TCIRRate,
        sapEgrQosQAvgOverhead       Unsigned32
    }

sapEgrQosQId OBJECT-TYPE
    SYNTAX          TEgressQueueId
    MAX-ACCESS      not-accessible
    STATUS          current
    DESCRIPTION     "The value of sapEgrQosQId indicates the ID of the
                     queue whose parameters are to be overridden."
    ::= { sapEgrQosQueueInfoEntry 1 }

sapEgrQosQRowStatus OBJECT-TYPE
    SYNTAX          RowStatus
    MAX-ACCESS      read-create
    STATUS          current
    DESCRIPTION     "The value of sapEgrQosQRowStatus controls the creation
                     and deletion of rows in this table."
    ::= { sapEgrQosQueueInfoEntry 2 }

sapEgrQosQLastMgmtChange OBJECT-TYPE
    SYNTAX          TimeStamp
    MAX-ACCESS      read-only
    STATUS          current
    DESCRIPTION     "The value of sapEgrQosQLastMgmtChange indicates the
                     value of sysUpTime at the time of the last management
                     change of any writable object of this row."
    ::= { sapEgrQosQueueInfoEntry 3 }

sapEgrQosQOverrideFlags OBJECT-TYPE
    SYNTAX          TQosQueueAttribute
    MAX-ACCESS      read-create
    STATUS          current
    DESCRIPTION     "The value of sapEgrQosQOverrideFlags specifies the
                     set of attributes whose values have been overridden
                     via management on this queue. Clearing a given flag
                     will return the corresponding overridden attribute
                     to the value defined on the SAP's ingress QoS policy."
    ::= { sapEgrQosQueueInfoEntry 4 }

sapEgrQosQCBS OBJECT-TYPE
    SYNTAX          TBurstSize
    UNITS           "kilo bytes"
    MAX-ACCESS      read-create
    STATUS          current
    DESCRIPTION     "The value of sapEgrQosQCBS specifies the amount of
                     reserved buffer space (in kilo bytes) for this queue."
    DEFVAL { -1 }
    ::= { sapEgrQosQueueInfoEntry 5 }

sapEgrQosQMBS OBJECT-TYPE
    SYNTAX          TBurstSize
    UNITS           "kilo bytes"
    MAX-ACCESS      read-create
    STATUS          current
    DESCRIPTION     "The value of sapEgrQosQMBS specifies the maximum
                     amount of buffer space (in kilo bytes) allowed for
                     this queue."
    DEFVAL { -1 }
    ::= { sapEgrQosQueueInfoEntry 6 }

sapEgrQosQHiPrioOnly OBJECT-TYPE
    SYNTAX          TBurstPercentOrDefault
    UNITS           "percent"
    MAX-ACCESS      read-create
    STATUS          current
    DESCRIPTION     "The value of sapEgrQosQHiPrioOnly specifies the
                     percentage of buffer space for this queue, used
                     exclusively by high priority packets."
    DEFVAL { -1 }
    ::= { sapEgrQosQueueInfoEntry 7 }

sapEgrQosQCIRAdaptation OBJECT-TYPE
    SYNTAX          TAdaptationRule
    MAX-ACCESS      read-create
    STATUS          current
    DESCRIPTION     "The value of sapEgrQosQCIRAdaptation specifies the
                     criteria to use to compute the operational CIR value
                     for this queue, while maintaining a minimum offset."
    DEFVAL { closest }
    ::= { sapEgrQosQueueInfoEntry 8 }

sapEgrQosQPIRAdaptation OBJECT-TYPE
    SYNTAX          TAdaptationRule
    MAX-ACCESS      read-create
    STATUS          current
    DESCRIPTION     "The value of sapEgrQosQPIRAdaptation specifies the
                     criteria to use to compute the operational PIR value
                     for this queue, while maintaining a minimum offset."
    DEFVAL { closest }
    ::= { sapEgrQosQueueInfoEntry 9 }

sapEgrQosQAdminPIR OBJECT-TYPE
    SYNTAX          TPIRRate
    UNITS           "kilo bits per second"
    MAX-ACCESS      read-create
    STATUS          current
    DESCRIPTION     "The value of sapEgrQosQAdminPIR specifies the desired
                     PIR value for this queue."
    DEFVAL { -1 }
    ::= { sapEgrQosQueueInfoEntry 10 }

sapEgrQosQAdminCIR OBJECT-TYPE
    SYNTAX          TCIRRate
    UNITS           "kilo bits per second"
    MAX-ACCESS      read-create
    STATUS          current
    DESCRIPTION     "The value of sapEgrQosQAdminCIR specifies the desired
                     CIR value for this queue."
    DEFVAL { -1 }
    ::= { sapEgrQosQueueInfoEntry 11 }

sapEgrQosQAvgOverhead   OBJECT-TYPE
    SYNTAX          Unsigned32 (0..10000)
    MAX-ACCESS      read-create
    STATUS          current
    DESCRIPTION     "The value of sapEgrQosQAvgOverhead specifies the
                     encapsulation overhead, in hundredths of a percent,
                     used to translate packet-based rate to frame-based
                     rate and vice versa."
    DEFVAL      { 0 }
    ::= { sapEgrQosQueueInfoEntry 12 }

-- ------------------------------------
-- SAP Ingress QoS Scheduler Table
-- ------------------------------------
sapIngQosSchedInfoTable OBJECT-TYPE
    SYNTAX          SEQUENCE OF SapIngQosSchedInfoEntry
    MAX-ACCESS      not-accessible
    STATUS          current
    DESCRIPTION     "This table is used to override the base parameters
                     of a virtual scheduler, as defined in the associated
                     SAP ingress scheduler policy."
    ::= { tmnxSapObjs 21 }

sapIngQosSchedInfoEntry OBJECT-TYPE
    SYNTAX          SapIngQosSchedInfoEntry
    MAX-ACCESS      not-accessible
    STATUS          current
    DESCRIPTION     "Override values for the specified SAP ingress virtual
                     scheduler. These values override the corresponding
                     ones specified in the associated SAP ingress scheduler
                     policy."
    INDEX           { svcId,
                      sapPortId,
                      sapEncapValue,
                      IMPLIED sapIngQosSName }
    ::= { sapIngQosSchedInfoTable 1 }

SapIngQosSchedInfoEntry ::=
    SEQUENCE {
        sapIngQosSName              TNamedItem,
        sapIngQosSRowStatus         RowStatus,
        sapIngQosSLastMgmtChange    TimeStamp,
        sapIngQosSOverrideFlags     TVirtSchedAttribute,
        sapIngQosSPIR               TPIRRate,
        sapIngQosSCIR               TCIRRate,
        sapIngQosSSummedCIR         TruthValue
    }

sapIngQosSName OBJECT-TYPE
    SYNTAX          TNamedItem
    MAX-ACCESS      not-accessible
    STATUS          current
    DESCRIPTION     "The value of sapIngQosSName indicates the name of
                     the virtual scheduler whose parameters are to be
                     overridden."
    ::= { sapIngQosSchedInfoEntry 1 }

sapIngQosSRowStatus OBJECT-TYPE
    SYNTAX          RowStatus
    MAX-ACCESS      read-create
    STATUS          current
    DESCRIPTION     "The value of sapIngQosSRowStatus controls the creation
                     and deletion of rows in this table."
    ::= { sapIngQosSchedInfoEntry 2 }

sapIngQosSLastMgmtChange OBJECT-TYPE
    SYNTAX          TimeStamp
    MAX-ACCESS      read-only
    STATUS          current
    DESCRIPTION     "The value of sapIngQosSLastMgmtChange indicates the
                     value of sysUpTime at the time of the last management
                     change of any writable object of this row."
    ::= { sapIngQosSchedInfoEntry 3 }

sapIngQosSOverrideFlags OBJECT-TYPE
    SYNTAX          TVirtSchedAttribute
    MAX-ACCESS      read-create
    STATUS          current
    DESCRIPTION     "The value of sapIngQosSOverrideFlags specifies the
                     set of attributes whose values have been overridden
                     via management on this virtual scheduler. Clearing a
                     given flag will return the corresponding overridden
                     attribute to the value defined on the SAP's ingress
                     scheduler policy."
    ::= { sapIngQosSchedInfoEntry 4 }

sapIngQosSPIR OBJECT-TYPE
    SYNTAX          TPIRRate
    UNITS           "kilo bits per second"
    MAX-ACCESS      read-create
    STATUS          current
    DESCRIPTION     "The value of sapIngQosSPIR specifies the desired
                     PIR value for this virtual scheduler."
    DEFVAL { -1 }
    ::= { sapIngQosSchedInfoEntry 5 }

sapIngQosSCIR OBJECT-TYPE
    SYNTAX          TCIRRate
    UNITS           "kilo bits per second"
    MAX-ACCESS      read-create
    STATUS          current
    DESCRIPTION     "The value of sapIngQosSCIR specifies the desired
                     CIR value for this virtual scheduler."
    DEFVAL { -1 }
    ::= { sapIngQosSchedInfoEntry 6 }

sapIngQosSSummedCIR     OBJECT-TYPE
    SYNTAX          TruthValue
    MAX-ACCESS      read-create
    STATUS          current
    DESCRIPTION     "The value of sapIngQosSSummedCIR specifies if the CIR
                     should be used as the summed CIR values of the children
                     schedulers or queues. If set to 'true', the applicable
                     scheduler CIR (sapIngQosSCIR) loses its meaning."
    DEFVAL { true }
    ::= { sapIngQosSchedInfoEntry 7 }

-- ------------------------------------
-- SAP Egress QoS Scheduler Table
-- ------------------------------------
sapEgrQosSchedInfoTable OBJECT-TYPE
    SYNTAX          SEQUENCE OF SapEgrQosSchedInfoEntry
    MAX-ACCESS      not-accessible
    STATUS          current
    DESCRIPTION     "This table is used to override the base parameters
                     of a virtual scheduler, as defined in the associated
                     SAP egress scheduler policy."
    ::= { tmnxSapObjs 22 }

sapEgrQosSchedInfoEntry OBJECT-TYPE
    SYNTAX          SapEgrQosSchedInfoEntry
    MAX-ACCESS      not-accessible
    STATUS          current
    DESCRIPTION     "Override values for the specified SAP egress virtual
                     scheduler. These values override the corresponding
                     ones specified in the associated SAP egress scheduler
                     policy."
    INDEX           { svcId,
                      sapPortId,
                      sapEncapValue,
                      IMPLIED sapEgrQosSName }
    ::= { sapEgrQosSchedInfoTable 1 }

SapEgrQosSchedInfoEntry ::=
    SEQUENCE {
        sapEgrQosSName              TNamedItem,
        sapEgrQosSRowStatus         RowStatus,
        sapEgrQosSLastMgmtChange    TimeStamp,
        sapEgrQosSOverrideFlags     TVirtSchedAttribute,
        sapEgrQosSPIR               TPIRRate,
        sapEgrQosSCIR               TCIRRate,
        sapEgrQosSSummedCIR         TruthValue
    }

sapEgrQosSName OBJECT-TYPE
    SYNTAX          TNamedItem
    MAX-ACCESS      not-accessible
    STATUS          current
    DESCRIPTION     "The value of sapEgrQosSName indicates the name of
                     the virtual scheduler whose parameters are to be
                     overridden."
    ::= { sapEgrQosSchedInfoEntry 1 }

sapEgrQosSRowStatus OBJECT-TYPE
    SYNTAX          RowStatus
    MAX-ACCESS      read-create
    STATUS          current
    DESCRIPTION     "The value of sapEgrQosSRowStatus controls the creation
                     and deletion of rows in this table."
    ::= { sapEgrQosSchedInfoEntry 2 }

sapEgrQosSLastMgmtChange OBJECT-TYPE
    SYNTAX          TimeStamp
    MAX-ACCESS      read-only
    STATUS          current
    DESCRIPTION     "The value of sapEgrQosSLastMgmtChange indicates the
                     value of sysUpTime at the time of the last management
                     change of any writable object of this row."
    ::= { sapEgrQosSchedInfoEntry 3 }

sapEgrQosSOverrideFlags OBJECT-TYPE
    SYNTAX          TVirtSchedAttribute
    MAX-ACCESS      read-create
    STATUS          current
    DESCRIPTION     "The value of sapEgrQosSOverrideFlags specifies the
                     set of attributes whose values have been overridden
                     via management on this virtual scheduler. Clearing a
                     given flag will return the corresponding overridden
                     attribute to the value defined on the SAP's egress
                     scheduler policy."
    ::= { sapEgrQosSchedInfoEntry 4 }

sapEgrQosSPIR OBJECT-TYPE
    SYNTAX          TPIRRate
    UNITS           "kilo bits per second"
    MAX-ACCESS      read-create
    STATUS          current
    DESCRIPTION     "The value of sapEgrQosSPIR specifies the desired
                     PIR value for this virtual scheduler."
    DEFVAL { -1 }
    ::= { sapEgrQosSchedInfoEntry 5 }

sapEgrQosSCIR OBJECT-TYPE
    SYNTAX          TCIRRate
    UNITS           "kilo bits per second"
    MAX-ACCESS      read-create
    STATUS          current
    DESCRIPTION     "The value of sapEgrQosSCIR specifies the desired
                     CIR value for this virtual scheduler."
    DEFVAL { -1 }
    ::= { sapEgrQosSchedInfoEntry 6 }

sapEgrQosSSummedCIR     OBJECT-TYPE
    SYNTAX          TruthValue
    MAX-ACCESS      read-create
    STATUS          current
    DESCRIPTION     "The value of sapEgrQosSSummedCIR specifies if the CIR
                     should be used as the summed CIR values of the children
                     schedulers or queues. If set to 'true', the applicable
                     scheduler CIR (sapEgrQosSCIR) loses its meaning."
    DEFVAL { true }
    ::= { sapEgrQosSchedInfoEntry 7 }

-- --------------------------------------
-- SAP Subscriber Management Table
-- --------------------------------------
sapSubMgmtInfoTable OBJECT-TYPE
    SYNTAX          SEQUENCE OF SapSubMgmtInfoEntry
    MAX-ACCESS      not-accessible
    STATUS          current
    DESCRIPTION     "A table that contains SAP subscriber management
                     information."
    ::= { tmnxSapObjs 23 }

sapSubMgmtInfoEntry OBJECT-TYPE
    SYNTAX          SapSubMgmtInfoEntry
    MAX-ACCESS      not-accessible
    STATUS          current
    DESCRIPTION     "Subscriber management specific information about a SAP."
    INDEX           { svcId, sapPortId, sapEncapValue }
    ::= { sapSubMgmtInfoTable 1 }

SapSubMgmtInfoEntry ::=
    SEQUENCE {
        sapSubMgmtAdminStatus           TmnxEnabledDisabled,
        sapSubMgmtDefSubProfile         ServObjName,
        sapSubMgmtDefSlaProfile         ServObjName,
        sapSubMgmtSubIdentPolicy        ServObjName,
        sapSubMgmtSubscriberLimit       Unsigned32,
        sapSubMgmtProfiledTrafficOnly   TruthValue,
        sapSubMgmtNonSubTrafficSubIdent DisplayString,
        sapSubMgmtNonSubTrafficSubProf  ServObjName,
        sapSubMgmtNonSubTrafficSlaProf  ServObjName,
        sapSubMgmtMacDaHashing          TruthValue,
        sapSubMgmtDefSubIdent           INTEGER,
        sapSubMgmtDefSubIdentString     DisplayString,
        sapSubMgmtDefAppProfile         ServObjName,
        sapSubMgmtNonSubTrafficAppProf  ServObjName
    }

sapSubMgmtAdminStatus OBJECT-TYPE
    SYNTAX          TmnxEnabledDisabled
    MAX-ACCESS      read-create
    STATUS          current
    DESCRIPTION     "The value of sapSubMgmtAdminStatus specifies whether
                     enhanced subscriber management is enabled on this SAP."
    DEFVAL { disabled }
    ::= { sapSubMgmtInfoEntry 1 }

sapSubMgmtDefSubProfile OBJECT-TYPE
    SYNTAX          ServObjName
    MAX-ACCESS      read-create
    STATUS          current
    DESCRIPTION     "The value of sapSubMgmtDefSubProfile specifies the default
                     subscriber profile applicable on this SAP. The
                     corresponding profile is defined in
                     TIMETRA-SUBSCRIBER-MGMT-MIB::tmnxSubProfileTable.

                     A value of 'default' is not allowed for this object."
    DEFVAL { "" }
    ::= { sapSubMgmtInfoEntry 2 }

sapSubMgmtDefSlaProfile OBJECT-TYPE
    SYNTAX          ServObjName
    MAX-ACCESS      read-create
    STATUS          current
    DESCRIPTION     "The value of sapSubMgmtDefSlaProfile specifies the default
                     SLA profile applicable on this SAP. The corresponding
                     profile is defined in
                     TIMETRA-SUBSCRIBER-MGMT-MIB::tmnxSLAProfileTable."
    DEFVAL { "" }
    ::= { sapSubMgmtInfoEntry 3 }

sapSubMgmtSubIdentPolicy OBJECT-TYPE
    SYNTAX          ServObjName
    MAX-ACCESS      read-create
    STATUS          current
    DESCRIPTION     "The value of sapSubMgmtSubIdentPolicy specifies the
                     subscriber identification policy applicable on this SAP.
                     The corresponding policy is defined in
                     TIMETRA-SUBSCRIBER-MGMT-MIB::tmnxSubIdentPolicyTable."
    DEFVAL { "" }
    ::= { sapSubMgmtInfoEntry 4 }

sapSubMgmtSubscriberLimit OBJECT-TYPE
    SYNTAX          Unsigned32 (0..8000)
    MAX-ACCESS      read-create
    STATUS          current
    DESCRIPTION     "The value of sapSubMgmtSubscriberLimit specifies the
                     maximum number of subscribers allowed for this SAP.

                     If the value is 0, there is no limit. Only if the value is
                     1, the 'single-sub-parameters' defined with objects
                     sapSubMgmtProfiledTrafficOnly,
                     sapSubMgmtNonSubTrafficSubProf and
                     sapSubMgmtNonSubTrafficSlaProf are meaningful."
    DEFVAL { 1 }
    ::= { sapSubMgmtInfoEntry 5 }

sapSubMgmtProfiledTrafficOnly OBJECT-TYPE
    SYNTAX          TruthValue
    MAX-ACCESS      read-create
    STATUS          current
    DESCRIPTION     "The value of sapSubMgmtProfiledTrafficOnly specifies
                     whether only profiled traffic is applicable for this SAP.
                     If set to 'true', all SAP queues will be deleted.

                     The value of this object is only meaningful if
                     sapSubMgmtSubscriberLimit is set to 1."
    DEFVAL { false }
    ::= { sapSubMgmtInfoEntry 6 }

sapSubMgmtNonSubTrafficSubIdent OBJECT-TYPE
    SYNTAX          DisplayString (SIZE (0..32))
    MAX-ACCESS      read-create
    STATUS          current
    DESCRIPTION     "The value of sapSubMgmtNonSubTrafficSubIdent specifies the
                     subscriber identification applicable on this SAP for all
                     non-subscriber traffic.

                     The value of this object is only meaningful if
                     sapSubMgmtSubscriberLimit is set to 1."
    DEFVAL { "" }
    ::= { sapSubMgmtInfoEntry 7 }

sapSubMgmtNonSubTrafficSubProf OBJECT-TYPE
    SYNTAX          ServObjName
    MAX-ACCESS      read-create
    STATUS          current
    DESCRIPTION     "The value of sapSubMgmtNonSubTrafficSubProf specifies the
                     subscriber profile applicable on this SAP for all
                     non-subscriber traffic.

                     The value of this object is only meaningful if
                     sapSubMgmtSubscriberLimit is set to 1."
    DEFVAL { "" }
    ::= { sapSubMgmtInfoEntry 8 }

sapSubMgmtNonSubTrafficSlaProf OBJECT-TYPE
    SYNTAX          ServObjName
    MAX-ACCESS      read-create
    STATUS          current
    DESCRIPTION     "The value of sapSubMgmtNonSubTrafficSlaProf specifies the
                     SLA profile applicable on this SAP for all non-subscriber
                     traffic.

                     The value of this object is only meaningful if
                     sapSubMgmtSubscriberLimit is set to 1."
    DEFVAL { "" }
    ::= { sapSubMgmtInfoEntry 9 }

sapSubMgmtMacDaHashing OBJECT-TYPE
    SYNTAX          TruthValue
    MAX-ACCESS      read-create
    STATUS          current
    DESCRIPTION     "The value of sapSubMgmtMacDaHashing specifies whether
                     subscriber traffic egressing a LAG SAP has its egress LAG
                     link selected by a function of the MAC destination address
                     instead of subscriber id.

                     The value of this object is only meaningful if
                     sapSubMgmtAdminStatus is set to 'enabled' and can only
                     be configured for TLS services."
    DEFVAL { false }
    ::= { sapSubMgmtInfoEntry 10 }

sapSubMgmtDefSubIdent OBJECT-TYPE
    SYNTAX          INTEGER {
                        useSapId  (1),
                        useString (2)
                    }
    MAX-ACCESS      read-create
    STATUS          current
    DESCRIPTION     "The value of sapSubMgmtDefSubIdent specifies what is
                     used as the default subscriber identification applicable
                     on this SAP.

                     This value is used in case no other source (like Radius)
                     provides a subscriber identification string.

                     If the value of this objects is set to 'useSapId',
                     the SAP-id is used as the default subscriber identification
                     string. In this case, sapSubMgmtDefSubIdentString must
                     contain the empty string.
                     If the value of this object is set to 'useString',
                     the value of sapSubMgmtDefSubIdentString is used as the
                     default subscriber identification string. In this case,
                     an empty sapSubMgmtDefSubIdentString means that there is no
                     default subscriber identification configured."
    DEFVAL { useString }
    ::= { sapSubMgmtInfoEntry 11 }

sapSubMgmtDefSubIdentString OBJECT-TYPE
    SYNTAX          DisplayString (SIZE (0..32))
    MAX-ACCESS      read-create
    STATUS          current
    DESCRIPTION     "The value of sapSubMgmtDefSubIdentString specifies the
                     default subscriber identification string applicable on
                     this SAP."
    DEFVAL { "" }
    ::= { sapSubMgmtInfoEntry 12 }

sapSubMgmtDefAppProfile OBJECT-TYPE
    SYNTAX          ServObjName
    MAX-ACCESS      read-create
    STATUS          current
    DESCRIPTION     "The value of sapSubMgmtDefAppProfile specifies the default
                     application profile applicable on this SAP. The
                     corresponding profile is defined in
                     TIMETRA-BSX-MIB::tmnxBsxAppProfTable."
    DEFVAL { "" }
    ::= { sapSubMgmtInfoEntry 13 }

sapSubMgmtNonSubTrafficAppProf OBJECT-TYPE
    SYNTAX          ServObjName
    MAX-ACCESS      read-create
    STATUS          current
    DESCRIPTION     "The value of sapSubMgmtNonSubTrafficAppProf specifies the
                     application profile applicable on this SAP for all
                     non-subscriber traffic.

                     The value of this object is only meaningful if
                     sapSubMgmtSubscriberLimit is set to 1."
    DEFVAL { "" }
    ::= { sapSubMgmtInfoEntry 14 }

-- -----------------------------------------
-- SAP TLS MSTI Table
-- -----------------------------------------
sapTlsMstiTable OBJECT-TYPE
    SYNTAX          SEQUENCE OF SapTlsMstiEntry
    MAX-ACCESS      not-accessible
    STATUS          current
    DESCRIPTION     "This table contains Multiple Spanning Tree Instance
                     information for the SAP. Each management VPLS running
                     MSTP can have upto 15 MSTI. An entry in this table is
                     automatically created when a tlsMstiEntry is created."
    ::= { tmnxSapObjs 24 }

sapTlsMstiEntry OBJECT-TYPE
    SYNTAX          SapTlsMstiEntry
    MAX-ACCESS      not-accessible
    STATUS          current
    DESCRIPTION     "Information about a specific MSTI for a SAP."
    INDEX           { svcId, sapPortId, sapEncapValue, tlsMstiInstanceId}
    ::= { sapTlsMstiTable 1 }

SapTlsMstiEntry ::=
    SEQUENCE {
        sapTlsMstiPriority          Integer32,
        sapTlsMstiPathCost          INTEGER,
        sapTlsMstiLastMgmtChange    TimeStamp,
        sapTlsMstiPortRole          StpPortRole,
        sapTlsMstiPortState         TStpPortState,
        sapTlsMstiDesignatedBridge  BridgeId,
        sapTlsMstiDesignatedPort    Integer32
    }

sapTlsMstiPriority OBJECT-TYPE
    SYNTAX          Integer32 (0..255)
    MAX-ACCESS      read-write
    STATUS          current
    DESCRIPTION     "The value of the object sapTlsMstiPriority specifies
                     the value of the port priority field which is contained in
                     the most significant 4 bits of the 16-bit Port ID
                     associated with this SAP and MSTI. As only the most
                     significant 4 bits of the value are used, the actual value
                     of this object is limited to multiples of 16: e.g. the
                     agent rounds down the value to one of: 0, 16, 32, .. ,
                     224, 240."
    DEFVAL          { 128 }
    ::= { sapTlsMstiEntry 1 }

sapTlsMstiPathCost OBJECT-TYPE
    SYNTAX          INTEGER (1..200000000)
    MAX-ACCESS      read-write
    STATUS          current
    DESCRIPTION     "The value of the object sapTlsMstiPathCost specifies the
                     contribution of this port to the MSTI path cost of paths
                     towards the spanning tree regional root which include this
                     port."
    DEFVAL          { 10 }
    ::= { sapTlsMstiEntry 2 }

sapTlsMstiLastMgmtChange OBJECT-TYPE
    SYNTAX          TimeStamp
    MAX-ACCESS      read-only
    STATUS          current
    DESCRIPTION     "The value of the object sapTlsMstiLastMgmtChange indicates
                     the value of sysUpTime at the time of the most recent
                     management-initiated change to this SAP MSTI information."
    ::= { sapTlsMstiEntry 3 }

sapTlsMstiPortRole OBJECT-TYPE
    SYNTAX          StpPortRole
    MAX-ACCESS      read-only
    STATUS          current
    DESCRIPTION     "sapTlsMstiPortRole indicates the current role of the
                     sap in the MSTI as defined by the Spanning Tree Protocol."
    ::= { sapTlsMstiEntry 4 }

sapTlsMstiPortState OBJECT-TYPE
    SYNTAX          TStpPortState
    MAX-ACCESS      read-only
    STATUS          current
    DESCRIPTION     "The value of the object sapTlsMstiPortState indicates the
                     port's current state as defined by application of the
                     Spanning Tree Protocol. This state controls what action a
                     port takes on reception of a frame. If the bridge has
                     detected a port that is malfunctioning it will
                     place that port into the 'broken' state."
    ::= { sapTlsMstiEntry 5 }

sapTlsMstiDesignatedBridge OBJECT-TYPE
    SYNTAX          BridgeId
    MAX-ACCESS      read-only
    STATUS          current
    DESCRIPTION     "The value of the object sapTlsMstiDesignatedBridge
                     indicates  the Bridge Identifier of the bridge which this
                     port considers to be the Designated Bridge for this port's
                     segment for this MSTI."
    ::= { sapTlsMstiEntry 6 }

sapTlsMstiDesignatedPort OBJECT-TYPE
    SYNTAX          Integer32
    MAX-ACCESS      read-only
    STATUS          current
    DESCRIPTION     "The value of the object sapTlsMstiDesignatedPort indicates
                     the Port Identifier of the port on the Designated Bridge
                     for this port's segment for this MSTI."
    ::= { sapTlsMstiEntry 7 }

-- -------------------------------------
-- IPIPE SAP Table
-- -------------------------------------
sapIpipeInfoTable OBJECT-TYPE
    SYNTAX          SEQUENCE OF SapIpipeInfoEntry
    MAX-ACCESS      not-accessible
    STATUS          current
    DESCRIPTION     "A table that contains IPIPE specific SAP information."
    ::= { tmnxSapObjs 25 }

sapIpipeInfoEntry OBJECT-TYPE
    SYNTAX          SapIpipeInfoEntry
    MAX-ACCESS      not-accessible
    STATUS          current
    DESCRIPTION     "IPIPE specific information about a SAP."
    INDEX           { svcId, sapPortId, sapEncapValue }
    ::= { sapIpipeInfoTable 1 }

SapIpipeInfoEntry ::=
    SEQUENCE {
        sapIpipeCeInetAddressType           InetAddressType,
        sapIpipeCeInetAddress               InetAddress,
        sapIpipeMacRefreshInterval          Unsigned32,
        sapIpipeMacAddress                  MacAddress,
        sapIpipeArpedMacAddress             MacAddress,
        sapIpipeArpedMacAddressTimeout      Unsigned32
    }

sapIpipeCeInetAddressType OBJECT-TYPE
    SYNTAX          InetAddressType
    MAX-ACCESS      read-write
    STATUS          current
    DESCRIPTION     "The value of the object sapIpipeCeInetAddressType
                     specifies the addresstype of the local end host IP
                     of an IPIPE."
    ::= { sapIpipeInfoEntry 1}

sapIpipeCeInetAddress OBJECT-TYPE
    SYNTAX          InetAddress (SIZE(0|4))
    MAX-ACCESS      read-write
    STATUS          current
    DESCRIPTION     "The type of this address is determined by the value of
                     the sapIpipeCeInetAddressType object.

                     This object specifies the IPv4 address of the
                     local end host of an IPIPE."
    ::= { sapIpipeInfoEntry 2 }

sapIpipeMacRefreshInterval OBJECT-TYPE
    SYNTAX      Unsigned32 (0..65535)
    UNITS       "seconds"
    MAX-ACCESS  read-write
    STATUS      current
    DESCRIPTION
        "The value of sapIpipeMacRefreshInterval specifies the interval
         between successive attempts to refresh the MAC address of the CE
         device associated with an Ethernet ipipe SAP. If no other event
         (such as reception of an ARP request from the CE) occurs that
         would refresh the MAC address before the end of the interval,
         an ARP request will be originated from the IPIPE SAP."
    DEFVAL { 14400 }
    ::= { sapIpipeInfoEntry 3 }

sapIpipeMacAddress  OBJECT-TYPE
    SYNTAX         MacAddress
    MAX-ACCESS     read-write
    STATUS         current
    DESCRIPTION    "The value of the object sapIpipeMacAddress specifies
                    the MAC address of an IPIPE Ethernet SAP."
    ::= { sapIpipeInfoEntry 4 }

sapIpipeArpedMacAddress  OBJECT-TYPE
    SYNTAX         MacAddress
    MAX-ACCESS     read-only
    STATUS         current
    DESCRIPTION    "The value of the object sapIpipeArpedMacAddress indicates
                    the MAC address of the local end host."
    ::= { sapIpipeInfoEntry 5 }


sapIpipeArpedMacAddressTimeout  OBJECT-TYPE
    SYNTAX      Unsigned32 (0..65535)
    MAX-ACCESS     read-only
    STATUS         current
    DESCRIPTION    "The value of the object sapIpipeArpedMacAddressTimeout
                    indicates the number of seconds to wait for the
                    sapIpipeArpedMacAddress to be re-refreshed."
    ::= { sapIpipeInfoEntry 6 }


-- -----------------------------------------
-- SAP Base ToD Monitoring Table
-- -----------------------------------------
sapTodMonitorTable OBJECT-TYPE
    SYNTAX          SEQUENCE OF SapTodMonitorEntry
    MAX-ACCESS      not-accessible
    STATUS          current
    DESCRIPTION     "This table contains information on configurable objects
                     on SAP level, that can be modified by a scheduled policy."
    ::= { tmnxSapObjs 26 }

sapTodMonitorEntry OBJECT-TYPE
    SYNTAX          SapTodMonitorEntry
    MAX-ACCESS      not-accessible
    STATUS          current
    DESCRIPTION     "Information about ToD policy modifiable config data
                     for a SAP."
    INDEX           { svcId, sapPortId, sapEncapValue }
    ::= { sapTodMonitorTable 1 }

SapTodMonitorEntry ::=
    SEQUENCE {
        sapCurrentIngressIpFilterId      TFilterID,
        sapCurrentIngressIpv6FilterId    TFilterID,
        sapCurrentIngressMacFilterId     TFilterID,
        sapCurrentIngressQosPolicyId     TSapIngressPolicyID,
        sapCurrentIngressQosSchedPlcy    ServObjName,
        sapCurrentEgressIpFilterId       TFilterID,
        sapCurrentEgressIpv6FilterId     TFilterID,
        sapCurrentEgressMacFilterId      TFilterID,
        sapCurrentEgressQosPolicyId      TSapEgressPolicyID,
        sapCurrentEgressQosSchedPlcy     ServObjName,
        sapIntendedIngressIpFilterId     TFilterID,
        sapIntendedIngressIpv6FilterId   TFilterID,
        sapIntendedIngressMacFilterId    TFilterID,
        sapIntendedIngressQosPolicyId    TSapIngressPolicyID,
        sapIntendedIngressQosSchedPlcy   ServObjName,
        sapIntendedEgressIpFilterId      TFilterID,
        sapIntendedEgressIpv6FilterId    TFilterID,
        sapIntendedEgressMacFilterId     TFilterID,
        sapIntendedEgressQosPolicyId     TSapEgressPolicyID,
        sapIntendedEgressQosSchedPlcy    ServObjName
    }

sapCurrentIngressIpFilterId OBJECT-TYPE
    SYNTAX          TFilterID
    MAX-ACCESS      read-only
    STATUS          current
    DESCRIPTION     "The value of the object sapCurrentIngressIpFilterId
                     indicates the index in the tIPFilterTable corresponding to
                     the ingress filter applied on this SAP, or zero if no
                     filter is currently active.
                     The active filter may deviate from sapIngressIpFilterId in
                     case it is overruled by a ToD Suite policy."
    ::= { sapTodMonitorEntry 1 }

sapCurrentIngressIpv6FilterId OBJECT-TYPE
    SYNTAX          TFilterID
    MAX-ACCESS      read-only
    STATUS          current
    DESCRIPTION     "The value of the object sapCurrentIngressIpv6FilterId
                     indicates the index in the tIPv6FilterTable corresponding
                     to the ingress Ipv6 filter applied on this SAP, or zero if
                     no filter is currently active.
                     The active filter may deviate from sapIngressIpv6FilterId
                     in case it is overruled by a ToD Suite policy."
    ::= { sapTodMonitorEntry 2 }

sapCurrentIngressMacFilterId OBJECT-TYPE
    SYNTAX          TFilterID
    MAX-ACCESS      read-only
    STATUS          current
    DESCRIPTION     "The value of the object sapCurrentIngressMacFilterId
                     indicates the index in the tMacFilterTable corresponding
                     to the ingress Mac filter applied on this SAP, or zero if
                     no filter is currently active.
                     The active filter may deviate from sapIngressMacFilterId
                     in case it is overruled by a ToD Suite policy."
    ::= { sapTodMonitorEntry 3 }

sapCurrentIngressQosPolicyId OBJECT-TYPE
    SYNTAX          TSapIngressPolicyID
    MAX-ACCESS      read-only
    STATUS          current
    DESCRIPTION     "The value of the object sapCurrentIngressQosPolicyId
                     indicates the index in the tSapIngressTable corresponding
                     to the ingress Qos Policy applied on this SAP, or zero if
                     no filter is currently active.
                     The active filter may deviate from sapIngressQosPolicyId
                     in case it is overruled by a ToD Suite policy."
    ::= { sapTodMonitorEntry 4 }

sapCurrentIngressQosSchedPlcy OBJECT-TYPE
    SYNTAX          ServObjName
    MAX-ACCESS      read-only
    STATUS          current
    DESCRIPTION     "The value of the object sapCurrentIngressQosSchedPlcy
                     indicates the ingress QoS scheduler on this SAP, or zero
                     if none is currently active.
                     The active policy may deviate from
                     sapIngressQosSchedulerPolicy in case it is overruled by a
                     ToD Suite policy defined on this SAP, or on the
                     multi-service this SAP belongs to. "
    ::= { sapTodMonitorEntry 5 }

sapCurrentEgressIpFilterId OBJECT-TYPE
    SYNTAX          TFilterID
    MAX-ACCESS      read-only
    STATUS          current
    DESCRIPTION     "The value of the object sapCurrentEgressIpFilterId
                     indicates the index in the tIPFilterTable corresponding to
                     the Egress filter applied on this SAP, or zero if no
                     filter is currently active.
                     The active filter may deviate from sapEgressIpFilterId in
                     case it is overruled by a ToD Suite policy."
    ::= { sapTodMonitorEntry 6 }

sapCurrentEgressIpv6FilterId OBJECT-TYPE
    SYNTAX          TFilterID
    MAX-ACCESS      read-only
    STATUS          current
    DESCRIPTION     "The value of the object sapCurrentEgressIpv6FilterId
                     indicates the index in the tIPv6FilterTable corresponding
                     to the Egress Ipv6 filter applied on this SAP, or zero if
                     no filter is currently active.
                     The active filter may deviate from sapEgressIpv6FilterId
                     in case it is overruled by a ToD Suite policy."
    ::= { sapTodMonitorEntry 7 }

sapCurrentEgressMacFilterId OBJECT-TYPE
    SYNTAX          TFilterID
    MAX-ACCESS      read-only
    STATUS          current
    DESCRIPTION     "The value of the object sapCurrentEgressMacFilterId
                     indicates the index in the tMacFilterTable corresponding
                     to the Egress Mac filter applied on this SAP, or zero if
                     no filter is currently active.
                     The active filter may deviate from sapEgressMacFilterId in
                     case it is overruled by a ToD Suite policy."
    ::= { sapTodMonitorEntry 8 }

sapCurrentEgressQosPolicyId OBJECT-TYPE
    SYNTAX          TSapEgressPolicyID
    MAX-ACCESS      read-only
    STATUS          current
    DESCRIPTION     "The value of the object sapCurrentEgressQosPolicyId
                     indicates the index in the tSapEgressTable corresponding
                     to the Egress Qos Policy applied on this SAP, or zero if
                     no filter is currently active.
                     The active filter may deviate from sapEgressQosPolicyId in
                     case it is overruled by a ToD Suite policy."
    ::= { sapTodMonitorEntry 9 }

sapCurrentEgressQosSchedPlcy OBJECT-TYPE
    SYNTAX          ServObjName
    MAX-ACCESS      read-only
    STATUS          current
    DESCRIPTION     "The value of the object sapCurrentEgressQosSchedPlcy
                     indicates the Egress QoS scheduler on this SAP, or zero if
                     none is currently active.
                     The active policy may deviate from
                     sapEgressQosSchedulerPolicy in case it is overruled by a
                     ToD Suite policy defined on this SAP, or on the
                     multi-customer this SAP belongs to."
    ::= { sapTodMonitorEntry 10 }

sapIntendedIngressIpFilterId OBJECT-TYPE
    SYNTAX          TFilterID
    MAX-ACCESS      read-only
    STATUS          current
    DESCRIPTION     "The value of the object sapIntendedIngressIpFilterId
                     indicates the index in the tIPFilterTable corresponding
                     to the ingress IP filter that should be applied on
                     this SAP.
                     If it deviates from sapCurrentIngressIpFilterId, this
                     means that there was a problem when trying to activate
                     this filter. It can only deviate when using ToD Suites
                     for the SAP. When the ToD Suites decides that a new
                     filter must be applied, it will try to do this. If it
                     fails, the current and intended field are not equal."
    ::= { sapTodMonitorEntry 11 }

sapIntendedIngressIpv6FilterId OBJECT-TYPE
    SYNTAX          TFilterID
    MAX-ACCESS      read-only
    STATUS          current
    DESCRIPTION     "The value of the object sapIntendedIngressIpv6FilterId
                     indicates the index in the tIPv6FilterTable corresponding
                     to the ingress Ipv6 filter that should be applied on this
                     SAP.
                     If it deviates from sapCurrentIngressIpv6FilterId, this
                     means that there was a problem when trying to activate
                     this filter. It can only deviate when using ToD Suites
                     for the SAP. When the ToD Suites decides that a new
                     filter must be applied, it will try to do this. If it
                     fails, the current and intended field are not equal."
    ::= { sapTodMonitorEntry 12 }

sapIntendedIngressMacFilterId OBJECT-TYPE
    SYNTAX          TFilterID
    MAX-ACCESS      read-only
    STATUS          current
    DESCRIPTION     "The value of the object sapIntendedIngressMacFilterId
                     indicates the index in the tMacFilterTable corresponding
                     to the ingress Mac filter that should be applied
                     on this SAP.
                     If it deviates from sapCurrentIngressMacFilterId, this
                     means that there was a problem when trying to activate
                     this filter. It can only deviate when using ToD Suites for
                     the SAP. When the ToD Suites decides that a new filter
                     must be applied, it will try to do this. If it fails,
                     the current and intended field are not equal."
    ::= { sapTodMonitorEntry 13 }

sapIntendedIngressQosPolicyId OBJECT-TYPE
    SYNTAX          TSapIngressPolicyID
    MAX-ACCESS      read-only
    STATUS          current
    DESCRIPTION     "The value of the object sapIntendedIngressQosPolicyId
                     indicates the index in the tSapIngressTable corresponding
                     to the ingress Qos policy that should be applied
                     on this SAP.
                     If it deviates from sapCurrentIngressQosPolicyId, this
                     means that there was a problem when trying to activate
                     this filter. It can only deviate when using ToD Suites for
                     the SAP. When the ToD Suites decides that a new filter
                     must be applied, it will try to do this. If it fails, the
                     current and intended field are not equal."
    ::= { sapTodMonitorEntry 14 }

sapIntendedIngressQosSchedPlcy OBJECT-TYPE
    SYNTAX          ServObjName
    MAX-ACCESS      read-only
    STATUS          current
    DESCRIPTION     "The value of the object sapIntendedIngressQosSchedPlcy
                     indicates the ingress QoS scheduler that should be applied
                     on this SAP.
                     If it deviates from sapCurrentIngressQosSchedPlcy, this
                     means that there was a problem when trying to activate
                     this filter. It can only deviate when using ToD Suites for
                     the SAP. When the ToD Suites decides that a new filter
                     must be applied, it will try to do this. If it fails,
                     the current and intended field are not equal."
    ::= { sapTodMonitorEntry 15 }

sapIntendedEgressIpFilterId OBJECT-TYPE
    SYNTAX          TFilterID
    MAX-ACCESS      read-only
    STATUS          current
    DESCRIPTION     "The value of the object sapIntendedEgressIpFilterId
                     indicates the index in the tIPFilterTable corresponding to
                     the Egress IP filter scheduler that should be applied on
                     this SAP.
                     If it deviates from sapCurrentEgressIpFilterId, this
                     means that there was a problem when trying to activate
                     this filter. It can only deviate when using ToD Suites for
                     the SAP. When the ToD Suites decides that a new filter
                     must be applied, it will try to do this. If it fails,
                     the current and intended field are not equal."
    ::= { sapTodMonitorEntry 16 }

sapIntendedEgressIpv6FilterId OBJECT-TYPE
    SYNTAX          TFilterID
    MAX-ACCESS      read-only
    STATUS          current
    DESCRIPTION     "The value of the object sapIntendedEgressIpv6FilterId
                     indicates the index in the tIPv6FilterTable corresponding
                     to the Egress IPv6 filter scheduler that should be applied
                     on this SAP.
                     If it deviates from sapCurrentEgressIpv6FilterId, this
                     means that there was a problem when trying to activate
                     this filter. It can only deviate when using ToD Suites for
                     the SAP. When the ToD Suites decides that a new filter
                     must be applied, it will try to do this. If it fails,
                     the current and intended field are not equal."
    ::= { sapTodMonitorEntry 17 }

sapIntendedEgressMacFilterId OBJECT-TYPE
    SYNTAX          TFilterID
    MAX-ACCESS      read-only
    STATUS          current
    DESCRIPTION     "The value of the object sapIntendedEgressMacFilterId
                     indicates the index in the tMacFilterTable corresponding
                     to the Egress mac filter scheduler that should be applied
                     on this SAP.
                     If it deviates from sapCurrentEgressMacFilterId, this
                     means that there was a problem when trying to activate
                     this filter. It can only deviate when using ToD Suites for
                     the SAP. When the ToD Suites decides that a new filter
                     must be applied, it will try to do this. If it fails,
                     the current and intended field are not equal."
    ::= { sapTodMonitorEntry 18 }

sapIntendedEgressQosPolicyId OBJECT-TYPE
    SYNTAX          TSapEgressPolicyID
    MAX-ACCESS      read-only
    STATUS          current
    DESCRIPTION     "The value of the object sapIntendedEgressQosPolicyId
                     indicates the index in the tSapEgressTable corresponding
                     to the Egress Qos Policy that should be applied
                     on this SAP.
                     If it deviates from sapCurrentEgressQosPolicyId, this
                     means that there was a problem when trying to activate
                     this filter. It can only deviate when using ToD Suites for
                     the SAP. When the ToD Suites decides that a new filter
                     must be applied, it will try to do this. If it fails,
                     the current and intended field are not equal."
    ::= { sapTodMonitorEntry 19 }

sapIntendedEgressQosSchedPlcy OBJECT-TYPE
    SYNTAX          ServObjName
    MAX-ACCESS      read-only
    STATUS          current
    DESCRIPTION     "The value of the object sapIntendedEgressQosSchedPlcy
                     indicates the index in the tSapEgressTable corresponding
                     to the Egress Qos Scheduler policy that should be applied
                     on this SAP.
                     If it deviates from sapCurrentEgressQosSchedPlcy, this
                     means that there was a problem when trying to activate
                     this filter. It can only deviate when using ToD Suites for
                     the SAP. When the ToD Suites decides that a new filter
                     must be applied, it will try to do this. If it fails,
                     the current and intended field are not equal."
    ::= { sapTodMonitorEntry 20 }

-- -------------------------------------------------
-- SAP Ingress Qos queue stats per Qos policy
-- -------------------------------------------------
sapIngrQosPlcyStatsTable OBJECT-TYPE
    SYNTAX          SEQUENCE OF SapIngrQosPlcyStatsEntry
    MAX-ACCESS      not-accessible
    STATUS          current
    DESCRIPTION     "A table that contains Ingress Qos policy related
                     statistics for a SAP."
    ::= { tmnxSapObjs 27 }

sapIngrQosPlcyStatsEntry OBJECT-TYPE
    SYNTAX          SapIngrQosPlcyStatsEntry
    MAX-ACCESS      not-accessible
    STATUS          current
    DESCRIPTION     "Statistics about a specific Ingress Qos Policy applied
                     on a specific SAP."
    INDEX           { svcId, sapPortId, sapEncapValue, sapIgQosPlcyId }
    ::= { sapIngrQosPlcyStatsTable 1 }

SapIngrQosPlcyStatsEntry ::=
    SEQUENCE {
        sapIgQosPlcyId                      TSapIngressPolicyID,
        sapIgQosPlcyDroppedHiPrioPackets    Counter64,
        sapIgQosPlcyDroppedHiPrioOctets     Counter64,
        sapIgQosPlcyDroppedLoPrioPackets    Counter64,
        sapIgQosPlcyDroppedLoPrioOctets     Counter64,
        sapIgQosPlcyForwardedInProfPackets  Counter64,
        sapIgQosPlcyForwardedInProfOctets   Counter64,
        sapIgQosPlcyForwardedOutProfPackets Counter64,
        sapIgQosPlcyForwardedOutProfOctets  Counter64
    }

sapIgQosPlcyId OBJECT-TYPE
    SYNTAX          TSapIngressPolicyID
    MAX-ACCESS      not-accessible
    STATUS          current
    DESCRIPTION     "The value of the object sapIgQosPlcyId indicates
                     the row index in the tSapIngressTable corresponding to this
                     ingress QoS policy, or one if no policy is specified."
    ::= { sapIngrQosPlcyStatsEntry 1 }

sapIgQosPlcyDroppedHiPrioPackets OBJECT-TYPE
    SYNTAX          Counter64
    MAX-ACCESS      read-only
    STATUS          current
    DESCRIPTION     "The value of the object sapIgQosPlcyDroppedHiPrioPackets
                     indicates the number of high priority packets,
                     as determined by the SAP ingress QoS
                     policy, dropped by the Qchip due to:
                     MBS exceeded, buffer pool limit exceeded, etc."
    ::= { sapIngrQosPlcyStatsEntry 2 }

sapIgQosPlcyDroppedHiPrioOctets OBJECT-TYPE
    SYNTAX          Counter64
    MAX-ACCESS      read-only
    STATUS          current
    DESCRIPTION     "The value of the object sapIgQosPlcyDroppedHiPrioOctets
                     indicates the number of high priority octets,
                     as determined by the SAP ingress QoS
                     policy, dropped by the Qchip due to:
                     MBS exceeded, buffer pool limit exceeded, etc."
    ::= { sapIngrQosPlcyStatsEntry 3 }

sapIgQosPlcyDroppedLoPrioPackets OBJECT-TYPE
    SYNTAX          Counter64
    MAX-ACCESS      read-only
    STATUS          current
    DESCRIPTION     "The value of the object sapIgQosPlcyDroppedLoPrioPackets
                     indicates the number of low priority packets,
                     as determined by the SAP ingress QoS
                     policy, dropped by the Qchip due to:
                     MBS exceeded, buffer pool limit exceeded, etc."
    ::= { sapIngrQosPlcyStatsEntry 4 }

sapIgQosPlcyDroppedLoPrioOctets OBJECT-TYPE
    SYNTAX          Counter64
    MAX-ACCESS      read-only
    STATUS          current
    DESCRIPTION     "The value of the object sapIgQosPlcyDroppedLoPrioOctets
                     indicates the number of low priority octets,
                     as determined by the SAP ingress QoS
                     policy, dropped by the Qchip due to:
                     MBS exceeded, buffer pool limit exceeded, etc."
    ::= { sapIngrQosPlcyStatsEntry 5 }

sapIgQosPlcyForwardedInProfPackets OBJECT-TYPE
    SYNTAX          Counter64
    MAX-ACCESS      read-only
    STATUS          current
    DESCRIPTION     "The value of the object sapIgQosPlcyForwardedInProfPackets
                     indicates the number of in-profile packets
                     (rate below CIR) forwarded by the ingress Qchip."
    ::= { sapIngrQosPlcyStatsEntry 6 }

sapIgQosPlcyForwardedInProfOctets OBJECT-TYPE
    SYNTAX          Counter64
    MAX-ACCESS      read-only
    STATUS          current
    DESCRIPTION     "The value of the object sapIgQosPlcyForwardedInProfOctets
                     indicates the number of in-profile octets
                     (rate below CIR) forwarded by the ingress Qchip."
    ::= { sapIngrQosPlcyStatsEntry 7 }

sapIgQosPlcyForwardedOutProfPackets OBJECT-TYPE
    SYNTAX          Counter64
    MAX-ACCESS      read-only
    STATUS          current
    DESCRIPTION     "The value of the object sapIgQosPlcyForwardedOutProfPackets
                     indicates the number of out-of-profile packets
                     (rate above CIR) forwarded by the ingress Qchip."
    ::= { sapIngrQosPlcyStatsEntry 8 }

sapIgQosPlcyForwardedOutProfOctets OBJECT-TYPE
    SYNTAX          Counter64
    MAX-ACCESS      read-only
    STATUS          current
    DESCRIPTION     "The value of the object sapIgQosPlcyForwardedOutProfOctets
                     indicates the number of out-of-profile octets
                     (rate above CIR) forwarded by the ingress Qchip."
    ::= { sapIngrQosPlcyStatsEntry 9 }

-- -------------------------------------------------
-- SAP Egress Qos queue stats per Qos policy
-- -------------------------------------------------
sapEgrQosPlcyStatsTable OBJECT-TYPE
    SYNTAX          SEQUENCE OF SapEgrQosPlcyStatsEntry
    MAX-ACCESS      not-accessible
    STATUS          current
    DESCRIPTION     "A table that contains Egress Qos policy related
                     statistics for a SAP."
    ::= { tmnxSapObjs 28 }

sapEgrQosPlcyStatsEntry OBJECT-TYPE
    SYNTAX          SapEgrQosPlcyStatsEntry
    MAX-ACCESS      not-accessible
    STATUS          current
    DESCRIPTION     "Statistics about a specific Egress Qos Policy applied
                     on a specific SAP."
    INDEX           { svcId, sapPortId, sapEncapValue, sapEgQosPlcyId }
    ::= { sapEgrQosPlcyStatsTable 1 }

SapEgrQosPlcyStatsEntry ::=
    SEQUENCE {
        sapEgQosPlcyId                      TSapEgressPolicyID,
        sapEgQosPlcyDroppedInProfPackets    Counter64,
        sapEgQosPlcyDroppedInProfOctets     Counter64,
        sapEgQosPlcyDroppedOutProfPackets   Counter64,
        sapEgQosPlcyDroppedOutProfOctets    Counter64,
        sapEgQosPlcyForwardedInProfPackets  Counter64,
        sapEgQosPlcyForwardedInProfOctets   Counter64,
        sapEgQosPlcyForwardedOutProfPackets Counter64,
        sapEgQosPlcyForwardedOutProfOctets  Counter64
    }

sapEgQosPlcyId OBJECT-TYPE
    SYNTAX          TSapEgressPolicyID
    MAX-ACCESS      not-accessible
    STATUS          current
    DESCRIPTION     "The value of the object sapEgQosPlcyId indicates
                     the row index in the tSapEgressTable corresponding to this
                     egress QoS policy, or one if no policy is specified."
    ::= { sapEgrQosPlcyStatsEntry 1 }

sapEgQosPlcyDroppedInProfPackets OBJECT-TYPE
    SYNTAX          Counter64
    MAX-ACCESS      read-only
    STATUS          current
    DESCRIPTION     "The value of the object sapEgQosPlcyDroppedInProfPackets
                     indicates the number of in-profile packets,
                     as determined by the SAP egress QoS
                     policy, dropped by the Qchip due to:
                     MBS exceeded, buffer pool limit exceeded, etc."
    ::= { sapEgrQosPlcyStatsEntry 2 }

sapEgQosPlcyDroppedInProfOctets OBJECT-TYPE
    SYNTAX          Counter64
    MAX-ACCESS      read-only
    STATUS          current
    DESCRIPTION     "The value of the object sapEgQosPlcyDroppedInProfOctets
                     indicates the number of in-profile octets,
                     as determined by the SAP egress QoS
                     policy, dropped by the Qchip due to:
                     MBS exceeded, buffer pool limit exceeded, etc."
    ::= { sapEgrQosPlcyStatsEntry 3 }

sapEgQosPlcyDroppedOutProfPackets OBJECT-TYPE
    SYNTAX          Counter64
    MAX-ACCESS      read-only
    STATUS          current
    DESCRIPTION     "The value of the object sapEgQosPlcyDroppedOutProfPackets
                     indicates the number of out-profile packets,
                     as determined by the SAP egress QoS
                     policy, dropped by the Qchip due to:
                     MBS exceeded, buffer pool limit exceeded, etc."
    ::= { sapEgrQosPlcyStatsEntry 4 }

sapEgQosPlcyDroppedOutProfOctets OBJECT-TYPE
    SYNTAX          Counter64
    MAX-ACCESS      read-only
    STATUS          current
    DESCRIPTION     "The value of the object sapEgQosPlcyDroppedOutProfOctets
                     indicates the number of out-profile octets,
                     as determined by the SAP egress QoS
                     policy, dropped by the Qchip due to:
                     MBS exceeded, buffer pool limit exceeded, etc."
    ::= { sapEgrQosPlcyStatsEntry 5 }

sapEgQosPlcyForwardedInProfPackets OBJECT-TYPE
    SYNTAX          Counter64
    MAX-ACCESS      read-only
    STATUS          current
    DESCRIPTION     "The value of the object sapEgQosPlcyForwardedInProfPackets
                     indicates the number of in-profile packets
                     (rate below CIR) forwarded by the egress Qchip."
    ::= { sapEgrQosPlcyStatsEntry 6 }

sapEgQosPlcyForwardedInProfOctets OBJECT-TYPE
    SYNTAX          Counter64
    MAX-ACCESS      read-only
    STATUS          current
    DESCRIPTION     "The value of the object sapEgQosPlcyForwardedInProfOctets
                     indicates the number of in-profile octets
                     (rate below CIR) forwarded by the egress Qchip."
    ::= { sapEgrQosPlcyStatsEntry 7 }

sapEgQosPlcyForwardedOutProfPackets OBJECT-TYPE
    SYNTAX          Counter64
    MAX-ACCESS      read-only
    STATUS          current
    DESCRIPTION     "The value of the object sapEgQosPlcyForwardedOutProfPackets
                     indicates the number of out-of-profile packets
                     (rate above CIR) forwarded by the egress Qchip."
    ::= { sapEgrQosPlcyStatsEntry 8 }

sapEgQosPlcyForwardedOutProfOctets OBJECT-TYPE
    SYNTAX          Counter64
    MAX-ACCESS      read-only
    STATUS          current
    DESCRIPTION     "The value of the object sapEgQosPlcyForwardedOutProfOctets
                     indicates the number of out-of-profile octets
                     (rate above CIR) forwarded by the egress Qchip."
    ::= { sapEgrQosPlcyStatsEntry 9 }

-- ------------------------------------------
-- Ingress QoS Plcy Queue SAP Statistics Table
-- ------------------------------------------
sapIngQosPlcyQueueStatsTable OBJECT-TYPE
    SYNTAX          SEQUENCE OF SapIngQosPlcyQueueStatsEntry
    MAX-ACCESS      not-accessible
    STATUS          current
    DESCRIPTION     "A table that contains ingress QoS queue SAP
                     statistics, per Ingress QoS Policy the queue
                     was used by."
    ::= { tmnxSapObjs 29 }

sapIngQosPlcyQueueStatsEntry OBJECT-TYPE
    SYNTAX          SapIngQosPlcyQueueStatsEntry
    MAX-ACCESS      not-accessible
    STATUS          current
    DESCRIPTION     "Ingress statistics about a specific SAP's
                     QoS queue for a given Qos policy."
    INDEX           { svcId,
                      sapPortId,
                      sapEncapValue,
                      sapIgQosPlcyQueuePlcyId,
                      sapIgQosPlcyQueueId }
    ::= { sapIngQosPlcyQueueStatsTable 1 }

SapIngQosPlcyQueueStatsEntry ::=
    SEQUENCE {
        sapIgQosPlcyQueuePlcyId                       TSapIngressPolicyID,
        sapIgQosPlcyQueueId                           TSapIngQueueId,
        sapIgQosPlcyQueueStatsOfferedHiPrioPackets    Counter64,
        sapIgQosPlcyQueueStatsDroppedHiPrioPackets    Counter64,
        sapIgQosPlcyQueueStatsOfferedLoPrioPackets    Counter64,
        sapIgQosPlcyQueueStatsDroppedLoPrioPackets    Counter64,
        sapIgQosPlcyQueueStatsOfferedHiPrioOctets     Counter64,
        sapIgQosPlcyQueueStatsDroppedHiPrioOctets     Counter64,
        sapIgQosPlcyQueueStatsOfferedLoPrioOctets     Counter64,
        sapIgQosPlcyQueueStatsDroppedLoPrioOctets     Counter64,
        sapIgQosPlcyQueueStatsForwardedInProfPackets  Counter64,
        sapIgQosPlcyQueueStatsForwardedOutProfPackets Counter64,
        sapIgQosPlcyQueueStatsForwardedInProfOctets   Counter64,
        sapIgQosPlcyQueueStatsForwardedOutProfOctets  Counter64,
        sapIgQosPlcyQueueCustId                       TmnxCustId,
        sapIgQosPlcyQueueStatsUncoloredPacketsOffered Counter64,
        sapIgQosPlcyQueueStatsUncoloredOctetsOffered  Counter64
    }

sapIgQosPlcyQueuePlcyId OBJECT-TYPE
    SYNTAX          TSapIngressPolicyID
    MAX-ACCESS      not-accessible
    STATUS          current
    DESCRIPTION     "The value of the object sapIgQosPlcyQueuePlcyId indicates
                     the row index in the tSapIngressTable corresponding to
                     this ingress QoS policy."
    ::= { sapIngQosPlcyQueueStatsEntry 1 }

sapIgQosPlcyQueueId OBJECT-TYPE
    SYNTAX          TSapIngQueueId
    MAX-ACCESS      not-accessible
    STATUS          current
    DESCRIPTION     "The index of the ingress QoS queue of this SAP used by the
                     policy indicated by sapIgQosPlcyQueuePlcyId."
    ::= { sapIngQosPlcyQueueStatsEntry 2 }

sapIgQosPlcyQueueStatsOfferedHiPrioPackets OBJECT-TYPE
    SYNTAX          Counter64
    MAX-ACCESS      read-only
    STATUS          current
    DESCRIPTION     "The value of sapIgQosPlcyQueueStatsOfferedHiPrioPackets
                     indicates the number of high priority packets,
                     as determined by the SAP ingress QoS policy, offered by
                     the Pchip to the Qchip."
    ::= { sapIngQosPlcyQueueStatsEntry 3 }

sapIgQosPlcyQueueStatsDroppedHiPrioPackets OBJECT-TYPE
    SYNTAX          Counter64
    MAX-ACCESS      read-only
    STATUS          current
    DESCRIPTION     "The value of sapIgQosPlcyQueueStatsDroppedHiPrioPackets
                     indicates the number of high priority packets,
                     as determined by the SAP ingress QoS policy, dropped by
                     the Qchip due to: MBS exceeded, buffer pool limit
                     exceeded, etc."
    ::= { sapIngQosPlcyQueueStatsEntry 4 }

sapIgQosPlcyQueueStatsOfferedLoPrioPackets OBJECT-TYPE
    SYNTAX          Counter64
    MAX-ACCESS      read-only
    STATUS          current
    DESCRIPTION     "The value of sapIgQosPlcyQueueStatsOfferedLoPrioPackets
                     indicates the number of  low priority packets,
                     as determined by the SAP ingress QoS policy, offered by
                     the Pchip to the Qchip."
    ::= { sapIngQosPlcyQueueStatsEntry 5 }

sapIgQosPlcyQueueStatsDroppedLoPrioPackets OBJECT-TYPE
    SYNTAX          Counter64
    MAX-ACCESS      read-only
    STATUS          current
    DESCRIPTION     "The value of sapIgQosPlcyQueueStatsDroppedLoPrioPackets
                     indicates the number of low priority packets,
                     as determined by the SAP ingress QoS policy, dropped by
                     the Qchip due to: MBS exceeded, buffer pool limit
                     exceeded, etc."
    ::= { sapIngQosPlcyQueueStatsEntry 6 }

sapIgQosPlcyQueueStatsOfferedHiPrioOctets OBJECT-TYPE
    SYNTAX          Counter64
    MAX-ACCESS      read-only
    STATUS          current
    DESCRIPTION     "The value of sapIgQosPlcyQueueStatsOfferedHiPrioOctets
                     indicates the number of high priority octets,
                     as determined by the SAP ingress QoS policy, offered by
                     the Pchip to the Qchip."
    ::= { sapIngQosPlcyQueueStatsEntry 7 }

sapIgQosPlcyQueueStatsDroppedHiPrioOctets OBJECT-TYPE
    SYNTAX          Counter64
    MAX-ACCESS      read-only
    STATUS          current
    DESCRIPTION     "The value of sapIgQosPlcyQueueStatsDroppedHiPrioOctets
                     indicates the number ofhigh priority octets,
                     as determined by the SAP ingress QoS policy, dropped by
                     the Qchip due to: MBS exceeded, buffer pool limit
                     exceeded, etc."
    ::= { sapIngQosPlcyQueueStatsEntry 8 }

sapIgQosPlcyQueueStatsOfferedLoPrioOctets OBJECT-TYPE
    SYNTAX          Counter64
    MAX-ACCESS      read-only
    STATUS          current
    DESCRIPTION     "The value of sapIgQosPlcyQueueStatsOfferedLoPrioOctets
                     indicates the number of low priority octets,
                     as determined by the SAP ingress QoS policy, offered by
                     the Pchip to the Qchip."
    ::= { sapIngQosPlcyQueueStatsEntry 9 }

sapIgQosPlcyQueueStatsDroppedLoPrioOctets OBJECT-TYPE
    SYNTAX          Counter64
    MAX-ACCESS      read-only
    STATUS          current
    DESCRIPTION     "The value of sapIgQosPlcyQueueStatsDroppedLoPrioOctets
                     indicates the number of low priority octets,
                     as determined by the SAP ingress QoS policy, dropped by
                     the Qchip due to: MBS exceeded, buffer pool limit
                     exceeded, etc."
    ::= { sapIngQosPlcyQueueStatsEntry 10 }

sapIgQosPlcyQueueStatsForwardedInProfPackets OBJECT-TYPE
    SYNTAX          Counter64
    MAX-ACCESS      read-only
    STATUS          current
    DESCRIPTION     "The value of sapIgQosPlcyQueueStatsForwardedInProfPackets
                     indicates the number of in-profile packets
                     (rate below CIR) forwarded by the ingress Qchip."
    ::= { sapIngQosPlcyQueueStatsEntry 11 }

sapIgQosPlcyQueueStatsForwardedOutProfPackets OBJECT-TYPE
    SYNTAX          Counter64
    MAX-ACCESS      read-only
    STATUS          current
    DESCRIPTION     "The value of sapIgQosPlcyQueueStatsForwardedOutProfPackets
                     indicates the number of out-of-profile packets
                     (rate above CIR) forwarded by the ingress Qchip."
    ::= { sapIngQosPlcyQueueStatsEntry 12 }

sapIgQosPlcyQueueStatsForwardedInProfOctets OBJECT-TYPE
    SYNTAX          Counter64
    MAX-ACCESS      read-only
    STATUS          current
    DESCRIPTION     "The value of sapIgQosPlcyQueueStatsForwardedInProfOctets
                     indicates the number of in-profile octets
                     (rate below CIR) forwarded by the ingress Qchip."
    ::= { sapIngQosPlcyQueueStatsEntry 13 }

sapIgQosPlcyQueueStatsForwardedOutProfOctets OBJECT-TYPE
    SYNTAX          Counter64
    MAX-ACCESS      read-only
    STATUS          current
    DESCRIPTION     "The value of sapIgQosPlcyQueueStatsForwardedOutProfOctets
                     indicates the number of  out-of-profile octets
                     (rate above CIR) forwarded by the ingress Qchip."
    ::= { sapIngQosPlcyQueueStatsEntry 14 }

sapIgQosPlcyQueueCustId OBJECT-TYPE
    SYNTAX          TmnxCustId
    MAX-ACCESS      read-only
    STATUS          current
    DESCRIPTION     "The value of the object sapIgQosPlcyQueueCustId
                     indicates the Customer ID for the associated service."
    ::= { sapIngQosPlcyQueueStatsEntry 15 }

sapIgQosPlcyQueueStatsUncoloredPacketsOffered OBJECT-TYPE
    SYNTAX          Counter64
    MAX-ACCESS      read-only
    STATUS          current
    DESCRIPTION     "The value of sapIgQosPlcyQueueStatsUncoloredPacketsOffered
                     indicates the number of uncolored packets offered to
                     the ingress Qchip."
    ::= { sapIngQosPlcyQueueStatsEntry 16 }

sapIgQosPlcyQueueStatsUncoloredOctetsOffered OBJECT-TYPE
    SYNTAX          Counter64
    MAX-ACCESS      read-only
    STATUS          current
    DESCRIPTION     "The value of sapIgQosPlcyQueueStatsUncoloredOctetsOffered
                     indicates the number of uncolored octets offered to
                     the ingress Qchip."
    ::= { sapIngQosPlcyQueueStatsEntry 17 }

-- ------------------------------------------
-- Egress QoS Plcy Queue SAP Statistics Table
-- ------------------------------------------
sapEgrQosPlcyQueueStatsTable OBJECT-TYPE
    SYNTAX          SEQUENCE OF SapEgrQosPlcyQueueStatsEntry
    MAX-ACCESS      not-accessible
    STATUS          current
    DESCRIPTION     "A table that contains egress QoS queue SAP
                     statistics per Egress QoS Policy the queue
                     was used by."
    ::= { tmnxSapObjs 30 }

sapEgrQosPlcyQueueStatsEntry OBJECT-TYPE
    SYNTAX          SapEgrQosPlcyQueueStatsEntry
    MAX-ACCESS      not-accessible
    STATUS          current
    DESCRIPTION     "Egress statistics about a specific SAP's
                     QoS queue for a given Qos policy."
    INDEX           { svcId,
                      sapPortId,
                      sapEncapValue,
                      sapEgQosPlcyQueuePlcyId,
                      sapEgQosPlcyQueueId }
    ::= { sapEgrQosPlcyQueueStatsTable 1 }

SapEgrQosPlcyQueueStatsEntry ::=
    SEQUENCE {
        sapEgQosPlcyQueuePlcyId                       TSapEgressPolicyID,
        sapEgQosPlcyQueueId                           TSapEgrQueueId,
        sapEgQosPlcyQueueStatsForwardedInProfPackets  Counter64,
        sapEgQosPlcyQueueStatsDroppedInProfPackets    Counter64,
        sapEgQosPlcyQueueStatsForwardedOutProfPackets Counter64,
        sapEgQosPlcyQueueStatsDroppedOutProfPackets   Counter64,
        sapEgQosPlcyQueueStatsForwardedInProfOctets   Counter64,
        sapEgQosPlcyQueueStatsDroppedInProfOctets     Counter64,
        sapEgQosPlcyQueueStatsForwardedOutProfOctets  Counter64,
        sapEgQosPlcyQueueStatsDroppedOutProfOctets    Counter64,
        sapEgQosPlcyQueueCustId                       TmnxCustId
    }

sapEgQosPlcyQueuePlcyId OBJECT-TYPE
    SYNTAX          TSapEgressPolicyID
    MAX-ACCESS      not-accessible
    STATUS          current
    DESCRIPTION     "The row index in the tSapEgressTable
                     corresponding to this egress QoS policy."
    ::= { sapEgrQosPlcyQueueStatsEntry 1 }

sapEgQosPlcyQueueId OBJECT-TYPE
    SYNTAX          TSapEgrQueueId
    MAX-ACCESS      not-accessible
    STATUS          current
    DESCRIPTION     "The value of sapEgQosPlcyQueueId indicates
                     index of the egress QoS queue of this SAP."
    ::= { sapEgrQosPlcyQueueStatsEntry 2 }

sapEgQosPlcyQueueStatsForwardedInProfPackets OBJECT-TYPE
    SYNTAX          Counter64
    MAX-ACCESS      read-only
    STATUS          current
    DESCRIPTION     "The value of sapEgQosPlcyQueueStatsForwardedInProfPackets
                     indicates the number of in-profile packets (rate below
                     CIR) forwarded by the egress Qchip."
    ::= { sapEgrQosPlcyQueueStatsEntry 3 }

sapEgQosPlcyQueueStatsDroppedInProfPackets OBJECT-TYPE
    SYNTAX          Counter64
    MAX-ACCESS      read-only
    STATUS          current
    DESCRIPTION     "The value of sapEgQosPlcyQueueStatsDroppedInProfPackets
                     indicates the number of in-profile packets discarded by
                     the egress Qchip due to: MBS exceeded, buffer pool limit
                     exceeded, etc."
    ::= { sapEgrQosPlcyQueueStatsEntry 4 }

sapEgQosPlcyQueueStatsForwardedOutProfPackets OBJECT-TYPE
    SYNTAX          Counter64
    MAX-ACCESS      read-only
    STATUS          current
    DESCRIPTION     "The value of sapEgQosPlcyQueueStatsForwardedOutProfPackets
                     indicates the number of out-of-profile packets (rate
                     above CIR) forwarded by the egress Qchip."
    ::= { sapEgrQosPlcyQueueStatsEntry 5 }

sapEgQosPlcyQueueStatsDroppedOutProfPackets OBJECT-TYPE
    SYNTAX          Counter64
    MAX-ACCESS      read-only
    STATUS          current
    DESCRIPTION     "The value of sapEgQosPlcyQueueStatsDroppedOutProfPackets
                     indicates the number out-of-profile packets discarded by
                     the egress Qchip due to: MBS exceeded, buffer pool limit
                     exceeded, etc."
    ::= { sapEgrQosPlcyQueueStatsEntry 6 }

sapEgQosPlcyQueueStatsForwardedInProfOctets OBJECT-TYPE
    SYNTAX          Counter64
    MAX-ACCESS      read-only
    STATUS          current
    DESCRIPTION     "The value of sapEgQosPlcyQueueStatsForwardedInProfOctets
                     indicates the number ofin-profile octets (rate below CIR)
                     forwarded by the egress Qchip."
    ::= { sapEgrQosPlcyQueueStatsEntry 7 }

sapEgQosPlcyQueueStatsDroppedInProfOctets OBJECT-TYPE
    SYNTAX          Counter64
    MAX-ACCESS      read-only
    STATUS          current
    DESCRIPTION     "The value of sapEgQosPlcyQueueStatsDroppedInProfOctets
                     indicates the number in-profile octets discarded by the
                     egress Qchip due to: MBS exceeded, buffer pool limit
                     exceeded, etc."
    ::= { sapEgrQosPlcyQueueStatsEntry 8 }

sapEgQosPlcyQueueStatsForwardedOutProfOctets OBJECT-TYPE
    SYNTAX          Counter64
    MAX-ACCESS      read-only
    STATUS          current
    DESCRIPTION     "The value of sapEgQosPlcyQueueStatsForwardedOutProfOctets
                     indicates the number of out-of-profile octets (rate
                     above CIR) forwarded by the egress Qchip."
    ::= { sapEgrQosPlcyQueueStatsEntry 9 }

sapEgQosPlcyQueueStatsDroppedOutProfOctets OBJECT-TYPE
    SYNTAX          Counter64
    MAX-ACCESS      read-only
    STATUS          current
    DESCRIPTION     "The value of sapEgQosPlcyQueueStatsDroppedOutProfOctets
                     indicates the number out-of-profile octets discarded by
                     the egress Qchip due to: MBS exceeded, buffer pool limit
                     exceeded, etc."
    ::= { sapEgrQosPlcyQueueStatsEntry 10 }

sapEgQosPlcyQueueCustId OBJECT-TYPE
    SYNTAX          TmnxCustId
    MAX-ACCESS      read-only
    STATUS          current
    DESCRIPTION     "The value of the object sapEgQosPlcyQueueCustId indicates
                     the Customer ID for the associated service."
    ::= { sapEgrQosPlcyQueueStatsEntry 11 }

-- ----------------------------------------
-- SAP DHCP Information Table
-- ----------------------------------------
sapDhcpInfoTable OBJECT-TYPE
    SYNTAX          SEQUENCE OF SapDhcpInfoEntry
    MAX-ACCESS      not-accessible
    STATUS          current
    DESCRIPTION     "sapDhcpInfoTable contains DHCP information related to a
                     routed CO subscriber SAP.  This table complements
                     sapBaseInfoTable, and contains an entry for each
                     routed CO subscriber SAP. Rows in this table
                     are created and deleted automatically by the system."
    ::= { tmnxSapObjs 31 }

sapDhcpInfoEntry OBJECT-TYPE
    SYNTAX          SapDhcpInfoEntry
    MAX-ACCESS      not-accessible
    STATUS          current
    DESCRIPTION     "DHCP specific information for a routed CO subscriber SAP."
    INDEX           { svcId, sapPortId, sapEncapValue }
    ::= { sapDhcpInfoTable 1 }

SapDhcpInfoEntry ::=
    SEQUENCE {
        sapDhcpOperLeasePopulate  Unsigned32
    }

sapDhcpOperLeasePopulate OBJECT-TYPE
    SYNTAX          Unsigned32
    MAX-ACCESS      read-only
    STATUS          current
    DESCRIPTION     "The value of the object sapDhcpOperLeasePopulate
                     indicates the number of DHCP lease states currently
                     allocated on this SAP."
    ::= { sapDhcpInfoEntry 1 }

-- -------------------------------------------------
-- SAP Ingress QoS Scheduler Per-Policy Statistics Table
-- -------------------------------------------------
sapIngSchedPlcyStatsTable OBJECT-TYPE
    SYNTAX          SEQUENCE OF SapIngSchedPlcyStatsEntry
    MAX-ACCESS      not-accessible
    STATUS          current
    DESCRIPTION     "A table that contains ingress QoS queue
                     statistics for the SAP's, organized by
                     scheduler policy."
    ::= { tmnxSapObjs 32 }

sapIngSchedPlcyStatsEntry OBJECT-TYPE
    SYNTAX          SapIngSchedPlcyStatsEntry
    MAX-ACCESS      not-accessible
    STATUS          current
    DESCRIPTION     "Statistics about a specific SAP's ingress Qos Scheduler.
                     Entries are created when a scheduler policy of a SAP
                     is replaced with another one due to Time-Of-Day policies."
    INDEX           { svcId, sapPortId, sapEncapValue, tSchedulerPolicyName,
                      IMPLIED sapIngQosSchedName }
    ::= { sapIngSchedPlcyStatsTable 1 }

SapIngSchedPlcyStatsEntry ::=
    SEQUENCE {
        sapIngSchedPlcyStatsFwdPkt    Counter64,
        sapIngSchedPlcyStatsFwdOct    Counter64
    }

sapIngSchedPlcyStatsFwdPkt OBJECT-TYPE
    SYNTAX          Counter64
    MAX-ACCESS      read-only
    STATUS          current
    DESCRIPTION     "The number of forwarded packets, as
                     determined by the SAP ingress scheduler
                     policy, offered by the Pchip to the
                     Qchip."
    ::= { sapIngSchedPlcyStatsEntry 1 }

sapIngSchedPlcyStatsFwdOct OBJECT-TYPE
    SYNTAX          Counter64
    MAX-ACCESS      read-only
    STATUS          current
    DESCRIPTION     "The number of forwarded octets, as
                     determined by the SAP ingress scheduler
                     policy, offered by the Pchip to the
                     Qchip."
    ::= { sapIngSchedPlcyStatsEntry 2 }

-- ---------------------------------------------
-- SAP Egress QoS Scheduler Per-Policy Statistics Table
-- ---------------------------------------------
sapEgrSchedPlcyStatsTable OBJECT-TYPE
    SYNTAX          SEQUENCE OF SapEgrSchedPlcyStatsEntry
    MAX-ACCESS      not-accessible
    STATUS          current
    DESCRIPTION     "A table that contains egress QoS scheduler
                     statistics for the SAP's, organized by
                     scheduler policy."
    ::= { tmnxSapObjs 33 }

sapEgrSchedPlcyStatsEntry OBJECT-TYPE
    SYNTAX          SapEgrSchedPlcyStatsEntry
    MAX-ACCESS      not-accessible
    STATUS          current
    DESCRIPTION     "Statistics about a specific SAP's egress QoS scheduler.
                     Entries are created when a scheduler policy of a SAP
                     is replaced with another one due to Time-Of-Day policies."
    INDEX           { svcId, sapPortId, sapEncapValue, tSchedulerPolicyName,
                      IMPLIED sapEgrQosSchedName }
    ::= { sapEgrSchedPlcyStatsTable 1 }

SapEgrSchedPlcyStatsEntry ::=
    SEQUENCE {
        sapEgrSchedPlcyStatsFwdPkt    Counter64,
        sapEgrSchedPlcyStatsFwdOct    Counter64
    }

sapEgrSchedPlcyStatsFwdPkt OBJECT-TYPE
    SYNTAX          Counter64
    MAX-ACCESS      read-only
    STATUS          current
    DESCRIPTION     "The number of packets forwarded by the
                     egress Qchip, as determined by the SAP
                     egress scheduler policy."
    ::= { sapEgrSchedPlcyStatsEntry 1 }

sapEgrSchedPlcyStatsFwdOct OBJECT-TYPE
    SYNTAX          Counter64
    MAX-ACCESS      read-only
    STATUS          current
    DESCRIPTION     "The number of octets forwarded by the
                     egress Qchip, as determined by the SAP
                     egress scheduler policy."
    ::= { sapEgrSchedPlcyStatsEntry 2 }
-- --------------------------------------------
-- SAP Ingress QoS Scheduler Per-Policy Statistics Table
-- with specific Port ID
-- --------------------------------------------
sapIngSchedPlcyPortStatsTable OBJECT-TYPE
    SYNTAX          SEQUENCE OF SapIngSchedPlcyPortStatsEntry
    MAX-ACCESS      not-accessible
    STATUS          current
    DESCRIPTION
        "The sapIngSchedPlcyPortStatsTable contains
         ingress QoS scheduler statistics for the SAP's, organized per
         scheduler policy and per port. This table is used when the SAP
         is  a CCAG or LAG in 'link' mode, or an APS.
         Entries are created when a scheduler policy of a SAP
         is replaced with another one due to Time-Of-Day policies."
    ::= { tmnxSapObjs 34 }

sapIngSchedPlcyPortStatsEntry OBJECT-TYPE
    SYNTAX          SapIngSchedPlcyPortStatsEntry
    MAX-ACCESS      not-accessible
    STATUS          current
    DESCRIPTION     "Statistics about a specific SAP's ingress Qos Scheduler.
                     Entries are created when a scheduler policy of a SAP
                     is replaced with another one due to Time-Of-Day policies."
    INDEX           { svcId, sapPortId, sapEncapValue, tSchedulerPolicyName,
                      tVirtualSchedulerName, sapPortIdIngPortId }
    ::= { sapIngSchedPlcyPortStatsTable 1 }

SapIngSchedPlcyPortStatsEntry ::=
    SEQUENCE {
        sapIngSchedPlcyPortStatsPort   TmnxPortID,
        sapIngSchedPlcyPortStatsFwdPkt Counter64,
        sapIngSchedPlcyPortStatsFwdOct Counter64
    }

sapIngSchedPlcyPortStatsPort OBJECT-TYPE
    SYNTAX          TmnxPortID
    MAX-ACCESS      read-only   -- not-accessible
    STATUS          current
    DESCRIPTION     "The value of sapIngSchedPlcyPortStatsPort is used
                     as an index of the ingress QoS scheduler of this SAP. When
                     the SAP is an aps/ccag/lag in 'link' mode, this object is
                     the TmnxPortID of the member-port on which the scheduler is
                     applied."
    ::= {sapIngSchedPlcyPortStatsEntry 1 }

sapIngSchedPlcyPortStatsFwdPkt OBJECT-TYPE
    SYNTAX          Counter64
    MAX-ACCESS      read-only
    STATUS          current
    DESCRIPTION     "The value of sapIngSchedPlcyPortStatsFwdPkt indicates
                     the number of forwarded packets, as determined by the SAP
                     ingress scheduler policy, offered by the Pchip to the
                     Qchip."
    ::= { sapIngSchedPlcyPortStatsEntry 2 }

sapIngSchedPlcyPortStatsFwdOct OBJECT-TYPE
    SYNTAX          Counter64
    MAX-ACCESS      read-only
    STATUS          current
    DESCRIPTION     "The value of sapIngSchedPlcyPortStatsFwdOct indicates
                     the number of forwarded octets,as determined by the SAP
                     ingress scheduler policy, offered by the Pchip to the
                     Qchip."
    ::= { sapIngSchedPlcyPortStatsEntry 3 }


-- ------------------------------------------------------------
-- SAP Egress QoS Scheduler Per-Policy Statistics Table
-- with specific Port ID
-- ------------------------------------------------------------
sapEgrSchedPlcyPortStatsTable OBJECT-TYPE
    SYNTAX          SEQUENCE OF SapEgrSchedPlcyPortStatsEntry
    MAX-ACCESS      not-accessible
    STATUS          current
    DESCRIPTION
        "The sapEgrSchedPlcyPortStatsTable contains
         egress QoS scheduler statistics for the SAP's, organized per
         scheduler policy and per port. This table is used when the SAP
         is  a CCAG or LAG in 'link' mode, or an APS.
         Entries are created when a scheduler policy of a SAP
         is replaced with another one due to Time-Of-Day policies."
    ::= { tmnxSapObjs 35 }

sapEgrSchedPlcyPortStatsEntry OBJECT-TYPE
    SYNTAX          SapEgrSchedPlcyPortStatsEntry
    MAX-ACCESS      not-accessible
    STATUS          current
    DESCRIPTION     "Statistics about a specific SAP's egress Qos Scheduler.
                     Entries are created when a scheduler policy of a SAP
                     is replaced with another one due to Time-Of-Day policies."
    INDEX           { svcId, sapPortId, sapEncapValue, tSchedulerPolicyName,
                      tVirtualSchedulerName, sapPortIdEgrPortId }
    ::= { sapEgrSchedPlcyPortStatsTable 1 }

SapEgrSchedPlcyPortStatsEntry ::=
    SEQUENCE {
        sapEgrSchedPlcyPortStatsPort   TmnxPortID,
        sapEgrSchedPlcyPortStatsFwdPkt Counter64,
        sapEgrSchedPlcyPortStatsFwdOct Counter64
    }

sapEgrSchedPlcyPortStatsPort OBJECT-TYPE
    SYNTAX          TmnxPortID
    MAX-ACCESS      read-only   -- not-accessible
    STATUS          current
    DESCRIPTION     "The value of sapEgrSchedPlcyPortStatsPort is used
                     as an index of the egress QoS scheduler of this SAP. When
                     the SAP is an aps/ccag/lag in 'link' mode, this object is
                     the TmnxPortID of the member-port on which the scheduler is
                     applied."
    ::= {sapEgrSchedPlcyPortStatsEntry 1 }

sapEgrSchedPlcyPortStatsFwdPkt OBJECT-TYPE
    SYNTAX          Counter64
    MAX-ACCESS      read-only
    STATUS          current
    DESCRIPTION     "The value of sapEgrSchedPlcyPortStatsFwdPkt indicates
                     the number of forwarded packets, as determined by the SAP
                     egress scheduler policy, offered by the Pchip to the
                     Qchip."
    ::= { sapEgrSchedPlcyPortStatsEntry 2 }

sapEgrSchedPlcyPortStatsFwdOct OBJECT-TYPE
    SYNTAX          Counter64
    MAX-ACCESS      read-only
    STATUS          current
    DESCRIPTION     "The value of sapEgrSchedPlcyPortStatsFwdOct indicates
                     the number of forwarded octets,as determined by the SAP
                     egress scheduler policy, offered by the Pchip to the
                     Qchip."
    ::= { sapEgrSchedPlcyPortStatsEntry 3 }


-- ---------------------------------------------------------------------
--  CEM SAP Information Table
--
--  Sparse Dependent Extention of the sapBaseInfoTable.
--
--  The same indexes are used for both the base table, sapBaseInfoTable,
--  and the sparse dependent table, sapCemInfoTable.
--
--  This in effect extends the sapBaseInfoTable with additional columns.
--  Rows are created in the sapCemInfoTable only for those entries
--  in the sapBaseInfoTable that are created on a port with 'cemEncap'
--  encapsulation.
--
--  Deletion of a row in the sapBaseInfoTable results in the
--  same fate for the row in the sapCemInfoTable.
-- ---------------------------------------------------------------------
sapCemInfoTable OBJECT-TYPE
    SYNTAX          SEQUENCE OF SapCemInfoEntry
    MAX-ACCESS      not-accessible
    STATUS          current
    DESCRIPTION     "A table that contains CEM SAP information."
    ::= { tmnxSapObjs 40 }

sapCemInfoEntry OBJECT-TYPE
    SYNTAX          SapCemInfoEntry
    MAX-ACCESS      not-accessible
    STATUS          current
    DESCRIPTION     "Information about a specific CEM SAP."
    INDEX           { svcId, sapPortId, sapEncapValue }
    ::= { sapCemInfoTable 1 }

SapCemInfoEntry ::=
    SEQUENCE {
        sapCemLastMgmtChange            TimeStamp,
        sapCemEndpointType              INTEGER,
        sapCemBitrate                   Unsigned32,
        sapCemCasTrunkFraming           TdmOptionsCasTrunkFraming,
        sapCemPayloadSize               Unsigned32,
        sapCemJitterBuffer              Unsigned32,
        sapCemUseRtpHeader              TruthValue,
        sapCemDifferential              TruthValue,
        sapCemTimestampFreq             Unsigned32,
        sapCemReportAlarm               CemSapReportAlarm,
        sapCemReportAlarmStatus         CemSapReportAlarm,
        sapCemLocalEcid                 CemSapEcid,
        sapCemRemoteMacAddr             MacAddress,
        sapCemRemoteEcid                CemSapEcid
  }

sapCemLastMgmtChange OBJECT-TYPE
    SYNTAX          TimeStamp
    MAX-ACCESS      read-only
    STATUS          current
    DESCRIPTION     "The value of the object sapCemLastMgmtChange indicates
                     the value of sysUpTime at the time of the most recent
                     management-initiated change to this CEM SAP information."
    ::= { sapCemInfoEntry 1 }

sapCemEndpointType   OBJECT-TYPE
    SYNTAX           INTEGER {
                         unstructuredE1 (1),
                         unstructuredT1 (2),
                         unstructuredE3 (3),
                         unstructuredT3 (4),
                         nxDS0          (5),
                         nxDS0WithCas   (6)
                     }
    MAX-ACCESS       read-only
    STATUS           current
    DESCRIPTION      "This object indicates the CEM SAP endpoint type."
    ::= { sapCemInfoEntry 2 }

sapCemBitrate        OBJECT-TYPE
    SYNTAX           Unsigned32 (0..699)
    UNITS            "64 Kbits/s"
    MAX-ACCESS       read-only
    STATUS           current
    DESCRIPTION      "This object indicates the bit-rate in multiples of
                      64 Kbit/s of the CEM SAP."
    ::= { sapCemInfoEntry 3 }

sapCemCasTrunkFraming  OBJECT-TYPE
    SYNTAX           TdmOptionsCasTrunkFraming
    MAX-ACCESS       read-only
    STATUS           current
    DESCRIPTION      "This object indicates the CAS trunk framing mode of
                      the CEM SAP."
    ::= { sapCemInfoEntry 4 }

sapCemPayloadSize   OBJECT-TYPE
    SYNTAX           Unsigned32 (0|16..2048)
    UNITS            "bytes"
    MAX-ACCESS       read-write
    STATUS           current
    DESCRIPTION      "This object specifies the payload size (in bytes) of
                      packets transmitted to the Packet Service Network (PSN)
                      by the CEM SAP.  This determines the size of the data
                      that will be transmitted over the service.  As well,
                      if the size of the data received is not consistent with
                      the payload size then the packet is considered malformed.

                      Default value depends on the CEM SAP endpoint type
                      (sapCemEndpointType), and if applicable, the number of
                      timeslots (sapCemBitrate):
                      ---------------------------------------------------------
                      | Endpoint Type      | Timeslots | Default payload size |
                      ---------------------+-----------+-----------------------
                      | 'unstructuredE1'   | n/a       |    256 bytes         |
                      ---------------------+-----------+-----------------------
                      | 'unstructuredT1'   | n/a       |    192 bytes         |
                      ---------------------+-----------+-----------------------
                      | 'unstructuredE3'   | n/a       |   1024 bytes         |
                      ---------------------+-----------+-----------------------
                      | 'unstructuredT3'   | n/a       |   1024 bytes         |
                      ---------------------+-----------+-----------------------
                      | 'nxDS0' (E1/T1)    | N = 1     |     64 bytes         |
                      |                    +-----------+-----------------------
                      |                    | N = 2..4  | N x 32 bytes         |
                      |                    +-----------+-----------------------
                      |                    | N = 5..15 | N x 16 bytes         |
                      |                    +-----------+-----------------------
                      |                    | N >= 16   | N x  8 bytes         |
                      ---------------------+-----------+-----------------------
                      | 'nxDS0WithCas' (E1)| N         | N x 16 bytes         |
                      ---------------------+-----------+-----------------------
                      | 'nxDS0WithCas' (T1)| N         | N x 24 bytes         |
                      ---------------------------------------------------------

                      For all endpoint types except for 'nxDS0WithCas',
                      valid payload size range is from the default (in the
                      table above) to 2048 bytes.

                      For 'nxDS0WithCas', sapCemPayloadSize divide by the
                      number of timeslots (sapCemBitrate) must be an integer
                      factor of the number of frames per trunk multiframe (i.e.
                      16 for E1 trunk and 24 for T1 trunk).

                      For '1xDS0', sapCemPayloadSize must be a multiple of 2.

                      For 'NxDS0', where N > 1, sapCemPayloadSize must be a
                      multiple of the number of timeslots (sapCemBitrate).

                      For 'unstructuredE1', 'unstructuredT1', 'unstructuredE3'
                      and 'unstructuredT3', sapCemPayloadSize must be a
                      multiple of 32 bytes.

                      Configuring sapCemPayloadSize and sapCemJitterBuffer to
                      values that result in less than 2 packet buffers or
                      greater than 32 packet buffer is not allowed.

                      Setting this object to 0 sets it back to the default
                      value."
    ::= { sapCemInfoEntry 5 }

sapCemJitterBuffer   OBJECT-TYPE
    SYNTAX           Unsigned32 (0|1..250)
    UNITS            "milliseconds"
    MAX-ACCESS       read-write
    STATUS           current
    DESCRIPTION      "This object specifies the jitter buffer size in
                      milliseconds (ms).

                      Default value depends on the CEM SAP endpoint type
                      (sapCemEndpointType), and if applicable, the number of
                      timeslots (sapCemBitrate):
                      ---------------------------------------------------------
                      | Endpoint Type      | Timeslots | Default jitter buf.  |
                      ---------------------+-----------+-----------------------
                      | 'unstructuredE1'   | n/a       |    5 ms              |
                      ---------------------+-----------+-----------------------
                      | 'unstructuredT1'   | n/a       |    5 ms              |
                      ---------------------+-----------+-----------------------
                      | 'unstructuredE3'   | n/a       |    5 ms              |
                      ---------------------+-----------+-----------------------
                      | 'unstructuredT3'   | n/a       |    5 ms              |
                      ---------------------+-----------+-----------------------
                      | 'nxDS0' (E1/T1)    | N = 1     |   32 ms              |
                      |                    +-----------+-----------------------
                      |                    | N = 2..4  |   16 ms              |
                      |                    +-----------+-----------------------
                      |                    | N = 5..15 |    8 ms              |
                      |                    +-----------+-----------------------
                      |                    | N >= 16   |    5 ms              |
                      ---------------------+-----------+-----------------------
                      | 'nxDS0WithCas' (E1)| N         |    8 ms              |
                      ---------------------+-----------+-----------------------
                      | 'nxDS0WithCas' (T1)| N         |   12 ms              |
                      ---------------------------------------------------------

                      Configuring sapCemPayloadSize and sapCemJitterBuffer to
                      values that result in less than 2 packet buffers or
                      greater than 32 packet buffers is not allowed.

                      The valid range is 1 to 250 ms.  Setting this object
                      to 0 sets it back to the default value."
    ::= { sapCemInfoEntry 6 }

sapCemUseRtpHeader  OBJECT-TYPE
    SYNTAX          TruthValue
    MAX-ACCESS      read-write
    STATUS          current
    DESCRIPTION     "This object specifies whether a RTP header is used when
                     packets are transmitted to the Packet Service Network
                     (PSN) by the CEM SAP."
    DEFVAL          { false }
    ::= { sapCemInfoEntry 7 }

sapCemDifferential  OBJECT-TYPE
    SYNTAX          TruthValue
    MAX-ACCESS      read-only
    STATUS          current
    DESCRIPTION     "This object specifies whether this CEM SAP is in
                     differential mode."
    ::= { sapCemInfoEntry 8 }

sapCemTimestampFreq OBJECT-TYPE
    SYNTAX          Unsigned32
    UNITS           "8 KHz"
    MAX-ACCESS      read-only
    STATUS          current
    DESCRIPTION     "This object specifies whether the value of the timestamp
                     frequency in multiples of 8 KHz for this CEM SAP."
    ::= { sapCemInfoEntry 9 }

sapCemReportAlarm OBJECT-TYPE
    SYNTAX          CemSapReportAlarm
    MAX-ACCESS      read-write
    STATUS          current
    DESCRIPTION
                    "The value of sapCemReportAlarm determines when and if to
                    generate notifications for the CEM SAP."
    DEFVAL      { {strayPkts, malformedPkts, pktLoss, bfrOverrun, bfrUnderrun} }
    ::= { sapCemInfoEntry 10 }

sapCemReportAlarmStatus  OBJECT-TYPE
    SYNTAX          CemSapReportAlarm
    MAX-ACCESS      read-only
    STATUS          current
    DESCRIPTION
                    "The value of sapCemReportAlarmStatus indicates the current
                     alarms on this CEM SAP."
    ::= { sapCemInfoEntry 11 }

sapCemLocalEcid OBJECT-TYPE
    SYNTAX          CemSapEcid
    MAX-ACCESS      read-write
    STATUS          current
    DESCRIPTION     "The value of the object sapCemLocalEcid specifies
                     the local ECID.

                     Only valid if CEM SAP belongs to an EPIPE service."
    DEFVAL { 0 }
    ::= { sapCemInfoEntry 12 }

sapCemRemoteMacAddr OBJECT-TYPE
    SYNTAX          MacAddress
    MAX-ACCESS      read-write
    STATUS          current
    DESCRIPTION     "The value of the object sapCemRemoteMacAddr specifies
                     the remote MAC address.

                     Only valid if CEM SAP belongs to an EPIPE service."
    DEFVAL { '000000000000'h }
    ::= { sapCemInfoEntry 13 }

sapCemRemoteEcid OBJECT-TYPE
    SYNTAX          CemSapEcid
    MAX-ACCESS      read-write
    STATUS          current
    DESCRIPTION     "The value of the object sapCemRemoteEcid specifies
                     the remote ECID.

                     Only valid if CEM SAP belongs to an EPIPE service."
    DEFVAL { 0 }
    ::= { sapCemInfoEntry 14 }

-- ---------------------------------------------------------------------
-- CEM SAP Statistics Table
--
--
--  Sparse Dependent Extention of the sapBaseInfoTable.
--
--  The same indexes are used for both the base table, sapBaseInfoTable,
--  and the sparse dependent table, sapCemStatsTable.
--
--  This in effect extends the sapBaseInfoTable with additional columns.
--  Rows are created in the sapCemStatsTable only for those entries
--  in the sapBaseInfoTable that are created on a port that 'cemEncap' set
--  for port encapsulation.
--
--  Deletion of a row in the sapBaseInfoTable results in the
--  same fate for the row in the sapCemStatsTable.
-- ---------------------------------------------------------------------
sapCemStatsTable OBJECT-TYPE
    SYNTAX          SEQUENCE OF SapCemStatsEntry
    MAX-ACCESS      not-accessible
    STATUS          current
    DESCRIPTION     "A table that contains CEM SAP statistics."
    ::= { tmnxSapObjs 41 }

sapCemStatsEntry OBJECT-TYPE
    SYNTAX          SapCemStatsEntry
    MAX-ACCESS      not-accessible
    STATUS          current
    DESCRIPTION     "Statistics for a specific CEM SAP."
    INDEX           { svcId, sapPortId, sapEncapValue }
    ::= { sapCemStatsTable 1 }

SapCemStatsEntry ::=
    SEQUENCE {
        sapCemStatsIngressForwardedPkts   Counter32,
        sapCemStatsIngressDroppedPkts     Counter32,
        sapCemStatsEgressForwardedPkts    Counter32,
        sapCemStatsEgressDroppedPkts      Counter32,
        sapCemStatsEgressMissingPkts      Counter32,
        sapCemStatsEgressPktsReOrder      Counter32,
        sapCemStatsEgressJtrBfrUnderruns  Counter32,
        sapCemStatsEgressJtrBfrOverruns   Counter32,
        sapCemStatsEgressMisOrderDropped  Counter32,
        sapCemStatsEgressMalformedPkts    Counter32,
        sapCemStatsEgressLBitDropped      Counter32,
        sapCemStatsEgressMultipleDropped  Counter32,
        sapCemStatsEgressESs              Counter32,
        sapCemStatsEgressSESs             Counter32,
        sapCemStatsEgressUASs             Counter32,
        sapCemStatsEgressFailureCounts    Counter32,
        sapCemStatsEgressUnderrunCounts   Counter32,
        sapCemStatsEgressOverrunCounts    Counter32
    }

sapCemStatsIngressForwardedPkts OBJECT-TYPE
    SYNTAX          Counter32
    MAX-ACCESS      read-only
    STATUS          current
    DESCRIPTION     "The value of sapCemStatsIngressForwardedPkts indicates
                     the number of packets that were successfully forwarded."
    ::= { sapCemStatsEntry 1 }

sapCemStatsIngressDroppedPkts OBJECT-TYPE
    SYNTAX          Counter32
    MAX-ACCESS      read-only
    STATUS          current
    DESCRIPTION     "The value of sapCemStatsIngressDroppedPkts indicates
                     the total number of packets that were dropped due to
                     errors."
    ::= { sapCemStatsEntry 2 }

sapCemStatsEgressForwardedPkts OBJECT-TYPE
    SYNTAX          Counter32
    MAX-ACCESS      read-only
    STATUS          current
    DESCRIPTION     "The value of sapCemStatsEgressForwardedPkts indicates the
                     number of packets that were successfully forwarded."
    ::= { sapCemStatsEntry 3 }

sapCemStatsEgressDroppedPkts OBJECT-TYPE
    SYNTAX          Counter32
    MAX-ACCESS      read-only
    STATUS          current
    DESCRIPTION     "The value of sapCemStatsEgressDroppedPkts indicates
                     the total number of packets that were dropped due to
                     errors."
    ::= { sapCemStatsEntry 4 }

sapCemStatsEgressMissingPkts   OBJECT-TYPE
    SYNTAX          Counter32
    MAX-ACCESS      read-only
    STATUS          current
    DESCRIPTION     "The value of sapCemStatsEgressMissingPkts indicates the
                     number of missing packets (as detected via control word
                     sequence number gaps)."
    ::= { sapCemStatsEntry 5 }

sapCemStatsEgressPktsReOrder   OBJECT-TYPE
    SYNTAX          Counter32
    MAX-ACCESS      read-only
    STATUS          current
    DESCRIPTION     "The value of sapCemStatsEgressPktsReOrder indicates the
                     number of packets detected out of sequence (via control
                     word sequence number), but successfully re-ordered."
    ::= { sapCemStatsEntry 6 }

sapCemStatsEgressJtrBfrUnderruns  OBJECT-TYPE
    SYNTAX          Counter32
    MAX-ACCESS      read-only
    STATUS          current
    DESCRIPTION     "The value of sapCemStatsEgressJtrBfrUnderruns indicates
                     the number of times a packet needed to be played out and
                     the jitter buffer was empty."
    ::= { sapCemStatsEntry 7 }

sapCemStatsEgressJtrBfrOverruns  OBJECT-TYPE
    SYNTAX          Counter32
    MAX-ACCESS      read-only
    STATUS          current
    DESCRIPTION     "The value of sapCemStatsEgressJtrBfrOverruns indicates
                     the number of times a packet was dropped because it could
                     not fit in the jitter buffer."
    ::= { sapCemStatsEntry 8 }

sapCemStatsEgressMisOrderDropped  OBJECT-TYPE
    SYNTAX          Counter32
    MAX-ACCESS      read-only
    STATUS          current
    DESCRIPTION     "The value of sapCemStatsEgressMisOrderDropped indicates
                     the number of packets detected out of order (via control
                     word sequence numbers), and could not be re-ordered, or
                     could not be placed in the jitter buffer because it was
                     out of the current window."
    ::= { sapCemStatsEntry 9 }

sapCemStatsEgressMalformedPkts  OBJECT-TYPE
    SYNTAX          Counter32
    MAX-ACCESS      read-only
    STATUS          current
    DESCRIPTION     "The value of sapCemStatsEgressMalformedPkts indicates the
                     number of packets detected with unexpected size, or bad
                     headers' stack."
    ::= { sapCemStatsEntry 10 }

sapCemStatsEgressLBitDropped  OBJECT-TYPE
    SYNTAX          Counter32
    MAX-ACCESS      read-only
    STATUS          current
    DESCRIPTION     "The value of sapCemStatsEgressLBitDropped indicates the
                     number of packets dropped due to the L bit set by the far
                     end."
    ::= { sapCemStatsEntry 11 }

sapCemStatsEgressMultipleDropped  OBJECT-TYPE
    SYNTAX          Counter32
    MAX-ACCESS      read-only
    STATUS          current
    DESCRIPTION     "The value of sapCemStatsEgressMultipleDropped indicates
                     the number of packets dropped due to multiple sequence
                     numbers."
    ::= { sapCemStatsEntry 12 }

sapCemStatsEgressESs  OBJECT-TYPE
    SYNTAX          Counter32
    MAX-ACCESS      read-only
    STATUS          current
    DESCRIPTION     "The value of sapCemStatsEgressESs indicates the number of
                     Error Seconds (ESs) encountered. Any malformed packet,
                     seq.  error, LOPS and similar are considered as error
                     seconds."
    ::= { sapCemStatsEntry 13 }

sapCemStatsEgressSESs  OBJECT-TYPE
    SYNTAX          Counter32
    MAX-ACCESS      read-only
    STATUS          current
    DESCRIPTION     "The value of sapCemStatsEgressSESs indicates the number
                     of Severely Error Seconds (SESs) encountered.  This is
                     when more than 30 percent of the packets within a one
                     second window are missing."
    ::= { sapCemStatsEntry 14 }

sapCemStatsEgressUASs  OBJECT-TYPE
    SYNTAX          Counter32
    MAX-ACCESS      read-only
    STATUS          current
    DESCRIPTION     "The value of sapCemStatsEgressUASs indicates the number of
                     Unavailable Seconds (UASs) encountered. Any consecutive
                     ten seconds of SESs are counted as one UAS."
    ::= { sapCemStatsEntry 15 }

sapCemStatsEgressFailureCounts  OBJECT-TYPE
    SYNTAX          Counter32
    MAX-ACCESS      read-only
    STATUS          current
    DESCRIPTION     "The value of sapCemStatsEgressFailureCounts indicates
                     the number failure events.  A failure event begins when
                     the LOPS failure is declared, and ends when the failure
                     is cleared."
    ::= { sapCemStatsEntry 16 }

sapCemStatsEgressUnderrunCounts  OBJECT-TYPE
    SYNTAX          Counter32
    MAX-ACCESS      read-only
    STATUS          current
    DESCRIPTION     "The value of sapCemStatsEgressUnderrunCounts indicates
                     the number of times the jitter buffer went into an
                     underrun state."
    ::= { sapCemStatsEntry 17 }

sapCemStatsEgressOverrunCounts  OBJECT-TYPE
    SYNTAX          Counter32
    MAX-ACCESS      read-only
    STATUS          current
    DESCRIPTION     "The value of sapCemStatsEgressOverrunCounts indicates
                     the number of times the jitter buffer went into an
                     overrun state."
    ::= { sapCemStatsEntry 18 }

-- ------------------------------------------------------------
-- SAP TLS L2PT Statistics Table
-- ------------------------------------------------------------
sapTlsL2ptStatsTable OBJECT-TYPE
    SYNTAX          SEQUENCE OF SapTlsL2ptStatsEntry
    MAX-ACCESS      not-accessible
    STATUS          current
    DESCRIPTION     "A table that contains SAP Layer 2 Protocol Tunneling
                     Statistics.
                     This table complements sapTlsInfoTable. Rows in this
                     table are created and deleted automatically by the
                     system."
    ::= { tmnxSapObjs 42 }

sapTlsL2ptStatsEntry OBJECT-TYPE
    SYNTAX          SapTlsL2ptStatsEntry
    MAX-ACCESS      not-accessible
    STATUS          current
    DESCRIPTION     "Layer 2 Protocol Tunneling Statistics for a specific SAP.
                     The statistics are provided for each combination of
                     Destination Address and LLC SNAP type."
    INDEX           { svcId, sapPortId, sapEncapValue }
    ::= { sapTlsL2ptStatsTable 1 }

SapTlsL2ptStatsEntry ::=
    SEQUENCE {
        sapTlsL2ptStatsLastClearedTime              TimeStamp,
        sapTlsL2ptStatsL2ptEncapStpConfigBpdusRx    Counter32,
        sapTlsL2ptStatsL2ptEncapStpConfigBpdusTx    Counter32,
        sapTlsL2ptStatsL2ptEncapStpRstBpdusRx       Counter32,
        sapTlsL2ptStatsL2ptEncapStpRstBpdusTx       Counter32,
        sapTlsL2ptStatsL2ptEncapStpTcnBpdusRx       Counter32,
        sapTlsL2ptStatsL2ptEncapStpTcnBpdusTx       Counter32,
        sapTlsL2ptStatsL2ptEncapPvstConfigBpdusRx   Counter32,
        sapTlsL2ptStatsL2ptEncapPvstConfigBpdusTx   Counter32,
        sapTlsL2ptStatsL2ptEncapPvstRstBpdusRx      Counter32,
        sapTlsL2ptStatsL2ptEncapPvstRstBpdusTx      Counter32,
        sapTlsL2ptStatsL2ptEncapPvstTcnBpdusRx      Counter32,
        sapTlsL2ptStatsL2ptEncapPvstTcnBpdusTx      Counter32,
        sapTlsL2ptStatsStpConfigBpdusRx             Counter32,
        sapTlsL2ptStatsStpConfigBpdusTx             Counter32,
        sapTlsL2ptStatsStpRstBpdusRx                Counter32,
        sapTlsL2ptStatsStpRstBpdusTx                Counter32,
        sapTlsL2ptStatsStpTcnBpdusRx                Counter32,
        sapTlsL2ptStatsStpTcnBpdusTx                Counter32,
        sapTlsL2ptStatsPvstConfigBpdusRx            Counter32,
        sapTlsL2ptStatsPvstConfigBpdusTx            Counter32,
        sapTlsL2ptStatsPvstRstBpdusRx               Counter32,
        sapTlsL2ptStatsPvstRstBpdusTx               Counter32,
        sapTlsL2ptStatsPvstTcnBpdusRx               Counter32,
        sapTlsL2ptStatsPvstTcnBpdusTx               Counter32,
        sapTlsL2ptStatsOtherBpdusRx                 Counter32,
        sapTlsL2ptStatsOtherBpdusTx                 Counter32,
        sapTlsL2ptStatsOtherL2ptBpdusRx             Counter32,
        sapTlsL2ptStatsOtherL2ptBpdusTx             Counter32,
        sapTlsL2ptStatsOtherInvalidBpdusRx          Counter32,
        sapTlsL2ptStatsOtherInvalidBpdusTx          Counter32,
        sapTlsL2ptStatsL2ptEncapCdpBpdusRx          Counter32,
        sapTlsL2ptStatsL2ptEncapCdpBpdusTx          Counter32,
        sapTlsL2ptStatsL2ptEncapVtpBpdusRx          Counter32,
        sapTlsL2ptStatsL2ptEncapVtpBpdusTx          Counter32,
        sapTlsL2ptStatsL2ptEncapDtpBpdusRx          Counter32,
        sapTlsL2ptStatsL2ptEncapDtpBpdusTx          Counter32,
        sapTlsL2ptStatsL2ptEncapPagpBpdusRx         Counter32,
        sapTlsL2ptStatsL2ptEncapPagpBpdusTx         Counter32,
        sapTlsL2ptStatsL2ptEncapUdldBpdusRx         Counter32,
        sapTlsL2ptStatsL2ptEncapUdldBpdusTx         Counter32,
        sapTlsL2ptStatsCdpBpdusRx                   Counter32,
        sapTlsL2ptStatsCdpBpdusTx                   Counter32,
        sapTlsL2ptStatsVtpBpdusRx                   Counter32,
        sapTlsL2ptStatsVtpBpdusTx                   Counter32,
        sapTlsL2ptStatsDtpBpdusRx                   Counter32,
        sapTlsL2ptStatsDtpBpdusTx                   Counter32,
        sapTlsL2ptStatsPagpBpdusRx                  Counter32,
        sapTlsL2ptStatsPagpBpdusTx                  Counter32,
        sapTlsL2ptStatsUdldBpdusRx                  Counter32,
        sapTlsL2ptStatsUdldBpdusTx                  Counter32
    }

sapTlsL2ptStatsLastClearedTime OBJECT-TYPE
    SYNTAX          TimeStamp
    MAX-ACCESS      read-only
    STATUS          current
    DESCRIPTION     "The value of sapTlsL2ptStatsLastClearedTime indicates
                     the last time that these stats were cleared. The value
                     zero indicates that they have not been cleared yet."
    ::= { sapTlsL2ptStatsEntry 1 }

sapTlsL2ptStatsL2ptEncapStpConfigBpdusRx OBJECT-TYPE
    SYNTAX          Counter32
    MAX-ACCESS      read-only
    STATUS          current
    DESCRIPTION     "The value of sapTlsL2ptStatsL2ptEncapStpConfigBpdusRx indicates the
                     number of L2PT encapsulated STP config bpdus received on this SAP."
    ::= { sapTlsL2ptStatsEntry 2 }

sapTlsL2ptStatsL2ptEncapStpConfigBpdusTx OBJECT-TYPE
    SYNTAX          Counter32
    MAX-ACCESS      read-only
    STATUS          current
    DESCRIPTION     "The value of sapTlsL2ptStatsL2ptEncapStpConfigBpdusTx indicates the
                     number of L2PT encapsulated STP config bpdus transmitted on this SAP."
    ::= { sapTlsL2ptStatsEntry 3 }

sapTlsL2ptStatsL2ptEncapStpRstBpdusRx OBJECT-TYPE
    SYNTAX          Counter32
    MAX-ACCESS      read-only
    STATUS          current
    DESCRIPTION     "The value of sapTlsL2ptStatsL2ptEncapStpRstBpdusRx indicates the
                     number of L2PT encapsulated STP rst bpdus received on this SAP."
    ::= { sapTlsL2ptStatsEntry 4 }

sapTlsL2ptStatsL2ptEncapStpRstBpdusTx OBJECT-TYPE
    SYNTAX          Counter32
    MAX-ACCESS      read-only
    STATUS          current
    DESCRIPTION     "The value of sapTlsL2ptStatsL2ptEncapStpRstBpdusTx indicates the
                     number of L2PT encapsulated STP rst bpdus transmitted on this SAP."
    ::= { sapTlsL2ptStatsEntry 5 }

sapTlsL2ptStatsL2ptEncapStpTcnBpdusRx OBJECT-TYPE
    SYNTAX          Counter32
    MAX-ACCESS      read-only
    STATUS          current
    DESCRIPTION     "The value of sapTlsL2ptStatsL2ptEncapStpTcnBpdusRx indicates the
                     number of L2PT encapsulated STP tcn bpdus received on this SAP."
    ::= { sapTlsL2ptStatsEntry 6 }

sapTlsL2ptStatsL2ptEncapStpTcnBpdusTx OBJECT-TYPE
    SYNTAX          Counter32
    MAX-ACCESS      read-only
    STATUS          current
    DESCRIPTION     "The value of sapTlsL2ptStatsL2ptEncapStpTcnBpdusTx indicates the
                     number of L2PT encapsulated STP tcn bpdus transmitted on this SAP."
    ::= { sapTlsL2ptStatsEntry 7 }

sapTlsL2ptStatsL2ptEncapPvstConfigBpdusRx OBJECT-TYPE
    SYNTAX          Counter32
    MAX-ACCESS      read-only
    STATUS          current
    DESCRIPTION     "The value of sapTlsL2ptStatsL2ptEncapPvstConfigBpdusRx indicates the
                     number of L2PT encapsulated PVST config bpdus received on this SAP."
    ::= { sapTlsL2ptStatsEntry 8 }

sapTlsL2ptStatsL2ptEncapPvstConfigBpdusTx OBJECT-TYPE
    SYNTAX          Counter32
    MAX-ACCESS      read-only
    STATUS          current
    DESCRIPTION     "The value of sapTlsL2ptStatsL2ptEncapPvstConfigBpdusTx indicates the
                     number of L2PT encapsulated PVST config bpdus transmitted on this SAP."
    ::= { sapTlsL2ptStatsEntry 9 }

sapTlsL2ptStatsL2ptEncapPvstRstBpdusRx OBJECT-TYPE
    SYNTAX          Counter32
    MAX-ACCESS      read-only
    STATUS          current
    DESCRIPTION     "The value of sapTlsL2ptStatsL2ptEncapPvstRstBpdusRx indicates the
                     number of L2PT encapsulated PVST rst bpdus received on this SAP."
    ::= { sapTlsL2ptStatsEntry 10 }

sapTlsL2ptStatsL2ptEncapPvstRstBpdusTx OBJECT-TYPE
    SYNTAX          Counter32
    MAX-ACCESS      read-only
    STATUS          current
    DESCRIPTION     "The value of sapTlsL2ptStatsL2ptEncapPvstRstBpdusTx indicates the
                     number of L2PT encapsulated PVST rst bpdus transmitted on this SAP."
    ::= { sapTlsL2ptStatsEntry 11 }

sapTlsL2ptStatsL2ptEncapPvstTcnBpdusRx OBJECT-TYPE
    SYNTAX          Counter32
    MAX-ACCESS      read-only
    STATUS          current
    DESCRIPTION     "The value of sapTlsL2ptStatsL2ptEncapPvstTcnBpdusRx indicates the
                     number of L2PT encapsulated PVST tcn bpdus received on this SAP."
    ::= { sapTlsL2ptStatsEntry 12 }

sapTlsL2ptStatsL2ptEncapPvstTcnBpdusTx OBJECT-TYPE
    SYNTAX          Counter32
    MAX-ACCESS      read-only
    STATUS          current
    DESCRIPTION     "The value of sapTlsL2ptStatsL2ptEncapPvstTcnBpdusTx indicates the
                     number of L2PT encapsulated PVST tcn bpdus transmitted on this SAP."
    ::= { sapTlsL2ptStatsEntry 13 }

sapTlsL2ptStatsStpConfigBpdusRx OBJECT-TYPE
    SYNTAX          Counter32
    MAX-ACCESS      read-only
    STATUS          current
    DESCRIPTION     "The value of sapTlsL2ptStatsStpConfigBpdusRx indicates the
                     number of STP config bpdus received on this SAP."
    ::= { sapTlsL2ptStatsEntry 14 }

sapTlsL2ptStatsStpConfigBpdusTx OBJECT-TYPE
    SYNTAX          Counter32
    MAX-ACCESS      read-only
    STATUS          current
    DESCRIPTION     "The value of sapTlsL2ptStatsStpConfigBpdusTx indicates the
                     number of STP config bpdus transmitted on this SAP."
    ::= { sapTlsL2ptStatsEntry 15 }

sapTlsL2ptStatsStpRstBpdusRx OBJECT-TYPE
    SYNTAX          Counter32
    MAX-ACCESS      read-only
    STATUS          current
    DESCRIPTION     "The value of sapTlsL2ptStatsStpRstBpdusRx indicates the
                     number of STP rst bpdus received on this SAP."
    ::= { sapTlsL2ptStatsEntry 16 }

sapTlsL2ptStatsStpRstBpdusTx OBJECT-TYPE
    SYNTAX          Counter32
    MAX-ACCESS      read-only
    STATUS          current
    DESCRIPTION     "The value of sapTlsL2ptStatsStpRstBpdusTx indicates the
                     number of STP rst bpdus transmitted on this SAP."
    ::= { sapTlsL2ptStatsEntry 17 }

sapTlsL2ptStatsStpTcnBpdusRx OBJECT-TYPE
    SYNTAX          Counter32
    MAX-ACCESS      read-only
    STATUS          current
    DESCRIPTION     "The value of sapTlsL2ptStatsStpTcnBpdusRx indicates the
                     number of STP tcn bpdus received on this SAP."
    ::= { sapTlsL2ptStatsEntry 18 }

sapTlsL2ptStatsStpTcnBpdusTx OBJECT-TYPE
    SYNTAX          Counter32
    MAX-ACCESS      read-only
    STATUS          current
    DESCRIPTION     "The value of sapTlsL2ptStatsStpTcnBpdusTx indicates the
                     number of STP tcn bpdus transmitted on this SAP."
    ::= { sapTlsL2ptStatsEntry 19 }

sapTlsL2ptStatsPvstConfigBpdusRx OBJECT-TYPE
    SYNTAX          Counter32
    MAX-ACCESS      read-only
    STATUS          current
    DESCRIPTION     "The value of sapTlsL2ptStatsPvstConfigBpdusRx indicates the
                     number of PVST config bpdus received on this SAP."
    ::= { sapTlsL2ptStatsEntry 20 }

sapTlsL2ptStatsPvstConfigBpdusTx OBJECT-TYPE
    SYNTAX          Counter32
    MAX-ACCESS      read-only
    STATUS          current
    DESCRIPTION     "The value of sapTlsL2ptStatsPvstConfigBpdusTx indicates the
                     number of PVST config bpdus transmitted on this SAP."
    ::= { sapTlsL2ptStatsEntry 21 }

sapTlsL2ptStatsPvstRstBpdusRx OBJECT-TYPE
    SYNTAX          Counter32
    MAX-ACCESS      read-only
    STATUS          current
    DESCRIPTION     "The value of sapTlsL2ptStatsPvstRstBpdusRx indicates the
                     number of PVST rst bpdus received on this SAP."
    ::= { sapTlsL2ptStatsEntry 22 }

sapTlsL2ptStatsPvstRstBpdusTx OBJECT-TYPE
    SYNTAX          Counter32
    MAX-ACCESS      read-only
    STATUS          current
    DESCRIPTION     "The value of sapTlsL2ptStatsPvstRstBpdusTx indicates the
                     number of PVST rst bpdus transmitted on this SAP."
    ::= { sapTlsL2ptStatsEntry 23 }

sapTlsL2ptStatsPvstTcnBpdusRx OBJECT-TYPE
    SYNTAX          Counter32
    MAX-ACCESS      read-only
    STATUS          current
    DESCRIPTION     "The value of sapTlsL2ptStatsPvstTcnBpdusRx indicates the
                     number of PVST tcn bpdus received on this SAP."
    ::= { sapTlsL2ptStatsEntry 24 }

sapTlsL2ptStatsPvstTcnBpdusTx OBJECT-TYPE
    SYNTAX          Counter32
    MAX-ACCESS      read-only
    STATUS          current
    DESCRIPTION     "The value of sapTlsL2ptStatsPvstTcnBpdusTx indicates the
                     number of PVST tcn bpdus transmitted on this SAP."
    ::= { sapTlsL2ptStatsEntry 25 }

sapTlsL2ptStatsOtherBpdusRx OBJECT-TYPE
    SYNTAX          Counter32
    MAX-ACCESS      read-only
    STATUS          current
    DESCRIPTION     "The value of sapTlsL2ptStatsOtherBpdusRx indicates the
                     number of other bpdus received on this SAP."
    ::= { sapTlsL2ptStatsEntry 26 }

sapTlsL2ptStatsOtherBpdusTx OBJECT-TYPE
    SYNTAX          Counter32
    MAX-ACCESS      read-only
    STATUS          current
    DESCRIPTION     "The value of sapTlsL2ptStatsOtherBpdusTx indicates the
                     number of other bpdus transmitted on this SAP."
    ::= { sapTlsL2ptStatsEntry 27 }

sapTlsL2ptStatsOtherL2ptBpdusRx OBJECT-TYPE
    SYNTAX          Counter32
    MAX-ACCESS      read-only
    STATUS          current
    DESCRIPTION     "The value of sapTlsL2ptStatsOtherL2ptBpdusRx indicates the
                     number of other L2PT bpdus received on this SAP."
    ::= { sapTlsL2ptStatsEntry 28 }

sapTlsL2ptStatsOtherL2ptBpdusTx OBJECT-TYPE
    SYNTAX          Counter32
    MAX-ACCESS      read-only
    STATUS          current
    DESCRIPTION     "The value of sapTlsL2ptStatsOtherL2ptBpdusTx indicates the
                     number of other L2PT bpdus transmitted on this SAP."
    ::= { sapTlsL2ptStatsEntry 29 }

sapTlsL2ptStatsOtherInvalidBpdusRx OBJECT-TYPE
    SYNTAX          Counter32
    MAX-ACCESS      read-only
    STATUS          current
    DESCRIPTION     "The value of sapTlsL2ptStatsOtherInvalidBpdusRx indicates the
                     number of other invalid bpdus received on this SAP."
    ::= { sapTlsL2ptStatsEntry 30 }

sapTlsL2ptStatsOtherInvalidBpdusTx OBJECT-TYPE
    SYNTAX          Counter32
    MAX-ACCESS      read-only
    STATUS          current
    DESCRIPTION     "The value of sapTlsL2ptStatsOtherInvalidBpdusTx indicates the
                     number of other invalid bpdus transmitted on this SAP."
    ::= { sapTlsL2ptStatsEntry 31 }

sapTlsL2ptStatsL2ptEncapCdpBpdusRx OBJECT-TYPE
    SYNTAX          Counter32
    MAX-ACCESS      read-only
    STATUS          current
    DESCRIPTION     "The value of sapTlsL2ptStatsL2ptEncapCdpBpdusRx indicates the
                     number of L2PT encapsulated CDP bpdus received on this SAP."
    ::= { sapTlsL2ptStatsEntry 32 }

sapTlsL2ptStatsL2ptEncapCdpBpdusTx OBJECT-TYPE
    SYNTAX          Counter32
    MAX-ACCESS      read-only
    STATUS          current
    DESCRIPTION     "The value of sapTlsL2ptStatsL2ptEncapCdpBpdusTx indicates the
                     number of L2PT encapsulated CDP bpdus transmitted on this SAP."
    ::= { sapTlsL2ptStatsEntry 33 }

sapTlsL2ptStatsL2ptEncapVtpBpdusRx OBJECT-TYPE
    SYNTAX          Counter32
    MAX-ACCESS      read-only
    STATUS          current
    DESCRIPTION     "The value of sapTlsL2ptStatsL2ptEncapVtpBpdusRx indicates the
                     number of L2PT encapsulated VTP bpdus received on this SAP."
    ::= { sapTlsL2ptStatsEntry 34 }

sapTlsL2ptStatsL2ptEncapVtpBpdusTx OBJECT-TYPE
    SYNTAX          Counter32
    MAX-ACCESS      read-only
    STATUS          current
    DESCRIPTION     "The value of sapTlsL2ptStatsL2ptEncapVtpBpdusTx indicates the
                     number of L2PT encapsulated VTP bpdus transmitted on this SAP."
    ::= { sapTlsL2ptStatsEntry 35 }

sapTlsL2ptStatsL2ptEncapDtpBpdusRx OBJECT-TYPE
    SYNTAX          Counter32
    MAX-ACCESS      read-only
    STATUS          current
    DESCRIPTION     "The value of sapTlsL2ptStatsL2ptEncapDtpBpdusRx indicates the
                     number of L2PT encapsulated DTP bpdus received on this SAP."
    ::= { sapTlsL2ptStatsEntry 36 }

sapTlsL2ptStatsL2ptEncapDtpBpdusTx OBJECT-TYPE
    SYNTAX          Counter32
    MAX-ACCESS      read-only
    STATUS          current
    DESCRIPTION     "The value of sapTlsL2ptStatsL2ptEncapDtpBpdusTx indicates the
                     number of L2PT encapsulated DTP bpdus transmitted on this SAP."
    ::= { sapTlsL2ptStatsEntry 37 }

sapTlsL2ptStatsL2ptEncapPagpBpdusRx OBJECT-TYPE
    SYNTAX          Counter32
    MAX-ACCESS      read-only
    STATUS          current
    DESCRIPTION     "The value of sapTlsL2ptStatsL2ptEncapPagpBpdusRx indicates the
                     number of L2PT encapsulated PAGP bpdus received on this SAP."
    ::= { sapTlsL2ptStatsEntry 38 }

sapTlsL2ptStatsL2ptEncapPagpBpdusTx OBJECT-TYPE
    SYNTAX          Counter32
    MAX-ACCESS      read-only
    STATUS          current
    DESCRIPTION     "The value of sapTlsL2ptStatsL2ptEncapPagpBpdusTx indicates the
                     number of L2PT encapsulated PAGP bpdus transmitted on this SAP."
    ::= { sapTlsL2ptStatsEntry 39 }


sapTlsL2ptStatsL2ptEncapUdldBpdusRx OBJECT-TYPE
    SYNTAX          Counter32
    MAX-ACCESS      read-only
    STATUS          current
    DESCRIPTION     "The value of sapTlsL2ptStatsL2ptEncapUdldBpdusRx indicates the
                     number of L2PT encapsulated UDLD bpdus received on this SAP."
    ::= { sapTlsL2ptStatsEntry 40 }

sapTlsL2ptStatsL2ptEncapUdldBpdusTx OBJECT-TYPE
    SYNTAX          Counter32
    MAX-ACCESS      read-only
    STATUS          current
    DESCRIPTION     "The value of sapTlsL2ptStatsL2ptEncapUdldBpdusTx indicates the
                     number of L2PT encapsulated UDLD bpdus transmitted on this SAP."
    ::= { sapTlsL2ptStatsEntry 41 }

sapTlsL2ptStatsCdpBpdusRx OBJECT-TYPE
    SYNTAX          Counter32
    MAX-ACCESS      read-only
    STATUS          current
    DESCRIPTION     "The value of sapTlsL2ptStatsCdpBpdusRx indicates the
                     number of CDP bpdus received on this SAP."
    ::= { sapTlsL2ptStatsEntry 42 }

sapTlsL2ptStatsCdpBpdusTx OBJECT-TYPE
    SYNTAX          Counter32
    MAX-ACCESS      read-only
    STATUS          current
    DESCRIPTION     "The value of sapTlsL2ptStatsCdpBpdusTx indicates the
                     number of CDP bpdus transmitted on this SAP."
    ::= { sapTlsL2ptStatsEntry 43 }

sapTlsL2ptStatsVtpBpdusRx OBJECT-TYPE
    SYNTAX          Counter32
    MAX-ACCESS      read-only
    STATUS          current
    DESCRIPTION     "The value of sapTlsL2ptStatsVtpBpdusRx indicates the
                     number of VTP bpdus received on this SAP."
    ::= { sapTlsL2ptStatsEntry 44 }

sapTlsL2ptStatsVtpBpdusTx OBJECT-TYPE
    SYNTAX          Counter32
    MAX-ACCESS      read-only
    STATUS          current
    DESCRIPTION     "The value of sapTlsL2ptStatsVtpBpdusTx indicates the
                     number of VTP bpdus transmitted on this SAP."
    ::= { sapTlsL2ptStatsEntry 45 }


sapTlsL2ptStatsDtpBpdusRx OBJECT-TYPE
    SYNTAX          Counter32
    MAX-ACCESS      read-only
    STATUS          current
    DESCRIPTION     "The value of sapTlsL2ptStatsDtpBpdusRx indicates the
                     number of DTP bpdus received on this SAP."
    ::= { sapTlsL2ptStatsEntry 46 }

sapTlsL2ptStatsDtpBpdusTx OBJECT-TYPE
    SYNTAX          Counter32
    MAX-ACCESS      read-only
    STATUS          current
    DESCRIPTION     "The value of sapTlsL2ptStatsDtpBpdusTx indicates the
                     number of DTP bpdus transmitted on this SAP."
    ::= { sapTlsL2ptStatsEntry 47 }

sapTlsL2ptStatsPagpBpdusRx OBJECT-TYPE
    SYNTAX          Counter32
    MAX-ACCESS      read-only
    STATUS          current
    DESCRIPTION     "The value of sapTlsL2ptStatsPagpBpdusRx indicates the
                     number of PAGP bpdus received on this SAP."
    ::= { sapTlsL2ptStatsEntry 48 }

sapTlsL2ptStatsPagpBpdusTx OBJECT-TYPE
    SYNTAX          Counter32
    MAX-ACCESS      read-only
    STATUS          current
    DESCRIPTION     "The value of sapTlsL2ptStatsPagpBpdusTx indicates the
                     number of PAGP bpdus transmitted on this SAP."
    ::= { sapTlsL2ptStatsEntry 49 }


sapTlsL2ptStatsUdldBpdusRx OBJECT-TYPE
    SYNTAX          Counter32
    MAX-ACCESS      read-only
    STATUS          current
    DESCRIPTION     "The value of sapTlsL2ptStatsUdldBpdusRx indicates the
                     number of UDLD bpdus received on this SAP."
    ::= { sapTlsL2ptStatsEntry 50 }

sapTlsL2ptStatsUdldBpdusTx OBJECT-TYPE
    SYNTAX          Counter32
    MAX-ACCESS      read-only
    STATUS          current
    DESCRIPTION     "The value of sapTlsL2ptStatsUdldBpdusTx indicates the
                     number of UDLD bpdus transmitted on this SAP."
    ::= { sapTlsL2ptStatsEntry 51 }


-- ---------------------------------------------------------------------
-- Ethernet SAP Table
--
--
--  Sparse Dependent Extension of the sapBaseInfoTable.
--
--  The same indexes are used for both the base table, sapBaseInfoTable,
--  and the sparse dependent table, sapEthernetInfoTable.
--
--  This in effect extends the sapBaseInfoTable with additional columns.
--  Rows are created in the sapEthernetInfoTable only for those entries
--  in the sapBaseInfoTable that are created on a port with a
--  tmnxPortEncapType of 'EthernetEncap.'
--
--  Deletion of a row in the sapBaseInfoTable results in the
--  same fate for the row in the sapEthernetInfoTable.
-- ---------------------------------------------------------------------
sapEthernetInfoTable OBJECT-TYPE
    SYNTAX          SEQUENCE OF SapEthernetInfoEntry
    MAX-ACCESS      not-accessible
    STATUS          current
    DESCRIPTION     "A table that contains Ethernet SAP information."
    ::= { tmnxSapObjs 43 }

sapEthernetInfoEntry OBJECT-TYPE
    SYNTAX          SapEthernetInfoEntry
    MAX-ACCESS      not-accessible
    STATUS          current
    DESCRIPTION     "Information about a specific Ethernet SAP."
    INDEX           { svcId, sapPortId, sapEncapValue }
    ::= { sapEthernetInfoTable 1 }

SapEthernetInfoEntry ::=
    SEQUENCE {
        sapEthernetLLFAdminStatus     ServiceAdminStatus,
        sapEthernetLLFOperStatus      INTEGER
    }

sapEthernetLLFAdminStatus OBJECT-TYPE
    SYNTAX          ServiceAdminStatus
    MAX-ACCESS      read-create
    STATUS          current
    DESCRIPTION     "sapEthernetLLFAdminStatus specifies whether or not Link-
                    Loss Forwarding is enabled ('up'). When this object is set
                    to 'up' the underlying port will be forced into the
                    operationally 'down' state if the service is operationally
                    'down', or any of the 'sdpBindPwPeerStatusBits' are set,
                    and will set the underlying port's
                    tmnxPortEtherReasonDownFlags 'linklossFwd' bit. Setting
                    this object to 'down' will clear the 'linklossFwd' reason.
                    sapEthernetLLFAdminStatus can only be enabled on saps
                    configured for an EPIPE service using an Ethernet
                    port with the tmnxPortEncapType set to 'nullEncap.'"
    DEFVAL          { down }
    ::= { sapEthernetInfoEntry 1 }

sapEthernetLLFOperStatus OBJECT-TYPE
    SYNTAX          INTEGER {
                        fault (1),   -- service is down or fault detected.
                        clear (2)    -- service is up and no fault detected.
                    }
    MAX-ACCESS      read-only
    STATUS          current
    DESCRIPTION     "sapEthernetLLFOperStatus indicates whether or not the
                    underlying port is forced operationally 'down' due to the
                    service being operationally 'down' or an
                    sdpBindPwPeerStatusBits bit is set.
                    sapEthernetLLFOperStatus is set to 'fault' when the
                    sapEthernetLLFAdminStatus is set to 'up,' and either a
                    fault has occurred on the pseudo-wire, or the service is
                    down, otherwise sapEthernetLLFOperStatus is set to 'clear.'"
    ::= { sapEthernetInfoEntry 2 }

-- --------------------------------------------------------
-- msapPlcyTable
-- --------------------------------------------------------
msapPlcyTable OBJECT-TYPE
    SYNTAX      SEQUENCE OF MsapPlcyEntry
    MAX-ACCESS  not-accessible
    STATUS      current
    DESCRIPTION
        "The msapPlcyTable has an entry for each managed SAP(MSAP) policy
         configured in the system."
    ::= { tmnxSapObjs 44 }

msapPlcyEntry    OBJECT-TYPE
    SYNTAX      MsapPlcyEntry
    MAX-ACCESS  not-accessible
    STATUS      current
    DESCRIPTION
        "Each entry represents the configuration for a managed SAP(MSAP) policy.

         The values for each entry will be used to populate the following
         tables when the MSAP policy is applied to a MSAP:

         ALCATEL-ENT1-TIMETRA-SAP-MIB::sapBaseInfoTable
         ALCATEL-ENT1-TIMETRA-SAP-MIB::sapSubMgmtInfoTable
        "
    INDEX { msapPlcyName }
    ::= { msapPlcyTable 1}

MsapPlcyEntry ::= SEQUENCE
    {
        msapPlcyName                     TNamedItem,
        msapPlcyRowStatus                RowStatus,
        msapPlcyLastChanged              TimeStamp,
        msapPlcyDescription              TItemDescription,
        msapPlcyCpmProtPolicyId          TCpmProtPolicyID,
        msapPlcyCpmProtMonitorMac        TruthValue,
        msapPlcySubMgmtDefSubId          INTEGER,
        msapPlcySubMgmtDefSubIdStr       TNamedItemOrEmpty,
        msapPlcySubMgmtDefSubProfile     TNamedItemOrEmpty,
        msapPlcySubMgmtDefSlaProfile     TNamedItemOrEmpty,
        msapPlcySubMgmtDefAppProfile     TNamedItemOrEmpty,
        msapPlcySubMgmtSubIdPlcy         TPolicyStatementNameOrEmpty,
        msapPlcySubMgmtSubscriberLimit   Unsigned32,
        msapPlcySubMgmtProfiledTrafOnly  TruthValue,
        msapPlcySubMgmtNonSubTrafSubId   TNamedItemOrEmpty,
        msapPlcySubMgmtNonSubTrafSubProf TNamedItemOrEmpty,
        msapPlcySubMgmtNonSubTrafSlaProf TNamedItemOrEmpty,
        msapPlcySubMgmtNonSubTrafAppProf TNamedItemOrEmpty,
        msapPlcyAssociatedMsaps          Counter32
    }

msapPlcyName        OBJECT-TYPE
    SYNTAX      TNamedItem
    MAX-ACCESS  not-accessible
    STATUS      current
    DESCRIPTION
        "The value of msapPlcyName specifies the name of the MSAP policy."
    ::= { msapPlcyEntry 1 }

msapPlcyRowStatus        OBJECT-TYPE
    SYNTAX      RowStatus
    MAX-ACCESS  read-create
    STATUS      current
    DESCRIPTION
        "The value of msapPlcyRowStatus is used for the creation
         and deletion of MSAP policies."
    ::= { msapPlcyEntry 2 }

msapPlcyLastChanged        OBJECT-TYPE
    SYNTAX      TimeStamp
    MAX-ACCESS  read-only
    STATUS      current
    DESCRIPTION
        "The value of msapPlcyLastChanged indicates the sysUpTime
         at the time of the last modification of this entry.

         If no changes were made to the entry since the last
         re-initialization of the local network management subsystem,
         then this object contains a zero value."
    ::= { msapPlcyEntry 3 }

msapPlcyDescription        OBJECT-TYPE
    SYNTAX      TItemDescription
    MAX-ACCESS  read-create
    STATUS      current
    DESCRIPTION
        "The value of msapPlcyDescription specifies the description
         of the MSAP policy."
    DEFVAL { "" }
    ::= { msapPlcyEntry 4 }

msapPlcyCpmProtPolicyId  OBJECT-TYPE
    SYNTAX          TCpmProtPolicyID
    MAX-ACCESS      read-create
    STATUS          current
    DESCRIPTION
        "The value of msapPlcyCpmProtPolicyId specifies a CPM Protection
         policy for the MSAP policy.

         If a corresponding policy is not defined in
         TIMETRA-SECURITY-MIB::tmnxCpmProtPolTable, an 'inconsistentValue'
         error will be returned.

         A value of one specifies that the default CPM Protection
         policy is associated with the Managed SAP.

         This object is not supported on SR-1 and ESS-1, where the
         value of ALCATEL-IND1-TIMETRA-CHASSIS-MIB::tmnxChassisType is '5',
         and 7710, where the value of ALCATEL-IND1-TIMETRA-CHASSIS-MIB::tmnxChassisType is
         '7' or '9'. An attempt  to set msapPlcyCpmProtPolicyId to a non-zero
         value on one of these unsupported chassis types will return
         an 'inconsistentValue' error."
    DEFVAL { 1 }
    ::= { msapPlcyEntry 5 }

msapPlcyCpmProtMonitorMac OBJECT-TYPE
    SYNTAX          TruthValue
    MAX-ACCESS      read-create
    STATUS          current
    DESCRIPTION
         "The value of msapPlcyCpmProtMonitorMac specifies whether the
          tmnxCpmProtPolPerSrcRateLimit of the CPM Protection policy,
          as specified by msapPlcyCpmProtPolicyId, must be applied.

         If the value of msapPlcyCpmProtMonitorMac is 'true', the
         per-source rate limit must be applied.

         If the value of msapPlcyCpmProtPolicyId is equal to zero,
         the value of msapPlcyCpmProtMonitorMac is irrelevant and
         will be ignored.

         This object is not supported on SR-1 and ESS-1, where the
         value of ALCATEL-IND1-TIMETRA-CHASSIS-MIB::tmnxChassisType is '5',
         and 7710, where the value of ALCATEL-IND1-TIMETRA-CHASSIS-MIB::tmnxChassisType is
         '7' or '9'. An attempt  to set msapPlcyCpmProtMonitorMac to 'true'
         on one of these unsupported chassis types will return an
         'inconsistentValue' error."
    DEFVAL { false }
    ::= { msapPlcyEntry 6 }

msapPlcySubMgmtDefSubId        OBJECT-TYPE
    SYNTAX      INTEGER {
                    useSapId  (1),
                    useString (2)
                }
    MAX-ACCESS  read-create
    STATUS      current
    DESCRIPTION
        "The value of msapPlcySubMgmtDefSubId specifies what will be used as
         the default subscriber identification applicable on the MSAP.

         This value is used in case no other source (like Radius) provides a
         subscriber identification string.

         If the value of this object is set to 'useSapId', the SAP-id will
         be used as the default subscriber identification string. In this case,
         msapPlcySubMgmtDefSubIdStr must contain the empty string, so any
         non-empty string in msapPlcySubMgmtDefSubIdStr will be set to an empty
         string.

         If the value of this object is set to 'useString', the value of
         msapPlcySubMgmtDefSubIdStr will be used as the default subscriber
         identification string. In this case, an empty msapPlcySubMgmtDefSubIdStr
         means that there is no default subscriber identification configured."
    DEFVAL { useString }
    ::= { msapPlcyEntry 7 }

msapPlcySubMgmtDefSubIdStr        OBJECT-TYPE
    SYNTAX      TNamedItemOrEmpty
    MAX-ACCESS  read-create
    STATUS      current
    DESCRIPTION
        "The value of msapPlcySubMgmtDefSubIdStr specifies the default
         subscriber identification string applicable on this MSAP."
    DEFVAL { "" }
    ::= { msapPlcyEntry 8 }

msapPlcySubMgmtDefSubProfile        OBJECT-TYPE
    SYNTAX      TNamedItemOrEmpty
    MAX-ACCESS  read-create
    STATUS      current
    DESCRIPTION
        "The value of msapPlcySubMgmtDefSubProfile specifies the default
         subscriber profile applicable on the MSAP.

         If a corresponding profile is not defined in tmnxSubProfileTable, an
         'inconsistentValue' error will be returned.

         A value of 'default' is not allowed for this object."
    DEFVAL { "" }
    ::= { msapPlcyEntry 9 }

msapPlcySubMgmtDefSlaProfile        OBJECT-TYPE
    SYNTAX      TNamedItemOrEmpty
    MAX-ACCESS  read-create
    STATUS      current
    DESCRIPTION
        "The value of msapPlcySubMgmtDefSlaProfile specifies the default SLA
         profile applicable on the MSAP.

         If a corresponding profile is not defined in tmnxSLAProfileTable, an
         'inconsistentValue' error will be returned."
    DEFVAL { "" }
    ::= { msapPlcyEntry 10 }

msapPlcySubMgmtDefAppProfile        OBJECT-TYPE
    SYNTAX      TNamedItemOrEmpty
    MAX-ACCESS  read-create
    STATUS      current
    DESCRIPTION
        "The value of msapPlcySubMgmtDefAppProfile specifies the default
         application profile applicable on the MSAP.

         If a corresponding profile is not defined in
         TIMETRA-BSX-MIB::tmnxBsxAppProfTable, an 'inconsistentValue'
         error will be returned."
    DEFVAL { "" }
    ::= { msapPlcyEntry 11 }

msapPlcySubMgmtSubIdPlcy        OBJECT-TYPE
    SYNTAX      TPolicyStatementNameOrEmpty
    MAX-ACCESS  read-create
    STATUS      current
    DESCRIPTION
        "The value of msapPlcySubMgmtSubIdPlcy specifies the subscriber
         identification policy applicable on the MSAP.

         If a corresponding profile is not defined in tmnxSubIdentPolicyTable,
         an 'inconsistentValue' error will be returned."
    DEFVAL { "" }
    ::= { msapPlcyEntry 12 }

msapPlcySubMgmtSubscriberLimit OBJECT-TYPE
    SYNTAX          Unsigned32 (0..8000)
    MAX-ACCESS      read-create
    STATUS          current
    DESCRIPTION
        "The value of msapPlcySubMgmtSubscriberLimit specifies the
         maximum number of subscribers allowed for the MSAP.

         A value is 0 means there is no limit.

         The values for the objects msapPlcySubMgmtProfiledTrafOnly,
         msapPlcySubMgmtNonSubTrafSubProf, and
         msapPlcySubMgmtNonSubTrafSlaProf are only meaningful when
         the value of msapPlcySubMgmtSubscriberLimit is 1 and will not
         be used when the value of msapPlcySubMgmtSubscriberLimit is
         not 1."
    DEFVAL { 1 }
    ::= { msapPlcyEntry 13 }

msapPlcySubMgmtProfiledTrafOnly OBJECT-TYPE
    SYNTAX          TruthValue
    MAX-ACCESS      read-create
    STATUS          current
    DESCRIPTION
        "The value of msapPlcySubMgmtProfiledTrafOnly specifies
         whether only profiled traffic is applicable for the MSAP.
         If set to 'true', the MSAP queues will be deleted.

         The value of this object is only meaningful if
         msapPlcySubMgmtSubscriberLimit is set to 1."
    DEFVAL { false }
    ::= { msapPlcyEntry 14 }

msapPlcySubMgmtNonSubTrafSubId OBJECT-TYPE
    SYNTAX          TNamedItemOrEmpty
    MAX-ACCESS      read-create
    STATUS          current
    DESCRIPTION
        "The value of msapPlcySubMgmtNonSubTrafSubId specifies the
         subscriber identification applicable on the MSAP for all
         non-subscriber traffic.

         The value of this object is only meaningful if
         msapPlcySubMgmtSubscriberLimit is set to 1."
    DEFVAL { "" }
    ::= { msapPlcyEntry 15 }

msapPlcySubMgmtNonSubTrafSubProf OBJECT-TYPE
    SYNTAX          TNamedItemOrEmpty
    MAX-ACCESS      read-create
    STATUS          current
    DESCRIPTION
        "The value of msapPlcySubMgmtNonSubTrafSubProf specifies the
         subscriber profile applicable on the MSAP for all
         non-subscriber traffic.

         The value of this object is only meaningful if
         msapPlcySubMgmtSubscriberLimit is set to 1."
    DEFVAL { "" }
    ::= { msapPlcyEntry 16 }

msapPlcySubMgmtNonSubTrafSlaProf OBJECT-TYPE
    SYNTAX          TNamedItemOrEmpty
    MAX-ACCESS      read-create
    STATUS          current
    DESCRIPTION
        "The value of msapPlcySubMgmtNonSubTrafSlaProf specifies the
         SLA profile applicable on the MSAP for all non-subscriber
         traffic.

         The value of this object is only meaningful if
         msapPlcySubMgmtSubscriberLimit is set to 1."
    DEFVAL { "" }
    ::= { msapPlcyEntry 17 }

msapPlcySubMgmtNonSubTrafAppProf OBJECT-TYPE
    SYNTAX          TNamedItemOrEmpty
    MAX-ACCESS      read-create
    STATUS          current
    DESCRIPTION
        "The value of msapPlcySubMgmtNonSubTrafAppProf specifies the
         Application profile applicable on the MSAP for all
         non-subscriber traffic.

         The value of this object is only meaningful if
         msapPlcySubMgmtSubscriberLimit is set to 1."
    DEFVAL { "" }
    ::= { msapPlcyEntry 18 }

msapPlcyAssociatedMsaps OBJECT-TYPE
    SYNTAX          Counter32
    MAX-ACCESS      read-only
    STATUS          current
    DESCRIPTION
        "The value of msapPlcyAssociatedMsaps indicates the
         number of MSAPs associated with this MSAP policy."
    ::= { msapPlcyEntry 19 }

-- --------------------------------------------------------
-- msapTlsPlcyTable
-- --------------------------------------------------------
msapTlsPlcyTable OBJECT-TYPE
    SYNTAX      SEQUENCE OF MsapTlsPlcyEntry
    MAX-ACCESS  not-accessible
    STATUS      current
    DESCRIPTION
        "The msapTlsPlcyTable has an entry for each managed SAP (MSAP)
         policy configured in the system."
    ::= { tmnxSapObjs 45 }

msapTlsPlcyEntry    OBJECT-TYPE
    SYNTAX      MsapTlsPlcyEntry
    MAX-ACCESS  not-accessible
    STATUS      current
    DESCRIPTION
        "Each entry represents the VPLS-related configuration for a managed
         SAP (MSAP) policy.

         The values for each entry will be used to populate the following
         VPLS-related tables when the MSAP policy is applied to a MSAP:

         TIMETRA-SAP-MIB::sapTlsInfoTable
         TIMETRA-SAP-MIB::sapTlsDhcpInfoTable
         ALCATEL-IGMP-SNOOPING-MIB::tlsIgmpSnpgConfigTable
        "
    AUGMENTS { msapPlcyEntry }
    ::= { msapTlsPlcyTable 1}

MsapTlsPlcyEntry ::= SEQUENCE
    {
        msapTlsPlcyLastChanged               TimeStamp,
        msapTlsPlcySplitHorizonGrp           TNamedItemOrEmpty,
        msapTlsPlcyArpReplyAgent             INTEGER,
        msapTlsPlcySubMgmtMacDaHashing       TruthValue,
        msapTlsPlcyDhcpLeasePopulate         Unsigned32,
        msapTlsPlcyDhcpPrxyAdminState        TmnxEnabledDisabled,
        msapTlsPlcyDhcpPrxyServAddrType      InetAddressType,
        msapTlsPlcyDhcpPrxyServAddr          InetAddress,
        msapTlsPlcyDhcpPrxyLeaseTime         Unsigned32,
        msapTlsPlcyDhcpPrxyLTRadOverride     TruthValue,
        msapTlsPlcyDhcpInfoAction            INTEGER,
        msapTlsPlcyDhcpCircuitId             INTEGER,
        msapTlsPlcyDhcpRemoteId              INTEGER,
        msapTlsPlcyDhcpRemoteIdString        TNamedItemOrEmpty,
        msapTlsPlcyDhcpVendorInclOpts        BITS,
        msapTlsPlcyDhcpVendorOptStr          TNamedItemOrEmpty,
        msapTlsPlcyEgressMcastGroup          TNamedItemOrEmpty,
        msapTlsPlcyIgmpSnpgImportPlcy        TPolicyStatementNameOrEmpty,
        msapTlsPlcyIgmpSnpgFastLeave         TmnxEnabledDisabled,
        msapTlsPlcyIgmpSnpgSendQueries       TmnxEnabledDisabled,
        msapTlsPlcyIgmpSnpgGenQueryIntv      Unsigned32,
        msapTlsPlcyIgmpSnpgQueryRespIntv     Unsigned32,
        msapTlsPlcyIgmpSnpgRobustCount       Unsigned32,
        msapTlsPlcyIgmpSnpgLastMembIntvl     Unsigned32,
        msapTlsPlcyIgmpSnpgMaxNbrGrps        Unsigned32,
        msapTlsPlcyIgmpSnpgMvrFromVplsId     TmnxServId,
        msapTlsPlcyIgmpSnpgVersion           TmnxIgmpVersion,
        msapTlsPlcyIgmpSnpgMcacPlcyName      TPolicyStatementNameOrEmpty,
        msapTlsPlcyIgmpSnpgMcacUncnstBW      Integer32,
        msapTlsPlcyIgmpSnpgMcacPrRsvMnBW     Integer32
    }

msapTlsPlcyLastChanged        OBJECT-TYPE
    SYNTAX      TimeStamp
    MAX-ACCESS  read-only
    STATUS      current
    DESCRIPTION
        "The value of msapTlsPlcyLastChanged indicates the sysUpTime
         at the time of the last modification of this entry.

         If no changes were made to the entry since the last
         re-initialization of the local network management subsystem,
         then this object contains a zero value."
    ::= { msapTlsPlcyEntry 1 }

msapTlsPlcySplitHorizonGrp        OBJECT-TYPE
    SYNTAX      TNamedItemOrEmpty
    MAX-ACCESS  read-create
    STATUS      current
    DESCRIPTION
        "The value of msapTlsPlcySplitHorizonGrp specifies the name of the
         split-horizon group for the MSAP.

         If the name specified does not correspond to a tlsShgInfoEntry
         for the VPLS service, the creation of the MSAP will fail.
         Additionally, if msapTlsPlcySplitHorizonGrp is set to a new value,
         the sapSplitHorizonGrp object for any existing MSAPs created by
         this policy will not be updated."
    DEFVAL { "" }
    ::= { msapTlsPlcyEntry 2 }

msapTlsPlcyArpReplyAgent        OBJECT-TYPE
    SYNTAX      INTEGER {
                    disabled               (1),
                    enabled                (2),
                    enabledWithSubscrIdent (3)
                }
    MAX-ACCESS  read-create
    STATUS      current
    DESCRIPTION
        "The value of msapTlsPlcyArpReplyAgent specifies the status of the special
         ARP response mechanism in the system for ARP requests destined to
         static or dynamic hosts associated with the MSAP.

         'disabled'               - the ARP reply function is not operational
         'enabled'                - the ARP reply function is enabled without
                                      subscriber identification.
         'enabledWithSubscrIdent' - the ARP reply function is enabled
                                      with subscriber identification."
    DEFVAL { disabled }
    ::= { msapTlsPlcyEntry 3 }

msapTlsPlcySubMgmtMacDaHashing OBJECT-TYPE
    SYNTAX          TruthValue
    MAX-ACCESS      read-create
    STATUS          current
    DESCRIPTION
        "The value of msapTlsPlcySubMgmtMacDaHashing specifies whether
         subscriber traffic egressing a LAG MSAP has its egress LAG
         link selected by a function of the MAC destination address
         instead of subscriber id."
    DEFVAL { false }
    ::= { msapTlsPlcyEntry 4 }

msapTlsPlcyDhcpLeasePopulate        OBJECT-TYPE
    SYNTAX      Unsigned32 (0..8000)
    MAX-ACCESS  read-create
    STATUS      current
    DESCRIPTION
        "The value of msapTlsPlcyDhcpLeasePopulate specifies the maximum number of
         DHCP lease states allowed on the MSAP."
    DEFVAL { 1 }
    ::= { msapTlsPlcyEntry 5 }

msapTlsPlcyDhcpPrxyAdminState        OBJECT-TYPE
    SYNTAX      TmnxEnabledDisabled
    MAX-ACCESS  read-create
    STATUS      current
    DESCRIPTION
        "The value of msapTlsPlcyDhcpPrxyAdminState specifies the desired
         administrative state of the proxy server on the interface."
    DEFVAL { disabled }
    ::= { msapTlsPlcyEntry 6 }

msapTlsPlcyDhcpPrxyServAddrType        OBJECT-TYPE
    SYNTAX      InetAddressType
    MAX-ACCESS  read-create
    STATUS      current
    DESCRIPTION
        "The value of msapTlsPlcyDhcpPrxyServAddrType specifies the address type
        of msapTlsPlcyDhcpPrxyServAddr."
    DEFVAL { unknown }
    ::= { msapTlsPlcyEntry 7 }

msapTlsPlcyDhcpPrxyServAddr        OBJECT-TYPE
    SYNTAX      InetAddress (SIZE(0|4|16|20))
    MAX-ACCESS  read-create
    STATUS      current
    DESCRIPTION
        "The value of msapTlsPlcyDhcpPrxyServAddr specifies the IP address of the
         which will be used as the source address of the emulated DHCP server
         in the context of the VPLS MSAP.

         This address is mandatory for the proxy server capability and it
         should be in the context of the subnet represented by the VPLS."
    DEFVAL { ''H }
    ::= { msapTlsPlcyEntry 8 }

msapTlsPlcyDhcpPrxyLeaseTime        OBJECT-TYPE
    SYNTAX      Unsigned32 (0|300..315446399)
    UNITS       "seconds"
    MAX-ACCESS  read-create
    STATUS      current
    DESCRIPTION
        "The value of msapTlsPlcyDhcpPrxyLeaseTime specifies, in seconds, how long
         a DHCP client is allowed to use the offered IP address.

         A value of 0 means the lease time provided by a RADIUS or an upstream
         DHCP server will not be overridden. A value of
         7 days (315446399 seconds) is used when RADIUS does not provide a
         lease time."
    DEFVAL { 0 }
    ::= { msapTlsPlcyEntry 9 }

msapTlsPlcyDhcpPrxyLTRadOverride        OBJECT-TYPE
    SYNTAX      TruthValue
    MAX-ACCESS  read-create
    STATUS      current
    DESCRIPTION
        "The value of msapTlsPlcyDhcpPrxyLTRadOverride specifies whether or not the
         lease time provided by the RADIUS server is presented to the DHCP
         client.

         By default the proxy-server will always make use of
         msapTlsPlcyDhcpPrxyLeaseTime, regardless of what lease time information is
         provided from the RADIUS server. When msapTlsPlcyDhcpPrxyLTRadOverride is
         set to 'true', the proxy-server will use the lease time
         information provided by the RADIUS server, regardless of the
         configured lease time."
    DEFVAL { false }
    ::= { msapTlsPlcyEntry 10 }

msapTlsPlcyDhcpInfoAction        OBJECT-TYPE
    SYNTAX      INTEGER {
                    replace (1),
                    drop    (2),
                    keep    (3)
                }
    MAX-ACCESS  read-create
    STATUS      current
    DESCRIPTION
        "The value of msapTlsPlcyDhcpInfoAction specifies the DHCP option
         reforwarding policy:

         'replace' - replace existing information with configured
                       information
         'drop'    - discard messages with existing relay information if the
                       option-82 information is also present
         'keep'    - retain the existing relay information"
    DEFVAL { keep }
    ::= { msapTlsPlcyEntry 11 }

msapTlsPlcyDhcpCircuitId        OBJECT-TYPE
    SYNTAX      INTEGER {
                    none           (0),
                    asciiTuple     (1),
                    vlanAsciiTuple (2)
                }
    MAX-ACCESS  read-create
    STATUS      current
    DESCRIPTION
        "The value of msapTlsPlcyDhcpCircuitId specifies whether or not the
         circuit-id suboption is present, and if it is present what
         information goes in it:

         none           - the circuit-id suboption will not be part of
                          the information option (Option 82).
         asciiTuple     - the ASCII-encoded concatenated tuple consisting
                          of the
                              - access-node-identifier
                              - service-id
                              - interface-name
                          is used.
         vlanAsciiTuple - the format will include VLAN-id and dot1p bits
                          in addition to what is included in ascii-tuple
                          already.  The format is supported on dot1q and
                          qinq encapsulated ports only.  Thus, when the
                          option 82 bits are stripped, dot1p bits will be
                          copied to the Ethernet header of an outgoing
                          packet."
    DEFVAL { asciiTuple }
    ::= { msapTlsPlcyEntry 12 }

msapTlsPlcyDhcpRemoteId        OBJECT-TYPE
    SYNTAX      INTEGER {
                    none      (1),
                    mac       (2),
                    remote-id (3)
                }
    MAX-ACCESS  read-create
    STATUS      current
    DESCRIPTION
        "The value of msapTlsPlcyDhcpRemoteId specifies what information goes into
         the remote-id suboption in the DHCP Relay packet.

         If the value of this object is set to 'none', the remote-id suboption
         will not be part of the information option (Option 82).

         If the value of this object is set to 'mac', the MAC address of the
         remote end is encoded in the suboption.

         If the value of this object is set to 'remote-id',
         msapTlsPlcyDhcpRemoteIdString will represent the remote-id.

         By default, the remote-id value is none."
    DEFVAL { none }
    ::= { msapTlsPlcyEntry 13 }

msapTlsPlcyDhcpRemoteIdString        OBJECT-TYPE
    SYNTAX      TNamedItemOrEmpty
    MAX-ACCESS  read-create
    STATUS      current
    DESCRIPTION
        "The value of msapTlsPlcyDhcpRemoteIdString specifies the remote-id. The
         value of this object is ignored if msapTlsPlcyDhcpRemoteId does not have
         the value of 'remote-id'."
    DEFVAL { "" }
    ::= { msapTlsPlcyEntry 14 }

msapTlsPlcyDhcpVendorInclOpts        OBJECT-TYPE
    SYNTAX      BITS {
                    systemId  (0),
                    clientMac (1),
                    serviceId (2),
                    sapId     (3)
                }
    MAX-ACCESS  read-create
    STATUS      current
    DESCRIPTION
        "The value of msapTlsPlcyDhcpVendorInclOpts specifies what is encoded in the
         Alcatel-Lucent vendor specific sub-option of option 82.

         The value of this object is only used when msapTlsPlcyDhcpInfoAction is
         'replace'."
    DEFVAL { { systemId } }
    ::= { msapTlsPlcyEntry 15 }

msapTlsPlcyDhcpVendorOptStr        OBJECT-TYPE
    SYNTAX      TNamedItemOrEmpty
    MAX-ACCESS  read-create
    STATUS      current
    DESCRIPTION
        "The value of msapTlsPlcyDhcpVendorOptStr specifies the string that goes
         into the Alcatel-Lucent vendor specific sub-option of option 82.

         This string is only used when msapTlsPlcyDhcpInfoAction is set to
         'replace'."
    DEFVAL { "" }
    ::= { msapTlsPlcyEntry 16 }

msapTlsPlcyEgressMcastGroup OBJECT-TYPE
    SYNTAX          TNamedItemOrEmpty
    MAX-ACCESS      read-create
    STATUS          current
    DESCRIPTION
        "The value of msapTlsPlcyEgressMcastGroup specifies the Egress Multicast
         Group for the MSAP."
    DEFVAL { "" }
    ::= { msapTlsPlcyEntry 17 }

msapTlsPlcyIgmpSnpgImportPlcy OBJECT-TYPE
    SYNTAX      TPolicyStatementNameOrEmpty
    MAX-ACCESS  read-create
    STATUS      current
    DESCRIPTION
        "The value of msapTlsPlcyIgmpSnpgImportPlcy specifies the policy statement
         that is be applied to all incoming IGMP messages on the MSAP."
    DEFVAL { "" }
    ::= { msapTlsPlcyEntry 18 }

msapTlsPlcyIgmpSnpgFastLeave OBJECT-TYPE
    SYNTAX      TmnxEnabledDisabled
    MAX-ACCESS  read-create
    STATUS      current
    DESCRIPTION
        "The value of msapTlsPlcyIgmpSnpgFastLeave specifies
         whether fast leave is allowed on this MSAP.

         If set to 'enabled', the system prunes the port on which an IGMP
         'leave' message has been received without waiting for the Group
         Specific Query to timeout."
    DEFVAL { disabled }
    ::= { msapTlsPlcyEntry 19 }

msapTlsPlcyIgmpSnpgSendQueries OBJECT-TYPE
    SYNTAX      TmnxEnabledDisabled
    MAX-ACCESS  read-create
    STATUS      current
    DESCRIPTION
        "The value of msapTlsPlcyIgmpSnpgSendQueries specifies
         whether the system generates General Queries by itself on
         the MSAP."
    DEFVAL { disabled }
    ::= { msapTlsPlcyEntry 20 }

msapTlsPlcyIgmpSnpgGenQueryIntv OBJECT-TYPE
    SYNTAX      Unsigned32 (2..1024)
    UNITS       "seconds"
    MAX-ACCESS  read-create
    STATUS      current
    DESCRIPTION
        "The value of msapTlsPlcyIgmpSnpgGenQueryIntv specifies
         the interval (in seconds) between two consecutive general queries sent
         by the system on the MSAP.

         The value of this object is only meaningful when the value of
         msapTlsPlcyIgmpSnpgSendQueries is 'enabled'."
    DEFVAL { 125 }
    ::= { msapTlsPlcyEntry 21 }

msapTlsPlcyIgmpSnpgQueryRespIntv OBJECT-TYPE
    SYNTAX      Unsigned32 (1..1023)
    UNITS       "seconds"
    MAX-ACCESS  read-create
    STATUS      current
    DESCRIPTION
        "The value of msapTlsPlcyIgmpSnpgQueryRespIntv specifies
         the maximum response time (in seconds) advertised in IGMPv2/v3
         queries.

         The value of this object is only meaningful when the value of
         msapTlsPlcyIgmpSnpgSendQueries is 'enabled'."
    DEFVAL { 10 }
    ::= { msapTlsPlcyEntry 22 }

msapTlsPlcyIgmpSnpgRobustCount OBJECT-TYPE
    SYNTAX      Unsigned32 (2..7)
    MAX-ACCESS  read-create
    STATUS      current
    DESCRIPTION
        "The value of msapTlsPlcyIgmpSnpgRobustCount specifies
         the robustness variable on the MSAP.

         This object allows tuning for the expected packet loss on the MSAP.
         If a MSAP is expected to be lossy, the Robustness Variable may be
         increased. IGMP snooping is robust to (Robustness Variable-1) packet
         losses.

         The value of this object is only meaningful when the value of
         msapTlsPlcyIgmpSnpgSendQueries is 'enabled'."
    DEFVAL { 2 }
    ::= { msapTlsPlcyEntry 23 }

msapTlsPlcyIgmpSnpgLastMembIntvl OBJECT-TYPE
    SYNTAX      Unsigned32 (1..50)
    UNITS       "deci-seconds"
    MAX-ACCESS  read-create
    STATUS      current
    DESCRIPTION
        "The value of msapTlsPlcyIgmpSnpgLastMembIntvl specifies the
         Max Response Time (in tenths of a second) used in
         Group-Specific and Group-Source-Specific Queries sent in response
         to 'leave' messages. This is also the amount of time between
         Group-Specific Query messages.

         This value may be tuned to modify the leave latency of the network.
         A reduced value results in reduced time to detect the loss of the last
         member of a group."
    DEFVAL { 10 }
    ::= { msapTlsPlcyEntry 24 }

msapTlsPlcyIgmpSnpgMaxNbrGrps OBJECT-TYPE
    SYNTAX      Unsigned32 (0..1000)
    MAX-ACCESS  read-create
    STATUS      current
    DESCRIPTION
        "The value of msapTlsPlcyIgmpSnpgMaxNbrGrps specifies how many group
         addresses are allowed for the MSAP.

         The value 0 means that no limit is imposed."
    DEFVAL { 0 }
    ::= { msapTlsPlcyEntry 25 }

msapTlsPlcyIgmpSnpgMvrFromVplsId OBJECT-TYPE
    SYNTAX      TmnxServId
    MAX-ACCESS  read-create
    STATUS      current
    DESCRIPTION
        "The value of msapTlsPlcyIgmpSnpgMvrFromVplsId specifies from which
         VPLS the multicast streams corresponding to the groups learned
         via the MSAP are copied.

         Groups which cannot be joined to the corresponding MVR VPLS
         (because MVR is not up or the configured MVR policy rejects the group)
         copy the multicast streams from the local VPLS if IGMP snooping is up
         (i.e. tlsIgmpSnpgCfgAdminState is 'enabled')."
    DEFVAL { 0 }
    ::= { msapTlsPlcyEntry 26 }

msapTlsPlcyIgmpSnpgVersion OBJECT-TYPE
    SYNTAX      TmnxIgmpVersion
    MAX-ACCESS  read-create
    STATUS      current
    DESCRIPTION
        "The value of msapTlsPlcyIgmpSnpgVersion specifies the version
         of IGMP running on the MSAP."
    DEFVAL { version3 }
    ::= { msapTlsPlcyEntry 27 }

msapTlsPlcyIgmpSnpgMcacPlcyName OBJECT-TYPE
    SYNTAX     TPolicyStatementNameOrEmpty
    MAX-ACCESS read-create
    STATUS     current
    DESCRIPTION
        "The value of msapTlsPlcyIgmpSnpgMcacPlcyName specifies the name
         of the multicast CAC (Connection Admission Control) policy."
    DEFVAL { "" }
    ::= { msapTlsPlcyEntry 28 }

msapTlsPlcyIgmpSnpgMcacUncnstBW OBJECT-TYPE
    SYNTAX      Integer32 (-1|0..2147483647)
    UNITS       "kbps"
    MAX-ACCESS  read-create
    STATUS      current
    DESCRIPTION
        "The value of msapTlsPlcyIgmpSnpgMcacUncnstBW specifies the bandwidth
         assigned for interface's multicast CAC policy traffic in kilo-bits per
         second(kbps).

         If the default value of '-1' is set, there is no constraint on
         bandwidth allocated at the interface.

         If the value of msapTlsPlcyIgmpSnpgMcacUncnstBW is set to '0' and if
         a multicast CAC policy is assigned on the interface, then
         no group (channel) from that policy is allowed on that interface."
    DEFVAL { -1 }
    ::= { msapTlsPlcyEntry 29 }

msapTlsPlcyIgmpSnpgMcacPrRsvMnBW OBJECT-TYPE
    SYNTAX      Integer32 (-1|0..2147483647)
    UNITS       "kbps"
    MAX-ACCESS  read-create
    STATUS      current
    DESCRIPTION
        "The value of msapTlsPlcyIgmpSnpgMcacPrRsvMnBW specifies the bandwidth
         pre-reserved for all the mandatory channels on a given interface
         in kilo-bits per second(kbps).

         If the value of msapTlsPlcyIgmpSnpgMcacUncnstBW is '0', no mandatory
         channels are allowed. If the value of msapTlsPlcyIgmpSnpgMcacPrRsvMnBW
         is '-1', then all mandatory and optional channels are allowed.

         If the value of msapTlsPlcyIgmpSnpgMcacPrRsvMnBW is equal to the
         value of msapTlsPlcyIgmpSnpgMcacUncnstBW, then all the unconstrained
         bandwidth on a given interface is allocated to mandatory channels
         configured through multicast CAC policy on that interface and no
         optional groups (channels) are allowed.

         The value of msapTlsPlcyIgmpSnpgMcacPrRsvMnBW should always be less
         than or equal to that of msapTlsPlcyIgmpSnpgMcacUncnstBW. An attempt
         to set the value of msapTlsPlcyIgmpSnpgMcacPrRsvMnBW greater than
         that of msapTlsPlcyIgmpSnpgMcacUncnstBW will result in
         'inconsistentValue' error."
    DEFVAL { -1 }
    ::= { msapTlsPlcyEntry 30 }

-- --------------------------------------------------------
--
--  msapIgmpSnpgMcacLevelTable
--
-- --------------------------------------------------------

msapIgmpSnpgMcacLevelTable OBJECT-TYPE
    SYNTAX      SEQUENCE OF MSapIgmpSnpgMcacLevelEntry
    MAX-ACCESS  not-accessible
    STATUS      current
    DESCRIPTION "The msapIgmpSnpgMcacLevelTable has an entry for each
                 multicast CAC policy constraint level configured for
                 a Managed SAP policy."
    ::= { tmnxSapObjs 46 }

msapIgmpSnpgMcacLevelEntry OBJECT-TYPE
    SYNTAX      MSapIgmpSnpgMcacLevelEntry
    MAX-ACCESS  not-accessible
    STATUS      current
    DESCRIPTION "Each row entry represents a multicast CAC policy
                 bundle level constraints for a particular Managed
                 SAP policy. Entries are created and deleted by
                 the user."
    INDEX { msapPlcyName, msapIgmpSnpgMcacLevelId }
    ::= { msapIgmpSnpgMcacLevelTable 1}

MSapIgmpSnpgMcacLevelEntry ::= SEQUENCE {
   msapIgmpSnpgMcacLevelId          Unsigned32,
   msapIgmpSnpgMcacLevelRowStatus   RowStatus,
   msapIgmpSnpgMcacLevelLastChanged TimeStamp,
   msapIgmpSnpgMcacLevelBW          Unsigned32
}

msapIgmpSnpgMcacLevelId OBJECT-TYPE
    SYNTAX      Unsigned32 (1..8)
    MAX-ACCESS  not-accessible
    STATUS      current
    DESCRIPTION "The value of msapIgmpSnpgMcacLevelId indicates
                 the level id of the multicast CAC policy bundle
                 constraint.

                 The value of level 1 has the highest priority and
                 level 8 the lowest."
    ::= { msapIgmpSnpgMcacLevelEntry 1 }

msapIgmpSnpgMcacLevelRowStatus OBJECT-TYPE
    SYNTAX      RowStatus
    MAX-ACCESS  read-create
    STATUS      current
    DESCRIPTION "The value of msapIgmpSnpgMcacLevelRowStatus is
                 used for creation and deletion of level constraint
                 in a CAC for a Managed SAP policy."
    ::= { msapIgmpSnpgMcacLevelEntry 2 }

msapIgmpSnpgMcacLevelLastChanged OBJECT-TYPE
    SYNTAX      TimeStamp
    MAX-ACCESS  read-only
    STATUS      current
    DESCRIPTION "The value of msapIgmpSnpgMcacLevelLastChanged indicates
                 the sysUpTime at the time of the last modification
                 of this entry.

                 If no changes were made to the entry since the last
                 re-initialization of the local network management
                 subsystem, then this object contains a zero value."
    ::= { msapIgmpSnpgMcacLevelEntry 3 }

msapIgmpSnpgMcacLevelBW OBJECT-TYPE
    SYNTAX      Unsigned32
    UNITS       "kbps"
    MAX-ACCESS  read-create
    STATUS      current
    DESCRIPTION "The value of msapIgmpSnpgMcacLevelBW specifies
                 the bandwidth in kilo-bits per second (kbps) for
                 the level."
    DEFVAL { 1 }
    ::= { msapIgmpSnpgMcacLevelEntry 4 }

-- --------------------------------------------------------
--
--  msapIgmpSnpgMcacLagTable
--
-- --------------------------------------------------------

msapIgmpSnpgMcacLagTable OBJECT-TYPE
    SYNTAX      SEQUENCE OF MSapIgmpSnpgMcacLagEntry
    MAX-ACCESS  not-accessible
    STATUS      current
    DESCRIPTION "The msapIgmpSnpgMcacLagTable has an entry for each lag
                 port configured for a multicast CAC policy bundle configured
                 for a Managed SAP policy."
    ::= { tmnxSapObjs 47 }

msapIgmpSnpgMcacLagEntry OBJECT-TYPE
    SYNTAX      MSapIgmpSnpgMcacLagEntry
    MAX-ACCESS  not-accessible
    STATUS      current
    DESCRIPTION "Each row entry represents a particular multicast CAC lag port
                 constraints for a Managed SAP policy.. Entries are
                 created and deleted by the user."
    INDEX { msapPlcyName, msapIgmpSnpgMcacLagPortsDown }
    ::= { msapIgmpSnpgMcacLagTable 1}

MSapIgmpSnpgMcacLagEntry ::= SEQUENCE {
   msapIgmpSnpgMcacLagPortsDown    Unsigned32,
   msapIgmpSnpgMcacLagRowStatus    RowStatus,
   msapIgmpSnpgMcacLagLastChanged  TimeStamp,
   msapIgmpSnpgMcacLagLevel        Unsigned32
}

msapIgmpSnpgMcacLagPortsDown OBJECT-TYPE
    SYNTAX      Unsigned32 (1..8)
    MAX-ACCESS  not-accessible
    STATUS      current
    DESCRIPTION "The value of msapIgmpSnpgMcacLagPortsDown indicates
                 the configured number of ports in a lag group that are down.

                 If the number of ports available in the lag is reduced by the
                 number of ports configured for msapIgmpSnpgMcacLagPortsDown
                 object then bandwidth allowed for bundle will be updated to
                 the value of msapIgmpSnpgMcacLevelBW indexed by
                 msapIgmpSnpgMcacLagLevel value."
    ::= { msapIgmpSnpgMcacLagEntry 1 }

msapIgmpSnpgMcacLagRowStatus OBJECT-TYPE
    SYNTAX      RowStatus
    MAX-ACCESS  read-create
    STATUS      current
    DESCRIPTION "The value of msapIgmpSnpgMcacLagRowStatus is used for
                 creation and deletion of lag constraint in a CAC policy."
    ::= { msapIgmpSnpgMcacLagEntry 2 }

msapIgmpSnpgMcacLagLastChanged OBJECT-TYPE
    SYNTAX      TimeStamp
    MAX-ACCESS  read-only
    STATUS      current
    DESCRIPTION "The value of msapIgmpSnpgMcacLagLastChanged indicates the
                 sysUpTime at the time of the last modification of this entry.

                 If no changes were made to the entry since the last
                 re-initialization of the local network management subsystem,
                 then this object contains a zero value."
    ::= { msapIgmpSnpgMcacLagEntry 3 }

msapIgmpSnpgMcacLagLevel OBJECT-TYPE
    SYNTAX      Unsigned32 (1..8)
    MAX-ACCESS  read-create
    STATUS      current
    DESCRIPTION "The value of msapIgmpSnpgMcacLagLevel specifies the level
                 id to use when the value of msapIgmpSnpgMcacLagPortsDown
                 matches the actual number of ports down in a lag.

                 Using the value of msapIgmpSnpgMcacLagLevel as an index,
                 the operational MSAP unconstrained bandwidth will be set
                 to msapIgmpSnpgMcacLevelBW.

                 By default, for all lag constraints the link level will
                 be set to 1 at row creation."
    DEFVAL { 1 }
    ::= { msapIgmpSnpgMcacLagEntry 4 }

-- ---------------------------------------------------------------------
--  Managed SAP Information Table
--
--  Sparse Dependent Extension of the sapBaseInfoTable.
--
--  The same indexes are used for both the base table, sapBaseInfoTable,
--  and the sparse dependent table, msapInfoTable.
--
--  This in effect extends the sapBaseInfoTable with additional columns.
--  Rows are created in the msapInfoTable only for those entries
--  in the sapBaseInfoTable that are created on a port with a
--  sapSubType of 'managed'.
--
--  Deletion of a row in the sapBaseInfoTable results in the
--  same fate for the row in the msapInfoTable.
-- ---------------------------------------------------------------------

msapInfoTable OBJECT-TYPE
    SYNTAX          SEQUENCE OF MSapInfoEntry
    MAX-ACCESS      not-accessible
    STATUS          current
    DESCRIPTION     "A table that contains Managed SAP information."
    ::= { tmnxSapObjs 48 }

msapInfoEntry OBJECT-TYPE
    SYNTAX          MSapInfoEntry
    MAX-ACCESS      not-accessible
    STATUS          current
    DESCRIPTION     "Information about a specific Managed SAP."
    INDEX           { svcId, sapPortId, sapEncapValue }
    ::= { msapInfoTable 1 }

MSapInfoEntry ::=
    SEQUENCE {
        msapInfoCreationSapPortEncapVal      TmnxEncapVal,
        msapInfoCreationPlcyName             TNamedItem,
        msapInfoReEvalPolicy                 TmnxActionType,
        msapInfoLastChanged                  TimeStamp
    }

msapInfoCreationSapPortEncapVal OBJECT-TYPE
    SYNTAX            TmnxEncapVal
    MAX-ACCESS        read-only
    STATUS            current
    DESCRIPTION       "The value of msapInfoCreationSapPortEncapVal indicates
                       the port encapsulation value of the SAP with a sapSubType
                       value of 'capture' that created this MSAP."
    ::= { msapInfoEntry 1 }

msapInfoCreationPlcyName OBJECT-TYPE
    SYNTAX           TNamedItem
    MAX-ACCESS       read-only
    STATUS           current
    DESCRIPTION      "The value of msapInfoCreationPlcyName indicates
                      the value of the msapPlcyName object for MSAP policy
                      used to create this MSAP."
    ::= { msapInfoEntry 2 }

msapInfoReEvalPolicy OBJECT-TYPE
    SYNTAX           TmnxActionType
    MAX-ACCESS       read-write
    STATUS           current
    DESCRIPTION      "The value of msapInfoReEvalPolicy specifies whether
                      to re-apply the Managed SAP policy associated with
                      this MSAP.

                      When a SET of this object is done with a value of
                      'doAction', the system will attempt to re-apply the
                      MSAP policy indicated by msapInfoCreationPlcyName.
                      If this action is successful, 'noError' will be returned.
                      If this action is unsuccessful, an 'inconsistentValue'
                      error will be returned. Attempting to SET this object with
                      a value of 'notApplicable' will have no effect and will
                      return 'noError'.

                      SNMP GET and GETNEXT requests on this object will
                      return 'notApplicable'."
    DEFVAL { notApplicable }
    ::= { msapInfoEntry 3 }

msapInfoLastChanged OBJECT-TYPE
    SYNTAX      TimeStamp
    MAX-ACCESS  read-only
    STATUS      current
    DESCRIPTION "The value of msapInfoLastChanged indicates the
                 sysUpTime at the time of the last modification of this entry.

                 If no changes were made to the entry since the last
                 re-initialization of the local network management subsystem,
                 then this object contains a zero value."
    ::= { msapInfoEntry 4 }

-- ---------------------------------------------------------------------
-- Capture SAP Stats Table
--
--
--  Sparse Dependent Extension of the sapBaseInfoTable.
--
--  The same indexes are used for both the base table, sapBaseInfoTable,
--  and the sparse dependent table, msapCaptureSapStatsTable.
--
--  This in effect extends the sapBaseInfoTable with additional columns.
--  Rows are created in the msapTriggerPktStatsTable only for those entries
--  in the sapBaseInfoTable that have a sapSubType of 'capture'.
--
--  Deletion of a row in the sapBaseInfoTable results in the
--  same fate for the row in the msapTriggerPktStatsTable.
-- ---------------------------------------------------------------------
msapCaptureSapStatsTable OBJECT-TYPE
    SYNTAX          SEQUENCE OF MSapCaptureSapStatsEntry
    MAX-ACCESS      not-accessible
    STATUS          current
    DESCRIPTION     "A table that contains statistics for SAPs
                     with a sapSubType value of 'capture'."
    ::= { tmnxSapObjs 49 }

msapCaptureSapStatsEntry OBJECT-TYPE
    SYNTAX          MSapCaptureSapStatsEntry
    MAX-ACCESS      not-accessible
    STATUS          current
    DESCRIPTION     "Statistics for a specific 'capture' SAP."
    INDEX           { svcId,
                      sapPortId,
                      sapEncapValue,
                      msapCaptureSapStatsTriggerType }
    ::= { msapCaptureSapStatsTable 1 }

MSapCaptureSapStatsEntry ::=
    SEQUENCE {
        msapCaptureSapStatsTriggerType   INTEGER,
        msapCaptureSapStatsPktsRecvd     Counter32,
        msapCaptureSapStatsPktsRedirect  Counter32,
        msapCaptureSapStatsPktsDropped   Counter32
    }

msapCaptureSapStatsTriggerType OBJECT-TYPE
    SYNTAX            INTEGER {
                          dhcp  (1),
                          pppoe (2)
                      }
    MAX-ACCESS        not-accessible
    STATUS            current
    DESCRIPTION       "The value of msapCaptureSapStatsTriggerType indicates the
                       type of trigger packets this entry is for."
    ::= { msapCaptureSapStatsEntry 1 }

msapCaptureSapStatsPktsRecvd OBJECT-TYPE
    SYNTAX           Counter32
    MAX-ACCESS       read-only
    STATUS           current
    DESCRIPTION      "The value of msapCaptureSapStatsPktsRecvd indicates the
                      number of packets received on this 'capture' SAP."
    ::= { msapCaptureSapStatsEntry 2 }

msapCaptureSapStatsPktsRedirect OBJECT-TYPE
    SYNTAX           Counter32
    MAX-ACCESS       read-only
    STATUS           current
    DESCRIPTION      "The value of msapCaptureSapStatsPktsRedirect indicates the
                      number of packets redirected on this 'capture' SAP."
    ::= { msapCaptureSapStatsEntry 3 }

msapCaptureSapStatsPktsDropped OBJECT-TYPE
    SYNTAX           Counter32
    MAX-ACCESS       read-only
    STATUS           current
    DESCRIPTION      "The value of msapCaptureSapStatsPktsDropped indicates the
                      number of packets dropped on this 'capture' SAP."
    ::= { msapCaptureSapStatsEntry 4 }

-- -------------------------------------
-- TLS SAP MRP Table
-- -------------------------------------
sapTlsMrpTable OBJECT-TYPE
    SYNTAX          SEQUENCE OF SapTlsMrpEntry
    MAX-ACCESS      not-accessible
    STATUS          current
    DESCRIPTION     "The sapTlsMrpTable augments sapTlsInfoTable with
                     attributes of the Multiple Registration Protocol (MRP)
                     feature for the TLS SAP."
    ::= { tmnxSapObjs 50 }

sapTlsMrpEntry OBJECT-TYPE
    SYNTAX          SapTlsMrpEntry
    MAX-ACCESS      not-accessible
    STATUS          current
    DESCRIPTION     "MRP specific information about a SAP in a TLS."
    AUGMENTS        { sapTlsInfoEntry }
    ::= { sapTlsMrpTable 1 }

SapTlsMrpEntry ::=
    SEQUENCE {
        sapTlsMrpRxPdus               Counter32,
        sapTlsMrpDroppedPdus          Counter32,
        sapTlsMrpTxPdus               Counter32,
        sapTlsMrpRxNewEvent           Counter32,
        sapTlsMrpRxJoinInEvent        Counter32,
        sapTlsMrpRxInEvent            Counter32,
        sapTlsMrpRxJoinEmptyEvent     Counter32,
        sapTlsMrpRxEmptyEvent         Counter32,
        sapTlsMrpRxLeaveEvent         Counter32,
        sapTlsMrpTxNewEvent           Counter32,
        sapTlsMrpTxJoinInEvent        Counter32,
        sapTlsMrpTxInEvent            Counter32,
        sapTlsMrpTxJoinEmptyEvent     Counter32,
        sapTlsMrpTxEmptyEvent         Counter32,
        sapTlsMrpTxLeaveEvent         Counter32
    }

sapTlsMrpRxPdus OBJECT-TYPE
    SYNTAX           Counter32
    MAX-ACCESS       read-only
    STATUS           current
    DESCRIPTION
        "The value of sapTlsMrpRxPdus indicates the number of MRP packets
        received on this SAP."
    ::= { sapTlsMrpEntry 1 }

sapTlsMrpDroppedPdus OBJECT-TYPE
    SYNTAX           Counter32
    MAX-ACCESS       read-only
    STATUS           current
    DESCRIPTION
        "The value of sapTlsMrpDroppedPdus indicates the number of dropped MRP
        packets on this SAP."
    ::= { sapTlsMrpEntry 2 }

sapTlsMrpTxPdus OBJECT-TYPE
    SYNTAX           Counter32
    MAX-ACCESS       read-only
    STATUS           current
    DESCRIPTION
        "The value of sapTlsMrpTxPdus indicates the number of MRP packets
        transmitted on this SAP."
    ::= { sapTlsMrpEntry 3 }

sapTlsMrpRxNewEvent OBJECT-TYPE
    SYNTAX           Counter32
    MAX-ACCESS       read-only
    STATUS           current
    DESCRIPTION
        "The value of sapTlsMrpRxNewEvent indicates the number of 'New' MRP
        events received on this SAP."
    ::= { sapTlsMrpEntry 4 }

sapTlsMrpRxJoinInEvent OBJECT-TYPE
    SYNTAX           Counter32
    MAX-ACCESS       read-only
    STATUS           current
    DESCRIPTION
        "The value of sapTlsMrpRxJoinInEvent indicates the number of 'Join-In'
        MRP events received on this SAP."
    ::= { sapTlsMrpEntry 5 }

sapTlsMrpRxInEvent OBJECT-TYPE
    SYNTAX           Counter32
    MAX-ACCESS       read-only
    STATUS           current
    DESCRIPTION
        "The value of sapTlsMrpRxInEvent indicates the number of 'In' MRP
        events received on this SAP."
    ::= { sapTlsMrpEntry 6 }

sapTlsMrpRxJoinEmptyEvent OBJECT-TYPE
    SYNTAX           Counter32
    MAX-ACCESS       read-only
    STATUS           current
    DESCRIPTION
        "The value of sapTlsMrpRxJoinEmptyEvent indicates the number of
        'Join Empty' MRP events received on this SAP."
    ::= { sapTlsMrpEntry 7 }

sapTlsMrpRxEmptyEvent OBJECT-TYPE
    SYNTAX           Counter32
    MAX-ACCESS       read-only
    STATUS           current
    DESCRIPTION
        "The value of sapTlsMrpRxEmptyEvent indicates the number of 'Empty'
        MRP events received on this SAP."
    ::= { sapTlsMrpEntry 8 }

sapTlsMrpRxLeaveEvent OBJECT-TYPE
    SYNTAX           Counter32
    MAX-ACCESS       read-only
    STATUS           current
    DESCRIPTION
        "The value of sapTlsMrpRxLeaveEvent indicates the number of 'Leave'
        MRP events received on this SAP."
    ::= { sapTlsMrpEntry 9 }

sapTlsMrpTxNewEvent OBJECT-TYPE
    SYNTAX           Counter32
    MAX-ACCESS       read-only
    STATUS           current
    DESCRIPTION
        "The value of sapTlsMrpTxNewEvent indicates the number of 'New' MRP
        events transmitted on this SAP."
    ::= { sapTlsMrpEntry 10 }

sapTlsMrpTxJoinInEvent OBJECT-TYPE
    SYNTAX           Counter32
    MAX-ACCESS       read-only
    STATUS           current
    DESCRIPTION
        "The value of sapTlsMrpTxJoinInEvent indicates the number of 'Join-In'
        MRP events transmitted on this SAP."
    ::= { sapTlsMrpEntry 11 }

sapTlsMrpTxInEvent OBJECT-TYPE
    SYNTAX           Counter32
    MAX-ACCESS       read-only
    STATUS           current
    DESCRIPTION
        "The value of sapTlsMrpTxInEvent indicates the number of 'In' MRP
        events transmitted on this SAP."
    ::= { sapTlsMrpEntry 12 }

sapTlsMrpTxJoinEmptyEvent OBJECT-TYPE
    SYNTAX           Counter32
    MAX-ACCESS       read-only
    STATUS           current
    DESCRIPTION
        "The value of sapTlsMrpTxJoinEmptyEvent indicates the number of
        'Join Empty' MRP events transmitted on this SAP."
    ::= { sapTlsMrpEntry 13 }

sapTlsMrpTxEmptyEvent OBJECT-TYPE
    SYNTAX           Counter32
    MAX-ACCESS       read-only
    STATUS           current
    DESCRIPTION
        "The value of sapTlsMrpTxEmptyEvent indicates the number of 'Empty'
        MRP events transmitted on this SAP."
    ::= { sapTlsMrpEntry 14 }

sapTlsMrpTxLeaveEvent OBJECT-TYPE
    SYNTAX           Counter32
    MAX-ACCESS       read-only
    STATUS           current
    DESCRIPTION
        "The value of sapTlsMrpTxLeaveEvent indicates the number of 'Leave'
        MRP events transmitted on this SAP."
    ::= { sapTlsMrpEntry 15 }

-- -------------------------------------
-- TLS SAP MMRP Table
-- -------------------------------------
sapTlsMmrpTable OBJECT-TYPE
    SYNTAX          SEQUENCE OF SapTlsMmrpEntry
    MAX-ACCESS      not-accessible
    STATUS          current
    DESCRIPTION     "This table contains an entry for each MAC address managed
                    by Multiple MAC Registration Protocol (MMRP) on the SAP
                    for the TLS.  Entries are dynamically created and
                    destroyed by the system as the MAC Addresses are registered
                    or declared in MMRP."
    ::= { tmnxSapObjs 51 }

sapTlsMmrpEntry OBJECT-TYPE
    SYNTAX          SapTlsMmrpEntry
    MAX-ACCESS      not-accessible
    STATUS          current
    DESCRIPTION     "MMRP specific information about a MAC address managed by
                    MMRP on a SAP in a TLS."
    INDEX           { svcId, sapPortId, sapEncapValue, sapTlsMmrpMacAddr }
    ::= { sapTlsMmrpTable 1 }

SapTlsMmrpEntry ::=
    SEQUENCE {
        sapTlsMmrpMacAddr              MacAddress,
        sapTlsMmrpDeclared             TruthValue,
        sapTlsMmrpRegistered           TruthValue
    }

sapTlsMmrpMacAddr OBJECT-TYPE
    SYNTAX        MacAddress
    MAX-ACCESS    not-accessible
    STATUS        current
    DESCRIPTION
        "The value of sapTlsMmrpMacAddr indicates an ethernet MAC address which
        is being managed by MMRP on this SAP."
    ::= { sapTlsMmrpEntry 1 }

sapTlsMmrpDeclared OBJECT-TYPE
    SYNTAX        TruthValue
    MAX-ACCESS    read-only
    STATUS        current
    DESCRIPTION
        "The value of sapTlsMmrpDeclared indicates whether the MRP applicant
        on this SAP is declaring this MAC address on behalf of MMRP."
    ::= { sapTlsMmrpEntry 2 }

sapTlsMmrpRegistered OBJECT-TYPE
    SYNTAX        TruthValue
    MAX-ACCESS    read-only
    STATUS        current
    DESCRIPTION
        "The value of sapTlsMmrpRegistered indicates whether the MRP registrant
        on this SAP has notified MMRP of a registration of this MAC address."
    ::= { sapTlsMmrpEntry 3 }

-- --------------------------------------
-- TblLastChgd objects for msap tables
-- --------------------------------------

msapPlcyTblLastChgd  OBJECT-TYPE
    SYNTAX          TimeStamp
    MAX-ACCESS      read-only
    STATUS          current
    DESCRIPTION     "The value of msapPlcyTblLastChgd indicates the
                     sysUpTime at the time of the last modification of
                     msapPlcyTable.

                     If no changes were made to the entry since the last
                     re-initialization of the local network management subsystem,
                     then this object contains a zero value."
    ::= { tmnxSapObjs 59 }

msapTlsPlcyTblLastChgd  OBJECT-TYPE
    SYNTAX          TimeStamp
    MAX-ACCESS      read-only
    STATUS          current
    DESCRIPTION     "The value of msapTlsPlcyTblLastChgd indicates the
                     sysUpTime at the time of the last modification of
                     msapTlsPlcyTable.

                     If no changes were made to the entry since the last
                     re-initialization of the local network management subsystem,
                     then this object contains a zero value."
    ::= { tmnxSapObjs 60 }

msapIgmpSnpgMcacLvlTblLastChgd  OBJECT-TYPE
    SYNTAX          TimeStamp
    MAX-ACCESS      read-only
    STATUS          current
    DESCRIPTION     "The value of msapIgmpSnpgMcacLvlTblLastChgd indicates the
                     sysUpTime at the time of the last modification of
                     msapIgmpSnpgMcacLevelTable.

                     If no changes were made to the entry since the last
                     re-initialization of the local network management subsystem,
                     then this object contains a zero value."
    ::= { tmnxSapObjs 61 }

msapIgmpSnpgMcacLagTblLastChgd  OBJECT-TYPE
    SYNTAX          TimeStamp
    MAX-ACCESS      read-only
    STATUS          current
    DESCRIPTION     "The value of msapIgmpSnpgMcacLagTblLastChgd indicates the
                     sysUpTime at the time of the last modification of
                     msapIgmpSnpgMcacLagTable.

                     If no changes were made to the entry since the last
                     re-initialization of the local network management subsystem,
                     then this object contains a zero value."
    ::= { tmnxSapObjs 62 }

msapInfoTblLastChgd  OBJECT-TYPE
    SYNTAX          TimeStamp
    MAX-ACCESS      read-only
    STATUS          current
    DESCRIPTION     "The value of msapInfoTblLastChgd indicates the
                     sysUpTime at the time of the last modification of
                     msapInfoTable.

                     If no changes were made to the entry since the last
                     re-initialization of the local network management subsystem,
                     then this object contains a zero value."
    ::= { tmnxSapObjs 63 }

-- --------------------------------------
-- SAP Notification Objects
-- --------------------------------------
-- tmnxSapNotifyObjs       OBJECT IDENTIFIER ::= ( tmnxSapObjs 100 }

sapNotifyPortId OBJECT-TYPE
    SYNTAX          TmnxPortID
    MAX-ACCESS      accessible-for-notify
    STATUS          current
    DESCRIPTION     "The ID of the access port where a SAP is defined.
                     This object is used by the sapPortStateChangeProcessed
                     notification to indicate the port ID that changed
                     state and that resulted in having the associated
                     sapStatusChanged events suppressed for all SAPs on
                     that port."
    ::= { tmnxSapNotifyObjs 1 }

msapStatus OBJECT-TYPE
    SYNTAX          ConfigStatus
    MAX-ACCESS      accessible-for-notify
    STATUS          current
    DESCRIPTION     "The status of the Managed SAP which is used
                     by the msapStateChanged notification to indicate
                     what state the Managed SAP has entered: 'created',
                     'modified', or 'deleted'."
    ::= { tmnxSapNotifyObjs 2 }

svcManagedSapCreationError OBJECT-TYPE
   SYNTAX         DisplayString
   MAX-ACCESS     accessible-for-notify
   STATUS         current
   DESCRIPTION    "The value of the object svcManagedSapCreationError
                   indicates the reason why the system was unable to create
                   the managed SAP."
   ::= { tmnxSapNotifyObjs 3 }

-- --------------------------------------
-- SAP Notifications
-- --------------------------------------
sapCreated NOTIFICATION-TYPE
    OBJECTS {
        custId,
        svcId,
        svcVpnId,
        sapPortId,
        sapEncapValue
    }
    STATUS          obsolete
    DESCRIPTION     "This trap is sent when a new row is created
                     in the sapBaseInfoTable."
    ::= { sapTraps 1 }

sapDeleted NOTIFICATION-TYPE
    OBJECTS {
        custId,
        svcId,
        svcVpnId,
        sapPortId,
        sapEncapValue
    }
    STATUS          obsolete
    DESCRIPTION     "This trap is sent when an existing row is
                     deleted from the sapBaseInfoTable."
    ::= { sapTraps 2 }

sapStatusChanged NOTIFICATION-TYPE
    OBJECTS {
        custId,
        svcId,
        svcVpnId,
        sapPortId,
        sapEncapValue,
        sapAdminStatus,
        sapOperStatus,
        sapOperFlags
    }
    STATUS          current
    DESCRIPTION     "The sapStatusChanged notification is generated
                     when there is a change in the administrative or
                     operating status of an SAP.

                     Notice that this trap is not generated whenever
                     the SAP operating status change is caused by an
                     operating status change on the associated access
                     port."
    ::= { sapTraps 3 }

sapTlsMacAddrLimitAlarmRaised  NOTIFICATION-TYPE
    OBJECTS {
        custId,
        svcId,
        svcVpnId,
        sapPortId,
        sapEncapValue
    }
    STATUS          current
    DESCRIPTION     "The trap sapTlsMacAddrLimitAlarmRaised is sent whenever
                     the number of MAC addresses stored in the FDB for this SAP
                     increases to reach the watermark specified by the object
                     svcTlsFdbTableFullHighWatermark."
    ::= { sapTraps 4 }

sapTlsMacAddrLimitAlarmCleared  NOTIFICATION-TYPE
    OBJECTS {
        custId,
        svcId,
        svcVpnId,
        sapPortId,
        sapEncapValue
    }
    STATUS          current
    DESCRIPTION     "The trap sapTlsMacAddrLimitAlarmCleared is sent whenever
                     the number of MAC addresses stored in the FDB for this SAP
                     drops to the watermark specified by the object
                     svcTlsFdbTableFullLowWatermark."
    ::= { sapTraps 5 }

sapTlsDHCPLseStEntriesExceeded   NOTIFICATION-TYPE
    OBJECTS {
        custId,
        svcId,
        svcVpnId,
        sapPortId,
        sapEncapValue,
        tlsDhcpLseStateNewCiAddr,
        tlsDhcpLseStateNewChAddr,
        tlsDHCPClientLease
    }
    STATUS          obsolete
    DESCRIPTION     "The sapTlsDHCPLseStEntriesExceeded notification is
                     generated when the number  of  DHCP  lease states
                     entries on a given SAP reaches a user configurable
                     upper limit given by sapTlsDhcpLeasePopulate."
    ::= { sapTraps 6 }

sapTlsDHCPLeaseStateOverride NOTIFICATION-TYPE
    OBJECTS {
        custId,
        svcId,
        svcVpnId,
        sapPortId,
        sapEncapValue,
        tlsDhcpLseStateNewCiAddr,
        tlsDhcpLseStateNewChAddr,
        tlsDhcpLseStateOldCiAddr,
        tlsDhcpLseStateOldChAddr
    }
    STATUS          obsolete
    DESCRIPTION     "The sapTlsDHCPLeaseStateOverride notification is
                     generated when an existing DHCP lease state is
                     overridden by a new lease state which has the same
                     IP address but a different MAC address."
    ::= { sapTraps 7 }

sapTlsDHCPSuspiciousPcktRcvd NOTIFICATION-TYPE
    OBJECTS {
        custId,
        svcId,
        svcVpnId,
        sapPortId,
        sapEncapValue,
        tlsDhcpPacketProblem
    }
    STATUS          obsolete
    DESCRIPTION     "The sapTlsDHCPSuspiciousPcktRcvd notification is
                     generated when a DHCP packet is received with suspicious
                     content."
    ::= { sapTraps 8 }

sapDHCPLeaseEntriesExceeded NOTIFICATION-TYPE
    OBJECTS {
        custId,
        svcId,
        svcVpnId,
        sapPortId,
        sapEncapValue,
        svcDhcpLseStateNewCiAddr,
        svcDhcpLseStateNewChAddr,
        svcDhcpClientLease
    }
    STATUS          current
    DESCRIPTION     "The sapDHCPLeaseEntriesExceeded notification is generated
                     when the number of DHCP lease state entries on a given SAP
                     reaches a user configurable upper limit. This limit is
                     given by sapTlsDhcpLeasePopulate for a TLS service and by
                     ALCATEL-IND1-TIMETRA-VRTR-MIB::vRtrIfDHCPLeasePopulate for an IES or
                     VPRN service."
    ::= { sapTraps 9 }

sapDHCPLseStateOverride NOTIFICATION-TYPE
    OBJECTS {
        custId,
        svcId,
        svcVpnId,
        sapPortId,
        sapEncapValue,
        svcDhcpLseStateNewCiAddr,
        svcDhcpLseStateNewChAddr,
        svcDhcpLseStateOldCiAddr,
        svcDhcpLseStateOldChAddr
    }
    STATUS          current
    DESCRIPTION     "The sapDHCPLseStateOverride notification is generated when
                     an existing DHCP lease state is overridden by a new lease
                     state which has the same IP address but a different MAC
                     address."
    ::= { sapTraps 10 }

sapDHCPSuspiciousPcktRcvd NOTIFICATION-TYPE
    OBJECTS {
        custId,
        svcId,
        svcVpnId,
        sapPortId,
        sapEncapValue,
        svcDhcpPacketProblem
    }
    STATUS          current
    DESCRIPTION     "The sapDHCPSuspiciousPcktRcvd notification is generated
                     when a DHCP packet is received with suspicious content."
    ::= { sapTraps 11 }

sapDHCPLseStatePopulateErr NOTIFICATION-TYPE
    OBJECTS {
        custId,
        svcId,
        svcVpnId,
        sapPortId,
        sapEncapValue,
        svcDhcpLseStatePopulateError
    }
    STATUS          current
    DESCRIPTION     "The sapDHCPLseStatePopulateErr notification indicates that
                     the system was unable to update the DHCP Lease State table
                     with the information contained in the DHCP ACK message.
                     The DHCP ACK message has been discarded."
    ::= { sapTraps 12 }

hostConnectivityLost NOTIFICATION-TYPE
    OBJECTS {
        custId,
        svcId,
        svcVpnId,
        sapPortId,
        sapEncapValue,
        hostConnectivityCiAddrType,
        hostConnectivityCiAddr,
        hostConnectivityChAddr
    }
    STATUS          current
    DESCRIPTION     "The hostConnectivityLost notification indicates that
                     the system lost the connectivity with the indicated host."
    ::= { sapTraps 13 }

hostConnectivityRestored NOTIFICATION-TYPE
    OBJECTS {
        custId,
        svcId,
        svcVpnId,
        sapPortId,
        sapEncapValue,
        hostConnectivityCiAddrType,
        hostConnectivityCiAddr,
        hostConnectivityChAddr
    }
    STATUS          current
    DESCRIPTION     "The hostConnectivityRestored notification indicates that
                     the system has restored the connectivity with the
                     indicated host."
    ::= { sapTraps 14 }

sapReceivedProtSrcMac NOTIFICATION-TYPE
    OBJECTS {
        svcId,
        sapPortId,
        sapEncapValue,
        protectedMacForNotify
    }
    STATUS          current
    DESCRIPTION     "The sapReceivedProtSrcMac notification is generated when a
                     protected source MAC is received on a TLS SAP with
                     sapTlsRestProtSrcMac 'true' and
                     sapTlsRestProtSrcMacAction 'alarm-only', or if the TLS
                     SAP belongs to an SHG with tlsShgRestProtSrcMac 'true'
                     and tlsShgRestProtSrcMacAction 'alarm-only'."
    ::= { sapTraps 15 }

sapStaticHostDynMacConflict NOTIFICATION-TYPE
    OBJECTS {
        svcId,
        sapPortId,
        sapEncapValue,
        staticHostDynamicMacIpAddress,
        staticHostDynamicMacConflict
    }
    STATUS          current
    DESCRIPTION     "The sapStaticHostDynMacConflict notification indicates
                     that the system is trying to learn a conflicting IP-only
                     static host dynamic MAC address
                     (sapStaticHostDynMacAddress)."
    ::= { sapTraps 16 }

sapTlsMacMoveExceeded NOTIFICATION-TYPE
    OBJECTS {
        custId,
        svcId,
        svcVpnId,
        sapPortId,
        sapEncapValue,
        sapAdminStatus,
        sapOperStatus,
        sapTlsMacMoveRateExcdLeft,
        sapTlsMacMoveNextUpTime,
        svcTlsMacMoveMaxRate
    }
    STATUS          current
    DESCRIPTION     "The sapTlsMacMoveExceeded notification is generated
                     when the SAP exceeds the TLS svcTlsMacMoveMaxRate."
    ::= { sapTraps 17 }

sapDHCPProxyServerError NOTIFICATION-TYPE
    OBJECTS {
        custId,
        svcId,
        svcVpnId,
        sapPortId,
        sapEncapValue,
        svcDhcpProxyError
    }
    STATUS          current
    DESCRIPTION     "The sapDHCPProxyServerError notification indicates that
                     the system was unable to proxy DHCP requests."
    ::= { sapTraps 18 }

sapDHCPCoAError NOTIFICATION-TYPE
    OBJECTS {
        custId,
        svcId,
        svcVpnId,
        sapPortId,
        sapEncapValue,
        svcDhcpCoAError
    }
    STATUS          obsolete
    DESCRIPTION     "The sapDHCPCoAError notification indicates that
                     the system was unable to process a Change of Authorization
                     (CoA) request from a Radius server."
    ::= { sapTraps 19 }

sapDHCPSubAuthError NOTIFICATION-TYPE
    OBJECTS {
        custId,
        svcId,
        svcVpnId,
        sapPortId,
        sapEncapValue,
        svcDhcpSubAuthError
    }
    STATUS          obsolete
    DESCRIPTION     "The sapDHCPSubAuthError notification indicates that
                     the system encountered a problem while trying to
                     authenticate a subscriber."
    ::= { sapTraps 20 }

sapPortStateChangeProcessed NOTIFICATION-TYPE
    OBJECTS {
        sapNotifyPortId
    }
    STATUS          current
    DESCRIPTION     "The sapPortStateChangeProcessed notification indicates
                     that the agent has finished processing an access port
                     state change event, and that the operating status of
                     all the affected SAP's has been updated accordingly.
                     The value of the sapNotifyPortId object indicates the
                     ID of the port that experienced the state change."
    ::= { sapTraps 21 }

sapDHCPLseStateMobilityError NOTIFICATION-TYPE
    OBJECTS {
        custId,
        svcId,
        svcVpnId,
        sapPortId,
        sapEncapValue
    }
    STATUS          current
    DESCRIPTION     "The sapDHCPLseStateMobilityError notification indicates
                     that the system was unable to perform a mobility check
                     for this lease state."
    ::= { sapTraps 22 }

sapCemPacketDefectAlarm NOTIFICATION-TYPE
   OBJECTS {
        custId,
        svcVpnId,
        sapCemReportAlarmStatus
   }
   STATUS            current
   DESCRIPTION       "Generated when a CEM SAP alarm condition is detected.
                      It is generated only when the packet error indicated
                      by 'sapCemReportAlarmStatus' persists over a 3 second
                      window."
    ::= { sapTraps 23 }

sapCemPacketDefectAlarmClear NOTIFICATION-TYPE
   OBJECTS {
        custId,
        svcVpnId,
        sapCemReportAlarmStatus
   }
   STATUS            current
   DESCRIPTION       "Generated when a CEM SAP alarm condition is cleared.
                      It is generated only when the packet error indicated
                      by 'sapCemReportAlarmStatus' no longer persists over
                      a 10 second window."
    ::= { sapTraps 24 }

msapStateChanged NOTIFICATION-TYPE
   OBJECTS {
       svcId,
       sapPortId,
       sapEncapValue,
       msapStatus
   }
   STATUS          current
   DESCRIPTION     "The msapStateChanged notification is generated when a
                    Managed SAP is 'created', 'modified', or 'deleted', with the
                    value of msapStatus indicated which state it has entered."
   ::= { sapTraps 25 }

msapCreationFailure  NOTIFICATION-TYPE
   OBJECTS {
       custId,
       svcId,
       svcVpnId,
       sapPortId,
       sapEncapValue,
       svcManagedSapCreationError
   }
   STATUS          current
   DESCRIPTION     "The trap msapCreationFailure is sent whenever
                    the system fails to create a managed SAP.
                    The svcId, svcVpnId, sapPortId and sapEncapValue are
                    those of the capturing SAP."
   ::= { sapTraps 26 }

-- ------------------------------------
-- TLS STP traps
-- ------------------------------------
topologyChangeSapMajorState NOTIFICATION-TYPE
    OBJECTS {
        custId,
        svcId,
        sapPortId,
        sapEncapValue
    }
    STATUS         current
    DESCRIPTION    "The    topologyChangeSapMajorState   notification    is
                    generated  when  a  SAP has transitioned its state from
                    learning  to  forwarding or from forwarding to blocking
                    or broken. The spanning tree topology has been modified
                    and   it   may   denote  loss  of  customer  access  or
                    redundancy.   Check   the   new  topology  against  the
                    provisioned  topology  to  determine  the  severity  of
                    connectivity loss."
    ::= { tstpTraps 1 }

newRootSap NOTIFICATION-TYPE
    OBJECTS {
        custId,
        svcId,
        sapPortId,
        sapEncapValue
    }
    STATUS          current
    DESCRIPTION     "The  newRootSap  notification is  generated  when  the
                     previous  root bridge has been aged out and a new root
                     bridge  has  been elected. A new root bridge creates a
                     new  spanning  tree topology and it may denote loss of
                     customer  access or redundancy. Check the new topology
                     against  the  provisioned  topology  to  determine the
                     severity of connectivity loss."
    ::= { tstpTraps 2 }

topologyChangeSapState NOTIFICATION-TYPE
    OBJECTS {
        custId,
        svcId,
        sapPortId,
        sapEncapValue
    }
    STATUS          current
    DESCRIPTION     "The topologyChangeSapState notification is   generated
                     when  a  SAP  has  transitioned  state  to blocking or
                     broken  from a state other than forwarding. This event
                     complements     what     is     not     covered     by
                     topologyChangeSapMajorState.    The    spanning   tree
                     topology  has  been modified and it may denote loss of
                     customer  access or redundancy. Check the new topology
                     against the provisioned topology to determine severity
                     of connectivity loss."
    ::= { tstpTraps 5 }

receivedTCN NOTIFICATION-TYPE
    OBJECTS {
        custId,
        svcId,
        sapPortId,
        sapEncapValue
    }
    STATUS          current
    DESCRIPTION     "The receivedTCN notification is generated  when  a SAP
                     has received TCN from another bridge. This bridge will
                     either  have  its  configured  BPDU  with the topology
                     change  flag  set  if  it is a root bridge, or it will
                     pass  TCN  to  its root bridge. Eventually the address
                     aging  timer  for the forwarding database will be made
                     shorter  for  a  short  period of time. No recovery is
                     needed."
    ::= { tstpTraps 6 }

higherPriorityBridge NOTIFICATION-TYPE
    OBJECTS {
        custId,
        svcId,
        sapPortId,
        sapEncapValue,
        tmnxCustomerBridgeId,
        tmnxCustomerRootBridgeId
    }
    STATUS          current
    DESCRIPTION     "The higherPriorityBridge notification is generated when
                     a  customer's device has been configured with a bridge
                     priority  equal  to  zero. The SAP that the customer's
                     device  is  connected  through will be blocked. Remove
                     the  customer's  device  or reconfigure the customer's
                     bridge priority with a value greater than zero."
    ::= { tstpTraps 9 }

bridgedTLS NOTIFICATION-TYPE
    OBJECTS {
        custId,
        svcId,
        sapPortId,
        sapEncapValue
    }
    STATUS          obsolete
    DESCRIPTION     "The  bridgedTLS  notification  is  generated  when   a
                     configuration  BPDU  has been received that identifies
                     that  another TLS with a different VPNID is attempting
                     to   bridge   with   this   TLS.   At  least  one  ESR
                     participating  within  one  of the TLS that is locally
                     connected must have an active VCP for this to be seen.
                     The  SAP  that  the  configuration BPDU is received on
                     will  be  blocked  to prevent the TLS to TLS bridging.
                     Reconfigure  the  bridged  TLS  into  a  single TLS or
                     remove the connectivity."
    ::= { tstpTraps 10 }

sapEncapPVST NOTIFICATION-TYPE
    OBJECTS {
        custId,
        svcId,
        sapPortId,
        sapEncapValue,
        tmnxOtherBridgeId
    }
    STATUS          current
    DESCRIPTION     "The sapEncapPVST  notification  is  generated when the
                     SAP  receives  a BPDU that is PVST encapsulated, after
                     having  received  BPDUs  that were 802.d encapsulated.
                     The  SAP  BPDUs  will  also  be  PVST encapsulated. No
                     recovery is needed."
    ::= { tstpTraps 11 }

sapEncapDot1d NOTIFICATION-TYPE
    OBJECTS {
        custId,
        svcId,
        sapPortId,
        sapEncapValue,
        tmnxOtherBridgeId
    }
    STATUS          current
    DESCRIPTION     "The  sapEncapDot1d  notification is generated when the
                     SAP  receives a BPDU that is 802.1d encapsulated after
                     having received BPDUs that were PVST encapsulated. The
                     SAP   BPDUs  will  also  be  802.1d  encapsulated.  No
                     recovery is needed."
    ::= { tstpTraps 12 }

sapReceiveOwnBpdu NOTIFICATION-TYPE
    OBJECTS {
        custId,
        svcId,
        sapPortId,
        sapEncapValue,
        tmnxOtherBridgeId
    }
    STATUS          obsolete
    DESCRIPTION     "The sapReceiveOwnBpdu notification is generated when the
                     SAP STP received it's own BPDU."
    ::= { tstpTraps 13 }

sapActiveProtocolChange NOTIFICATION-TYPE
    OBJECTS {
        custId,
        svcId,
        sapPortId,
        sapEncapValue,
        sapTlsStpOperProtocol
    }
    STATUS          current
    DESCRIPTION     "The sapActiveProtocolChange notification is generated
                     when  the  spanning  tree protocol on this SAP changes
                     from  rstp  to  stp  or  vise  versa.  No  recovery is
                     needed."
    ::= { tstpTraps 30 }

tmnxStpRootGuardViolation NOTIFICATION-TYPE
    OBJECTS {
        svcId,
        sapPortId,
        sapEncapValue,
        sapTlsStpRootGuardViolation
    }
    STATUS          current
    DESCRIPTION     "The tmnxStpRootGuardViolation notification is
                     generated when a SAP which has root-guard configured is
                     trying to become root (has a better STP priority vector).
                     The SAP will become alternate and traffic will be blocked."
    ::= { tstpTraps 35 }

tmnxSapStpExcepCondStateChng NOTIFICATION-TYPE
    OBJECTS {
        custId,
        svcId,
        sapPortId,
        sapEncapValue,
        sapTlsStpException
    }
    STATUS          current
    DESCRIPTION     "The tmnxSapStpExcepCondStateChng notification is
                     generated when the value of the object sapTlsStpException
                     has changed, i.e. when the exception condition
                     changes on the indicated SAP."
    ::= { tstpTraps 37 }

-- ----------------------------------------------------------------------------
-- Conformance Information
-- ----------------------------------------------------------------------------
tmnxSapCompliances  OBJECT IDENTIFIER ::= { tmnxSapConformance 1 }
tmnxSapGroups       OBJECT IDENTIFIER ::= { tmnxSapConformance 2 }

-- ----------------------------------------------
-- Compliance Statements
-- ----------------------------------------------
tmnxSap7450V6v0Compliance MODULE-COMPLIANCE
    STATUS  current
    DESCRIPTION
        "The compliance statement for management of services SAPs
         on Alcatel 7450 ESS series systems."
    MODULE  -- this module
        MANDATORY-GROUPS
        {
           tmnxSapV6v0Group,
           tmnxSapTlsV6v0Group,
           tmnxSapBaseV6v0Group,
           -- tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapNotifyGroup,
           -- tmnxSapCemNotificationV6v0Group,
           -- tmnxTlsMsapPppoeV6v0Group,
           -- tmnxSapCemV6v0Group
           -- tmnxSapIpV6FilterV6v0Group
           tmnxSapDhcpV6v0Group,
           tmnxSapMrpV6v0Group
           -- tmnxSapBsxV6v0Group
       }
    ::= { tmnxSapCompliances 100 }

tmnxSap7750V6v0Compliance MODULE-COMPLIANCE
    STATUS  current
    DESCRIPTION
        "The compliance statement for management of services SAPs
         on Alcatel 7750 SR series systems."
    MODULE  -- this module
        MANDATORY-GROUPS
        {
           tmnxSapV6v0Group,
           tmnxSapTlsV6v0Group,
           tmnxSapBaseV6v0Group,
           tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapNotifyGroup,
           -- tmnxSapCemNotificationV6v0Group,
           tmnxTlsMsapPppoeV6v0Group,
           tmnxSapCemV6v0Group,
           tmnxSapIpV6FilterV6v0Group,
           tmnxSapDhcpV6v0Group,
           tmnxSapMrpV6v0Group
           -- tmnxSapBsxV6v0Group
       }
    ::= { tmnxSapCompliances 101 }

tmnxSap7710V6v0Compliance MODULE-COMPLIANCE
    STATUS  current
    DESCRIPTION
        "The compliance statement for management of services SAPs
         on Alcatel 7710 SR series systems."
    MODULE  -- this module
        MANDATORY-GROUPS
        {
           tmnxSapV6v0Group,
           tmnxSapTlsV6v0Group,
           tmnxSapBaseV6v0Group,
           tmnxSapAtmV6v0Group,
           tmnxSapQosV6v0Group,
           tmnxSapStaticHostV6v0Group,
           tmnxSapPortIdV6v0Group,
           tmnxSapSubMgmtV6v0Group,
           tmnxSapMstiV6v0Group,
           tmnxSapIppipeV6v0Group,
           tmnxSapPolicyV6v0Group,
           tmnxSapL2ptV6v0Group,
           tmnxSapMsapV6v0Group,
           tmnxSapNotifyGroup,
           tmnxSapCemNotificationV6v0Group,
           tmnxTlsMsapPppoeV6v0Group,
           tmnxSapCemV6v0Group,
           tmnxSapIpV6FilterV6v0Group,
           tmnxSapDhcpV6v0Group,
           tmnxSapMrpV6v0Group
           -- tmnxSapBsxV6v0Group           no Application Assurance on 7710
       }
    ::= { tmnxSapCompliances 102 }

-- ----------------------
-- SAP Group
-- ----------------------

tmnxSapV6v0Group OBJECT-GROUP
    OBJECTS {
      sapNumEntries,
      sapPortId,
      sapEncapValue,
      sapRowStatus,
      sapType,
      sapDescription,
      sapAdminStatus,
      sapOperStatus,
      sapIngressQosPolicyId,
      sapIngressMacFilterId,
      sapIngressIpFilterId,
      sapIngressVlanTranslationId,
      sapEgressQosPolicyId,
      sapEgressMacFilterId,
      sapEgressIpFilterId,
      sapMirrorStatus,
      sapIesIfIndex,
      sapLastMgmtChange,
      sapCollectAcctStats,
      sapAccountingPolicyId,
      sapVpnId,
      sapCustId,
      sapCustMultSvcSite,
      sapIngressQosSchedulerPolicy,
      sapEgressQosSchedulerPolicy,
      sapSplitHorizonGrp,
      sapIngressSharedQueuePolicy,
      sapIngressMatchQinQDot1PBits,
      sapOperFlags,
      sapLastStatusChange,
      sapAntiSpoofing,
      sapTodSuite,
      sapIngUseMultipointShared,
      sapEgressQinQMarkTopOnly,
      sapEgressAggRateLimit,
      sapEndPoint,
      sapIngressVlanTranslation,
      sapSubType,
      sapCpmProtPolicyId,
      sapCpmProtMonitorMac,
      sapEgressFrameBasedAccounting,
      sapEthernetLLFAdminStatus,
      sapEthernetLLFOperStatus,
      sapTlsMvplsRowStatus,
      sapAntiSpoofIpAddress,
      sapAntiSpoofMacAddress
    }
    STATUS      current
    DESCRIPTION
        "The group of objects supporting management of Sap
         general capabilities on Alcatel 7x50 SR series systems."
    ::= { tmnxSapGroups 100 }


tmnxSapTlsV6v0Group OBJECT-GROUP
    OBJECTS {
      sapTlsStpAdminStatus,
      sapTlsStpPriority,
      sapTlsStpPortNum,
      sapTlsStpPathCost,
      sapTlsStpRapidStart,
      sapTlsStpBpduEncap,
      sapTlsStpPortState,
      sapTlsStpDesignatedBridge,
      sapTlsStpDesignatedPort,
      sapTlsStpForwardTransitions,
      sapTlsStpInConfigBpdus,
      sapTlsStpInTcnBpdus,
      sapTlsStpInBadBpdus,
      sapTlsStpOutConfigBpdus,
      sapTlsStpOutTcnBpdus,
      sapTlsStpOperBpduEncap,
      sapTlsVpnId,
      sapTlsCustId,
      sapTlsMacAddressLimit,
      sapTlsNumMacAddresses,
      sapTlsNumStaticMacAddresses,
      sapTlsMacLearning,
      sapTlsMacAgeing,
      sapTlsStpOperEdge,
      sapTlsStpAdminPointToPoint,
      sapTlsStpPortRole,
      sapTlsStpAutoEdge,
      sapTlsStpOperProtocol,
      sapTlsStpInRstBpdus,
      sapTlsStpOutRstBpdus,
      sapTlsLimitMacMove,
      sapTlsMacPinning,
      sapTlsDiscardUnknownSource,
      sapTlsMvplsPruneState,
      sapTlsMvplsMgmtService,
      sapTlsMvplsMgmtPortId,
      sapTlsMvplsMgmtEncapValue,
      sapTlsArpReplyAgent,
      sapTlsStpException,
      sapTlsAuthenticationPolicy,
      sapTlsL2ptTermination,
      sapTlsBpduTranslation,
      sapTlsStpRootGuard,
      sapTlsStpInsideRegion,
      sapTlsEgressMcastGroup,
      sapTlsStpInMstBpdus,
      sapTlsStpOutMstBpdus,
      sapTlsRestProtSrcMac,
      sapTlsRestProtSrcMacAction,
      sapTlsRestUnprotDstMac,
      sapTlsStpRxdDesigBridge,
      sapTlsStpRootGuardViolation,
      sapTlsShcvAction,
      sapTlsShcvSrcIp,
      sapTlsShcvSrcMac,
      sapTlsShcvInterval,
      sapTlsMvplsMgmtMsti,
      sapTlsMacMoveNextUpTime,
      sapTlsMacMoveRateExcdLeft,
      sapTlsL2ptForceBoundary,
      sapTlsLimitMacMoveLevel,
      sapTlsBpduTransOper,
      sapTlsDefMsapPolicy,
      sapTlsL2ptProtocols,
      sapTlsL2ptForceProtocols,
      sapTlsDhcpMsapTrigger,
      sapTlsDhcpProxyLeaseTime,
      sapTlsDhcpRemoteId,
      sapTlsMrpJoinTime,
      sapTlsMrpLeaveTime,
      sapTlsMrpLeaveAllTime,
      sapTlsMrpPeriodicTime,
      sapTlsMrpPeriodicEnabled
      }
    STATUS      current
    DESCRIPTION
        "The group of objects supporting management of Sap
         TLS capabilities on Alcatel 7x50 SR series systems."
    ::= { tmnxSapGroups 101 }

tmnxSapAtmV6v0Group OBJECT-GROUP
    OBJECTS {
      sapAtmEncapsulation,
      sapAtmIngressTrafficDescIndex,
      sapAtmEgressTrafficDescIndex,
      sapAtmOamAlarmCellHandling,
      sapAtmOamTerminate,
      sapAtmOamPeriodicLoopback
      }
    STATUS      current
    DESCRIPTION
        "The group of objects supporting management of Sap
         ATM capabilities on Alcatel 7x50 SR series systems."
    ::= { tmnxSapGroups 102 }

tmnxSapBaseV6v0Group OBJECT-GROUP
    OBJECTS {
      sapBaseStatsIngressPchipDroppedPackets,
      sapBaseStatsIngressPchipDroppedOctets,
      sapBaseStatsIngressPchipOfferedHiPrioPackets,
      sapBaseStatsIngressPchipOfferedHiPrioOctets,
      sapBaseStatsIngressPchipOfferedLoPrioPackets,
      sapBaseStatsIngressPchipOfferedLoPrioOctets,
      sapBaseStatsIngressQchipDroppedHiPrioPackets,
      sapBaseStatsIngressQchipDroppedHiPrioOctets,
      sapBaseStatsIngressQchipDroppedLoPrioPackets,
      sapBaseStatsIngressQchipDroppedLoPrioOctets,
      sapBaseStatsIngressQchipForwardedInProfPackets,
      sapBaseStatsIngressQchipForwardedInProfOctets,
      sapBaseStatsIngressQchipForwardedOutProfPackets,
      sapBaseStatsIngressQchipForwardedOutProfOctets,
      sapBaseStatsEgressQchipDroppedInProfPackets,
      sapBaseStatsEgressQchipDroppedInProfOctets,
      sapBaseStatsEgressQchipDroppedOutProfPackets,
      sapBaseStatsEgressQchipDroppedOutProfOctets,
      sapBaseStatsEgressQchipForwardedInProfPackets,
      sapBaseStatsEgressQchipForwardedInProfOctets,
      sapBaseStatsEgressQchipForwardedOutProfPackets,
      sapBaseStatsEgressQchipForwardedOutProfOctets,
      sapBaseStatsCustId,
      sapBaseStatsIngressPchipOfferedUncoloredPackets,
      sapBaseStatsIngressPchipOfferedUncoloredOctets,
      sapBaseStatsAuthenticationPktsDiscarded,
      sapBaseStatsAuthenticationPktsSuccess,
      sapBaseStatsLastClearedTime
      }
    STATUS      current
    DESCRIPTION
        "The group of objects supporting management of Sap
         Base capabilities on Alcatel 7x50 SR series systems."
    ::= { tmnxSapGroups 103 }

tmnxSapQosV6v0Group OBJECT-GROUP
    OBJECTS {
      sapIngQosQueueId,
      sapIngQosQueueStatsOfferedHiPrioPackets,
      sapIngQosQueueStatsDroppedHiPrioPackets,
      sapIngQosQueueStatsOfferedLoPrioPackets,
      sapIngQosQueueStatsDroppedLoPrioPackets,
      sapIngQosQueueStatsOfferedHiPrioOctets,
      sapIngQosQueueStatsDroppedHiPrioOctets,
      sapIngQosQueueStatsOfferedLoPrioOctets,
      sapIngQosQueueStatsDroppedLoPrioOctets,
      sapIngQosQueueStatsForwardedInProfPackets,
      sapIngQosQueueStatsForwardedOutProfPackets,
      sapIngQosQueueStatsForwardedInProfOctets,
      sapIngQosQueueStatsForwardedOutProfOctets,
      sapIngQosCustId,
      sapIngQosQueueStatsUncoloredPacketsOffered,
      sapIngQosQueueStatsUncoloredOctetsOffered,
      sapEgrQosQueueId,
      sapEgrQosQueueStatsForwardedInProfPackets,
      sapEgrQosQueueStatsDroppedInProfPackets,
      sapEgrQosQueueStatsForwardedOutProfPackets,
      sapEgrQosQueueStatsDroppedOutProfPackets,
      sapEgrQosQueueStatsForwardedInProfOctets,
      sapEgrQosQueueStatsDroppedInProfOctets,
      sapEgrQosQueueStatsForwardedOutProfOctets,
      sapEgrQosQueueStatsDroppedOutProfOctets,
      sapEgrQosCustId,
      sapIngQosSchedStatsForwardedPackets,
      sapIngQosSchedStatsForwardedOctets,
      sapIngQosSchedCustId,
      sapEgrQosSchedStatsForwardedPackets,
      sapEgrQosSchedStatsForwardedOctets,
      sapEgrQosSchedCustId,

      sapIngQosQRowStatus,
      sapIngQosQLastMgmtChange,
      sapIngQosQOverrideFlags,
      sapIngQosQCBS,
      sapIngQosQMBS,
      sapIngQosQHiPrioOnly,
      sapIngQosQCIRAdaptation,
      sapIngQosQPIRAdaptation,
      sapIngQosQAdminPIR,
      sapIngQosQAdminCIR,
      sapEgrQosQRowStatus,
      sapEgrQosQLastMgmtChange,
      sapEgrQosQOverrideFlags,
      sapEgrQosQCBS,
      sapEgrQosQMBS,
      sapEgrQosQHiPrioOnly,
      sapEgrQosQCIRAdaptation,
      sapEgrQosQPIRAdaptation,
      sapEgrQosQAdminPIR,
      sapEgrQosQAdminCIR,
      sapEgrQosQAvgOverhead,
      sapIngQosSRowStatus,
      sapIngQosSLastMgmtChange,
      sapIngQosSOverrideFlags,
      sapIngQosSPIR,
      sapIngQosSCIR,
      sapIngQosSSummedCIR,
      sapEgrQosSRowStatus,
      sapEgrQosSLastMgmtChange,
      sapEgrQosSOverrideFlags,
      sapEgrQosSPIR,
      sapEgrQosSCIR,
      sapEgrQosSSummedCIR
      }
    STATUS      current
    DESCRIPTION
        "The group of objects supporting management of Sap
         Ingress/Egress QoS capabilities on Alcatel 7x50 SR series systems."
    ::= { tmnxSapGroups 104 }

tmnxSapStaticHostV6v0Group OBJECT-GROUP
    OBJECTS {
      sapStaticHostRowStatus,
      sapStaticHostSubscrIdent,
      sapStaticHostSubProfile,
      sapStaticHostSlaProfile,
      sapStaticHostShcvOperState,
      sapStaticHostShcvChecks,
      sapStaticHostShcvReplies,
      sapStaticHostShcvReplyTime,
      sapStaticHostDynMacAddress,
      sapStaticHostRetailerSvcId,
      sapStaticHostRetailerIf,
      sapStaticHostFwdingState,
      sapStaticHostAncpString,
      sapStaticHostSubIdIsSapId,
      sapStaticHostIntermediateDestId
      }
    STATUS      current
    DESCRIPTION
        "The group of objects supporting management of Sap
         static host capabilities on Alcatel 7x50 SR series systems."
    ::= { tmnxSapGroups 105 }


tmnxSapDhcpV6v0Group OBJECT-GROUP
    OBJECTS {
      sapTlsDhcpAdminState,
      sapTlsDhcpDescription,
      sapTlsDhcpSnoop,
      sapTlsDhcpLeasePopulate,
      sapTlsDhcpOperLeasePopulate,
      sapTlsDhcpInfoAction,
      sapTlsDhcpCircuitId,
      sapTlsDhcpRemoteIdString,
      sapTlsDhcpProxyAdminState,
      sapTlsDhcpProxyServerAddr,
      sapTlsDhcpProxyLTRadiusOverride,
      sapTlsDhcpVendorIncludeOptions,
      sapTlsDhcpVendorOptionString,
      sapTlsDhcpStatsClntSnoopdPckts,
      sapTlsDhcpStatsSrvrSnoopdPckts,
      sapTlsDhcpStatsClntForwdPckts,
      sapTlsDhcpStatsSrvrForwdPckts,
      sapTlsDhcpStatsClntDropdPckts,
      sapTlsDhcpStatsSrvrDropdPckts,
      sapTlsDhcpStatsClntProxRadPckts,
      sapTlsDhcpStatsClntProxLSPckts,
      sapTlsDhcpStatsGenReleasePckts,
      sapTlsDhcpStatsGenForceRenPckts,
      sapDhcpOperLeasePopulate
      }
    STATUS      current
    DESCRIPTION
        "The group of objects supporting management of Sap
         TLS DHCP capabilities on Alcatel 7x50 SR series systems."
    ::= { tmnxSapGroups 106 }


tmnxSapPortIdV6v0Group OBJECT-GROUP
    OBJECTS {
      sapPortIdIngQosSchedFwdPkts,
      sapPortIdIngQosSchedFwdOctets,
      sapPortIdIngQosSchedCustId,
      sapPortIdEgrQosSchedFwdPkts,
      sapPortIdEgrQosSchedFwdOctets,
      sapPortIdEgrQosSchedCustId
      }
    STATUS      current
    DESCRIPTION
        "The group of objects supporting management of Sap
         Port ID capabilities on Alcatel 7x50 SR series systems."
    ::= { tmnxSapGroups 107 }


tmnxSapSubMgmtV6v0Group OBJECT-GROUP
    OBJECTS {
      sapSubMgmtAdminStatus,
      sapSubMgmtDefSubProfile,
      sapSubMgmtDefSlaProfile,
      sapSubMgmtSubIdentPolicy,
      sapSubMgmtSubscriberLimit,
      sapSubMgmtProfiledTrafficOnly,
      sapSubMgmtNonSubTrafficSubIdent,
      sapSubMgmtNonSubTrafficSubProf,
      sapSubMgmtNonSubTrafficSlaProf,
      sapSubMgmtMacDaHashing,
      sapSubMgmtDefSubIdent,
      sapSubMgmtDefSubIdentString
      }
    STATUS      current
    DESCRIPTION
        "The group of objects supporting management of Sap
         Sub-management capabilities on Alcatel 7x50 SR series systems."
    ::= { tmnxSapGroups 108 }


tmnxSapMstiV6v0Group OBJECT-GROUP
    OBJECTS {
      sapTlsMstiPriority,
      sapTlsMstiPathCost,
      sapTlsMstiLastMgmtChange,
      sapTlsMstiPortRole,
      sapTlsMstiPortState,
      sapTlsMstiDesignatedBridge,
      sapTlsMstiDesignatedPort
      }
    STATUS      current
    DESCRIPTION
        "The group of objects supporting management of Sap
         TLS MSTI capabilities on Alcatel 7x50 SR series systems."
    ::= { tmnxSapGroups 109 }


tmnxSapIppipeV6v0Group OBJECT-GROUP
    OBJECTS {
      sapIpipeCeInetAddress,
      sapIpipeCeInetAddressType,
      sapIpipeMacRefreshInterval,
      sapIpipeMacAddress,
      sapIpipeArpedMacAddress,
      sapIpipeArpedMacAddressTimeout
      }
    STATUS      current
    DESCRIPTION
        "The group of objects supporting management of Sap
         I-Pipe capabilities on Alcatel 7x50 SR series systems."
    ::= { tmnxSapGroups 110 }

tmnxSapPolicyV6v0Group OBJECT-GROUP
    OBJECTS {
      sapCurrentIngressIpFilterId,
      sapCurrentIngressMacFilterId,
      sapCurrentIngressQosPolicyId,
      sapCurrentIngressQosSchedPlcy,
      sapCurrentEgressIpFilterId,
      sapCurrentEgressMacFilterId,
      sapCurrentEgressQosPolicyId,
      sapCurrentEgressQosSchedPlcy,
      sapIntendedIngressIpFilterId,
      sapIntendedIngressMacFilterId,
      sapIntendedIngressQosPolicyId,
      sapIntendedIngressQosSchedPlcy,
      sapIntendedEgressIpFilterId,
      sapIntendedEgressMacFilterId,
      sapIntendedEgressQosPolicyId,
      sapIntendedEgressQosSchedPlcy,

      sapIgQosPlcyDroppedHiPrioPackets,
      sapIgQosPlcyDroppedHiPrioOctets,
      sapIgQosPlcyDroppedLoPrioPackets,
      sapIgQosPlcyDroppedLoPrioOctets,
      sapIgQosPlcyForwardedInProfPackets,
      sapIgQosPlcyForwardedInProfOctets,
      sapIgQosPlcyForwardedOutProfPackets,
      sapIgQosPlcyForwardedOutProfOctets,
      sapEgQosPlcyDroppedInProfPackets,
      sapEgQosPlcyDroppedInProfOctets,
      sapEgQosPlcyDroppedOutProfPackets,
      sapEgQosPlcyDroppedOutProfOctets,
      sapEgQosPlcyForwardedInProfPackets,
      sapEgQosPlcyForwardedInProfOctets,
      sapEgQosPlcyForwardedOutProfPackets,
      sapEgQosPlcyForwardedOutProfOctets,
      sapIgQosPlcyQueueStatsOfferedHiPrioPackets,
      sapIgQosPlcyQueueStatsDroppedHiPrioPackets,
      sapIgQosPlcyQueueStatsOfferedLoPrioPackets,
      sapIgQosPlcyQueueStatsDroppedLoPrioPackets,
      sapIgQosPlcyQueueStatsOfferedHiPrioOctets,
      sapIgQosPlcyQueueStatsDroppedHiPrioOctets,
      sapIgQosPlcyQueueStatsOfferedLoPrioOctets,
      sapIgQosPlcyQueueStatsDroppedLoPrioOctets,
      sapIgQosPlcyQueueStatsForwardedInProfPackets,
      sapIgQosPlcyQueueStatsForwardedOutProfPackets,
      sapIgQosPlcyQueueStatsForwardedInProfOctets,
      sapIgQosPlcyQueueStatsForwardedOutProfOctets,
      sapIgQosPlcyQueueCustId,
      sapIgQosPlcyQueueStatsUncoloredPacketsOffered,
      sapIgQosPlcyQueueStatsUncoloredOctetsOffered,
      sapEgQosPlcyQueueStatsForwardedInProfPackets,
      sapEgQosPlcyQueueStatsDroppedInProfPackets,
      sapEgQosPlcyQueueStatsForwardedOutProfPackets,
      sapEgQosPlcyQueueStatsDroppedOutProfPackets,
      sapEgQosPlcyQueueStatsForwardedInProfOctets,
      sapEgQosPlcyQueueStatsDroppedInProfOctets,
      sapEgQosPlcyQueueStatsForwardedOutProfOctets,
      sapEgQosPlcyQueueStatsDroppedOutProfOctets,
      sapEgQosPlcyQueueCustId,

      sapIngSchedPlcyStatsFwdPkt,
      sapIngSchedPlcyStatsFwdOct,
      sapEgrSchedPlcyStatsFwdPkt,
      sapEgrSchedPlcyStatsFwdOct,
      sapEgrSchedPlcyPortStatsPort,
      sapIngSchedPlcyPortStatsFwdPkt,
      sapIngSchedPlcyPortStatsFwdOct,
      sapIngSchedPlcyPortStatsPort,
      sapEgrSchedPlcyPortStatsFwdPkt,
      sapEgrSchedPlcyPortStatsFwdOct
      }
    STATUS      current
    DESCRIPTION
        "The group of objects supporting management of Sap
         ingress/egress capabilities on Alcatel 7x50 SR series systems."
    ::= { tmnxSapGroups 111 }


tmnxSapCemV6v0Group OBJECT-GROUP
    OBJECTS {
      sapCemLastMgmtChange,
      sapCemEndpointType,
      sapCemBitrate,
      sapCemCasTrunkFraming,
      sapCemPayloadSize,
      sapCemJitterBuffer,
      sapCemUseRtpHeader,
      sapCemDifferential,
      sapCemTimestampFreq,
      sapCemReportAlarm,
      sapCemReportAlarmStatus,
      sapCemLocalEcid,
      sapCemRemoteMacAddr,
      sapCemRemoteEcid,
      sapCemStatsIngressForwardedPkts,
      sapCemStatsIngressDroppedPkts,
      sapCemStatsEgressForwardedPkts,
      sapCemStatsEgressDroppedPkts,
      sapCemStatsEgressMissingPkts,
      sapCemStatsEgressPktsReOrder,
      sapCemStatsEgressJtrBfrUnderruns,
      sapCemStatsEgressJtrBfrOverruns,
      sapCemStatsEgressMisOrderDropped,
      sapCemStatsEgressMalformedPkts,
      sapCemStatsEgressLBitDropped,
      sapCemStatsEgressMultipleDropped,
      sapCemStatsEgressESs,
      sapCemStatsEgressSESs,
      sapCemStatsEgressUASs,
      sapCemStatsEgressFailureCounts,
      sapCemStatsEgressUnderrunCounts,
      sapCemStatsEgressOverrunCounts
      }
    STATUS      current
    DESCRIPTION
        "The group of objects supporting management of Sap
         Cem capabilities on Alcatel 7x50 SR series systems."
    ::= { tmnxSapGroups 112 }


tmnxSapL2ptV6v0Group OBJECT-GROUP
    OBJECTS {
      sapTlsL2ptStatsLastClearedTime,
      sapTlsL2ptStatsL2ptEncapStpConfigBpdusRx,
      sapTlsL2ptStatsL2ptEncapStpConfigBpdusTx,
      sapTlsL2ptStatsL2ptEncapStpRstBpdusRx,
      sapTlsL2ptStatsL2ptEncapStpRstBpdusTx,
      sapTlsL2ptStatsL2ptEncapStpTcnBpdusRx,
      sapTlsL2ptStatsL2ptEncapStpTcnBpdusTx,
      sapTlsL2ptStatsL2ptEncapPvstConfigBpdusRx,
      sapTlsL2ptStatsL2ptEncapPvstConfigBpdusTx,
      sapTlsL2ptStatsL2ptEncapPvstRstBpdusRx,
      sapTlsL2ptStatsL2ptEncapPvstRstBpdusTx,
      sapTlsL2ptStatsL2ptEncapPvstTcnBpdusRx,
      sapTlsL2ptStatsL2ptEncapPvstTcnBpdusTx,
      sapTlsL2ptStatsStpConfigBpdusRx,
      sapTlsL2ptStatsStpConfigBpdusTx,
      sapTlsL2ptStatsStpRstBpdusRx,
      sapTlsL2ptStatsStpRstBpdusTx,
      sapTlsL2ptStatsStpTcnBpdusRx,
      sapTlsL2ptStatsStpTcnBpdusTx,
      sapTlsL2ptStatsPvstConfigBpdusRx,
      sapTlsL2ptStatsPvstConfigBpdusTx,
      sapTlsL2ptStatsPvstRstBpdusRx,
      sapTlsL2ptStatsPvstRstBpdusTx,
      sapTlsL2ptStatsPvstTcnBpdusRx,
      sapTlsL2ptStatsPvstTcnBpdusTx,
      sapTlsL2ptStatsOtherBpdusRx,
      sapTlsL2ptStatsOtherBpdusTx,
      sapTlsL2ptStatsOtherL2ptBpdusRx,
      sapTlsL2ptStatsOtherL2ptBpdusTx,
      sapTlsL2ptStatsOtherInvalidBpdusRx,
      sapTlsL2ptStatsOtherInvalidBpdusTx,
      sapTlsL2ptStatsL2ptEncapCdpBpdusRx,
      sapTlsL2ptStatsL2ptEncapCdpBpdusTx,
      sapTlsL2ptStatsL2ptEncapVtpBpdusRx,
      sapTlsL2ptStatsL2ptEncapVtpBpdusTx,
      sapTlsL2ptStatsL2ptEncapDtpBpdusRx,
      sapTlsL2ptStatsL2ptEncapDtpBpdusTx,
      sapTlsL2ptStatsL2ptEncapPagpBpdusRx,
      sapTlsL2ptStatsL2ptEncapPagpBpdusTx,
      sapTlsL2ptStatsL2ptEncapUdldBpdusRx,
      sapTlsL2ptStatsL2ptEncapUdldBpdusTx,
      sapTlsL2ptStatsCdpBpdusRx,
      sapTlsL2ptStatsCdpBpdusTx,
      sapTlsL2ptStatsVtpBpdusRx,
      sapTlsL2ptStatsVtpBpdusTx,
      sapTlsL2ptStatsDtpBpdusRx,
      sapTlsL2ptStatsDtpBpdusTx,
      sapTlsL2ptStatsPagpBpdusRx,
      sapTlsL2ptStatsPagpBpdusTx,
      sapTlsL2ptStatsUdldBpdusRx,
      sapTlsL2ptStatsUdldBpdusTx
      }
    STATUS      current
    DESCRIPTION
        "The group of objects supporting management of Sap
         TLS L2pt capabilities on Alcatel 7x50 SR series systems."
    ::= { tmnxSapGroups 113 }


tmnxSapMsapV6v0Group OBJECT-GROUP
    OBJECTS {
      msapPlcyRowStatus,
      msapPlcyLastChanged,
      msapPlcyDescription,
      msapPlcyCpmProtPolicyId,
      msapPlcyCpmProtMonitorMac,
      msapPlcySubMgmtDefSubId,
      msapPlcySubMgmtDefSubIdStr,
      msapPlcySubMgmtDefSubProfile,
      msapPlcySubMgmtDefSlaProfile,
      msapPlcySubMgmtSubIdPlcy,
      msapPlcySubMgmtSubscriberLimit,
      msapPlcySubMgmtProfiledTrafOnly,
      msapPlcySubMgmtNonSubTrafSubId,
      msapPlcySubMgmtNonSubTrafSubProf,
      msapPlcySubMgmtNonSubTrafSlaProf,
      msapPlcyAssociatedMsaps,
      msapTlsPlcyLastChanged,
      msapTlsPlcySplitHorizonGrp,
      msapTlsPlcyArpReplyAgent,
      msapTlsPlcySubMgmtMacDaHashing,
      msapTlsPlcyDhcpLeasePopulate,
      msapTlsPlcyDhcpPrxyAdminState,
      msapTlsPlcyDhcpPrxyServAddr,
      msapTlsPlcyDhcpPrxyServAddrType,
      msapTlsPlcyDhcpPrxyLTRadOverride,
      msapTlsPlcyDhcpInfoAction,
      msapTlsPlcyDhcpCircuitId,
      msapTlsPlcyDhcpRemoteId,
      msapTlsPlcyDhcpRemoteIdString,
      msapTlsPlcyDhcpVendorInclOpts,
      msapTlsPlcyDhcpVendorOptStr,
      msapTlsPlcyDhcpPrxyLeaseTime,
      msapTlsPlcyEgressMcastGroup,
      msapTlsPlcyIgmpSnpgImportPlcy,
      msapTlsPlcyIgmpSnpgFastLeave,
      msapTlsPlcyIgmpSnpgSendQueries,
      msapTlsPlcyIgmpSnpgGenQueryIntv,
      msapTlsPlcyIgmpSnpgQueryRespIntv,
      msapTlsPlcyIgmpSnpgRobustCount,
      msapTlsPlcyIgmpSnpgLastMembIntvl,
      msapTlsPlcyIgmpSnpgMaxNbrGrps,
      msapTlsPlcyIgmpSnpgMvrFromVplsId,
      msapTlsPlcyIgmpSnpgVersion,
      msapTlsPlcyIgmpSnpgMcacPlcyName,
      msapTlsPlcyIgmpSnpgMcacPrRsvMnBW,
      msapTlsPlcyIgmpSnpgMcacUncnstBW,

      msapIgmpSnpgMcacLevelRowStatus,
      msapIgmpSnpgMcacLevelLastChanged,
      msapIgmpSnpgMcacLevelBW,
      msapIgmpSnpgMcacLagRowStatus,
      msapIgmpSnpgMcacLagLastChanged,
      msapIgmpSnpgMcacLagLevel,
      msapInfoCreationSapPortEncapVal,
      msapInfoCreationPlcyName,
      msapInfoReEvalPolicy,
      msapInfoLastChanged,
      msapCaptureSapStatsPktsRecvd,
      msapCaptureSapStatsPktsRedirect,
      msapCaptureSapStatsPktsDropped,
      msapPlcyTblLastChgd,
      msapTlsPlcyTblLastChgd,
      msapIgmpSnpgMcacLvlTblLastChgd,
      msapIgmpSnpgMcacLagTblLastChgd,
      msapInfoTblLastChgd
      }
    STATUS      current
    DESCRIPTION
        "The group of objects supporting management of
         managed SAP capabilities on Alcatel 7x50 SR series systems."
    ::= { tmnxSapGroups 114 }


tmnxSapMrpV6v0Group OBJECT-GROUP
    OBJECTS {
      sapTlsMrpRxPdus,
      sapTlsMrpDroppedPdus,
      sapTlsMrpTxPdus,
      sapTlsMrpRxNewEvent,
      sapTlsMrpRxJoinInEvent,
      sapTlsMrpRxInEvent,
      sapTlsMrpRxJoinEmptyEvent,
      sapTlsMrpRxEmptyEvent,
      sapTlsMrpRxLeaveEvent,
      sapTlsMrpTxNewEvent,
      sapTlsMrpTxJoinInEvent,
      sapTlsMrpTxInEvent,
      sapTlsMrpTxJoinEmptyEvent,
      sapTlsMrpTxEmptyEvent,
      sapTlsMrpTxLeaveEvent,
      sapTlsMmrpDeclared,
      sapTlsMmrpRegistered
      }
    STATUS      current
    DESCRIPTION
        "The group of objects supporting management of Sap
         MRP capabilities on Alcatel 7x50 SR series systems."
    ::= { tmnxSapGroups 115 }

tmnxTlsMsapPppoeV6v0Group OBJECT-GROUP
    OBJECTS {
        sapTlsPppoeMsapTrigger
    }
    STATUS      current
    DESCRIPTION
        "The group of objects supporting PPPOE on Managed SAPs
         feature on the Alcatel 7x50 SR series systems."
    ::= { tmnxSapGroups 117 }

tmnxSapIpV6FilterV6v0Group OBJECT-GROUP
    OBJECTS {
      sapIngressIpv6FilterId,
      sapEgressIpv6FilterId,
      sapCurrentIngressIpv6FilterId,
      sapCurrentEgressIpv6FilterId,
      sapIntendedIngressIpv6FilterId,
      sapIntendedEgressIpv6FilterId
    }
    STATUS      current
    DESCRIPTION
        "The group of objects supporting management of Sap Ingress Policy
         capabilities on Alcatel 7x50 SR series systems."
    ::= { tmnxSapGroups 118 }

tmnxSapBsxV6v0Group OBJECT-GROUP
    OBJECTS {
      sapStaticHostAppProfile,
      sapSubMgmtDefAppProfile,
      sapSubMgmtNonSubTrafficAppProf,
      msapPlcySubMgmtDefAppProfile,
      msapPlcySubMgmtNonSubTrafAppProf
      }
    STATUS      current
    DESCRIPTION
        "The group of objects supporting management of BSX (Application
         Assurance) capabilities on Alcatel 7x50 SR series systems."
    ::= { tmnxSapGroups 119 }

-- Notification objects

tmnxSapNotificationObjV6v0Group OBJECT-GROUP
    OBJECTS {
      sapNotifyPortId,
      svcManagedSapCreationError,
      msapStatus
    }
    STATUS      current
    DESCRIPTION
        "The group of objects supporting management of notifications
         on Alcatel 7x50 SR series systems."
    ::= { tmnxSapGroups 200 }

-- Obsoleted Group
tmnxSapObsoletedV6v0Group OBJECT-GROUP
    OBJECTS {
      sapTlsDhcpSnooping,
      sapTlsDhcpLseStateRemainLseTime,
      sapTlsDhcpLseStateOption82,
      sapTlsDhcpLseStatePersistKey
    }
    STATUS      current
    DESCRIPTION
        "The group of obsolete objects for the services feature
         on Alcatel 7x50 SR series systems."
    ::= { tmnxSapGroups 300 }

-- NOTIFICATION Group
tmnxSapNotifyGroup NOTIFICATION-GROUP
    NOTIFICATIONS   {
      sapStatusChanged,
      sapTlsMacAddrLimitAlarmRaised,
      sapTlsMacAddrLimitAlarmCleared,
      sapDHCPLeaseEntriesExceeded,
      sapDHCPLseStateOverride,
      sapDHCPSuspiciousPcktRcvd,
      sapDHCPLseStatePopulateErr,
      hostConnectivityLost,
      hostConnectivityRestored,
      sapReceivedProtSrcMac,
      sapStaticHostDynMacConflict,
      sapTlsMacMoveExceeded,
      sapDHCPProxyServerError,
      sapPortStateChangeProcessed,
      sapDHCPLseStateMobilityError,
      msapStateChanged,
      msapCreationFailure,
      topologyChangeSapMajorState,
      newRootSap,
      topologyChangeSapState,
      receivedTCN,
      higherPriorityBridge,
      sapEncapPVST,
      sapEncapDot1d,
      sapActiveProtocolChange,
      tmnxStpRootGuardViolation,
      tmnxSapStpExcepCondStateChng
    }
    STATUS      current
    DESCRIPTION
        "The group of obsolete notifications for the Sap feature
         on Alcatel 7x50 SR series systems."
    ::= { tmnxSapGroups 400 }

tmnxSapCemNotificationV6v0Group NOTIFICATION-GROUP
    NOTIFICATIONS   {
        sapCemPacketDefectAlarm,
        sapCemPacketDefectAlarmClear
    }
    STATUS      current
    DESCRIPTION
        "The group of notifications supporting the CEM Sap feature
         on Alcatel 7710 SR series systems."
    ::= { tmnxSapGroups 401 }

tmnxSapObsoletedNotifyGroup NOTIFICATION-GROUP
    NOTIFICATIONS   {
      sapCreated,
      sapDeleted,
      sapTlsDHCPLseStEntriesExceeded,
      sapTlsDHCPLeaseStateOverride,
      sapTlsDHCPSuspiciousPcktRcvd,
      sapDHCPCoAError,
      sapDHCPSubAuthError,
      bridgedTLS,
      sapReceiveOwnBpdu
    }
    STATUS      current
    DESCRIPTION
        "The group of obsolete notifications for the Sap feature
         on Alcatel 7x50 SR series systems."
    ::= { tmnxSapGroups 402 }

END
