ALCATEL-ENT1-DA-MIB DEFINITIONS ::= BEGIN

    IMPORTS
                MODULE-IDENTITY,
                OBJECT-IDENTITY,
                OBJECT-TYPE,
                NOTIFICATION-TYPE,
                Integer32, Unsigned32, IpAddress, Counter32
                        FROM SNMPv2-SMI
                MacAddress, DateAndTime, TimeStamp, TEXTUAL-CONVENTION, TruthValue, RowStatus
                        FROM SNMPv2-TC
                softentIND1Da
                        FROM ALCATEL-ENT1-BASE
                MODULE-COMPLIANCE, OBJECT-GROUP, NOTIFICATION-GROUP
                        FROM SNMPv2-CONF
                InterfaceIndex, InterfaceIndexOrZero
                        FROM IF-MIB
                InetAddressType, InetAddress, InetAddressIPv4
                        FROM INET-ADDRESS-MIB
                SnmpAdminString
                        FROM SNMP-FRAMEWORK-MIB
                TmnxEncapVal
                        FROM ALCATEL-ENT1-TIMETRA-TC-MIB
                        ;

        alcatelIND1DaMIB MODULE-IDENTITY
                LAST-UPDATED "201008160000Z"
                ORGANIZATION "Alcatel-Lucent"
                CONTACT-INFO
            "Please consult with Customer Service to ensure the most appropriate
             version of this document is used with the products in question:

                        Alcatel-Lucent, Enterprise Solutions Division
                       (Formerly Alcatel Internetworking, Incorporated)
                               26801 West Agoura Road
                            Agoura Hills, CA  91301-5122
                              United States Of America

            Telephone:               North America  +1 800 995 2696
                                     Latin America  +1 877 919 9526
                                     Europe         +31 23 556 0100
                                     Asia           +65 394 7933
                                     All Other      +1 818 878 4507

            Electronic Mail:         support@ind.alcatel.com
            World Wide Web:          http://alcatel-lucent.com/wps/portal/enterprise
            File Transfer Protocol:  ftp://ftp.ind.alcatel.com/pub/products/mibs"

                DESCRIPTION
                        "This module describes an authoritative enterprise-specific Simple
             Network Management Protocol (SNMP) Management Information Base (MIB):

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                         Copyright (C) 1995-2007 Alcatel-Lucent
                             ALL RIGHTS RESERVED WORLDWIDE"

                REVISION      "200704030000Z"
        DESCRIPTION
            "DA module is taking care of the authentication and classification of MACs
			on a DA port. The pkts from the MAC would be allowed to enter the network
			only if the authentication and/or classification is done by the DA task."
                ::= { softentIND1Da 1}



alaIND1DaMIBNotifications OBJECT-IDENTITY
        STATUS current
        DESCRIPTION
            "Branch For DA Subsystem Notifications."
        ::= { alcatelIND1DaMIB 0 }

alaIND1DaMIBObjects OBJECT-IDENTITY
        STATUS current
        DESCRIPTION
            "Branch For DA Subsystem Managed Objects."
        ::= { alcatelIND1DaMIB 1 }


    alaIND1DaMIBConformance OBJECT-IDENTITY
        STATUS current
        DESCRIPTION
            "Branch for DA Module MIB Subsystem Conformance Information."
        ::= { alcatelIND1DaMIB 2 }


    alaIND1DaMIBGroups OBJECT-IDENTITY
        STATUS current
        DESCRIPTION
            "Branch for DA Module MIB Subsystem Units of Conformance."
        ::= { alaIND1DaMIBConformance 1 }

    AlaDaClassificationPolicyType ::= TEXTUAL-CONVENTION
       STATUS       current
       DESCRIPTION
               "This policy type is the classification policy used to classify
                a device onto the system. "
                SYNTAX  INTEGER {
                    authPassAltUnp	( 1 ),
                                    authPassDefUnp	( 2 ),
                                    authPassSrvUnp	( 3 ),
                                    noAuthMacRuleUnp	( 4 ),
                                    noAuthMacRangeRuleUnp	( 5 ),
                                    noAuthIpRuleUnp	( 6 ),
                                    authFailDefUnp	( 7 ),
                                    authFailMacRuleUnp	( 8 ),
                                    authFailMacRangeRuleUnp	( 9 ),
                                    authFailIpRuleUnp	( 10 ),
                                    authFailRuleDefUnp	( 11 ),
                                    authFailMacRangeVlanTagRuleUnp	( 12 ),
                                    tagAuthFailMacRuleUnp	( 13 ),
                                    tagAuthFailMacVlanTagRuleUnp	( 14 ),
                                    tagAuthFailMacRangeRuleUnp	( 15 ),
                                    tagAuthFailMacRangeVlanTagRuleUnp	( 16 ),
                                    tagAuthFailIpRuleUnp	( 17 ),
                                    tagAuthFailIpVlanTagRuleUnp	( 18 ),
                                    tagAuthFailVlanTagRuleUnp	( 19 ),
                                    tagAuthPassAltUnp	( 20 ),
                                    tagAuthPassDefUnp	( 21 ),
                                    tagAuthPassSrvUnp	( 22 ),
                                    tagMacRuleUnp	( 23 ),
                                    tagMacVlanTagRuleUnp	( 24 ),
                                    tagMacRangeRuleUnp	( 25 ),
                                    tagMacRangeVlanTagRuleUnp	( 26 ),
                                    tagIpRuleUnp	( 27 ),
                                    tagIpVlanTagRuleUnp	( 28 ),
                                    tagVlanTagRuleUnp	( 29 ),
                                    tagRuleDefUnp	( 30 ),
                                    authPassDefUnpBlk	( 31 ),
                                    authFailDefUnpBlk	( 32 ),
                                    authFailRuleDefUnpBlk	( 33 ),
                                    tagAuthPassDefUnpBlk	( 34 ),
                                    tagRuleDefUnpBlk	( 35 ),
                                    authPassSrvUnpTagMismatchBlk	( 36 ),
                                    authPassAltUnpTagMismatchBlk	( 37 ),
                                    authPassDefUnpTagMismatchBlk	( 38 ),
                                    authFailMacRuleUnpTagMismatchBlk	( 39 ),
                                    authFailMacVlanRuleUnpTagMismatchBlk	( 40 ),
                                    authFailMacRangeRuleUnpTagMismatchBlk	( 41 ),
                                    authFailMacRangeVlanRuleUnpTagMismatchBlk	( 42 ),
                                    authFailIpRuleUnpTagMismatchBlk	( 43 ),
                                    authFailIpVlanRuleUnpTagMismatchBlk	( 44 ),
                                    authFailVlanRuleUnpTagMismatchBlk	( 45 ),
                                    defUnpBlk	( 46 ),
                                    authPassSrvUnpBlk	( 47 ),
                                    authPassAltUnpBlk	( 48 ),
                                    authFailMacRuleUnpBlk	( 49 ),
                                    authFailMacRangeRuleUnpBlk	( 50 ),
                                    authFailIpRuleUnpBlk	( 51 ),
                                    tagMacRuleUnpBlk	( 52 ),
                                    tagMacVlanTagRuleUnpBlk	( 53 ),
                                    tagMacRangeRuleUnpBlk	( 54 ),
                                    tagMacRangeVlanTagRuleUnpBlk	( 55 ),
                                    tagIpRuleUnpBlk	( 56 ),
                                    tagIpVlanTagRuleUnpBlk	( 57 ),
                                    tagVlanTagRuleUnpBlk	( 58 ),
                                    authSrvDownUnpTagMismatchBlk	( 59 ),
                                    noMatchingUnpBlk	( 60 ),
                                    trustTag	( 61 ),
                                    authSrvDownUnp	( 62 ),
                                    defUnp	( 63 ),
                                    lpsUnpBlk	( 64 ),
                                    sysDefSpb	( 65 ),
                                    defSpbProfile	( 66 ),
                                    noSpbResource	( 67 ),
                                    tagAuthPassPortMacIpRuleUnp	( 68 ),
                                    tagAuthPassPortMacRuleUnp	( 69 ),
                                    tagAuthPassPortIpRuleUnp	( 70 ),
                                    tagAuthPassGroupMacIpRuleUnp	( 71 ),
                                    tagAuthPassGroupMacRuleUnp	( 72 ),
                                    tagAuthPassGroupIpRuleUnp	( 73 ),
                                    tagAuthPassPortRuleUnp	( 74 ),
                                    tagAuthPassGroupRuleUnp	( 75 ),
                                    tagAuthPassMacVlanRuleUnp	( 76 ),
                                    tagAuthPassMacRuleUnp	( 77 ),
                                    tagAuthPassMacouiRuleUnp	( 78 ),
                                    tagAuthPassMacrangeVlanRuleUnp	( 79 ),
                                    tagAuthPassMacrangeRuleUnp	( 80 ),
                                    tagAuthPassLldpRuleUnp	( 81 ),
                                    tagAuthPassL2authRuleUnp	( 82 ),
                                    tagAuthPassIpVlanRuleUnp	( 83 ),
                                    tagAuthPassIpRuleUnp	( 84 ),
                                    tagAuthPassVlanRuleUnp	( 85 ),
                                    tagAuthPassDmGroupRuleUnp	( 86 ),
                                    tagAuthFailPortMacIpRuleUnp	( 87 ),
                                    tagAuthFailPortMacRuleUnp	( 88 ),
                                    tagAuthFailPortIpRuleUnp	( 89 ),
                                    tagAuthFailGroupMacIpRuleUnp	( 90 ),
                                    tagAuthFailGroupMacRuleUnp	( 91 ),
                                    tagAuthFailGroupIpRuleUnp	( 92 ),
                                    tagAuthFailPortRuleUnp	( 93 ),
                                    tagAuthFailGroupRuleUnp	( 94 ),
                                    tagAuthFailMacouiRuleUnp	( 95 ),
                                    tagAuthFailLldpRuleUnp	( 96 ),
                                    tagAuthFailL2authRuleUnp	( 97 ),
                                    tagAuthFailDmGroupRuleUnp	( 98 ),
                                    tagPortMacIpRuleUnp	( 99 ),
                                    tagPortMacRuleUnp	( 100 ),
                                    tagPortIpRuleUnp	( 101 ),
                                    tagGroupMacIpRuleUnp	( 102 ),
                                    tagGroupMacRuleUnp	( 103 ),
                                    tagGroupIpRuleUnp	( 104 ),
                                    tagPortRuleUnp	( 105 ),
                                    tagGroupRuleUnp	( 106 ),
                                    tagMacouiRuleUnp	( 107 ),
                                    tagLldpRuleUnp	( 108 ),
                                    tagL2authRuleUnp	( 109 ),
                                    tagDmGroupRuleUnp	( 110 ),
                                    authPassPortMacIpRuleUnp	( 111 ),
                                    authPassPortMacRuleUnp	( 112 ),
                                    authPassPortIpRuleUnp	( 113 ),
                                    authPassGroupMacIpRuleUnp	( 114 ),
                                    authPassGroupMacRuleUnp	( 115 ),
                                    authPassGroupIpRuleUnp	( 116 ),
                                    authPassPortRuleUnp	( 117 ),
                                    authPassGroupRuleUnp	( 118 ),
                                    authPassMacRuleUnp	( 119 ),
                                    authPassMacouiRuleUnp	( 120 ),
                                    authPassMacrangeRuleUnp	( 121 ),
                                    authPassLldpRuleUnp	( 122 ),
                                    authPassL2authRuleUnp	( 123 ),
                                    authPassIpRuleUnp	( 124 ),
                                    authPassDmGroupRuleUnp	( 125 ),
                                    authFailPortMacIpRuleUnp	( 126 ),
                                    authFailPortMacRuleUnp	( 127 ),
                                    authFailPortIpRuleUnp	( 128 ),
                                    authFailGroupMacIpRuleUnp	( 129 ),
                                    authFailGroupMacRuleUnp	( 130 ),
                                    authFailGroupIpRuleUnp	( 131 ),
                                    authFailPortRuleUnp	( 132 ),
                                    authFailGroupRuleUnp	( 133 ),
                                    authFailMacouiRuleUnp	( 134 ),
                                    authFailLldpRuleUnp	( 135 ),
                                    authFailL2authRuleUnp	( 136 ),
                                    authFailDmGroupRuleUnp	( 137 ),
                                    noAuthPortMacIpRuleUnp	( 138 ),
                                    noAuthPortMacRuleUnp	( 139 ),
                                    noAuthPortIpRuleUnp	( 140 ),
                                    noAuthGroupMacIpRuleUnp	( 141 ),
                                    noAuthGroupMacRuleUnp	( 142 ),
                                    noAuthGroupIpRuleUnp	( 143 ),
                                    noAuthPortRuleUnp	( 144 ),
                                    noAuthGroupRuleUnp	( 145 ),
                                    noAuthMacouiRuleUnp	( 146 ),
                                    noAuthLldpRuleUnp	( 147 ),
                                    noAuthL2authRuleUnp	( 148 ),
                                    noAuthDmGroupRuleUnp	( 149 ),
                                    authPassPortMacIpRuleUnpTagMismatchBlk	( 150 ),
                                    authPassPortMacRuleUnpTagMismatchBlk	( 151 ),
                                    authPassPortIpRuleUnpTagMismatchBlk	( 152 ),
                                    authPassGroupMacIpRuleUnpTagMismatchBlk	( 153 ),
                                    authPassGroupMacRuleUnpTagMismatchBlk	( 154 ),
                                    authPassGroupIpRuleUnpTagMismatchBlk	( 155 ),
                                    authPassPortRuleUnpTagMismatchBlk	( 156 ),
                                    authPassGroupRuleUnpTagMismatchBlk	( 157 ),
                                    authPassMacVlanRuleUnpTagMismatchBlk	( 158 ),
                                    authPassMacRuleUnpTagMismatchBlk	( 159 ),
                                    authPassMacouiRuleUnpTagMismatchBlk	( 160 ),
                                    authPassMacrangeVlanRuleUnpTagMismatchBlk	( 161 ),
                                    authPassMacrangeRuleUnpTagMismatchBlk	( 162 ),
                                    authPassLldpRuleUnpTagMismatchBlk	( 163 ),
                                    authPassL2authRuleUnpTagMismatchBlk	( 164 ),
                                    authPassIpVlanRuleUnpTagMismatchBlk	( 165 ),
                                    authPassIpRuleUnpTagMismatchBlk	( 166 ),
                                    authPassVlanRuleUnpTagMismatchBlk	( 167 ),
                                    authPassDmGroupRuleUnpTagMismatchBlk	( 168 ),
                                    authFailPortMacIpRuleUnpTagMismatchBlk	( 169 ),
                                    authFailPortMacRuleUnpTagMismatchBlk	( 170 ),
                                    authFailPortIpRuleUnpTagMismatchBlk	( 171 ),
                                    authFailGroupMacIpRuleUnpTagMismatchBlk	( 172 ),
                                    authFailGroupMacRuleUnpTagMismatchBlk	( 173 ),
                                    authFailGroupIpRuleUnpTagMismatchBlk	( 174 ),
                                    authFailPortRuleUnpTagMismatchBlk	( 175 ),
                                    authFailGroupRuleUnpTagMismatchBlk	( 176 ),
                                    authFailMacouiRuleUnpTagMismatchBlk	( 177 ),
                                    authFailLldpRuleUnpTagMismatchBlk	( 178 ),
                                    authFailL2authRuleUnpTagMismatchBlk	( 179 ),
                                    authFailDmGroupRuleUnpTagMismatchBlk	( 180 ),
                                    portMacIpRuleUnpTagMismatchBlk	( 181 ),
                                    portMacRuleUnpTagMismatchBlk	( 182 ),
                                    portIpRuleUnpTagMismatchBlk	( 183 ),
                                    groupMacIpRuleUnpTagMismatchBlk	( 184 ),
                                    groupMacRuleUnpTagMismatchBlk	( 185 ),
                                    groupIpRuleUnpTagMismatchBlk	( 186 ),
                                    portRuleUnpTagMismatchBlk	( 187 ),
                                    groupRuleUnpTagMismatchBlk	( 188 ),
                                    macouiRuleUnpTagMismatchBlk	( 189 ),
                                    lldpRuleUnpTagMismatchBlk	( 190 ),
                                    l2authRuleUnpTagMismatchBlk	( 191 ),
                                    dmGroupRuleUnpTagMismatchBlk	( 192 ),
                                    tagAuthPassExtendedRuleUnp	( 193 ),
                                    tagAuthFailExtendedRuleUnp	( 194 ),
                                    tagExtendedRuleUnp	( 195 ),
                                    authPassExtendedRuleUnp	( 196 ),
                                    authFailExtendedRuleUnp	( 197 ),
                                    noAuthExtendedRuleUnp	( 198 ),
                                    authPassExtendedRuleUnpTagMismatchBlk	( 199 ),
                                    authFailExtendedRuleUnpTagMismatchBlk	( 200 ),
                                    extendedRuleUnpTagMismatchBlk	( 201 ),
                                    lpsStatic	( 202 ),
                                    lpsPseudoStatic	( 203 ),
                                    lpsDupStatic	( 204 ),
                                    authSrvDownEdgeProfileUnp	( 205 ),
                                    byodPauseTimerFilter	( 206 ),
                                    byodServerUnp	( 207 ),
                                    noVxlanResource	( 208 ),
                                    noVxlanResourceAuthSrvDownUnp	( 209 ),
                                    defVxlanProfile	( 210 ),
                                    sysDefVxlan	( 211 ),
                                    cportalEdgeProfilePolicy	( 212 ),
                                    tagAuthPassPortMacIpVlanRuleUnp	( 213 ),
                                    tagAuthPassPortMacVlanRuleUnp	( 214 ),
                                    tagAuthPassPortIpVlanRuleUnp	( 215 ),
                                    tagAuthPassGroupMacIpVlanRuleUnp	( 216 ),
                                    tagAuthPassGroupMacVlanRuleUnp	( 217 ),
                                    tagAuthPassGroupIpVlanRuleUnp	( 218 ),
                                    tagAuthPassPortVlanRuleUnp	( 219 ),
                                    tagAuthPassGroupVlanRuleUnp	( 220 ),
                                    tagAuthPassMacouiVlanRuleUnp	( 221 ),
                                    tagAuthPassL2authVlanRuleUnp	( 222 ),
                                    tagAuthPassDmGroupVlanRuleUnp	( 223 ),
                                    tagAuthFailPortMacIpVlanRuleUnp	( 224 ),
                                    tagAuthFailPortMacVlanRuleUnp	( 225 ),
                                    tagAuthFailPortIpVlanRuleUnp	( 226 ),
                                    tagAuthFailGroupMacIpVlanRuleUnp	( 227 ),
                                    tagAuthFailGroupMacVlanRuleUnp	( 228 ),
                                    tagAuthFailGroupIpVlanRuleUnp	( 229 ),
                                    tagAuthFailPortVlanRuleUnp	( 230 ),
                                    tagAuthFailGroupVlanRuleUnp	( 231 ),
                                    tagAuthFailMacouiVlanRuleUnp	( 232 ),
                                    tagAuthFailL2authVlanRuleUnp	( 233 ),
                                    tagAuthFailDmGroupVlanRuleUnp	( 234 ),
                                    tagPortMacIpVlanRuleUnp	( 235 ),
                                    tagPortMacVlanRuleUnp	( 236 ),
                                    tagPortIpVlanRuleUnp	( 237 ),
                                    tagGroupMacIpVlanRuleUnp	( 238 ),
                                    tagGroupMacVlanRuleUnp	( 239 ),
                                    tagGroupIpVlanRuleUnp	( 240 ),
                                    tagPortVlanRuleUnp	( 241 ),
                                    tagGroupVlanRuleUnp	( 242 ),
                                    tagMacouiVlanRuleUnp	( 243 ),
                                    tagL2authVlanRuleUnp	( 244 ),
                                    tagDmGroupVlanRuleUnp	( 245 ),
                                    authPassPortMacIpVlanRuleUnp	( 246 ),
                                    authPassPortMacVlanRuleUnp	( 247 ),
                                    authPassPortIpVlanRuleUnp	( 248 ),
                                    authPassGroupMacIpVlanRuleUnp	( 249 ),
                                    authPassGroupMacVlanRuleUnp	( 250 ),
                                    authPassGroupIpVlanRuleUnp	( 251 ),
                                    authPassPortVlanRuleUnp	( 252 ),
                                    authPassGroupVlanRuleUnp	( 253 ),
                                    authPassMacouiVlanRuleUnp	( 254 ),
                                    authPassL2authVlanRuleUnp	( 255 ),
                                    authPassDmGroupVlanRuleUnp	( 256 ),
                                    authFailPortMacIpVlanRuleUnp	( 257 ),
                                    authFailPortMacVlanRuleUnp	( 258 ),
                                    authFailPortIpVlanRuleUnp	( 259 ),
                                    authFailGroupMacIpVlanRuleUnp	( 260 ),
                                    authFailGroupMacVlanRuleUnp	( 261 ),
                                    authFailGroupIpVlanRuleUnp	( 262 ),
                                    authFailPortVlanRuleUnp	( 263 ),
                                    authFailGroupVlanRuleUnp	( 264 ),
                                    authFailMacouiVlanRuleUnp	( 265 ),
                                    authFailL2authVlanRuleUnp	( 266 ),
                                    authFailDmGroupVlanRuleUnp	( 267 ),
                                    noAuthPortMacIpVlanRuleUnp	( 268 ),
                                    noAuthPortMacVlanRuleUnp	( 269 ),
                                    noAuthPortIpVlanRuleUnp	( 270 ),
                                    noAuthGroupMacIpVlanRuleUnp	( 271 ),
                                    noAuthGroupMacVlanRuleUnp	( 272 ),
                                    noAuthGroupIpVlanRuleUnp	( 273 ),
                                    noAuthPortVlanRuleUnp	( 274 ),
                                    noAuthGroupVlanRuleUnp	( 275 ),
                                    noAuthMacouiVlanRuleUnp	( 276 ),
                                    noAuthL2authVlanRuleUnp	( 277 ),
                                    noAuthDmGroupVlanRuleUnp	( 278 ),
                                    authPassPortMacIpVlanRuleUnpTagMismatchBlk	( 279 ),
                                    authPassPortMacVlanRuleUnpTagMismatchBlk	( 280 ),
                                    authPassPortIpVlanRuleUnpTagMismatchBlk	( 281 ),
                                    authPassGroupMacIpVlanRuleUnpTagMismatchBlk	( 282 ),
                                    authPassGroupMacVlanRuleUnpTagMismatchBlk	( 283 ),
                                    authPassGroupIpVlanRuleUnpTagMismatchBlk	( 284 ),
                                    authPassPortVlanRuleUnpTagMismatchBlk	( 285 ),
                                    authPassGroupVlanRuleUnpTagMismatchBlk	( 286 ),
                                    authPassMacouiVlanRuleUnpTagMismatchBlk	( 287 ),
                                    authPassL2authVlanRuleUnpTagMismatchBlk	( 288 ),
                                    authPassDmGroupVlanRuleUnpTagMismatchBlk	( 289 ),
                                    authFailPortMacIpVlanRuleUnpTagMismatchBlk	( 290 ),
                                    authFailPortMacVlanRuleUnpTagMismatchBlk	( 291 ),
                                    authFailPortIpVlanRuleUnpTagMismatchBlk	( 292 ),
                                    authFailGroupMacIpVlanRuleUnpTagMismatchBlk	( 293 ),
                                    authFailGroupMacVlanRuleUnpTagMismatchBlk	( 294 ),
                                    authFailGroupIpVlanRuleUnpTagMismatchBlk	( 295 ),
                                    authFailPortVlanRuleUnpTagMismatchBlk	( 296 ),
                                    authFailGroupVlanRuleUnpTagMismatchBlk	( 297 ),
                                    authFailMacouiVlanRuleUnpTagMismatchBlk	( 298 ),
                                    authFailL2authVlanRuleUnpTagMismatchBlk	( 299 ),
                                    authFailDmGroupVlanRuleUnpTagMismatchBlk	( 300 ),
                                    portMacIpVlanRuleUnpTagMismatchBlk	( 301 ),
                                    portMacVlanRuleUnpTagMismatchBlk	( 302 ),
                                    portIpVlanRuleUnpTagMismatchBlk	( 303 ),
                                    groupMacIpVlanRuleUnpTagMismatchBlk	( 304 ),
                                    groupMacVlanRuleUnpTagMismatchBlk	( 305 ),
                                    groupIpVlanRuleUnpTagMismatchBlk	( 306 ),
                                    portVlanRuleUnpTagMismatchBlk	( 307 ),
                                    groupVlanRuleUnpTagMismatchBlk	( 308 ),
                                    macouiVlanRuleUnpTagMismatchBlk	( 309 ),
                                    l2authVlanRuleUnpTagMismatchBlk	( 310 ),
                                    dmGroupVlanRuleUnpTagMismatchBlk	( 311 ),
                                    cportalPauseTimerFilter	( 312 )
                }

       AlaDaAuthenticationType ::= TEXTUAL-CONVENTION
       STATUS       current
       DESCRIPTION
               "The type of authentication used"
       SYNTAX  INTEGER {
                   noAuthentication   (1),
                   dot1XAuthentication (2),
                   macAuthentication  (3),
                   captivePortal      (4)
       }

      AlaDaAuthenticationResult ::= TEXTUAL-CONVENTION
       STATUS       current
       DESCRIPTION
               "The result of the authentication.  If the AlaDaAuthenticationType of this
                 device is noAuthentication then this object will return notApplicable.  If the
                 authentication has not completed then this object will return inProgress."
       SYNTAX  INTEGER {
                   notApplicable (0),
                   inProgress    (1),
                   success       (2),
                   fail          (3)
       }

      AlaDaMacLearntState ::= TEXTUAL-CONVENTION
       STATUS       current
       DESCRIPTION
               "The state of MAC address in the system"
       SYNTAX  INTEGER {
                   bridging      (0), -- Normal access to the network.
                   filtering     (1) -- Access to the network blocked.
       }

	-- Should be used for all tables where MCLAG consistency status needs to be kept
       AlaMultiChassisConfigStatus ::= TEXTUAL-CONVENTION
       STATUS       current
       DESCRIPTION
               "The status of Multi-Chassis consistency check. If no MCLAG involved
                then status is local to the switch."
       SYNTAX  INTEGER {
	        local (1),
	        sync  (2),
	        outOfSync (3)
       }

      MacOui ::= TEXTUAL-CONVENTION
      DISPLAY-HINT "1x:"
      STATUS       current
      DESCRIPTION
                "Represents a MAC-OUI."
      SYNTAX       OCTET STRING (SIZE (3))

--------------------------------------------------
-- User Network Profile Table configuration MIB --
-- This table is deprecated as part of unification
--------------------------------------------------

alaDaUserNetProfileTable OBJECT-TYPE
    SYNTAX        SEQUENCE OF AlaDaUserNetProfileEntry
    MAX-ACCESS    not-accessible
    STATUS        deprecated
    DESCRIPTION
        "This table stores the UNP profiles created in the system.
         The entries would be mapped to vlan ID which would be used
         by device authentication for classifying users."
    ::= { alaIND1DaMIBObjects 1 }

alaDaUserNetProfileEntry OBJECT-TYPE
    SYNTAX        AlaDaUserNetProfileEntry
    MAX-ACCESS    not-accessible
    STATUS        deprecated
    DESCRIPTION
        "User Network Profile entry"
    INDEX {alaDaUserNetProfileName}
    ::= { alaDaUserNetProfileTable 1 }

AlaDaUserNetProfileEntry ::= SEQUENCE  {
    alaDaUserNetProfileName              SnmpAdminString,
    alaDaUserNetProfileVlanID            Integer32,
    alaDaUserNetProfileRowStatus         RowStatus,
    alaDaUserNetProfileQosPolicyListName SnmpAdminString,
    alaDaUserNetProfileMCLagConfigStatus AlaMultiChassisConfigStatus,
    alaDaUserNetProfileSaaProfileName    SnmpAdminString,
    alaDaUserNetProfileMobileTag         INTEGER,
    alaDaUserNetProfileMaxIngressBw      Integer32,
    alaDaUserNetProfileMaxEgressBw       Integer32,
    alaDaUserNetProfileMaxIngressDepth   Integer32,
    alaDaUserNetProfileMaxEgressDepth    Integer32
}

alaDaUserNetProfileName OBJECT-TYPE
    SYNTAX        SnmpAdminString ( SIZE( 1 .. 32 ) )
    MAX-ACCESS    not-accessible
    STATUS        deprecated
    DESCRIPTION
        "The name of this profile."
    ::= { alaDaUserNetProfileEntry 1 }

alaDaUserNetProfileVlanID OBJECT-TYPE
    SYNTAX        Integer32 (1 .. 4094)
    MAX-ACCESS    read-create
    STATUS        deprecated
    DESCRIPTION
        "The VLAN id for this profile."
    ::= { alaDaUserNetProfileEntry 2}

alaDaUserNetProfileRowStatus OBJECT-TYPE
    SYNTAX        RowStatus
    MAX-ACCESS    read-create
    STATUS        deprecated
    DESCRIPTION
        "The status of this table entry."
    ::= { alaDaUserNetProfileEntry 3}

alaDaUserNetProfileQosPolicyListName OBJECT-TYPE
    SYNTAX        SnmpAdminString ( SIZE( 0 .. 32 ) )
    MAX-ACCESS    read-create
    STATUS        deprecated
    DESCRIPTION
        "The name of the QoS Policy List name that will be used if this
         User Network Profile is applied for a given device along with
         alaDaUserNetProfileVlanID."
    ::= { alaDaUserNetProfileEntry 4 }

alaDaUserNetProfileMCLagConfigStatus OBJECT-TYPE
    SYNTAX      AlaMultiChassisConfigStatus
    MAX-ACCESS  read-only
    STATUS      deprecated
    DESCRIPTION
        "Result of MCLAG Consistency Check. All rows will be created as local.
         Actual status will be set through remote chassis synchronization."
    DEFVAL { local }
    ::= {  alaDaUserNetProfileEntry 5 }

alaDaUserNetProfileSaaProfileName OBJECT-TYPE
    SYNTAX        SnmpAdminString ( SIZE( 0 .. 32 ) )
    MAX-ACCESS    read-create
    STATUS        deprecated
    DESCRIPTION
        "The name of the SAA profile that is associated to this profile."
    ::= { alaDaUserNetProfileEntry 6 }

alaDaUserNetProfileMobileTag   OBJECT-TYPE
    SYNTAX      INTEGER {
                   enable  (1),
                   disable (2)
                }
    MAX-ACCESS  read-create
    STATUS      deprecated
    DESCRIPTION
        "User Net Profile Mobile Tag ."
    DEFVAL { disable }
    ::= { alaDaUserNetProfileEntry 7 }

alaDaUserNetProfileMaxIngressBw OBJECT-TYPE
    SYNTAX       Integer32 (-1|0..2147483647)
    UNITS        "kilobits per second"
    MAX-ACCESS   read-create
    STATUS       deprecated
    DESCRIPTION
        "Maximum Ingress Bandwidth (Kbits/sec or Mbits/sec) allowed for traffic associated to this profile.
        If value is set to -1, then the Ingress Bandwidth specified for the profile is unconfigured."
    DEFVAL { 0 }
    ::= { alaDaUserNetProfileEntry 8 }

alaDaUserNetProfileMaxEgressBw OBJECT-TYPE
    SYNTAX       Integer32 (-1|0..2147483647)
    UNITS        "kilobits per second"
    MAX-ACCESS   read-create
    STATUS       deprecated
    DESCRIPTION
        "Maximum Egress Bandwidth (Kbits/sec or Mbits/sec) allowed for traffic associated to this profile.
        If value is set to -1, then the Egress Bandwidth specified for the profile is unconfigured."
    DEFVAL { 0 }
    ::= { alaDaUserNetProfileEntry 9 }

alaDaUserNetProfileMaxIngressDepth OBJECT-TYPE
    SYNTAX       Integer32 (-1|0..16384)
    MAX-ACCESS   read-create
    STATUS       deprecated
    DESCRIPTION
        "Maximum Ingress Depth associated to Bandwidth.
        If set to -1, then the Depth associated with the profile is unconfigured."
    DEFVAL { 0 }
    ::= { alaDaUserNetProfileEntry 10 }

alaDaUserNetProfileMaxEgressDepth OBJECT-TYPE
    SYNTAX       Integer32 (-1|0..16384)
    MAX-ACCESS   read-create
    STATUS       deprecated
    DESCRIPTION
        "Maximum Egress Depth associated to Bandwidth.
        If set to -1, then the Depth associated with the profile is unconfigured."
    DEFVAL { 0 }
    ::= { alaDaUserNetProfileEntry 11 }

------------------------------------------------
-- DA Classification IP network address rule  --
------------------------------------------------

        alaDaUNPIpNetRuleTable  OBJECT-TYPE
            SYNTAX  SEQUENCE OF AlaDaUNPIpNetRuleEntry
            MAX-ACCESS  not-accessible
            STATUS  deprecated
            DESCRIPTION
                "A list of IP network address rules.  This is used to match
                 the InetAddress of a packet to a User Network Profile entry."
            ::= { alaIND1DaMIBObjects 2 }

        alaDaUNPIpNetRuleEntry  OBJECT-TYPE
            SYNTAX  AlaDaUNPIpNetRuleEntry
            MAX-ACCESS  not-accessible
            STATUS  deprecated
            DESCRIPTION
                 "An IP network address rule entry."
            INDEX { alaDaUNPIpNetRuleAddrType,
                    alaDaUNPIpNetRuleAddr,
                    alaDaUNPIpNetRuleMask }
            ::= { alaDaUNPIpNetRuleTable 1 }

        AlaDaUNPIpNetRuleEntry ::= SEQUENCE {
                alaDaUNPIpNetRuleAddrType
                        InetAddressType,
                alaDaUNPIpNetRuleAddr
                        InetAddress,
                alaDaUNPIpNetRuleMask
                        InetAddress,
                alaDaUNPIpNetRuleProfileName
                        SnmpAdminString,
		alaDaUNPIpNetRuleVlanTag
			Integer32,
                alaDaUNPIpNetRuleRowStatus
                        RowStatus,
                alaDaUNPIpNetRuleMCLagConfigStatus
                        AlaMultiChassisConfigStatus
                }

        alaDaUNPIpNetRuleAddrType  OBJECT-TYPE
            SYNTAX  InetAddressType
            MAX-ACCESS  not-accessible
            STATUS  deprecated
            DESCRIPTION
                 "The IP network address type used for VLAN classification.  For now
                   Only IPv4 is supported."
            ::= { alaDaUNPIpNetRuleEntry 1 }

        alaDaUNPIpNetRuleAddr  OBJECT-TYPE
            SYNTAX  InetAddress
            MAX-ACCESS  not-accessible
            STATUS  deprecated
            DESCRIPTION
                 "The IP network address used for VLAN classification.  Only IPv4 is
                  supported."
            ::= { alaDaUNPIpNetRuleEntry 2 }

        alaDaUNPIpNetRuleMask  OBJECT-TYPE
            SYNTAX  InetAddress
            MAX-ACCESS  not-accessible
            STATUS  deprecated
            DESCRIPTION
                 "The IP network mask applying to the IP network address."
            ::= { alaDaUNPIpNetRuleEntry 3 }


        alaDaUNPIpNetRuleProfileName  OBJECT-TYPE
            SYNTAX  SnmpAdminString ( SIZE( 1 .. 32 ) )
            MAX-ACCESS  read-create
            STATUS  deprecated
            DESCRIPTION
                 "The profile name in the User Network Profile Table to be
                  applied."
            ::= { alaDaUNPIpNetRuleEntry 4 }

        alaDaUNPIpNetRuleVlanTag  OBJECT-TYPE
            SYNTAX  Integer32 (0..4094)
            MAX-ACCESS  read-create
            STATUS  deprecated
            DESCRIPTION
                 "The vlan tag to be used for classification of tagged pkts.
                 Vlan tag of 0 indicates no VLAN is associated."
            ::= { alaDaUNPIpNetRuleEntry 5 }

        alaDaUNPIpNetRuleRowStatus  OBJECT-TYPE
            SYNTAX  RowStatus
            MAX-ACCESS  read-create
            STATUS  deprecated
            DESCRIPTION
                "Row Status for creating/deleting rules."
            ::= { alaDaUNPIpNetRuleEntry 6 }

        alaDaUNPIpNetRuleMCLagConfigStatus  OBJECT-TYPE
            SYNTAX  AlaMultiChassisConfigStatus
            MAX-ACCESS  read-only
            STATUS  deprecated
            DESCRIPTION
                "Result of MCLAG Consistency Check. All rows will be created as local.
                 Actual status will be set through remote chassis synchronization."
            DEFVAL { local }
            ::= { alaDaUNPIpNetRuleEntry 7 }

--
-- DA Classification MAC address rule
--


        alaDaUNPMacRuleTable  OBJECT-TYPE
                SYNTAX  SEQUENCE OF AlaDaUNPMacRuleEntry
                MAX-ACCESS  not-accessible
                STATUS  deprecated
                DESCRIPTION
                "A list of MAC address rules.  This is used to match
                 the MAC Address of a packet to a User Network Profile entry "
                ::= { alaIND1DaMIBObjects 3 }

        alaDaUNPMacRuleEntry  OBJECT-TYPE
            SYNTAX  AlaDaUNPMacRuleEntry
            MAX-ACCESS  not-accessible
            STATUS  deprecated
            DESCRIPTION
                 "A MAC rule entry."
            INDEX {alaDaUNPMacRuleAddr }
            ::= { alaDaUNPMacRuleTable 1 }

        AlaDaUNPMacRuleEntry ::= SEQUENCE {
                alaDaUNPMacRuleAddr
                        MacAddress,
                alaDaUNPMacRuleProfileName
                        SnmpAdminString,
		alaDaUNPMacRuleVlanTag
			Integer32,
                alaDaUNPMacRuleRowStatus
                        RowStatus,

               alaDaUNPMacRuleMCLagConfigStatus
                   AlaMultiChassisConfigStatus
                }

        alaDaUNPMacRuleAddr  OBJECT-TYPE
                SYNTAX  MacAddress
                MAX-ACCESS  not-accessible
                STATUS  deprecated
                DESCRIPTION
                "The MAC address used for VLAN classification."
                ::= { alaDaUNPMacRuleEntry 1 }

        alaDaUNPMacRuleProfileName  OBJECT-TYPE
                SYNTAX  SnmpAdminString ( SIZE( 1 .. 32 ) )
                MAX-ACCESS  read-create
                STATUS  deprecated
                DESCRIPTION
                 "The profile name in the User Network Profile Table to be
                  applied."
                ::= { alaDaUNPMacRuleEntry 2 }

        alaDaUNPMacRuleVlanTag  OBJECT-TYPE
            SYNTAX  Integer32 (0..4094)
            MAX-ACCESS  read-create
            STATUS  deprecated
            DESCRIPTION
                 "The vlan tag to be used for classification of tagged pkts.
                 Vlan tag of 0 indicates no VLAN is associated."
            ::= { alaDaUNPMacRuleEntry 3 }

        alaDaUNPMacRuleRowStatus  OBJECT-TYPE
                SYNTAX  RowStatus
                MAX-ACCESS  read-create
                STATUS  deprecated
                DESCRIPTION
                "Row Status for creating/deleting rules."
                 ::= { alaDaUNPMacRuleEntry 4 }

         alaDaUNPMacRuleMCLagConfigStatus  OBJECT-TYPE
                SYNTAX  AlaMultiChassisConfigStatus
                MAX-ACCESS  read-only
                STATUS  deprecated
                DESCRIPTION
                    "Result of MCLAG Consistency Check. All rows will be created as local.
                     Actual status will be set through remote chassis synchronization."
                DEFVAL { local }
                 ::= { alaDaUNPMacRuleEntry 5 }

--
-- DA Classification MAC range rule
--

        alaDaUNPMacRangeRuleTable  OBJECT-TYPE
                SYNTAX  SEQUENCE OF AlaDaUNPMacRangeRuleEntry
                MAX-ACCESS  not-accessible
                STATUS  deprecated
                DESCRIPTION
                "A list of MAC range rules.  This is used to match
                 the MAC Address Range of a packet to a User Network Profile entry."
                ::= { alaIND1DaMIBObjects 4 }

        alaDaUNPMacRangeRuleEntry  OBJECT-TYPE
            SYNTAX  AlaDaUNPMacRangeRuleEntry
            MAX-ACCESS  not-accessible
            STATUS  deprecated
            DESCRIPTION
                 "A MAC range rule entry."
            INDEX {alaDaUNPMacRangeRuleLoAddr }
            ::= { alaDaUNPMacRangeRuleTable 1 }

        AlaDaUNPMacRangeRuleEntry ::= SEQUENCE {
                alaDaUNPMacRangeRuleLoAddr
                        MacAddress,
                alaDaUNPMacRangeRuleHiAddr
                        MacAddress,
                alaDaUNPMacRangeRuleProfileName
                        SnmpAdminString,
		alaDaUNPMacRangeRuleVlanTag
			Integer32,
                alaDaUNPMacRangeRuleRowStatus
                        RowStatus,

             alaDaUNPMacRangeRuleMCLagConfigStatus
                        AlaMultiChassisConfigStatus
                }

        alaDaUNPMacRangeRuleLoAddr  OBJECT-TYPE
                SYNTAX  MacAddress
                MAX-ACCESS  not-accessible
                STATUS  deprecated
                DESCRIPTION
                "The lower bound of  MAC address range used for VLAN classification."
                ::= { alaDaUNPMacRangeRuleEntry 1 }

        alaDaUNPMacRangeRuleHiAddr  OBJECT-TYPE
                SYNTAX  MacAddress
                MAX-ACCESS  read-create
                STATUS  deprecated
                DESCRIPTION
                "The upper bound of MAC address range used for VLAN classification."
                ::= { alaDaUNPMacRangeRuleEntry 2 }

        alaDaUNPMacRangeRuleProfileName  OBJECT-TYPE
                SYNTAX  SnmpAdminString ( SIZE( 1 .. 32 ) )
                MAX-ACCESS  read-create
                STATUS  deprecated
                DESCRIPTION
                 "The profile name in the User Network Profile Table to be
                  applied."
                ::= { alaDaUNPMacRangeRuleEntry 3 }

        alaDaUNPMacRangeRuleVlanTag  OBJECT-TYPE
                SYNTAX  Integer32 (0..4094)
                MAX-ACCESS  read-create
                STATUS  deprecated
                DESCRIPTION
                     "The vlan tag to be used for classification of tagged pkts.
                     The range states the valid vlan range in the system.
                     Vlan tag of 0 indicates no VLAN is associated."
                ::= { alaDaUNPMacRangeRuleEntry 4 }

        alaDaUNPMacRangeRuleRowStatus  OBJECT-TYPE
                SYNTAX  RowStatus
                MAX-ACCESS  read-create
                STATUS  deprecated
                DESCRIPTION
                "Row Status for creating/deleting rules."
                 ::= { alaDaUNPMacRangeRuleEntry 5 }



        alaDaUNPMacRangeRuleMCLagConfigStatus  OBJECT-TYPE
                SYNTAX  AlaMultiChassisConfigStatus
                MAX-ACCESS  read-only
                STATUS  deprecated
                DESCRIPTION
                    "Result of MCLAG Consistency Check. All rows will be created as local.
                     Actual status will be set through remote chassis synchronization."
                DEFVAL { local }
                 ::= { alaDaUNPMacRangeRuleEntry 6 }

--
-- DA Classification VLAN TAG rule
--

        alaDaUNPVlanTagRuleTable  OBJECT-TYPE
                SYNTAX  SEQUENCE OF AlaDaUNPVlanTagRuleEntry
                MAX-ACCESS  not-accessible
                STATUS  deprecated
                DESCRIPTION
                "A list of Vlan Tag based classification rules.  This is used to match
                 the vlan tag in a packet to a User Network Profile entry "
                ::= { alaIND1DaMIBObjects 5 }

        alaDaUNPVlanTagRuleEntry  OBJECT-TYPE
            SYNTAX  AlaDaUNPVlanTagRuleEntry
            MAX-ACCESS  not-accessible
            STATUS  deprecated
            DESCRIPTION
                 "A Vlan Tag rule entry."
            INDEX {alaDaUNPVlanTagRuleVlan }
            ::= { alaDaUNPVlanTagRuleTable 1 }

        AlaDaUNPVlanTagRuleEntry ::= SEQUENCE {
                alaDaUNPVlanTagRuleVlan
			Integer32,
                alaDaUNPVlanTagRuleProfileName
                        SnmpAdminString,
                alaDaUNPVlanTagRuleRowStatus
                        RowStatus,
                alaDaUNPVlanTagRuleMCLagConfigStatus

                        AlaMultiChassisConfigStatus
                }

        alaDaUNPVlanTagRuleVlan  OBJECT-TYPE
                SYNTAX  Integer32 (1..4094)
                MAX-ACCESS  not-accessible
                STATUS  deprecated
                DESCRIPTION
                "The Vlan Tag used for VLAN classification. The range states the valid
				Vlan range in the system."
                ::= { alaDaUNPVlanTagRuleEntry 1 }

        alaDaUNPVlanTagRuleProfileName  OBJECT-TYPE
                SYNTAX  SnmpAdminString ( SIZE( 1 .. 32 ) )
                MAX-ACCESS  read-create
                STATUS  deprecated
                DESCRIPTION
                 "The profile name in the User Network Profile Table to be
                  applied."
                ::= { alaDaUNPVlanTagRuleEntry 2 }

        alaDaUNPVlanTagRuleRowStatus  OBJECT-TYPE
                SYNTAX  RowStatus
                MAX-ACCESS  read-create
                STATUS  deprecated
                DESCRIPTION
                "Row Status for creating/deleting rules."
                 ::= { alaDaUNPVlanTagRuleEntry 3 }

         alaDaUNPVlanTagRuleMCLagConfigStatus OBJECT-TYPE
                SYNTAX  AlaMultiChassisConfigStatus
                MAX-ACCESS  read-only
                STATUS  deprecated
                DESCRIPTION
                    "Result of MCLAG Consistency Check. All rows will be created as local.
                     Actual status will be set through remote chassis synchronization."
                DEFVAL { local }
                 ::= { alaDaUNPVlanTagRuleEntry 4 }

--
-- DA MAC User Table. This is deperecated in 7.2.1.R02.
-- The new user table is alaDaMacVlanUserTable.
--

alaDaMacUserTable OBJECT-TYPE
        SYNTAX      SEQUENCE OF AlaDaMacUserEntry
        MAX-ACCESS  not-accessible
        STATUS      current
        DESCRIPTION
        "A table of MAC address learned on an UNP port."
::= { alaIND1DaMIBObjects 6 }

alaDaMacUserEntry OBJECT-TYPE
        SYNTAX      AlaDaMacUserEntry
        MAX-ACCESS  not-accessible
        STATUS      current
        DESCRIPTION
                "Non 802.1x supplicant information."
        INDEX { alaDaMacUserIntfNum,
                alaDaMacUserMACAddress }
::= { alaDaMacUserTable 1 }


AlaDaMacUserEntry ::=
        SEQUENCE {
                alaDaMacUserIntfNum
                   	InterfaceIndex,

                alaDaMacUserMACAddress

			MacAddress,

                alaDaMacUserVlanID

			Integer32,

                alaDaAuthenticationStatus

			INTEGER,
		alaDaMacUserIpAddress
			IpAddress,
		alaDaMacUserUnpUsed
			SnmpAdminString,
		alaDaMacUserLoginTimeStamp
			DateAndTime,
		alaDaMacUserAuthtype
			INTEGER,
		alaDaMacUserClassificationSource
			AlaDaClassificationPolicyType,
	        alaDaMacUserName
			SnmpAdminString
                }

alaDaMacUserIntfNum OBJECT-TYPE
    SYNTAX      InterfaceIndex
    MAX-ACCESS  not-accessible
    STATUS      current
    DESCRIPTION
        "The ifIndex representing the slot and port where the non 802.1x supplicant is learned."
    ::= { alaDaMacUserEntry 1 }

alaDaMacUserMACAddress OBJECT-TYPE
    SYNTAX      MacAddress
    MAX-ACCESS  not-accessible
    STATUS      current
    DESCRIPTION
        "The MAC address of the non 802.1x supplicant."
    ::= { alaDaMacUserEntry 2 }

alaDaMacUserVlanID OBJECT-TYPE
        SYNTAX      Integer32 (1..4096)
        MAX-ACCESS  read-only
        STATUS      current
        DESCRIPTION
        "The Id of the VLAN on which the non 802.1x supplicant is learned."
    ::= { alaDaMacUserEntry 3 }

alaDaAuthenticationStatus  OBJECT-TYPE
        SYNTAX  INTEGER {
                idle (1),
                inProgress (2),
                authenticated (3),
                failed (4),
                failedTimeout (5),
                failedNoServer (6),
                failedNoResources (7)
            }

        MAX-ACCESS  read-only
        STATUS      current
        DESCRIPTION
        "Authentication status of the non 802.1x supplicant."
    ::= { alaDaMacUserEntry 4 }

alaDaMacUserIpAddress OBJECT-TYPE
    SYNTAX      IpAddress
    MAX-ACCESS  read-only
    STATUS      current
    DESCRIPTION
        "The ip address from which the mac user is sending the packets"
    ::= { alaDaMacUserEntry 5 }

alaDaMacUserUnpUsed OBJECT-TYPE
    SYNTAX      SnmpAdminString
    MAX-ACCESS  read-only
    STATUS      current
    DESCRIPTION
        "The UNP used for classifying the mac user"
    ::= { alaDaMacUserEntry 6 }

alaDaMacUserLoginTimeStamp OBJECT-TYPE
    SYNTAX      DateAndTime
    MAX-ACCESS  read-only
    STATUS      current
    DESCRIPTION
        "The Login time stamp of the mac user"
    ::= { alaDaMacUserEntry 7 }

alaDaMacUserAuthtype OBJECT-TYPE
    SYNTAX      INTEGER {
		macAuthentication	(0),
		others (1),
    onexAuthentication (2)
	}
    MAX-ACCESS  read-only
    STATUS      current
    DESCRIPTION
        "The authentication type of the mac user"
    ::= { alaDaMacUserEntry 8 }

alaDaMacUserClassificationSource OBJECT-TYPE
        SYNTAX      AlaDaClassificationPolicyType
        MAX-ACCESS  read-only
        STATUS      current
        DESCRIPTION
        "Classification policy under which the non 802.1x supplicant is learned."
    ::= { alaDaMacUserEntry 9 }

alaDaMacUserName OBJECT-TYPE
    SYNTAX      SnmpAdminString
    MAX-ACCESS  read-only
    STATUS      current
    DESCRIPTION
        "The mac user name"
    ::= { alaDaMacUserEntry 10 }

--------------------------------------------------------------
-- Logical Port table
--------------------------------------------------------------

alaDaUNPPortTable OBJECT-TYPE
    SYNTAX      SEQUENCE OF AlaDaUNPPortEntry
    MAX-ACCESS  not-accessible
    STATUS      current
    DESCRIPTION
        "A table of system level information for each port
        supported by the Port Access Entity.  An entry appears
        in this table for each port of this system."
    ::= { alaIND1DaMIBObjects 7 }

alaDaUNPPortEntry OBJECT-TYPE
    SYNTAX      AlaDaUNPPortEntry
    MAX-ACCESS  not-accessible
    STATUS      current
    DESCRIPTION
        "Each of these entries represents a user port on which UNP is enabled
         and their configuration."
    INDEX { alaDaUNPPortIfIndex }
    ::= { alaDaUNPPortTable 1 }

AlaDaUNPPortEntry ::=
    SEQUENCE {
        alaDaUNPPortIfIndex
            InterfaceIndexOrZero,
        alaDaUNPPortDefaultProfileName
            SnmpAdminString,
        alaDaUNPPortPassAltProfileName
            SnmpAdminString,
        alaDaUNPPortRowStatus
            RowStatus,
        alaDaUNPPortMacAuthFlag
            INTEGER,
        alaDaUNPPortClassificationFlag
            INTEGER,
        alaDaUNPPortTrustTagStatus
            INTEGER,
        alaDaUNPPortMCLagConfigStatus
            AlaMultiChassisConfigStatus,
        alaDaUNPPortCustomerDomainId
            Unsigned32,       --deprecated
        alaDaUNPPortType
            INTEGER,
        alaDaUNPPortPassAltSpbProfileName
            SnmpAdminString,  --deprecated
        alaDaUNPPortDefaultSpbProfileName
            SnmpAdminString, --deprecated
        alaDaUNPPortDefaultEdgeProfName
            SnmpAdminString,  --deprecated
        alaDaUNPPortMacPassEdgeProfName
            SnmpAdminString,  --deprecated
        alaDaUNPPort8021XEdgeProfName
            SnmpAdminString,  --deprecated
        alaDaUNPPort8021XAuthStatus
            INTEGER,
        alaDaUNPPort8021XTxPeriodStatus
            INTEGER,     --deprecated
        alaDaUNPPort8021XTxPeriod
            Integer32,
        alaDaUNPPort8021XSuppTimeoutStatus
            INTEGER,   --deprecated
        alaDaUNPPort8021XSuppTimeOut
            Integer32,
        alaDaUNPPort8021XMaxReqStatus
            INTEGER,    --deprecated
        alaDaUNPPort8021XMaxReq
            Integer32,
        alaDaUNPPortGroupId
            Integer32, --deprecated
        alaDaUNPPortAaaProfile
            SnmpAdminString,
        alaDaUNPPortEdgeTemplate
            SnmpAdminString,   --deprecated
        alaDaUNPPortRedirectPortBounce
          INTEGER,
        alaDaUNPPort8021XFailurePolicy
          INTEGER,
        alaDaUNPPort8021XBypassStatus
          INTEGER,
        alaDaUNPPortMacAllowEap
          INTEGER,
        alaDaUNPPortAdminControlledDirections
          INTEGER,
        alaDaUNPPortAdminControlledOperDirections
          INTEGER,
        alaDaUNPPort8021XPassAltUserNetProfName
            SnmpAdminString,  --deprecated
        alaDaUNPPort8021XPassAltSpbProfName
            SnmpAdminString,  --deprecated
        alaDaUNPPort8021XPassAltVxlanProfName
            SnmpAdminString,  --deprecated
        alaDaUNPPortPassAltVxlanProfileName
            SnmpAdminString,  --deprecated
        alaDaUNPPortDefaultVxlanProfileName
            SnmpAdminString,  --deprecated
        alaDaUNPPortAFDConfig
            INTEGER,
        alaDaUNPPortMaxIngressBw
            Integer32,
        alaDaUNPPortMaxIngressBwSource
            INTEGER,
        alaDaUNPPortMaxEgressBw
            Integer32,
        alaDaUNPPortMaxEgressBwSource
            INTEGER,
        alaDaUNPPortMaxIngressDepth
            Integer32,
        alaDaUNPPortMaxEgressDepth
            Integer32,
        alaDaUNPPortIngressSourceProfile
            SnmpAdminString,
        alaDaUNPPortEgressSourceProfile
            SnmpAdminString,
        alaDaUNPPortForceL3Learning
            INTEGER,
        alaDaUNPPortForceL3LearningPortBounce
            INTEGER,
        alaDaUNPPort8021XPassAltProfileName
            SnmpAdminString,
        alaDaUNPPortPortTemplateName
            SnmpAdminString,
        alaDaUNPPortDomainID
            Unsigned32,
        alaDaUNPPortAdminState
            INTEGER,
        alaDaUNPPortDynamicService
            INTEGER,
        alaDaUNPPortPVlanPortType
            INTEGER
    }

alaDaUNPPortIfIndex OBJECT-TYPE
    SYNTAX      InterfaceIndexOrZero
    MAX-ACCESS  not-accessible
    STATUS      current
    DESCRIPTION
        "The interface index of the UNP enabled port."
    ::= { alaDaUNPPortEntry 1 }

alaDaUNPPortDefaultProfileName OBJECT-TYPE
    SYNTAX      SnmpAdminString ( SIZE( 0 .. 32 ) )
    MAX-ACCESS  read-create
    STATUS      current
    DESCRIPTION
        "The default UNP name."
    ::= { alaDaUNPPortEntry 2 }

alaDaUNPPortPassAltProfileName OBJECT-TYPE
    SYNTAX      SnmpAdminString ( SIZE( 0 .. 32 ) )
    MAX-ACCESS  read-create
    STATUS      current
    DESCRIPTION
        "The Pass alternate UNP name."
    ::= { alaDaUNPPortEntry 3 }

alaDaUNPPortRowStatus OBJECT-TYPE
    SYNTAX      RowStatus
    MAX-ACCESS  read-create
    STATUS      current
    DESCRIPTION
        "The status of this table entry."
    ::= { alaDaUNPPortEntry 4 }

alaDaUNPPortMacAuthFlag OBJECT-TYPE
    SYNTAX     INTEGER {
                   enable  (1),
                   disable (2)
               }
    MAX-ACCESS  read-create
    STATUS      current
    DESCRIPTION
        "The flag to indicate if MAC AUTH is enabled on port."
    ::= { alaDaUNPPortEntry 5 }

alaDaUNPPortClassificationFlag OBJECT-TYPE
    SYNTAX     INTEGER {
                   enable  (1),
                   disable (2)
               }
    MAX-ACCESS  read-create
    STATUS      current
    DESCRIPTION
        "The flag to indicate if Classification is enabled on port."
    ::= { alaDaUNPPortEntry 6 }

alaDaUNPPortTrustTagStatus OBJECT-TYPE
    SYNTAX     INTEGER {
                   enable  (1),
                   disable (2)
               }
    MAX-ACCESS  read-create
    STATUS      current
    DESCRIPTION
        "The flag to indicate whether the vlan tag in the incoming packet
         could be used for classifying the user when mac authentication fails
         and classification rules dont match."
    ::= { alaDaUNPPortEntry 7 }

alaDaUNPPortMCLagConfigStatus OBJECT-TYPE
    SYNTAX      AlaMultiChassisConfigStatus
    MAX-ACCESS  read-only
    STATUS      current
    DESCRIPTION
          "Result of MCLAG Consistency Check. All rows will be created as local.
           Actual status will be set through remote chassis synchronization."
    DEFVAL { local }
    ::= { alaDaUNPPortEntry 8 }


alaDaUNPPortCustomerDomainId OBJECT-TYPE
    SYNTAX      Unsigned32 (0..4294967295)
    MAX-ACCESS  read-create
    STATUS      deprecated
    DESCRIPTION
        "The Customer Domain that this port belongs to.  Default is on domain 0."
    ::= { alaDaUNPPortEntry 9 }

alaDaUNPPortType OBJECT-TYPE
    SYNTAX      INTEGER {
                    bridgePort (1),
                    spbAccessPort (2),
                    edge (3),
                    vxlanAccessPort (4),
                    accessPort (5)
                }
    MAX-ACCESS  read-create
    STATUS      current
    DESCRIPTION
        "The object defines the port as UNP enable bridge-port(1), spb-access-port(2), edge-port(3) and vxlan-access-port(4)."
    DEFVAL { bridgePort }
    ::= { alaDaUNPPortEntry 10 }

alaDaUNPPortPassAltSpbProfileName OBJECT-TYPE
    SYNTAX      SnmpAdminString ( SIZE( 0 .. 32 ) )
    MAX-ACCESS  read-create
    STATUS      deprecated
    DESCRIPTION
        "The Pass alternate Spb Profile name.  This is to be used on a successful authentication
         and there is no SPB profile passed back from the Authentication Server."
    ::= { alaDaUNPPortEntry 11 }

alaDaUNPPortDefaultSpbProfileName OBJECT-TYPE
    SYNTAX      SnmpAdminString ( SIZE( 0 .. 32 ) )
    MAX-ACCESS  read-create
    STATUS      deprecated
    DESCRIPTION
        "The default Spb Profile name."
    ::= { alaDaUNPPortEntry 12 }

alaDaUNPPortDefaultEdgeProfName  OBJECT-TYPE
    SYNTAX      SnmpAdminString ( SIZE( 0 .. 32 ) )
    MAX-ACCESS  read-create
    STATUS      deprecated
    DESCRIPTION
        "The default Edge  Profile name."
    ::= { alaDaUNPPortEntry 13 }

alaDaUNPPortMacPassEdgeProfName   OBJECT-TYPE
    SYNTAX      SnmpAdminString ( SIZE( 0 .. 32 ) )
    MAX-ACCESS  read-create
    STATUS      deprecated
    DESCRIPTION
        "Mac Authenticattion Edge Profile Name ."
    ::= { alaDaUNPPortEntry 14 }

alaDaUNPPort8021XEdgeProfName OBJECT-TYPE
    SYNTAX      SnmpAdminString ( SIZE( 0 .. 32 ) )
    MAX-ACCESS  read-create
    STATUS      deprecated
    DESCRIPTION
        "802.1X Pass Alternate Edge Profile ."
    ::= { alaDaUNPPortEntry 15 }

alaDaUNPPort8021XAuthStatus OBJECT-TYPE
    SYNTAX     INTEGER {
                   enable  (1),
                   disable (2)
               }
    MAX-ACCESS  read-create
    STATUS      current
    DESCRIPTION
        " flag to indicate 802.1X Authentication ."
    DEFVAL { disable }
    ::= { alaDaUNPPortEntry 16 }

alaDaUNPPort8021XTxPeriodStatus OBJECT-TYPE
    SYNTAX     INTEGER {
                   enable  (1),
                   disable (2)
               }
    MAX-ACCESS  read-create
    STATUS      deprecated
    DESCRIPTION
        " flag to indicate if 802.1X Authentication
          tx-period is configured or not."
        DEFVAL { disable }
    ::= { alaDaUNPPortEntry 17 }

alaDaUNPPort8021XTxPeriod   OBJECT-TYPE
    SYNTAX      Integer32(1..60)
    UNITS           "seconds"
    MAX-ACCESS  read-create
    STATUS      current
    DESCRIPTION
        "802.1X Tx periaod ."
    DEFVAL { 30 }
    ::= { alaDaUNPPortEntry 18 }

alaDaUNPPort8021XSuppTimeoutStatus OBJECT-TYPE
    SYNTAX     INTEGER {
                   enable  (1),
                   disable (2)
               }
    MAX-ACCESS  read-create
    STATUS      deprecated
    DESCRIPTION
        " flag to indicate if 802.1X Authentication
          supp-timeout is configured or not."
        DEFVAL { disable }
    ::= { alaDaUNPPortEntry 19 }

alaDaUNPPort8021XSuppTimeOut OBJECT-TYPE
    SYNTAX      Integer32(1..120)
     UNITS           "seconds"
    MAX-ACCESS  read-create
    STATUS      current
    DESCRIPTION
        "802.1X Authenttication Supp Timeout ."
    DEFVAL { 30 }
    ::= { alaDaUNPPortEntry 20 }

alaDaUNPPort8021XMaxReqStatus OBJECT-TYPE
    SYNTAX     INTEGER {
                   enable  (1),
                   disable (2)
               }
    MAX-ACCESS  read-create
    STATUS      deprecated
    DESCRIPTION
        " flag to indicate if 802.1X Authentication
          max-req is configured or not."
        DEFVAL { disable }
    ::= { alaDaUNPPortEntry 21 }

alaDaUNPPort8021XMaxReq OBJECT-TYPE
    SYNTAX      Integer32(0..3)
    MAX-ACCESS  read-create
    STATUS      current
    DESCRIPTION
        " 802.1X Authenttication Max Req ."
        DEFVAL { 2 }
    ::= { alaDaUNPPortEntry 22 }

alaDaUNPPortGroupId OBJECT-TYPE
    SYNTAX      Integer32(0..255)
    MAX-ACCESS  read-create
    STATUS      deprecated
    DESCRIPTION
        "Associated Group ID ."
    ::= { alaDaUNPPortEntry 23 }

alaDaUNPPortAaaProfile  OBJECT-TYPE
    SYNTAX      SnmpAdminString ( SIZE( 0 .. 32 ) )
    MAX-ACCESS  read-create
    STATUS      current
    DESCRIPTION
        "Associated Aaa Profile."
    ::= { alaDaUNPPortEntry 24 }

alaDaUNPPortEdgeTemplate    OBJECT-TYPE
    SYNTAX      SnmpAdminString ( SIZE( 0 .. 32 ) )
    MAX-ACCESS  read-create
    STATUS      deprecated
    DESCRIPTION
        "Associated Edge Template ."
    ::= { alaDaUNPPortEntry 25 }

alaDaUNPPortRedirectPortBounce OBJECT-TYPE
    SYNTAX     INTEGER {
                   enable  (1),
                   disable (2)
               }
    MAX-ACCESS  read-create
    STATUS      current
    DESCRIPTION
            "The flag to indicate whether port-bounce is enabled or disabled on port."
    ::= { alaDaUNPPortEntry 26 }

alaDaUNPPort8021XFailurePolicy OBJECT-TYPE
    SYNTAX INTEGER {
               default (1),
               macAuth (2)
           }
    MAX-ACCESS read-create
    STATUS current
    DESCRIPTION
    " Failure Policy type."
    ::= { alaDaUNPPortEntry 27 }

alaDaUNPPort8021XBypassStatus  OBJECT-TYPE
    SYNTAX     INTEGER {
                   enable  (1),
                   disable (2)
               }
    MAX-ACCESS read-create
    STATUS current
    DESCRIPTION
    " Flag to indicate Bypass enable status on port."
    ::= { alaDaUNPPortEntry 28 }

alaDaUNPPortMacAllowEap OBJECT-TYPE
    SYNTAX INTEGER {
               pass   (1),
               fail   (2),
               noauth (3),
               none   (4)
           }
    MAX-ACCESS read-create
    STATUS current
    DESCRIPTION
        " Flag to indicate Allow Eap on port."
    ::= { alaDaUNPPortEntry 29 }

alaDaUNPPortAdminControlledDirections OBJECT-TYPE
    SYNTAX      INTEGER {
                    both    (1),
                    in      (2),
                    noVal   (3)
                }
    MAX-ACCESS  read-create
    STATUS      current
    DESCRIPTION
         "The current value of the administrative controlled
         directions parameter for the Port."
    DEFVAL { both }
    ::= { alaDaUNPPortEntry 30 }

alaDaUNPPortAdminControlledOperDirections OBJECT-TYPE
    SYNTAX      INTEGER {
                    both    (1),
                    in      (2),
                    noVal   (3)
                }
    MAX-ACCESS  read-only
    STATUS      current
    DESCRIPTION
         "The operational value of the administrative controlled
         directions parameter for the Port."
    DEFVAL { both }
    ::= { alaDaUNPPortEntry 31 }

alaDaUNPPort8021XPassAltUserNetProfName OBJECT-TYPE
    SYNTAX      SnmpAdminString ( SIZE( 0 .. 32 ) )
    MAX-ACCESS  read-create
    STATUS      deprecated
    DESCRIPTION
        "802.1X Pass Alternate Vlan Profile ."
    ::= { alaDaUNPPortEntry 32 }

alaDaUNPPort8021XPassAltSpbProfName OBJECT-TYPE
    SYNTAX      SnmpAdminString ( SIZE( 0 .. 32 ) )
    MAX-ACCESS  read-create
    STATUS      deprecated
    DESCRIPTION
        "802.1X Pass Alternate SPB Profile ."
    ::= { alaDaUNPPortEntry 33 }

alaDaUNPPort8021XPassAltVxlanProfName OBJECT-TYPE
    SYNTAX      SnmpAdminString ( SIZE( 0 .. 32 ) )
    MAX-ACCESS  read-create
    STATUS      deprecated
    DESCRIPTION
        "802.1X Pass Alternate VXLAN Profile ."
    ::= { alaDaUNPPortEntry 34 }

alaDaUNPPortPassAltVxlanProfileName OBJECT-TYPE
    SYNTAX      SnmpAdminString ( SIZE( 0 .. 32 ) )
    MAX-ACCESS  read-create
    STATUS      deprecated
    DESCRIPTION
        "The Pass alternate VXLAN Profile name."
    ::= { alaDaUNPPortEntry 35 }

alaDaUNPPortDefaultVxlanProfileName OBJECT-TYPE
    SYNTAX      SnmpAdminString ( SIZE( 0 .. 32 ) )
    MAX-ACCESS  read-create
    STATUS      deprecated
    DESCRIPTION
        "The default VXLAN Profile name."
    ::= { alaDaUNPPortEntry 36 }

alaDaUNPPortAFDConfig OBJECT-TYPE
    SYNTAX      INTEGER {
                    admin       (1),
                    autoFabric  (2)
                }
    MAX-ACCESS  read-only
    STATUS      current
    DESCRIPTION
         "Configuration is made by admin or auto-fabric on
         this interface"
    DEFVAL { admin }
    ::= { alaDaUNPPortEntry 37 }

alaDaUNPPortMaxIngressBw OBJECT-TYPE
    SYNTAX      Integer32 (-1|0..10485760)
    UNITS       "kilobits per second"
    MAX-ACCESS  read-only
    STATUS      current
    DESCRIPTION
         "Current Ingress BW active on UNP Port in Kbps.
          If value is -1, it means no Ingress Bandwidth exists on port."
    DEFVAL { 0 }
    ::= { alaDaUNPPortEntry 38 }

alaDaUNPPortMaxIngressBwSource  OBJECT-TYPE
    SYNTAX      INTEGER {
         notApplicable (1),
         unp           (2),
         qos           (3)
    }
    MAX-ACCESS  read-only
    STATUS      current
    DESCRIPTION
         "Application responsible for setting Ingress BW on port."
    DEFVAL { notApplicable }
    ::= { alaDaUNPPortEntry 39 }

alaDaUNPPortMaxEgressBw OBJECT-TYPE
    SYNTAX      Integer32 (-1|0..10485760)
    UNITS       "kilobits per second"
    MAX-ACCESS  read-only
    STATUS      current
    DESCRIPTION
         "Current Egress BW active on UNP Port in Kbps.
          If value is -1, it means no Egress Bandwidth exists on port."
    DEFVAL { 0 }
    ::= { alaDaUNPPortEntry 40 }

alaDaUNPPortMaxEgressBwSource  OBJECT-TYPE
    SYNTAX      INTEGER {
          notApplicable (1),
          unp           (2),
          qos           (3)
    }
    MAX-ACCESS  read-only
    STATUS      current
    DESCRIPTION
         "Application responsible for setting Egress BW on port."
    DEFVAL { notApplicable }
    ::= { alaDaUNPPortEntry 41 }

alaDaUNPPortMaxIngressDepth OBJECT-TYPE
    SYNTAX      Integer32 (-1|0..16384)
    MAX-ACCESS  read-only
    STATUS      current
    DESCRIPTION
         "Ingress Depth applied on the port."
    DEFVAL { 0 }
    ::= { alaDaUNPPortEntry 42 }

alaDaUNPPortMaxEgressDepth OBJECT-TYPE
    SYNTAX      Integer32 (-1|0..16384)
    MAX-ACCESS  read-only
    STATUS      current
    DESCRIPTION
         "Egress Depth applied on the port."
    DEFVAL { 0 }
    ::= { alaDaUNPPortEntry 43 }

alaDaUNPPortIngressSourceProfile OBJECT-TYPE
    SYNTAX      SnmpAdminString ( SIZE( 0 .. 32 ) )
    MAX-ACCESS  read-only
    STATUS      current
    DESCRIPTION
        "The name of the UNP Profile responsible for setting current Ingress
        Bandwidth limitation on port. Applicable only if current bandwidth set is
        due to UNP classification on port."
    ::= { alaDaUNPPortEntry  44 }

alaDaUNPPortEgressSourceProfile OBJECT-TYPE
    SYNTAX      SnmpAdminString ( SIZE( 0 .. 32 ) )
    MAX-ACCESS  read-only
    STATUS      current
    DESCRIPTION
        "The name of the UNP Profile responsible for setting current Egress
        Bandwidth limitation on port. Applicable only if current bandwidth set is
        due to UNP classification on port"
    ::= { alaDaUNPPortEntry  45 }

alaDaUNPPortForceL3Learning  OBJECT-TYPE
    SYNTAX     INTEGER {
        enable (1),
        disable (2)
    }
    MAX-ACCESS  read-create
    STATUS      current
    DESCRIPTION
              "UNP force L3 learning status on the UNP Port."
    ::= { alaDaUNPPortEntry 46 }

alaDaUNPPortForceL3LearningPortBounce OBJECT-TYPE
    SYNTAX     INTEGER {
        enable (1),
        disable (2)
    }
    MAX-ACCESS  read-create
    STATUS      current
    DESCRIPTION
              "Port-Bounce associated with UNP force L3 learning status on the UNP Port."
    ::= { alaDaUNPPortEntry 47 }

alaDaUNPPort8021XPassAltProfileName OBJECT-TYPE
    SYNTAX      SnmpAdminString ( SIZE( 0 .. 32 ) )
    MAX-ACCESS  read-create
    STATUS      current
    DESCRIPTION
        "802.1X Pass Alternate Profile ."
    ::= { alaDaUNPPortEntry 48 }

alaDaUNPPortPortTemplateName OBJECT-TYPE
    SYNTAX      SnmpAdminString ( SIZE( 0 .. 32 ) )
    MAX-ACCESS  read-create
    STATUS      current
    DESCRIPTION
        "Associated port Template ."
    ::= { alaDaUNPPortEntry 49 }

alaDaUNPPortDomainID OBJECT-TYPE
    SYNTAX      Unsigned32 (0..4294967295)
    MAX-ACCESS  read-create
    STATUS      current
    DESCRIPTION
        "The Domain that this port belongs to.  Default is on domain 0."
    ::= { alaDaUNPPortEntry 50 }

alaDaUNPPortAdminState OBJECT-TYPE
    SYNTAX      INTEGER {
                    enable  (1),
                    disable (2)
                }
    MAX-ACCESS  read-create
    STATUS      current
    DESCRIPTION
        "The flag to indicate if admin state is enabled on port."
    ::= { alaDaUNPPortEntry 51 }

alaDaUNPPortDynamicService OBJECT-TYPE
    SYNTAX      INTEGER {
                    none (1),
                    spb  (2),
                    vxlan (3)
                }
    MAX-ACCESS  read-create
    STATUS      current
    DESCRIPTION
        "Indicates the type of dynamic service for the port.
	Dynamic Service type SPB/VXLAN are applicable for Access type UNP port."
    DEFVAL          { none }
    ::= { alaDaUNPPortEntry 52 }

alaDaUNPPortPVlanPortType OBJECT-TYPE
    SYNTAX      INTEGER {
                    none (1),
                    community (2),
                    isolated (3)
                }
    MAX-ACCESS  read-only
    STATUS      current
    DESCRIPTION
        "The Port type in PVLAN Domain."
    DEFVAL      { none }
    ::= { alaDaUNPPortEntry 53 }

--------------------------------------------------------------
--  UNP Global configuration
--------------------------------------------------------------

alaDaUNPGlobalConfiguration    OBJECT IDENTIFIER ::= { alaIND1DaMIBObjects 8 }

alaDaUNPDynamicVlanConfigFlag OBJECT-TYPE
    SYNTAX      INTEGER {
                    enable  (1),
                    disable (2)
                }
    MAX-ACCESS  read-write
    STATUS      current
    DESCRIPTION
        "Indicated whether dynamic vlan configuration is enabled or not."
    DEFVAL      { disable }
    ::= { alaDaUNPGlobalConfiguration 1 }

alaDaUNPAuthServerDownUnp OBJECT-TYPE
    SYNTAX      SnmpAdminString (SIZE(0..32))
    MAX-ACCESS  read-write
    STATUS      deprecated
    DESCRIPTION
        "The UNP to be used for classification if the authentication server
        is not reachable."
    ::= { alaDaUNPGlobalConfiguration 2 }

alaDaUNPAuthServerDownTimeout OBJECT-TYPE
    SYNTAX      Integer32 (10..1000)
    UNITS       "Seconds"
    MAX-ACCESS  read-write
    STATUS      current
    DESCRIPTION
        "The timeout, in seconds, after which all the users learned in the auth-server-down
         UNP will be sent for re-authentication."
    DEFVAL      { 60 }
    ::= { alaDaUNPGlobalConfiguration 3 }

alaDaUNPDynamicVlanMCLagConfigStatus   OBJECT-TYPE
    SYNTAX      AlaMultiChassisConfigStatus
    MAX-ACCESS  read-only
    STATUS      current
    DESCRIPTION
        "Indicated whether dynamic vlan configuration is sync across both MCLAG chassis or not.
         All rows will be created as local. Actual status will be set through remote chassis
         synchronization."
    DEFVAL      { local }
    ::= { alaDaUNPGlobalConfiguration 4 }

alaDaUNPAuthServerDownUNPMCLagConfigStatus OBJECT-TYPE
    SYNTAX      AlaMultiChassisConfigStatus
    MAX-ACCESS  read-only
    STATUS      current
    DESCRIPTION
        "Indicated whether Auth server down UNP config is sync across both MCLAG
         chassis or not. All rows will be created as local. Actual status will be
         set through remote chassis synchronization."
    DEFVAL      { local }
    ::= { alaDaUNPGlobalConfiguration 5 }

alaDaUNPAuthServerDownTimeoutMCLagConfigStatus OBJECT-TYPE
    SYNTAX      AlaMultiChassisConfigStatus
    MAX-ACCESS  read-only
    STATUS      current
    DESCRIPTION
        "Indicated whether Auth server down timeout config is sync across both MCLAG
         chassis or not. All rows will be created as local. Actual status will be set
         through remote chassis synchronization."
    DEFVAL      { local }
    ::= { alaDaUNPGlobalConfiguration 6 }

alaDaUNPDynamicProfileConfigFlag OBJECT-TYPE
    SYNTAX      INTEGER {
                    enable  (1),
                    disable (2)
                }
    MAX-ACCESS  read-write
    STATUS      current
    DESCRIPTION
        "Indicated whether dynamic profile configuration is enabled or not."
    DEFVAL      { disable }
    ::= { alaDaUNPGlobalConfiguration 7 }

alaDaUNPDynamicProfileConfigMCLagConfigStatus OBJECT-TYPE
    SYNTAX      AlaMultiChassisConfigStatus
    MAX-ACCESS  read-only
    STATUS      current
    DESCRIPTION
        "Indicated whether dynamic profile creation is sync across both MCLAG
        chassis or not."
    DEFVAL      { local }
    ::= { alaDaUNPGlobalConfiguration 8 }

alaDaUNPReloadVsiTypeDB OBJECT-TYPE
    SYNTAX      INTEGER {
                    default  (0),
                    true     (1)
                }
    MAX-ACCESS  read-write
    STATUS      current
    DESCRIPTION
        "The object triggers the system to reload the VSI Type DB from flash.
         Once the operation is done it is reset to zero (0)."
    ::= { alaDaUNPGlobalConfiguration 9 }

alaDaUNPAuthSrvDownEdgeProfName OBJECT-TYPE
    SYNTAX      SnmpAdminString (SIZE(0..32))
    MAX-ACCESS  read-write
    STATUS      deprecated
    DESCRIPTION
        "The Edge Profile  to be used for classification if the authentication server
        is not reachable."
    ::= { alaDaUNPGlobalConfiguration 10 }

alaDaUNPAuthServerDowneEdgeProfTimeout OBJECT-TYPE
    SYNTAX      Integer32 (10..1000)
    UNITS       "Seconds"
    MAX-ACCESS  read-write
    STATUS      deprecated
    DESCRIPTION
        "The timeout, in seconds, after which all the users learned in the auth-server-down
        Edge Profile will be sent for re-authentication."
    DEFVAL      { 60 }
    ::= { alaDaUNPGlobalConfiguration 11 }

alaDaUNPEdgeUserFlush OBJECT-TYPE
    SYNTAX      TruthValue
    MAX-ACCESS  read-write
    STATUS      deprecated
    DESCRIPTION
        "Global configuration to flush Edge User ."
    DEFVAL   { false }
    ::= { alaDaUNPGlobalConfiguration 12 }

alaDaUNP8021XEdgeUserFlush OBJECT-TYPE
    SYNTAX      TruthValue
    MAX-ACCESS  read-write
    STATUS      current
    DESCRIPTION
        "Global configuration to flush Edge User based on auth 802.1X ."
    DEFVAL   { false }
    ::= { alaDaUNPGlobalConfiguration 13 }

alaDaUNPMacEdgeUserFlush OBJECT-TYPE
    SYNTAX      TruthValue
    MAX-ACCESS  read-write
    STATUS      current
    DESCRIPTION
        "Global configuration to flush Edge User based on auth mac ."
    DEFVAL   { false }
    ::= { alaDaUNPGlobalConfiguration 14 }

alaDaUNPNoAuthEdgeUserFlush OBJECT-TYPE
    SYNTAX      TruthValue
    MAX-ACCESS  read-write
    STATUS      current
    DESCRIPTION
        "For no authentication , Global configuration to flush Edge User ."
    DEFVAL   { false }
    ::= { alaDaUNPGlobalConfiguration 15 }

alaDaUNPRedirectPortBounce OBJECT-TYPE
    SYNTAX      INTEGER {
                    enable  (1),
                    disable (2)
                }
    MAX-ACCESS  read-write
    STATUS      current
    DESCRIPTION
        "Redirect port bounce status."
    DEFVAL      { disable }
    ::= { alaDaUNPGlobalConfiguration 16 }

alaDaUNPRedirectPauseTimer OBJECT-TYPE
    SYNTAX      Integer32(0|60..65535)
    MAX-ACCESS  read-write
    STATUS      current
    DESCRIPTION
        "The integer value used to identify the redirect pause timer.
        A value of zero shall be used to not support pause timer."
    ::= { alaDaUNPGlobalConfiguration 17 }

alaDaUNPRedirectProxyServerPort OBJECT-TYPE
    SYNTAX      Integer32(0| 1024..49151)
    MAX-ACCESS  read-write
    STATUS      current
    DESCRIPTION
        "The integer representing logical port on HTTP Server, By Default proxy HTTP port is 8080."
   ::= { alaDaUNPGlobalConfiguration 18 }

alaDaUNPRedirectServerIPType  OBJECT-TYPE
    SYNTAX        InetAddressType  {
                      ipv4(1),
                      ipv6(2)
                  }
    MAX-ACCESS  read-write
    STATUS      current
    DESCRIPTION
        "Address type of UNP Redirect Server."
    DEFVAL { ipv4 }
    ::= { alaDaUNPGlobalConfiguration 19 }

alaDaUNPRedirectServerIP  OBJECT-TYPE
    SYNTAX     InetAddress
    MAX-ACCESS  read-write
    STATUS      current
    DESCRIPTION
        "UNP Redirect Server IP Address."
    ::= { alaDaUNPGlobalConfiguration 20 }

alaDaUNPAuthSrvDownVxlanProfileName OBJECT-TYPE
    SYNTAX      SnmpAdminString (SIZE(0..32))
    MAX-ACCESS  read-write
    STATUS      deprecated
    DESCRIPTION
        "The Vxlan Profile  to be used for classification if the authentication server
         is not reachable."
    ::= { alaDaUNPGlobalConfiguration 21 }

alaDaUNPAuthSrvDownVxlanProfileTimeout OBJECT-TYPE
    SYNTAX      Integer32 (10..1000)
    UNITS       "Seconds"
    MAX-ACCESS  read-write
    STATUS      deprecated
    DESCRIPTION
        "The timeout, in seconds, after which all the users learned in the auth-server-down
         VXLAN Profile will be sent for re-authentication."
    DEFVAL      { 60 }
    ::= { alaDaUNPGlobalConfiguration 22 }

alaDaUNPForceL3Learning  OBJECT-TYPE
    SYNTAX     INTEGER {
        enable (1),
        disable (2)
    }
    MAX-ACCESS  read-write
    STATUS      current
    DESCRIPTION
              "UNP force L3 learning status."
    ::= { alaDaUNPGlobalConfiguration 23 }

alaDaUNPForceL3LearningPortBounce OBJECT-TYPE
    SYNTAX     INTEGER {
        enable (1),
        disable (2)
    }
    MAX-ACCESS  read-write
    STATUS      current
    DESCRIPTION
              "Port-Bounce associated with UNP force L3 learning status."
    ::= { alaDaUNPGlobalConfiguration 24 }

alaDaUNPAuthServerDownProfile1 OBJECT-TYPE
    SYNTAX      SnmpAdminString (SIZE(0..32))
    MAX-ACCESS  read-write
    STATUS      current
    DESCRIPTION
        "The profile to be used for classification if the authentication server
         is not reachable."
    ::= { alaDaUNPGlobalConfiguration 25 }

alaDaUNPAuthServerDownProfile2 OBJECT-TYPE
    SYNTAX      SnmpAdminString (SIZE(0..32))
    MAX-ACCESS  read-write
    STATUS      current
    DESCRIPTION
        "The profile to be used for classification if the authentication server
          is not reachable."
    ::= { alaDaUNPGlobalConfiguration 26 }

alaDaUNPAuthServerDownProfile3 OBJECT-TYPE
    SYNTAX      SnmpAdminString (SIZE(0..32))
    MAX-ACCESS  read-write
    STATUS      current
    DESCRIPTION
        "The profile to be used for classification if the authentication server
         is not reachable."
    ::= { alaDaUNPGlobalConfiguration 27 }

alaDaUNPVlanUserFlush OBJECT-TYPE
    SYNTAX      TruthValue
    MAX-ACCESS  read-write
    STATUS      current
    DESCRIPTION
        "Global configuration to flush Vlan User ."
    DEFVAL   { false }
    ::= { alaDaUNPGlobalConfiguration 28 }

--------------------------------------------------------------
-- DA MAC VLAN User Table
--------------------------------------------------------------

alaDaMacVlanUserTable OBJECT-TYPE
        SYNTAX      SEQUENCE OF AlaDaMacVlanUserEntry
        MAX-ACCESS  not-accessible
        STATUS      current
        DESCRIPTION
        "A table of non 802.1x supplicants learned on 802.1x authenticated ports."
::= { alaIND1DaMIBObjects 9 }

alaDaMacVlanUserEntry OBJECT-TYPE
        SYNTAX      AlaDaMacVlanUserEntry
        MAX-ACCESS  not-accessible
        STATUS      current
        DESCRIPTION
                "Non 802.1x supplicant information."
        INDEX { alaDaMacVlanUserIntfNum,
                alaDaMacVlanUserMACAddress,
				alaDaMacVlanUserVlanID }
::= { alaDaMacVlanUserTable 1 }


AlaDaMacVlanUserEntry ::=
        SEQUENCE {
                alaDaMacVlanUserIntfNum
                    InterfaceIndex,
                alaDaMacVlanUserMACAddress
					MacAddress,
				alaDaMacVlanUserVlanID
					Integer32,
                alaDaMacVlanUserAuthStatus
					INTEGER,
                alaDaMacVlanUserIpAddressType
					InetAddressType,
				alaDaMacVlanUserIpAddress
					InetAddress,
				alaDaMacVlanUserUnpUsed
					SnmpAdminString,
				alaDaMacVlanUserLoginTimeStamp
					DateAndTime,
				alaDaMacVlanUserAuthtype
					INTEGER,
				alaDaMacVlanUserClassificationSource
					AlaDaClassificationPolicyType,
				alaDaMacVlanUserMCLagLearningLoc
					INTEGER,
				alaDaMacVlanUserName
					SnmpAdminString,
				alaDaMacVlanUserRole
					SnmpAdminString,
				alaDaMacVlanUserRoleSource
					SnmpAdminString,
				alaDaMacVlanUserAuthFailReason
					SnmpAdminString,
				alaDaMacVlanUserAuthRetryCount
					Integer32,
				alaDaMacVlanUserClassifProfRule
					SnmpAdminString,
				alaDaMacVlanUserRoleRule
					SnmpAdminString,
				alaDaMacVlanUserRestAccessStatus
					INTEGER,
				alaDaMacVlanUserLocPolicyStatus
					INTEGER,
				alaDaMacVlanUserTimePolicyStatus
					INTEGER,
				alaDaMacVlanUserCapPortalStatus
					INTEGER,
				alaDaMacVlanUserQMRStatus
                                        INTEGER,
                                alaDaMacVlanUserAuthServerIpType
                                        InetAddressType,
                                alaDaMacVlanUserAuthServerIpUsed
                                        InetAddress,
                                alaDaMacVlanUserAuthServerUsed
                                        SnmpAdminString,
                                alaDaMacVlanUserServerMessage
                                        SnmpAdminString,
                                alaDaMacVlanUserRedirectionUrl
                                        SnmpAdminString,
				alaDaMacVlanUserSIPCallType
					INTEGER,
				alaDaMacVlanUserSIPMediaType
					INTEGER,
                                alaDaMacVlanUserUnpFromAuthServer
                                        SnmpAdminString,
				alaDaMacVlanUserType
					INTEGER,
				alaDaMacVlanUserServiceID
					Unsigned32,
				alaDaMacVlanUserServiceSapIDIfIndex
					InterfaceIndex,
				alaDaMacVlanUserServiceSapIDEncapVal
					TmnxEncapVal,
				alaDaMacVlanUserVxlanVnid
					Unsigned32,
				alaDaMacVlanUserSpbIsid
					Unsigned32,
				alaDaMacVlanUserSpbBVlan
					Unsigned32,
                                alaDaMacVlanUserKerberosStatus
                    			INTEGER
        }

alaDaMacVlanUserIntfNum OBJECT-TYPE
    SYNTAX      InterfaceIndex
    MAX-ACCESS  not-accessible
    STATUS      current
    DESCRIPTION
        "The ifIndex representing the slot and port where the non 802.1x supplicant is learned."
    ::= { alaDaMacVlanUserEntry 1 }

alaDaMacVlanUserMACAddress OBJECT-TYPE
    SYNTAX      MacAddress
    MAX-ACCESS  not-accessible
    STATUS      current
    DESCRIPTION
        "The MAC address of the non 802.1x supplicant."
    ::= { alaDaMacVlanUserEntry 2 }

alaDaMacVlanUserVlanID OBJECT-TYPE
        SYNTAX      Integer32 (1..4096)
        MAX-ACCESS  not-accessible
        STATUS      current
        DESCRIPTION
        "The Id of the VLAN on which the non 802.1x supplicant is learned."
    ::= { alaDaMacVlanUserEntry 3 }

alaDaMacVlanUserAuthStatus  OBJECT-TYPE
        SYNTAX  INTEGER {
                idle (1),
                inProgress (2),
                authenticated (3),
                failed (4),
                failedTimeout (5),
                failedNoServer (6),
                failedNoResources (7)
            }

        MAX-ACCESS  read-only
        STATUS      current
        DESCRIPTION
        "Authentication status of the non 802.1x supplicant."
    ::= { alaDaMacVlanUserEntry 4 }

alaDaMacVlanUserIpAddressType  OBJECT-TYPE
    SYNTAX  InetAddressType
    MAX-ACCESS read-only
    STATUS  current
    DESCRIPTION
        "The type of the IP address of the user.  For now
         only IPv4 is supported."
    ::= { alaDaMacVlanUserEntry 5 }

alaDaMacVlanUserIpAddress OBJECT-TYPE
    SYNTAX      InetAddress
    MAX-ACCESS  read-only
    STATUS      current
    DESCRIPTION
        "The ip address from which the mac user is sending the packets"
    ::= { alaDaMacVlanUserEntry 6 }

alaDaMacVlanUserUnpUsed OBJECT-TYPE
    SYNTAX      SnmpAdminString
    MAX-ACCESS  read-only
    STATUS      current
    DESCRIPTION
        "The UNP used for classifying the mac user"
    ::= { alaDaMacVlanUserEntry 7 }

alaDaMacVlanUserLoginTimeStamp OBJECT-TYPE
    SYNTAX      DateAndTime
    MAX-ACCESS  read-only
    STATUS      current
    DESCRIPTION
        "The Login time stamp of the mac user"
    ::= { alaDaMacVlanUserEntry 8 }

alaDaMacVlanUserAuthtype OBJECT-TYPE
    SYNTAX      INTEGER {
		macAuthentication	(0),
		others (1),
    onexAuthentication (2)
	}
    MAX-ACCESS  read-only
    STATUS      current
    DESCRIPTION
        "The authentication type of the mac user"
    ::= { alaDaMacVlanUserEntry 9 }

alaDaMacVlanUserClassificationSource OBJECT-TYPE
        SYNTAX      AlaDaClassificationPolicyType
        MAX-ACCESS  read-only
        STATUS      current
        DESCRIPTION
        "Classification policy under which the non 802.1x supplicant is learned."
    ::= { alaDaMacVlanUserEntry 10 }

alaDaMacVlanUserMCLagLearningLoc OBJECT-TYPE
        SYNTAX      INTEGER { local (1),
							  remote (2)
				    		}
        MAX-ACCESS  read-only
        STATUS      current
        DESCRIPTION
        "Source of Learning. Informs whether the Mac was learnt locally or through remote."
    ::= { alaDaMacVlanUserEntry 11 }

alaDaMacVlanUserName OBJECT-TYPE
    SYNTAX      SnmpAdminString
    MAX-ACCESS  read-only
    STATUS      current
    DESCRIPTION
        "The UNP used for classifying the mac user"
    ::= { alaDaMacVlanUserEntry 12 }

alaDaMacVlanUserRole OBJECT-TYPE
    SYNTAX      SnmpAdminString (SIZE(0..32))
    MAX-ACCESS  read-only
    STATUS      current
    DESCRIPTION
        "The UNP used for classifying the mac user role"
    ::= { alaDaMacVlanUserEntry 13 }

alaDaMacVlanUserRoleSource OBJECT-TYPE
    SYNTAX      SnmpAdminString (SIZE(0..32))
    MAX-ACCESS  read-only
    STATUS      current
    DESCRIPTION
        "The mac user role source"
    ::= { alaDaMacVlanUserEntry 14 }

alaDaMacVlanUserAuthFailReason OBJECT-TYPE
    SYNTAX      SnmpAdminString(SIZE(1..32))
    MAX-ACCESS  read-only
    STATUS      current
    DESCRIPTION
        "The mac vlan user auth fail reason."
    ::= { alaDaMacVlanUserEntry 15 }

alaDaMacVlanUserAuthRetryCount OBJECT-TYPE
    SYNTAX      Integer32 (1..2147483647)
    MAX-ACCESS  read-only
    STATUS      current
    DESCRIPTION
        "The mac vlan user auth retry count."
    ::= { alaDaMacVlanUserEntry 16 }

alaDaMacVlanUserClassifProfRule OBJECT-TYPE
    SYNTAX      SnmpAdminString (SIZE(0..32))
    MAX-ACCESS  read-only
    STATUS      current
    DESCRIPTION
        "The mac vlan user auth server ip address."
    ::= { alaDaMacVlanUserEntry 17 }

alaDaMacVlanUserRoleRule OBJECT-TYPE
    SYNTAX      SnmpAdminString (SIZE(0..32))
    MAX-ACCESS  read-only
    STATUS      current
    DESCRIPTION
        "The mac vlan user auth server ip address."
    ::= { alaDaMacVlanUserEntry 18 }

alaDaMacVlanUserRestAccessStatus OBJECT-TYPE
    SYNTAX      INTEGER { yes(1), no(2) }
    MAX-ACCESS  read-only
    STATUS      current
    DESCRIPTION
        "The mac vlan user auth server ip address."
    ::= { alaDaMacVlanUserEntry 19 }

alaDaMacVlanUserLocPolicyStatus OBJECT-TYPE
    SYNTAX      INTEGER { notApplicable(1), pass(2), fail(3) }
    MAX-ACCESS  read-only
    STATUS      current
    DESCRIPTION
        "The mac vlan user auth server ip address."
    ::= { alaDaMacVlanUserEntry 20 }

alaDaMacVlanUserTimePolicyStatus OBJECT-TYPE
    SYNTAX      INTEGER { notApplicable(1), pass(2), fail(3) }
    MAX-ACCESS  read-only
    STATUS      current
    DESCRIPTION
        "The mac vlan user auth server ip address."
    ::= { alaDaMacVlanUserEntry 21 }

alaDaMacVlanUserCapPortalStatus OBJECT-TYPE
    SYNTAX      INTEGER { notApplicable(1), pass(2), fail(3) }
    MAX-ACCESS  read-only
    STATUS      current
    DESCRIPTION
        "The mac vlan user auth server ip address."
    ::= { alaDaMacVlanUserEntry 22 }

alaDaMacVlanUserQMRStatus OBJECT-TYPE
    SYNTAX      INTEGER { notApplicable(1), pass(2), fail(3) }
    MAX-ACCESS  read-only
    STATUS      current
    DESCRIPTION
        "The mac vlan user auth server ip address."
    ::= { alaDaMacVlanUserEntry 23 }

alaDaMacVlanUserAuthServerIpType OBJECT-TYPE
    SYNTAX  InetAddressType
    MAX-ACCESS read-only
    STATUS  current
    DESCRIPTION
        "The type of the IP address of the user.  For now
         only IPv4 is supported."
    ::= { alaDaMacVlanUserEntry 24 }

alaDaMacVlanUserAuthServerIpUsed OBJECT-TYPE
    SYNTAX      InetAddress
    MAX-ACCESS  read-only
    STATUS      current
    DESCRIPTION
        "The authentication server ip address used to
         authentication the user."
    ::= { alaDaMacVlanUserEntry 25 }

alaDaMacVlanUserAuthServerUsed OBJECT-TYPE
    SYNTAX      SnmpAdminString (SIZE(0..32))
    MAX-ACCESS  read-only
    STATUS      current
    DESCRIPTION
        "The authentication server name (configured in AAA)
         used for the latest authentication session of the user."
    ::= { alaDaMacVlanUserEntry 26 }

alaDaMacVlanUserServerMessage OBJECT-TYPE
    SYNTAX      SnmpAdminString
    MAX-ACCESS  read-only
    STATUS      current
    DESCRIPTION
        "The RADIUS server message displayed to the user. In case of successful
         authentication the information returned in the RADIUS Reply-Message
         attribute is displayed to the user, otherwise the reason for failure
         is displayed to the user."
    ::= { alaDaMacVlanUserEntry 27 }

alaDaMacVlanUserRedirectionUrl OBJECT-TYPE
    SYNTAX      SnmpAdminString
    MAX-ACCESS  read-only
    STATUS      current
    DESCRIPTION
        "The mac vlan user redirection URL."
    ::= { alaDaMacVlanUserEntry 28 }

alaDaMacVlanUserSIPCallType  OBJECT-TYPE
        SYNTAX  INTEGER {
                normalCall (1),
                emergencyCall (2),
                notInCall (3)
            }
        MAX-ACCESS  read-only
        STATUS      current
        DESCRIPTION
        "SIP call type status of the non 802.1x supplicant."
        DEFVAL      { notInCall }
    ::= { alaDaMacVlanUserEntry 29 }

alaDaMacVlanUserSIPMediaType  OBJECT-TYPE
        SYNTAX  INTEGER {
                other (1),
                audio (2),
                video (3),
                none (4)
            }

        MAX-ACCESS  read-only
        STATUS      current
        DESCRIPTION
        "SIP media type status of the non 802.1x supplicant."
        DEFVAL      { none }
    ::= { alaDaMacVlanUserEntry 30 }

alaDaMacVlanUserUnpFromAuthServer OBJECT-TYPE
    SYNTAX      SnmpAdminString
    MAX-ACCESS  read-only
    STATUS      current
    DESCRIPTION
        "The UNP profile returned from the Authentication
         server. It also indicates if the profile is configured
         in the system or not."
    ::= { alaDaMacVlanUserEntry 31 }

alaDaMacVlanUserType  OBJECT-TYPE
        SYNTAX  INTEGER {
		bridge (1),
		spbAccess (2),
        	edge (3),
        	vxlanAccess (4)
            	}
        MAX-ACCESS  read-only
        STATUS      current
        DESCRIPTION
        "Service type of UNP user."
    ::= { alaDaMacVlanUserEntry 32 }

alaDaMacVlanUserServiceID OBJECT-TYPE
        SYNTAX        Unsigned32
        MAX-ACCESS    read-only
        STATUS        current
        DESCRIPTION
        "Service ID assigned to of UNP user."
        ::= { alaDaMacVlanUserEntry 33 }

alaDaMacVlanUserServiceSapIDIfIndex OBJECT-TYPE
        SYNTAX        InterfaceIndex
        MAX-ACCESS    read-only
        STATUS        current
        DESCRIPTION
        "Interface Index of the Service SAP-ID assigned to the UNP users."
        ::= { alaDaMacVlanUserEntry 34 }

alaDaMacVlanUserServiceSapIDEncapVal OBJECT-TYPE
        SYNTAX        TmnxEncapVal
        MAX-ACCESS    read-only
        STATUS        current
        DESCRIPTION
        "Encapsulation Value of the Service SAP-ID assigned to of UNP user."
        ::= { alaDaMacVlanUserEntry 35 }

alaDaMacVlanUserVxlanVnid OBJECT-TYPE
        SYNTAX        Unsigned32
        MAX-ACCESS    read-only
        STATUS        current
        DESCRIPTION
        "VNID assigned to the VXLAN UNP user."
        ::= { alaDaMacVlanUserEntry 36 }

alaDaMacVlanUserSpbIsid OBJECT-TYPE
        SYNTAX        Unsigned32
        MAX-ACCESS    read-only
        STATUS        current
        DESCRIPTION
        "I-SID assigned to the SPB UNP user."
        ::= { alaDaMacVlanUserEntry 37 }

alaDaMacVlanUserSpbBVlan OBJECT-TYPE
        SYNTAX        Unsigned32
        MAX-ACCESS    read-only
        STATUS        current
        DESCRIPTION
        "BVLAN ID assigned to the SPB UNP user."
        ::= { alaDaMacVlanUserEntry 38 }

alaDaMacVlanUserKerberosStatus OBJECT-TYPE
    SYNTAX      INTEGER { notApplicable(1), pass(2), fail(3) }
    MAX-ACCESS  read-only
    STATUS      current
    DESCRIPTION
        "The mac vlan user Kerberos authentication status."
    ::= { alaDaMacVlanUserEntry 39 }

--
--  Trap Definitions
--

alaDaUNPNotificationObjects    OBJECT IDENTIFIER ::= { alaIND1DaMIBObjects 10 }

unpMcLagMacIgnored NOTIFICATION-TYPE
    OBJECTS      { alaDaUnpMacAddr,
                   alaDaUnpSourceIpAddr,
                   alaDaUnpNativeVlan,
                   alaDaUnpVlan,
                   alaDaUnpMCLAGId

                 }
    STATUS       current
    DESCRIPTION
        "This trap is generated if a MAC/User is dropped due to vlan not existing or UNP is not enabled on the MCLAG"
    ::= { alaIND1DaMIBNotifications    1 }

unpMcLagConfigInconsistency NOTIFICATION-TYPE
    OBJECTS      {
                   alaDaUnpCommandType,
                   alaDaUnpName,
                   alaDaUnpMacAddr1,
                   alaDaUnpMacAddr2,
                   alaDaUnpIpAddr,
                   alaDaUnpIpMask,
                   alaDaUnpVlanTag,
                   alaDaUnpMCLAGId
                 }
    STATUS       current
    DESCRIPTION
        "This trap is generated when configuration becomes Out_of_Sync."
    ::= { alaIND1DaMIBNotifications 2 }

alaDaKerberosReqTimeoutTrap NOTIFICATION-TYPE
   OBJECTS  	{
		alaDaKerberosIpAddress,
		alaDaKerberosUserMac
		}
STATUS   current
DESCRIPTION
"This trap shall be raised when the KERBEROS server do not reply in time."
::= { alaIND1DaMIBNotifications 3 }

alaDaKerberosInactivityTimerExpiryTrap   NOTIFICATION-TYPE
	OBJECTS {
		alaDaKerberosUserName,
		alaDaKerberosUserMac,
		alaDaKerberosUserDomain
		}
STATUS   current
DESCRIPTION
"The trap shall be raised when the KERBEROS lease timer get expired for the user"
::= { alaIND1DaMIBNotifications 4}

alaDaKerberosRateLimitExceed NOTIFICATION-TYPE
	OBJECTS {
		alaDaKerberosRateLimitString
		}
STATUS   current
DESCRIPTION
"This trap shall be raised when the kerberos packets exceed the Limit."
::= { alaIND1DaMIBNotifications 5 }



alaDaUnpMacAddr OBJECT-TYPE
    SYNTAX        MacAddress
    MAX-ACCESS   accessible-for-notify
    STATUS       current
    DESCRIPTION
        "The mac which failed to get configured on peer chassis."
    ::= { alaDaUNPNotificationObjects 1 }

alaDaUnpSourceIpAddr OBJECT-TYPE
    SYNTAX        IpAddress
    MAX-ACCESS   accessible-for-notify
    STATUS       current
    DESCRIPTION
        "The ip-address of mac which failed to get configured on peer chassis."
    ::= { alaDaUNPNotificationObjects 2 }

alaDaUnpNativeVlan OBJECT-TYPE
    SYNTAX        Integer32
    MAX-ACCESS   accessible-for-notify
    STATUS       current
    DESCRIPTION
        "The native vlan of MCLAG on which the mac ingressed."
    ::= { alaDaUNPNotificationObjects 3 }


alaDaUnpVlan OBJECT-TYPE
    SYNTAX        Integer32 (1..4094)
    MAX-ACCESS   accessible-for-notify
    STATUS       current
    DESCRIPTION
        "The vlan on which mac was classified on local chassis"
    ::= { alaDaUNPNotificationObjects 4 }

alaDaUnpMCLAGId OBJECT-TYPE
    SYNTAX        Integer32
    MAX-ACCESS   accessible-for-notify
    STATUS       current
    DESCRIPTION
        "The lag id for MCLAG"
    ::= { alaDaUNPNotificationObjects 5 }



alaDaUnpCommandType OBJECT-TYPE
        SYNTAX  INTEGER {
                unpConfigCmd (1),
                macRuleConfigCmd (2),
                macRangeRuleConfigCmd (3),
                ipRuleConfigCmd (4),
                vlanTagRuleConfigCmd (5),
                authServerUnpConfigCmd (6),
                authServerTimerConfigCmd (7),
                dynamicVlanConfigCmd (8),
                lagConfigCmd (9),
                dynamicProfileConfigCmd (10)
            }
    MAX-ACCESS   accessible-for-notify
    STATUS       current
    DESCRIPTION
        "Indicates which configuration command is out-of-sync"
    ::= { alaDaUNPNotificationObjects 6 }

alaDaUnpName OBJECT-TYPE
    SYNTAX      SnmpAdminString (SIZE( 1 .. 32 ))
    MAX-ACCESS   accessible-for-notify
    STATUS       current
    DESCRIPTION
        "Indicates which unp profile is out-of-sync. If there is no UNP Profile
        associated then zero length string is sent"
    ::= { alaDaUNPNotificationObjects 7 }

alaDaUnpMacAddr1 OBJECT-TYPE
    SYNTAX       MacAddress
    MAX-ACCESS   accessible-for-notify
    STATUS       current
    DESCRIPTION
        "The mac for mac rule or the lower limit of mac-range rule."
    ::= { alaDaUNPNotificationObjects 8 }

alaDaUnpMacAddr2 OBJECT-TYPE
    SYNTAX       MacAddress
    MAX-ACCESS   accessible-for-notify
    STATUS       current
    DESCRIPTION
        "The upper limit of mac-range rule."
    ::= { alaDaUNPNotificationObjects 9 }

alaDaUnpIpAddr OBJECT-TYPE
    SYNTAX       IpAddress
    MAX-ACCESS   accessible-for-notify
    STATUS       current
    DESCRIPTION
        "The ip-address in ip-rule"
    ::= { alaDaUNPNotificationObjects 10 }

alaDaUnpIpMask OBJECT-TYPE
    SYNTAX       InetAddress
    MAX-ACCESS   accessible-for-notify
    STATUS       current
    DESCRIPTION
        "The ip-address in ip-rule"
    ::= { alaDaUNPNotificationObjects 11 }


alaDaUnpVlanTag OBJECT-TYPE
    SYNTAX        Integer32 (0..4094)
    MAX-ACCESS   accessible-for-notify
    STATUS       current
    DESCRIPTION
        "The vlan vlan-tag rule. Zero value means it is not applicable"
    ::= { alaDaUNPNotificationObjects 12 }


alaDaKerberosRateLimitString   OBJECT-TYPE
SYNTAX               SnmpAdminString (SIZE(1..32))
MAX-ACCESS           accessible-for-notify
STATUS               current
DESCRIPTION          "Failure string for Rate Limit Trap."
::= { alaDaUNPNotificationObjects 13 }


-- UNP Customer Domain Table configuration MIB --

    alaDaUnpCustomerDomainTable OBJECT-TYPE
        SYNTAX        SEQUENCE OF AlaDaUnpCustomerDomainEntry

        MAX-ACCESS    not-accessible
        STATUS        current
        DESCRIPTION
            "This table creates and deletes the UNP group within a switch."
        ::= { alaIND1DaMIBObjects 11 }

    alaDaUnpCustomerDomainEntry OBJECT-TYPE
        SYNTAX        AlaDaUnpCustomerDomainEntry
        MAX-ACCESS    not-accessible
        STATUS        current
        DESCRIPTION
            "UNP Group: entry"
        INDEX {alaDaUnpCustomerDomainId}
        ::= { alaDaUnpCustomerDomainTable 1 }

    AlaDaUnpCustomerDomainEntry ::= SEQUENCE
        {
            alaDaUnpCustomerDomainId        Unsigned32,
            alaDaUnpCustomerDomainDesc      SnmpAdminString,
            alaDaUnpCustomerDomainRowStatus RowStatus
        }

    alaDaUnpCustomerDomainId OBJECT-TYPE
        SYNTAX        Unsigned32 (0..4294967295)
        MAX-ACCESS    not-accessible
        STATUS        current
        DESCRIPTION
            "The Customer Domain ID.  Domain ID zero (0) is the default and is always present in the switch."
        ::= { alaDaUnpCustomerDomainEntry 1 }

    alaDaUnpCustomerDomainDesc OBJECT-TYPE
        SYNTAX        SnmpAdminString ( SIZE( 0 .. 128 ) )
        MAX-ACCESS    read-create
        STATUS        current
        DESCRIPTION
            "A field to provide meaningful description of the Customer Domain for easy identification of the domain."
        ::= { alaDaUnpCustomerDomainEntry 2 }

    alaDaUnpCustomerDomainRowStatus OBJECT-TYPE
        SYNTAX        RowStatus
        MAX-ACCESS    read-create
        STATUS        current
        DESCRIPTION
            "The status of this table entry."
        ::= { alaDaUnpCustomerDomainEntry 3}

--------------------------------------------------------------
-- Spb Classification Profile Table configuration MIB --
-- This table is deprecated as part of unification
--------------------------------------------------------------

alaDaSpbProfileTable OBJECT-TYPE
    SYNTAX        SEQUENCE OF AlaDaSpbProfileEntry
    MAX-ACCESS    not-accessible
    STATUS        deprecated
    DESCRIPTION
        "This table stores the Service Classification profiles created in the system.
         The entries provides information to classify device in the Service domain."
    ::= { alaIND1DaMIBObjects 12 }

alaDaSpbProfileEntry OBJECT-TYPE
    SYNTAX        AlaDaSpbProfileEntry
    MAX-ACCESS    not-accessible
    STATUS        deprecated
    DESCRIPTION
        "Service Classification Profile entry"
    INDEX {alaDaSpbProfileName}
    ::= { alaDaSpbProfileTable 1 }

AlaDaSpbProfileEntry ::= SEQUENCE   {
    alaDaSpbProfileName              SnmpAdminString,
    alaDaSpbProfileEncapVal          TmnxEncapVal,
    alaDaSpbProfileQosPolicyListName SnmpAdminString,
    alaDaSpbProfileIsid              Unsigned32,
    alaDaSpbProfileBVlan             Unsigned32,
    alaDaSpbProfileRowStatus         RowStatus,
    alaDaSpbProfileMulticastMode     INTEGER,
    alaDaSpbProfileSapVlanXlation    INTEGER,
    alaDaSpbProfileMobileTag         INTEGER,
    alaDaSpbProfileAFDConfig         INTEGER
}

alaDaSpbProfileName OBJECT-TYPE
    SYNTAX        SnmpAdminString ( SIZE( 1 .. 32 ) )
    MAX-ACCESS    not-accessible
    STATUS        deprecated
    DESCRIPTION
        "The name of this profile."
    ::= { alaDaSpbProfileEntry 1 }

alaDaSpbProfileEncapVal OBJECT-TYPE
    SYNTAX        TmnxEncapVal
    MAX-ACCESS    read-create
    STATUS        deprecated
    DESCRIPTION
        "The encapsulation to be used for the SAP connecting to the service."
    ::= { alaDaSpbProfileEntry 2 }

alaDaSpbProfileQosPolicyListName OBJECT-TYPE
    SYNTAX        SnmpAdminString ( SIZE( 0 .. 32 ) )
    MAX-ACCESS    read-create
    STATUS        deprecated
    DESCRIPTION
        "The name of the QoS Policy List name that will be used if this
         User Network Profile is applied for a given device along with
         alaDaSpbProfileVlanID."
    ::= { alaDaSpbProfileEntry 3 }

alaDaSpbProfileIsid OBJECT-TYPE
    SYNTAX        Unsigned32 (256..16777214)
    MAX-ACCESS    read-create
    STATUS        deprecated
    DESCRIPTION
        "The object represnet the I-SID that is to be dynamically created when
         alaDaSpbProfileServiceID does not exist in the system and must be
         used along with alaDaSpbProfileBVlan."
    ::= { alaDaSpbProfileEntry 4 }

alaDaSpbProfileBVlan OBJECT-TYPE
    SYNTAX        Unsigned32 (1..4094)
    MAX-ACCESS    read-create
    STATUS        deprecated
    DESCRIPTION
        "The Backbone VLAN ID (BVLAN) used for the I-SID specified in alaDaSpbProfileIsid.
         This object must be specified along with alaDaSpbProfileIsid."
    ::= { alaDaSpbProfileEntry 5 }

alaDaSpbProfileRowStatus OBJECT-TYPE
    SYNTAX        RowStatus
    MAX-ACCESS    read-create
    STATUS        deprecated
    DESCRIPTION
        "The row status of this table entry."
    ::= { alaDaSpbProfileEntry 6}

alaDaSpbProfileMulticastMode OBJECT-TYPE
    SYNTAX          INTEGER { headend(1), tandem(2) }
    MAX-ACCESS      read-create
    STATUS          deprecated
    DESCRIPTION
        "To configure the multicast replication mode for each service:
         Head-end(1) where a non-unicast packet entering the SAP port
         is replicated once for each receiver in the b-domain using its
         unicast BMAC.
         Tandem(2) where a non-unicast packet entering the SAP port is
         replicated once at each node using the multicast group address."
    DEFVAL          { headend }
    ::= { alaDaSpbProfileEntry 7 }

alaDaSpbProfileSapVlanXlation OBJECT-TYPE
    SYNTAX          INTEGER {
                        enable (1),
                        disable (2)
                    }
    MAX-ACCESS      read-create
    STATUS          deprecated
    DESCRIPTION
        "To enable/disable the vlan translation for all the SAPs configured
         in this service if the corresponding access ports for the SAPs also
         has the vlan translation enabled."
    DEFVAL          { enable }
    ::= { alaDaSpbProfileEntry 8 }

alaDaSpbProfileMobileTag   OBJECT-TYPE
    SYNTAX      INTEGER {
                    enable  (1),
                    disable (2)
                }
    MAX-ACCESS  read-create
    STATUS      deprecated
    DESCRIPTION
        "SPB Profile Mobile Tag ."
    DEFVAL { disable }
    ::= { alaDaSpbProfileEntry 9 }

alaDaSpbProfileAFDConfig OBJECT-TYPE
     SYNTAX      INTEGER {
                     admin       (1),
                     autoFabric  (2)
                 }
    MAX-ACCESS  read-only
    STATUS      deprecated
    DESCRIPTION
         "Configuration is made by admin or auto-fabric on
         this profile"
    DEFVAL { admin }
    ::= { alaDaSpbProfileEntry 10 }

--
-- DA Classification Customer Domain EVB Group ID rule --
--

        alaDaUNPCustDomainEvbGpIdRuleTable  OBJECT-TYPE
                SYNTAX  SEQUENCE OF AlaDaUNPCustDomainEvbGpIdRuleEntry
                MAX-ACCESS  not-accessible
                STATUS  current
                DESCRIPTION
                "A list of EVB group ID based classification rules.  This is used to match
                 the EVB Group ID passed from EVB to a User Network Profile entry "
                ::= { alaIND1DaMIBObjects 13 }

        alaDaUNPCustDomainEvbGpIdRuleEntry  OBJECT-TYPE
            SYNTAX  AlaDaUNPCustDomainEvbGpIdRuleEntry
            MAX-ACCESS  not-accessible
            STATUS  current
            DESCRIPTION
                 "A EVB Group ID rule entry."
            INDEX {alaDaUNPCustDomainEvbGpIdRuleCustomerDomainId, alaDaUNPCustDomainEvbGpIdRuleGroupId }
            ::= { alaDaUNPCustDomainEvbGpIdRuleTable 1 }

        AlaDaUNPCustDomainEvbGpIdRuleEntry ::= SEQUENCE {
                alaDaUNPCustDomainEvbGpIdRuleCustomerDomainId Unsigned32,
                alaDaUNPCustDomainEvbGpIdRuleGroupId          Unsigned32,
                alaDaUNPCustDomainEvbGpIdRuleVlanProfileName  SnmpAdminString,
                alaDaUNPCustDomainEvbGpIdRuleSpbProfileName   SnmpAdminString,
                alaDaUNPCustDomainEvbGpIdRuleRowStatus        RowStatus,
                alaDaUNPCustDomainEvbGpIdRuleVxlanProfileName  SnmpAdminString
                }

        alaDaUNPCustDomainEvbGpIdRuleCustomerDomainId  OBJECT-TYPE
                SYNTAX  Unsigned32 (0..4294967295)
                MAX-ACCESS  not-accessible
                STATUS  current
                DESCRIPTION
                 "The UNP Customer Domain ID that will be used for profile lookup."

                ::= { alaDaUNPCustDomainEvbGpIdRuleEntry 1 }

        alaDaUNPCustDomainEvbGpIdRuleGroupId  OBJECT-TYPE
                SYNTAX  Unsigned32 (0..4294967295)
                MAX-ACCESS  not-accessible
                STATUS  current
                DESCRIPTION
                "The EVB Group ID used for profile lookup."
                ::= { alaDaUNPCustDomainEvbGpIdRuleEntry 2 }

        alaDaUNPCustDomainEvbGpIdRuleVlanProfileName  OBJECT-TYPE
                SYNTAX  SnmpAdminString ( SIZE( 1 .. 32 ) )
                MAX-ACCESS  read-create
                STATUS  current
                DESCRIPTION
                 "The VLAN profile name in the User Network Profile Table to be
                  applied."
                ::= { alaDaUNPCustDomainEvbGpIdRuleEntry 3 }

        alaDaUNPCustDomainEvbGpIdRuleSpbProfileName  OBJECT-TYPE

                SYNTAX  SnmpAdminString ( SIZE( 1 .. 32 ) )
                MAX-ACCESS  read-create
                STATUS  current
                DESCRIPTION
                 "The SBP profile name in the User Network Profile Table to be
                  applied."
                ::= { alaDaUNPCustDomainEvbGpIdRuleEntry 4 }

        alaDaUNPCustDomainEvbGpIdRuleRowStatus  OBJECT-TYPE

                SYNTAX  RowStatus
                MAX-ACCESS  read-create
                STATUS  current
                DESCRIPTION
                "Row Status for creating/deleting rules."
                 ::= { alaDaUNPCustDomainEvbGpIdRuleEntry 5 }

        alaDaUNPCustDomainEvbGpIdRuleVxlanProfileName  OBJECT-TYPE
                SYNTAX  SnmpAdminString ( SIZE( 0 .. 32 ) )
                MAX-ACCESS  read-create
                STATUS  current
                DESCRIPTION
                 "The VXLAN profile name in the User Network Profile Table to be
                  applied."
                ::= { alaDaUNPCustDomainEvbGpIdRuleEntry 6 }

-------------------------------------------------------
-- DA Classification Customer Domain VLAN TAG rule
-------------------------------------------------------

alaDaUNPCustDomainVlanTagRuleTable  OBJECT-TYPE
    SYNTAX  SEQUENCE OF AlaDaUNPCustDomainVlanTagRuleEntry
    MAX-ACCESS  not-accessible
    STATUS  current
    DESCRIPTION
        "A list of Customer Domain and Vlan Tag based classification rules.  This is used to match
        the vlan tag in a packet and the port's UNP Customer Domain to a User Network Profile entry "
    ::= { alaIND1DaMIBObjects 14 }

alaDaUNPCustDomainVlanTagRuleEntry  OBJECT-TYPE
    SYNTAX  AlaDaUNPCustDomainVlanTagRuleEntry
    MAX-ACCESS  not-accessible
    STATUS  current
    DESCRIPTION
        "A Vlan Tag rule entry."
    INDEX {
              alaDaUNPCustDomainVlanTagRuleDomainId,
	      alaDaUNPCustDomainVlanTagRuleVlan
	  }
    ::= { alaDaUNPCustDomainVlanTagRuleTable 1 }

AlaDaUNPCustDomainVlanTagRuleEntry ::= SEQUENCE {
    alaDaUNPCustDomainVlanTagRuleDomainId
        Integer32,
    alaDaUNPCustDomainVlanTagRuleVlan
	Integer32,
    alaDaUNPCustDomainVlanTagRuleVlanProfileName
        SnmpAdminString,            --deprecated
    alaDaUNPCustDomainVlanTagRuleRowStatus
        RowStatus,
    alaDaUNPCustDomainVlanTagRuleMCLagConfigStatus
        AlaMultiChassisConfigStatus,
    alaDaUNPCustDomainVlanTagRuleSpbProfileName
        SnmpAdminString,            --deprecated
    alaDaUNPCustDomainVlanTagRuleTagPosition
        INTEGER,                    --deprecated
    alaDaUNPCustDomainVlanTagRuleVxlanProfileName
        SnmpAdminString,            --deprecated
    alaDaUNPCustDomainVlanTagRuleProfile1
        SnmpAdminString,
    alaDaUNPCustDomainVlanTagRuleProfile2
        SnmpAdminString,
    alaDaUNPCustDomainVlanTagRuleProfile3
        SnmpAdminString
}

alaDaUNPCustDomainVlanTagRuleDomainId  OBJECT-TYPE
    SYNTAX  Integer32 (0..4294967295)
    MAX-ACCESS  not-accessible
    STATUS  current
    DESCRIPTION
        "The UNP Customer Domain ID for profile lookup."
    ::= { alaDaUNPCustDomainVlanTagRuleEntry 1 }

alaDaUNPCustDomainVlanTagRuleVlan  OBJECT-TYPE
    SYNTAX  Integer32 (1..4094)
    MAX-ACCESS  not-accessible
    STATUS  current
    DESCRIPTION
        "The VLAN Tag used for VLAN classification. The range states the valid
	VLAN range in the system. The VLAN Tag is of the Q-in-Q VLAN Tag
        format, where the value of the outer 802.1Q VLAN ID is encoded in the
        least significant 16 bits, and the value of the inner VLAN ID is
        encoded in the most significant 16 bits."
    ::= { alaDaUNPCustDomainVlanTagRuleEntry 2 }

alaDaUNPCustDomainVlanTagRuleVlanProfileName  OBJECT-TYPE
    SYNTAX  SnmpAdminString ( SIZE( 1 .. 32 ) )
    MAX-ACCESS  read-create
    STATUS  deprecated
    DESCRIPTION
        "The VLAN profile name in the User Network Profile Table to be applied."
    ::= { alaDaUNPCustDomainVlanTagRuleEntry 3 }

alaDaUNPCustDomainVlanTagRuleRowStatus  OBJECT-TYPE
    SYNTAX  RowStatus
    MAX-ACCESS  read-create
    STATUS  current
    DESCRIPTION
        "Row Status for creating/deleting rules."
    ::= { alaDaUNPCustDomainVlanTagRuleEntry 4 }

alaDaUNPCustDomainVlanTagRuleMCLagConfigStatus OBJECT-TYPE
    SYNTAX  AlaMultiChassisConfigStatus
    MAX-ACCESS  read-only
    STATUS  current
    DESCRIPTION
        "Result of MCLAG Consistency Check. All rows will be created as local.
        Actual status will be set through remote chassis synchronization."
    DEFVAL { local }
    ::= { alaDaUNPCustDomainVlanTagRuleEntry 5 }

alaDaUNPCustDomainVlanTagRuleSpbProfileName  OBJECT-TYPE
    SYNTAX  SnmpAdminString ( SIZE( 1 .. 32 ) )
    MAX-ACCESS  read-create
    STATUS  deprecated
    DESCRIPTION
        "The profile name in the User Network Profile Table to be
         applied."
    ::= { alaDaUNPCustDomainVlanTagRuleEntry 6 }

alaDaUNPCustDomainVlanTagRuleTagPosition  OBJECT-TYPE
    SYNTAX  INTEGER {
                notApplicable (0),
                outerTag      (1),
                innerTag      (2)
            }
    MAX-ACCESS  read-create
    STATUS  deprecated
    DESCRIPTION
        "This object specify the tag position to apply this Vlan Tag rule for
         double tagged frames."
    DEFVAL { outerTag }
    ::= { alaDaUNPCustDomainVlanTagRuleEntry 7 }

alaDaUNPCustDomainVlanTagRuleVxlanProfileName  OBJECT-TYPE
    SYNTAX  SnmpAdminString ( SIZE( 0 .. 32 ) )
    MAX-ACCESS  read-create
    STATUS  deprecated
    DESCRIPTION
        "The VXLAN profile name in the User Network Profile Table to be
        applied."
    ::= { alaDaUNPCustDomainVlanTagRuleEntry 8 }

alaDaUNPCustDomainVlanTagRuleProfile1  OBJECT-TYPE
    SYNTAX  SnmpAdminString ( SIZE( 0 .. 32 ) )
    MAX-ACCESS  read-create
    STATUS  current
    DESCRIPTION
        "The profile name in the User Network Profile Table to be
        applied."
    ::= { alaDaUNPCustDomainVlanTagRuleEntry 9 }

alaDaUNPCustDomainVlanTagRuleProfile2  OBJECT-TYPE
    SYNTAX  SnmpAdminString ( SIZE( 0 .. 32 ) )
    MAX-ACCESS  read-create
    STATUS  current
    DESCRIPTION
        "The profile name in the User Network Profile Table to be
        applied."
    ::= { alaDaUNPCustDomainVlanTagRuleEntry 10 }

alaDaUNPCustDomainVlanTagRuleProfile3  OBJECT-TYPE
    SYNTAX  SnmpAdminString ( SIZE( 0 .. 32 ) )
    MAX-ACCESS  read-create
    STATUS  current
    DESCRIPTION
        "The profile name in the User Network Profile Table to be
        applied."
    ::= { alaDaUNPCustDomainVlanTagRuleEntry 11 }

-- DA Classification Customer Domain IP network address rule

alaDaUNPCustDomainIpNetRuleTable  OBJECT-TYPE
    SYNTAX  SEQUENCE OF AlaDaUNPCustDomainIpNetRuleEntry
    MAX-ACCESS  not-accessible
    STATUS  current
    DESCRIPTION
        "A list of IP network address rules.  This is used to match
         the InetAddress of a packet to a User Network Profile entry."
    ::= { alaIND1DaMIBObjects 15 }

alaDaUNPCustDomainIpNetRuleEntry  OBJECT-TYPE
    SYNTAX  AlaDaUNPCustDomainIpNetRuleEntry
    MAX-ACCESS  not-accessible
    STATUS  current
    DESCRIPTION
        "An IP network address rule entry."
    INDEX {
              alaDaUNPCustDomainIpNetRuleDomainId,
              alaDaUNPCustDomainIpNetRuleAddrType,
              alaDaUNPCustDomainIpNetRuleAddr,
              alaDaUNPCustDomainIpNetRuleMask
          }
    ::= { alaDaUNPCustDomainIpNetRuleTable 1 }

AlaDaUNPCustDomainIpNetRuleEntry ::= SEQUENCE {
    alaDaUNPCustDomainIpNetRuleDomainId
        Integer32,
    alaDaUNPCustDomainIpNetRuleAddrType
        InetAddressType,
    alaDaUNPCustDomainIpNetRuleAddr
        InetAddress,
    alaDaUNPCustDomainIpNetRuleMask
        InetAddress,
    alaDaUNPCustDomainIpNetRuleProfileName
        SnmpAdminString,                  --deprecated
    alaDaUNPCustDomainIpNetRuleVlanTag
        Integer32,
    alaDaUNPCustDomainIpNetRuleRowStatus
        RowStatus,
    alaDaUNPCustDomainIpNetRuleMCLagConfigStatus
        AlaMultiChassisConfigStatus,
    alaDaUNPCustDomainIpNetRuleSpbProfileName
        SnmpAdminString,                  --deprecated
    alaDaUNPCustDomainIpNetRuleEdgeProfile
        SnmpAdminString,                  --deprecated
    alaDaUNPCustDomainIpNetRuleVxlanProfileName
        SnmpAdminString,                  --deprecated
    alaDaUNPCustDomainIpNetRuleProfile1
        SnmpAdminString,
    alaDaUNPCustDomainIpNetRuleProfile2
        SnmpAdminString,
    alaDaUNPCustDomainIpNetRuleProfile3
        SnmpAdminString
}

alaDaUNPCustDomainIpNetRuleDomainId  OBJECT-TYPE
    SYNTAX  Integer32 (0..4294967295)
    MAX-ACCESS  not-accessible
    STATUS  current
    DESCRIPTION
        "The UNP Customer Domain ID for profile lookup."
    ::= { alaDaUNPCustDomainIpNetRuleEntry 1 }

alaDaUNPCustDomainIpNetRuleAddrType  OBJECT-TYPE
    SYNTAX  InetAddressType
    MAX-ACCESS  not-accessible
    STATUS  current
    DESCRIPTION
        "The IP network address type used for VLAN classification.  For now
         Only IPv4 is supported."
    ::= { alaDaUNPCustDomainIpNetRuleEntry 2 }

alaDaUNPCustDomainIpNetRuleAddr  OBJECT-TYPE
    SYNTAX  InetAddress (SIZE (4|16))
    MAX-ACCESS  not-accessible
    STATUS  current
    DESCRIPTION
        "The IP network address used for VLAN classification.  Only IPv4 is
         supported."
    ::= { alaDaUNPCustDomainIpNetRuleEntry 3 }

alaDaUNPCustDomainIpNetRuleMask  OBJECT-TYPE
    SYNTAX  InetAddress (SIZE (4|16))
    MAX-ACCESS  not-accessible
    STATUS  current
    DESCRIPTION
        "The IP network mask applying to the IP network address."
    ::= { alaDaUNPCustDomainIpNetRuleEntry 4 }

alaDaUNPCustDomainIpNetRuleProfileName  OBJECT-TYPE
    SYNTAX  SnmpAdminString ( SIZE( 1 .. 32 ) )
    MAX-ACCESS  read-create
    STATUS  deprecated
    DESCRIPTION
        "The profile name in the User Network Profile Table to be
         applied."
    ::= { alaDaUNPCustDomainIpNetRuleEntry 5 }

alaDaUNPCustDomainIpNetRuleVlanTag  OBJECT-TYPE
    SYNTAX  Integer32 (0..4094)
    MAX-ACCESS  read-create
    STATUS  current
    DESCRIPTION
        "The VLAN Tag to be used for classification of tagged pkts.
         VLAN Tag of 0 indicates no VLAN is associated.
         The VLAN Tag is of the Q-in-Q VLAN Tag format, where the value of the
         outer 802.1Q VLAN ID is encoded in the least significant 16 bits,
         and the value of the inner VLAN ID is encoded in the most significant
         16 bits."
    ::= { alaDaUNPCustDomainIpNetRuleEntry 6 }

alaDaUNPCustDomainIpNetRuleRowStatus  OBJECT-TYPE
    SYNTAX  RowStatus
    MAX-ACCESS  read-create
    STATUS  current
    DESCRIPTION
        "Row Status for creating/deleting rules."
    ::= { alaDaUNPCustDomainIpNetRuleEntry 7 }

alaDaUNPCustDomainIpNetRuleMCLagConfigStatus  OBJECT-TYPE
    SYNTAX  AlaMultiChassisConfigStatus
    MAX-ACCESS  read-only
    STATUS  current
    DESCRIPTION
        "Result of MCLAG Consistency Check. All rows will be created as local.
         Actual status will be set through remote chassis synchronization."
    DEFVAL { local }
    ::= { alaDaUNPCustDomainIpNetRuleEntry 8 }

alaDaUNPCustDomainIpNetRuleSpbProfileName  OBJECT-TYPE
    SYNTAX  SnmpAdminString ( SIZE( 1 .. 32 ) )
    MAX-ACCESS  read-create
    STATUS  deprecated
    DESCRIPTION
        "The profile name in the User Network Profile Table to be
         applied."
    ::= { alaDaUNPCustDomainIpNetRuleEntry 9 }

alaDaUNPCustDomainIpNetRuleEdgeProfile  OBJECT-TYPE
    SYNTAX  SnmpAdminString ( SIZE( 1 .. 32 ) )
    MAX-ACCESS  read-create
    STATUS  deprecated
    DESCRIPTION
        "The edge profile name in the User Network Profile Table to be
         applied."
    ::= { alaDaUNPCustDomainIpNetRuleEntry 10 }

alaDaUNPCustDomainIpNetRuleVxlanProfileName  OBJECT-TYPE
    SYNTAX  SnmpAdminString ( SIZE( 0 .. 32 ) )
    MAX-ACCESS  read-create
    STATUS  deprecated
    DESCRIPTION
        "The VXLAN profile name in the User Network Profile Table to be
         applied."
    ::= { alaDaUNPCustDomainIpNetRuleEntry 11 }

alaDaUNPCustDomainIpNetRuleProfile1  OBJECT-TYPE
    SYNTAX  SnmpAdminString ( SIZE( 0 .. 32 ) )
    MAX-ACCESS  read-create
    STATUS  current
    DESCRIPTION
        "The profile name in the User Network Profile Table to be
         applied."
    ::= { alaDaUNPCustDomainIpNetRuleEntry 12 }

alaDaUNPCustDomainIpNetRuleProfile2  OBJECT-TYPE
    SYNTAX  SnmpAdminString ( SIZE( 0 .. 32 ) )
    MAX-ACCESS  read-create
    STATUS  current
    DESCRIPTION
        "The profile name in the User Network Profile Table to be
         applied."
    ::= { alaDaUNPCustDomainIpNetRuleEntry 13 }

alaDaUNPCustDomainIpNetRuleProfile3  OBJECT-TYPE
    SYNTAX  SnmpAdminString ( SIZE( 0 .. 32 ) )
    MAX-ACCESS  read-create
    STATUS  current
    DESCRIPTION
        "The profile name in the User Network Profile Table to be
         applied."
    ::= { alaDaUNPCustDomainIpNetRuleEntry 14 }

---------------------------------------------------------------
-- DA Classification Customer Domain MAC address rule
---------------------------------------------------------------

alaDaUNPCustDomainMacRuleTable  OBJECT-TYPE
    SYNTAX  SEQUENCE OF AlaDaUNPCustDomainMacRuleEntry
    MAX-ACCESS  not-accessible
    STATUS  current
    DESCRIPTION
        "A list of MAC address rules.  This is used to match
         the MAC Address of a packet to a User Network Profile entry "
    ::= { alaIND1DaMIBObjects 16 }

alaDaUNPCustDomainMacRuleEntry  OBJECT-TYPE
    SYNTAX  AlaDaUNPCustDomainMacRuleEntry
    MAX-ACCESS  not-accessible
    STATUS  current
    DESCRIPTION
        "A MAC rule entry."
    INDEX {
              alaDaUNPCustDomainMacRuleDomainId,
              alaDaUNPCustDomainMacRuleAddr
          }
    ::= { alaDaUNPCustDomainMacRuleTable 1 }

AlaDaUNPCustDomainMacRuleEntry ::= SEQUENCE {
    alaDaUNPCustDomainMacRuleDomainId
        Integer32,
    alaDaUNPCustDomainMacRuleAddr
        MacAddress,
    alaDaUNPCustDomainMacRuleProfileName
        SnmpAdminString,        --deprecated
    alaDaUNPCustDomainMacRuleVlanTag
        Integer32,
    alaDaUNPCustDomainMacRuleRowStatus
        RowStatus,
    alaDaUNPCustDomainMacRuleMCLagConfigStatus
        AlaMultiChassisConfigStatus,
    alaDaUNPCustDomainMacRuleSpbProfileName
        SnmpAdminString,        --deprecated
    alaDaUNPCustDomainMacRuleEdgeProfileName
        SnmpAdminString,        --deprecated
    alaDaUNPCustDomainMacRuleVxlanProfileName
        SnmpAdminString,        --deprecated
   alaDaUNPCustDomainMacRuleProfile1
        SnmpAdminString,
   alaDaUNPCustDomainMacRuleProfile2
        SnmpAdminString,
   alaDaUNPCustDomainMacRuleProfile3
        SnmpAdminString
}

alaDaUNPCustDomainMacRuleDomainId  OBJECT-TYPE
    SYNTAX  Integer32 (0..4294967295)
    MAX-ACCESS  not-accessible
    STATUS  current
    DESCRIPTION
        "The UNP Customer Domain ID for profile lookup."
    ::= { alaDaUNPCustDomainMacRuleEntry 1 }

alaDaUNPCustDomainMacRuleAddr  OBJECT-TYPE
    SYNTAX  MacAddress
    MAX-ACCESS  not-accessible
    STATUS  current
    DESCRIPTION
        "The MAC address used for VLAN classification."
    ::= { alaDaUNPCustDomainMacRuleEntry 2 }

alaDaUNPCustDomainMacRuleProfileName  OBJECT-TYPE
    SYNTAX  SnmpAdminString ( SIZE( 1 .. 32 ) )
    MAX-ACCESS  read-create
    STATUS  deprecated
    DESCRIPTION
        "The profile name in the User Network Profile Table to be
         applied."
    ::= { alaDaUNPCustDomainMacRuleEntry 3 }

alaDaUNPCustDomainMacRuleVlanTag  OBJECT-TYPE
    SYNTAX  Integer32 (0..4094)
    MAX-ACCESS  read-create
    STATUS  current
    DESCRIPTION
        "The VLAN Tag to be used for classification of tagged pkts.
         VLAN Tag of 0 indicates no VLAN is associated. The VLAN Tag is of
         the Q-in-Q VLAN Tag format, where the value of the outer 802.1Q
         VLAN ID is encoded in the least significant 16 bits, and the value of
         inner VLAN ID is encoded  in the most significant 16 bits."
    ::= { alaDaUNPCustDomainMacRuleEntry 4 }

alaDaUNPCustDomainMacRuleRowStatus  OBJECT-TYPE
    SYNTAX  RowStatus
    MAX-ACCESS  read-create
    STATUS  current
    DESCRIPTION
        "Row Status for creating/deleting rules."
    ::= { alaDaUNPCustDomainMacRuleEntry 5 }

alaDaUNPCustDomainMacRuleMCLagConfigStatus  OBJECT-TYPE
    SYNTAX  AlaMultiChassisConfigStatus
    MAX-ACCESS  read-only
    STATUS  current
    DESCRIPTION
        "Result of MCLAG Consistency Check. All rows will be created as local.
         Actual status will be set through remote chassis synchronization."
    DEFVAL { local }
    ::= { alaDaUNPCustDomainMacRuleEntry 6 }

alaDaUNPCustDomainMacRuleSpbProfileName  OBJECT-TYPE
    SYNTAX  SnmpAdminString ( SIZE( 1 .. 32 ) )
    MAX-ACCESS  read-create
    STATUS  deprecated
    DESCRIPTION
        "The SBP profile name in the User Network Profile Table to be
         applied."
    ::= { alaDaUNPCustDomainMacRuleEntry 7 }

alaDaUNPCustDomainMacRuleEdgeProfileName  OBJECT-TYPE
    SYNTAX  SnmpAdminString ( SIZE( 1 .. 32 ) )
    MAX-ACCESS  read-create
    STATUS  deprecated
    DESCRIPTION
        "The SBP profile name in the User Network Profile Table to be
         applied."
    ::= { alaDaUNPCustDomainMacRuleEntry 8 }

alaDaUNPCustDomainMacRuleVxlanProfileName  OBJECT-TYPE
    SYNTAX  SnmpAdminString ( SIZE( 0 .. 32 ) )
    MAX-ACCESS  read-create
    STATUS  deprecated
    DESCRIPTION
        "The VXLAN profile name in the User Network Profile Table to be
         applied."
    ::= { alaDaUNPCustDomainMacRuleEntry 9 }

alaDaUNPCustDomainMacRuleProfile1  OBJECT-TYPE
    SYNTAX  SnmpAdminString ( SIZE( 1 .. 32 ) )
    MAX-ACCESS  read-create
    STATUS  current
    DESCRIPTION
        "The profile name to be applied."
    ::= { alaDaUNPCustDomainMacRuleEntry 10 }

alaDaUNPCustDomainMacRuleProfile2  OBJECT-TYPE
    SYNTAX  SnmpAdminString ( SIZE( 1 .. 32 ) )
    MAX-ACCESS  read-create
    STATUS  current
    DESCRIPTION
        "The profile name to be applied."
    ::= { alaDaUNPCustDomainMacRuleEntry 11 }

alaDaUNPCustDomainMacRuleProfile3  OBJECT-TYPE
    SYNTAX  SnmpAdminString ( SIZE( 1 .. 32 ) )
    MAX-ACCESS  read-create
    STATUS  current
    DESCRIPTION
        "The profile name to be applied."
    ::= { alaDaUNPCustDomainMacRuleEntry 12 }

-- DA Classification Customer Domain MAC range rule

alaDaUNPCustDomainMacRangeRuleTable  OBJECT-TYPE
    SYNTAX  SEQUENCE OF AlaDaUNPCustDomainMacRangeRuleEntry
    MAX-ACCESS  not-accessible
    STATUS  current
    DESCRIPTION
        "A list of MAC range rules.  This is used to match
         the MAC Address Range of a packet to a User Network Profile entry."
    ::= { alaIND1DaMIBObjects 17 }

alaDaUNPCustDomainMacRangeRuleEntry  OBJECT-TYPE
    SYNTAX  AlaDaUNPCustDomainMacRangeRuleEntry
    MAX-ACCESS  not-accessible
    STATUS  current
    DESCRIPTION
        "A MAC range rule entry."
    INDEX {
              alaDaUNPCustDomainMacRangeRuleDomainId,
              alaDaUNPCustDomainMacRangeRuleLoAddr
          }
    ::= { alaDaUNPCustDomainMacRangeRuleTable 1 }

AlaDaUNPCustDomainMacRangeRuleEntry ::= SEQUENCE {
    alaDaUNPCustDomainMacRangeRuleDomainId
        Integer32,
    alaDaUNPCustDomainMacRangeRuleLoAddr
        MacAddress,
    alaDaUNPCustDomainMacRangeRuleHiAddr
        MacAddress,
    alaDaUNPCustDomainMacRangeRuleProfileName
        SnmpAdminString,   --deprecated
    alaDaUNPCustDomainMacRangeRuleVlanTag
        Integer32,
    alaDaUNPCustDomainMacRangeRuleRowStatus
        RowStatus,
    alaDaUNPCustDomainMacRangeRuleMCLagConfigStatus
        AlaMultiChassisConfigStatus,
    alaDaUNPCustDomainMacRangeRuleSpbProfileName
        SnmpAdminString,   --deprecated
    alaDaUNPCustDomainMacRangeRuleEdgeProfileName
        SnmpAdminString,   --deprecated
    alaDaUNPCustDomainMacRangeRuleVxlanProfileName
        SnmpAdminString,   --deprecated
    alaDaUNPCustDomainMacRangeRuleProfile1
        SnmpAdminString,
    alaDaUNPCustDomainMacRangeRuleProfile2
        SnmpAdminString,
    alaDaUNPCustDomainMacRangeRuleProfile3
        SnmpAdminString
}

alaDaUNPCustDomainMacRangeRuleDomainId  OBJECT-TYPE
    SYNTAX  Integer32 (0..4294967295)
    MAX-ACCESS  not-accessible
    STATUS  current
    DESCRIPTION
        "The UNP Customer Domain ID for profile lookup."
    ::= { alaDaUNPCustDomainMacRangeRuleEntry 1 }

alaDaUNPCustDomainMacRangeRuleLoAddr  OBJECT-TYPE
    SYNTAX  MacAddress
    MAX-ACCESS  not-accessible
    STATUS  current
    DESCRIPTION
        "The lower bound of  MAC address range used for VLAN classification."
    ::= { alaDaUNPCustDomainMacRangeRuleEntry 2 }

alaDaUNPCustDomainMacRangeRuleHiAddr  OBJECT-TYPE
    SYNTAX  MacAddress
    MAX-ACCESS  read-create
    STATUS  current
    DESCRIPTION
        "The upper bound of MAC address range used for VLAN classification."
    ::= { alaDaUNPCustDomainMacRangeRuleEntry 3 }

alaDaUNPCustDomainMacRangeRuleProfileName  OBJECT-TYPE
    SYNTAX  SnmpAdminString ( SIZE( 0 .. 32 ) )
    MAX-ACCESS  read-create
    STATUS  deprecated
    DESCRIPTION
        "The profile name in the User Network Profile Table to be
         applied."
    ::= { alaDaUNPCustDomainMacRangeRuleEntry 4 }

alaDaUNPCustDomainMacRangeRuleVlanTag  OBJECT-TYPE
    SYNTAX  Integer32 (0..4094)
    MAX-ACCESS  read-create
    STATUS  current
    DESCRIPTION
        "The VLAN Tag to be used for classification of tagged pkts.
         The range states the valid VLAN range in the system.
         VLAN Tag of 0 indicates no VLAN is associated. The VLAN tag is of the
         Q-in-Q VLAN Tag format, where the value of the outer 802.1Q VLAN ID is
         encoded in the least significant 16 bits, and the value of the inner
         VLAN ID is encoded in the most significant 16 bits."
    ::= { alaDaUNPCustDomainMacRangeRuleEntry 5 }

alaDaUNPCustDomainMacRangeRuleRowStatus  OBJECT-TYPE
    SYNTAX  RowStatus
    MAX-ACCESS  read-create
    STATUS  current
    DESCRIPTION
        "Row Status for creating/deleting rules."
    ::= { alaDaUNPCustDomainMacRangeRuleEntry 6 }

alaDaUNPCustDomainMacRangeRuleMCLagConfigStatus  OBJECT-TYPE
    SYNTAX  AlaMultiChassisConfigStatus
    MAX-ACCESS  read-only
    STATUS  current
    DESCRIPTION
        "Result of MCLAG Consistency Check. All rows will be created as local.
         Actual status will be set through remote chassis synchronization."
    DEFVAL { local }
    ::= { alaDaUNPCustDomainMacRangeRuleEntry 7 }

alaDaUNPCustDomainMacRangeRuleSpbProfileName  OBJECT-TYPE
    SYNTAX  SnmpAdminString ( SIZE( 0 .. 32 ) )
    MAX-ACCESS  read-create
    STATUS  deprecated
    DESCRIPTION
        "The SBP profile name in the User Network Profile Table to be
         applied."
    ::= { alaDaUNPCustDomainMacRangeRuleEntry 8 }

alaDaUNPCustDomainMacRangeRuleEdgeProfileName  OBJECT-TYPE
    SYNTAX  SnmpAdminString ( SIZE( 0 .. 32 ) )
    MAX-ACCESS  read-create
    STATUS  deprecated
    DESCRIPTION
        "The Edge profile name in the User Network Profile Table to be
         applied."
   ::= { alaDaUNPCustDomainMacRangeRuleEntry 9 }

alaDaUNPCustDomainMacRangeRuleVxlanProfileName  OBJECT-TYPE
    SYNTAX  SnmpAdminString ( SIZE( 0 .. 32 ) )
    MAX-ACCESS  read-create
    STATUS  deprecated
    DESCRIPTION
        "The VXLAN profile name in the User Network Profile Table to be
         applied."
    ::= { alaDaUNPCustDomainMacRangeRuleEntry 10 }

alaDaUNPCustDomainMacRangeRuleProfile1  OBJECT-TYPE
    SYNTAX  SnmpAdminString ( SIZE( 0 .. 32 ) )
    MAX-ACCESS  read-create
    STATUS  current
    DESCRIPTION
        "The profile name to be appiled."
    ::= { alaDaUNPCustDomainMacRangeRuleEntry 11 }

alaDaUNPCustDomainMacRangeRuleProfile2  OBJECT-TYPE
    SYNTAX  SnmpAdminString ( SIZE( 0 .. 32 ) )
    MAX-ACCESS  read-create
    STATUS  current
    DESCRIPTION
        "The profile name to be appiled."
    ::= { alaDaUNPCustDomainMacRangeRuleEntry 12 }

alaDaUNPCustDomainMacRangeRuleProfile3  OBJECT-TYPE
    SYNTAX  SnmpAdminString ( SIZE( 0 .. 32 ) )
    MAX-ACCESS  read-create
    STATUS  current
    DESCRIPTION
        "The profile name to be appiled."
    ::= { alaDaUNPCustDomainMacRangeRuleEntry 13 }

------------------------------------------------------------
-- SAA Profile Table configuration MIB --
------------------------------------------------------------

    alaDaSaaProfileTable OBJECT-TYPE
        SYNTAX        SEQUENCE OF AlaDaSaaProfileEntry
        MAX-ACCESS    not-accessible
        STATUS        current
        DESCRIPTION
            "This table stores the SAA Performance Monitoring profiles
             that holds the Latency and Jitter Threshold of a network connection."
        ::= { alaIND1DaMIBObjects 18 }

    alaDaSaaProfileEntry OBJECT-TYPE
        SYNTAX        AlaDaSaaProfileEntry
        MAX-ACCESS    not-accessible
        STATUS        current
        DESCRIPTION
            "Service Classification Profile entry"
        INDEX {alaDaSaaProfileName}
        ::= { alaDaSaaProfileTable 1 }

    AlaDaSaaProfileEntry ::= SEQUENCE
        {
            alaDaSaaProfileName              SnmpAdminString,
            alaDaSaaProfileLatencyThreshold  Integer32,
            alaDaSaaProfileJitterThreshold   Integer32,
            alaDaSaaProfileRowStatus         RowStatus
        }

    alaDaSaaProfileName OBJECT-TYPE

        SYNTAX        SnmpAdminString ( SIZE( 1 .. 32 ) )
        MAX-ACCESS    not-accessible
        STATUS        current
        DESCRIPTION
            "The name of this profile."
        ::= { alaDaSaaProfileEntry 1 }

    alaDaSaaProfileLatencyThreshold OBJECT-TYPE
        SYNTAX        Integer32 (0..1000000)
        MAX-ACCESS    read-create
        STATUS        current
        DESCRIPTION
            "The object holds the Latency Threshold. A value of zero (0) means no threshold"
	DEFVAL { 0 }
        ::= { alaDaSaaProfileEntry 4}

    alaDaSaaProfileJitterThreshold OBJECT-TYPE
        SYNTAX        Integer32 (0..1000000)
        MAX-ACCESS    read-create
        STATUS        current
        DESCRIPTION
            "The object holds the Jitter Threshold. A value of zero (0) means no threshold"
	DEFVAL { 0 }
        ::= { alaDaSaaProfileEntry 5}

    alaDaSaaProfileRowStatus OBJECT-TYPE
        SYNTAX        RowStatus
        MAX-ACCESS    read-create
        STATUS        current
        DESCRIPTION
            "The row status of this table entry."
        ::= { alaDaSaaProfileEntry 6}

------------------------------------------------------------
-- Captive Portal related Config  --
------------------------------------------------------------

    alaDaCPortalMIBObjects    OBJECT IDENTIFIER ::= { alaIND1DaMIBObjects 19 }

    alaDaCPortalGlobalConfig   OBJECT IDENTIFIER ::= { alaDaCPortalMIBObjects 1 }

    alaDaCPortalRedirectUrlName OBJECT-TYPE
        SYNTAX        SnmpAdminString ( SIZE( 0.. 32 ) )
        MAX-ACCESS    read-write
        STATUS        current
        DESCRIPTION
  			"Name of the rediret URL that is used for
			accessing a public certificate."
          DEFVAL { "captive-portal" }
                ::= { alaDaCPortalGlobalConfig 1 }


    alaDaCPortalIpAddressType OBJECT-TYPE
        SYNTAX        InetAddressType
			{
		  	 	ipv4(1),
				ipv6(2)
			}
        MAX-ACCESS    read-write
        STATUS        current
        DESCRIPTION
            "Address type of address associated with captive portal."
      DEFVAL { ipv4 }
        ::= { alaDaCPortalGlobalConfig  2 }

    alaDaCPortalIpAddress	OBJECT-TYPE
        SYNTAX 		  InetAddress (SIZE(4|16))
        MAX-ACCESS 	  read-write
        STATUS 		  current
        DESCRIPTION
            "The factory default Captive Portal IP address is 10.123.0.1.
             If the 10.123.0.0 subnet is already in use, user can change
             the Captive Portal IP address to another 10.x.0.0 subnet.
            Only the second octet of the Captive Portal IP address can
            be changed."
        ::= { alaDaCPortalGlobalConfig 3 }

        alaDaCPortalMode OBJECT-TYPE
        SYNTAX      INTEGER
                    {
                       internal(1),
                       external(2)
                     }
        MAX-ACCESS  read-write
        STATUS      current
        DESCRIPTION
            "Captive Portal Mode"
        DEFVAL { internal }
        ::= { alaDaCPortalGlobalConfig 4 }

    alaDaCPortalSuccRedirectUrl  OBJECT-TYPE
        SYNTAX      SnmpAdminString (SIZE (0..63))
        MAX-ACCESS  read-write
        STATUS      current
        DESCRIPTION
            "Captive Portal's Redirect Url upon successful authentication."
    ::= { alaDaCPortalGlobalConfig  5 }

    alaDaCPortalProxyPort  OBJECT-TYPE
        SYNTAX      Integer32  (0|1024..49151 )
        MAX-ACCESS  read-write
        STATUS      current
        DESCRIPTION
            "Captive Portal's user defined proxy port number."
        ::= { alaDaCPortalGlobalConfig 6 }

    alaDaCPortalRetryCnt OBJECT-TYPE
        SYNTAX      Integer32 (1..99)
        MAX-ACCESS  read-write
        STATUS      current
        DESCRIPTION
            "Number of retries for the Captive Portal user to provide the user
             credential before the software will classify the user to the failed
             policy according the the alaCaptivePortalPolicy."
  	DEFVAL { 3 }
        ::= { alaDaCPortalGlobalConfig 7 }

    alaDaCPortalPolicyListName OBJECT-TYPE
        SYNTAX      SnmpAdminString (SIZE (0..32))
        MAX-ACCESS  read-write
        STATUS      current
        DESCRIPTION
        "Captive Portal Global Policy List Name"
    ::= { alaDaCPortalGlobalConfig 8 }

    alaDaCPortalCustomization OBJECT-TYPE

        SYNTAX      INTEGER
                    {
			enable  (1),
			disable (2)
                     }
        MAX-ACCESS  read-write
        STATUS      current
        DESCRIPTION
            "Captive Portal Customization"
        DEFVAL { disable }
        ::= { alaDaCPortalGlobalConfig 9 }

    alaDaCPortalUNPProfile OBJECT-TYPE
        SYNTAX      SnmpAdminString (SIZE (0..32))
        MAX-ACCESS  read-write
        STATUS      current
        DESCRIPTION
        "Captive Portal Global UNP Profile Name"
    ::= { alaDaCPortalGlobalConfig 10 }

    alaDaCPortalUNPProfileChange OBJECT-TYPE
        SYNTAX      INTEGER { enable(1), disable(2) }
        MAX-ACCESS  read-write
        STATUS      current
        DESCRIPTION
        "Captive Portal Global UNP Profile Status"
    ::= { alaDaCPortalGlobalConfig 11 }

    alaDaCPortalAuthPassTable  OBJECT-TYPE
        SYNTAX      SEQUENCE OF AlaDaCPortalAuthPassEntry
        MAX-ACCESS  not-accessible
        STATUS      current
        DESCRIPTION
        "Current Rate Limit Table On 8021x Port"
        ::= { alaDaCPortalMIBObjects 2  }

   alaDaCPortalAuthPassEntry OBJECT-TYPE
        SYNTAX       AlaDaCPortalAuthPassEntry
        MAX-ACCESS   not-accessible
        STATUS       current
        DESCRIPTION
       "Captive Portal Auth Pass Enty"
        INDEX   { alaDaCPortalAuthDomainName }
        ::= { alaDaCPortalAuthPassTable 1 }

  AlaDaCPortalAuthPassEntry ::=
     SEQUENCE {
                alaDaCPortalAuthDomainName        SnmpAdminString,
                alaDaCPortalAuthRealm             INTEGER,
                alaDaCPortalAuthPolicyListName    SnmpAdminString,
                alaDaCPortalAuthRowStatus         RowStatus,
		alaDaCPortalAuthUNPProfile	  SnmpAdminString,
		alaDaCPortalAuthUNPProfileChange  INTEGER
              }

    alaDaCPortalAuthDomainName OBJECT-TYPE
        SYNTAX        SnmpAdminString(SIZE (1..32))
        MAX-ACCESS    not-accessible
        STATUS        current
        DESCRIPTION
        "Captive Portal Authenticated Pass Domain Name."
        ::= { alaDaCPortalAuthPassEntry 1 }

    alaDaCPortalAuthRealm OBJECT-TYPE
        SYNTAX        INTEGER {
                                 prefix(1),
                                 suffix(2)
                               }
        MAX-ACCESS    read-create
        STATUS        current
        DESCRIPTION
        "Captive Portal Authenticated Pass Realm"
	DEFVAL { prefix }
        ::= { alaDaCPortalAuthPassEntry 2 }

    alaDaCPortalAuthPolicyListName OBJECT-TYPE
        SYNTAX        SnmpAdminString(SIZE (1..32))
        MAX-ACCESS    read-create
        STATUS        current
        DESCRIPTION
        "Captive Portal Authenticated Policy List Name."
        ::= { alaDaCPortalAuthPassEntry 3 }

    alaDaCPortalAuthRowStatus OBJECT-TYPE
        SYNTAX        RowStatus
        MAX-ACCESS    read-create
        STATUS        current
        DESCRIPTION
        "This object allows entries to be created and deleted in the table"
        ::= { alaDaCPortalAuthPassEntry 4 }

    alaDaCPortalAuthUNPProfile OBJECT-TYPE
        SYNTAX        SnmpAdminString(SIZE (0..32))
        MAX-ACCESS    read-create
        STATUS        current
        DESCRIPTION
        "Captive Portal Authenticated UNP Profile Name."
        ::= { alaDaCPortalAuthPassEntry 5 }

    alaDaCPortalAuthUNPProfileChange OBJECT-TYPE
        SYNTAX      INTEGER { enable(1), disable(2) }
        MAX-ACCESS  read-create
        STATUS      current
        DESCRIPTION
        "Captive Portal Global UNP Profile Status"
        ::= { alaDaCPortalAuthPassEntry 6 }

        alaDaCPortalProfTable OBJECT-TYPE
        SYNTAX        SEQUENCE OF AlaDaCPortalProfEntry
        MAX-ACCESS    not-accessible
        STATUS        current
        DESCRIPTION
        "Table contain Captive Portal profiles "
        ::=  {   alaDaCPortalMIBObjects 3 }

        alaDaCPortalProfEntry  OBJECT-TYPE
        SYNTAX        AlaDaCPortalProfEntry
        MAX-ACCESS    not-accessible
        STATUS        current
        DESCRIPTION
        "Each entry defines Captive portal  profile "
        INDEX { alaDaCPortalProfName }
        ::= { alaDaCPortalProfTable   1 }

        AlaDaCPortalProfEntry ::= SEQUENCE
        {
            alaDaCPortalProfName                   SnmpAdminString,
            alaDaCPortalProfMode                   INTEGER,
            alaDaCPortalProfSuccRedirectUrl        SnmpAdminString,
            alaDaCPortalProfRetryCnt               Integer32,
            alaDaCPortalProfAuthPolicyListName     SnmpAdminString,
            alaDaCPortalProfAaaProf                SnmpAdminString,
            alaDaCPortalProfRowStatus              RowStatus,
	    alaDaCPortalProfUNPProfile		   SnmpAdminString,
	    alaDaCPortalProfUNPProfileChange 	   INTEGER
        }

    alaDaCPortalProfName	OBJECT-TYPE
        SYNTAX        SnmpAdminString ( SIZE( 1 .. 32 ) )
        MAX-ACCESS    not-accessible
        STATUS        current
        DESCRIPTION
  			"Captive Portal Profile  name ."
                ::= { alaDaCPortalProfEntry   1 }

   alaDaCPortalProfMode OBJECT-TYPE
        SYNTAX        INTEGER
                      {
                         internal(1),
                         external(2)
                      }
        MAX-ACCESS   read-create
        STATUS       current
        DESCRIPTION
            "Captive Portal Profile Mode"
        DEFVAL { internal }
        ::= { alaDaCPortalProfEntry 2 }

    alaDaCPortalProfSuccRedirectUrl  OBJECT-TYPE
        SYNTAX      SnmpAdminString (SIZE (0..63))
        MAX-ACCESS  read-create
        STATUS      current
        DESCRIPTION
            "Captive Portal's Redirect Url upon successful authentication."
    ::= { alaDaCPortalProfEntry 3 }

    alaDaCPortalProfRetryCnt OBJECT-TYPE
        SYNTAX      Integer32 (1..99)
        MAX-ACCESS  read-create
        STATUS      current
        DESCRIPTION
            "Number of retries for the Captive Portal Profile  to provide the user
             credential before the software will classify the user to the failed
             policy according the the alaCaptivePortalPolicy."
 	    DEFVAL { 3 }
        ::= { alaDaCPortalProfEntry  4 }

    alaDaCPortalProfAuthPolicyListName    OBJECT-TYPE
        SYNTAX      SnmpAdminString(SIZE (0..32))
        MAX-ACCESS  read-create
        STATUS      current
        DESCRIPTION
        "Captive Portal Profile Authenticated Pass Policy List Name"
        ::= { alaDaCPortalProfEntry 5 }

    alaDaCPortalProfAaaProf OBJECT-TYPE
        SYNTAX      SnmpAdminString(SIZE (0..32))
        MAX-ACCESS  read-create
        STATUS      current
        DESCRIPTION
        "Captive Portal Profile associated with AAA profile"
        ::= { alaDaCPortalProfEntry 6 }

    alaDaCPortalProfRowStatus OBJECT-TYPE
        SYNTAX      RowStatus
        MAX-ACCESS  read-create
        STATUS      current
        DESCRIPTION
            "Row Status for initiating a MIB retrieval request."
        ::= { alaDaCPortalProfEntry 7 }

    alaDaCPortalProfUNPProfile OBJECT-TYPE
        SYNTAX      SnmpAdminString(SIZE (0..32))
        MAX-ACCESS  read-create
        STATUS      current
        DESCRIPTION
        "UNP Profile associated with Captive Portal Profile"
        ::= { alaDaCPortalProfEntry 8 }

    alaDaCPortalProfUNPProfileChange OBJECT-TYPE
        SYNTAX      INTEGER { enable(1), disable(2)}
        MAX-ACCESS  read-create
        STATUS      current
        DESCRIPTION
        "UNP Profile Status associated with Captive Portal Profile"
        ::= { alaDaCPortalProfEntry 9 }
------------------------------------------------------------
-- Captive Portal Profile Domain Table--
------------------------------------------------------------

   alaDaCPortalProfDomainTable OBJECT-TYPE
	SYNTAX        SEQUENCE OF AlaDaCPortalProfDomainEntry
	MAX-ACCESS    not-accessible
	STATUS        current
	DESCRIPTION
	"Table contain Captive Portal profiles domain specific policy list."
	::=  {   alaDaCPortalMIBObjects 4 }

	alaDaCPortalProfDomainEntry  OBJECT-TYPE
	SYNTAX        AlaDaCPortalProfDomainEntry
	MAX-ACCESS    not-accessible
	STATUS        current
	DESCRIPTION
	"Each entry defines Captive portal  profiles domain specific policy paramaters."
	INDEX { alaDaCPortalProfName , alaDaCPortalProfDomainAuthDomainName }
	::= { alaDaCPortalProfDomainTable   1 }

	AlaDaCPortalProfDomainEntry ::= SEQUENCE
        {
	     alaDaCPortalProfDomainAuthDomainName         SnmpAdminString,
	     alaDaCPortalProfDomainAuthPolicyListName     SnmpAdminString,
             alaDaCPortalProfDomainAuthRealm              INTEGER,
	     alaDaCPortalProfDomainRowStatus              RowStatus,
	     alaDaCPortalProfDomainUNPProfile		  SnmpAdminString,
	     alaDaCPortalProfDomainUNPProfileChange      INTEGER
        }

    alaDaCPortalProfDomainAuthDomainName    OBJECT-TYPE
        SYNTAX        SnmpAdminString(SIZE (1..32))
        MAX-ACCESS    not-accessible
        STATUS        current
        DESCRIPTION
        "Captive Portal Profile Authenticated Domain Name"
        ::= { alaDaCPortalProfDomainEntry 1 }

    alaDaCPortalProfDomainAuthPolicyListName    OBJECT-TYPE
        SYNTAX        SnmpAdminString(SIZE (1..32))
        MAX-ACCESS    read-create
        STATUS        current
        DESCRIPTION
        "Captive Portal Profile Authenticated Pass Policy List Name"
        ::= { alaDaCPortalProfDomainEntry 2 }

    alaDaCPortalProfDomainAuthRealm OBJECT-TYPE
        SYNTAX        INTEGER {
                                 prefix(1),
                                 suffix(2)
                               }
        MAX-ACCESS    read-create
        STATUS        current
        DESCRIPTION
        "Captive Portal Profile Authenticated Pass Realm"
	DEFVAL { prefix }
        ::= { alaDaCPortalProfDomainEntry 3 }

    alaDaCPortalProfDomainRowStatus OBJECT-TYPE
        SYNTAX        RowStatus
        MAX-ACCESS    read-create
        STATUS        current
        DESCRIPTION
        "This object allows entries to be created and deleted in the table"
        ::= { alaDaCPortalProfDomainEntry 4 }

    alaDaCPortalProfDomainUNPProfile OBJECT-TYPE
        SYNTAX        SnmpAdminString(SIZE (0..32))
        MAX-ACCESS    read-create
        STATUS        current
        DESCRIPTION
        "Captive Portal Profile Authenticated UNP Profile."
        ::= { alaDaCPortalProfDomainEntry 5 }

    alaDaCPortalProfDomainUNPProfileChange OBJECT-TYPE
        SYNTAX        INTEGER {
                                 enable(1),
                                 disable(2)
                               }
        MAX-ACCESS    read-create
        STATUS        current
        DESCRIPTION
        "Captive Portal Profile Authenticated UNP Profile Status."
	DEFVAL { enable }
        ::= { alaDaCPortalProfDomainEntry 6 }
------------------------------------------------------------
-- HIC related Config  --
------------------------------------------------------------

    alaDaHICMIBObjects    OBJECT IDENTIFIER ::= { alaIND1DaMIBObjects 20 }

    alaDaHICGlobalConfig   OBJECT IDENTIFIER ::= { alaDaHICMIBObjects 1 }

    alaDaHICStatus OBJECT-TYPE
        SYNTAX        INTEGER {enable(1), disable(2)}
        MAX-ACCESS    read-write
        STATUS        current
        DESCRIPTION
        "HIC Status. The HIC server has to be configured before HIC
        can be enabled."
        DEFVAL { disable }
        ::= { alaDaHICGlobalConfig 1 }

    alaDaHICWebAgentDownloadUrl OBJECT-TYPE
        SYNTAX        SnmpAdminString ( SIZE( 0 .. 127 ) )
        MAX-ACCESS    read-write
        STATUS        current
        DESCRIPTION
        "The URL for web agent download."
        ::= { alaDaHICGlobalConfig 2 }

    alaDaHICCustomHttpProxyPort OBJECT-TYPE
        SYNTAX        Integer32( 1025 .. 65535 )
        MAX-ACCESS    read-write
        STATUS        current
        DESCRIPTION
        "The custom HTTP port for QoS to intercept the host's initial HTTP request."
        DEFVAL { 8080 }
        ::= { alaDaHICGlobalConfig 3 }

    alaDaHICBgPollInterval OBJECT-TYPE
        SYNTAX        Integer32(
                                    16 | 32 | 48 | 64 |
                                    80 | 96 | 112 | 128 | 144 |
                                    160 | 176 | 192 | 208 | 224 | 240 | 256
                                 )
        UNITS         "seconds"
        MAX-ACCESS    read-write
        STATUS        current
        DESCRIPTION
        "Background-poll-interval provides time frequency in seconds for background polling packets."
        DEFVAL { 16 }
        ::= { alaDaHICGlobalConfig 4 }

    alaDaHICSvrFailMode OBJECT-TYPE
        SYNTAX         INTEGER {
                                    hold(1),
                                    passthrough(2)
                                }
        MAX-ACCESS    read-write
        STATUS        current
        DESCRIPTION
        "The server-failure-mode specifies the policy to be followed
         in case both the servers are not reachable,
         value can be either passthrough or hold"
        DEFVAL { hold }
        ::= { alaDaHICGlobalConfig 5 }


--  HIC Server Table MIB --

    alaDaHICSvrTable OBJECT-TYPE
        SYNTAX        SEQUENCE OF AlaDaHICSvrEntry
        MAX-ACCESS    not-accessible
        STATUS        current
        DESCRIPTION
        "This table shows current configuration for each HIC server."
        ::= { alaDaHICMIBObjects 2 }

    alaDaHICSvrEntry OBJECT-TYPE
        SYNTAX        AlaDaHICSvrEntry
        MAX-ACCESS    not-accessible
        STATUS        current
        DESCRIPTION
        "A HIC server configuration."
        INDEX     { alaDaHICSvrName }
        ::= { alaDaHICSvrTable 1 }

    AlaDaHICSvrEntry ::= SEQUENCE
        {
            alaDaHICSvrName          SnmpAdminString,
            alaDaHICSvrIpAddrType    InetAddressType,
            alaDaHICSvrIpAddr        InetAddress,
            alaDaHICSvrPort          Integer32,
            alaDaHICSvrKey           SnmpAdminString,
	        alaDaHICSvrStatus	       INTEGER,
            alaDaHICSvrRole          INTEGER,
            alaDaHICSvrConnection    INTEGER,
            alaDaHICSvrRowStatus     RowStatus
        }

    alaDaHICSvrName OBJECT-TYPE
        SYNTAX        SnmpAdminString ( SIZE( 1 .. 31 ) )
        MAX-ACCESS    not-accessible
        STATUS        current
        DESCRIPTION
        "Name of the server.
        This name is given by the operator to refer the server."
        ::= { alaDaHICSvrEntry 1 }

    alaDaHICSvrIpAddrType OBJECT-TYPE
        SYNTAX         InetAddressType
        {
            ipv4(1),
            ipv6(2)
        }
        MAX-ACCESS    read-create
        STATUS        current
        DESCRIPTION
        "IP address of the server host."
        ::= { alaDaHICSvrEntry 2 }

    alaDaHICSvrIpAddr OBJECT-TYPE
        SYNTAX        InetAddress(SIZE(4|16))
        MAX-ACCESS    read-create
        STATUS        current
        DESCRIPTION
        "IP address of the server host."
        ::= { alaDaHICSvrEntry 3 }

    alaDaHICSvrPort OBJECT-TYPE
        SYNTAX        Integer32 ( 1025 .. 65535 )
        MAX-ACCESS    read-create
        STATUS        current
        DESCRIPTION
        "For HIC server only. Port number for HIC request"
        DEFVAL        { 11707 }
        ::= { alaDaHICSvrEntry 4 }

    alaDaHICSvrKey OBJECT-TYPE
        SYNTAX        SnmpAdminString ( SIZE( 1 .. 31 ) )
        MAX-ACCESS    read-create
        STATUS        current
        DESCRIPTION
        "The shared secret is a string of characters known to the switch
        and to the HIC server. It is used to compute the digest to
        preserve the integrity between the HIC server and the AoS Switch.
        The secret is stored encrypted using a two way algorithm."
        ::= { alaDaHICSvrEntry 5 }

    alaDaHICSvrStatus OBJECT-TYPE
        SYNTAX        INTEGER {down(1), up(2)}
        MAX-ACCESS    read-only
        STATUS        current
        DESCRIPTION
        "HIC server status."
        DEFVAL { down }
        ::= { alaDaHICSvrEntry 6 }

    alaDaHICSvrRole OBJECT-TYPE
        SYNTAX        INTEGER
                      {
                          primary(1),
                          backup(2)
                      }
        MAX-ACCESS    read-only
        STATUS        current
        DESCRIPTION
        "Role of the server either primary or backup"
        DEFVAL { primary }
        ::= { alaDaHICSvrEntry 7 }

    alaDaHICSvrConnection OBJECT-TYPE
        SYNTAX      INTEGER
                    {
                        active(1),
                        inactive(2)
                    }
        MAX-ACCESS    read-only
        STATUS        current
        DESCRIPTION
        "The server connection specifies the current mode of the server either active or inactive."
        DEFVAL { inactive }
        ::= { alaDaHICSvrEntry 8 }

    alaDaHICSvrRowStatus OBJECT-TYPE
        SYNTAX        RowStatus
        MAX-ACCESS    read-create
        STATUS        current
        DESCRIPTION
        "The status of this table entry."
        ::= { alaDaHICSvrEntry 9 }


    --  HIC Allowed/Exception IP Table MIB --

    alaDaHICAllowedTable OBJECT-TYPE
        SYNTAX        SEQUENCE OF AlaDaHICAllowedEntry
        MAX-ACCESS    not-accessible
        STATUS        current
        DESCRIPTION
        "This table contains the list of allowed/exception IP Addresses the
        the HIC hosts allowed to access during HIC. Those are the IP addresses
        of the Remediation/Patch servers, and the Web Agent Download server."
        ::= { alaDaHICMIBObjects 3 }

    alaDaHICAllowedEntry OBJECT-TYPE
        SYNTAX        AlaDaHICAllowedEntry
        MAX-ACCESS    not-accessible
        STATUS        current
        DESCRIPTION
        "A Remediation server configuration."
        INDEX     { alaDaHICAllowedName }
        ::= { alaDaHICAllowedTable 1 }

    AlaDaHICAllowedEntry ::= SEQUENCE
        {
            alaDaHICAllowedName           SnmpAdminString,
            alaDaHICAllowedIpAddrType     InetAddressType,
            alaDaHICAllowedIpAddr         InetAddress,
            alaDaHICAllowedIpMaskType     InetAddressType,
            alaDaHICAllowedIpMask         InetAddress,
            alaDaHICAllowedRowStatus      RowStatus
        }

    alaDaHICAllowedName OBJECT-TYPE
        SYNTAX        SnmpAdminString ( SIZE( 1 .. 31 ) )
        MAX-ACCESS    not-accessible
        STATUS        current
        DESCRIPTION
        "Name of the server.
        This name is given by the operator to refer the server."
        ::= { alaDaHICAllowedEntry 1}

    alaDaHICAllowedIpAddrType OBJECT-TYPE
        SYNTAX        InetAddressType
                      {
                           ipv4(1),
                           ipv6(2)
                       }
        MAX-ACCESS    read-create
        STATUS        current
        DESCRIPTION
            "IP address of the allowed entry."
         ::= { alaDaHICAllowedEntry 2 }

    alaDaHICAllowedIpAddr OBJECT-TYPE
        SYNTAX        InetAddress(SIZE(4|16))
        MAX-ACCESS    read-create
        STATUS        current
        DESCRIPTION
        "IP address of the allowed entry."
        ::= { alaDaHICAllowedEntry 3 }

    alaDaHICAllowedIpMaskType OBJECT-TYPE
        SYNTAX        InetAddressType
                      {
                           ipv4(1),
                           ipv6(2)
                       }
        MAX-ACCESS    read-create
        STATUS        current
        DESCRIPTION
            "IP mask type of the allowed entry."
         ::= { alaDaHICAllowedEntry 4 }

    alaDaHICAllowedIpMask OBJECT-TYPE
        SYNTAX        InetAddress(SIZE(4|16))
        MAX-ACCESS    read-create
        STATUS        current
        DESCRIPTION
        "IP Mask of the allowed entry."
        DEFVAL      { 'FFFFFFFF'H }
        ::= { alaDaHICAllowedEntry 5 }

    alaDaHICAllowedRowStatus OBJECT-TYPE
        SYNTAX        RowStatus
        MAX-ACCESS    read-create
        STATUS        current
        DESCRIPTION
        "The status of this table entry."
        ::= { alaDaHICAllowedEntry 6 }

    alaDaHICSvrFailPolicyTable OBJECT-TYPE
        SYNTAX        SEQUENCE OF AlaDaHICSvrFailPolicyEntry
        MAX-ACCESS    not-accessible
        STATUS        current
        DESCRIPTION
        "This table shows current configuration for HIC server Fail Policy list mapping."
        ::= { alaDaHICMIBObjects 4 }

    alaDaHICSvrFailPolicyEntry OBJECT-TYPE
        SYNTAX        AlaDaHICSvrFailPolicyEntry
        MAX-ACCESS    not-accessible
        STATUS        current
        DESCRIPTION
        "A HIC server Fail UNP configuration."
        INDEX     { alaDaHICSvrFailPolicyName }
        ::= { alaDaHICSvrFailPolicyTable 1 }

    AlaDaHICSvrFailPolicyEntry ::= SEQUENCE
        {
            alaDaHICSvrFailPolicyName         SnmpAdminString,
            alaDaHICSvrFailChangedPolicyName  SnmpAdminString,
            alaDaHICSvrFailRowStatus          RowStatus
        }

    alaDaHICSvrFailPolicyName OBJECT-TYPE
        SYNTAX  SnmpAdminString ( SIZE( 1 .. 32 ) )
        MAX-ACCESS  not-accessible
        STATUS  current
        DESCRIPTION
        "The profile name which needs to be modified when the HIC server is down."
        ::= { alaDaHICSvrFailPolicyEntry 1 }

    alaDaHICSvrFailChangedPolicyName OBJECT-TYPE
        SYNTAX  SnmpAdminString ( SIZE( 1 .. 32 ) )
        MAX-ACCESS  read-create
        STATUS  current
        DESCRIPTION
        "The profile name to which the host needs to be moved when the HIC server is down."
        ::= { alaDaHICSvrFailPolicyEntry 2 }

    alaDaHICSvrFailRowStatus  OBJECT-TYPE
        SYNTAX  RowStatus
        MAX-ACCESS  read-create
        STATUS  current
        DESCRIPTION
        "Row Status for creating/deleting policy list  name ."
        ::= { alaDaHICSvrFailPolicyEntry 3 }


    --  HIC Host Table MIB --

    alaDaHICHostTable OBJECT-TYPE
        SYNTAX        SEQUENCE OF AlaDaHICHostEntry
        MAX-ACCESS    not-accessible
        STATUS        current
        DESCRIPTION
        "This table shows list of HIC Hosts and their active HIC status."
        ::= { alaDaHICMIBObjects 5 }

    alaDaHICHostEntry OBJECT-TYPE
        SYNTAX        AlaDaHICHostEntry
        MAX-ACCESS    not-accessible
        STATUS        current
        DESCRIPTION
        "HIC Host status information."
        INDEX     { alaDaHICHostMac }
        ::= { alaDaHICHostTable 1 }

    AlaDaHICHostEntry ::= SEQUENCE
    {
        alaDaHICHostMac               MacAddress,
        alaDaHICHostStatus            INTEGER
    }

    alaDaHICHostMac OBJECT-TYPE
        SYNTAX        MacAddress
        MAX-ACCESS    not-accessible
        STATUS        current
        DESCRIPTION
        "Static MAC address index to each override entry."
        ::= { alaDaHICHostEntry 1}

    alaDaHICHostStatus OBJECT-TYPE
        SYNTAX        INTEGER {inprogress(1),success(2),fail(3),timeout(4)}
        MAX-ACCESS    read-only
        STATUS        current
        DESCRIPTION
        "HIC status of each HIC Host."
        DEFVAL { fail }
        ::= { alaDaHICHostEntry 2}


--------------------------------------------------------
-- Unp Edge Template Table
-- This table is deprecated as part of unification
--------------------------------------------------------

alaDaUNPETmplTable OBJECT-TYPE
    SYNTAX      SEQUENCE OF AlaDaUNPETmplEntry
    MAX-ACCESS  not-accessible
    STATUS      deprecated
    DESCRIPTION
        "Unp Edge Template Table ."
    ::= { alaIND1DaMIBObjects 21 }

alaDaUNPETmplEntry OBJECT-TYPE
    SYNTAX      AlaDaUNPETmplEntry
    MAX-ACCESS  not-accessible
    STATUS      deprecated
    DESCRIPTION
        "EdgeTemplate Entries."
    INDEX { alaDaUNPETmplName}
    ::= { alaDaUNPETmplTable 1 }

AlaDaUNPETmplEntry ::= SEQUENCE {
    alaDaUNPETmplName                   SnmpAdminString,
    alaDaUNPETmpl8021XAuthStatus        INTEGER,
    alaDaUNPETmpl8021XTxPeriodStatus    INTEGER,
    alaDaUNPETmpl8021XTxPeriod          Integer32,
    alaDaUNPETmpl8021XSuppTimeoutStatus INTEGER,
    alaDaUNPETmpl8021XSuppTimeOut       Integer32,
    alaDaUNPETmpl8021XMaxReqStatus      INTEGER,
    alaDaUNPETmpl8021XMaxReq            Integer32,
    alaDaUNPETmpl8021XPassAltEProf      SnmpAdminString,
    alaDaUNPETmplMacAuthStatus          INTEGER,
    alaDaUNPETmplMacPassAltEProf        SnmpAdminString,
    alaDaUNPETmplClassifStatus          INTEGER,
    alaDaUNPETmplDefEProf               SnmpAdminString,
    alaDaUNPETmplGroupId                Integer32,
    alaDaUNPETmplAaaProf                SnmpAdminString,
    alaDaUNPETmplRowStatus              RowStatus,
    alaDaUNPETmplRedirectPortBounce     INTEGER,
    alaDaUNPETmplFailurePolicy          INTEGER,
    alaDaUNPETmplBypassStatus           INTEGER,
    alaDaUNPETmplMacAllowEap            INTEGER,
    alaDaUNPETmplAdminControlledDirections  INTEGER,
    alaDaUNPETmplTrustTagStatus         INTEGER,
    alaDaUNPETmplForceL3Learning         INTEGER,
    alaDaUNPETmplForceL3LearningPortBounce INTEGER
}

alaDaUNPETmplName OBJECT-TYPE
    SYNTAX    SnmpAdminString ( SIZE( 1 .. 32 ) )
    MAX-ACCESS not-accessible
    STATUS      deprecated
    DESCRIPTION
        "UNP Edge Template name."
    ::= { alaDaUNPETmplEntry 1 }

alaDaUNPETmpl8021XAuthStatus    OBJECT-TYPE
    SYNTAX      INTEGER {
                    enable  (1),
                    disable (2)
               }
    MAX-ACCESS  read-create
    STATUS      deprecated
    DESCRIPTION
        "Edge Template  802.1X Authenttication Status ."
    DEFVAL { disable }
    ::= { alaDaUNPETmplEntry 2 }

alaDaUNPETmpl8021XTxPeriodStatus OBJECT-TYPE
    SYNTAX      INTEGER {
                    enable  (1),
                    disable (2)
               }
    MAX-ACCESS  read-create
    STATUS      deprecated
    DESCRIPTION
        "Edge Template  802.1X Authentication
         tx-period configured or not."
    DEFVAL { disable }
    ::= { alaDaUNPETmplEntry 3 }

alaDaUNPETmpl8021XTxPeriod  OBJECT-TYPE
    SYNTAX      Integer32(1..60)
    UNITS           "seconds"
    MAX-ACCESS  read-create
    STATUS      deprecated
    DESCRIPTION
        "Edge Template 802.1X Tx period ."
        DEFVAL { 30 }
    ::= { alaDaUNPETmplEntry 4 }

alaDaUNPETmpl8021XSuppTimeoutStatus OBJECT-TYPE
    SYNTAX      INTEGER {
                    enable  (1),
                    disable (2)
               }
    MAX-ACCESS  read-create
    STATUS      deprecated
    DESCRIPTION
        "Edge Template  802.1X Authentication
         supp-timeout configured or not."
    DEFVAL { disable }
    ::= { alaDaUNPETmplEntry 5 }

alaDaUNPETmpl8021XSuppTimeOut       OBJECT-TYPE
    SYNTAX      Integer32(1..120)
    UNITS           "seconds"
    MAX-ACCESS  read-create
    STATUS      deprecated
    DESCRIPTION
        "Edge Template 802.1X Authenttication Supp Timeout ."
    DEFVAL { 30 }
    ::= { alaDaUNPETmplEntry 6 }

alaDaUNPETmpl8021XMaxReqStatus OBJECT-TYPE
    SYNTAX      INTEGER {
                    enable  (1),
                    disable (2)
               }
    MAX-ACCESS  read-create
    STATUS      deprecated
    DESCRIPTION
        "Edge Template  802.1X Authentication
         supp-timeout configured or not."
    DEFVAL { disable }
    ::= { alaDaUNPETmplEntry 7 }

alaDaUNPETmpl8021XMaxReq OBJECT-TYPE
    SYNTAX      Integer32(0..3)
    MAX-ACCESS  read-create
    STATUS      deprecated
    DESCRIPTION
        " Edge Template 802.1X Authenttication Max Req ."
    DEFVAL { 2 }
    ::= { alaDaUNPETmplEntry 8 }

alaDaUNPETmpl8021XPassAltEProf OBJECT-TYPE
    SYNTAX      SnmpAdminString ( SIZE( 0 .. 32 ) )
    MAX-ACCESS  read-create
    STATUS      deprecated
    DESCRIPTION
        " 802.1X Auth Pass Alternate Edge Profile name."
    ::= { alaDaUNPETmplEntry 9 }

alaDaUNPETmplMacAuthStatus OBJECT-TYPE
    SYNTAX      INTEGER {
                    enable  (1),
                    disable (2)
               }
    MAX-ACCESS  read-create
    STATUS      deprecated
    DESCRIPTION
        "Edge Template  Mac Authenttication Status ."
    DEFVAL { disable }
    ::= { alaDaUNPETmplEntry 10 }

alaDaUNPETmplMacPassAltEProf OBJECT-TYPE
    SYNTAX      SnmpAdminString ( SIZE( 0 .. 32 ) )
    MAX-ACCESS  read-create
    STATUS      deprecated
    DESCRIPTION
        " Mac Auth Pass Alternate Edge Profile name."
    ::= { alaDaUNPETmplEntry 11 }

alaDaUNPETmplClassifStatus OBJECT-TYPE
    SYNTAX      INTEGER {
                    enable  (1),
                    disable (2)
               }
    MAX-ACCESS  read-create
    STATUS      deprecated
    DESCRIPTION
        "Edge Template Classification Status ."
    DEFVAL { disable }
    ::= { alaDaUNPETmplEntry 12 }

alaDaUNPETmplDefEProf OBJECT-TYPE
    SYNTAX      SnmpAdminString ( SIZE( 0 .. 32 ) )
    MAX-ACCESS  read-create
    STATUS      deprecated
    DESCRIPTION
        " Edge Template default Profile ."
    ::= { alaDaUNPETmplEntry 13 }

alaDaUNPETmplGroupId OBJECT-TYPE
    SYNTAX      Integer32(0..255)
    MAX-ACCESS  read-create
    STATUS      deprecated
    DESCRIPTION
        "Associated Group ID ."
    ::= { alaDaUNPETmplEntry 14 }

alaDaUNPETmplAaaProf  OBJECT-TYPE
    SYNTAX      SnmpAdminString ( SIZE( 0 .. 32 ) )
    MAX-ACCESS  read-create
    STATUS      deprecated
    DESCRIPTION
        "Associated Aaa Profile."
    ::= { alaDaUNPETmplEntry 15 }

alaDaUNPETmplRowStatus OBJECT-TYPE
    SYNTAX        RowStatus
    MAX-ACCESS    read-create
    STATUS        deprecated
    DESCRIPTION
        "The status of this table entry."
    ::= { alaDaUNPETmplEntry 16 }

 alaDaUNPETmplRedirectPortBounce OBJECT-TYPE
    SYNTAX      INTEGER {
                    enable  (1),
                    disable (2)
               }
    MAX-ACCESS  read-create
    STATUS      deprecated
    DESCRIPTION
        "Edge Template Classification Status ."
    DEFVAL { disable }
    ::= { alaDaUNPETmplEntry 17 }

alaDaUNPETmplFailurePolicy OBJECT-TYPE
    SYNTAX INTEGER {
               default (1),
               macAuth (2)
          }
    MAX-ACCESS read-create
    STATUS deprecated
    DESCRIPTION
        " Failure Policy type."
    ::= { alaDaUNPETmplEntry 18 }

alaDaUNPETmplBypassStatus   OBJECT-TYPE
    SYNTAX      INTEGER {
                    enable  (1),
                    disable (2)
               }
    MAX-ACCESS read-create
    STATUS deprecated
    DESCRIPTION
        " Flag to indicate Bypass enable status on port."
    ::= { alaDaUNPETmplEntry 19 }

alaDaUNPETmplMacAllowEap OBJECT-TYPE
    SYNTAX INTEGER {
               pass   (1),
               fail   (2),
               noauth (3),
               none   (4)
           }
    MAX-ACCESS read-create
    STATUS deprecated
    DESCRIPTION
        " Flag to indicate Allow Eap on port."
    ::= { alaDaUNPETmplEntry 20 }

alaDaUNPETmplAdminControlledDirections OBJECT-TYPE
    SYNTAX      INTEGER {
                    both    (1),
                    in      (2),
                    noVal   (3)
                }
    MAX-ACCESS  read-create
    STATUS      deprecated
    DESCRIPTION
         "The current value of the administrative controlled
         directions parameter for the Port."
    DEFVAL { both }
    ::= {alaDaUNPETmplEntry 21}

alaDaUNPETmplTrustTagStatus OBJECT-TYPE
    SYNTAX      INTEGER {
                    enable  (1),
                    disable (2)
               }
    MAX-ACCESS  read-create
    STATUS      deprecated
    DESCRIPTION
        "The flag to indicate whether the vlan tag in the incoming packet
         could be used for classifying the user when MAC authentication fails
         and classification rules dont match."
    ::= { alaDaUNPETmplEntry 22 }

alaDaUNPETmplForceL3Learning  OBJECT-TYPE
    SYNTAX     INTEGER {
        enable (1),
        disable (2)
    }
    MAX-ACCESS  read-create
    STATUS      current
    DESCRIPTION
              "UNP force L3 learning status on the Edge-Template."
    ::= { alaDaUNPETmplEntry 23 }

alaDaUNPETmplForceL3LearningPortBounce OBJECT-TYPE
    SYNTAX     INTEGER {
        enable (1),
        disable (2)
    }
    MAX-ACCESS  read-create
    STATUS      current
    DESCRIPTION
              "Port-Bounce associated with UNP force L3 learning status on the Edge-Template."
    ::= { alaDaUNPETmplEntry 24 }

--------------------------------------------------------
-- Edge Profile Table
-- This table is deprecated as part of unification
--------------------------------------------------------

alaDaUNPEdgeProfTable OBJECT-TYPE
    SYNTAX      SEQUENCE OF AlaDaUNPEdgeProfEntry
    MAX-ACCESS  not-accessible
    STATUS      deprecated
    DESCRIPTION
        "Unp Edge Profile Table ."
    ::= { alaIND1DaMIBObjects 22 }

alaDaUNPEdgeProfEntry OBJECT-TYPE
    SYNTAX     AlaDaUNPEdgeProfEntry
    MAX-ACCESS  not-accessible
    STATUS      deprecated
    DESCRIPTION
        "Edge Profile Table Entries ."
    INDEX { alaDaUNPEdgeProfName}
    ::= { alaDaUNPEdgeProfTable 1 }

AlaDaUNPEdgeProfEntry ::= SEQUENCE  {
    alaDaUNPEdgeProfName               SnmpAdminString,
    alaDaUNPEdgeProfQosPolicyList      SnmpAdminString,
    alaDaUNPEdgeProfLocationPolicy     SnmpAdminString,
    alaDaUNPEdgeProfPeriodPolicy       SnmpAdminString,
    alaDaUNPEdgeProfHICStatus          INTEGER,
    alaDaUNPEdgeProfCPortalAuth        INTEGER,
    alaDaUNPEdgeProfAuthStatus         INTEGER,
    alaDaUNPEdgeProfMobileTag          INTEGER,
    alaDaUNPEdgeProfDHCPEnforcment     INTEGER,
    alaDaUNPEdgeProfCPortalProf        SnmpAdminString,
    alaDaUNPEdgeProfRowStatus          RowStatus,
    alaDaUNPEdgeProfRedirectStatus     INTEGER,
    alaDaUNPEdgeProfKerberosStatus     INTEGER,
    alaDaUNPEdgeProfMaxIngressBw       Integer32,
    alaDaUNPEdgeProfMaxEgressBw        Integer32,
    alaDaUNPEdgeProfMaxIngressDepth    Integer32,
    alaDaUNPEdgeProfMaxEgressDepth     Integer32
}

alaDaUNPEdgeProfName    OBJECT-TYPE
    SYNTAX    SnmpAdminString ( SIZE( 1 .. 32 ) )
    MAX-ACCESS not-accessible
    STATUS      deprecated
    DESCRIPTION
        "UNP Edge Profile name."
    ::= { alaDaUNPEdgeProfEntry   1 }

alaDaUNPEdgeProfQosPolicyList   OBJECT-TYPE
    SYNTAX    SnmpAdminString ( SIZE( 0 .. 32 ) )
    MAX-ACCESS read-create
    STATUS      deprecated
    DESCRIPTION
        "Associated Qos Policy List."
    ::= { alaDaUNPEdgeProfEntry   2 }

alaDaUNPEdgeProfLocationPolicy OBJECT-TYPE
    SYNTAX    SnmpAdminString ( SIZE( 0 .. 32 ) )
    MAX-ACCESS read-create
    STATUS      deprecated
    DESCRIPTION
        "Associated Edge Profile Location Policy Name ."
    ::= { alaDaUNPEdgeProfEntry  3  }

alaDaUNPEdgeProfPeriodPolicy OBJECT-TYPE
    SYNTAX    SnmpAdminString ( SIZE( 0 .. 32 ) )
    MAX-ACCESS read-create
    STATUS      deprecated
    DESCRIPTION
        "Associated Edge Profile Period  Policy Name ."
    ::= { alaDaUNPEdgeProfEntry  4  }

alaDaUNPEdgeProfHICStatus   OBJECT-TYPE
    SYNTAX      INTEGER {
                    enable  (1),
                    disable (2)
                }
    MAX-ACCESS  read-create
    STATUS      deprecated
    DESCRIPTION
        "Edge Profile HIC Status ."
    DEFVAL { disable }
    ::= { alaDaUNPEdgeProfEntry 5 }

alaDaUNPEdgeProfCPortalAuth OBJECT-TYPE
    SYNTAX      INTEGER {
                    enable  (1),
                    disable (2)
                }
    MAX-ACCESS  read-create
    STATUS      deprecated
    DESCRIPTION
        "Edge Profile Captive Portal Authentication Status."
    DEFVAL { disable }
    ::= { alaDaUNPEdgeProfEntry 6 }

alaDaUNPEdgeProfAuthStatus OBJECT-TYPE
    SYNTAX      INTEGER {
                    enable  (1),
                    disable (2)
                }
    MAX-ACCESS  read-create
    STATUS      deprecated
    DESCRIPTION
        "Edge Profile Authentication Status ."
    DEFVAL { disable }
    ::= { alaDaUNPEdgeProfEntry 7 }

alaDaUNPEdgeProfMobileTag   OBJECT-TYPE
    SYNTAX INTEGER {
               enable  (1),
               disable (2)
           }
    MAX-ACCESS  read-create
    STATUS      deprecated
    DESCRIPTION
        "Edge Profile Mobile Tag ."
    DEFVAL { disable }
    ::= { alaDaUNPEdgeProfEntry 8 }

alaDaUNPEdgeProfDHCPEnforcment OBJECT-TYPE
    SYNTAX INTEGER {
               enable  (1),
               disable (2)
           }
    MAX-ACCESS  read-create
    STATUS      deprecated
    DESCRIPTION
        "Edge Profile Dhcp Enforcement ."
    DEFVAL { disable }
    ::= { alaDaUNPEdgeProfEntry 9 }

alaDaUNPEdgeProfCPortalProf OBJECT-TYPE
    SYNTAX    SnmpAdminString ( SIZE( 0 .. 32 ) )
    MAX-ACCESS read-create
    STATUS      deprecated
    DESCRIPTION
        "Associated Captive Portal Profile ."
    ::= { alaDaUNPEdgeProfEntry  10  }

alaDaUNPEdgeProfRowStatus OBJECT-TYPE
    SYNTAX        RowStatus
    MAX-ACCESS    read-create
    STATUS        deprecated
    DESCRIPTION
        "The status of this table entry."
    ::= { alaDaUNPEdgeProfEntry 11 }

alaDaUNPEdgeProfRedirectStatus OBJECT-TYPE
    SYNTAX INTEGER {
               enable  (1),
               disable (2)
           }
    MAX-ACCESS  read-create
    STATUS      deprecated
    DESCRIPTION
        "Edge Profile Port bounce Status ."
    DEFVAL { disable }
    ::= { alaDaUNPEdgeProfEntry 12 }

alaDaUNPEdgeProfKerberosStatus OBJECT-TYPE
    SYNTAX INTEGER {
               enable  (1),
               disable (2)
           }
    MAX-ACCESS  read-create
    STATUS      deprecated
    DESCRIPTION
        "Edge Profile Kerberos Status ."
    DEFVAL { disable }
    ::= { alaDaUNPEdgeProfEntry 13 }

alaDaUNPEdgeProfMaxIngressBw OBJECT-TYPE
    SYNTAX      Integer32 (-1|0..2147483647)
    UNITS       "kilobits per second"
    MAX-ACCESS  read-create
    STATUS      deprecated
    DESCRIPTION
        "Maximum Ingress Bandwidth (Kbits/sec or Mbits/sec) allowed for traffic associated to this profile.
         If value is set to -1, then the Ingress Bandwidth specified for the profile is unconfigured."
    DEFVAL { 0 }
    ::= { alaDaUNPEdgeProfEntry 14 }

alaDaUNPEdgeProfMaxEgressBw OBJECT-TYPE
    SYNTAX      Integer32 (-1|0..2147483647)
    UNITS       "kilobits per second"
    MAX-ACCESS  read-create
    STATUS      deprecated
    DESCRIPTION
        "Maximum Egress Bandwidth (Kbits/sec or Mbits/sec) allowed for traffic associated to this profile.
         If value is set to -1, then the Egress Bandwidth specified for the profile is unconfigured."
    DEFVAL { 0 }
    ::= { alaDaUNPEdgeProfEntry 15 }

alaDaUNPEdgeProfMaxIngressDepth OBJECT-TYPE
    SYNTAX      Integer32 (-1|0..16384)
    MAX-ACCESS  read-create
    STATUS      deprecated
    DESCRIPTION
        "Maximum Ingress Depth associated to Bandwidth.
         If set to 0, then the Depth associated with the profile is unconfigured."
    DEFVAL { 0 }
    ::= { alaDaUNPEdgeProfEntry 16 }

alaDaUNPEdgeProfMaxEgressDepth OBJECT-TYPE
    SYNTAX      Integer32 (-1|0..16384)
    MAX-ACCESS  read-create
    STATUS      deprecated
    DESCRIPTION
        "Maximum Egress Depth associated to Bandwidth.
         If set to 0, then the Depth associated with the profile is unconfigured."
    DEFVAL { 0 }
    ::= { alaDaUNPEdgeProfEntry 17 }

--------------------------------------------------
-- Classification Rule Port Based Table
----------------------------------------------------

alaDaUNPPortRuleTable OBJECT-TYPE
    SYNTAX      SEQUENCE OF AlaDaUNPPortRuleEntry
    MAX-ACCESS  not-accessible
    STATUS      current
    DESCRIPTION
        "Unp Port Rule Table ."
    ::= { alaIND1DaMIBObjects 23 }

alaDaUNPPortRuleEntry    OBJECT-TYPE
    SYNTAX    AlaDaUNPPortRuleEntry
    MAX-ACCESS  not-accessible
    STATUS      current
    DESCRIPTION
        "PortRule Table Entries ."
    INDEX { alaDaUNPPortRuleNum }
    ::= { alaDaUNPPortRuleTable 1 }

AlaDaUNPPortRuleEntry ::= SEQUENCE  {
    alaDaUNPPortRuleNum            InterfaceIndex,
    alaDaUNPPortRuleEdgeProf       SnmpAdminString, --deprecated
    alaDaUNPPortRuleRowStatus      RowStatus,
    alaDaUNPPortRuleVlanTag        Integer32,
    alaDaUNPPortRuleProfile1       SnmpAdminString,
    alaDaUNPPortRuleProfile2       SnmpAdminString,
    alaDaUNPPortRuleProfile3       SnmpAdminString
}

alaDaUNPPortRuleNum  OBJECT-TYPE
    SYNTAX      InterfaceIndex
    MAX-ACCESS  not-accessible
    STATUS      current
    DESCRIPTION
        " ifIndex ."
    ::= { alaDaUNPPortRuleEntry 1 }

alaDaUNPPortRuleEdgeProf OBJECT-TYPE
    SYNTAX    SnmpAdminString ( SIZE( 0 .. 32 ) )
    MAX-ACCESS read-create
    STATUS      deprecated
    DESCRIPTION
        "Associated Edge Profile Name ."
    ::= { alaDaUNPPortRuleEntry 2  }

alaDaUNPPortRuleRowStatus OBJECT-TYPE
    SYNTAX        RowStatus
    MAX-ACCESS    read-create
    STATUS        current
    DESCRIPTION
        "The status of this table entry."
    ::= { alaDaUNPPortRuleEntry 3 }

alaDaUNPPortRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPPortRuleEntry 4 }

alaDaUNPPortRuleProfile1 OBJECT-TYPE
    SYNTAX    SnmpAdminString ( SIZE( 0 .. 32 ) )
    MAX-ACCESS read-create
    STATUS      current
    DESCRIPTION
        "Associated Profile Name ."
    ::= { alaDaUNPPortRuleEntry 5 }

alaDaUNPPortRuleProfile2 OBJECT-TYPE
    SYNTAX    SnmpAdminString ( SIZE( 0 .. 32 ) )
    MAX-ACCESS read-create
    STATUS      current
    DESCRIPTION
        "Associated Profile Name ."
    ::= { alaDaUNPPortRuleEntry 6 }

alaDaUNPPortRuleProfile3 OBJECT-TYPE
    SYNTAX    SnmpAdminString ( SIZE( 0 .. 32 ) )
    MAX-ACCESS read-create
    STATUS      current
    DESCRIPTION
        "Associated Profile Name ."
    ::= { alaDaUNPPortRuleEntry 7 }

-----------------------------------------------
-- Classification Rule Group Id  Based Table
-- This table is deprecated as part of unification
-----------------------------------------------

alaDaUNPGroupRuleTable OBJECT-TYPE
    SYNTAX      SEQUENCE OF AlaDaUNPGroupRuleEntry
    MAX-ACCESS  not-accessible
    STATUS      deprecated
    DESCRIPTION
        "Based on Group id , Edge Profile Classification table  ."
    ::= { alaIND1DaMIBObjects 24 }

alaDaUNPGroupRuleEntry   OBJECT-TYPE
    SYNTAX   AlaDaUNPGroupRuleEntry
    MAX-ACCESS  not-accessible
    STATUS      deprecated
    DESCRIPTION
        "Group Rule Table Entries ."
    INDEX { alaDaUNPGroupRuleId }
    ::= { alaDaUNPGroupRuleTable 1 }

AlaDaUNPGroupRuleEntry ::= SEQUENCE  {
    alaDaUNPGroupRuleId           Integer32,
    alaDaUNPGroupRuleEdgeProf     SnmpAdminString,
    alaDaUNPGroupRuleRowStatus    RowStatus,
    alaDaUNPGroupRuleVlanTag      Integer32
}

alaDaUNPGroupRuleId  OBJECT-TYPE
    SYNTAX      Integer32(1..255)
    MAX-ACCESS  not-accessible
    STATUS      deprecated
    DESCRIPTION
        "Group Id ."
    ::= { alaDaUNPGroupRuleEntry 1 }

alaDaUNPGroupRuleEdgeProf OBJECT-TYPE
    SYNTAX    SnmpAdminString ( SIZE( 0 .. 32 ) )
    MAX-ACCESS read-create
    STATUS      deprecated
    DESCRIPTION
        "Associated Edge Profile ."
    ::= { alaDaUNPGroupRuleEntry 2  }

alaDaUNPGroupRuleRowStatus OBJECT-TYPE
    SYNTAX        RowStatus
    MAX-ACCESS    read-create
    STATUS        deprecated
    DESCRIPTION
        "The status of this table entry."
    ::= { alaDaUNPGroupRuleEntry 3 }

alaDaUNPGroupRuleVlanTag  OBJECT-TYPE
    SYNTAX        Integer32 (0..4094)
    MAX-ACCESS    read-create
    STATUS        deprecated
    DESCRIPTION
        "The vlan tag to be used for classification of tagged pkts.
         Vlan tag of 0 indicates no VLAN is associated."
    ::= { alaDaUNPGroupRuleEntry 4 }

-----------------------------------------------
-- Mac OUI Rule Table
-----------------------------------------------

alaDaUNPMacOuiRuleTable  OBJECT-TYPE
    SYNTAX  SEQUENCE OF AlaDaUNPMacOuiRuleEntry
    MAX-ACCESS  not-accessible
    STATUS  current
    DESCRIPTION
        "A list of MAC Oui rules.  This is used to match
         the MAC Oui  of a packet to a User Network Profile entry "
    ::= { alaIND1DaMIBObjects 25 }

alaDaUNPMacOuiRuleEntry OBJECT-TYPE
    SYNTAX  AlaDaUNPMacOuiRuleEntry
    MAX-ACCESS  not-accessible
    STATUS  current
    DESCRIPTION
        "A MAC rule entry."
    INDEX { alaDaUNPMacOuiRuleAddr }
    ::= { alaDaUNPMacOuiRuleTable 1 }

AlaDaUNPMacOuiRuleEntry ::= SEQUENCE {
    alaDaUNPMacOuiRuleAddr
        MacOui,
    alaDaUNPMacOuiRuleEdgeProfile
        SnmpAdminString,      --deprecated
    alaDaUNPMacOuiRuleRowStatus
        RowStatus,
    alaDaUNPMacOuiRuleVlanTag
        Integer32,
    alaDaUNPMacOuiRuleProfile1
        SnmpAdminString,
    alaDaUNPMacOuiRuleProfile2
        SnmpAdminString,
    alaDaUNPMacOuiRuleProfile3
        SnmpAdminString
}

alaDaUNPMacOuiRuleAddr OBJECT-TYPE
    SYNTAX MacOui
    MAX-ACCESS  not-accessible
    STATUS  current
    DESCRIPTION
        "The MAC Oui address used for classification."
    ::= { alaDaUNPMacOuiRuleEntry 1 }

alaDaUNPMacOuiRuleEdgeProfile   OBJECT-TYPE
    SYNTAX  SnmpAdminString ( SIZE( 1 .. 32 ) )
    MAX-ACCESS  read-create
    STATUS  deprecated
    DESCRIPTION
        "The profile name in the User Network Profile Table to be
         applied."
    ::= { alaDaUNPMacOuiRuleEntry 2 }

alaDaUNPMacOuiRuleRowStatus OBJECT-TYPE
    SYNTAX        RowStatus
    MAX-ACCESS    read-create
    STATUS        current
    DESCRIPTION
        "The status of this table entry."
    ::= { alaDaUNPMacOuiRuleEntry 3 }

alaDaUNPMacOuiRuleVlanTag  OBJECT-TYPE
    SYNTAX      Integer32 (0..4094)
    MAX-ACCESS  read-create
    STATUS      current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPMacOuiRuleEntry 4 }

alaDaUNPMacOuiRuleProfile1   OBJECT-TYPE
    SYNTAX  SnmpAdminString ( SIZE( 1 .. 32 ) )
    MAX-ACCESS  read-create
    STATUS  current
    DESCRIPTION
        "The profile name in the User Network Profile Table to be
         applied."
    ::= { alaDaUNPMacOuiRuleEntry 5 }

alaDaUNPMacOuiRuleProfile2   OBJECT-TYPE
    SYNTAX  SnmpAdminString ( SIZE( 1 .. 32 ) )
    MAX-ACCESS  read-create
    STATUS  current
    DESCRIPTION
        "The profile name in the User Network Profile Table to be
         applied."
    ::= { alaDaUNPMacOuiRuleEntry 6 }

alaDaUNPMacOuiRuleProfile3   OBJECT-TYPE
    SYNTAX  SnmpAdminString ( SIZE( 1 .. 32 ) )
    MAX-ACCESS  read-create
    STATUS  current
    DESCRIPTION
        "The profile name in the User Network Profile Table to be
         applied."
    ::= { alaDaUNPMacOuiRuleEntry 7 }

-----------------------------------------------
-- End Point Rule Table
-----------------------------------------------

alaDaUNPEndPoinRuleTable  OBJECT-TYPE
    SYNTAX  SEQUENCE OF AlaDaUNPEndPoinRuleEntry
    MAX-ACCESS  not-accessible
    STATUS  current
    DESCRIPTION
        "A list of  End point  rules.  This is used to match
         the lldp med-endpoint   of a packet to a User Network Profile entry "
    ::= { alaIND1DaMIBObjects 26 }

alaDaUNPEndPoinRuleEntry    OBJECT-TYPE
    SYNTAX  AlaDaUNPEndPoinRuleEntry
    MAX-ACCESS  not-accessible
    STATUS  current
    DESCRIPTION
        "A MAC rule entry."
    INDEX {  alaDaUNPEndPoinRuleId }
    ::= { alaDaUNPEndPoinRuleTable 1 }

AlaDaUNPEndPoinRuleEntry ::= SEQUENCE  {
    alaDaUNPEndPoinRuleId               INTEGER,
    alaDaUNPEndPoinEdgeProfile          SnmpAdminString, --deprecated
    alaDaUNPEndPoinRuleRowStatus        RowStatus,
    alaDaUNPEndPoinProfile1             SnmpAdminString,
    alaDaUNPEndPoinProfile2             SnmpAdminString,
    alaDaUNPEndPoinProfile3             SnmpAdminString,
    alaDaUNPEndPoinVlanTag              Integer32
}

alaDaUNPEndPoinRuleId   OBJECT-TYPE
    SYNTAX        INTEGER {
                      ipPhone(1)
                  }
    MAX-ACCESS    not-accessible
    STATUS        current
    DESCRIPTION
        "End Point Identifier ."
    ::= { alaDaUNPEndPoinRuleEntry 1 }

alaDaUNPEndPoinEdgeProfile OBJECT-TYPE
    SYNTAX  SnmpAdminString ( SIZE( 1 .. 32 ) )
    MAX-ACCESS  read-create
    STATUS  deprecated
    DESCRIPTION
        "The edge profile name in the User Network Profile Table to be
         applied."
    ::= { alaDaUNPEndPoinRuleEntry 2 }

alaDaUNPEndPoinRuleRowStatus OBJECT-TYPE
    SYNTAX        RowStatus
    MAX-ACCESS    read-create
    STATUS        current
    DESCRIPTION
        "The status of this table entry."
    ::= { alaDaUNPEndPoinRuleEntry 3 }

alaDaUNPEndPoinProfile1 OBJECT-TYPE
    SYNTAX  SnmpAdminString ( SIZE( 1 .. 32 ) )
    MAX-ACCESS  read-create
    STATUS  current
    DESCRIPTION
        "The profile name in the User Network Profile Table to be
         applied."
    ::= { alaDaUNPEndPoinRuleEntry 4 }

alaDaUNPEndPoinProfile2 OBJECT-TYPE
    SYNTAX  SnmpAdminString ( SIZE( 1 .. 32 ) )
    MAX-ACCESS  read-create
    STATUS  current
    DESCRIPTION
        "The profile name in the User Network Profile Table to be
         applied."
    ::= { alaDaUNPEndPoinRuleEntry 5 }

alaDaUNPEndPoinProfile3 OBJECT-TYPE
    SYNTAX  SnmpAdminString ( SIZE( 1 .. 32 ) )
    MAX-ACCESS  read-create
    STATUS  current
    DESCRIPTION
        "The profile name in the User Network Profile Table to be
         applied."
    ::= { alaDaUNPEndPoinRuleEntry 6 }

alaDaUNPEndPoinVlanTag  OBJECT-TYPE
    SYNTAX  Integer32 (0..4094)
    MAX-ACCESS  read-create
    STATUS  current
    DESCRIPTION
        "The VLAN Tag to be used for classification of tagged pkts.
         VLAN Tag of 0 indicates no VLAN is associated. The VLAN Tag is of
         the Q-in-Q VLAN Tag format, where the value of the outer 802.1Q
         VLAN ID is encoded in the least significant 16 bits, and the value of
         inner VLAN ID is encoded  in the most significant 16 bits."
    ::= { alaDaUNPEndPoinRuleEntry 7 }

-----------------------------------------------
-- Auth Rule Table
-----------------------------------------------

alaDaUNPAuthRuleTable  OBJECT-TYPE
    SYNTAX  SEQUENCE OF AlaDaUNPAuthRuleEntry
    MAX-ACCESS  not-accessible
    STATUS  current
    DESCRIPTION
        "A list of  Auth  rules.  This is used to match
         authentication type  to a User Network Profile entry "
    ::= { alaIND1DaMIBObjects 27 }

alaDaUNPAuthRuleEntry OBJECT-TYPE
    SYNTAX  AlaDaUNPAuthRuleEntry
    MAX-ACCESS  not-accessible
    STATUS  current
    DESCRIPTION
        " Auth based  rule entry."
    INDEX {  alaDaUNPAuthRuleType }
    ::= { alaDaUNPAuthRuleTable 1 }

AlaDaUNPAuthRuleEntry ::= SEQUENCE  {
    alaDaUNPAuthRuleType             INTEGER,
    alaDaUNPAuthRuleEdgeProfile      SnmpAdminString, --deprecated
    alaDaUNPAuthRuleRowStatus        RowStatus,
    alaDaUNPAuthRuleVlanTag          Integer32,
    alaDaUNPAuthRuleProfile1         SnmpAdminString,
    alaDaUNPAuthRuleProfile2         SnmpAdminString,
    alaDaUNPAuthRuleProfile3         SnmpAdminString
}

alaDaUNPAuthRuleType    OBJECT-TYPE
    SYNTAX        INTEGER {
                      none(1),
                      dot1x(2),
                      mac(3),
                      dot1xFail(4),
                      macFail(5),
                      noAuth(6)
                  }
    MAX-ACCESS    not-accessible
    STATUS        current
    DESCRIPTION
    "Auth Rule Identifier ."
    ::= { alaDaUNPAuthRuleEntry 1 }

alaDaUNPAuthRuleEdgeProfile OBJECT-TYPE
    SYNTAX  SnmpAdminString ( SIZE( 1 .. 32 ) )
    MAX-ACCESS  read-create
    STATUS  deprecated
    DESCRIPTION
        "The edge profile name in the User Network Profile Table to be
         applied."
    ::= { alaDaUNPAuthRuleEntry 2 }

alaDaUNPAuthRuleRowStatus OBJECT-TYPE
    SYNTAX        RowStatus
    MAX-ACCESS    read-create
    STATUS        current
    DESCRIPTION
        "The status of this table entry."
    ::= { alaDaUNPAuthRuleEntry 3 }

alaDaUNPAuthRuleVlanTag  OBJECT-TYPE
    SYNTAX  Integer32 (0..4094)
    MAX-ACCESS  read-create
    STATUS  current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPAuthRuleEntry 4 }

alaDaUNPAuthRuleProfile1 OBJECT-TYPE
    SYNTAX  SnmpAdminString ( SIZE( 1 .. 32 ) )
    MAX-ACCESS  read-create
    STATUS  current
    DESCRIPTION
        "The profile name in the User Network Profile Table to be
         applied."
    ::= { alaDaUNPAuthRuleEntry 5 }

alaDaUNPAuthRuleProfile2 OBJECT-TYPE
    SYNTAX  SnmpAdminString ( SIZE( 1 .. 32 ) )
    MAX-ACCESS  read-create
    STATUS  current
    DESCRIPTION
        "The profile name in the User Network Profile Table to be
         applied."
    ::= { alaDaUNPAuthRuleEntry 6 }

alaDaUNPAuthRuleProfile3 OBJECT-TYPE
    SYNTAX  SnmpAdminString ( SIZE( 1 .. 32 ) )
    MAX-ACCESS  read-create
    STATUS  current
    DESCRIPTION
        "The profile name in the User Network Profile Table to be
         applied."
    ::= { alaDaUNPAuthRuleEntry 7 }

-----------------------------------------------
--Classification Rule Table
-----------------------------------------------

alaDaUNPClassifRuleTable  OBJECT-TYPE
    SYNTAX  SEQUENCE OF AlaDaUNPClassifRuleEntry
    MAX-ACCESS  not-accessible
    STATUS  current
    DESCRIPTION
        "A list of  Calssification rules.  This is used to match
         classification rule  to a User Network Profile entry "
    ::= { alaIND1DaMIBObjects 28 }

alaDaUNPClassifRuleEntry OBJECT-TYPE
    SYNTAX   AlaDaUNPClassifRuleEntry
    MAX-ACCESS  not-accessible
    STATUS  current
    DESCRIPTION
        " Classification   rule entry."
    INDEX {   alaDaUNPClassifRuleName }
    ::= { alaDaUNPClassifRuleTable 1 }

AlaDaUNPClassifRuleEntry    ::= SEQUENCE {
    alaDaUNPClassifRuleName                  SnmpAdminString,
    alaDaUNPClassifRulePrecedenceNum         Integer32,
    alaDaUNPClassifRuleEdgeProfile           SnmpAdminString,  --deprecated
    alaDaUNPClassifRulePort                  InterfaceIndexOrZero,
    alaDaUNPClassifRulePortHigh              InterfaceIndexOrZero,
    alaDaUNPClassifRuleGroupId               Integer32,   --deprecated
    alaDaUNPClassifRuleMacAddr               MacAddress,
    alaDaUNPClassifRuleMacRngLoaddr          MacAddress,
    alaDaUNPClassifRuleMacRngHiaddr          MacAddress,
    alaDaUNPClassifRuleMacOuiAddr            OCTET STRING,
    alaDaUNPClassifRuleEndPoin               INTEGER,
    alaDaUNPClassifRuleAuthType              INTEGER,
    alaDaUNPClassifRuleIpAddressType         InetAddressType,
    alaDaUNPClassifRuleIpAddress             InetAddress,
    alaDaUNPClassifRuleIpMaskType            InetAddressType,
    alaDaUNPClassifRuleIpMask                InetAddress,
    alaDaUNPClassifRowStatus                 RowStatus,
    alaDaUNPClassifRuleVlanTag               Integer32,
    alaDaUNPClassifRuleCustomerDomain        Integer32,
    alaDaUNPClassifRuleProfile1              SnmpAdminString,
    alaDaUNPClassifRuleProfile2              SnmpAdminString,
    alaDaUNPClassifRuleProfile3              SnmpAdminString
}

alaDaUNPClassifRuleName OBJECT-TYPE
    SYNTAX  SnmpAdminString ( SIZE( 1 .. 32 ) )
    MAX-ACCESS  not-accessible
    STATUS  current
    DESCRIPTION
        "Classification Rule Name ."
    ::= { alaDaUNPClassifRuleEntry  1 }

alaDaUNPClassifRulePrecedenceNum    OBJECT-TYPE
    SYNTAX  Integer32(1..255)
    MAX-ACCESS  read-create
    STATUS  current
    DESCRIPTION
        "Classification Rule Precedence number ."
    DEFVAL { 1 }
    ::= { alaDaUNPClassifRuleEntry  2 }

alaDaUNPClassifRuleEdgeProfile OBJECT-TYPE
    SYNTAX  SnmpAdminString ( SIZE( 0 .. 32 ) )
    MAX-ACCESS  read-create
    STATUS  deprecated
    DESCRIPTION
        "Classification Rule Edge ProfileName ."
    ::= { alaDaUNPClassifRuleEntry  3 }

alaDaUNPClassifRulePort OBJECT-TYPE
    SYNTAX  InterfaceIndexOrZero
    MAX-ACCESS  read-create
    STATUS  current
    DESCRIPTION
        "Classification Rule  port ."
    ::= { alaDaUNPClassifRuleEntry  4 }

alaDaUNPClassifRulePortHigh OBJECT-TYPE
    SYNTAX  InterfaceIndexOrZero
    MAX-ACCESS  read-create
    STATUS  current
    DESCRIPTION
        "Classification Rule  port ."
    ::= { alaDaUNPClassifRuleEntry  5 }

alaDaUNPClassifRuleGroupId  OBJECT-TYPE
    SYNTAX  Integer32(-1..255)
    MAX-ACCESS  read-create
    STATUS  deprecated
    DESCRIPTION
        "Classification Rule Group Id. Value of -1
         indicates uncofiguring the previously
         configured groupId value ."
    DEFVAL { 0 }
    ::= { alaDaUNPClassifRuleEntry  6 }

alaDaUNPClassifRuleMacAddr  OBJECT-TYPE
    SYNTAX  MacAddress
    MAX-ACCESS  read-create
    STATUS  current
    DESCRIPTION
        "Classification Rule mac Address."
    ::= { alaDaUNPClassifRuleEntry  7 }

alaDaUNPClassifRuleMacRngLoaddr   OBJECT-TYPE
    SYNTAX  MacAddress
    MAX-ACCESS  read-create
    STATUS  current
    DESCRIPTION
        "Classification Rule mac Address Range starting address."
    ::= { alaDaUNPClassifRuleEntry  8 }

alaDaUNPClassifRuleMacRngHiaddr OBJECT-TYPE
    SYNTAX  MacAddress
    MAX-ACCESS  read-create
    STATUS  current
    DESCRIPTION
        "Classification Rule mac Address Range ending address."
    ::= { alaDaUNPClassifRuleEntry  9 }

alaDaUNPClassifRuleMacOuiAddr OBJECT-TYPE
    SYNTAX OCTET STRING (SIZE (0|3..3))
    MAX-ACCESS  read-create
    STATUS  current
    DESCRIPTION
        "Classification Rule mac oui address."
    ::= { alaDaUNPClassifRuleEntry  10 }

alaDaUNPClassifRuleEndPoin  OBJECT-TYPE
    SYNTAX        INTEGER {
                      none(0),
                      ipPhone(1)
                  }
    MAX-ACCESS   read-create
    STATUS        current
    DESCRIPTION
        "End Point Identifier ."
    DEFVAL { none }
    ::= { alaDaUNPClassifRuleEntry  11 }

alaDaUNPClassifRuleAuthType OBJECT-TYPE
    SYNTAX        INTEGER {
                      none(0),
                      noAuth(1),
                      dot1x(2),
                      mac(3),
                      dot1xFail(4),
                      macFail(5)
                  }
    MAX-ACCESS   read-create
    STATUS        current
    DESCRIPTION
        "Classification Rule Auth Type ."
    DEFVAL  { none }
    ::= { alaDaUNPClassifRuleEntry  12 }

alaDaUNPClassifRuleIpAddressType OBJECT-TYPE
    SYNTAX  InetAddressType
    MAX-ACCESS read-create
    STATUS current
    DESCRIPTION
        "The IP address type ."
    ::= { alaDaUNPClassifRuleEntry 13   }

alaDaUNPClassifRuleIpAddress OBJECT-TYPE
    SYNTAX InetAddress
    MAX-ACCESS read-create
    STATUS  current
    DESCRIPTION
        "Classification Rule Ip address."
    ::= { alaDaUNPClassifRuleEntry 14 }

alaDaUNPClassifRuleIpMaskType OBJECT-TYPE
    SYNTAX  InetAddressType
    MAX-ACCESS read-create
    STATUS current
    DESCRIPTION
        "The IP Mask type ."
    ::= { alaDaUNPClassifRuleEntry 15 }

alaDaUNPClassifRuleIpMask OBJECT-TYPE
    SYNTAX InetAddress
    MAX-ACCESS read-create
    STATUS  current
    DESCRIPTION
        "Classification Rule Ip Mask."
    ::= { alaDaUNPClassifRuleEntry 16 }

alaDaUNPClassifRowStatus    OBJECT-TYPE
    SYNTAX        RowStatus
    MAX-ACCESS    read-create
    STATUS        current
    DESCRIPTION
        "The status of this table entry."
    ::= { alaDaUNPClassifRuleEntry  17 }

alaDaUNPClassifRuleVlanTag   OBJECT-TYPE
    SYNTAX      Integer32 (-1|0..4094)
    MAX-ACCESS  read-create
    STATUS      current
    DESCRIPTION
        "The VLAN Tag to be used for classification of tagged pkts.
         The VLAN Tag is of the Q-in-Q VLAN Tag format,
         where the value of the outer 802.1Q VLAN ID is
         encoded in the least significant 16 bits, and the value of the inner
         VLAN ID is encoded in the most significant 16 bits. Value of -1
	 indicates unconfiguring of the previously configured VLAN-Tag."
    ::= { alaDaUNPClassifRuleEntry 18 }

alaDaUNPClassifRuleCustomerDomain  OBJECT-TYPE
    SYNTAX      Integer32(-1|0..4294967295)
    MAX-ACCESS  read-create
    STATUS      current
    DESCRIPTION
        "Classification Rule Customer Domain. Value of -1
                indicates uncofiguring the previously
                configured customer domain value ."
    DEFVAL { 0 }
    ::= { alaDaUNPClassifRuleEntry  19 }

alaDaUNPClassifRuleProfile1 OBJECT-TYPE
    SYNTAX              SnmpAdminString ( SIZE( 0 .. 32 ) )
    MAX-ACCESS          read-create
    STATUS              current
    DESCRIPTION
        "Profile with priority 1 associated with the Classification Rule."
    ::= { alaDaUNPClassifRuleEntry  20 }

alaDaUNPClassifRuleProfile2 OBJECT-TYPE
    SYNTAX          SnmpAdminString ( SIZE( 0 .. 32 ) )
    MAX-ACCESS      read-create
    STATUS          current
    DESCRIPTION
        "Profile with priority 2 associated with the Classification Rule."
    ::= { alaDaUNPClassifRuleEntry  21 }

alaDaUNPClassifRuleProfile3 OBJECT-TYPE
    SYNTAX          SnmpAdminString ( SIZE( 0 .. 32 ) )
    MAX-ACCESS      read-create
    STATUS          current
    DESCRIPTION
        "Profile with priority 3 associated with the Classification Rule."
    ::= { alaDaUNPClassifRuleEntry  22 }

----------------------------------------------
-- MAC, PORT Based classification table
----------------------------------------------

alaDaUNPMacPortRuleTable  OBJECT-TYPE
    SYNTAX  SEQUENCE OF AlaDaUNPMacPortRuleEntry
    MAX-ACCESS  not-accessible
    STATUS  current
    DESCRIPTION
        "Mac Address & port classification table ."
    ::= { alaIND1DaMIBObjects 29 }

alaDaUNPMacPortRuleEntry OBJECT-TYPE
    SYNTAX  AlaDaUNPMacPortRuleEntry
    MAX-ACCESS  not-accessible
    STATUS  current
    DESCRIPTION
        " Mac & port  based  classification rule ."
    INDEX {
              alaDaUNPMacPortRuleMacAddr,
              alaDaUNPMacPortRuleNum
          }
    ::= { alaDaUNPMacPortRuleTable 1 }

AlaDaUNPMacPortRuleEntry ::= SEQUENCE  {
    alaDaUNPMacPortRuleMacAddr            MacAddress,
    alaDaUNPMacPortRuleNum                InterfaceIndex,
    alaDaUNPMacPortRuleEdgeProf           SnmpAdminString, --deprecated
    alaDaUNPMacPortRuleRowStatus          RowStatus,
    alaDaUNPMacPortRuleVlanTag            Integer32,
    alaDaUNPMacPortRuleProfile1           SnmpAdminString,
    alaDaUNPMacPortRuleProfile2           SnmpAdminString,
    alaDaUNPMacPortRuleProfile3           SnmpAdminString
}

alaDaUNPMacPortRuleMacAddr OBJECT-TYPE
    SYNTAX  MacAddress(SIZE(6))
    MAX-ACCESS not-accessible
    STATUS  current
    DESCRIPTION
        "Classification Rule mac Address."
    ::= { alaDaUNPMacPortRuleEntry 1 }

alaDaUNPMacPortRuleNum  OBJECT-TYPE
    SYNTAX       InterfaceIndex (1..2147483647)
    MAX-ACCESS    not-accessible
    STATUS        current
    DESCRIPTION
        "Classification Rule Port num."
    ::= { alaDaUNPMacPortRuleEntry 2 }

alaDaUNPMacPortRuleEdgeProf OBJECT-TYPE
    SYNTAX  SnmpAdminString ( SIZE( 1 .. 32 ) )
    MAX-ACCESS  read-create
    STATUS  deprecated
    DESCRIPTION
        "The edge profile name in the User Network Profile Table to be
         applied."
    ::= { alaDaUNPMacPortRuleEntry 3 }

alaDaUNPMacPortRuleRowStatus OBJECT-TYPE
    SYNTAX        RowStatus
    MAX-ACCESS    read-create
    STATUS        current
    DESCRIPTION
        "The status of this table entry."
    ::= { alaDaUNPMacPortRuleEntry 4 }

alaDaUNPMacPortRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPMacPortRuleEntry 5 }

alaDaUNPMacPortRuleProfile1 OBJECT-TYPE
    SYNTAX  SnmpAdminString ( SIZE( 1 .. 32 ) )
    MAX-ACCESS  read-create
    STATUS  current
    DESCRIPTION
        "The profile name in the User Network Profile Table to be
         applied."
    ::= { alaDaUNPMacPortRuleEntry 6 }

alaDaUNPMacPortRuleProfile2 OBJECT-TYPE
    SYNTAX  SnmpAdminString ( SIZE( 1 .. 32 ) )
    MAX-ACCESS  read-create
    STATUS  current
    DESCRIPTION
        "The profile name in the User Network Profile Table to be
         applied."
    ::= { alaDaUNPMacPortRuleEntry 7 }

alaDaUNPMacPortRuleProfile3 OBJECT-TYPE
    SYNTAX  SnmpAdminString ( SIZE( 1 .. 32 ) )
    MAX-ACCESS  read-create
    STATUS  current
    DESCRIPTION
        "The profile name in the User Network Profile Table to be
         applied."
    ::= { alaDaUNPMacPortRuleEntry 8 }

------------------------------------------------
-- Ip , Port based classification table
------------------------------------------------
alaDaUNPIpPortRuleTable  OBJECT-TYPE
    SYNTAX  SEQUENCE OF AlaDaUNPIpPortRuleEntry
    MAX-ACCESS  not-accessible
    STATUS  current
    DESCRIPTION
        "Ip Address & port classification table ."
    ::= { alaIND1DaMIBObjects 30 }

alaDaUNPIpPortRuleEntry OBJECT-TYPE
    SYNTAX  AlaDaUNPIpPortRuleEntry
    MAX-ACCESS  not-accessible
    STATUS  current
    DESCRIPTION
     " Ip & port  based  classification rule ."
     INDEX {
               alaDaUNPIpPortRuleAddrType,
               alaDaUNPIpPortRuleAddr,
               alaDaUNPIpPortRuleNum
           }
     ::= { alaDaUNPIpPortRuleTable 1 }

AlaDaUNPIpPortRuleEntry ::= SEQUENCE  {
    alaDaUNPIpPortRuleAddrType           InetAddressType,
    alaDaUNPIpPortRuleAddr               InetAddress,
    alaDaUNPIpPortRuleNum                InterfaceIndex,
    alaDaUNPIpPortRuleEdgeProf           SnmpAdminString,   --deprecated
    alaDaUNPIpPortRuleRowStatus          RowStatus,
    alaDaUNPIpPortRuleVlanTag            Integer32,
    alaDaUNPIpPortRuleProfile1           SnmpAdminString,
    alaDaUNPIpPortRuleProfile2           SnmpAdminString,
    alaDaUNPIpPortRuleProfile3           SnmpAdminString,
    alaDaUNPIpPortRuleMaskType           InetAddressType,
    alaDaUNPIpPortRuleMask               InetAddress
}

alaDaUNPIpPortRuleAddrType  OBJECT-TYPE
    SYNTAX  InetAddressType
    MAX-ACCESS  not-accessible
    STATUS current
    DESCRIPTION
        "The IP address type ."
    ::= { alaDaUNPIpPortRuleEntry 1 }

alaDaUNPIpPortRuleAddr  OBJECT-TYPE
    SYNTAX  InetAddress
    MAX-ACCESS  not-accessible
    STATUS  current
    DESCRIPTION
        "The IP network address ."
    ::= { alaDaUNPIpPortRuleEntry 2 }

alaDaUNPIpPortRuleNum  OBJECT-TYPE
    SYNTAX       InterfaceIndex (1..2147483647)
    MAX-ACCESS    not-accessible
    STATUS        current
    DESCRIPTION
        "Classification Rule Port num."
    ::= { alaDaUNPIpPortRuleEntry 3 }

alaDaUNPIpPortRuleEdgeProf OBJECT-TYPE
    SYNTAX  SnmpAdminString ( SIZE( 1 .. 32 ) )
    MAX-ACCESS  read-create
    STATUS  deprecated
    DESCRIPTION
        "The edge profile name in the User Network Profile Table to be
          applied."
    ::= { alaDaUNPIpPortRuleEntry 4 }

alaDaUNPIpPortRuleRowStatus OBJECT-TYPE
    SYNTAX        RowStatus
    MAX-ACCESS    read-create
    STATUS        current
    DESCRIPTION
        "The status of this table entry."
    ::= { alaDaUNPIpPortRuleEntry 5 }

alaDaUNPIpPortRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPIpPortRuleEntry 6 }

alaDaUNPIpPortRuleProfile1 OBJECT-TYPE
    SYNTAX  SnmpAdminString ( SIZE( 1 .. 32 ) )
    MAX-ACCESS  read-create
    STATUS  current
    DESCRIPTION
        "The profile name in the User Network Profile Table to be
          applied."
    ::= { alaDaUNPIpPortRuleEntry 7 }

alaDaUNPIpPortRuleProfile2 OBJECT-TYPE
    SYNTAX  SnmpAdminString ( SIZE( 1 .. 32 ) )
    MAX-ACCESS  read-create
    STATUS  current
    DESCRIPTION
        "The profile name in the User Network Profile Table to be
          applied."
    ::= { alaDaUNPIpPortRuleEntry 8 }

alaDaUNPIpPortRuleProfile3 OBJECT-TYPE
    SYNTAX  SnmpAdminString ( SIZE( 1 .. 32 ) )
    MAX-ACCESS  read-create
    STATUS  current
    DESCRIPTION
        "The profile name in the User Network Profile Table to be
          applied."
    ::= { alaDaUNPIpPortRuleEntry 9 }

alaDaUNPIpPortRuleMaskType OBJECT-TYPE
    SYNTAX  InetAddressType
                {
                    ipv4(1),
                    ipv6(2)
                }
    MAX-ACCESS  read-create
    STATUS  current
    DESCRIPTION
        "The IP mask type. This field is mandatory."
    ::= { alaDaUNPIpPortRuleEntry 10 }

alaDaUNPIpPortRuleMask OBJECT-TYPE
    SYNTAX  InetAddress (SIZE (4|16))
    MAX-ACCESS  read-create
    STATUS  current
    DESCRIPTION
        "The IP network mask applying to the IP network address. This field is mandatory."
    ::= { alaDaUNPIpPortRuleEntry 11 }

-----------------------------------------------
-- MAC,IP,PORT classification table
-----------------------------------------------

alaDaUNPMacIpPortRuleTable  OBJECT-TYPE
    SYNTAX  SEQUENCE OF AlaDaUNPMacIpPortRuleEntry
    MAX-ACCESS  not-accessible
    STATUS  current
    DESCRIPTION
        "Mac, Ip Address & port classification table ."
    ::= { alaIND1DaMIBObjects 31 }

alaDaUNPMacIpPortRuleEntry OBJECT-TYPE
    SYNTAX  AlaDaUNPMacIpPortRuleEntry
    MAX-ACCESS  not-accessible
    STATUS  current
    DESCRIPTION
        " Mac, Ip & port  based  classification rule ."
    INDEX {
              alaDaUNPMacIpPortRuleMacAddr,
              alaDaUNPMacIpPortRuleAddrIpType,
              alaDaUNPMacIpPortRuleIpAddr,
              alaDaUNPMacIpPortRuleNum
         }
    ::= { alaDaUNPMacIpPortRuleTable 1 }

AlaDaUNPMacIpPortRuleEntry ::= SEQUENCE  {
    alaDaUNPMacIpPortRuleMacAddr                MacAddress,
    alaDaUNPMacIpPortRuleAddrIpType             InetAddressType,
    alaDaUNPMacIpPortRuleIpAddr                 InetAddress,
    alaDaUNPMacIpPortRuleNum                    InterfaceIndex,
    alaDaUNPMacIpPortRuleEdgeProf               SnmpAdminString, --deprecated
    alaDaUNPMacIpPortRuleRowStatus              RowStatus,
    alaDaUNPMacIpPortRuleVlanTag                Integer32,
    alaDaUNPMacIpPortRuleProfile1               SnmpAdminString,
    alaDaUNPMacIpPortRuleProfile2               SnmpAdminString,
    alaDaUNPMacIpPortRuleProfile3               SnmpAdminString,
    alaDaUNPMacIpPortRuleIpMaskType             InetAddressType,
    alaDaUNPMacIpPortRuleIpMask                 InetAddress
}

alaDaUNPMacIpPortRuleMacAddr OBJECT-TYPE
    SYNTAX  MacAddress (SIZE(6))
    MAX-ACCESS not-accessible
    STATUS  current
    DESCRIPTION
        "Classification Rule mac Address."
    ::= { alaDaUNPMacIpPortRuleEntry 1 }

alaDaUNPMacIpPortRuleAddrIpType OBJECT-TYPE
    SYNTAX  InetAddressType
    MAX-ACCESS  not-accessible
    STATUS current
    DESCRIPTION
        "The IP address type ."
    ::= { alaDaUNPMacIpPortRuleEntry 2   }

alaDaUNPMacIpPortRuleIpAddr OBJECT-TYPE
    SYNTAX  InetAddress
    MAX-ACCESS  not-accessible
    STATUS  current
    DESCRIPTION
        "The IP network address ."
    ::= { alaDaUNPMacIpPortRuleEntry 3 }

alaDaUNPMacIpPortRuleNum    OBJECT-TYPE
    SYNTAX       InterfaceIndex (1..2147483647)
    MAX-ACCESS    not-accessible
    STATUS        current
    DESCRIPTION
    "Classification Rule Port num."
    ::= { alaDaUNPMacIpPortRuleEntry 4 }

alaDaUNPMacIpPortRuleEdgeProf OBJECT-TYPE
    SYNTAX  SnmpAdminString ( SIZE( 1 .. 32 ) )
    MAX-ACCESS  read-create
    STATUS  deprecated
    DESCRIPTION
        "The edge profile name in the User Network Profile Table to be
         applied."
    ::= { alaDaUNPMacIpPortRuleEntry 5 }

alaDaUNPMacIpPortRuleRowStatus OBJECT-TYPE
    SYNTAX        RowStatus
    MAX-ACCESS    read-create
    STATUS        current
    DESCRIPTION
        "The status of this table entry."
    ::= { alaDaUNPMacIpPortRuleEntry 6 }

alaDaUNPMacIpPortRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPMacIpPortRuleEntry 7 }

alaDaUNPMacIpPortRuleProfile1 OBJECT-TYPE
    SYNTAX  SnmpAdminString ( SIZE( 1 .. 32 ) )
    MAX-ACCESS  read-create
    STATUS  current
    DESCRIPTION
        "The profile name in the User Network Profile Table to be
         applied."
    ::= { alaDaUNPMacIpPortRuleEntry 8 }

alaDaUNPMacIpPortRuleProfile2 OBJECT-TYPE
    SYNTAX  SnmpAdminString ( SIZE( 1 .. 32 ) )
    MAX-ACCESS  read-create
    STATUS  current
    DESCRIPTION
        "The profile name in the User Network Profile Table to be
         applied."
    ::= { alaDaUNPMacIpPortRuleEntry 9 }

alaDaUNPMacIpPortRuleProfile3 OBJECT-TYPE
    SYNTAX  SnmpAdminString ( SIZE( 1 .. 32 ) )
    MAX-ACCESS  read-create
    STATUS  current
    DESCRIPTION
        "The profile name in the User Network Profile Table to be
         applied."
    ::= { alaDaUNPMacIpPortRuleEntry 10 }

alaDaUNPMacIpPortRuleIpMaskType OBJECT-TYPE
    SYNTAX  InetAddressType
                {
                    ipv4(1),
                    ipv6(2)
                }
    MAX-ACCESS  read-create
    STATUS  current
    DESCRIPTION
        "The IP mask type. This field is mandatory."
    ::= { alaDaUNPMacIpPortRuleEntry 11 }

alaDaUNPMacIpPortRuleIpMask OBJECT-TYPE
    SYNTAX  InetAddress (SIZE (4|16))
    MAX-ACCESS  read-create
    STATUS  current
    DESCRIPTION
        "The IP network mask applying to the IP network address. This field is mandatory."
    ::= { alaDaUNPMacIpPortRuleEntry 12 }

--------------------------------------------
-- Mac , Groupid based classification table
-- This table is deprecated as part of unification
--------------------------------------------

alaDaUNPMacGroupRuleTable  OBJECT-TYPE
    SYNTAX  SEQUENCE OF AlaDaUNPMacGroupRuleEntry
    MAX-ACCESS  not-accessible
    STATUS  deprecated
    DESCRIPTION
    "Mac Address & Group classification table ."
    ::= { alaIND1DaMIBObjects 32 }

alaDaUNPMacGroupRuleEntry OBJECT-TYPE
    SYNTAX  AlaDaUNPMacGroupRuleEntry
    MAX-ACCESS  not-accessible
    STATUS  deprecated
    DESCRIPTION
        " Mac & group  based  classification rule ."
    INDEX {
               alaDaUNPMacGroupRuleAddr,
               alaDaUNPMacGroupRuleId
          }
    ::= { alaDaUNPMacGroupRuleTable 1 }

AlaDaUNPMacGroupRuleEntry ::= SEQUENCE  {
    alaDaUNPMacGroupRuleAddr       MacAddress,
    alaDaUNPMacGroupRuleId         Integer32,
    alaDaUNPMacGroupRuleEdgeProf   SnmpAdminString,
    alaDaUNPMacGroupRuleRowStatus  RowStatus,
    alaDaUNPMacGroupRuleVlanTag    Integer32
}

alaDaUNPMacGroupRuleAddr    OBJECT-TYPE
    SYNTAX  MacAddress(SIZE(6))
    MAX-ACCESS not-accessible
    STATUS  deprecated
    DESCRIPTION
    "Classification Rule mac Address."
    ::= { alaDaUNPMacGroupRuleEntry 1 }

alaDaUNPMacGroupRuleId  OBJECT-TYPE
    SYNTAX       Integer32(0..255)
    MAX-ACCESS    not-accessible
    STATUS        deprecated
    DESCRIPTION
        "Classification Rule Group Id."
    ::= { alaDaUNPMacGroupRuleEntry 2 }

alaDaUNPMacGroupRuleEdgeProf OBJECT-TYPE
    SYNTAX  SnmpAdminString ( SIZE( 1 .. 32 ) )
    MAX-ACCESS  read-create
    STATUS  deprecated
    DESCRIPTION
        "The edge profile name in the User Network Profile Table to be
         applied."
    ::= { alaDaUNPMacGroupRuleEntry 3 }

alaDaUNPMacGroupRuleRowStatus OBJECT-TYPE
    SYNTAX        RowStatus
    MAX-ACCESS    read-create
    STATUS        deprecated
    DESCRIPTION
        "The status of this table entry."
    ::= { alaDaUNPMacGroupRuleEntry 4 }

alaDaUNPMacGroupRuleVlanTag  OBJECT-TYPE
    SYNTAX        Integer32 (0..4094)
    MAX-ACCESS    read-create
    STATUS        deprecated
    DESCRIPTION
    "The vlan tag to be used for classification of tagged pkts.
    Vlan tag of 0 indicates no VLAN is associated."
    ::= { alaDaUNPMacGroupRuleEntry 5 }

--------------------------------------------------------------
-- Ip , Group Classification Table
-- This table is deprecated as part of unification
--------------------------------------------------------------

alaDaUNPIpGroupRuleTable  OBJECT-TYPE
    SYNTAX  SEQUENCE OF AlaDaUNPIpGroupRuleEntry
    MAX-ACCESS  not-accessible
    STATUS  deprecated
    DESCRIPTION
        "Ip Address & Group classification table ."
    ::= { alaIND1DaMIBObjects 33 }

alaDaUNPIpGroupRuleEntry OBJECT-TYPE
    SYNTAX  AlaDaUNPIpGroupRuleEntry
    MAX-ACCESS  not-accessible
    STATUS  deprecated
    DESCRIPTION
     " Ip & Group  based  classification rule ."
     INDEX {
               alaDaUNPIpGroupRuleAddrType,
               alaDaUNPIpGroupRuleAddr,
               alaDaUNPIpGroupRuleNum
           }
     ::= { alaDaUNPIpGroupRuleTable 1 }

AlaDaUNPIpGroupRuleEntry ::= SEQUENCE  {
    alaDaUNPIpGroupRuleAddrType           InetAddressType,
    alaDaUNPIpGroupRuleAddr               InetAddress,
    alaDaUNPIpGroupRuleNum                Integer32,
    alaDaUNPIpGroupRuleEdgeProf           SnmpAdminString,
    alaDaUNPIpGroupRuleRowStatus          RowStatus,
    alaDaUNPIpGroupRuleVlanTag            Integer32
}

alaDaUNPIpGroupRuleAddrType  OBJECT-TYPE
    SYNTAX  InetAddressType
    MAX-ACCESS  not-accessible
    STATUS deprecated
    DESCRIPTION
        "The IP address type ."
    ::= { alaDaUNPIpGroupRuleEntry   1 }

alaDaUNPIpGroupRuleAddr  OBJECT-TYPE
    SYNTAX  InetAddress
    MAX-ACCESS  not-accessible
    STATUS  deprecated
    DESCRIPTION
        "The IP network address ."
    ::= { alaDaUNPIpGroupRuleEntry 2 }

alaDaUNPIpGroupRuleNum  OBJECT-TYPE
    SYNTAX      Integer32(0..255)
    MAX-ACCESS    not-accessible
    STATUS        deprecated
    DESCRIPTION
        "Classification Rule Group num."
    ::= { alaDaUNPIpGroupRuleEntry 3 }

alaDaUNPIpGroupRuleEdgeProf OBJECT-TYPE
    SYNTAX  SnmpAdminString ( SIZE( 1 .. 32 ) )
    MAX-ACCESS  read-create
    STATUS  deprecated
    DESCRIPTION
        "The edge profile name in the User Network Profile Table to be
         applied."
    ::= { alaDaUNPIpGroupRuleEntry 4 }

alaDaUNPIpGroupRuleRowStatus OBJECT-TYPE
    SYNTAX        RowStatus
    MAX-ACCESS    read-create
    STATUS        deprecated
    DESCRIPTION
        "The status of this table entry."
    ::= { alaDaUNPIpGroupRuleEntry 5 }

alaDaUNPIpGroupRuleVlanTag  OBJECT-TYPE
    SYNTAX        Integer32 (0..4094)
    MAX-ACCESS    read-create
    STATUS        deprecated
    DESCRIPTION
        "The vlan tag to be used for classification of tagged pkts.
         Vlan tag of 0 indicates no VLAN is associated."
    ::= { alaDaUNPIpGroupRuleEntry 6 }

--------------------------------------------------------------
-- Mac , IpAddress, Group Classification Table
-- This table is deprecated as part of unification
--------------------------------------------------------------

alaDaUNPMacIpGroupRuleTable  OBJECT-TYPE
    SYNTAX  SEQUENCE OF AlaDaUNPMacIpGroupRuleEntry
    MAX-ACCESS  not-accessible
    STATUS  deprecated
    DESCRIPTION
        "Mac Address,IP  & Group classification table ."
    ::= { alaIND1DaMIBObjects 34 }

alaDaUNPMacIpGroupRuleEntry OBJECT-TYPE
    SYNTAX  AlaDaUNPMacIpGroupRuleEntry
    MAX-ACCESS  not-accessible
    STATUS  deprecated
    DESCRIPTION
    " Mac Ip & group  based  classification rule entries ."
    INDEX {
              alaDaUNPMacIpGroupRuleMacAddr,
              alaDaUNPMacIpGroupRuleIpAddrType,
              alaDaUNPMacIpGroupRuleIpAddr,
              alaDaUNPMacIpGroupRuleId
          }
    ::= { alaDaUNPMacIpGroupRuleTable 1 }

AlaDaUNPMacIpGroupRuleEntry ::= SEQUENCE  {
    alaDaUNPMacIpGroupRuleMacAddr       MacAddress,
    alaDaUNPMacIpGroupRuleIpAddrType    InetAddressType,
    alaDaUNPMacIpGroupRuleIpAddr        InetAddress,
    alaDaUNPMacIpGroupRuleId            Integer32,
    alaDaUNPMacIpGroupRuleEdgeProf      SnmpAdminString,
    alaDaUNPMacIpGroupRuleRowStatus     RowStatus,
    alaDaUNPMacIpGroupRuleVlanTag       Integer32
}

alaDaUNPMacIpGroupRuleMacAddr    OBJECT-TYPE
    SYNTAX  MacAddress (SIZE(6))
    MAX-ACCESS not-accessible
    STATUS  deprecated
    DESCRIPTION
        "Classification Rule mac Address."
    ::= { alaDaUNPMacIpGroupRuleEntry 1 }

alaDaUNPMacIpGroupRuleIpAddrType OBJECT-TYPE
    SYNTAX  InetAddressType
    MAX-ACCESS  not-accessible
    STATUS deprecated
    DESCRIPTION
        "The IP address type ."
    ::= { alaDaUNPMacIpGroupRuleEntry 2 }

alaDaUNPMacIpGroupRuleIpAddr OBJECT-TYPE
    SYNTAX  InetAddress
    MAX-ACCESS  not-accessible
    STATUS  deprecated
    DESCRIPTION
        "The IP network address ."
    ::= { alaDaUNPMacIpGroupRuleEntry 3 }

alaDaUNPMacIpGroupRuleId OBJECT-TYPE
    SYNTAX       Integer32(0..255)
    MAX-ACCESS    not-accessible
    STATUS        deprecated
    DESCRIPTION
        "Classification Rule Group Id."
    ::= { alaDaUNPMacIpGroupRuleEntry 4 }

alaDaUNPMacIpGroupRuleEdgeProf OBJECT-TYPE
    SYNTAX  SnmpAdminString ( SIZE( 1 .. 32 ) )
    MAX-ACCESS  read-create
    STATUS  deprecated
    DESCRIPTION
        "The edge profile name in the User Network Profile Table to be
        applied."
    ::= { alaDaUNPMacIpGroupRuleEntry 5 }

alaDaUNPMacIpGroupRuleRowStatus OBJECT-TYPE
    SYNTAX        RowStatus
    MAX-ACCESS    read-create
    STATUS        deprecated
    DESCRIPTION
        "The status of this table entry."
    ::= { alaDaUNPMacIpGroupRuleEntry 6 }

alaDaUNPMacIpGroupRuleVlanTag  OBJECT-TYPE
    SYNTAX        Integer32 (0..4094)
    MAX-ACCESS    read-create
    STATUS        deprecated
    DESCRIPTION
        "The vlan tag to be used for classification of tagged pkts.
         Vlan tag of 0 indicates no VLAN is associated."
    ::= { alaDaUNPMacIpGroupRuleEntry 7 }

--------------------------------------------------------------
-- USER Role Table
--------------------------------------------------------------

alaDaUNPUserRoleTable  OBJECT-TYPE
    SYNTAX  SEQUENCE OF AlaDaUNPUserRoleEntry
    MAX-ACCESS  not-accessible
    STATUS  current
    DESCRIPTION
        "User Role Table."
    ::= { alaIND1DaMIBObjects 35 }

alaDaUNPUserRoleEntry OBJECT-TYPE
    SYNTAX   AlaDaUNPUserRoleEntry
    MAX-ACCESS  not-accessible
    STATUS  current
    DESCRIPTION
         " User Role Name  based  rule entry."
    INDEX {   alaDaUNPUserRoleName }
    ::= { alaDaUNPUserRoleTable 1 }

AlaDaUNPUserRoleEntry    ::= SEQUENCE  {
    alaDaUNPUserRoleName                  SnmpAdminString,
    alaDaUNPUserRolePrecedenceNum         Integer32,
    alaDaUNPUserRolePolicyList            SnmpAdminString,
    alaDaUNPUserRoleEdgeProfile           SnmpAdminString, --deprecated
    alaDaUNPUserRoleAuthType              INTEGER,
    alaDaUNPUserRolePostLoginStatus       INTEGER,
    alaDaUNPUserRoleRowStatus             RowStatus,
    alaDaUNPUserRoleKerberosPostLoginStatus     INTEGER,
    alaDaUNPUserRoleProfile1              SnmpAdminString,
    alaDaUNPUserRoleProfile2              SnmpAdminString,
    alaDaUNPUserRoleProfile3              SnmpAdminString
}

alaDaUNPUserRoleName OBJECT-TYPE
    SYNTAX  SnmpAdminString ( SIZE( 1 .. 32 ) )
    MAX-ACCESS  not-accessible
    STATUS  current
    DESCRIPTION
         "User Role Name ."
    ::= { alaDaUNPUserRoleEntry  1 }

alaDaUNPUserRolePrecedenceNum    OBJECT-TYPE
    SYNTAX  Integer32(1..255)
    MAX-ACCESS  read-create
    STATUS  current
    DESCRIPTION
         "User Role Precedence number ."
    DEFVAL { 1 }
    ::= { alaDaUNPUserRoleEntry  2 }

alaDaUNPUserRolePolicyList OBJECT-TYPE
    SYNTAX  SnmpAdminString ( SIZE( 0 .. 32 ) )
    MAX-ACCESS  read-create
    STATUS  current
    DESCRIPTION
         "User Role Policy List Name ."
    ::= { alaDaUNPUserRoleEntry  3 }

alaDaUNPUserRoleEdgeProfile OBJECT-TYPE
    SYNTAX  SnmpAdminString ( SIZE( 0 .. 32 ) )
    MAX-ACCESS  read-create
    STATUS  deprecated
    DESCRIPTION
         "User Role  Edge ProfileName ."
    ::= { alaDaUNPUserRoleEntry  4 }

alaDaUNPUserRoleAuthType OBJECT-TYPE
    SYNTAX        INTEGER {
                      noAuth(0),
                      none(1),
                      dot1x(2),
                      mac(3),
                      dot1xFail(4),
                      macFail(5)
                  }
    MAX-ACCESS   read-create
    STATUS        current
    DESCRIPTION
        "User Rule Auth Type ."
    DEFVAL { none }
    ::= { alaDaUNPUserRoleEntry  5 }

alaDaUNPUserRolePostLoginStatus OBJECT-TYPE
    SYNTAX       INTEGER {
                     enable(1),
                     disable(2)
                 }
    MAX-ACCESS read-create
    STATUS current
    DESCRIPTION
        " Enable/Disable Captive Portal Post Login Status "
    DEFVAL { disable }
    ::= { alaDaUNPUserRoleEntry  6 }

alaDaUNPUserRoleRowStatus    OBJECT-TYPE
    SYNTAX        RowStatus
    MAX-ACCESS    read-create
    STATUS        current
    DESCRIPTION
        "The status of this table entry."
    ::= { alaDaUNPUserRoleEntry 7 }

alaDaUNPUserRoleKerberosPostLoginStatus OBJECT-TYPE
    SYNTAX       INTEGER {
                     enable(1),
                     disable(2)
                 }
    MAX-ACCESS read-create
    STATUS current
    DESCRIPTION
        " Enable/Disable Kerberos Post Login Status "
    DEFVAL { disable }
    ::= { alaDaUNPUserRoleEntry  8 }

alaDaUNPUserRoleProfile1 OBJECT-TYPE
    SYNTAX  SnmpAdminString ( SIZE( 0 .. 32 ) )
    MAX-ACCESS  read-create
    STATUS  current
    DESCRIPTION
         "User Role ProfileName ."
    ::= { alaDaUNPUserRoleEntry 9 }

alaDaUNPUserRoleProfile2 OBJECT-TYPE
    SYNTAX  SnmpAdminString ( SIZE( 0 .. 32 ) )
    MAX-ACCESS  read-create
    STATUS  current
    DESCRIPTION
         "User Role ProfileName ."
    ::= { alaDaUNPUserRoleEntry 10 }

alaDaUNPUserRoleProfile3 OBJECT-TYPE
    SYNTAX  SnmpAdminString ( SIZE( 0 .. 32 ) )
    MAX-ACCESS  read-create
    STATUS  current
    DESCRIPTION
         "User Role ProfileName ."
    ::= { alaDaUNPUserRoleEntry 11 }

--
-- Restricted Role Based Table
--

alaDaUNPRstrctedRoleTable  OBJECT-TYPE
SYNTAX  SEQUENCE OF AlaDaUNPRstrctedRoleEntry
MAX-ACCESS  not-accessible
STATUS  current
DESCRIPTION
"Restricted  Role Table."
::= { alaIND1DaMIBObjects 36 }

alaDaUNPRstrctedRoleEntry OBJECT-TYPE
SYNTAX  AlaDaUNPRstrctedRoleEntry
MAX-ACCESS  not-accessible
STATUS  current
DESCRIPTION
 " Entry identified by Restricted Role ."
INDEX {   alaDaUNPRstrctedRoleType }
::= { alaDaUNPRstrctedRoleTable 1 }

AlaDaUNPRstrctedRoleEntry ::= SEQUENCE
{
alaDaUNPRstrctedRoleType             INTEGER,
alaDaUNPRstrctedRolePolicyList       SnmpAdminString,
alaDaUNPRstrctedRoleRowStatus        RowStatus
}
alaDaUNPRstrctedRoleType    OBJECT-TYPE
SYNTAX        INTEGER
      {
    unauthorized(1),
    hic(2),
    qmr(3),
    blacklist(4),
    cpPreLogin(5),
    kerberosPreLogin(6)
      }
MAX-ACCESS   not-accessible
STATUS        current
DESCRIPTION
"Unp Restricted Roles ."
::= { alaDaUNPRstrctedRoleEntry 1}

alaDaUNPRstrctedRolePolicyList OBJECT-TYPE
SYNTAX  SnmpAdminString ( SIZE( 1 .. 32 ) )
MAX-ACCESS  read-create
STATUS  current
DESCRIPTION
 "Restricted  Role Policy List Name ."
::= { alaDaUNPRstrctedRoleEntry 2 }

alaDaUNPRstrctedRoleRowStatus OBJECT-TYPE
SYNTAX        RowStatus
MAX-ACCESS    read-create
STATUS        current
DESCRIPTION
"The status of this table entry."
::= { alaDaUNPRstrctedRoleEntry 3 }

--
-- VLAN/UNP Mapping Table
-- This table is deprecated as part of unification
--

alaDaUNPVlanMapTable  OBJECT-TYPE
    SYNTAX  SEQUENCE OF AlaDaUNPVlanMapEntry
    MAX-ACCESS  not-accessible
    STATUS  deprecated
    DESCRIPTION
        "Vlan/Unp Mapping Table ."
    ::= { alaIND1DaMIBObjects 37 }

alaDaUNPVlanMapEntry OBJECT-TYPE
    SYNTAX  AlaDaUNPVlanMapEntry
    MAX-ACCESS  not-accessible
    STATUS  deprecated
    DESCRIPTION
        " Entry identified by Edge Profile Name  ."
    INDEX {   alaDaUNPVlanMapEdgeProf }
    ::= { alaDaUNPVlanMapTable 1 }

AlaDaUNPVlanMapEntry ::= SEQUENCE {
    alaDaUNPVlanMapEdgeProf         SnmpAdminString,
    alaDaUNPVlanMapIdent            Integer32,
    alaDaUNPVlanMapRowStatus        RowStatus
}

alaDaUNPVlanMapEdgeProf OBJECT-TYPE
    SYNTAX  SnmpAdminString ( SIZE( 1 .. 32 ) )
    MAX-ACCESS  not-accessible
    STATUS  deprecated
    DESCRIPTION
        "Edge Profile  Name ."
    ::= { alaDaUNPVlanMapEntry 1 }

alaDaUNPVlanMapIdent OBJECT-TYPE
    SYNTAX        Integer32(0..4094)
    MAX-ACCESS    read-create
    STATUS        deprecated
    DESCRIPTION
        "Vlan Identifier which is mapped to Edge profile ."
    DEFVAL { 0 }
    ::= { alaDaUNPVlanMapEntry 2}

alaDaUNPVlanMapRowStatus OBJECT-TYPE
    SYNTAX        RowStatus
    MAX-ACCESS    read-create
    STATUS        deprecated
    DESCRIPTION
        "The status of this table entry."
    ::= { alaDaUNPVlanMapEntry 3 }

--
-- Group Id table
--

alaDaUnpGroupIdTable OBJECT-TYPE
SYNTAX        SEQUENCE OF AlaDaUnpGroupIdEntry
MAX-ACCESS    not-accessible
STATUS        deprecated
DESCRIPTION
    "This table creates and deletes the UNP group within a switch."
::= { alaIND1DaMIBObjects 38 }

alaDaUnpGroupIdEntry OBJECT-TYPE
SYNTAX        AlaDaUnpGroupIdEntry
MAX-ACCESS    not-accessible
STATUS        deprecated
DESCRIPTION
    "UNP GroupId entry"
INDEX { alaDaUnpGroupId }
::= { alaDaUnpGroupIdTable 1 }

AlaDaUnpGroupIdEntry ::= SEQUENCE
{
    alaDaUnpGroupId        Integer32,
    alaDaUnpGroupDescription SnmpAdminString,
    alaDaUnpGroupIdRowStatus RowStatus
}

alaDaUnpGroupId OBJECT-TYPE
SYNTAX        Integer32 (0..255)
MAX-ACCESS    not-accessible
STATUS        deprecated
DESCRIPTION
    "Unp Group Id."
::= { alaDaUnpGroupIdEntry 1 }

alaDaUnpGroupDescription OBJECT-TYPE
SYNTAX        SnmpAdminString (SIZE(0..128))
MAX-ACCESS    read-create
STATUS        deprecated
DESCRIPTION
    "Unp Group Id."
::= { alaDaUnpGroupIdEntry 2 }

alaDaUnpGroupIdRowStatus OBJECT-TYPE
SYNTAX        RowStatus
MAX-ACCESS    read-create
STATUS        deprecated
DESCRIPTION
    "The status of this table entry."
::= { alaDaUnpGroupIdEntry 3 }

--
-- Edge flush Table
--
alaDaUNPEdgeFlushTable OBJECT-TYPE
SYNTAX      SEQUENCE OF AlaDaUNPEdgeFlushEntry
MAX-ACCESS  not-accessible
STATUS      current
DESCRIPTION
"Port, LinkAgg, Mac, Edge User Type Based Flush Table ."
::= { alaIND1DaMIBObjects 39 }

alaDaUNPEdgeFlushEntry OBJECT-TYPE
SYNTAX      AlaDaUNPEdgeFlushEntry
MAX-ACCESS  not-accessible
STATUS      current
DESCRIPTION
"One entry  to flush edge users on the basis of user criteria."
INDEX { alaDaUNPEdgeFlushIndex }
::= { alaDaUNPEdgeFlushTable 1 }


AlaDaUNPEdgeFlushEntry ::= SEQUENCE
{
alaDaUNPEdgeFlushIndex Integer32,
alaDaUNPEdgeFlushPortLow   InterfaceIndex,
alaDaUNPEdgeFlushPortHigh   InterfaceIndex,
alaDaUNPEdgeFlushType	INTEGER,
alaDaUNPEdgrFlushMac	MacAddress,
alaDaUNPEdgeFlushComplete INTEGER,
alaDaUNPEdgeFlushProfile  SnmpAdminString
}

alaDaUNPEdgeFlushIndex OBJECT-TYPE
SYNTAX      Integer32(1)
MAX-ACCESS  not-accessible
STATUS      current
DESCRIPTION
" Interface index ."
::= { alaDaUNPEdgeFlushEntry 1 }

alaDaUNPEdgeFlushPortLow OBJECT-TYPE
SYNTAX     InterfaceIndex
MAX-ACCESS  read-write
STATUS      current
DESCRIPTION
" Edge Flush Port Criteria ."
::= { alaDaUNPEdgeFlushEntry 2 }

alaDaUNPEdgeFlushPortHigh OBJECT-TYPE
SYNTAX     InterfaceIndex
MAX-ACCESS  read-write
STATUS      current
DESCRIPTION
" Edge Flush Port Criteria ."
::= { alaDaUNPEdgeFlushEntry 3 }

alaDaUNPEdgeFlushType OBJECT-TYPE
SYNTAX     INTEGER { noAuth(1), onex(2), mac(3), none(4) }
MAX-ACCESS  read-write
STATUS      current
DESCRIPTION
" Edge Flush Type criteria ."
::= { alaDaUNPEdgeFlushEntry 4 }

alaDaUNPEdgrFlushMac OBJECT-TYPE
SYNTAX     MacAddress(SIZE(6))
MAX-ACCESS  read-write
STATUS      current
DESCRIPTION
" Edge Flush MAC criteria ."
::= { alaDaUNPEdgeFlushEntry 5 }

alaDaUNPEdgeFlushComplete OBJECT-TYPE
SYNTAX     INTEGER { no(1), all(2) }
MAX-ACCESS  read-write
STATUS      current
DESCRIPTION
" To flush all Edge Users ."
DEFVAL { no }
::= { alaDaUNPEdgeFlushEntry 6 }

alaDaUNPEdgeFlushProfile OBJECT-TYPE
SYNTAX      SnmpAdminString ( SIZE( 0 .. 32 ) )
MAX-ACCESS  read-write
STATUS      current
DESCRIPTION
" To flush all Edge Users in the given Edge-Profile"
::= { alaDaUNPEdgeFlushEntry 7 }

-----------------------------------------------
-- MAC Based classification rule --
-- This table is deprecated as part of unification
-----------------------------------------------

alaDaUNPMacRulesTable  OBJECT-TYPE
    SYNTAX  SEQUENCE OF AlaDaUNPMacRulesEntry
    MAX-ACCESS  not-accessible
    STATUS  deprecated
    DESCRIPTION
        "Mac Address classification table ."
    ::= { alaIND1DaMIBObjects 40 }

alaDaUNPMacRulesEntry OBJECT-TYPE
    SYNTAX  AlaDaUNPMacRulesEntry
    MAX-ACCESS  not-accessible
    STATUS  deprecated
    DESCRIPTION
         " Mac based  classification rule ."
    INDEX {  alaDaUNPMacRulesMacAddr  }
    ::= { alaDaUNPMacRulesTable 1 }

AlaDaUNPMacRulesEntry ::= SEQUENCE   {
    alaDaUNPMacRulesMacAddr            MacAddress,
    alaDaUNPMacRulesEdgeProf           SnmpAdminString,
    alaDaUNPMacRulesRowStatus           RowStatus,
    alaDaUNPMacRulesVlanTag             Integer32
}

alaDaUNPMacRulesMacAddr OBJECT-TYPE
    SYNTAX  MacAddress(SIZE(6))
    MAX-ACCESS not-accessible
    STATUS  deprecated
    DESCRIPTION
        "Classification Rule mac Address."
    ::= { alaDaUNPMacRulesEntry 1 }

alaDaUNPMacRulesEdgeProf OBJECT-TYPE
    SYNTAX  SnmpAdminString ( SIZE( 1 .. 32 ) )
    MAX-ACCESS  read-create
    STATUS  deprecated
    DESCRIPTION
         "The edge profile name in the User Network Profile Table to be
          applied."
    ::= { alaDaUNPMacRulesEntry 2 }

alaDaUNPMacRulesRowStatus OBJECT-TYPE
    SYNTAX        RowStatus
    MAX-ACCESS    read-create
    STATUS        deprecated
    DESCRIPTION
        "The status of this table entry."
    ::= { alaDaUNPMacRulesEntry 3 }

alaDaUNPMacRulesVlanTag  OBJECT-TYPE
    SYNTAX  Integer32 (0..4094)
    MAX-ACCESS  read-create
    STATUS  deprecated
    DESCRIPTION
         "The vlan tag to be used for classification of tagged pkts.
         Vlan tag of 0 indicates no VLAN is associated."
    ::= { alaDaUNPMacRulesEntry 4 }

-----------------------------------------------
-- DA Mac Range table  --
-- This table is deprecated as part of unification
-----------------------------------------------

alaDaUNPMacRangeTable  OBJECT-TYPE
    SYNTAX  SEQUENCE OF AlaDaUNPMacRangeEntry
    MAX-ACCESS  not-accessible
    STATUS  deprecated
    DESCRIPTION
        "Mac Address classification table ."
    ::= { alaIND1DaMIBObjects 41 }

alaDaUNPMacRangeEntry OBJECT-TYPE
    SYNTAX  AlaDaUNPMacRangeEntry
    MAX-ACCESS  not-accessible
    STATUS  deprecated
    DESCRIPTION
     " Mac based  classification rule ."
    INDEX { alaDaUNPMacRangeStartMacAddr }
    ::= { alaDaUNPMacRangeTable 1 }

AlaDaUNPMacRangeEntry ::= SEQUENCE   {
    alaDaUNPMacRangeStartMacAddr       MacAddress,
    alaDaUNPMacRangeEndMacAddr         MacAddress,
    alaDaUNPMacRangeEdgeProf           SnmpAdminString,
    alaDaUNPMacRangeRowStatus          RowStatus,
    alaDaUNPMacRangeVlanTag            Integer32
}

alaDaUNPMacRangeStartMacAddr OBJECT-TYPE
    SYNTAX  MacAddress(SIZE(6))
    MAX-ACCESS not-accessible
    STATUS  deprecated
    DESCRIPTION
        "Classification Rule start mac Address."
    ::= { alaDaUNPMacRangeEntry 1 }

alaDaUNPMacRangeEndMacAddr OBJECT-TYPE
    SYNTAX  MacAddress(SIZE(6))
    MAX-ACCESS read-create
    STATUS  deprecated
    DESCRIPTION
        "Classification Rule end mac Address."
    ::= { alaDaUNPMacRangeEntry 2 }

alaDaUNPMacRangeEdgeProf OBJECT-TYPE
    SYNTAX  SnmpAdminString ( SIZE( 1 .. 32 ) )
    MAX-ACCESS  read-create
    STATUS  deprecated
    DESCRIPTION
     "The edge profile name in the User Network Profile Table to be
      applied."
    ::= { alaDaUNPMacRangeEntry 3 }

alaDaUNPMacRangeRowStatus OBJECT-TYPE
    SYNTAX        RowStatus
    MAX-ACCESS    read-create
    STATUS        deprecated
    DESCRIPTION
        "The status of this table entry."
    ::= { alaDaUNPMacRangeEntry 4 }

alaDaUNPMacRangeVlanTag  OBJECT-TYPE
    SYNTAX  Integer32 (0..4094)
    MAX-ACCESS  read-create
    STATUS  deprecated
    DESCRIPTION
         "The vlan tag to be used for classification of tagged pkts.
         Vlan tag of 0 indicates no VLAN is associated."
    ::= { alaDaUNPMacRangeEntry 5 }

------------------------------------------------
-- DA IP mask rule  --
-- This table is deprecated as part of unification
------------------------------------------------

alaDaUNPIpMaskRuleTable  OBJECT-TYPE
    SYNTAX  SEQUENCE OF AlaDaUNPIpMaskRuleEntry
    MAX-ACCESS  not-accessible
    STATUS  deprecated
    DESCRIPTION
        "Ip Address & port classification table ."
    ::= { alaIND1DaMIBObjects 42 }

alaDaUNPIpMaskRuleEntry OBJECT-TYPE
    SYNTAX  AlaDaUNPIpMaskRuleEntry
    MAX-ACCESS  not-accessible
    STATUS  deprecated
    DESCRIPTION
     " Ip & Mask  based  classification rule ."
    INDEX {
              alaDaUNPIpMaskRuleAddrType,
              alaDaUNPIpMaskRuleAddr,
              alaDaUNPIpMaskRuleMaskType,
              alaDaUNPIpMaskRuleMask
          }
    ::= { alaDaUNPIpMaskRuleTable 1 }

AlaDaUNPIpMaskRuleEntry ::= SEQUENCE  {
    alaDaUNPIpMaskRuleAddrType           InetAddressType,
    alaDaUNPIpMaskRuleAddr               InetAddress,
    alaDaUNPIpMaskRuleMaskType           InetAddressType,
    alaDaUNPIpMaskRuleMask               InetAddress,
    alaDaUNPIpMaskRuleEdgeProf           SnmpAdminString,
    alaDaUNPIpMaskRuleRowStatus          RowStatus,
    alaDaUNPIpMaskRuleVlanTag            Integer32
}

alaDaUNPIpMaskRuleAddrType  OBJECT-TYPE
    SYNTAX  InetAddressType
    MAX-ACCESS  not-accessible
    STATUS deprecated
    DESCRIPTION
        "The IP address type ."
    ::= { alaDaUNPIpMaskRuleEntry   1 }

alaDaUNPIpMaskRuleAddr  OBJECT-TYPE
    SYNTAX  InetAddress
    MAX-ACCESS  not-accessible
    STATUS  deprecated
    DESCRIPTION
        "The IP network address ."
    ::= { alaDaUNPIpMaskRuleEntry 2 }

alaDaUNPIpMaskRuleMaskType OBJECT-TYPE
    SYNTAX  InetAddressType
    MAX-ACCESS  not-accessible
    STATUS deprecated
    DESCRIPTION
        "The IP mask type ."
    ::= { alaDaUNPIpMaskRuleEntry   3 }

alaDaUNPIpMaskRuleMask OBJECT-TYPE
    SYNTAX       InetAddress
    MAX-ACCESS    not-accessible
    STATUS        deprecated
    DESCRIPTION
        "The IP network mask."
    ::= { alaDaUNPIpMaskRuleEntry 4 }

alaDaUNPIpMaskRuleEdgeProf OBJECT-TYPE
    SYNTAX  SnmpAdminString ( SIZE( 1 .. 32 ) )
    MAX-ACCESS  read-create
    STATUS  deprecated
    DESCRIPTION
         "The edge profile name in the User Network Profile Table to be
          applied."
    ::= { alaDaUNPIpMaskRuleEntry 5 }

alaDaUNPIpMaskRuleRowStatus OBJECT-TYPE
    SYNTAX        RowStatus
    MAX-ACCESS    read-create
    STATUS        deprecated
    DESCRIPTION
        "The status of this table entry."
    ::= { alaDaUNPIpMaskRuleEntry 6 }

alaDaUNPIpMaskRuleVlanTag  OBJECT-TYPE
    SYNTAX  Integer32 (0..4094)
    MAX-ACCESS  read-create
    STATUS  deprecated
    DESCRIPTION
         "The vlan tag to be used for classification of tagged pkts.
         Vlan tag of 0 indicates no VLAN is associated."
    ::= { alaDaUNPIpMaskRuleEntry 7 }

------------------------------------------------------------
-- QMR related Config  --
------------------------------------------------------------

    alaDaQMRMIBObjects    OBJECT IDENTIFIER ::= { alaIND1DaMIBObjects 43 }

    alaDaQMRGlobalConfig   OBJECT IDENTIFIER ::= { alaDaQMRMIBObjects 1 }

    alaDaQMRPage OBJECT-TYPE
        SYNTAX        INTEGER {enable (1), disable (2)}
        MAX-ACCESS    read-write
        STATUS        current
        DESCRIPTION   "Flag to indicate whether to send back a quarantined page
		      when a client is quarantined but a remediation URL is not specified."
        DEFVAL { disable }
        ::= { alaDaQMRGlobalConfig 1 }

    alaDaQMRPath OBJECT-TYPE
        SYNTAX        SnmpAdminString ( SIZE( 0 .. 255 ) )
        MAX-ACCESS    read-write
        STATUS        current
        DESCRIPTION   "Default path for remediation server redirect."
        ::= { alaDaQMRGlobalConfig 2 }

    alaDaQMRCustomHttpProxyPort OBJECT-TYPE
        SYNTAX        Integer32(0|1025 .. 65535)
        MAX-ACCESS    read-write
        STATUS        current
        DESCRIPTION
        "The custom HTTP port for QoS to intercept the host's initial HTTP request.
        If set to 0 then custom HTTP port will be reset to its default value 8080."
   	DEFVAL { 8080 }
        ::= { alaDaQMRGlobalConfig 3 }

    alaDaQMRPolicyList OBJECT-TYPE
        SYNTAX        SnmpAdminString ( SIZE( 0 .. 32) )
        MAX-ACCESS    read-write
        STATUS        current
        DESCRIPTION   "The name of the policy associated with QMR."
        ::= { alaDaQMRGlobalConfig 4 }


--  QMR Allowed IP Address Table MIB --

    alaDaQMRAllowedTable OBJECT-TYPE
        SYNTAX        SEQUENCE OF AlaDaQMRAllowedEntry
        MAX-ACCESS    not-accessible
        STATUS        current
        DESCRIPTION   "This table shows the list of IP addresses the host can communicate with
       		      when it is in quarantined state."
        ::= { alaDaQMRMIBObjects 2 }

    alaDaQMRAllowedEntry OBJECT-TYPE
        SYNTAX        AlaDaQMRAllowedEntry
        MAX-ACCESS    not-accessible
        STATUS        current
        DESCRIPTION   "Entry of the IP address the host can communicate with
		      when it is in quarantined state.."
        INDEX     { alaDaQMRAllowedName }
        ::= { alaDaQMRAllowedTable 1 }

    AlaDaQMRAllowedEntry ::= SEQUENCE
        {
	      alaDaQMRAllowedName		SnmpAdminString,
              alaDaQMRAllowedIpAddrType  	InetAddressType,
              alaDaQMRAllowedIpAddr		InetAddress,
              alaDaQMRAllowedIpMaskType         InetAddressType,
              alaDaQMRAllowedIpMask             InetAddress,
	      alaDaQMRAllowedRowStatus          RowStatus
        }

    alaDaQMRAllowedName OBJECT-TYPE
	SYNTAX         SnmpAdminString ( SIZE( 0 .. 32) )
	MAX-ACCESS     not-accessible
	STATUS         current
	DESCRIPTION    "Allowed name."
	::= { alaDaQMRAllowedEntry 1 }

    alaDaQMRAllowedIpAddrType OBJECT-TYPE
        SYNTAX         InetAddressType
        MAX-ACCESS    read-create
        STATUS        current
        DESCRIPTION   "IP address type of the IP Adddress that is allowed."
        ::= { alaDaQMRAllowedEntry 2 }

    alaDaQMRAllowedIpAddr OBJECT-TYPE
        SYNTAX        InetAddress(SIZE(4|16))
        MAX-ACCESS    read-create
        STATUS        current
        DESCRIPTION   "The IP address that is allowed to access."
        ::= { alaDaQMRAllowedEntry 3 }

    alaDaQMRAllowedIpMaskType OBJECT-TYPE
        SYNTAX        InetAddressType
        MAX-ACCESS    read-create
        STATUS        current
        DESCRIPTION   "IP mask type of the allowed entry."
         ::= { alaDaQMRAllowedEntry 4 }

    alaDaQMRAllowedIpMask OBJECT-TYPE
        SYNTAX        InetAddress(SIZE(4|16))
        MAX-ACCESS    read-create
        STATUS        current
        DESCRIPTION   "IP Mask of the allowed entry."
        DEFVAL      { 'FFFFFFFF'H }
        ::= { alaDaQMRAllowedEntry 5 }

    alaDaQMRAllowedRowStatus OBJECT-TYPE
        SYNTAX        RowStatus
        MAX-ACCESS    read-create
        STATUS        current
        DESCRIPTION   "The status of this table entry."
        ::= { alaDaQMRAllowedEntry 6 }

--
-- Definition of Validity Period Table

alaDaUNPValidityPeriodTable OBJECT-TYPE
  SYNTAX      SEQUENCE OF AlaDaUNPValidityPeriodEntry
  MAX-ACCESS  not-accessible
  STATUS      current
  DESCRIPTION "Table of UNP ValidityPeriod definitions"
  ::= { alaIND1DaMIBObjects 44 }

alaDaUNPValidityPeriodEntry OBJECT-TYPE
  SYNTAX      AlaDaUNPValidityPeriodEntry
  MAX-ACCESS  not-accessible
  STATUS      current
  DESCRIPTION "Definition of UNP ValidityPeriod"
  INDEX {
    alaDaUNPValidityPeriodName
  }
  ::= { alaDaUNPValidityPeriodTable 1 }

AlaDaUNPValidityPeriodEntry ::= SEQUENCE
{
  alaDaUNPValidityPeriodName                                SnmpAdminString,
  alaDaUNPValidityPeriodDays                                Integer32,
  alaDaUNPValidityPeriodDaysStatus                          INTEGER,
  alaDaUNPValidityPeriodMonths                              Integer32,
  alaDaUNPValidityPeriodMonthsStatus                        INTEGER,
  alaDaUNPValidityPeriodHour                                SnmpAdminString,
  alaDaUNPValidityPeriodHourStatus                          INTEGER,
  alaDaUNPValidityPeriodEndHour                             SnmpAdminString,
  alaDaUNPValidityPeriodInterval                            SnmpAdminString,
  alaDaUNPValidityPeriodIntervalStatus                      INTEGER,
  alaDaUNPValidityPeriodEndInterval                         SnmpAdminString,
  alaDaUNPValidityPeriodTimezone                            INTEGER,
  alaDaUNPValidityPeriodTimezoneStatus                      INTEGER,
  alaDaUNPValidityPeriodActiveStatus                        INTEGER,
  alaDaUNPValidityPeriodRowStatus                           RowStatus
}

alaDaUNPValidityPeriodName OBJECT-TYPE
  SYNTAX      SnmpAdminString (SIZE(1..32))
  MAX-ACCESS  not-accessible
  STATUS      current
  DESCRIPTION "Name of validity period"
  ::= { alaDaUNPValidityPeriodEntry 1 }

alaDaUNPValidityPeriodDays OBJECT-TYPE
  SYNTAX      Integer32
  MAX-ACCESS  read-create
  STATUS      current
  DESCRIPTION "Bitfield for each day of the week this validity period
  is active.  Monday is least significant, Sunday is most significant."
  ::= { alaDaUNPValidityPeriodEntry 2 }

alaDaUNPValidityPeriodDaysStatus OBJECT-TYPE
  SYNTAX      INTEGER {
    enabled (1),
    disabled (2)
  }
  MAX-ACCESS  read-create
  STATUS      current
  DESCRIPTION "Status field indicating whether the validity period
  has specific active days of the month."
  DEFVAL      { disabled }
  ::= { alaDaUNPValidityPeriodEntry 3 }

alaDaUNPValidityPeriodMonths OBJECT-TYPE
  SYNTAX      Integer32
  MAX-ACCESS  read-create
  STATUS      current
  DESCRIPTION "Bitfield for each month this validity period
  is active.  January is least significant. Decemeber
  is most significant."
  ::= { alaDaUNPValidityPeriodEntry 4 }

alaDaUNPValidityPeriodMonthsStatus OBJECT-TYPE
  SYNTAX      INTEGER {
    enabled (1),
    disabled (2)
  }
  MAX-ACCESS  read-create
  STATUS      current
  DESCRIPTION "Status field indicating whether the validity period
  has specific active days of the week."
  DEFVAL      { disabled }
  ::= { alaDaUNPValidityPeriodEntry 5 }

alaDaUNPValidityPeriodHour OBJECT-TYPE
  SYNTAX      SnmpAdminString (SIZE(0..7))
  MAX-ACCESS  read-create
  STATUS      current
  DESCRIPTION "Time of day this period becomes active.
  Format is 'hh:mm'"
  ::= { alaDaUNPValidityPeriodEntry 6 }

alaDaUNPValidityPeriodHourStatus OBJECT-TYPE
  SYNTAX      INTEGER {
    enabled (1),
    disabled (2)
  }
  MAX-ACCESS  read-create
  STATUS      current
  DESCRIPTION "Status field indicating whether the validity period
  has specific active hours of the day."
  DEFVAL      { disabled }
  ::= { alaDaUNPValidityPeriodEntry 7 }

alaDaUNPValidityPeriodEndHour OBJECT-TYPE
  SYNTAX      SnmpAdminString (SIZE(0..7))
  MAX-ACCESS  read-create
  STATUS      current
  DESCRIPTION "Time of day this period becomes inactive.
  Format is 'hh:mm'"
  ::= { alaDaUNPValidityPeriodEntry 8 }

alaDaUNPValidityPeriodInterval OBJECT-TYPE
  SYNTAX      SnmpAdminString (SIZE(0..19))
  MAX-ACCESS  read-create
  STATUS      current
  DESCRIPTION "Date/time when the validity period begins.
  Format is 'mm/dd/yyyy hh:mm'"
  ::= { alaDaUNPValidityPeriodEntry 9 }

  alaDaUNPValidityPeriodIntervalStatus OBJECT-TYPE
  SYNTAX      INTEGER {
    enabled (1),
    disabled (2)
  }
  MAX-ACCESS  read-create
  STATUS      current
  DESCRIPTION "Status field indicating whether the validity period
  has a specific active date-time interval."
  DEFVAL      { disabled }
  ::= { alaDaUNPValidityPeriodEntry 10 }

alaDaUNPValidityPeriodEndInterval OBJECT-TYPE
  SYNTAX      SnmpAdminString (SIZE(0..19))
  MAX-ACCESS  read-create
  STATUS      current
  DESCRIPTION "Date/time when the validity period ends.
  Format is 'mm/dd/yyyy hh:mm'"
  ::= { alaDaUNPValidityPeriodEntry 11 }

alaDaUNPValidityPeriodTimezone OBJECT-TYPE
SYNTAX      INTEGER {
	     nzst (1),
	     zp11 (2),
	     aest (3),
	     gst (4),
	     acst (5),
	     kst (6),
	     jst (7),
	     awst (8),
	     zp8 (9),
	     zp7 (10),
	     zp6 (11),
	     ist (12),
	     zp5 (13),
	     zp4 (14),
	     msk (15),
	     eet (16),
	     cet (17),
	     met (18),
	     bst (19),
	     wat (20),
	     utc (21),
	     gmt (22),
	     wet (23),
	     zm2 (24),
	     zm3 (25),
	     nst (26),
	     ast (27),
	     astcam (28),
	     est (29),
	     estcam (30),
	     cst (31),
	     cstcam (32),
	     mst (33),
	     mstcam (34),
	     pst (35),
	     pstcam (36),
	     akst (37),
	     hst (38),
	     zm11 (39)
	}
  MAX-ACCESS  read-create
  STATUS      current
  DESCRIPTION "Timezone in which the policy's time has
  to be interpreted."
  ::= { alaDaUNPValidityPeriodEntry 12 }

alaDaUNPValidityPeriodTimezoneStatus OBJECT-TYPE
  SYNTAX      INTEGER {
    enabled (1),
    disabled (2)
  }
  MAX-ACCESS  read-create
  STATUS      current
  DESCRIPTION "Status field indicating whether the validity period
  has specific timezone enabled."
  DEFVAL      { disabled }
  ::= { alaDaUNPValidityPeriodEntry 13 }

  alaDaUNPValidityPeriodActiveStatus OBJECT-TYPE
  SYNTAX      INTEGER {
    active(1),
    inactive(2)
  }
  MAX-ACCESS  read-only
  STATUS      current
  DESCRIPTION "Status field indicating whether the validity period
  is currently active in the system so that Access Guardian will
  utilize it for Time-based Policy checks."
  DEFVAL      { inactive }
  ::= { alaDaUNPValidityPeriodEntry 14 }

  alaDaUNPValidityPeriodRowStatus OBJECT-TYPE
  SYNTAX      RowStatus
  MAX-ACCESS  read-create
  STATUS      current
  DESCRIPTION "Used to create/delete validity periods according
  to the RowStatus convention"
  ::= { alaDaUNPValidityPeriodEntry 15 }

--
-- Definition of Location Policy Table
--

alaDaUNPLocationPolicyTable OBJECT-TYPE
  SYNTAX      SEQUENCE OF AlaDaUNPLocationPolicyEntry
  MAX-ACCESS  not-accessible
  STATUS      current
  DESCRIPTION "Table of UNP Location Policy definitions"
  ::= { alaIND1DaMIBObjects 45 }

alaDaUNPLocationPolicyEntry OBJECT-TYPE
  SYNTAX      AlaDaUNPLocationPolicyEntry
  MAX-ACCESS  not-accessible
  STATUS      current
  DESCRIPTION "Definition of UNP Location Policy"
  INDEX {
    alaDaUNPLocationPolicyName
  }
  ::= { alaDaUNPLocationPolicyTable 1 }

AlaDaUNPLocationPolicyEntry ::=
SEQUENCE
{
  alaDaUNPLocationPolicyName                                SnmpAdminString,
  alaDaUNPLocationPolicyPort                                InterfaceIndex,
  alaDaUNPLocationPolicyPortHigh                            InterfaceIndex,
  alaDaUNPLocationPolicyPortStatus                          INTEGER,
  alaDaUNPLocationPolicySystemName                          SnmpAdminString,
  alaDaUNPLocationPolicySystemLocation                      SnmpAdminString,
  alaDaUNPLocationPolicyRowStatus                           RowStatus
}

alaDaUNPLocationPolicyName OBJECT-TYPE
  SYNTAX      SnmpAdminString (SIZE(1..32))
  MAX-ACCESS  not-accessible
  STATUS      current
  DESCRIPTION "Name of the Location Policy"
  ::= { alaDaUNPLocationPolicyEntry 1 }

  alaDaUNPLocationPolicyPort OBJECT-TYPE
  SYNTAX      InterfaceIndex
  MAX-ACCESS  read-create
  STATUS      current
  DESCRIPTION "Specifies the port criterion"
  ::= { alaDaUNPLocationPolicyEntry 2 }

  alaDaUNPLocationPolicyPortHigh OBJECT-TYPE
  SYNTAX      InterfaceIndex
  MAX-ACCESS  read-create
  STATUS      current
  DESCRIPTION "Specifies the upper bound of the port criterion"
  ::= { alaDaUNPLocationPolicyEntry 3 }

  alaDaUNPLocationPolicyPortStatus OBJECT-TYPE
  SYNTAX      INTEGER {
		    enable(1),
		    disable(2)
  		}
  MAX-ACCESS  read-create
  STATUS      current
  DESCRIPTION "This object has to be set to ENABLE when the ports form one of the criteria for the location policy.
 	It should be set to DISABLE when the ports are to be removed."
  DEFVAL      { disable }
  ::= { alaDaUNPLocationPolicyEntry 4 }

  alaDaUNPLocationPolicySystemName OBJECT-TYPE
  SYNTAX      SnmpAdminString (SIZE(0..31))
  MAX-ACCESS  read-create
  STATUS      current
  DESCRIPTION "System Name criterion of the Location Policy"
  ::= { alaDaUNPLocationPolicyEntry 5 }

  alaDaUNPLocationPolicySystemLocation OBJECT-TYPE
  SYNTAX      SnmpAdminString (SIZE(0..31))
  MAX-ACCESS  read-create
  STATUS      current
  DESCRIPTION "System Location criterion of the Location Policy"
  ::= { alaDaUNPLocationPolicyEntry 6 }

  alaDaUNPLocationPolicyRowStatus OBJECT-TYPE
  SYNTAX      RowStatus
  MAX-ACCESS  read-create
  STATUS      current
  DESCRIPTION "Used to create/delete location policies according
  to the RowStatus convention"
  ::= { alaDaUNPLocationPolicyEntry 7 }

  alaDaUNPRedirectAllowedServerTable OBJECT-TYPE
  SYNTAX      SEQUENCE OF AlaDaUNPRedirectAllowedServerEntry
  MAX-ACCESS  not-accessible
  STATUS      current
  DESCRIPTION "Table of UNP Redirect Allowed Server"
  ::= { alaIND1DaMIBObjects 46 }

  alaDaUNPRedirectAllowedServerEntry OBJECT-TYPE
  SYNTAX      AlaDaUNPRedirectAllowedServerEntry
  MAX-ACCESS  not-accessible
  STATUS      current
  DESCRIPTION "Definition of UNP Redirect Allowed Server"
  INDEX {
      alaDaUNPRedirectAllowedServerName
  }
  ::= { alaDaUNPRedirectAllowedServerTable 1 }

  AlaDaUNPRedirectAllowedServerEntry ::=
  SEQUENCE
  {
    alaDaUNPRedirectAllowedServerName                       SnmpAdminString,
    alaDaUNPRedirectAllowedServerIPType                     InetAddressType,
    alaDaUNPRedirectAllowedServerIP                         InetAddress,
    alaDaUNPRedirectAllowedMaskIPType                       InetAddressType,
    alaDaUNPRedirectAllowedMaskIP                           InetAddress,
    alaDaUNPRedirectAllowedRowStatus                        RowStatus
  }

  alaDaUNPRedirectAllowedServerName OBJECT-TYPE
  SYNTAX      SnmpAdminString (SIZE(1..32))
  MAX-ACCESS  not-accessible
  STATUS      current
  DESCRIPTION "Name of Redirect Allowed Server"
  ::= { alaDaUNPRedirectAllowedServerEntry 1 }

  alaDaUNPRedirectAllowedServerIPType OBJECT-TYPE
  SYNTAX InetAddressType
  MAX-ACCESS read-create
  STATUS current
  DESCRIPTION "IP Address Type IPV4/IPV6 of Redirect server"
  ::= { alaDaUNPRedirectAllowedServerEntry 2 }

  alaDaUNPRedirectAllowedServerIP OBJECT-TYPE
  SYNTAX InetAddress
  MAX-ACCESS read-create
  STATUS current
  DESCRIPTION "IP Address of Redirect server"
  ::= { alaDaUNPRedirectAllowedServerEntry 3 }

  alaDaUNPRedirectAllowedMaskIPType OBJECT-TYPE
  SYNTAX InetAddressType
  MAX-ACCESS read-create
  STATUS current
  DESCRIPTION "IP Mask Type IPV4/IPV6 of Redirect server"
  ::= { alaDaUNPRedirectAllowedServerEntry 4 }

  alaDaUNPRedirectAllowedMaskIP OBJECT-TYPE
  SYNTAX InetAddress
  MAX-ACCESS read-create
  STATUS current
  DESCRIPTION "IP Mask Address of Redirect server"
  ::= { alaDaUNPRedirectAllowedServerEntry 5 }

  alaDaUNPRedirectAllowedRowStatus OBJECT-TYPE
  SYNTAX RowStatus
  MAX-ACCESS read-create
  STATUS current
  DESCRIPTION "ROwStatus Implies deleting/adding Entry to Table."
  ::= { alaDaUNPRedirectAllowedServerEntry 6 }

--
-- DA MAC VLAN User Extended Table
--

alaDaMacVlanUserExtTable OBJECT-TYPE
        SYNTAX      SEQUENCE OF AlaDaMacVlanUserExtEntry
        MAX-ACCESS  not-accessible
        STATUS      current
        DESCRIPTION
        "Extension to alaDaMacVlanUserTable to support number of applications."
::= { alaIND1DaMIBObjects 47 }

alaDaMacVlanUserExtEntry OBJECT-TYPE
        SYNTAX      AlaDaMacVlanUserExtEntry
        MAX-ACCESS  not-accessible
        STATUS      current
        DESCRIPTION
                "Non 802.1x supplicant information."
        INDEX { alaDaMacVlanUserExtIntfNum,
                alaDaMacVlanUserExtMACAddress,
                alaDaMacVlanUserExtVlanID,
                alaDaMacVlanUserExtAppID
              }
::= { alaDaMacVlanUserExtTable 1 }

AlaDaMacVlanUserExtEntry ::=
        SEQUENCE {
                     alaDaMacVlanUserExtIntfNum
                           InterfaceIndex,
                     alaDaMacVlanUserExtMACAddress
                           MacAddress,
                     alaDaMacVlanUserExtVlanID
                           Integer32,
                     alaDaMacVlanUserExtAppID
                           Unsigned32,
                     alaDaMacVlanUserExtAppName
                           SnmpAdminString
                 }

alaDaMacVlanUserExtIntfNum OBJECT-TYPE
    SYNTAX      InterfaceIndex
    MAX-ACCESS  not-accessible
    STATUS      current
    DESCRIPTION
        "The ifIndex representing the slot and port where the non 802.1x supplicant is learned."
    ::= { alaDaMacVlanUserExtEntry 1 }

alaDaMacVlanUserExtMACAddress OBJECT-TYPE
    SYNTAX      MacAddress
    MAX-ACCESS  not-accessible
    STATUS      current
    DESCRIPTION
        "The MAC address of the non 802.1x supplicant."
    ::= { alaDaMacVlanUserExtEntry 2 }

alaDaMacVlanUserExtVlanID OBJECT-TYPE
        SYNTAX      Integer32 (1..4096)
        MAX-ACCESS  not-accessible
        STATUS      current
        DESCRIPTION
        "The Id of the VLAN on which the non 802.1x supplicant is learned."
    ::= { alaDaMacVlanUserExtEntry 3 }

alaDaMacVlanUserExtAppID OBJECT-TYPE
    SYNTAX      Unsigned32 (0..32)
    MAX-ACCESS  not-accessible
    STATUS      current
    DESCRIPTION
        "to indicate the application number or ID."
    ::= { alaDaMacVlanUserExtEntry 4 }

alaDaMacVlanUserExtAppName OBJECT-TYPE
    SYNTAX      SnmpAdminString
    MAX-ACCESS  read-only
    STATUS      current
    DESCRIPTION
        "Applications added to the non 802.1x supplicant"
    ::= { alaDaMacVlanUserExtEntry 5 }

------------------------------------------------------------
-- VXLAN Profile Table configuration MIB --
-- This table is deprecated as part of unification
------------------------------------------------------------

alaDaUNPVxlanProfileTable OBJECT-TYPE
    SYNTAX        SEQUENCE OF AlaDaUNPVxlanProfileEntry
    MAX-ACCESS    not-accessible
    STATUS        deprecated
    DESCRIPTION
        "This table stores the Service Classification profiles created in the system.
         The entries provides information to classify device in the VXLAN Service domain."
    ::= { alaIND1DaMIBObjects 48 }

alaDaUNPVxlanProfileEntry OBJECT-TYPE
    SYNTAX        AlaDaUNPVxlanProfileEntry
    MAX-ACCESS    not-accessible
    STATUS        deprecated
    DESCRIPTION
        "VXLAN Service Classification Profile entry"
    INDEX {alaDaUNPVxlanProfileName}
    ::= { alaDaUNPVxlanProfileTable 1 }

AlaDaUNPVxlanProfileEntry ::= SEQUENCE  {
    alaDaUNPVxlanProfileName                  SnmpAdminString,
    alaDaUNPVxlanProfileEncapVal              TmnxEncapVal,
    alaDaUNPVxlanProfileVnid                  Unsigned32,
    alaDaUNPVxlanProfileQosPolicyListName     SnmpAdminString,
    alaDaUNPVxlanProfileFarEndIPListName      SnmpAdminString,
    alaDaUNPVxlanProfileMulticastIPAddressType InetAddressType,
    alaDaUNPVxlanProfileMulticastIPAddress     InetAddress,
    alaDaUNPVxlanProfileSapVlanXlation         INTEGER,
    alaDaUNPVxlanProfileMobileTagStatus        INTEGER,
    alaDaUNPVxlanProfileMulticastMode          INTEGER,
    alaDaUNPVxlanProfileRowStatus              RowStatus
}

alaDaUNPVxlanProfileName OBJECT-TYPE
    SYNTAX        SnmpAdminString (SIZE(1 .. 32))
    MAX-ACCESS    not-accessible
    STATUS        deprecated
    DESCRIPTION
        "The name of the profile."
    ::= { alaDaUNPVxlanProfileEntry 1 }

alaDaUNPVxlanProfileEncapVal OBJECT-TYPE
    SYNTAX        TmnxEncapVal
    MAX-ACCESS    read-create
    STATUS        deprecated
    DESCRIPTION
        "The encapsulation to be used for the SAP connecting to the service."
    ::= { alaDaUNPVxlanProfileEntry 2 }

alaDaUNPVxlanProfileVnid OBJECT-TYPE
    SYNTAX        Unsigned32 (1..16777214)
    MAX-ACCESS    read-create
    STATUS        deprecated
    DESCRIPTION
        "The object represnet the VNID that is to be used to dynamically
         create a VXLAN service."
    ::= { alaDaUNPVxlanProfileEntry 3 }

alaDaUNPVxlanProfileQosPolicyListName OBJECT-TYPE
    SYNTAX        SnmpAdminString (SIZE(0 .. 32))
    MAX-ACCESS    read-create
    STATUS        deprecated
    DESCRIPTION
        "The name of the QoS Policy List name that will be used if this
         User Network Profile is applied for a given device."
    ::= { alaDaUNPVxlanProfileEntry 4 }

alaDaUNPVxlanProfileFarEndIPListName OBJECT-TYPE
    SYNTAX        SnmpAdminString (SIZE(0 .. 32))
    MAX-ACCESS    read-create
    STATUS        deprecated
    DESCRIPTION
        "The name of the Far End IP List that will be used if this
         User Network Profile is applied for a given device."
    ::= { alaDaUNPVxlanProfileEntry 5 }

alaDaUNPVxlanProfileMulticastIPAddressType OBJECT-TYPE
    SYNTAX  	InetAddressType
    MAX-ACCESS 	read-create
    STATUS 		deprecated
    DESCRIPTION
        "The IP address type of the multicast group IP address."
    ::= { alaDaUNPVxlanProfileEntry 6 }

alaDaUNPVxlanProfileMulticastIPAddress OBJECT-TYPE
    SYNTAX  	InetAddress
    MAX-ACCESS 	read-create
    STATUS  	deprecated
    DESCRIPTION
        "The multicast group IP address."
    ::= { alaDaUNPVxlanProfileEntry 7 }

alaDaUNPVxlanProfileSapVlanXlation OBJECT-TYPE
    SYNTAX         INTEGER {
                        enable (1),
                        disable (2)
                   }
    MAX-ACCESS         read-create
    STATUS          deprecated
    DESCRIPTION
        "To enable/disable the vlan translation for all the SAPs configured
         in this service if the corresponding access ports for the SAPs also
         has the vlan translation enabled."
    DEFVAL          { enable }
    ::= { alaDaUNPVxlanProfileEntry 8 }

alaDaUNPVxlanProfileMobileTagStatus OBJECT-TYPE
    SYNTAX      INTEGER {
                    enable (1),
                    disable (2)
                }
    MAX-ACCESS  read-create
    STATUS      deprecated
    DESCRIPTION
        "VXLAN Profile Mobile Tag status. When enabled, the packets egressing out on the SAP
         will be tagged."
    DEFVAL { disable }
    ::= { alaDaUNPVxlanProfileEntry 9 }

alaDaUNPVxlanProfileMulticastMode OBJECT-TYPE
    SYNTAX      INTEGER {
     	            headend (1),
                    tandem (2),
                    hybrid (3)
                 }
    MAX-ACCESS      read-create
    STATUS          deprecated
    DESCRIPTION
         "To configure the multicast replication mode for each service:
          Head-end(1) where a non-unicast packet entering the SAP port
          is replicated once for each receiver in the b-domain using its
          unicast BMAC.
          Tandem(2) where a non-unicast packet entering the SAP port is
          replicated once at each node using the multicast group address."
    DEFVAL          { headend }
    ::= { alaDaUNPVxlanProfileEntry 10 }

alaDaUNPVxlanProfileRowStatus OBJECT-TYPE
    SYNTAX        RowStatus
    MAX-ACCESS    read-create
    STATUS        deprecated
    DESCRIPTION
        "The row status of this table entry."
    ::= { alaDaUNPVxlanProfileEntry 11 }

------------------------------------------------------------
-- VXLAN User Flush Table
-- This table is deprecated as part of unification
------------------------------------------------------------

alaDaUNPVxlanFlushTable OBJECT-TYPE
    SYNTAX      SEQUENCE OF AlaDaUNPVxlanFlushEntry
    MAX-ACCESS  not-accessible
    STATUS      deprecated
    DESCRIPTION
        "Table to flush the VXLAN access users based on some criteria
         such as MAC Address, Authentication Type, SAP, Service and/or Profile."
    ::= { alaIND1DaMIBObjects 49 }

alaDaUNPVxlanFlushEntry OBJECT-TYPE
    SYNTAX      AlaDaUNPVxlanFlushEntry
    MAX-ACCESS  not-accessible
    STATUS      deprecated
    DESCRIPTION
        "One entry  to flush VXLAN access users on the basis of user criteria."
    INDEX { alaDaUNPVxlanFlushIndex }
    ::= { alaDaUNPVxlanFlushTable 1 }

AlaDaUNPVxlanFlushEntry ::= SEQUENCE {
    alaDaUNPVxlanFlushIndex         Unsigned32,
    alaDaUNPVxlanFlushComplete      INTEGER,
    alaDaUNPVxlanFlushAuthType      INTEGER,
    alaDaUNPVxlanFlushMacAddress    MacAddress,
    alaDaUNPVxlanFlushSapIDIfIndex  InterfaceIndex,
    alaDaUNPVxlanFlushSapIDEncapVal TmnxEncapVal,
    alaDaUNPVxlanFlushServiceID     Unsigned32,
    alaDaUNPVxlanFlushVxlanProfile  SnmpAdminString
}

alaDaUNPVxlanFlushIndex OBJECT-TYPE
    SYNTAX      Unsigned32
    MAX-ACCESS  not-accessible
    STATUS      deprecated
    DESCRIPTION
        "Flush index."
    ::= { alaDaUNPVxlanFlushEntry 1 }

alaDaUNPVxlanFlushComplete OBJECT-TYPE
    SYNTAX     INTEGER {
                   none (1),
                   all (2)
               }
    MAX-ACCESS  read-write
    STATUS      deprecated
    DESCRIPTION
        "Flush all users learnt on all VXLAN-access type ports."
    DEFVAL { none }
    ::= { alaDaUNPVxlanFlushEntry 2 }

alaDaUNPVxlanFlushAuthType OBJECT-TYPE
    SYNTAX     INTEGER {
                   noAuth (1),
                   onex (2),
                   mac (3)
               }
    MAX-ACCESS  read-write
    STATUS      deprecated
    DESCRIPTION
        "Flush based on the authentication type of the user."
    ::= { alaDaUNPVxlanFlushEntry 3 }

alaDaUNPVxlanFlushMacAddress OBJECT-TYPE
    SYNTAX     MacAddress(SIZE(6))
    MAX-ACCESS  read-write
    STATUS      deprecated
    DESCRIPTION
        "Flush based on a single MAC address."
    ::= { alaDaUNPVxlanFlushEntry 4 }

alaDaUNPVxlanFlushSapIDIfIndex OBJECT-TYPE
    SYNTAX        InterfaceIndex
    MAX-ACCESS    read-write
    STATUS        deprecated
    DESCRIPTION
        "Flush the users learnt on the given SAP-ID Interface Index."
    ::= { alaDaUNPVxlanFlushEntry 5 }

alaDaUNPVxlanFlushSapIDEncapVal OBJECT-TYPE
    SYNTAX        TmnxEncapVal
    MAX-ACCESS    read-write
    STATUS        deprecated
    DESCRIPTION
        "Flush the users learnt on the given SAP-ID Encapsulation."
    ::= { alaDaUNPVxlanFlushEntry 6 }

alaDaUNPVxlanFlushServiceID OBJECT-TYPE
    SYNTAX        Unsigned32
    MAX-ACCESS    read-write
    STATUS        deprecated
    DESCRIPTION
        "Flush the users learnt of the given VXLAN service."
    ::= { alaDaUNPVxlanFlushEntry 7 }

alaDaUNPVxlanFlushVxlanProfile OBJECT-TYPE
    SYNTAX        SnmpAdminString (SIZE( 0..32 ))
    MAX-ACCESS    read-write
    STATUS        deprecated
    DESCRIPTION
        "Flush the users learnt on the given VXLAN Profile."
    ::= { alaDaUNPVxlanFlushEntry 8 }

------------------------------------------------------------
-- VXLAN Far-End-IP-List Table
------------------------------------------------------------

   alaDaUNPVxlanFarEndIPListTable OBJECT-TYPE
        SYNTAX      SEQUENCE OF AlaDaUNPVxlanFarEndIPListEntry
        MAX-ACCESS  not-accessible
        STATUS      current
        DESCRIPTION
        "Table shows all the Far-End-IP-Lists configured."
        ::= { alaIND1DaMIBObjects 50 }

   alaDaUNPVxlanFarEndIPListEntry OBJECT-TYPE
        SYNTAX      AlaDaUNPVxlanFarEndIPListEntry
        MAX-ACCESS  not-accessible
        STATUS      current
        DESCRIPTION
        "Far-end IP List entry."
        INDEX { alaDaUNPVxlanFarEndIPListName }
        ::= { alaDaUNPVxlanFarEndIPListTable 1 }

    AlaDaUNPVxlanFarEndIPListEntry ::= SEQUENCE
    {
    	alaDaUNPVxlanFarEndIPListName 		SnmpAdminString,
    	alaDaUNPVxlanFarEndIPListIPAddressCount Unsigned32,
      alaDaUNPVxlanFarEndIPListRemove		INTEGER
    }

    alaDaUNPVxlanFarEndIPListName OBJECT-TYPE
        SYNTAX        SnmpAdminString (SIZE(1..32))
        MAX-ACCESS    not-accessible
        STATUS        current
        DESCRIPTION
        "Name of the Far-End-IP list configured."
        ::= { alaDaUNPVxlanFarEndIPListEntry 1 }

    alaDaUNPVxlanFarEndIPListIPAddressCount OBJECT-TYPE
        SYNTAX        Unsigned32
        MAX-ACCESS    read-only
        STATUS        current
        DESCRIPTION
            "The count of the IP Addresses configured for the corresponding Far-End-IP-List."
        ::= { alaDaUNPVxlanFarEndIPListEntry 2 }

    alaDaUNPVxlanFarEndIPListRemove OBJECT-TYPE
        SYNTAX      INTEGER {
		      no (1),
		      yes (2)
			  }
        MAX-ACCESS    read-write
        STATUS        current
        DESCRIPTION
            "This object is used to remove a Far-End-IP-List."
        DEFVAL { no }
        ::= { alaDaUNPVxlanFarEndIPListEntry 3 }

------------------------------------------------------------
-- VXLAN Far-End-IP-List Address Table
------------------------------------------------------------

   alaDaUNPVxlanFarEndIPAddressListTable OBJECT-TYPE
        SYNTAX      SEQUENCE OF AlaDaUNPVxlanFarEndIPAddressListEntry
        MAX-ACCESS  not-accessible
        STATUS      current
        DESCRIPTION
        "Table to configure the Far-End-List and the IP Addresses for that list."
        ::= { alaIND1DaMIBObjects 51 }

   alaDaUNPVxlanFarEndIPAddressListEntry OBJECT-TYPE
        SYNTAX      AlaDaUNPVxlanFarEndIPAddressListEntry
        MAX-ACCESS  not-accessible
        STATUS      current
        DESCRIPTION
        "Far-end IP Address List entry."
        INDEX { alaDaUNPVxlanFarEndIPListName, alaDaUNPVxlanFarEndIPAddressListIPType, alaDaUNPVxlanFarEndIPAddressListIP }
        ::= { alaDaUNPVxlanFarEndIPAddressListTable 1 }

    AlaDaUNPVxlanFarEndIPAddressListEntry ::= SEQUENCE
    {
        alaDaUNPVxlanFarEndIPAddressListIPType 		InetAddressType,
        alaDaUNPVxlanFarEndIPAddressListIP		InetAddress,
        alaDaUNPVxlanFarEndIPAddressListRowStatus 	RowStatus
    }

    alaDaUNPVxlanFarEndIPAddressListIPType OBJECT-TYPE
        SYNTAX  	InetAddressType
                  	{
                     		ipv4(1),
                     		ipv6(2)
                  	}
        MAX-ACCESS      not-accessible
        STATUS 		current
        DESCRIPTION
          "The IP address type of the IP address."
        ::= { alaDaUNPVxlanFarEndIPAddressListEntry 1 }

    alaDaUNPVxlanFarEndIPAddressListIP OBJECT-TYPE
        SYNTAX  	InetAddress (SIZE(4|16))
        MAX-ACCESS 	not-accessible
        STATUS  	current
        DESCRIPTION
          "The Far-End IP address."
        ::= { alaDaUNPVxlanFarEndIPAddressListEntry 2 }

    alaDaUNPVxlanFarEndIPAddressListRowStatus OBJECT-TYPE
        SYNTAX        RowStatus
        MAX-ACCESS    read-create
        STATUS        current
        DESCRIPTION
            "The row status of this table entry."
        ::= { alaDaUNPVxlanFarEndIPAddressListEntry 3 }

------------------------------------------------------------
-- SPB User Flush Table
-- This table is deprecated as part of unification
------------------------------------------------------------

alaDaUNPSpbFlushTable OBJECT-TYPE
    SYNTAX      SEQUENCE OF AlaDaUNPSpbFlushEntry
    MAX-ACCESS  not-accessible
    STATUS      deprecated
    DESCRIPTION
        "Table to flush the VXLAN access users based on some criteria
         such as MAC Address, Authentication Type, SAP, Service and/or Profile."
    ::= { alaIND1DaMIBObjects 52 }

alaDaUNPSpbFlushEntry OBJECT-TYPE
    SYNTAX      AlaDaUNPSpbFlushEntry
    MAX-ACCESS  not-accessible
    STATUS      deprecated
    DESCRIPTION
        "One entry to flush SPB access users on the basis of user criteria."
    INDEX { alaDaUNPSpbFlushIndex }
    ::= { alaDaUNPSpbFlushTable 1 }

AlaDaUNPSpbFlushEntry ::= SEQUENCE  {
    alaDaUNPSpbFlushIndex         Integer32,
    alaDaUNPSpbFlushComplete      INTEGER,
    alaDaUNPSpbFlushAuthType      INTEGER,
    alaDaUNPSpbFlushMacAddress    MacAddress,
    alaDaUNPSpbFlushSapIDIfIndex  InterfaceIndex,
    alaDaUNPSpbFlushSapIDEncapVal TmnxEncapVal,
    alaDaUNPSpbFlushServiceID     Unsigned32,
    alaDaUNPSpbFlushSpbProfile    SnmpAdminString
}

alaDaUNPSpbFlushIndex OBJECT-TYPE
    SYNTAX      Integer32(1)
    MAX-ACCESS  not-accessible
    STATUS      deprecated
    DESCRIPTION
        "Flush index."
    ::= { alaDaUNPSpbFlushEntry 1 }

alaDaUNPSpbFlushComplete OBJECT-TYPE
    SYNTAX     INTEGER {
                   none (1),
                   all (2)
               }
    MAX-ACCESS  read-write
    STATUS      deprecated
    DESCRIPTION
        "Flush all users learnt on all SPB-access type ports."
    DEFVAL { none }
    ::= { alaDaUNPSpbFlushEntry 2 }

alaDaUNPSpbFlushAuthType OBJECT-TYPE
    SYNTAX     INTEGER {
                   noAuth (1),
                   onex (2),
                   mac (3)
               }
    MAX-ACCESS  read-write
    STATUS      deprecated
    DESCRIPTION
        "Flush based on the authentication type of the user."
    ::= { alaDaUNPSpbFlushEntry 3 }

alaDaUNPSpbFlushMacAddress OBJECT-TYPE
    SYNTAX     MacAddress(SIZE(6))
    MAX-ACCESS  read-write
    STATUS      deprecated
    DESCRIPTION
        "Flush based on a single mac-address."
    ::= { alaDaUNPSpbFlushEntry 4 }

alaDaUNPSpbFlushSapIDIfIndex OBJECT-TYPE
    SYNTAX        InterfaceIndex
    MAX-ACCESS    read-write
    STATUS        deprecated
    DESCRIPTION
        "Flush the users learnt on the given SAP-ID Interface Index."
    ::= { alaDaUNPSpbFlushEntry 5 }

alaDaUNPSpbFlushSapIDEncapVal OBJECT-TYPE
    SYNTAX        TmnxEncapVal
    MAX-ACCESS    read-write
    STATUS        deprecated
    DESCRIPTION
        "Flush the users learnt on the given SAP-ID Encapsulation."
    ::= { alaDaUNPSpbFlushEntry 6 }

alaDaUNPSpbFlushServiceID OBJECT-TYPE
    SYNTAX        Unsigned32
    MAX-ACCESS    read-write
    STATUS        deprecated
    DESCRIPTION
        "Flush the users learnt of the given VXLAN service."
    ::= { alaDaUNPSpbFlushEntry 7 }

alaDaUNPSpbFlushSpbProfile OBJECT-TYPE
    SYNTAX        SnmpAdminString (SIZE( 0..32 ))
    MAX-ACCESS    read-write
    STATUS        deprecated
    DESCRIPTION
        "Flush the users learnt on the given SPB Profile."
    ::= { alaDaUNPSpbFlushEntry 8 }

------------------------------------------------------------
-- Kerberos related Config  --
------------------------------------------------------------

alaDaKerberosMIBObjects    OBJECT IDENTIFIER ::= { alaIND1DaMIBObjects 53 }

alaDaKerberosGlobalConfig   OBJECT IDENTIFIER ::= { alaDaKerberosMIBObjects 1 }


-- *******************************************************************
-- The Kerberos Mac-Move Status object
-- *******************************************************************

alaDaKerberosGlobalMacMoveStatus OBJECT-TYPE
    SYNTAX       INTEGER {
                 enable(1),
                 disable(2)
                 }
    MAX-ACCESS   read-write
    STATUS       current
    DESCRIPTION
       "Defines the global mac move status for Kerberos."
    DEFVAL { enable }
    ::= { alaDaKerberosGlobalConfig 1 }

-- *******************************************************************
-- The Kerberos Inactivity Timer Value object
-- *******************************************************************

alaDaKerberosGlobalInactivityTimer OBJECT-TYPE
    SYNTAX        Integer32 ( 10..600)
    MAX-ACCESS    read-write
    STATUS        current
    DESCRIPTION
       "Inactivity Timer value for the Kerberos users in minutes.
        It will be configured globally."
    DEFVAL { 300 }
    ::= { alaDaKerberosGlobalConfig 2}


-- *******************************************************************
-- The Kerberos Global User policy object
-- *******************************************************************

alaDaKerberosGlobalPolicy OBJECT-TYPE
   SYNTAX        SnmpAdminString (SIZE (0..31))
   MAX-ACCESS    read-write
   STATUS        current
   DESCRIPTION
      "The name of the QoS Policy List name that will be used for a kerberos user
      if per domain QOS Policy List is not configured by object alaDaKerberosPolicyName."
   ::= { alaDaKerberosGlobalConfig 3}

alaDaKerberosGlobalPolicyStatus OBJECT-TYPE
   SYNTAX        INTEGER {
                    none(1),
                    active(2),
                    inactive(3)
                    }
   MAX-ACCESS    read-only
   STATUS        current
   DESCRIPTION
      "The status of global policy list. This can be Active or Inactive if
       alaDaKerberosGlobalPolicy is configured else it will be none."
   ::= { alaDaKerberosGlobalConfig 4}

-- *******************************************************************
-- The Kerberos Global Statistics object
-- *******************************************************************

alaDaKerberosClientPktHwDiscardStats  OBJECT-TYPE
   SYNTAX        Counter32
   MAX-ACCESS    read-only
   STATUS        current
   DESCRIPTION
      "The total number of packets dropped due to hardware rate limiter, destined to Kerberos server."
   ::= { alaDaKerberosGlobalConfig 5}

alaDaKerberosServerPktHwDiscardStats  OBJECT-TYPE
   SYNTAX        Counter32
   MAX-ACCESS    read-only
   STATUS        current
   DESCRIPTION
      "The total number of packets from kerberos server, dropped due to hardware rate limiter."

   ::= { alaDaKerberosGlobalConfig 6}

alaDaKerberosTotalClientPktRxStats  OBJECT-TYPE
   SYNTAX        Counter32
   MAX-ACCESS    read-only
   STATUS        current
   DESCRIPTION
      "The total number of packets received by software, destined to the kerberos server."
   ::= { alaDaKerberosGlobalConfig 7}

alaDaKerberosTotalServerPktRxStats  OBJECT-TYPE
   SYNTAX        Counter32
   MAX-ACCESS    read-only
   STATUS        current
   DESCRIPTION
      "The total number of packets received by software from kerberos server."
   ::= { alaDaKerberosGlobalConfig 8}

alaDaKerberosClientPktSwDiscardStats  OBJECT-TYPE
   SYNTAX        Counter32
   MAX-ACCESS    read-only
   STATUS        current
   DESCRIPTION
      "Total number of packtes discarded by software, destined to kerberos server."
   ::= { alaDaKerberosGlobalConfig 9}


alaDaKerberosServerPktSwDiscardStats  OBJECT-TYPE
   SYNTAX        Counter32
   MAX-ACCESS    read-only
   STATUS        current
   DESCRIPTION
      "Total number of packets discarded by software, received from kerberos server."
   ::= { alaDaKerberosGlobalConfig 10}

alaDaKerberosTotalASREQRxStats  OBJECT-TYPE
   SYNTAX        Counter32
   MAX-ACCESS    read-only
   STATUS        current
   DESCRIPTION
      "Total number of AS-REQ packet received by Kerberos application."
   ::= { alaDaKerberosGlobalConfig 11}

alaDaKerberosTotalASREPRxStats  OBJECT-TYPE
   SYNTAX        Counter32
   MAX-ACCESS    read-only
   STATUS        current
   DESCRIPTION
      "Total number of AS-REP packet received by Kerberos application."
   ::= { alaDaKerberosGlobalConfig 12}


alaDaKerberosTotalTGSREQRxStats  OBJECT-TYPE
   SYNTAX        Counter32
   MAX-ACCESS    read-only
   STATUS        current
   DESCRIPTION
      "Total number of TGS-REQ packet received by Kerberos application."
   ::= { alaDaKerberosGlobalConfig 13}


alaDaKerberosTotalTGSREPRxStats  OBJECT-TYPE
   SYNTAX        Counter32
   MAX-ACCESS    read-only
   STATUS        current
   DESCRIPTION
      "Total number of TGS-REP packet received by Kerberos application."
   ::= { alaDaKerberosGlobalConfig 14}


alaDaKerberosTotalErrorRxStats  OBJECT-TYPE
   SYNTAX        Counter32
   MAX-ACCESS    read-only
   STATUS        current
   DESCRIPTION
      "Total number of KRB-ERROR packet received by Kerberos application."
   ::= { alaDaKerberosGlobalConfig 15}

alaDaKerberosGlobalClearStats  OBJECT-TYPE
   SYNTAX        INTEGER {
                    default(1),
                    reset(2)
                    }
   MAX-ACCESS    read-write
   STATUS        current
   DESCRIPTION
      "Defines the global clear statistics control for Kerberos Snooping
        The value reset (1) indicates that clear all global statistic counters."
    DEFVAL  { default }
   ::= { alaDaKerberosGlobalConfig 16}


alaDaKerberosGlobalClearPortStats  OBJECT-TYPE
   SYNTAX        INTEGER {
                    default(1),
                    reset(2)
                    }
   MAX-ACCESS    read-write
   STATUS        current
   DESCRIPTION
      "Defines the global clear statistics control for Kerberos Snooping
        The value reset (1) indicates that clear all per port statistic counters."
    DEFVAL  { default }
   ::= { alaDaKerberosGlobalConfig 17}

-- *******************************************************************
-- The Kerberos Server Timeout Timer Value object
-- *******************************************************************

alaDaKerberosGlobalServerTimeoutTimer  OBJECT-TYPE
   SYNTAX        Integer32(1 .. 30)
   MAX-ACCESS    read-write
   STATUS        current
   DESCRIPTION
      "Defines the global reply timeout value for Kerberos Server in seconds."
    DEFVAL  {2}
   ::= { alaDaKerberosGlobalConfig 18}

-- ******************************************************************
-- The Kerberos Per domain policy Table
-- ******************************************************************

alaDaKerberosPolicyConfigTable OBJECT-TYPE
   SYNTAX        SEQUENCE OF AlaDaKerberosPolicyConfigEntry
   MAX-ACCESS    not-accessible
   STATUS        current
   DESCRIPTION
      "Provide the list of user policies configured per user domain."
   ::= { alaDaKerberosMIBObjects 2}

alaDaKerberosPolicyConfigEntry OBJECT-TYPE
   SYNTAX        AlaDaKerberosPolicyConfigEntry
   MAX-ACCESS    not-accessible
   STATUS        current
   DESCRIPTION
      "Policy config table entry."
   INDEX {IMPLIED alaDaKerberosPolicyDomainName}
   ::= { alaDaKerberosPolicyConfigTable 1 }

AlaDaKerberosPolicyConfigEntry ::= SEQUENCE
   {
        alaDaKerberosPolicyDomainName    SnmpAdminString,
        alaDaKerberosPolicyName          SnmpAdminString,
        alaDaKerberosPolicyStatus        INTEGER,
        alaDaKerberosPolicyRowStatus     RowStatus
   }

alaDaKerberosPolicyDomainName OBJECT-TYPE
   SYNTAX        SnmpAdminString (SIZE (1..32))
   MAX-ACCESS    not-accessible
   STATUS        current
   DESCRIPTION
      "The name of the kerberos user domain."

   ::= { alaDaKerberosPolicyConfigEntry 1}

alaDaKerberosPolicyName OBJECT-TYPE
   SYNTAX        SnmpAdminString (SIZE (1..31))
   MAX-ACCESS    read-create
   STATUS        current
   DESCRIPTION
      "The name of the QoS Policy List name that will be used for a kerberos user
      in the domain."

   ::= { alaDaKerberosPolicyConfigEntry 2}

alaDaKerberosPolicyStatus OBJECT-TYPE
   SYNTAX        INTEGER {
                    active(1),
                    inactive(2)
                    }
   MAX-ACCESS    read-only
   STATUS        current
   DESCRIPTION
      "The status of domain level policy list. This can be Active or Inactive."
   ::= { alaDaKerberosPolicyConfigEntry 3}

alaDaKerberosPolicyRowStatus  OBJECT-TYPE
   SYNTAX        RowStatus
   MAX-ACCESS    read-create
   STATUS        current
   DESCRIPTION
      "This object allows entries to be created and deleted in the table"
   ::= { alaDaKerberosPolicyConfigEntry 4}

-- ******************************************************************
-- The Kerberos User Table
-- ******************************************************************


alaDaKerberosUserTable OBJECT-TYPE
   SYNTAX        SEQUENCE OF AlaDaKerberosUserEntry
   MAX-ACCESS    not-accessible
   STATUS        current
   DESCRIPTION
       "Provide the list of Kerberos users."
   ::= { alaDaKerberosMIBObjects 3 }

alaDaKerberosUserEntry OBJECT-TYPE
   SYNTAX        AlaDaKerberosUserEntry
   MAX-ACCESS    not-accessible
   STATUS        current
   DESCRIPTION
      "Kerberos user Table entry."
   INDEX {alaDaKerberosUserMac}
   ::= { alaDaKerberosUserTable 1 }

AlaDaKerberosUserEntry ::= SEQUENCE
   {
       alaDaKerberosUserMac          MacAddress,
       alaDaKerberosUserPort         InterfaceIndex,
       alaDaKerberosUserName         SnmpAdminString,
       alaDaKerberosUserDomain       SnmpAdminString,
       alaDaKerberosUserAuthState    INTEGER,
       alaDaKerberosUserPolicy       SnmpAdminString,
       alaDaKerberosUserLeftTime     Integer32,
       alaDaKerberosUserState        INTEGER
   }

alaDaKerberosUserMac OBJECT-TYPE
   SYNTAX        MacAddress
   MAX-ACCESS    not-accessible
   STATUS        current
   DESCRIPTION
      "Mac address of the user."
   ::= { alaDaKerberosUserEntry 1 }

alaDaKerberosUserPort OBJECT-TYPE
   SYNTAX        InterfaceIndex
   MAX-ACCESS    read-only
   STATUS        current
   DESCRIPTION
      "Port number on which user is learned."
   ::= { alaDaKerberosUserEntry 2 }

alaDaKerberosUserName OBJECT-TYPE
   SYNTAX        SnmpAdminString(SIZE(1..32))
   MAX-ACCESS    read-only
   STATUS        current
   DESCRIPTION
      "Name of the user"
   ::= { alaDaKerberosUserEntry 3}

alaDaKerberosUserDomain   OBJECT-TYPE
   SYNTAX        SnmpAdminString(SIZE(1..32))
   MAX-ACCESS    read-only
   STATUS        current
   DESCRIPTION
   "Domain of the user."
   ::= { alaDaKerberosUserEntry 4 }

alaDaKerberosUserAuthState  OBJECT-TYPE
   SYNTAX        INTEGER {
   asAuthenticating(1),
   asAuthenticated(2),
   asFailed(3),
   asTimeout(4),
   tgsAuthenticating(5),
   tgsAuthenticated(6),
   tgsFailed(7),
   tgsTimeout(8)

   }
   MAX-ACCESS    read-only
   STATUS        current
   DESCRIPTION
      "Current state of the Kerberos User authentication."
   ::= { alaDaKerberosUserEntry 5 }

alaDaKerberosUserPolicy  OBJECT-TYPE
   SYNTAX        SnmpAdminString (SIZE (0..32))
   MAX-ACCESS    read-only
   STATUS        current
   DESCRIPTION
      "Classification Policy applied for the user."
   ::= { alaDaKerberosUserEntry 6 }

alaDaKerberosUserLeftTime OBJECT-TYPE
    SYNTAX        Integer32
    MAX-ACCESS    read-only
    STATUS        current
    DESCRIPTION
       "Inactivity Timer left value for the Kerberos users in seconds."
    ::= { alaDaKerberosUserEntry 7}

alaDaKerberosUserState  OBJECT-TYPE
   SYNTAX        INTEGER {
   idle(1),
   active(2)
   }
   MAX-ACCESS    read-only
   STATUS        current
   DESCRIPTION
      "Current state of the Kerberos User."
   ::= { alaDaKerberosUserEntry 8 }

-- ******************************************************************
-- The Kerberos Per Port Statistics Table
-- ******************************************************************

alaDaKerberosPortStatsTable  OBJECT-TYPE
   SYNTAX        SEQUENCE OF AlaDaKerberosPortStatsEntry
   MAX-ACCESS    not-accessible
   STATUS        current
   DESCRIPTION
       "This table contains the statistics for kerberos on per port basis."
   ::= { alaDaKerberosMIBObjects 4 }

alaDaKerberosPortStatsEntry OBJECT-TYPE
   SYNTAX        AlaDaKerberosPortStatsEntry
   MAX-ACCESS    not-accessible
   STATUS        current
   DESCRIPTION
      "Kerberos statistics table entry."
   INDEX {alaDaKerberosStatsIfIndex}
   ::= { alaDaKerberosPortStatsTable 1 }

AlaDaKerberosPortStatsEntry ::= SEQUENCE
   {
       alaDaKerberosStatsIfIndex                  InterfaceIndex,
       alaDaKerberosPortClearStats                INTEGER,
       alaDaKerberosPortClientPktRxStats          Counter32,
       alaDaKerberosPortServerPktRxStats          Counter32,
       alaDaKerberosPortClientPktSwDiscardStats   Counter32,
       alaDaKerberosPortServerPktSwDiscardStats   Counter32,
       alaDaKerberosPortASREQRxStats              Counter32,
       alaDaKerberosPortASREPRxStats              Counter32,
       alaDaKerberosPortTGSREQRxStats             Counter32,
       alaDaKerberosPortTGSREPRxStats             Counter32,
       alaDaKerberosPortErrorRxStats              Counter32
   }

alaDaKerberosStatsIfIndex   OBJECT-TYPE
    SYNTAX          InterfaceIndex
    MAX-ACCESS      not-accessible
    STATUS          current
    DESCRIPTION
        "The ifindex of the port on which Kerberos Snooping is running."
    ::= { alaDaKerberosPortStatsEntry 1 }

alaDaKerberosPortClearStats   OBJECT-TYPE
    SYNTAX          INTEGER {
                    default(1),
                    reset(2)
                     }
    MAX-ACCESS     read-write
    STATUS         current
    DESCRIPTION
        "When this object is set to reset(1), all statistics parameters
         corresponding to this port gets cleared (reset)."
    DEFVAL  { default }
    ::= { alaDaKerberosPortStatsEntry 2 }


alaDaKerberosPortClientPktRxStats  OBJECT-TYPE
    SYNTAX         Counter32
    MAX-ACCESS     read-only
    STATUS         current
    DESCRIPTION
        "Number of packets received by software on a port, destined to the kerberos server."
    ::= { alaDaKerberosPortStatsEntry 3 }


alaDaKerberosPortServerPktRxStats  OBJECT-TYPE
    SYNTAX         Counter32
    MAX-ACCESS     read-only
    STATUS         current
    DESCRIPTION
        "Number of packets from kerberos server received by software on a port."
    ::= { alaDaKerberosPortStatsEntry 4 }


alaDaKerberosPortClientPktSwDiscardStats  OBJECT-TYPE
    SYNTAX         Counter32
    MAX-ACCESS     read-only
    STATUS         current
    DESCRIPTION
        "Number of packets discarded by software on a port, destined to the kerberos server."
    ::= { alaDaKerberosPortStatsEntry 5 }


alaDaKerberosPortServerPktSwDiscardStats  OBJECT-TYPE
    SYNTAX         Counter32
    MAX-ACCESS     read-only
    STATUS         current
    DESCRIPTION
        "Number of packets from kerberos server discarded by software on a port."
    ::= { alaDaKerberosPortStatsEntry 6 }


alaDaKerberosPortASREQRxStats  OBJECT-TYPE
    SYNTAX         Counter32
    MAX-ACCESS     read-only
    STATUS         current
    DESCRIPTION
        "Number of AS-REQ packets received on a port."
    ::= { alaDaKerberosPortStatsEntry 7 }


alaDaKerberosPortASREPRxStats  OBJECT-TYPE
    SYNTAX         Counter32
    MAX-ACCESS     read-only
    STATUS         current
    DESCRIPTION
        "Number of AS-REP packets received on a port."
    ::= { alaDaKerberosPortStatsEntry 8 }


alaDaKerberosPortTGSREQRxStats  OBJECT-TYPE
    SYNTAX         Counter32
    MAX-ACCESS     read-only
    STATUS         current
    DESCRIPTION
        "Number of TGS-REQ packets received on a port."
    ::= { alaDaKerberosPortStatsEntry 9 }


alaDaKerberosPortTGSREPRxStats  OBJECT-TYPE
    SYNTAX         Counter32
    MAX-ACCESS     read-only
    STATUS         current
    DESCRIPTION
        "Number of TGS-REP packets received on a port."
    ::= { alaDaKerberosPortStatsEntry 10 }

alaDaKerberosPortErrorRxStats  OBJECT-TYPE
   SYNTAX        Counter32
   MAX-ACCESS    read-only
   STATUS        current
   DESCRIPTION
      "Number of KRB-ERROR packet received on a port."
   ::= { alaDaKerberosPortStatsEntry 11}
-- ******************************************************************
-- Kerberos Server IP Configuration Table
-- ******************************************************************

alaDaKerberosServerTable  OBJECT-TYPE
   SYNTAX        SEQUENCE OF AlaDaKerberosServerEntry
   MAX-ACCESS    not-accessible
   STATUS        current
   DESCRIPTION
       "This table configures the kerberos server ip address."
   ::= { alaDaKerberosMIBObjects 5 }

alaDaKerberosServerEntry OBJECT-TYPE
   SYNTAX        AlaDaKerberosServerEntry
   MAX-ACCESS    not-accessible
   STATUS        current
   DESCRIPTION
      "Kerberos server table entry."
   INDEX {alaDaKerberosIpAddressType,alaDaKerberosIpAddress}
   ::= { alaDaKerberosServerTable 1 }

AlaDaKerberosServerEntry ::= SEQUENCE
   {
       alaDaKerberosIpAddressType		  InetAddressType,
       alaDaKerberosIpAddress                     InetAddress,
       alaDaKerberosUdpPort                       INTEGER,
       alaDaKerberosRowStatus                     RowStatus
   }

alaDaKerberosIpAddressType   OBJECT-TYPE
    SYNTAX          InetAddressType
    MAX-ACCESS      not-accessible
    STATUS          current
    DESCRIPTION
        "The ip-address type of the Kerberos server."
    ::= { alaDaKerberosServerEntry 1 }

alaDaKerberosIpAddress   OBJECT-TYPE
    SYNTAX          InetAddress
    MAX-ACCESS      not-accessible
    STATUS          current
    DESCRIPTION
        "The ip-address of the Kerberos server."
    ::= { alaDaKerberosServerEntry 2 }

alaDaKerberosUdpPort    OBJECT-TYPE
    SYNTAX          INTEGER ( 1 .. 65535 )
    MAX-ACCESS      read-create
    STATUS          current
    DESCRIPTION
        "The UDP port number for Kerberos server host."
    DEFVAL        { 88 }
    ::= { alaDaKerberosServerEntry 3 }

alaDaKerberosRowStatus OBJECT-TYPE
        SYNTAX        RowStatus
        MAX-ACCESS    read-create
        STATUS        current
        DESCRIPTION
            "The status of this table entry."
        DEFVAL        { notInService }
        ::= { alaDaKerberosServerEntry 4}

--
-- UNP Port Vlan Table
--

alaDaUNPPortVlanTable OBJECT-TYPE
    SYNTAX      SEQUENCE OF AlaDaUNPPortVlanEntry
    MAX-ACCESS  not-accessible
    STATUS      current
    DESCRIPTION
        "This table contains a list of untagged VLANs configured for an UNP Port/Linkagg"
    ::= { alaIND1DaMIBObjects 54 }

alaDaUNPPortVlanEntry OBJECT-TYPE
    SYNTAX      AlaDaUNPPortVlanEntry
    MAX-ACCESS  not-accessible
    STATUS      current
    DESCRIPTION
        "Each of these entries represents an untagged Vlan Port association"
    INDEX { alaDaUNPPortIfIndex, alaDaUNPPortVlanVID }
    ::= { alaDaUNPPortVlanTable 1 }

AlaDaUNPPortVlanEntry ::= SEQUENCE
    {
        alaDaUNPPortVlanVID        Unsigned32,
        alaDaUNPPortVlanRowStatus  RowStatus
    }

alaDaUNPPortVlanVID OBJECT-TYPE
    SYNTAX          Unsigned32 (1..4094)
    MAX-ACCESS      not-accessible
    STATUS          current
    DESCRIPTION
     "Untagged VLAN for an UNP Port/Linkagg."
    ::= { alaDaUNPPortVlanEntry 1 }

alaDaUNPPortVlanRowStatus OBJECT-TYPE
    SYNTAX      RowStatus
    MAX-ACCESS  read-create
    STATUS      current
    DESCRIPTION
     "On create, the specified UNP Port/Linkagg must exist in alaDaUNPPortTable,
      otherwise an entry creation in this table would not be allowed. Deletion of an UNP Port/Linkagg entry in
      alaDaUNPPortTable would result in deletion of all entries for that Port/Linkagg in the
      alaDaUNPPortVlanEntry"
    ::= { alaDaUNPPortVlanEntry 2 }

------------------------------------------------
-- DA Vlan Tag rule  --
------------------------------------------------
alaDaUNPVlanRuleTable  OBJECT-TYPE
SYNTAX  SEQUENCE OF AlaDaUNPVlanRuleEntry
MAX-ACCESS  not-accessible
STATUS  current
DESCRIPTION
"Vlan Tag classification table ."
::= { alaIND1DaMIBObjects 55 }

alaDaUNPVlanRuleEntry OBJECT-TYPE
SYNTAX  AlaDaUNPVlanRuleEntry
MAX-ACCESS  not-accessible
STATUS  current
DESCRIPTION
 " VlanTag  based  classification rule ."
INDEX { alaDaUNPVlanRuleVlanTag }
::= { alaDaUNPVlanRuleTable 1 }

AlaDaUNPVlanRuleEntry ::= SEQUENCE
{
     alaDaUNPVlanRuleVlanTag             Integer32,
     alaDaUNPVlanRuleVlanTagPosition     INTEGER,
     alaDaUNPVlanRuleEdgeProf            SnmpAdminString,
     alaDaUNPVlanRuleRowStatus           RowStatus
}

alaDaUNPVlanRuleVlanTag  OBJECT-TYPE
    SYNTAX  Integer32 (1..4094)
    MAX-ACCESS  not-accessible
    STATUS  current
    DESCRIPTION
         "The vlan tag to be used for classification of tagged pkts. The range states
          the valid Vlan range in the system."
    ::= { alaDaUNPVlanRuleEntry 1 }

alaDaUNPVlanRuleVlanTagPosition OBJECT-TYPE
    SYNTAX      INTEGER {
        outerTag (1),
        innerTag (2)
    }
    MAX-ACCESS read-create
    STATUS      current
    DESCRIPTION
          "This object specifies the tag position to which this Vlan Tag rule should be applied in the case of double tagged frames."
    DEFVAL      { outerTag }
    ::= { alaDaUNPVlanRuleEntry 2 }

alaDaUNPVlanRuleEdgeProf OBJECT-TYPE
SYNTAX  SnmpAdminString ( SIZE( 1 .. 32 ) )
MAX-ACCESS  read-create
STATUS  current
DESCRIPTION
 "The edge profile name in the User Network Profile Table to be
  applied."
::= { alaDaUNPVlanRuleEntry 3 }

alaDaUNPVlanRuleRowStatus OBJECT-TYPE
SYNTAX        RowStatus
MAX-ACCESS    read-create
STATUS        current
DESCRIPTION
"The Row status of this table entry."
::= { alaDaUNPVlanRuleEntry 4 }

--
-- UNP Edge Template Vlan Table
--

alaDaUNPETmplVlanTable OBJECT-TYPE
    SYNTAX      SEQUENCE OF AlaDaUNPETmplVlanEntry
    MAX-ACCESS  not-accessible
    STATUS      current
    DESCRIPTION
        "This table contains a list of untagged VLANs configured for an UNP Edge Template."
    ::= { alaIND1DaMIBObjects 56 }

alaDaUNPETmplVlanEntry OBJECT-TYPE
    SYNTAX      AlaDaUNPETmplVlanEntry
    MAX-ACCESS  not-accessible
    STATUS      current
    DESCRIPTION
        "Each of these entries represents an untagged Vlan Edge Template association."
    INDEX { alaDaUNPETmplName, alaDaUNPETmplVlanVID }
    ::= { alaDaUNPETmplVlanTable 1 }

AlaDaUNPETmplVlanEntry ::= SEQUENCE
    {
        alaDaUNPETmplVlanVID		Unsigned32,
        alaDaUNPETmplVlanRowStatus	RowStatus
    }

alaDaUNPETmplVlanVID OBJECT-TYPE
    SYNTAX          Unsigned32 (1..4094)
    MAX-ACCESS      not-accessible
    STATUS          current
    DESCRIPTION
     "Untagged VLAN for an UNP Edge Template."
    ::= { alaDaUNPETmplVlanEntry 1 }

alaDaUNPETmplVlanRowStatus OBJECT-TYPE
    SYNTAX      RowStatus
    MAX-ACCESS  read-create
    STATUS      current
    DESCRIPTION
     "On create, the specified UNP Edge Template must exist in alaDaUNPETmplTable,
      otherwise an entry creation in this table would not be allowed. Deletion of an Edge Template entry in
      alaDaUNPETmplTable would result in deletion of all entries for that Edge Template in the
      alaDaUNPETmplVlanTable."
    ::= { alaDaUNPETmplVlanEntry 2 }

------------------------------------------------------------
-- UNP User Flush Table
------------------------------------------------------------

alaDaUNPUserFlushTable OBJECT-TYPE
    SYNTAX      SEQUENCE OF AlaDaUNPUserFlushEntry
    MAX-ACCESS  not-accessible
    STATUS      current
    DESCRIPTION
        "Table to flush the UNP users based on some criteria
         such as MAC Address, Authentication Type and Port or SAP/Service."
    ::= { alaIND1DaMIBObjects 57 }

alaDaUNPUserFlushEntry OBJECT-TYPE
    SYNTAX      AlaDaUNPUserFlushEntry
    MAX-ACCESS  not-accessible
    STATUS      current
    DESCRIPTION
        "One entry to flush users on the basis of user criteria."
    INDEX { alaDaUNPUserFlushIndex }
    ::= { alaDaUNPUserFlushTable 1 }

AlaDaUNPUserFlushEntry ::= SEQUENCE  {
    alaDaUNPUserFlushIndex         Integer32,
    alaDaUNPUserFlushComplete      INTEGER,
    alaDaUNPUserFlushAuthType      INTEGER,
    alaDaUNPUserFlushMacAddress    MacAddress,
    alaDaUNPUserFlushProfile       SnmpAdminString,
    alaDaUNPUserFlushPortStart 	   InterfaceIndex,
    alaDaUNPUserFlushPortEnd	   InterfaceIndex,
    alaDaUNPUserFlushSapIDIfIndex  InterfaceIndex,
    alaDaUNPUserFlushSapIDEncapVal TmnxEncapVal,
    alaDaUNPUserFlushServiceID     Unsigned32
}

alaDaUNPUserFlushIndex OBJECT-TYPE
    SYNTAX      Integer32(1)
    MAX-ACCESS  not-accessible
    STATUS      current
    DESCRIPTION
        "Flush index."
    ::= { alaDaUNPUserFlushEntry 1 }

alaDaUNPUserFlushComplete OBJECT-TYPE
    SYNTAX     INTEGER {
                   none (1),
                   all (2)
               }
    MAX-ACCESS  read-write
    STATUS      current
    DESCRIPTION
        "Flush all users learnt on all access type ports."
    DEFVAL { none }
    ::= { alaDaUNPUserFlushEntry 2 }

alaDaUNPUserFlushAuthType OBJECT-TYPE
    SYNTAX     INTEGER {
                   noAuth (1),
                   onex (2),
                   mac (3)
               }
    MAX-ACCESS  read-write
    STATUS      current
    DESCRIPTION
        "Flush based on the authentication type of the user."
    ::= { alaDaUNPUserFlushEntry 3 }

alaDaUNPUserFlushMacAddress OBJECT-TYPE
    SYNTAX     MacAddress(SIZE(6))
    MAX-ACCESS  read-write
    STATUS      current
    DESCRIPTION
        "Flush based on a single MAC address."
    ::= { alaDaUNPUserFlushEntry 4 }

alaDaUNPUserFlushProfile OBJECT-TYPE
    SYNTAX        SnmpAdminString (SIZE( 0..32 ))
    MAX-ACCESS    read-write
    STATUS        current
    DESCRIPTION
        "Flush the users learnt on the given Profile."
    ::= { alaDaUNPUserFlushEntry 5 }

alaDaUNPUserFlushPortStart OBJECT-TYPE
    SYNTAX        InterfaceIndex
    MAX-ACCESS    read-write
    STATUS        current
    DESCRIPTION
        "Start of the Port-Range on which the users learnt need to be flushed."
    ::= { alaDaUNPUserFlushEntry 6 }

alaDaUNPUserFlushPortEnd OBJECT-TYPE
    SYNTAX        InterfaceIndex
    MAX-ACCESS    read-write
    STATUS        current
    DESCRIPTION
        "End of the Port-Range on which the users learnt need to be flushed."
    ::= { alaDaUNPUserFlushEntry 7 }

alaDaUNPUserFlushSapIDIfIndex OBJECT-TYPE
    SYNTAX        InterfaceIndex
    MAX-ACCESS    read-write
    STATUS        current
    DESCRIPTION
        "Flush the users learnt on the given SAP-ID Interface Index."
    ::= { alaDaUNPUserFlushEntry 8 }

alaDaUNPUserFlushSapIDEncapVal OBJECT-TYPE
    SYNTAX        TmnxEncapVal
    MAX-ACCESS    read-write
    STATUS        current
    DESCRIPTION
        "Flush the users learnt on the given SAP-ID Encapsulation."
    ::= { alaDaUNPUserFlushEntry 9 }

alaDaUNPUserFlushServiceID OBJECT-TYPE
    SYNTAX        Unsigned32
    MAX-ACCESS    read-write
    STATUS        current
    DESCRIPTION
        "Flush the users learnt of the given service."
    ::= { alaDaUNPUserFlushEntry 10 }

------------------------------------------------------------
-- Classification Rule Customer Domain Id  Based Table
------------------------------------------------------------

alaDaUNPCustDomainRuleTable OBJECT-TYPE
    SYNTAX      SEQUENCE OF AlaDaUNPCustDomainRuleEntry
    MAX-ACCESS  not-accessible
    STATUS      current
    DESCRIPTION
        "Based on customer domain id , Profile Classification table."
    ::= { alaIND1DaMIBObjects 58 }

alaDaUNPCustDomainRuleEntry   OBJECT-TYPE
    SYNTAX   AlaDaUNPCustDomainRuleEntry
    MAX-ACCESS  not-accessible
    STATUS      current
    DESCRIPTION
        "Customer Domain Rule Table Entries ."
    INDEX { alaDaUNPCustDomainRuleId }
    ::= { alaDaUNPCustDomainRuleTable 1 }

AlaDaUNPCustDomainRuleEntry ::= SEQUENCE  {
    alaDaUNPCustDomainRuleId           Integer32,
    alaDaUNPCustDomainRuleVlanTag      Integer32,
    alaDaUNPCustDomainRuleProfile1     SnmpAdminString,
    alaDaUNPCustDomainRuleProfile2     SnmpAdminString,
    alaDaUNPCustDomainRuleProfile3     SnmpAdminString,
    alaDaUNPCustDomainRuleRowStatus    RowStatus
}

alaDaUNPCustDomainRuleId  OBJECT-TYPE
    SYNTAX      Integer32(1..255)
    MAX-ACCESS  not-accessible
    STATUS      current
    DESCRIPTION
        "CustDomain Id ."
    ::= { alaDaUNPCustDomainRuleEntry 1 }

alaDaUNPCustDomainRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPCustDomainRuleEntry 2 }

alaDaUNPCustDomainRuleProfile1 OBJECT-TYPE
    SYNTAX    SnmpAdminString ( SIZE( 0 .. 32 ) )
    MAX-ACCESS read-create
    STATUS      current
    DESCRIPTION
        "Associated Profile ."
    ::= { alaDaUNPCustDomainRuleEntry 3 }

alaDaUNPCustDomainRuleProfile2 OBJECT-TYPE
    SYNTAX    SnmpAdminString ( SIZE( 0 .. 32 ) )
    MAX-ACCESS read-create
    STATUS      current
    DESCRIPTION
        "Associated Profile ."
    ::= { alaDaUNPCustDomainRuleEntry 4 }

alaDaUNPCustDomainRuleProfile3 OBJECT-TYPE
    SYNTAX    SnmpAdminString ( SIZE( 0 .. 32 ) )
    MAX-ACCESS read-create
    STATUS      current
    DESCRIPTION
        "Associated Profile ."
    ::= { alaDaUNPCustDomainRuleEntry 5 }

alaDaUNPCustDomainRuleRowStatus OBJECT-TYPE
    SYNTAX        RowStatus
    MAX-ACCESS    read-create
    STATUS        current
    DESCRIPTION
        "The status of this table entry."
    ::= { alaDaUNPCustDomainRuleEntry 6 }

------------------------------------------------------------
-- Port Template Table --
------------------------------------------------------------

alaDaUNPPortTemplateTable OBJECT-TYPE
    SYNTAX      SEQUENCE OF AlaDaUNPPortTemplateEntry
    MAX-ACCESS  not-accessible
    STATUS      current
    DESCRIPTION
        "Unp Port Template Table."
    ::= { alaIND1DaMIBObjects 59 }

alaDaUNPPortTemplateEntry OBJECT-TYPE
    SYNTAX      AlaDaUNPPortTemplateEntry
    MAX-ACCESS  not-accessible
    STATUS      current
    DESCRIPTION
        "EdgeTemplate Entries."
    INDEX { alaDaUNPPortTemplateName }
    ::= { alaDaUNPPortTemplateTable 1 }

AlaDaUNPPortTemplateEntry ::= SEQUENCE  {
    alaDaUNPPortTemplateName                    SnmpAdminString,
    alaDaUNPPortTemplateAdminState              INTEGER,
    alaDaUNPPortTemplateDirection               INTEGER,
    alaDaUNPPortTemplateDomainID                Unsigned32,
    alaDaUNPPortTemplateClassification          INTEGER,
    alaDaUNPPortTemplateTrustTag                INTEGER,
    alaDaUNPPortTemplateDynamicService          INTEGER,
    alaDaUNPPortTemplateDefaultProfile          SnmpAdminString,
    alaDaUNPPortTemplateAAAProfile              SnmpAdminString,
    alaDaUNPPortTemplateRedirectPortBounce      INTEGER,
    alaDaUNPPortTemplate8021XAuth               INTEGER,
    alaDaUNPPortTemplate8021XAuthPassAlternate  SnmpAdminString,
    alaDaUNPPortTemplate8021XAuthBypass         INTEGER,
    alaDaUNPPortTemplate8021XAuthFailPolicy     INTEGER,
    alaDaUNPPortTemplate8021XAuthTxPeriod       Unsigned32,
    alaDaUNPPortTemplate8021XAuthSuppTimeout    Unsigned32,
    alaDaUNPPortTemplate8021XAuthMaxReq         Unsigned32,
    alaDaUNPPortTemplateMACAuth                 INTEGER,
    alaDaUNPPortTemplateMACAuthPassAlternate    SnmpAdminString,
    alaDaUNPPortTemplateMACAuthAllowEAP         INTEGER,
    alaDaUNPPortTemplateForceL3Learning         INTEGER,
    alaDaUNPPortTemplateForceL3LearningPortBounce INTEGER,
    alaDaUNPPortTemplateRowStatus               RowStatus
}

alaDaUNPPortTemplateName OBJECT-TYPE
    SYNTAX          SnmpAdminString (SIZE(1 .. 32))
    MAX-ACCESS      not-accessible
    STATUS          current
    DESCRIPTION
        "The name of the Port Template."
    ::= { alaDaUNPPortTemplateEntry 1 }

alaDaUNPPortTemplateAdminState OBJECT-TYPE
    SYNTAX          INTEGER {
                        enable (1),
                        disable (2)
                    }
    MAX-ACCESS      read-create
    STATUS          current
    DESCRIPTION
        "To enable/disable the Port Template."
    DEFVAL          { enable }
    ::= { alaDaUNPPortTemplateEntry 2 }

alaDaUNPPortTemplateDirection OBJECT-TYPE
    SYNTAX          INTEGER {
                    both    (1),
                    in      (2),
                    noVal   (3)
                    }
    MAX-ACCESS      read-create
    STATUS          current
    DESCRIPTION
        "The current value of the administrative controlled
          directions parameter for the Port Template."
    DEFVAL          { both }
    ::= { alaDaUNPPortTemplateEntry 3 }

alaDaUNPPortTemplateDomainID OBJECT-TYPE
    SYNTAX      Unsigned32 (0..4294967295)
    MAX-ACCESS  read-create
    STATUS      current
    DESCRIPTION
        "The Domain that this port belongs to.  Default is on domain 0."
    ::= { alaDaUNPPortTemplateEntry 4 }

alaDaUNPPortTemplateClassification OBJECT-TYPE
    SYNTAX          INTEGER {
                        enable (1),
                        disable (2)
                    }
    MAX-ACCESS      read-create
    STATUS          current
    DESCRIPTION
        "To enable/disable Classification on the Port Template."
    DEFVAL          { enable }
    ::= { alaDaUNPPortTemplateEntry 5 }

alaDaUNPPortTemplateTrustTag OBJECT-TYPE
    SYNTAX          INTEGER {
                        enable (1),
                        disable (2)
                     }
    MAX-ACCESS              read-create
    STATUS          current
    DESCRIPTION
        "To enable/disable Truth Tag on the Port Template."
    DEFVAL          { enable }
    ::= { alaDaUNPPortTemplateEntry 6 }

alaDaUNPPortTemplateDynamicService OBJECT-TYPE
    SYNTAX          INTEGER {
                        none (1),
                        spb  (2),
                        vxlan (3)
                    }
    MAX-ACCESS              read-create
    STATUS          current
    DESCRIPTION
        "Indicates the type of dynamic service for the port-template.
	Dynamic Service type SPB/VXLAN are applicable for Access type UNP port."
    DEFVAL          { none }
    ::= { alaDaUNPPortTemplateEntry 7 }

alaDaUNPPortTemplateDefaultProfile OBJECT-TYPE
    SYNTAX          SnmpAdminString (SIZE(0 .. 32))
    MAX-ACCESS      read-create
    STATUS          current
    DESCRIPTION
        "The default profile for the Port Template."
    ::= { alaDaUNPPortTemplateEntry 8 }

alaDaUNPPortTemplateAAAProfile OBJECT-TYPE
    SYNTAX          SnmpAdminString (SIZE(0 .. 32))
    MAX-ACCESS      read-create
    STATUS          current
    DESCRIPTION
        "The AAA profile for the Port Template."
    ::= { alaDaUNPPortTemplateEntry 9 }

alaDaUNPPortTemplateRedirectPortBounce OBJECT-TYPE
    SYNTAX          INTEGER {
                        enable (1),
                        disable (2)
                    }
    MAX-ACCESS      read-create
    STATUS          current
    DESCRIPTION
        "To enable/disable Redirect Port bounce on the Port Template."
    DEFVAL          { enable }
    ::= { alaDaUNPPortTemplateEntry 10 }

alaDaUNPPortTemplate8021XAuth OBJECT-TYPE
    SYNTAX          INTEGER {
                        enable (1),
                        disable (2)
                    }
    MAX-ACCESS      read-create
    STATUS          current
    DESCRIPTION
        "To enable/disable 802.1x authentication on the Port Template."
    DEFVAL          { enable }
    ::= { alaDaUNPPortTemplateEntry 11 }

alaDaUNPPortTemplate8021XAuthPassAlternate OBJECT-TYPE
    SYNTAX                  SnmpAdminString (SIZE(0 .. 32))
    MAX-ACCESS      read-create
    STATUS          current
    DESCRIPTION
        "The Pass-Alternate profile for 802.1X authentication on the Port Template."
    ::= { alaDaUNPPortTemplateEntry 12 }

alaDaUNPPortTemplate8021XAuthBypass OBJECT-TYPE
    SYNTAX          INTEGER {
                        enable (1),
                        disable (2)
                    }
    MAX-ACCESS              read-create
    STATUS          current
    DESCRIPTION
        "To enable/disable 802.1x authentication bypass on the Port Template."
    DEFVAL          { enable }
    ::= { alaDaUNPPortTemplateEntry 13 }

alaDaUNPPortTemplate8021XAuthFailPolicy OBJECT-TYPE
    SYNTAX          INTEGER {
                        default (1),
                        mac (2)
                    }
    MAX-ACCESS              read-create
    STATUS          current
    DESCRIPTION
        "802.1x authentication failure policy for the Port Template."
    DEFVAL          { mac }
    ::= { alaDaUNPPortTemplateEntry 14 }

alaDaUNPPortTemplate8021XAuthTxPeriod OBJECT-TYPE
    SYNTAX          Unsigned32 (1..60)
    UNITS           "seconds"
    MAX-ACCESS      read-create
    STATUS          current
    DESCRIPTION
        "802.1x authentication Tx period."
    DEFVAL          { 30 }
    ::= { alaDaUNPPortTemplateEntry 15 }

alaDaUNPPortTemplate8021XAuthSuppTimeout OBJECT-TYPE
    SYNTAX          Unsigned32 (1..120)
    UNITS           "seconds"
    MAX-ACCESS      read-create
    STATUS          current
    DESCRIPTION
        "802.1x authentication supplicant Timeout period."
    DEFVAL          { 30 }
    ::= { alaDaUNPPortTemplateEntry 16 }

alaDaUNPPortTemplate8021XAuthMaxReq OBJECT-TYPE
    SYNTAX          Unsigned32 (1..3)
    MAX-ACCESS      read-create
    STATUS          current
    DESCRIPTION
        "802.1x authentication Max requests."
    DEFVAL          { 2 }
    ::= { alaDaUNPPortTemplateEntry 17 }

alaDaUNPPortTemplateMACAuth OBJECT-TYPE
    SYNTAX          INTEGER {
                        enable (1),
                        disable (2)
                    }
    MAX-ACCESS              read-create
    STATUS          current
    DESCRIPTION
        "To enable/disable MAC authentication on the Port Template."
    DEFVAL          { enable }
    ::= { alaDaUNPPortTemplateEntry 18 }

alaDaUNPPortTemplateMACAuthPassAlternate OBJECT-TYPE
    SYNTAX          SnmpAdminString (SIZE(0 .. 32))
    MAX-ACCESS      read-create
    STATUS          current
    DESCRIPTION
        "The Pass-Alternate profile for MAC authentication on the Port Template."
    ::= { alaDaUNPPortTemplateEntry 19 }

alaDaUNPPortTemplateMACAuthAllowEAP OBJECT-TYPE
    SYNTAX          INTEGER {
                        pass (1),
                        fail (2),
                        noAuth (3),
                        none (4)
                    }
    MAX-ACCESS      read-create
    STATUS          current
    DESCRIPTION
        "To enable/disable MAC authentication on the Port Template."
    DEFVAL          { none }
    ::= { alaDaUNPPortTemplateEntry 20 }

alaDaUNPPortTemplateForceL3Learning  OBJECT-TYPE
    SYNTAX     INTEGER {
        enable (1),
        disable (2)
    }
    MAX-ACCESS  read-create
    STATUS      current
    DESCRIPTION
              "UNP force L3 learning status on the UNP Port-Template."
    ::= { alaDaUNPPortTemplateEntry 21 }

alaDaUNPPortTemplateForceL3LearningPortBounce OBJECT-TYPE
    SYNTAX     INTEGER {
        enable (1),
        disable (2)
    }
    MAX-ACCESS  read-create
    STATUS      current
    DESCRIPTION
              "Port-Bounce associated with UNP force L3 learning status on the UNP Port-Template."
    ::= { alaDaUNPPortTemplateEntry 22 }

alaDaUNPPortTemplateRowStatus OBJECT-TYPE
    SYNTAX          RowStatus
    MAX-ACCESS      read-create
    STATUS          current
    DESCRIPTION
        "Row Status for this table."
    ::= { alaDaUNPPortTemplateEntry 23 }

------------------------------------------------------------
-- Profile Table configuration MIB --
------------------------------------------------------------

alaDaUNPProfileTable OBJECT-TYPE
    SYNTAX        SEQUENCE OF AlaDaUNPProfileEntry
    MAX-ACCESS    not-accessible
    STATUS        current
    DESCRIPTION
        "This table stores the profiles created in the system."
    ::= { alaIND1DaMIBObjects 60 }

alaDaUNPProfileEntry OBJECT-TYPE
    SYNTAX        AlaDaUNPProfileEntry
    MAX-ACCESS    not-accessible
    STATUS        current
    DESCRIPTION
        "Profile entry."
    INDEX { alaDaUNPProfileName }
    ::= { alaDaUNPProfileTable 1 }

AlaDaUNPProfileEntry ::= SEQUENCE {
    alaDaUNPProfileName                     SnmpAdminString,
    alaDaUNPProfileAuthenticationFlag       INTEGER,
    alaDaUNPProfileMobileTag                INTEGER,
    alaDaUNPProfileCPortalAuthentication    INTEGER,
    alaDaUNPProfileRedirect                 INTEGER,
    alaDaUNPProfileQoSPolicy		    SnmpAdminString,
    alaDaUNPProfilePeriodPolicy             SnmpAdminString,
    alaDaUNPProfileCPortalProfile           SnmpAdminString,
    alaDaUNPProfileLocationPolicy           SnmpAdminString,
    alaDaUNPProfileSaaProfile               SnmpAdminString,
    alaDaUNPProfileInactivityInterval       Integer32,
    alaDaUNPProfileKerberosAuthentication   INTEGER,
    alaDaUNPProfileMaxIngressBandwidth      Integer32,
    alaDaUNPProfileMaxEgressBandwidth       Integer32,
    alaDaUNPProfileMaxIngressDepth          Integer32,
    alaDaUNPProfileMaxEgressDepth           Integer32,
    alaDaUNPProfileRowStatus                RowStatus,
    alaDaUNPProfileAFDConfig                INTEGER
}

alaDaUNPProfileName OBJECT-TYPE
    SYNTAX        SnmpAdminString (SIZE(1 .. 32))
    MAX-ACCESS    not-accessible
    STATUS        current
    DESCRIPTION
        "The name of the UNP profile."
    ::= { alaDaUNPProfileEntry 1 }

alaDaUNPProfileAuthenticationFlag OBJECT-TYPE
    SYNTAX          INTEGER {
                        enable (1),
                        disable (2)
                    }
    MAX-ACCESS      read-create
    STATUS          current
    DESCRIPTION
        "UNP profile authentication flag."
    ::= { alaDaUNPProfileEntry 2 }

alaDaUNPProfileMobileTag OBJECT-TYPE
    SYNTAX          INTEGER {
                        enable (1),
                        disable (2)
                    }
    MAX-ACCESS      read-create
    STATUS          current
    DESCRIPTION
        "UNP profile Mobile Tag flag."
    ::= { alaDaUNPProfileEntry 3 }

alaDaUNPProfileCPortalAuthentication OBJECT-TYPE
    SYNTAX          INTEGER {
                        enable (1),
                        disable (2)
                    }
    MAX-ACCESS      read-create
    STATUS          current
    DESCRIPTION
        "UNP profile Captive Profile Authentication flag."
    ::= { alaDaUNPProfileEntry 4 }

alaDaUNPProfileRedirect OBJECT-TYPE
    SYNTAX          INTEGER {
                        enable (1),
                        disable (2)
                    }
    MAX-ACCESS      read-create
    STATUS          current
    DESCRIPTION
        "UNP profile redirect flag."
    ::= { alaDaUNPProfileEntry 5 }

alaDaUNPProfileQoSPolicy OBJECT-TYPE
    SYNTAX        SnmpAdminString (SIZE(0 .. 32))
    MAX-ACCESS    read-create
    STATUS        current
    DESCRIPTION
        "The name of the QoS Policy List name that will be used if this
        User Network Profile is applied for a given device."
    ::= { alaDaUNPProfileEntry 6 }

alaDaUNPProfilePeriodPolicy OBJECT-TYPE
    SYNTAX        SnmpAdminString (SIZE(0 .. 32))
    MAX-ACCESS    read-create
    STATUS        current
    DESCRIPTION
        "The name of the Period Policy List name that will be used if this
        User Network Profile is applied for a given device."
    ::= { alaDaUNPProfileEntry 7 }

alaDaUNPProfileCPortalProfile OBJECT-TYPE
    SYNTAX        SnmpAdminString (SIZE(0 .. 32))
    MAX-ACCESS    read-create
    STATUS        current
    DESCRIPTION
        "The name of the Captive Portal Profile Policy List name that will be used if this
        User Network Profile is applied for a given device."
    ::= { alaDaUNPProfileEntry 8 }

alaDaUNPProfileLocationPolicy OBJECT-TYPE
    SYNTAX        SnmpAdminString (SIZE(0 .. 32))
    MAX-ACCESS    read-create
    STATUS        current
    DESCRIPTION
        "The name of the Location Policy name that will be used if this
        User Network Profile is applied for a given device."
    ::= { alaDaUNPProfileEntry 9 }

alaDaUNPProfileSaaProfile OBJECT-TYPE
    SYNTAX        SnmpAdminString (SIZE(0 .. 32))
    MAX-ACCESS    read-create
    STATUS        current
    DESCRIPTION
        "The name of the SAA profile name that will be used if this
            User Network Profile is applied for a given device."
    ::= { alaDaUNPProfileEntry 10 }

alaDaUNPProfileInactivityInterval OBJECT-TYPE
    SYNTAX        Integer32 ( 10..600)
    UNITS         "minutes"
    MAX-ACCESS    read-create
    STATUS        current
    DESCRIPTION
        "Inactivity Timer value for the UNP profile users in minutes."
    DEFVAL { 300 }
    ::= { alaDaUNPProfileEntry 11 }

alaDaUNPProfileKerberosAuthentication OBJECT-TYPE
    SYNTAX          INTEGER {
                        enable (1),
                        disable (2)
                    }
    MAX-ACCESS      read-create
    STATUS          current
    DESCRIPTION
        "UNP profile Kerberos Authentication flag."
    ::= { alaDaUNPProfileEntry 12 }

alaDaUNPProfileMaxIngressBandwidth OBJECT-TYPE
    SYNTAX      Integer32 (-1|0..2147483647)
    UNITS       "kilobits per second"
    MAX-ACCESS  read-create
    STATUS      current
    DESCRIPTION
        "Maximum Ingress Bandwidth (Kbits/sec or Mbits/sec) allowed for traffic associated to this profile.
         If value is set to -1, then the Ingress Bandwidth specified for the profile is unconfigured."
    DEFVAL { 0 }
    ::= { alaDaUNPProfileEntry 13 }

alaDaUNPProfileMaxEgressBandwidth OBJECT-TYPE
    SYNTAX      Integer32 (-1|0..2147483647)
    UNITS       "kilobits per second"
    MAX-ACCESS  read-create
    STATUS      current
    DESCRIPTION
        "Maximum Egress Bandwidth (Kbits/sec or Mbits/sec) allowed for traffic associated to this profile.
         If value is set to -1, then the Egress Bandwidth specified for the profile is unconfigured."
    DEFVAL { 0 }
    ::= { alaDaUNPProfileEntry 14 }

alaDaUNPProfileMaxIngressDepth OBJECT-TYPE
    SYNTAX      Integer32 (-1|0..16384)
    MAX-ACCESS  read-create
    STATUS      current
    DESCRIPTION
        "Maximum Ingress Depth associated to Bandwidth.
         If set to -1, then the Depth associated with the profile is unconfigured."
    DEFVAL { 0 }
    ::= { alaDaUNPProfileEntry 15 }

alaDaUNPProfileMaxEgressDepth OBJECT-TYPE
    SYNTAX      Integer32 (-1|0..16384)
    MAX-ACCESS  read-create
    STATUS      current
    DESCRIPTION
        "Maximum Egress Depth associated to Bandwidth.
         If set to -1, then the Depth associated with the profile is unconfigured."
    DEFVAL { 0 }
    ::= { alaDaUNPProfileEntry 16 }

alaDaUNPProfileRowStatus OBJECT-TYPE
    SYNTAX        RowStatus
    MAX-ACCESS    read-create
    STATUS        current
    DESCRIPTION
        "The row status of this table entry."
    ::= { alaDaUNPProfileEntry 17 }

alaDaUNPProfileAFDConfig OBJECT-TYPE
     SYNTAX      INTEGER {
                     admin       (1),
                     autoFabric  (2)
                 }
    MAX-ACCESS  read-only
    STATUS      current
    DESCRIPTION
         "Configuration is made by admin or auto-fabric on
         this profile"
    DEFVAL { admin }
    ::= { alaDaUNPProfileEntry 18 }

--------------------------------------------------
-- VLAN Profile MAP Table configuration MIB --
--------------------------------------------------

alaDaUNPProfileMapVlanTable OBJECT-TYPE
    SYNTAX        SEQUENCE OF AlaDaUNPProfileMapVlanEntry
    MAX-ACCESS    not-accessible
    STATUS        current
    DESCRIPTION
        "This table stores the VLAN profiles created in the system.
        The entries would be mapped to vlan ID which would be used
        by device authentication for classifying users."
    ::= { alaIND1DaMIBObjects 61 }

alaDaUNPProfileMapVlanEntry OBJECT-TYPE
    SYNTAX        AlaDaUNPProfileMapVlanEntry
    MAX-ACCESS    not-accessible
    STATUS        current
    DESCRIPTION
        "VLAN Profile entry."
    INDEX { alaDaUNPProfileName }
    ::= { alaDaUNPProfileMapVlanTable 1 }

AlaDaUNPProfileMapVlanEntry ::= SEQUENCE  {
    alaDaUNPProfileMapVlanVlanID            Unsigned32,
    alaDaUNPProfileMapVlanRowStatus         RowStatus
}

alaDaUNPProfileMapVlanVlanID OBJECT-TYPE
    SYNTAX        Unsigned32 (1 .. 4094)
    MAX-ACCESS    read-create
    STATUS        current
    DESCRIPTION
        "The VLAN ID for this profile."
    ::= { alaDaUNPProfileMapVlanEntry 1 }

alaDaUNPProfileMapVlanRowStatus OBJECT-TYPE
    SYNTAX        RowStatus
    MAX-ACCESS    read-create
    STATUS        current
    DESCRIPTION
        "The row status of this table entry."
    ::= { alaDaUNPProfileMapVlanEntry 2 }

------------------------------------------------------------
-- SPB Profile Map Table configuration MIB --
------------------------------------------------------------

alaDaUNPProfileMapSpbTable OBJECT-TYPE
    SYNTAX        SEQUENCE OF AlaDaUNPProfileMapSpbEntry
    MAX-ACCESS    not-accessible
    STATUS        current
    DESCRIPTION
        "This table stores the Service Classification profiles created in the system.
        The entries provides information to classify device in the Service domain."
    ::= { alaIND1DaMIBObjects 62 }

alaDaUNPProfileMapSpbEntry OBJECT-TYPE
    SYNTAX        AlaDaUNPProfileMapSpbEntry
    MAX-ACCESS    not-accessible
    STATUS        current
    DESCRIPTION
        "Service Classification Profile entry"
    INDEX { alaDaUNPProfileName }
    ::= { alaDaUNPProfileMapSpbTable 1 }

AlaDaUNPProfileMapSpbEntry ::= SEQUENCE  {
    alaDaUNPProfileMapSpbEncapVal          TmnxEncapVal,
    alaDaUNPProfileMapSpbIsid              Unsigned32,
    alaDaUNPProfileMapSpbBVlan             Unsigned32,
    alaDaUNPProfileMapSpbMulticastMode     INTEGER,
    alaDaUNPProfileMapSpbVlanXlation    INTEGER,
    alaDaUNPProfileMapSpbRowStatus         RowStatus
}

alaDaUNPProfileMapSpbEncapVal OBJECT-TYPE
    SYNTAX        TmnxEncapVal
    MAX-ACCESS    read-create
    STATUS        current
    DESCRIPTION
        "The encapsulation to be used for the SAP connecting to the service."
    ::= { alaDaUNPProfileMapSpbEntry 1 }

alaDaUNPProfileMapSpbIsid OBJECT-TYPE
    SYNTAX        Unsigned32 (256..16777214)
    MAX-ACCESS    read-create
    STATUS        current
    DESCRIPTION
        "The object represent the I-SID that is to be dynamically created when
        SPB Service ID does not exist in the system and must be
        used along with B-VLAN."
    ::= { alaDaUNPProfileMapSpbEntry 2 }

alaDaUNPProfileMapSpbBVlan OBJECT-TYPE
    SYNTAX        Unsigned32 (1..4094)
    MAX-ACCESS    read-create
    STATUS        current
    DESCRIPTION
        "The Backbone VLAN ID (BVLAN) used for the I-SID specified in alaUNPProfileMapSpbIsid.
        This object must be specified along with alaUNPProfileMapSpbIsid."
    ::= { alaDaUNPProfileMapSpbEntry 3 }

alaDaUNPProfileMapSpbMulticastMode OBJECT-TYPE
    SYNTAX          INTEGER { headend(1), tandem(2) }
    MAX-ACCESS      read-create
    STATUS          current
    DESCRIPTION
        "To configure the multicast replication mode for each service:
        Head-end(1) where a non-unicast packet entering the SAP port
        is replicated once for each receiver in the b-domain using its
        unicast BMAC.
        Tandem(2) where a non-unicast packet entering the SAP port is
        replicated once at each node using the multicast group address."
    DEFVAL                  { headend }
    ::= { alaDaUNPProfileMapSpbEntry 4 }

alaDaUNPProfileMapSpbVlanXlation OBJECT-TYPE
    SYNTAX          INTEGER { enable (1), disable (2) }
    MAX-ACCESS      read-create
    STATUS          current
    DESCRIPTION
        "To enable/disable the vlan translation for all the SAPs configured
        in this service if the corresponding access ports for the SAPs also
        has the VLAN translation enabled."
    DEFVAL          { enable }
    ::= { alaDaUNPProfileMapSpbEntry 5 }

alaDaUNPProfileMapSpbRowStatus OBJECT-TYPE
    SYNTAX        RowStatus
    MAX-ACCESS    read-create
    STATUS        current
    DESCRIPTION
        "The row status of this table entry."
    ::= { alaDaUNPProfileMapSpbEntry 6 }

------------------------------------------------------------
-- VXLAN Profile Map Table configuration MIB --
------------------------------------------------------------

alaDaUNPProfileMapVxlanTable OBJECT-TYPE
    SYNTAX        SEQUENCE OF AlaDaUNPProfileMapVxlanEntry
    MAX-ACCESS    not-accessible
    STATUS        current
    DESCRIPTION
        "This table stores the Service Classification profiles created in the system.
        The entries provides information to classify device in the VXLAN Service domain."
    ::= { alaIND1DaMIBObjects 63 }

alaDaUNPProfileMapVxlanEntry OBJECT-TYPE
    SYNTAX        AlaDaUNPProfileMapVxlanEntry
    MAX-ACCESS    not-accessible
    STATUS        current
    DESCRIPTION
        "VXLAN Service Classification Profile entry"
    INDEX {alaDaUNPProfileName}
    ::= { alaDaUNPProfileMapVxlanTable 1 }

AlaDaUNPProfileMapVxlanEntry ::= SEQUENCE  {
    alaDaUNPProfileMapVxlanEncapVal                 TmnxEncapVal,
    alaDaUNPProfileMapVxlanVnid                     Unsigned32,
    alaDaUNPProfileMapVxlanFarEndIPList		    SnmpAdminString,
    alaDaUNPProfileMapVxlanMulticastIPAddressType   InetAddressType,
    alaDaUNPProfileMapVxlanMulticastIPAddress       InetAddress,
    alaDaUNPProfileMapVxlanVlanXlation              INTEGER,
    alaDaUNPProfileMapVxlanMulticastMode            INTEGER,
    alaDaUNPProfileMapVxlanRowStatus                RowStatus
}

alaDaUNPProfileMapVxlanEncapVal OBJECT-TYPE
    SYNTAX        TmnxEncapVal
    MAX-ACCESS    read-create
    STATUS        current
    DESCRIPTION
        "The encapsulation to be used for the SAP connecting to the service."
    ::= { alaDaUNPProfileMapVxlanEntry 1 }

alaDaUNPProfileMapVxlanVnid OBJECT-TYPE
    SYNTAX        Unsigned32 (1..16777214)
    MAX-ACCESS    read-create
    STATUS        current
    DESCRIPTION
        "The object represnet the VNID that is to be used to dynamically
        create a VXLAN service."
    ::= { alaDaUNPProfileMapVxlanEntry 2 }

alaDaUNPProfileMapVxlanFarEndIPList OBJECT-TYPE
    SYNTAX        SnmpAdminString (SIZE(0 .. 32))
    MAX-ACCESS    read-create
    STATUS        current
    DESCRIPTION
        "The name of the Far End IP List that will be used if this
        User Network Profile is applied for a given device."
    ::= { alaDaUNPProfileMapVxlanEntry 3 }

alaDaUNPProfileMapVxlanMulticastIPAddressType OBJECT-TYPE
    SYNTAX          InetAddressType
    MAX-ACCESS      read-create
    STATUS          current
    DESCRIPTION
        "The IP address type of the multicast group IP address."
    ::= { alaDaUNPProfileMapVxlanEntry 4 }

alaDaUNPProfileMapVxlanMulticastIPAddress OBJECT-TYPE
    SYNTAX          InetAddress
    MAX-ACCESS      read-create
    STATUS          current
    DESCRIPTION
        "The multicast group IP address."
    ::= { alaDaUNPProfileMapVxlanEntry 5 }

alaDaUNPProfileMapVxlanVlanXlation OBJECT-TYPE
    SYNTAX          INTEGER {
                        enable (1),
                        disable (2)
                    }
    MAX-ACCESS      read-create
    STATUS      current
    DESCRIPTION
        "To enable/disable the vlan translation for all the SAPs configured
        in this service if the corresponding access ports for the SAPs also
        has the vlan translation enabled."
    DEFVAL          { enable }
    ::= { alaDaUNPProfileMapVxlanEntry 6 }

alaDaUNPProfileMapVxlanMulticastMode OBJECT-TYPE
    SYNTAX      INTEGER {
                    headend (1),
                    tandem (2),
                    hybrid (3)
                }
    MAX-ACCESS      read-create
    STATUS          current
    DESCRIPTION
        "To configure the multicast replication mode for each service:
        Head-end(1) where a non-unicast packet entering the SAP port
        is replicated once for each receiver in the b-domain using its
        unicast BMAC.
        Tandem(2) where a non-unicast packet entering the SAP port is
        replicated once at each node using the multicast group address."
    DEFVAL          { headend }
    ::= { alaDaUNPProfileMapVxlanEntry 7 }

alaDaUNPProfileMapVxlanRowStatus OBJECT-TYPE
    SYNTAX        RowStatus
    MAX-ACCESS    read-create
    STATUS        current
    DESCRIPTION
        "The row status of this table entry."
    ::= { alaDaUNPProfileMapVxlanEntry 8 }

--------------------------------------------------
-- Static Profile MAP Table configuration MIB --
--------------------------------------------------

alaDaUNPProfileMapStaticTable OBJECT-TYPE
    SYNTAX        SEQUENCE OF AlaDaUNPProfileMapStaticEntry
    MAX-ACCESS    not-accessible
    STATUS        current
    DESCRIPTION
        "This table stores the Static profiles created in the system."
    ::= { alaIND1DaMIBObjects 64 }

alaDaUNPProfileMapStaticEntry OBJECT-TYPE
    SYNTAX        AlaDaUNPProfileMapStaticEntry
    MAX-ACCESS    not-accessible
    STATUS        current
    DESCRIPTION
        "Static Profile entry."
    INDEX { alaDaUNPProfileName }
    ::= { alaDaUNPProfileMapStaticTable 1 }

AlaDaUNPProfileMapStaticEntry ::= SEQUENCE  {
    alaDaUNPProfileMapStaticEncapVal        TmnxEncapVal,
    alaDaUNPProfileMapStaticServiceID       Unsigned32,
    alaDaUNPProfileMapStaticRowStatus       RowStatus
}

alaDaUNPProfileMapStaticEncapVal OBJECT-TYPE
    SYNTAX        TmnxEncapVal
    MAX-ACCESS    read-create
    STATUS        current
    DESCRIPTION
        "The encapsulation to be used for the SAP connecting to the service."
    ::= { alaDaUNPProfileMapStaticEntry 1 }

alaDaUNPProfileMapStaticServiceID OBJECT-TYPE
    SYNTAX        Unsigned32
    MAX-ACCESS    read-create
    STATUS        current
    DESCRIPTION
        "The Service ID for this profile."
    ::= { alaDaUNPProfileMapStaticEntry 2 }

alaDaUNPProfileMapStaticRowStatus OBJECT-TYPE
    SYNTAX        RowStatus
    MAX-ACCESS    read-create
    STATUS        current
    DESCRIPTION
        "The row status of this table entry."
    ::= { alaDaUNPProfileMapStaticEntry 3 }

--------------------------------------------------------------
-- Mac , IpAddress, Group Classification Table
--------------------------------------------------------------

alaDaUNPCustDomainMacIpRuleTable  OBJECT-TYPE
    SYNTAX  SEQUENCE OF AlaDaUNPCustDomainMacIpRuleEntry
    MAX-ACCESS  not-accessible
    STATUS  current
    DESCRIPTION
        "Mac Address,IP  & customer domain classification table ."
    ::= { alaIND1DaMIBObjects 65 }

alaDaUNPCustDomainMacIpRuleEntry OBJECT-TYPE
    SYNTAX  AlaDaUNPCustDomainMacIpRuleEntry
    MAX-ACCESS  not-accessible
    STATUS  current
    DESCRIPTION
    " Mac Ip & customer domain  based  classification rule entries ."
    INDEX {
              alaDaUNPCustDomainMacIpRuleMacAddr,
              alaDaUNPCustDomainMacIpRuleIpAddrType,
              alaDaUNPCustDomainMacIpRuleIpAddr,
              alaDaUNPCustDomainMacIpRuleDomainId
          }
    ::= { alaDaUNPCustDomainMacIpRuleTable 1 }

AlaDaUNPCustDomainMacIpRuleEntry ::= SEQUENCE  {
    alaDaUNPCustDomainMacIpRuleMacAddr       MacAddress,
    alaDaUNPCustDomainMacIpRuleIpAddrType    InetAddressType,
    alaDaUNPCustDomainMacIpRuleIpAddr        InetAddress,
    alaDaUNPCustDomainMacIpRuleDomainId      Integer32,
    alaDaUNPCustDomainMacIpRuleVlanTag       Integer32,
    alaDaUNPCustDomainMacIpRuleProfile1      SnmpAdminString,
    alaDaUNPCustDomainMacIpRuleProfile2      SnmpAdminString,
    alaDaUNPCustDomainMacIpRuleProfile3      SnmpAdminString,
    alaDaUNPCustDomainMacIpRuleRowStatus     RowStatus,
    alaDaUNPCustDomainMacIpRuleIpMaskType    InetAddressType,
    alaDaUNPCustDomainMacIpRuleIpMask        InetAddress
}

alaDaUNPCustDomainMacIpRuleMacAddr    OBJECT-TYPE
    SYNTAX  MacAddress (SIZE(6))
    MAX-ACCESS not-accessible
    STATUS  current
    DESCRIPTION
        "Classification Rule mac Address."
    ::= { alaDaUNPCustDomainMacIpRuleEntry 1 }

alaDaUNPCustDomainMacIpRuleIpAddrType OBJECT-TYPE
    SYNTAX  InetAddressType
    MAX-ACCESS  not-accessible
    STATUS current
    DESCRIPTION
        "The IP address type ."
    ::= { alaDaUNPCustDomainMacIpRuleEntry 2 }

alaDaUNPCustDomainMacIpRuleIpAddr OBJECT-TYPE
    SYNTAX  InetAddress
    MAX-ACCESS  not-accessible
    STATUS  current
    DESCRIPTION
        "The IP network address ."
    ::= { alaDaUNPCustDomainMacIpRuleEntry 3 }

alaDaUNPCustDomainMacIpRuleDomainId OBJECT-TYPE
    SYNTAX       Integer32(0..255)
    MAX-ACCESS    not-accessible
    STATUS        current
    DESCRIPTION
        "Classification Rule Group Id."
    ::= { alaDaUNPCustDomainMacIpRuleEntry 4 }

alaDaUNPCustDomainMacIpRuleVlanTag  OBJECT-TYPE
    SYNTAX        Integer32 (0..4094)
    MAX-ACCESS    read-create
    STATUS        current
    DESCRIPTION
        "The VLAN Tag to be used for classification of tagged pkts.
         VLAN Tag of 0 indicates no VLAN is associated. The VLAN Tag is of the
         Q-in-Q VLAN Tag format, where the value of the outer 802.1Q VLAN ID is
         encoded in the least significant 16 bits, and the value of the inner
         VLAN ID is encoded in the most significant 16 bits."
    ::= { alaDaUNPCustDomainMacIpRuleEntry 5 }

alaDaUNPCustDomainMacIpRuleProfile1 OBJECT-TYPE
    SYNTAX  SnmpAdminString ( SIZE( 1 .. 32 ) )
    MAX-ACCESS  read-create
    STATUS  current
    DESCRIPTION
        "The  profile name in the User Network Profile Table to be
        applied."
    ::= { alaDaUNPCustDomainMacIpRuleEntry 6 }

alaDaUNPCustDomainMacIpRuleProfile2  OBJECT-TYPE
    SYNTAX  SnmpAdminString ( SIZE( 1 .. 32 ) )
    MAX-ACCESS  read-create
    STATUS  current
    DESCRIPTION
        "The  profile name in the User Network Profile Table to be
        applied."
    ::= { alaDaUNPCustDomainMacIpRuleEntry 7 }

alaDaUNPCustDomainMacIpRuleProfile3  OBJECT-TYPE
    SYNTAX  SnmpAdminString ( SIZE( 1 .. 32 ) )
    MAX-ACCESS  read-create
    STATUS  current
    DESCRIPTION
        "The  profile name in the User Network Profile Table to be
        applied."
    ::= { alaDaUNPCustDomainMacIpRuleEntry 8 }

alaDaUNPCustDomainMacIpRuleRowStatus OBJECT-TYPE
    SYNTAX        RowStatus
    MAX-ACCESS    read-create
    STATUS        current
    DESCRIPTION
        "The status of this table entry."
    ::= { alaDaUNPCustDomainMacIpRuleEntry 9 }

alaDaUNPCustDomainMacIpRuleIpMaskType OBJECT-TYPE
    SYNTAX  InetAddressType
                {
                    ipv4(1),
                    ipv6(2)
                }
    MAX-ACCESS  read-create
    STATUS  current
    DESCRIPTION
        "The IP mask type. This object is mandatory."
    ::= { alaDaUNPCustDomainMacIpRuleEntry 10 }

alaDaUNPCustDomainMacIpRuleIpMask OBJECT-TYPE
    SYNTAX  InetAddress (SIZE (4|16))
    MAX-ACCESS  read-create
    STATUS  current
    DESCRIPTION
        "The IP network mask applying to the IP network address.
         This object is mandatory."
    ::= { alaDaUNPCustDomainMacIpRuleEntry 11 }

--
-- UNP Port Template Vlan Table
--

alaDaUNPPortTemplateVlanTable OBJECT-TYPE
    SYNTAX      SEQUENCE OF AlaDaUNPPortTemplateVlanEntry
    MAX-ACCESS  not-accessible
    STATUS      current
    DESCRIPTION
        "This table contains a list of untagged VLANs configured for an UNP Port Template."
    ::= { alaIND1DaMIBObjects 66 }

alaDaUNPPortTemplateVlanEntry OBJECT-TYPE
    SYNTAX      AlaDaUNPPortTemplateVlanEntry
    MAX-ACCESS  not-accessible
    STATUS      current
    DESCRIPTION
        "Each of these entries represents an untagged Vlan Port Template association."
    INDEX { alaDaUNPPortTemplateName, alaDaUNPPortTemplateVlanVID }
    ::= { alaDaUNPPortTemplateVlanTable 1 }

AlaDaUNPPortTemplateVlanEntry ::= SEQUENCE
    {
        alaDaUNPPortTemplateVlanVID        Unsigned32,
        alaDaUNPPortTemplateVlanRowStatus  RowStatus
    }

alaDaUNPPortTemplateVlanVID OBJECT-TYPE
    SYNTAX          Unsigned32 (1..4094)
    MAX-ACCESS      not-accessible
    STATUS          current
    DESCRIPTION
     "Untagged VLAN for an UNP Port Template."
    ::= { alaDaUNPPortTemplateVlanEntry 1 }

alaDaUNPPortTemplateVlanRowStatus OBJECT-TYPE
    SYNTAX      RowStatus
    MAX-ACCESS  read-create
    STATUS      current
    DESCRIPTION
     "On create, the specified UNP Port Template must exist in alaDaUNPPortTemplateTable,
      otherwise an entry creation in this table would not be allowed. Deletion of an Port Template entry in
      alaDaUNPPortTemplateTable would result in deletion of all entries for that Port Template in the
      alaDaUNPPortTmplVlanTable."
    ::= { alaDaUNPPortTemplateVlanEntry 2 }

----------------------------------------------------------------
-- MIB compliance
----------------------------------------------------------------

alaIND1DaMIBCompliances MODULE-COMPLIANCE
    STATUS  current
    DESCRIPTION
        "Compliance statement for Alcatel DA module."
    MODULE
        MANDATORY-GROUPS {
            alaDaUserNetProfileGroup,
            alaDaUNPIpNetRuleGroup,
            alaDaUNPMacRuleGroup,
            alaDaUNPMacRangeGroup,
            alaDaUNPVlanTagGroup,
            alaDaMacUserGroup,
            alaDaUNPPortGroup,
            alaDaUNPGlobalGroup,
            alaDaNotificationObjectGroup,
            alaDaNotificationsGroup,
            alaDaUnpCustomerDomainGroup,
            alaDaSpbProfileGroup,
            alaDaUNPCustDomainEvbGpIdRuleGroup,
            alaDaUNPCustDomainVlanTagRuleGroup,
            alaDaSaaProfileGroup,
            alaDaCPortalGroup,
            alaDaHICGroup,
            alaDaUNPEdgeTemplateGroup,
            alaDaUNPEdgeProfileGroup,
            alaDaUNPClassificationRuleGroup,
            alaDaUNPGroupIdEdgeClassifyGroup,
            alaDaUNPMacOuiGroup,
            alaDaUNPEndPointGroup,
            alaDaUNPAuthRuleGroup,
            alaDaUNPRuleGroup,
            alaDaUNPMacPortClassifyGroup,
            alaDaUNPIpPortClassifyGroup,
            alaDaUNPMacIpClassifyGroup,
            alaDaUNPMacClassifyGroup,
            alaDaUNPIpAddressGroup,
            alaDaUNPMacIpGroup,
            alaDaUNPUserRoleGroup,
            alaDaUNPRestrictedRoleGroup,
            alaDaUNPVlanMappingGroup,
            alaDaUNPGroup,
            alaDaUNPEdgeFlushGroup,
            alaDaUNPMacAddrsRuleGroup,
            alaDaUNPMacRangesGroup,
            alaDaUNPIpMaskGroup,
            alaDaQMRGroup,
            alaDaUNPValidityPeriodGroup,
            alaDaUNPLocationPolicyGroup,
            alaDaUNPRedirectAllowedServerGroup,
            alaDaMacVlanUserExtGroup,
            alaDaKerberosGroup,
            alaDaUNPVlanGroup,
            alaDaUNPPortVlanGroup,
            alaDaUNPETmplVlanGroup,
            alaDaUNPUserFlushGroup,
            alaDaUNPCustDomainRuleGroup,
            alaDaUNPPortTemplateGroup,
            alaDaUNPProfileGroup,
            alaDaUNPProfileMapVlanGroup,
            alaDaUNPProfileMapSpbGroup,
            alaDaUNPProfileMapVxlanGroup,
            alaDaUNPProfileMapStaticGroup,
            alaDaUNPCustDomainMacIpRuleGroup,
            alaDaUNPPortTemplateVlanGroup
        }
        ::= { alaIND1DaMIBConformance 2 }

------------------------------------------------------------
-- Units of Conformance
------------------------------------------------------------

alaDaUserNetProfileGroup OBJECT-GROUP
    OBJECTS  {
        alaDaUserNetProfileVlanID,
        alaDaUserNetProfileRowStatus,
        alaDaUserNetProfileQosPolicyListName,
        alaDaUserNetProfileMCLagConfigStatus,
        alaDaUserNetProfileSaaProfileName,
        alaDaUserNetProfileMobileTag,
        alaDaUserNetProfileMaxIngressBw,
        alaDaUserNetProfileMaxEgressBw,
        alaDaUserNetProfileMaxIngressDepth,
        alaDaUserNetProfileMaxEgressDepth
    }
    STATUS  deprecated
    DESCRIPTION
        "Collection of DA objects for UNP Table"
    ::= { alaIND1DaMIBGroups 1 }

alaDaUNPIpNetRuleGroup OBJECT-GROUP
    OBJECTS  {
        alaDaUNPIpNetRuleProfileName,
        alaDaUNPIpNetRuleVlanTag,
        alaDaUNPIpNetRuleRowStatus,
        alaDaUNPIpNetRuleMCLagConfigStatus
    }
    STATUS  current
    DESCRIPTION
        "Collection of DA objects for system level UNP Ip rule"
    ::= { alaIND1DaMIBGroups 2 }

alaDaUNPMacRuleGroup OBJECT-GROUP
    OBJECTS  {
        alaDaUNPMacRuleProfileName,
        alaDaUNPMacRuleVlanTag,
        alaDaUNPMacRuleRowStatus,
        alaDaUNPMacRuleMCLagConfigStatus
    }
    STATUS  current
    DESCRIPTION
        "Collection of DA objects for system level UNP Mac Rule"
    ::= { alaIND1DaMIBGroups 3 }

alaDaUNPMacRangeGroup OBJECT-GROUP
    OBJECTS  {
        alaDaUNPMacRangeRuleHiAddr,
        alaDaUNPMacRangeRuleProfileName,
        alaDaUNPMacRangeRuleVlanTag,
        alaDaUNPMacRangeRuleRowStatus,
        alaDaUNPMacRangeRuleMCLagConfigStatus
    }
    STATUS  current
    DESCRIPTION
        "Collection of DA objects for system level UNP Mac Range Rule"
    ::= { alaIND1DaMIBGroups 4 }

alaDaUNPVlanTagGroup OBJECT-GROUP
    OBJECTS  {
        alaDaUNPVlanTagRuleProfileName,
        alaDaUNPVlanTagRuleRowStatus,
        alaDaUNPVlanTagRuleMCLagConfigStatus
    }
    STATUS  current
    DESCRIPTION
        "Collection of DA objects for system level Vlan Tag Rule"
    ::= { alaIND1DaMIBGroups 5 }

alaDaMacUserGroup OBJECT-GROUP
    OBJECTS  {
        alaDaMacUserVlanID,
        alaDaAuthenticationStatus,
        alaDaMacUserIpAddress,
        alaDaMacUserUnpUsed,
        alaDaMacUserLoginTimeStamp,
        alaDaMacUserAuthtype,
        alaDaMacUserClassificationSource,
        alaDaMacUserName
    }
    STATUS  current
    DESCRIPTION
        "Collection of DA objects for UNP Mac User"
    ::= { alaIND1DaMIBGroups 6 }

alaDaUNPPortGroup OBJECT-GROUP
    OBJECTS  {
        alaDaUNPPortDefaultProfileName,
        alaDaUNPPortPassAltProfileName,
        alaDaUNPPortRowStatus,
        alaDaUNPPortMacAuthFlag,
        alaDaUNPPortClassificationFlag,
        alaDaUNPPortTrustTagStatus,
        alaDaUNPPortMCLagConfigStatus
    }
    STATUS  current
    DESCRIPTION
        "Collection of DA UNP Ports"
    ::= { alaIND1DaMIBGroups 7 }

alaDaUNPGlobalGroup OBJECT-GROUP
    OBJECTS  {
        alaDaUNPDynamicVlanConfigFlag,
        alaDaUNPAuthServerDownUnp, --deprecated
        alaDaUNPAuthServerDownTimeout,
        alaDaUNPDynamicVlanMCLagConfigStatus,
        alaDaUNPAuthServerDownUNPMCLagConfigStatus,
        alaDaUNPAuthServerDownTimeoutMCLagConfigStatus,
        alaDaUNPDynamicProfileConfigFlag,
        alaDaUNPDynamicProfileConfigMCLagConfigStatus,
        alaDaUNPReloadVsiTypeDB,
        alaDaUNPAuthSrvDownEdgeProfName, --deprecated
        alaDaUNPAuthServerDowneEdgeProfTimeout, --deprecated
        alaDaUNPEdgeUserFlush, --deprecated
        alaDaUNP8021XEdgeUserFlush,
        alaDaUNPMacEdgeUserFlush,
        alaDaUNPNoAuthEdgeUserFlush,
        alaDaUNPRedirectPortBounce,
        alaDaUNPRedirectPauseTimer,
        alaDaUNPRedirectProxyServerPort,
        alaDaUNPRedirectServerIPType,
        alaDaUNPRedirectServerIP,
        alaDaUNPAuthSrvDownVxlanProfileName, --deprecated
        alaDaUNPAuthSrvDownVxlanProfileTimeout, --deprecated
        alaDaUNPForceL3Learning,
        alaDaUNPForceL3LearningPortBounce,
        alaDaUNPAuthServerDownProfile1,
        alaDaUNPAuthServerDownProfile2,
        alaDaUNPAuthServerDownProfile3,
        alaDaUNPVlanUserFlush
    }
    STATUS  current
    DESCRIPTION
        "Collection of DA objects for Global parameters"
    ::= { alaIND1DaMIBGroups 8 }

alaDaNotificationObjectGroup OBJECT-GROUP
    OBJECTS  {
        alaDaUnpMacAddr,
        alaDaUnpSourceIpAddr,
        alaDaUnpNativeVlan,
        alaDaUnpVlan,
        alaDaUnpMCLAGId,
        alaDaUnpCommandType,
        alaDaUnpName,
        alaDaUnpMacAddr1,
        alaDaUnpMacAddr2,
        alaDaUnpIpAddr,
        alaDaUnpIpMask,
        alaDaUnpVlanTag,
        alaDaKerberosRateLimitString
    }
    STATUS  current
    DESCRIPTION
        "Collection of DA objects for Notifications"
    ::= { alaIND1DaMIBGroups 9 }

alaDaNotificationsGroup NOTIFICATION-GROUP
    NOTIFICATIONS {
        unpMcLagMacIgnored,
        unpMcLagConfigInconsistency,
        alaDaKerberosReqTimeoutTrap,
        alaDaKerberosInactivityTimerExpiryTrap,
        alaDaKerberosRateLimitExceed
    }
    STATUS  current
    DESCRIPTION
        "Collection of Notifications for management of DA."
    ::= { alaIND1DaMIBGroups 10 }

alaDaMacVlanUserGroup OBJECT-GROUP
    OBJECTS  {
        alaDaMacVlanUserAuthStatus,
        alaDaMacVlanUserIpAddressType,
        alaDaMacVlanUserIpAddress,
        alaDaMacVlanUserUnpUsed,
        alaDaMacVlanUserLoginTimeStamp,
        alaDaMacVlanUserAuthtype,
        alaDaMacVlanUserClassificationSource,
        alaDaMacVlanUserMCLagLearningLoc,
        alaDaMacVlanUserName,
        alaDaMacVlanUserRole,
        alaDaMacVlanUserRoleSource,
        alaDaMacVlanUserAuthFailReason,
        alaDaMacVlanUserAuthRetryCount,
        alaDaMacVlanUserClassifProfRule,
        alaDaMacVlanUserRoleRule,
        alaDaMacVlanUserRestAccessStatus,
        alaDaMacVlanUserLocPolicyStatus,
        alaDaMacVlanUserTimePolicyStatus,
        alaDaMacVlanUserCapPortalStatus,
        alaDaMacVlanUserQMRStatus,
        alaDaMacVlanUserAuthServerIpType,
        alaDaMacVlanUserAuthServerIpUsed,
        alaDaMacVlanUserAuthServerUsed,
        alaDaMacVlanUserServerMessage,
        alaDaMacVlanUserRedirectionUrl,
        alaDaMacVlanUserSIPCallType,
        alaDaMacVlanUserSIPMediaType,
        alaDaMacVlanUserUnpFromAuthServer,
        alaDaMacVlanUserType,
        alaDaMacVlanUserServiceID,
        alaDaMacVlanUserServiceSapIDIfIndex,
        alaDaMacVlanUserServiceSapIDEncapVal,
        alaDaMacVlanUserVxlanVnid,
        alaDaMacVlanUserSpbIsid,
        alaDaMacVlanUserSpbBVlan,
        alaDaMacVlanUserKerberosStatus
    }
    STATUS  current
    DESCRIPTION
        "Collection of DA objects for UNP Mac User"
    ::= { alaIND1DaMIBGroups 11 }

alaDaUnpCustomerDomainGroup OBJECT-GROUP
    OBJECTS  {
        alaDaUnpCustomerDomainDesc,
        alaDaUnpCustomerDomainRowStatus
    }
    STATUS  current
    DESCRIPTION
        "Collection of DA objects for UNP Group"
    ::= { alaIND1DaMIBGroups 12 }

alaDaSpbProfileGroup OBJECT-GROUP
    OBJECTS  {
        alaDaSpbProfileEncapVal,
        alaDaSpbProfileQosPolicyListName,
        alaDaSpbProfileIsid,
        alaDaSpbProfileBVlan,
        alaDaSpbProfileRowStatus,
        alaDaSpbProfileMulticastMode,
        alaDaSpbProfileSapVlanXlation,
        alaDaSpbProfileMobileTag,
        alaDaSpbProfileAFDConfig
    }
    STATUS  deprecated
    DESCRIPTION
        "Collection of DA objects for Service Classification Profile."
    ::= { alaIND1DaMIBGroups 13 }

alaDaUNPCustDomainEvbGpIdRuleGroup OBJECT-GROUP
    OBJECTS  {
        alaDaUNPCustDomainEvbGpIdRuleVlanProfileName,
        alaDaUNPCustDomainEvbGpIdRuleRowStatus,
        alaDaUNPCustDomainEvbGpIdRuleSpbProfileName,
        alaDaUNPCustDomainEvbGpIdRuleVxlanProfileName
    }
    STATUS  current
    DESCRIPTION
        "Collection of DA objects for system level EVB Group ID Rule."
    ::= { alaIND1DaMIBGroups 14 }

alaDaUNPCustDomainVlanTagRuleGroup OBJECT-GROUP
    OBJECTS  {
        alaDaUNPCustDomainVlanTagRuleVlanProfileName, --deprecated
        alaDaUNPCustDomainVlanTagRuleSpbProfileName, --deprecated
        alaDaUNPCustDomainVlanTagRuleRowStatus,
        alaDaUNPCustDomainVlanTagRuleMCLagConfigStatus,
        alaDaUNPCustDomainVlanTagRuleTagPosition,   --deprecated
        alaDaUNPCustDomainVlanTagRuleVxlanProfileName, --deprecated
        alaDaUNPCustDomainVlanTagRuleProfile1,
        alaDaUNPCustDomainVlanTagRuleProfile2,
        alaDaUNPCustDomainVlanTagRuleProfile3
    }
    STATUS  current
    DESCRIPTION
        "Collection of DA objects for system level Vlan Tag Rule"
    ::= { alaIND1DaMIBGroups 15 }

alaDaUNPCustDomainIpNetRuleGroup OBJECT-GROUP
    OBJECTS  {
        alaDaUNPCustDomainIpNetRuleProfileName,   --deprecated
        alaDaUNPCustDomainIpNetRuleSpbProfileName,   --deprecated
        alaDaUNPCustDomainIpNetRuleVlanTag,
        alaDaUNPCustDomainIpNetRuleRowStatus,
        alaDaUNPCustDomainIpNetRuleMCLagConfigStatus,
        alaDaUNPCustDomainIpNetRuleEdgeProfile,   --deprecated
        alaDaUNPCustDomainIpNetRuleVxlanProfileName,   --deprecated
        alaDaUNPCustDomainIpNetRuleProfile1,
        alaDaUNPCustDomainIpNetRuleProfile2,
        alaDaUNPCustDomainIpNetRuleProfile3
    }
    STATUS  current
    DESCRIPTION
        "Collection of DA objects for system level UNP Ip rule"
    ::= { alaIND1DaMIBGroups 16 }

alaDaUNPCustDomainMacRuleGroup OBJECT-GROUP
    OBJECTS  {
        alaDaUNPCustDomainMacRuleProfileName, --deprecated
        alaDaUNPCustDomainMacRuleSpbProfileName, --deprecated
        alaDaUNPCustDomainMacRuleVlanTag,
        alaDaUNPCustDomainMacRuleRowStatus,
        alaDaUNPCustDomainMacRuleMCLagConfigStatus,
        alaDaUNPCustDomainMacRuleEdgeProfileName, --deprecated
        alaDaUNPCustDomainMacRuleVxlanProfileName, --deprecated
        alaDaUNPCustDomainMacRuleProfile1,
        alaDaUNPCustDomainMacRuleProfile2,
        alaDaUNPCustDomainMacRuleProfile3
    }
    STATUS  current
    DESCRIPTION
        "Collection of DA objects for system level UNP Mac Rule"
    ::= { alaIND1DaMIBGroups 17 }

alaDaUNPCustDomainMacRangeGroup OBJECT-GROUP
    OBJECTS   {
        alaDaUNPCustDomainMacRangeRuleHiAddr,
        alaDaUNPCustDomainMacRangeRuleProfileName,   --deprecated
        alaDaUNPCustDomainMacRangeRuleSpbProfileName,   --deprecated
        alaDaUNPCustDomainMacRangeRuleVlanTag,
        alaDaUNPCustDomainMacRangeRuleRowStatus,
        alaDaUNPCustDomainMacRangeRuleMCLagConfigStatus,
        alaDaUNPCustDomainMacRangeRuleEdgeProfileName,   --deprecated
        alaDaUNPCustDomainMacRangeRuleVxlanProfileName,   --deprecated
        alaDaUNPCustDomainMacRangeRuleProfile1,
        alaDaUNPCustDomainMacRangeRuleProfile2,
        alaDaUNPCustDomainMacRangeRuleProfile3
    }
    STATUS  current
    DESCRIPTION
        "Collection of DA objects for system level UNP Mac Range Rule"
    ::= { alaIND1DaMIBGroups 18 }

alaDaUNPGroupObjects OBJECT-GROUP
    OBJECTS  {
        alaDaUNPPortCustomerDomainId, --deprecated
        alaDaUNPPortType,
        alaDaUNPPortPassAltSpbProfileName,  --deprecated
        alaDaUNPPortDefaultSpbProfileName, --deprecated
        alaDaUNPPortDefaultEdgeProfName, --deprecated
        alaDaUNPPortMacPassEdgeProfName, --deprecated
        alaDaUNPPort8021XEdgeProfName, --deprecated
        alaDaUNPPort8021XAuthStatus,
        alaDaUNPPort8021XTxPeriodStatus, --deprecated
        alaDaUNPPort8021XTxPeriod,
        alaDaUNPPort8021XSuppTimeoutStatus, --deprecated
        alaDaUNPPort8021XSuppTimeOut,
        alaDaUNPPort8021XMaxReqStatus, --deprecated
        alaDaUNPPort8021XMaxReq,
        alaDaUNPPortGroupId,
        alaDaUNPPortAaaProfile,
        alaDaUNPPortEdgeTemplate, --deprecated
        alaDaUNPPortRedirectPortBounce,
        alaDaUNPPort8021XFailurePolicy,
        alaDaUNPPort8021XBypassStatus,
        alaDaUNPPortMacAllowEap,
        alaDaUNPPortAdminControlledDirections,
        alaDaUNPPortAdminControlledOperDirections,
        alaDaUNPPort8021XPassAltUserNetProfName, --deprecated
        alaDaUNPPort8021XPassAltSpbProfName, --deprecated
        alaDaUNPPort8021XPassAltVxlanProfName, --deprecated
        alaDaUNPPortPassAltVxlanProfileName, --deprecated
        alaDaUNPPortDefaultVxlanProfileName, --deprecated
        alaDaUNPPortAFDConfig,
        alaDaUNPPortMaxIngressBw,
        alaDaUNPPortMaxIngressBwSource,
        alaDaUNPPortMaxEgressBw,
        alaDaUNPPortMaxEgressBwSource,
        alaDaUNPPortMaxIngressDepth,
        alaDaUNPPortMaxEgressDepth,
        alaDaUNPPortIngressSourceProfile,
        alaDaUNPPortEgressSourceProfile,
        alaDaUNPPortForceL3Learning,
        alaDaUNPPortForceL3LearningPortBounce,
	alaDaUNPPort8021XPassAltProfileName,
        alaDaUNPPortPortTemplateName,
        alaDaUNPPortDomainID,
        alaDaUNPPortAdminState,
        alaDaUNPPortDynamicService,
        alaDaUNPPortPVlanPortType
    }
    STATUS  current
    DESCRIPTION
        "Collection of DA objects created to keep SNMP4J compiler happy."
    ::= { alaIND1DaMIBGroups 19 }

alaDaSaaProfileGroup OBJECT-GROUP
    OBJECTS  {
        alaDaSaaProfileLatencyThreshold,
        alaDaSaaProfileJitterThreshold,
        alaDaSaaProfileRowStatus
    }
    STATUS  current
    DESCRIPTION
        "Collection of DA objects for SAA Profile."
    ::= { alaIND1DaMIBGroups 20 }

    alaDaCPortalGroup   OBJECT-GROUP
        OBJECTS
        {
            alaDaCPortalRedirectUrlName, -- Global Config objects
            alaDaCPortalIpAddressType,
            alaDaCPortalIpAddress,
            alaDaCPortalMode,
            alaDaCPortalSuccRedirectUrl,
            alaDaCPortalProxyPort,
	    alaDaCPortalPolicyListName,
            alaDaCPortalRetryCnt,
            alaDaCPortalAuthRealm,  -- alaDaCPortalAuthPassTable
            alaDaCPortalAuthPolicyListName,
            alaDaCPortalAuthRowStatus,
	    alaDaCPortalAuthUNPProfile,
     	    alaDaCPortalAuthUNPProfileChange,
            alaDaCPortalProfMode,
            alaDaCPortalProfSuccRedirectUrl,
            alaDaCPortalProfRetryCnt,
            alaDaCPortalProfAuthPolicyListName,
            alaDaCPortalProfAaaProf,
            alaDaCPortalProfRowStatus,
	    alaDaCPortalProfDomainAuthPolicyListName,
	    alaDaCPortalProfDomainAuthRealm,
            alaDaCPortalProfDomainRowStatus,
	    alaDaCPortalCustomization,
	    alaDaCPortalProfUNPProfile,
	    alaDaCPortalProfUNPProfileChange,
	    alaDaCPortalUNPProfile,
	    alaDaCPortalUNPProfileChange,
	    alaDaCPortalProfDomainUNPProfile,
	    alaDaCPortalProfDomainUNPProfileChange
        }
        STATUS  current
        DESCRIPTION
            "Collection of Captive Portal  objects ."
        ::= { alaIND1DaMIBGroups 21 }

alaDaHICGroup   OBJECT-GROUP
    OBJECTS  {
        alaDaHICStatus,
        alaDaHICWebAgentDownloadUrl,
        alaDaHICCustomHttpProxyPort,
        alaDaHICBgPollInterval,
        alaDaHICSvrFailMode,
        alaDaHICSvrIpAddrType,  ---Server Table
        alaDaHICSvrIpAddr,
        alaDaHICSvrPort,
        alaDaHICSvrKey,
        alaDaHICSvrStatus,
        alaDaHICSvrRole,
        alaDaHICSvrConnection,
        alaDaHICSvrRowStatus,
        alaDaHICAllowedIpAddrType,  --- Allowed/Exception IP Table
        alaDaHICAllowedIpAddr,
        alaDaHICAllowedIpMaskType,
        alaDaHICAllowedIpMask,
        alaDaHICAllowedRowStatus,
        alaDaHICSvrFailChangedPolicyName, -- SrvFailPolicy Table
        alaDaHICSvrFailRowStatus,
        alaDaHICHostStatus
    }
    STATUS  current
    DESCRIPTION
        "Collection of HIC  objects ."
    ::= { alaIND1DaMIBGroups 22 }

alaDaUNPEdgeTemplateGroup   OBJECT-GROUP
    OBJECTS  {
        alaDaUNPETmpl8021XAuthStatus,
        alaDaUNPETmpl8021XTxPeriodStatus,
        alaDaUNPETmpl8021XTxPeriod,
        alaDaUNPETmpl8021XSuppTimeoutStatus,
        alaDaUNPETmpl8021XSuppTimeOut,
        alaDaUNPETmpl8021XMaxReqStatus,
        alaDaUNPETmpl8021XMaxReq,
        alaDaUNPETmpl8021XPassAltEProf,
        alaDaUNPETmplMacAuthStatus,
        alaDaUNPETmplMacPassAltEProf,
        alaDaUNPETmplClassifStatus,
        alaDaUNPETmplDefEProf,
        alaDaUNPETmplGroupId,
        alaDaUNPETmplAaaProf,
        alaDaUNPETmplRowStatus,
        alaDaUNPETmplRedirectPortBounce,
        alaDaUNPETmplFailurePolicy,
        alaDaUNPETmplBypassStatus,
        alaDaUNPETmplMacAllowEap,
        alaDaUNPETmplAdminControlledDirections,
        alaDaUNPETmplTrustTagStatus,
        alaDaUNPETmplForceL3Learning,
        alaDaUNPETmplForceL3LearningPortBounce
    }
    STATUS  deprecated
    DESCRIPTION
        "Collection of UNP Edge Template Objects."
    ::= { alaIND1DaMIBGroups 23 }

alaDaUNPEdgeProfileGroup   OBJECT-GROUP
    OBJECTS  {
        alaDaUNPEdgeProfQosPolicyList,
        alaDaUNPEdgeProfLocationPolicy,
        alaDaUNPEdgeProfPeriodPolicy,
        alaDaUNPEdgeProfHICStatus,
        alaDaUNPEdgeProfCPortalAuth,
        alaDaUNPEdgeProfAuthStatus,
        alaDaUNPEdgeProfMobileTag,
        alaDaUNPEdgeProfDHCPEnforcment,
        alaDaUNPEdgeProfCPortalProf,
        alaDaUNPEdgeProfRowStatus,
        alaDaUNPEdgeProfRedirectStatus,
        alaDaUNPEdgeProfKerberosStatus,
        alaDaUNPEdgeProfMaxIngressBw,
        alaDaUNPEdgeProfMaxEgressBw,
        alaDaUNPEdgeProfMaxIngressDepth,
        alaDaUNPEdgeProfMaxEgressDepth
    }
    STATUS  deprecated
    DESCRIPTION
        "Collection of UNP Edge Profile Table Objects."
    ::= { alaIND1DaMIBGroups 24 }

alaDaUNPClassificationRuleGroup   OBJECT-GROUP
    OBJECTS  {
        alaDaUNPPortRuleEdgeProf, --deprecated
        alaDaUNPPortRuleRowStatus,
        alaDaUNPPortRuleVlanTag,
        alaDaUNPPortRuleProfile1,
        alaDaUNPPortRuleProfile2,
        alaDaUNPPortRuleProfile3
    }
    STATUS  current
    DESCRIPTION
        "Collection of UNP Classification Rule Port Objects."
    ::= { alaIND1DaMIBGroups 25 }

alaDaUNPGroupIdEdgeClassifyGroup   OBJECT-GROUP
    OBJECTS  {
        alaDaUNPGroupRuleEdgeProf,
        alaDaUNPGroupRuleRowStatus,
        alaDaUNPGroupRuleVlanTag
    }
    STATUS  deprecated
    DESCRIPTION
        "Collection of UNP Classification Rule Port Objects."
    ::= { alaIND1DaMIBGroups 26 }

alaDaUNPMacOuiGroup   OBJECT-GROUP
    OBJECTS  {
        alaDaUNPMacOuiRuleEdgeProfile,      --deprecated
        alaDaUNPMacOuiRuleRowStatus,
        alaDaUNPMacOuiRuleVlanTag,
        alaDaUNPMacOuiRuleProfile1,
        alaDaUNPMacOuiRuleProfile2,
        alaDaUNPMacOuiRuleProfile3
    }
    STATUS  current
    DESCRIPTION
        "Collection of UNP MAC Oui Objects."
    ::= { alaIND1DaMIBGroups 27 }

alaDaUNPEndPointGroup   OBJECT-GROUP
    OBJECTS  {
        alaDaUNPEndPoinEdgeProfile, --deprecated
        alaDaUNPEndPoinRuleRowStatus,
        alaDaUNPEndPoinProfile1,
        alaDaUNPEndPoinProfile2,
        alaDaUNPEndPoinProfile3,
        alaDaUNPEndPoinVlanTag
    }
    STATUS  current
    DESCRIPTION
        "Collection of UNP MAC Oui Objects."
    ::= { alaIND1DaMIBGroups 28 }

alaDaUNPAuthRuleGroup   OBJECT-GROUP
    OBJECTS  {
        alaDaUNPAuthRuleEdgeProfile, --deprecated
        alaDaUNPAuthRuleRowStatus,
        alaDaUNPAuthRuleVlanTag,
        alaDaUNPAuthRuleProfile1,
        alaDaUNPAuthRuleProfile2,
        alaDaUNPAuthRuleProfile3
    }
    STATUS  current
    DESCRIPTION
        "Collection of UNP Authentication Rule Objects."
    ::= { alaIND1DaMIBGroups 29 }

alaDaUNPRuleGroup   OBJECT-GROUP
    OBJECTS   {
        alaDaUNPClassifRulePrecedenceNum,
        alaDaUNPClassifRuleEdgeProfile,  --deprecated
        alaDaUNPClassifRulePort,
        alaDaUNPClassifRulePortHigh,
        alaDaUNPClassifRuleGroupId,  --deprecated
        alaDaUNPClassifRuleMacAddr,
        alaDaUNPClassifRuleMacRngLoaddr,
        alaDaUNPClassifRuleMacRngHiaddr,
        alaDaUNPClassifRuleMacOuiAddr,
        alaDaUNPClassifRuleEndPoin,
        alaDaUNPClassifRuleAuthType,
        alaDaUNPClassifRuleIpAddressType,
        alaDaUNPClassifRuleIpAddress,
        alaDaUNPClassifRuleIpMaskType,
        alaDaUNPClassifRuleIpMask,
        alaDaUNPClassifRowStatus,
        alaDaUNPClassifRuleVlanTag,
        alaDaUNPClassifRuleCustomerDomain,
        alaDaUNPClassifRuleProfile1,
        alaDaUNPClassifRuleProfile2,
        alaDaUNPClassifRuleProfile3
    }
    STATUS  current
    DESCRIPTION
        "Collection of UNP Rule Objects."
    ::= { alaIND1DaMIBGroups 30 }

alaDaUNPMacPortClassifyGroup   OBJECT-GROUP
    OBJECTS   {
        alaDaUNPMacPortRuleEdgeProf,--deprecated
        alaDaUNPMacPortRuleRowStatus,
        alaDaUNPMacPortRuleVlanTag,
        alaDaUNPMacPortRuleProfile1,
        alaDaUNPMacPortRuleProfile2,
        alaDaUNPMacPortRuleProfile3
    }
    STATUS  current
    DESCRIPTION
        "Collection of Objects for Mac & Port  based  classification rule."
    ::= { alaIND1DaMIBGroups 31 }

alaDaUNPIpPortClassifyGroup   OBJECT-GROUP
    OBJECTS  {
        alaDaUNPIpPortRuleEdgeProf,  --deprecated
        alaDaUNPIpPortRuleRowStatus,
        alaDaUNPIpPortRuleVlanTag,
        alaDaUNPIpPortRuleProfile1,
        alaDaUNPIpPortRuleProfile2,
        alaDaUNPIpPortRuleProfile3,
        alaDaUNPIpPortRuleMaskType,
        alaDaUNPIpPortRuleMask
    }
    STATUS  current
    DESCRIPTION
        "Collection of Objects for Ip & port  based  classification rule."
    ::= { alaIND1DaMIBGroups 32 }

alaDaUNPMacIpClassifyGroup   OBJECT-GROUP
    OBJECTS  {
        alaDaUNPMacIpPortRuleEdgeProf,  --deprecated
        alaDaUNPMacIpPortRuleRowStatus,
        alaDaUNPMacIpPortRuleVlanTag,
        alaDaUNPMacIpPortRuleProfile1,
        alaDaUNPMacIpPortRuleProfile2,
        alaDaUNPMacIpPortRuleProfile3,
        alaDaUNPMacIpPortRuleIpMaskType,
        alaDaUNPMacIpPortRuleIpMask
    }
    STATUS  current
    DESCRIPTION
        "Collection of Objects for Mac, Ip & port  based  classification rule."
    ::= { alaIND1DaMIBGroups 33 }

alaDaUNPMacClassifyGroup   OBJECT-GROUP
    OBJECTS  {
        alaDaUNPMacGroupRuleEdgeProf,
        alaDaUNPMacGroupRuleRowStatus,
        alaDaUNPMacGroupRuleVlanTag
    }
    STATUS  deprecated
    DESCRIPTION
        "Collection of Objects for Mac Address and Group classification."
    ::= { alaIND1DaMIBGroups 34 }

alaDaUNPIpAddressGroup   OBJECT-GROUP
    OBJECTS  {
        alaDaUNPIpGroupRuleEdgeProf,
        alaDaUNPIpGroupRuleRowStatus,
        alaDaUNPIpGroupRuleVlanTag
    }
    STATUS  deprecated
    DESCRIPTION
        "Collection of Objects for IP and Group Classification."
    ::= { alaIND1DaMIBGroups 35 }

alaDaUNPMacIpGroup   OBJECT-GROUP
    OBJECTS {
        alaDaUNPMacIpGroupRuleEdgeProf,
        alaDaUNPMacIpGroupRuleRowStatus,
        alaDaUNPMacIpGroupRuleVlanTag
    }
    STATUS  deprecated
    DESCRIPTION
        "Collection of objects for UNP MAC, IP and Group Classification."
    ::= { alaIND1DaMIBGroups 36 }

alaDaUNPUserRoleGroup   OBJECT-GROUP
    OBJECTS {
        alaDaUNPUserRolePrecedenceNum,
        alaDaUNPUserRolePolicyList,
        alaDaUNPUserRoleEdgeProfile, --deprecated
        alaDaUNPUserRoleAuthType,
        alaDaUNPUserRolePostLoginStatus,
        alaDaUNPUserRoleKerberosPostLoginStatus,
        alaDaUNPUserRoleRowStatus,
        alaDaUNPUserRoleProfile1,
        alaDaUNPUserRoleProfile2,
        alaDaUNPUserRoleProfile3
    }
    STATUS  current
    DESCRIPTION
        "Collection of UNP User Role Objects."
    ::= { alaIND1DaMIBGroups 37 }

alaDaUNPRestrictedRoleGroup   OBJECT-GROUP
    OBJECTS  {
        alaDaUNPRstrctedRolePolicyList,
        alaDaUNPRstrctedRoleRowStatus
    }
    STATUS  current
    DESCRIPTION
        "Collection of UNP Restricted Role Objects."
    ::= { alaIND1DaMIBGroups 38 }

alaDaUNPVlanMappingGroup   OBJECT-GROUP
    OBJECTS  {
        alaDaUNPVlanMapIdent,
        alaDaUNPVlanMapRowStatus
    }
    STATUS  deprecated
    DESCRIPTION
        "Collection of UNP Vlan Mapping Objects."
    ::= { alaIND1DaMIBGroups 39 }

alaDaUNPGroup   OBJECT-GROUP
    OBJECTS  {
        alaDaUnpGroupDescription,
        alaDaUnpGroupIdRowStatus
    }
    STATUS  deprecated
    DESCRIPTION
        "Collection of Objects for UNP Group Creation and Deletion."
    ::= { alaIND1DaMIBGroups 40 }

alaDaUNPEdgeFlushGroup   OBJECT-GROUP
    OBJECTS  {
        alaDaUNPEdgeFlushPortLow,
        alaDaUNPEdgeFlushPortHigh,
        alaDaUNPEdgeFlushType,
        alaDaUNPEdgrFlushMac,
        alaDaUNPEdgeFlushComplete,
        alaDaUNPEdgeFlushProfile
    }
    STATUS  current
    DESCRIPTION
        "Collection of UNP Port Edge Flush Objects."
    ::= { alaIND1DaMIBGroups 41 }

alaDaUNPMacAddrsRuleGroup   OBJECT-GROUP
    OBJECTS  {
        alaDaUNPMacRulesEdgeProf,
        alaDaUNPMacRulesRowStatus,
        alaDaUNPMacRulesVlanTag
    }
    STATUS  deprecated
    DESCRIPTION
        "Collection of UNP MAC Edge Flush Objects."
    ::= { alaIND1DaMIBGroups 42 }

alaDaUNPMacRangesGroup   OBJECT-GROUP
    OBJECTS  {
        alaDaUNPMacRangeEndMacAddr,
        alaDaUNPMacRangeEdgeProf,
        alaDaUNPMacRangeRowStatus,
        alaDaUNPMacRangeVlanTag
    }
    STATUS  deprecated
    DESCRIPTION
        "Collection of UNP MAC Edge Flush Objects."
    ::= { alaIND1DaMIBGroups 43 }

alaDaUNPIpMaskGroup   OBJECT-GROUP
    OBJECTS  {
        alaDaUNPIpMaskRuleEdgeProf,
        alaDaUNPIpMaskRuleRowStatus,
        alaDaUNPIpMaskRuleVlanTag
    }
    STATUS  deprecated
    DESCRIPTION
        "Collection of UNP MAC Edge Flush Objects."
    ::= { alaIND1DaMIBGroups 44 }

  --
  -- QMR
  --
alaDaQMRGroup   OBJECT-GROUP
    OBJECTS  {
        alaDaQMRPage,
        alaDaQMRPath,
        alaDaQMRCustomHttpProxyPort,
        alaDaQMRPolicyList,
        alaDaQMRAllowedIpAddrType,
        alaDaQMRAllowedIpAddr,
        alaDaQMRAllowedIpMaskType,
        alaDaQMRAllowedIpMask,
        alaDaQMRAllowedRowStatus
    }
    STATUS  current
    DESCRIPTION
        "Collection of QMR objects ."
    ::= { alaIND1DaMIBGroups 45 }

 alaDaUNPValidityPeriodGroup OBJECT-GROUP
     OBJECTS   {
         alaDaUNPValidityPeriodDays,
         alaDaUNPValidityPeriodDaysStatus,
         alaDaUNPValidityPeriodMonths,
         alaDaUNPValidityPeriodMonthsStatus,
         alaDaUNPValidityPeriodHour,
         alaDaUNPValidityPeriodHourStatus,
         alaDaUNPValidityPeriodEndHour,
         alaDaUNPValidityPeriodInterval,
         alaDaUNPValidityPeriodIntervalStatus,
         alaDaUNPValidityPeriodEndInterval,
         alaDaUNPValidityPeriodTimezone,
         alaDaUNPValidityPeriodTimezoneStatus,
         alaDaUNPValidityPeriodActiveStatus,
         alaDaUNPValidityPeriodRowStatus
     }
     STATUS  current
     DESCRIPTION
         "Collection of UNP Validity Period Objects."
     ::= { alaIND1DaMIBGroups 46 }

alaDaUNPLocationPolicyGroup OBJECT-GROUP
    OBJECTS  {
        alaDaUNPLocationPolicyPort,
        alaDaUNPLocationPolicyPortHigh,
        alaDaUNPLocationPolicyPortStatus,
        alaDaUNPLocationPolicySystemName,
        alaDaUNPLocationPolicySystemLocation,
        alaDaUNPLocationPolicyRowStatus
    }
    STATUS  current
    DESCRIPTION
        "Collection of UNP Location Policy Objects."
    ::= { alaIND1DaMIBGroups 47 }

alaDaUNPRedirectAllowedServerGroup OBJECT-GROUP
    OBJECTS {
        alaDaUNPRedirectAllowedServerIPType,
        alaDaUNPRedirectAllowedServerIP,
        alaDaUNPRedirectAllowedMaskIPType,
        alaDaUNPRedirectAllowedMaskIP,
        alaDaUNPRedirectAllowedRowStatus
    }
    STATUS  current
    DESCRIPTION
        "Collection of UNP Redirect Allowed Server Objects."
    ::= { alaIND1DaMIBGroups 48 }

 alaDaMacVlanUserExtGroup OBJECT-GROUP
     OBJECTS  {
         alaDaMacVlanUserExtAppName
     }
     STATUS  current
     DESCRIPTION
         "Collection of Mac Vlan User Extended Objects."
     ::= { alaIND1DaMIBGroups 49 }

alaDaUNPVxlanProfileGroup OBJECT-GROUP
    OBJECTS  {
        alaDaUNPVxlanProfileEncapVal,
        alaDaUNPVxlanProfileVnid,
        alaDaUNPVxlanProfileQosPolicyListName,
        alaDaUNPVxlanProfileFarEndIPListName,
        alaDaUNPVxlanProfileMulticastIPAddressType,
        alaDaUNPVxlanProfileMulticastIPAddress,
        alaDaUNPVxlanProfileSapVlanXlation,
        alaDaUNPVxlanProfileMobileTagStatus,
        alaDaUNPVxlanProfileMulticastMode,
        alaDaUNPVxlanProfileRowStatus
    }
    STATUS  deprecated
    DESCRIPTION
        "Collection of DA objects for VXLAN Service Classification Profile."
    ::= { alaIND1DaMIBGroups 50 }

alaDaUNPVxlanFlushGroup OBJECT-GROUP
    OBJECTS  {
        alaDaUNPVxlanFlushComplete,
        alaDaUNPVxlanFlushAuthType,
        alaDaUNPVxlanFlushMacAddress,
        alaDaUNPVxlanFlushSapIDIfIndex,
        alaDaUNPVxlanFlushSapIDEncapVal,
        alaDaUNPVxlanFlushServiceID,
        alaDaUNPVxlanFlushVxlanProfile
    }
    STATUS  deprecated
    DESCRIPTION
        "Collection of DA objects for VXLAN Users Flush Table."
    ::= { alaIND1DaMIBGroups 51 }

alaDaUNPVxlanFarEndIPListGroup OBJECT-GROUP
    OBJECTS  {
        alaDaUNPVxlanFarEndIPListIPAddressCount,
        alaDaUNPVxlanFarEndIPListRemove
    }
    STATUS  current
    DESCRIPTION
        "Collection of DA objects for VXLAN Far-End-IP Lists Table."
    ::= { alaIND1DaMIBGroups 52 }

alaDaUNPVxlanFarEndIPAddressListGroup OBJECT-GROUP
    OBJECTS  {
        alaDaUNPVxlanFarEndIPAddressListRowStatus
    }
    STATUS  current
    DESCRIPTION
        "Collection of DA objects for VXLAN Far-End-IP Lists Table."
    ::= { alaIND1DaMIBGroups 53 }

alaDaUNPSpbFlushGroup OBJECT-GROUP
    OBJECTS  {
        alaDaUNPSpbFlushComplete,
        alaDaUNPSpbFlushAuthType,
        alaDaUNPSpbFlushMacAddress,
        alaDaUNPSpbFlushSapIDIfIndex,
        alaDaUNPSpbFlushSapIDEncapVal,
        alaDaUNPSpbFlushServiceID,
        alaDaUNPSpbFlushSpbProfile
    }
    STATUS  deprecated
    DESCRIPTION
        "Collection of DA objects for SPB Users Flush Table."
    ::= { alaIND1DaMIBGroups 54 }

alaDaKerberosGroup OBJECT-GROUP
    OBJECTS  {
        alaDaKerberosGlobalMacMoveStatus,
        alaDaKerberosGlobalInactivityTimer,
        alaDaKerberosGlobalPolicy,
        alaDaKerberosGlobalPolicyStatus,
        alaDaKerberosClientPktHwDiscardStats,
        alaDaKerberosServerPktHwDiscardStats,
        alaDaKerberosTotalClientPktRxStats,
        alaDaKerberosTotalServerPktRxStats,
        alaDaKerberosClientPktSwDiscardStats,
        alaDaKerberosServerPktSwDiscardStats,
        alaDaKerberosTotalASREQRxStats,
        alaDaKerberosTotalASREPRxStats,
        alaDaKerberosTotalTGSREQRxStats,
        alaDaKerberosTotalTGSREPRxStats,
        alaDaKerberosTotalErrorRxStats,
        alaDaKerberosGlobalClearStats,
        alaDaKerberosGlobalClearPortStats,
        alaDaKerberosGlobalServerTimeoutTimer,
        alaDaKerberosPolicyName,
        alaDaKerberosPolicyStatus,
        alaDaKerberosPolicyRowStatus,
        alaDaKerberosUserPort,
        alaDaKerberosUserName,
        alaDaKerberosUserDomain,
        alaDaKerberosUserAuthState,
        alaDaKerberosUserPolicy,
        alaDaKerberosUserLeftTime,
        alaDaKerberosUserState,
        alaDaKerberosPortClearStats,
        alaDaKerberosPortClientPktRxStats,
        alaDaKerberosPortServerPktRxStats,
        alaDaKerberosPortClientPktSwDiscardStats,
        alaDaKerberosPortServerPktSwDiscardStats,
        alaDaKerberosPortASREQRxStats,
        alaDaKerberosPortASREPRxStats,
        alaDaKerberosPortTGSREQRxStats,
        alaDaKerberosPortTGSREPRxStats,
        alaDaKerberosPortErrorRxStats,
        alaDaKerberosUdpPort,
        alaDaKerberosRowStatus
    }
    STATUS          current
    DESCRIPTION
        "Collection of objects for the management of Kerberos Global configuration."
    ::= { alaIND1DaMIBGroups 55 }

alaDaUNPVlanGroup   OBJECT-GROUP
    OBJECTS  {
        alaDaUNPVlanRuleVlanTagPosition,
        alaDaUNPVlanRuleEdgeProf,
        alaDaUNPVlanRuleRowStatus
    }
    STATUS  current
    DESCRIPTION
        "Collection of UNP VlanTag ClassificationRule Objects."
    ::= { alaIND1DaMIBGroups 56 }

alaDaUNPPortVlanGroup OBJECT-GROUP
    OBJECTS  {
        alaDaUNPPortVlanRowStatus
    }
    STATUS          current
    DESCRIPTION
       "Collection of objects for the management of
        UNP static Port-Vlan configuration."
    ::= { alaIND1DaMIBGroups 57 }

   alaDaUNPETmplVlanGroup OBJECT-GROUP
       OBJECTS {
           alaDaUNPETmplVlanRowStatus
       }
       STATUS          current
       DESCRIPTION
           "Collection of objects for the management of
            UNP Edge Template configuration."
       ::={ alaIND1DaMIBGroups 58 }

alaDaUNPUserFlushGroup OBJECT-GROUP
    OBJECTS  {
        alaDaUNPUserFlushComplete,
        alaDaUNPUserFlushAuthType,
        alaDaUNPUserFlushMacAddress,
        alaDaUNPUserFlushProfile,
        alaDaUNPUserFlushPortStart,
        alaDaUNPUserFlushPortEnd,
        alaDaUNPUserFlushSapIDIfIndex,
        alaDaUNPUserFlushSapIDEncapVal,
        alaDaUNPUserFlushServiceID
    }
    STATUS  current
    DESCRIPTION
        "Collection of DA objects for Access Users Flush Table."
    ::= { alaIND1DaMIBGroups 59 }

alaDaUNPCustDomainRuleGroup OBJECT-GROUP
    OBJECTS  {
        alaDaUNPCustDomainRuleVlanTag,
        alaDaUNPCustDomainRuleProfile1,
        alaDaUNPCustDomainRuleProfile2,
        alaDaUNPCustDomainRuleProfile3,
        alaDaUNPCustDomainRuleRowStatus
    }
    STATUS  current
    DESCRIPTION
        "Collection of DA objects for Customer Domain Rule Table."
    ::= { alaIND1DaMIBGroups 60 }

alaDaUNPPortTemplateGroup OBJECT-GROUP
    OBJECTS  {
        alaDaUNPPortTemplateAdminState,
        alaDaUNPPortTemplateDirection,
        alaDaUNPPortTemplateDomainID,
        alaDaUNPPortTemplateClassification,
        alaDaUNPPortTemplateTrustTag,
        alaDaUNPPortTemplateDynamicService,
        alaDaUNPPortTemplateDefaultProfile,
        alaDaUNPPortTemplateAAAProfile,
        alaDaUNPPortTemplateRedirectPortBounce,
        alaDaUNPPortTemplate8021XAuth,
        alaDaUNPPortTemplate8021XAuthPassAlternate,
        alaDaUNPPortTemplate8021XAuthBypass,
        alaDaUNPPortTemplate8021XAuthFailPolicy,
        alaDaUNPPortTemplate8021XAuthTxPeriod,
        alaDaUNPPortTemplate8021XAuthSuppTimeout,
        alaDaUNPPortTemplate8021XAuthMaxReq,
        alaDaUNPPortTemplateMACAuth,
        alaDaUNPPortTemplateMACAuthPassAlternate,
        alaDaUNPPortTemplateMACAuthAllowEAP,
        alaDaUNPPortTemplateForceL3Learning,
        alaDaUNPPortTemplateForceL3LearningPortBounce,
        alaDaUNPPortTemplateRowStatus
    }
    STATUS          current
    DESCRIPTION
        "Collection of objects for the management of
         UNP Template configuration."
    ::={ alaIND1DaMIBGroups 61 }

alaDaUNPProfileGroup OBJECT-GROUP
    OBJECTS  {
        alaDaUNPProfileAuthenticationFlag,
        alaDaUNPProfileMobileTag,
        alaDaUNPProfileCPortalAuthentication,
        alaDaUNPProfileRedirect,
        alaDaUNPProfileQoSPolicy,
        alaDaUNPProfilePeriodPolicy,
        alaDaUNPProfileCPortalProfile,
        alaDaUNPProfileLocationPolicy,
        alaDaUNPProfileSaaProfile,
        alaDaUNPProfileInactivityInterval,
        alaDaUNPProfileKerberosAuthentication,
        alaDaUNPProfileMaxIngressBandwidth,
        alaDaUNPProfileMaxEgressBandwidth,
        alaDaUNPProfileMaxIngressDepth,
        alaDaUNPProfileMaxEgressDepth,
        alaDaUNPProfileRowStatus,
        alaDaUNPProfileAFDConfig
    }
    STATUS  current
    DESCRIPTION
        "Collection of DA objects for UNP Profile."
    ::= { alaIND1DaMIBGroups 62 }

alaDaUNPProfileMapVlanGroup OBJECT-GROUP
    OBJECTS  {
        alaDaUNPProfileMapVlanVlanID,
        alaDaUNPProfileMapVlanRowStatus
    }
    STATUS  current
    DESCRIPTION
        "Collection of DA objects for VLAN Classification Profile."
    ::= { alaIND1DaMIBGroups 63 }

alaDaUNPProfileMapSpbGroup OBJECT-GROUP
    OBJECTS {
        alaDaUNPProfileMapSpbEncapVal,
        alaDaUNPProfileMapSpbIsid,
        alaDaUNPProfileMapSpbBVlan,
        alaDaUNPProfileMapSpbMulticastMode,
        alaDaUNPProfileMapSpbVlanXlation,
        alaDaUNPProfileMapSpbRowStatus
    }
    STATUS  current
    DESCRIPTION
        "Collection of DA objects for VLAN Service Classification Profile."
    ::= { alaIND1DaMIBGroups 64 }

alaDaUNPProfileMapVxlanGroup OBJECT-GROUP
    OBJECTS  {
        alaDaUNPProfileMapVxlanEncapVal,
        alaDaUNPProfileMapVxlanVnid,
        alaDaUNPProfileMapVxlanFarEndIPList,
        alaDaUNPProfileMapVxlanMulticastIPAddressType,
        alaDaUNPProfileMapVxlanMulticastIPAddress,
        alaDaUNPProfileMapVxlanVlanXlation,
        alaDaUNPProfileMapVxlanMulticastMode,
        alaDaUNPProfileMapVxlanRowStatus
    }
    STATUS  current
    DESCRIPTION
       "Collection of DA objects for VXLAN Service Classification Profile."
    ::= { alaIND1DaMIBGroups 65 }

alaDaUNPProfileMapStaticGroup OBJECT-GROUP
    OBJECTS  {
        alaDaUNPProfileMapStaticEncapVal,
        alaDaUNPProfileMapStaticServiceID,
        alaDaUNPProfileMapStaticRowStatus
    }
    STATUS  current
    DESCRIPTION
        "Collection of DA objects for Static Classification Profile."
    ::= { alaIND1DaMIBGroups 66 }

alaDaUNPCustDomainMacIpRuleGroup OBJECT-GROUP
    OBJECTS  {
        alaDaUNPCustDomainMacIpRuleVlanTag,
        alaDaUNPCustDomainMacIpRuleProfile1,
        alaDaUNPCustDomainMacIpRuleProfile2,
        alaDaUNPCustDomainMacIpRuleProfile3,
        alaDaUNPCustDomainMacIpRuleRowStatus,
        alaDaUNPCustDomainMacIpRuleIpMaskType,
        alaDaUNPCustDomainMacIpRuleIpMask
    }
    STATUS  current
    DESCRIPTION
        "Collection of DA objects for system level
             UNP Mac, Ip and Domain Id rule"
    ::= { alaIND1DaMIBGroups 67 }

alaDaUNPPortTemplateVlanGroup OBJECT-GROUP
    OBJECTS {
        alaDaUNPPortTemplateVlanRowStatus
    }
    STATUS          current
    DESCRIPTION
        "Collection of objects for the management of
         UNP Port Template configuration."
    ::={ alaIND1DaMIBGroups 68 }

END
