ALCATEL-ENT1-LLDP-TRUST-MIB DEFINITIONS ::= BEGIN

  IMPORTS
     MODULE-IDENTITY, OBJECT-IDENTITY, OBJECT-TYPE, NOTIFICATION-TYPE
         FROM SNMPv2-SMI
     LldpPortNumber ,LldpChassisId,  LldpChassisIdSubtype , LldpPortId, LldpPortIdSubtype
        FROM LLDP-MIB
     MODULE-COMPLIANCE, OBJECT-GROUP, NOTIFICATION-GROUP
        FROM SNMPv2-CONF
     InterfaceIndex
        FROM IF-MIB
     RowStatus, TruthValue
        FROM SNMPv2-TC
     softentIND1LldpTrust
        FROM ALCATEL-ENT1-BASE
        ;

    alcatelIND1LLDPTRUSTMIB MODULE-IDENTITY
        LAST-UPDATED "200908110000Z"
        ORGANIZATION "Alcatel-Lucent"
        CONTACT-INFO
            "Please consult with Customer Service to insure the most appropriate
            version of this document is used with the products in question:

            Alcatel-Lucent, Enterprise Solutions Division
            (Formerly Alcatel Internetworking, Incorporated)
            26801 West Agoura Road
            Agoura Hills, CA  91301-5122
            United States Of America

            Telephone:              North America  +1 800 995 2696
                                Latin America  +1 877 919 9526
                                Europe         +31 23 556 0100
                                Asia           +65 394 7933
                                All Other      +1 818 878 4507

            Electronic Mail:        support@ind.alcatel.com
            World Wide Web:         http://alcatel-lucent.com/wps/portal/enterprise
            File Transfer Protocol: ftp://ftp.ind.alcatel.com/pub/products/mibs"

        DESCRIPTION
            "This module describes an authoritative enterprise-specific Simple
            Network Management Protocol (SNMP) Management Information Base (MIB):

            For the Birds Of Prey Product Line
            LLDP MED Management Information base for Media Endpoint Discovery Information.

            The right to make changes in specification and other information
            contained in this document without prior notice is reserved.

            No liability shall be assumed for any incidental, indirect, special, or
            consequential damages whatsoever arising from or related to this
            document or the information contained herein.

            Vendors, end-users, and other interested parties are granted
            non-exclusive license to use this specification in connection with
            management of the products for which it is intended to be used.

            Copyright (C) 1995-2009 Alcatel-Lucent, Incorporated
            ALL RIGHTS RESERVED WORLDWIDE"

        REVISION    "200908110000Z"

        DESCRIPTION
            "LLDP TRUST - ALCATEL-LUCENT proprietary MIB"
        ::= { softentIND1LldpTrust 1}

    alaLLDPTraps OBJECT-IDENTITY
        STATUS current
        DESCRIPTION
            "Branch for LLDP TRUST Subsystem Trap Objects."
        ::= { alcatelIND1LLDPTRUSTMIB 0 }

    alcatelIND1LLDPTRUSTMIBObjects OBJECT-IDENTITY
        STATUS  current
        DESCRIPTION
            "Branch For LLDP TRUST Subsystem Managed Objects."
        ::= { alcatelIND1LLDPTRUSTMIB 1 }


    alaIND1LLDPTRUSTMIBObjects OBJECT IDENTIFIER ::= { alcatelIND1LLDPTRUSTMIBObjects 1 }

    alaIND1LLDPTRUSTMIBConformance OBJECT-IDENTITY
        STATUS  current
        DESCRIPTION
            "Branch For LLDP TRUST Subsystem Conformance Information."
        ::= { alcatelIND1LLDPTRUSTMIB 2 }

    alaIND1LLDPTRUSTMIBGroups OBJECT-IDENTITY
        STATUS  current
        DESCRIPTION
            "Branch For LLDP TRUST Subsystem Units Of Conformance."
        ::= { alaIND1LLDPTRUSTMIBConformance 1 }

    alaIND1LLDPTRUSTMIBCompliances OBJECT-IDENTITY
        STATUS  current
        DESCRIPTION
            "Branch for LLDP Module MIB Subsystem Compliance Statements."
        ::= { alaIND1LLDPTRUSTMIBConformance 2 }

----------------------------------------------------------------
-- LLDP TRUST MIB
----------------------------------------------------------------

 alaLLDPTrustPortTable OBJECT-TYPE
 SYNTAX      SEQUENCE OF AlaLLDPTrustPortEntry
 MAX-ACCESS  not-accessible
 STATUS      current
 DESCRIPTION
 "A table of system level information for each port
 supported by the LLDP security mechanism.  An entry appears
 in this table for each port of this system."
 ::= { alaIND1LLDPTRUSTMIBObjects 1 }

 alaLLDPTrustPortEntry OBJECT-TYPE
 SYNTAX      AlaLLDPTrustPortEntry
 MAX-ACCESS  not-accessible
 STATUS      current
 DESCRIPTION
 "An entry in the alaLLDPPortTable"
 INDEX { alaLLDPTrustLocalPortNumber }
 ::= { alaLLDPTrustPortTable 1 }


 AlaLLDPTrustPortEntry ::=
 SEQUENCE {
 alaLLDPTrustLocalPortNumber
 LldpPortNumber,
 alaLldpTrustAdminStatus
 INTEGER,
 alaLldpTrustAction
 INTEGER,
 alaLldpTrustedStatus
 INTEGER,
 alaLldpTrustedChassisSubtype
 INTEGER
 }

 alaLLDPTrustLocalPortNumber   OBJECT-TYPE
 SYNTAX      LldpPortNumber
 MAX-ACCESS  not-accessible
 STATUS      current
 DESCRIPTION
 "The index value used to identify the port component
 (contained in the local chassis with the LLDP agent)
 associated with this entry.  The lldpRemLocalPortNum
 identifies the port on which the remote system information
 is received.

 The value of this object is used as a port index to the
 lldpRemTable."
 ::= { alaLLDPTrustPortEntry 1}

 alaLldpTrustAdminStatus OBJECT-TYPE
 SYNTAX INTEGER {
 enabled(1),
 disabled(2)
 }
 MAX-ACCESS read-write
 STATUS      current
 DESCRIPTION
 "Admin status of the trust agent status on a given port."
 ::= { alaLLDPTrustPortEntry 2 }

 alaLldpTrustAction OBJECT-TYPE
 SYNTAX INTEGER {
 trap(1),
 shutdown(2),
 both(3)
 }
 MAX-ACCESS read-write
 STATUS      current
 DESCRIPTION
 "To decide what action to be taken in case of any violation occur."
 ::= { alaLLDPTrustPortEntry 3 }

 alaLldpTrustedStatus OBJECT-TYPE
 SYNTAX INTEGER {
 trusted(1),
 violated (2)
 }
 MAX-ACCESS read-only
 STATUS      current
 DESCRIPTION
 "To get the current violation status of the give port."
 ::= { alaLLDPTrustPortEntry 4 }

 alaLldpTrustedChassisSubtype OBJECT-TYPE
 SYNTAX INTEGER {
 chassisComponent(1),
 interfaceAlias(2),
 portComponent(3),
 macAddress(4),
 networkAddress(5),
 interfaceName(6),
 local(7),
 any(8)
 }
 MAX-ACCESS read-write
 STATUS      current
 DESCRIPTION
 "User configured/Allowed chassis id subtype on a given port."
 ::= { alaLLDPTrustPortEntry 5 }

-----------------------------------------------------------
--    TRUSTED REMOTE    SYSTEMS    DATA
-----------------------------------------------------------

alaLLDPTrustedRemTable OBJECT-TYPE
SYNTAX      SEQUENCE OF AlaLLDPTrustedRemEntry
MAX-ACCESS  not-accessible
STATUS      current
DESCRIPTION
"This table contains one trusted agent know on a given port."
::= { alaIND1LLDPTRUSTMIBObjects 2 }

alaLLDPTrustedRemEntry OBJECT-TYPE
SYNTAX      AlaLLDPTrustedRemEntry
MAX-ACCESS  not-accessible
STATUS      current
DESCRIPTION
"Information about a particular physical network connection.
Entries may be read from this table by the agent,
if a physical topology discovery process is active."
INDEX   {

alaLLDPTrustedRemLocalPortNumber

}
::= { alaLLDPTrustedRemTable 1 }

AlaLLDPTrustedRemEntry ::= SEQUENCE {

alaLLDPTrustedRemLocalPortNumber    LldpPortNumber,
alaLLDPTrustedRemChassisIdSubtype   LldpChassisIdSubtype,
alaLLDPTrustedRemChassisId          LldpChassisId,
alaLLDPTrustedRemPortIdSubtype      LldpPortIdSubtype,
alaLLDPTrustedRemPortId             LldpPortId
}


alaLLDPTrustedRemLocalPortNumber   OBJECT-TYPE
SYNTAX      LldpPortNumber
MAX-ACCESS  not-accessible
STATUS      current
DESCRIPTION
"The index value used to identify the port component
(contained in the local chassis with the LLDP agent)
associated with this entry.  The lldpRemLocalPortNum
identifies the port on which the remote system information
is received.

The value of this object is used as a port index to the
lldpRemTable."
::= { alaLLDPTrustedRemEntry 1}

alaLLDPTrustedRemChassisIdSubtype  OBJECT-TYPE
SYNTAX      LldpChassisIdSubtype
MAX-ACCESS  read-only
STATUS      current
DESCRIPTION
"The type of encoding used to identify the chassis associated
with the remote system."
REFERENCE
"IEEE 802.1AB-2005 9.5.2.2"
::= { alaLLDPTrustedRemEntry 2}

alaLLDPTrustedRemChassisId  OBJECT-TYPE
SYNTAX      LldpChassisId
MAX-ACCESS  read-only
STATUS      current
DESCRIPTION
"The string value used to identify the chassis component
associated with the remote system."
REFERENCE
"IEEE 802.1AB-2005 9.5.2.3"
::= { alaLLDPTrustedRemEntry 3}

alaLLDPTrustedRemPortIdSubtype  OBJECT-TYPE
SYNTAX      LldpPortIdSubtype
MAX-ACCESS  read-only
STATUS      current
DESCRIPTION
"The type of port identifier encoding used in the associated
'lldpRemPortId' object."
REFERENCE
"IEEE 802.1AB-2005 9.5.3.2"
::= { alaLLDPTrustedRemEntry 4}

alaLLDPTrustedRemPortId  OBJECT-TYPE
SYNTAX      LldpPortId
MAX-ACCESS  read-only
STATUS      current
DESCRIPTION
"The string value used to identify the port component
associated with the remote system."
REFERENCE
"IEEE 802.1AB-2005 9.5.3.3"
::= { alaLLDPTrustedRemEntry 5}

-----------------------------------------------------------
--   TRAP NOTIFICATIONS
-----------------------------------------------------------
alaLLDPTrustPortIfIndex   OBJECT-TYPE
    SYNTAX  InterfaceIndex
    MAX-ACCESS  accessible-for-notify
    STATUS      current
    DESCRIPTION
    "Interface index of the port, used for sending TRAP."
    ::= { alaIND1LLDPTRUSTMIBObjects 3 }

    alaLLDPTrustViolationReason   OBJECT-TYPE
    SYNTAX  INTEGER {
    agentalreadyexistonport (1),
    agentalreadyexistonotherport (2),
    chassisidsubtypemissmatch(3)
    }
    MAX-ACCESS  accessible-for-notify
    STATUS  current
    DESCRIPTION
    "Type of Violation.
    agentalreadyexistonport - There is already one trust agent exists on the port, Only
    one trust agent can be allowed on a port.
    agentalreadyexistonotherport - Same agent already present on another port, Any given
    remote agent shall be part of only on port.
    chassisidsubtypemissmatch - Chassisid Subtype is not matching with configured subtype."
    ::= { alaIND1LLDPTRUSTMIBObjects 4 }


    alaLLDPTrustPortId   OBJECT-TYPE
    SYNTAX               INTEGER
    MAX-ACCESS           accessible-for-notify
    STATUS               current
    DESCRIPTION          "LLDP Trust Port Violation."
    ::= { alaIND1LLDPTRUSTMIBObjects 5 }

    alaLLDPTrustChassisId   OBJECT-TYPE
    SYNTAX               LldpChassisId
    MAX-ACCESS           accessible-for-notify
    STATUS               current
    DESCRIPTION          "LLDP Trust Port ChassisId"
    ::= { alaIND1LLDPTRUSTMIBObjects 6 }

    alaLldpTrustViolation NOTIFICATION-TYPE
    OBJECTS {
    alaLLDPTrustPortIfIndex,
    alaLLDPTrustViolationReason
    }
    STATUS  current
    DESCRIPTION
    " Port configured to LLDP trust agent have violated.
    Notify the user by raising the Trap."
    ::= { alaLLDPTraps   1}

---------------------------------------------------------------
--  UNITS OF CONFORMANCE
---------------------------------------------------------------

alaINDLLDPTrustBaseGroup   OBJECT-GROUP
OBJECTS
{
alaLLDPTrustPortIfIndex,
alaLLDPTrustViolationReason,
alaLLDPTrustPortId,
alaLLDPTrustChassisId
}
STATUS  current
DESCRIPTION
"Collection of objects for management of LLDP Base Group."
::= { alaIND1LLDPTRUSTMIBGroups 1 }


alaINDLLDPTrustAgentGroup OBJECT-GROUP
OBJECTS
{
alaLldpTrustAdminStatus,
alaLldpTrustAction,
alaLldpTrustedStatus,
alaLldpTrustedChassisSubtype
}
STATUS  current
DESCRIPTION
"Collection of LLDP security mechanism objects for port status."
::= { alaIND1LLDPTRUSTMIBGroups 2 }

alaINDLLDPTrustRemoteAgentGroup OBJECT-GROUP
OBJECTS
{
alaLLDPTrustedRemChassisIdSubtype,
alaLLDPTrustedRemChassisId,
alaLLDPTrustedRemPortIdSubtype,
alaLLDPTrustedRemPortId
}
STATUS  current
DESCRIPTION
"Collection of LLDP trusted remote agent on port."
::= { alaIND1LLDPTRUSTMIBGroups 3 }

alaLldpTrustTrapGroup NOTIFICATION-GROUP
NOTIFICATIONS
{
alaLldpTrustViolation
}
STATUS  current
DESCRIPTION
"Collection of objects for LLDP Traps."
::= { alaIND1LLDPTRUSTMIBGroups 4 }

----------------------------------------------------------
-- COMPLIANCE
----------------------------------------------------------

alaIND1LLDPTRUSTMIBCompliance MODULE-COMPLIANCE
STATUS  current
DESCRIPTION
"Compliance statement for Alcatel LLDP"
MODULE
MANDATORY-GROUPS
{
alaINDLLDPTrustAgentGroup,
alaINDLLDPTrustRemoteAgentGroup,
alaINDLLDPTrustBaseGroup,
alaLldpTrustTrapGroup

}

::= { alaIND1LLDPTRUSTMIBCompliances 1 }

END
