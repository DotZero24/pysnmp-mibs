ALCATEL-ENT1-MSG-SRV-MIB DEFINITIONS ::= BEGIN

        IMPORTS
                Unsigned32, IpAddress,
                MODULE-IDENTITY, OBJECT-TYPE,
                NOTIFICATION-TYPE, OBJECT-IDENTITY
                                        FROM SNMPv2-SMI
                MacAddress, DisplayString, DateAndTime
                                        FROM SNMPv2-TC
                MODULE-COMPLIANCE, OBJECT-GROUP,
                NOTIFICATION-GROUP
                                        FROM SNMPv2-CONF
		InetAddress, InetAddressType
                        		FROM INET-ADDRESS-MIB
                softentIND1MsgSrvMIB
                                        FROM ALCATEL-ENT1-BASE;


                alcatelIND1MsgSrvMIB MODULE-IDENTITY
                LAST-UPDATED "201306050000Z"
                ORGANIZATION "Alcatel - Architects Of An Internet World"
                CONTACT-INFO
                "Please consult with Customer Service to insure the most appropriate
                version of this document is used with the products in question:

                        Alcatel Internetworking, Incorporated
                        (Division 1, Formerly XYLAN Corporation)
                        26801 West Agoura Road
                        Agoura Hills, CA  91301-5122
                        United States Of America

                        Telephone:      North America  +1 800 995 2696
                                        Latin America  +1 877 919 9526
                                        Europe         +31 23 556 0100
                                        Asia           +65 394 7933
                                        All Other      +1 818 878 4507

                Electronic Mail:         support@ind.alcatel.com
                World Wide Web:          http://www.ind.alcatel.com
                File Transfer Protocol:  ftp://ftp.ind.alcatel.com/pub/products/mibs"

                DESCRIPTION
                        "This module describes an authoritative enterprise-specific Simple
                        Network Management Protocol (SNMP) Management Information Base (MIB):

                        For the Birds Of Prey Product Line
                        MsgSrv for dynamically assigning IP to clients.

                        The right to make changes in specification and other information
                        contained in this document without prior notice is reserved.

                        No liability shall be assumed for any incidental, indirect, special, or
                        consequential damages whatsoever arising from or related to this
                        document or the information contained herein.

                        Vendors, end-users, and other interested parties are granted
                        non-exclusive license to use this specification in connection with
                        management of the products for which it is intended to be used.

                        Copyright (C) 1995-2002 Alcatel Internetworking, Incorporated
                        ALL RIGHTS RESERVED WORLDWIDE"

                REVISION      "201306050000Z"
                DESCRIPTION
                        "The QIP Message Service provides a framework for components
			such as DHCP server interact with other QIP components in the network.
                        This MIB provides the configuration information for Message Service."
                ::= { softentIND1MsgSrvMIB 1 }

-- --------------------------------------------------------------
                alcatelIND1MsgSrvMIBNotifications OBJECT-IDENTITY
                STATUS current
                DESCRIPTION
                        "Branch For Message Service Subsystem Notifications."
                ::= { alcatelIND1MsgSrvMIB 0 }

                alcatelIND1MsgSrvMIBObjects OBJECT-IDENTITY
                STATUS current
                DESCRIPTION
                        "Branch For Message Service Subsystem Managed Objects."
                ::= { alcatelIND1MsgSrvMIB 1 }

                alcatelIND1MsgSrvMIBConformance OBJECT-IDENTITY
                STATUS current
                DESCRIPTION
                        "Branch for MsgSrv Module MIB Subsystem Conformance Information."
                ::= { alcatelIND1MsgSrvMIB 2 }

                alcatelIND1MsgSrvMIBGroups OBJECT-IDENTITY
                STATUS current
                DESCRIPTION
                        "Branch for MsgSrv Module MIB Subsystem Units of Conformance."
                ::= { alcatelIND1MsgSrvMIBConformance 1 }

                alcatelIND1MsgSrvMIBCompliances OBJECT-IDENTITY
                STATUS current
                DESCRIPTION
                        "Branch for MsgSrv Module MIB Subsystem Compliance Statements."
                ::= { alcatelIND1MsgSrvMIBConformance 2 }

-- --------------------------------------------------------------


alaMsgSrvGlobalConfigStatus OBJECT-TYPE
        SYNTAX INTEGER
                {
                  enable(1),
                  disable(2)
                }
        MAX-ACCESS read-write
        STATUS current
        DESCRIPTION
            "This object is used to enable(1) or disable(2) QIP Message Service on the switch."
	DEFVAL { disable }
::= { alcatelIND1MsgSrvMIBObjects 1 }

alaMsgSrvGlobalRestart OBJECT-TYPE
        SYNTAX INTEGER
                {
                  inactive(1),
                  restart(2)
                }
        MAX-ACCESS read-write
        STATUS current
        DESCRIPTION
            "This object is used to restart(2) the QIP Message Service on the switch. Default value is
            inactive(1) which user can not set."
        DEFVAL { inactive }
::= { alcatelIND1MsgSrvMIBObjects 2 }


-- -------------------------------------------------------------
-- COMPLIANCE
-- -------------------------------------------------------------
alcatelIND1MsgSrvMIBCompliance MODULE-COMPLIANCE
        STATUS    current
        DESCRIPTION
            "Compliance statement for QIP Message Service."
        MODULE
        MANDATORY-GROUPS
        {
                alaMsgSrvGlobalConfigGroup
        }
        ::= { alcatelIND1MsgSrvMIBCompliances 1 }

-- -------------------------------------------------------------
-- UNITS OF CONFORMANCE
-- -------------------------------------------------------------
alaMsgSrvGlobalConfigGroup OBJECT-GROUP
        OBJECTS
        {
                alaMsgSrvGlobalConfigStatus,
                alaMsgSrvGlobalRestart
        }
        STATUS  current
        DESCRIPTION
            "Collection of objects for management of QIP Message Service Global Configuration."
        ::= { alcatelIND1MsgSrvMIBGroups 1 }


-- -------------------------------------------------------------

END
