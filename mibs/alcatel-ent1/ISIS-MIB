-- Changes in version 08.
--      Changed definiton of isisCircLevelDesIS to hold 7, not 6 bytes
--      Moved isisCircLocalID to CircLevel rather than IsisCircEntry
--      Remove isisCircIndex from isisIPRAEntry
--      Edit description of isisISAdjNeighPriority
--      Replace isisISAdjIPAddrAdjIndex with isisISAdjIndex
--      Simplified the names of variables which include Adj twice
--              isisISAdjAreaAddrAdjIndex, isisISAdjIPAddrAdjIndex,
--              and isisISAdjProtSuppAdjIndex.
--      Added isisSysMaxAge to control MaxAge for LSPs we generate
--      Added isisSysReceiveLSPBufferSize to control LSPs buffers

ISIS-MIB DEFINITIONS ::= BEGIN

     IMPORTS
        TEXTUAL-CONVENTION, DisplayString, RowStatus, TruthValue,
            TestAndIncr
                FROM SNMPv2-TC
        MODULE-IDENTITY, OBJECT-TYPE, OBJECT-IDENTITY, NOTIFICATION-TYPE,
            Integer32, Counter32, experimental
                FROM SNMPv2-SMI
        MODULE-COMPLIANCE, OBJECT-GROUP, NOTIFICATION-GROUP
                FROM SNMPv2-CONF
        InetAddressType, InetAddress, InetAddressPrefixLength
                FROM INET-ADDRESS-MIB;

    isisMIB MODULE-IDENTITY
        LAST-UPDATED "200205061200Z" -- UTC date of the most recent REVISION.
        ORGANIZATION "IETF IS-IS for IP Internets Working Group"
        CONTACT-INFO
             "Jeff Parker
              Axiowave Networks
              200 Nickerson Rd.
              Marlborough, MA 01752

              jparker@axiowave.com"

        DESCRIPTION
         "This document describes a management information base for
          the IS-IS Routing protocol, as described in ISO 10589,
          when it is used to construct routing tables for IP networks,
          as described in RFC 1195.

          This memo defines an experimental portion of the Management
          Information Base (MIB) for use with network management
          protocols in the Internet community.

          This memo is based on a 1994 IETF draft by Chris Gunner.
          This version has been modified to include MIB-II syntax, to
          exclude portions of the protocol that are not relevant to IP,
          and to add management support for current practice."
          REVISION "200205061200Z"
        DESCRIPTION
       "This version published as RFC 1195"
    ::= { experimental 37 }

-- Top-level stucture of the MIB

isisObjects             OBJECT IDENTIFIER ::= { isisMIB 1 }
isisNotifications       OBJECT IDENTIFIER ::= { isisMIB 2 }
isisConformance         OBJECT IDENTIFIER ::= { isisMIB 3 }

-- OBJECT IDENTIFIER definitions

    isisSystem OBJECT-IDENTITY
        STATUS  current
        DESCRIPTION
            "The object describes system wide attributes."
    ::= { isisObjects 1 }

    isisCirc OBJECT-IDENTITY
        STATUS  current
        DESCRIPTION
            "This object describes attributes associated with
             one Circuit"
    ::= { isisObjects 2 }

    isisCircLevelValues OBJECT-IDENTITY
        STATUS  current
        DESCRIPTION
            "This object describes attributes associated with
             area or domain relevant within a Circuit."
    ::= { isisObjects 3 }

    isisCircPDUCounters OBJECT-IDENTITY
        STATUS  current
        DESCRIPTION
            "This object collects counters associated with one Circuit
             at one level."
    ::= { isisObjects 4 }

    isisISAdj OBJECT-IDENTITY
        STATUS  current
        DESCRIPTION
            "This object describes attributes associated with an
             assoiciation with an adjacent Protocol Peer."
    ::= { isisObjects 5 }

    isisReachAddr OBJECT-IDENTITY
        STATUS  current
        DESCRIPTION
            "This object describes attributes associated with
             a configured address"
    ::= { isisObjects 6 }

    isisIPReachAddr OBJECT-IDENTITY
        STATUS  current
        DESCRIPTION
            "This object describes attributes associated with
             IP routes learned by configuration or through another
             protocol."
    ::= { isisObjects 7 }

    isisNotification OBJECT-IDENTITY
        STATUS  current
        DESCRIPTION
            "Objects included in Notifications."
    ::= { isisObjects 8 }


-- Type definitions


    OSINSAddress ::= TEXTUAL-CONVENTION
       STATUS       current
       DESCRIPTION
          "OSI Network Service Address, e.g. NSAP, SNPA, or Network
           Entity Title"
       SYNTAX     OCTET STRING (SIZE(0..21))

    SystemID ::= TEXTUAL-CONVENTION
       STATUS       current
       DESCRIPTION
          "A system ID."
     SYNTAX            OCTET STRING (SIZE(0..6))

    LinkStatePDUID ::= TEXTUAL-CONVENTION
       STATUS       current
       DESCRIPTION
          "A Link State PDU Identifier."
     SYNTAX            OCTET STRING (SIZE(8))

    AdminState ::= TEXTUAL-CONVENTION
       STATUS       current
       DESCRIPTION
             "Type used in enabling and disabling a row."
       SYNTAX       INTEGER
                     {
                      off(1),
                      on(2)
                     }

    UpTime ::= TEXTUAL-CONVENTION
       DISPLAY-HINT "d"
       STATUS       current
       DESCRIPTION
             "Number of seconds since the object has entered the state 'up'.
              If the object is not up, the number of seconds since the
              circuit was up, or since the system started, if the circuit
              has never been up."
       SYNTAX       Integer32

    LSPBuffSize ::= TEXTUAL-CONVENTION
       DISPLAY-HINT "d"
       STATUS       current
       DESCRIPTION
             "Integer sub range for LSP size."
       SYNTAX         Integer32 (512..16000)

    LevelState ::= TEXTUAL-CONVENTION
       STATUS       current
       DESCRIPTION
             "states of the ISIS protocol."
       SYNTAX        INTEGER
                        {
                         off (1),
                         on (2),
                         waiting (3),
                         overloaded(4)
                        }

    SupportedProtocol ::= TEXTUAL-CONVENTION
       STATUS       current
       DESCRIPTION
             "Types of network protocol supported by Integrated ISIS.
              The values for ISO8473 and IP are those registered for
              these protocols in ISO TR9577."
       SYNTAX        INTEGER
                        {
                         iso8473(129),
                         ip(204),
                         ipV6(205)
                        }

    DefaultMetric ::= TEXTUAL-CONVENTION
       DISPLAY-HINT "d"
       STATUS       current
       DESCRIPTION
          "Integer sub-range for default metric for single hop.
           ISO 10589 provides for 4 types of metric.  Only the
           'default' metric is used in practice."
       SYNTAX        Integer32 (1..63)

    MetricType ::= TEXTUAL-CONVENTION
       STATUS       current
       DESCRIPTION
          "Is this an Internal or External Metric?"
       SYNTAX           INTEGER
                           {
                            internal(1),
                            external(2)
                           }

    MetricStyle ::= TEXTUAL-CONVENTION
       STATUS       current
       DESCRIPTION
          "Do we use 1195 style Metrics or wide metrics."
       SYNTAX           INTEGER
                           {
                            narrow(1),
                            wide(2),
                            both(3)
                           }

    ISLevel ::= TEXTUAL-CONVENTION
       STATUS       current
       DESCRIPTION
          "Identifies a level."
       SYNTAX           INTEGER
                           {
                            area(1),
                            domain(2),
                            none(3)
                           }

    IsisPDUHeader ::= TEXTUAL-CONVENTION
       STATUS       current
       DESCRIPTION
          "A block to contain the header from a PDU."
       SYNTAX     OCTET STRING (SIZE(1..64))

    CircuitID ::= TEXTUAL-CONVENTION
       STATUS       current
       DESCRIPTION
             "ID for a circuit."
       SYNTAX OCTET STRING (SIZE(2..9))
    ISPriority ::= TEXTUAL-CONVENTION
       DISPLAY-HINT "d"
       STATUS       current
       DESCRIPTION
          "Integer sub-range for ISIS priority."
     SYNTAX             Integer32 (1..127)

-- Behavior Definitions

-- ResettingTimer behavior definition
-- "This object specifies the interval between certain events in
-- the operation of the protocol state machine. If the value of
-- this object is set to a new value while the protocol state
-- machine is in operation, the implementation shall take the
-- necessary steps to ensure that for any time interval which
-- was in progress when the value of the corresponding object
-- was changed, the next expiration of that interval takes place
-- the specified time after the original start of that interval,
-- or immediately, whichever is later. The precision with which
-- this time shall be implemented shall be the same as that
-- associated with the basic operation of the timer object."

-- ReplaceOnlyWhileDisabled behavior definition
-- "This object may not be modified while the corresponding
-- table row's variable of type AdminState is in state on."

-- OperationalState behavior definition
-- "This object controls the enabling and disabling of the
-- corresponding table row. Setting this object to the value
-- off has the effect of disabling the corresponding row.
-- Setting this object to the value on has the effect of
-- enabling the corresponding row. Setting the value of this
-- object to the same value as its current value has no effect.
-- If the table entry also contains an object controlling the
-- row status then the object following the operationalState
-- behavior shall not be set to on when the object following
-- the Row Status behavior has value off. An attempt to do
-- so is rejected."

     isisSysTable OBJECT-TYPE
         SYNTAX SEQUENCE OF IsisSysEntry
         MAX-ACCESS not-accessible
         STATUS current
         DESCRIPTION
             "The set of instance of the Integrated IS-IS
              protocol existing on the system."
     ::= { isisSystem 1 }

     isisSysEntry OBJECT-TYPE
         SYNTAX IsisSysEntry
         MAX-ACCESS not-accessible
         STATUS current
         DESCRIPTION
             "Each row defines information specific to a single
              instance of the IS-IS protocol existing on the system."
         REFERENCE "{ISIS.poi cLNSISISBasic-P (1)}"
         INDEX { isisSysInstance }
     ::= { isisSysTable 1 }

     IsisSysEntry ::=
         SEQUENCE {
             isisSysInstance
                 Integer32,
             isisSysVersion
                 DisplayString,
             isisSysType
                 INTEGER,
             isisSysID
                 SystemID,
             isisSysMaxPathSplits
                 Integer32,
             isisSysMaxLSPGenInt
                 Integer32,
             isisSysOrigL1LSPBuffSize
                 LSPBuffSize,
             isisSysMaxAreaAddresses
                 Integer32,
             isisSysMinL1LSPGenInt
                 Integer32,
             isisSysMinL2LSPGenInt
                 Integer32,
             isisSysPollESHelloRate
                 Integer32,
             isisSysWaitTime
                 Integer32,
             isisSysAdminState
                 AdminState,
             isisSysL1State
                 LevelState,
             isisSysOrigL2LSPBuffSize
                 LSPBuffSize,
             isisSysL2State
                 LevelState,
             isisSysLogAdjacencyChanges
                 TruthValue,
             isisSysMaxAreaCheck
                 TruthValue,
             isisSysNextCircIndex
                 TestAndIncr,
             isisSysExistState
                 RowStatus,
             isisSysL2toL1Leaking
                 TruthValue,
             isisSysSetOverload
                 INTEGER,
             isisSysL1MetricStyle
                 MetricStyle,
             isisSysL1SPFConsiders
                 MetricStyle,
             isisSysL2MetricStyle
                 MetricStyle,
             isisSysL2SPFConsiders
                 MetricStyle,
             isisSysTEEnabled
                 ISLevel,
             isisSysMaxAge
                 Integer32,
             isisSysReceiveLSPBufferSize
                 Integer32
         }

     isisSysInstance OBJECT-TYPE
         SYNTAX Integer32 (1..10000)
         MAX-ACCESS not-accessible
         STATUS current
         DESCRIPTION
             "The unique identifier of the Integrated IS-IS
              instance to which this row corresponds.
              This object follows the index behavior."
     ::= { isisSysEntry 1 }

     isisSysVersion OBJECT-TYPE
         SYNTAX DisplayString
         MAX-ACCESS read-only
         STATUS current
         DESCRIPTION
             "The version number of the IS-IS protocol which this
              instance implements."
         REFERENCE "{ISIS.aoi version (1)}"
         DEFVAL { "1" }
     ::= { isisSysEntry 2 }

     isisSysType OBJECT-TYPE
         SYNTAX INTEGER {
             level1IS (1),
             level2IS (2),
             level1L2IS (3)
             }
         MAX-ACCESS read-create
         STATUS current
         DESCRIPTION
             "The type of this instance of the Integrated
              IS-IS protocol. This object follows the
              replaceOnlyWhileDisabled behavior."
         REFERENCE "{ISIS.aoi iSType (2)}"
         DEFVAL { level1L2IS }
     ::= { isisSysEntry 3 }

     isisSysID OBJECT-TYPE
         SYNTAX SystemID
         MAX-ACCESS read-create
         STATUS current
         DESCRIPTION
             "The ID for this instance of the Integrated IS-IS
              protocol. This value is appended to each of the
              area addresses to form the Network Entity Titles.
              The derivation of a value for this object is
              implementation-specific.  Some implementations may
              automatically assign values and not permit an
              SNMP write, while others may require the value
              to be set manually."
         REFERENCE "{ISIS.aoi systemId (119)}"
     ::= { isisSysEntry 4 }

     isisSysMaxPathSplits OBJECT-TYPE
         SYNTAX Integer32 (1..32)
         MAX-ACCESS read-create
         STATUS current
         DESCRIPTION
             "Maximum number of paths with equal routing metric value
             which it is permitted to split between. This object
             follows the replaceOnlyWhileDisabled behavior."
         REFERENCE "{ISIS.aoi maximumPathSplits (3)}"
         DEFVAL { 2 }
     ::= { isisSysEntry 5 }

     isisSysMaxLSPGenInt OBJECT-TYPE
         SYNTAX Integer32 (1..65535)
         UNITS "seconds"
         MAX-ACCESS read-create
         STATUS current
         DESCRIPTION
             "Maximum interval, in seconds, between generated LSPs
              by this instance of the protocol. This object follows
              the resettingTimer behavior.
              Should be at least 300 seconds less than isisSysMaxAge."
         REFERENCE "{ISIS.aoi maximumLSPGenerationInterval (6)}"
         DEFVAL { 900 }
     ::= { isisSysEntry 6 }

     isisSysOrigL1LSPBuffSize OBJECT-TYPE
         SYNTAX LSPBuffSize
         MAX-ACCESS read-create
         STATUS current
         DESCRIPTION
             "The maximum size of Level 1 LSPs and SNPs originated by
             this instance of the protocol. This object follows the
             replaceOnlyWhileDisabled behavior."
         REFERENCE "{ISIS.aoi originatingL1LSPBufferSize (9)}"
         DEFVAL { 1492 }
     ::= { isisSysEntry 7 }

     isisSysMaxAreaAddresses OBJECT-TYPE
         SYNTAX Integer32 (3..254)
         MAX-ACCESS read-create
         STATUS current
         DESCRIPTION
             "The maximum number of area addresses to be permitted for
              this instance of the protocol. Note that all
              Intermediate Systems in the same area must have the same
              value configured for this attribute if correct operation
              is to be assumed. This object follows the
              replaceOnlyWhileDisabled behavior."
         REFERENCE "{ISIS.aoi maximumAreaAddresses (4)}"
         DEFVAL { 3 }
     ::= { isisSysEntry 8 }

     isisSysMinL1LSPGenInt OBJECT-TYPE
         SYNTAX Integer32 (1..65535)
         UNITS "seconds"
         MAX-ACCESS read-create
         STATUS current
         DESCRIPTION
             "Minimum interval, in seconds, between successive generation
              of L1 LSPs with the same LSPID by this instace of the protocol.
              This object follows the resettingTimer behavior."
         REFERENCE "{ISIS.aoi minimumLSPGenerationInterval (11)}"
         DEFVAL { 30 }
     ::= { isisSysEntry 9 }

     isisSysMinL2LSPGenInt OBJECT-TYPE
         SYNTAX Integer32 (1..65535)
         UNITS "seconds"
         MAX-ACCESS read-create
         STATUS current
         DESCRIPTION
             "Minimum interval, in seconds, between successive generation
             of L2 LSPs with the same LSPID by this instance of the protocol.
             This object follows the resettingTimer behavior."
         REFERENCE "{ISIS.aoi minimumLSPGenerationInterval (11)}"
         DEFVAL { 30 }
     ::= { isisSysEntry 10 }

     isisSysPollESHelloRate OBJECT-TYPE
         SYNTAX Integer32 (1..65535)
         UNITS "seconds"
         MAX-ACCESS read-create
         STATUS current
         DESCRIPTION
             "The value, in seconds, to be used for the suggested ES
             configuration timer in ISH PDUs when soliciting the ES
             configuration."
         REFERENCE "{ISIS.aoi pollESHelloRate (13)}"
         DEFVAL { 50 }
     ::= { isisSysEntry 11 }

     isisSysWaitTime OBJECT-TYPE
         SYNTAX Integer32 (1..65535)
         UNITS "seconds"
         MAX-ACCESS read-create
         STATUS current
         DESCRIPTION
             "Number of seconds to delay in waiting state before
             entering on state. This object follows the resettingTimer
             behavior."
         REFERENCE "{ISIS.aoi waitingTime (15)}"
         DEFVAL { 60 }
     ::= { isisSysEntry 12 }

     isisSysAdminState OBJECT-TYPE
         SYNTAX AdminState
         MAX-ACCESS read-create
         STATUS current
         DESCRIPTION
             "The administrative state of this instance of the
              Integrated IS-IS protocol. Setting this object to the
              value 'on' when its current value is 'off' enables operation
              of this instnace of the Integrated IS-IS protocol."
         DEFVAL { off }
     ::= { isisSysEntry 13 }

     isisSysL1State OBJECT-TYPE
         SYNTAX LevelState
         MAX-ACCESS read-only
         STATUS current
         DESCRIPTION
             "The state of the Level 1 database.
              The value 'overloaded' indicates a database that is
              low on an essential resource, such as memory.
              The administrator may set the state to 'wait' when
              the router is initializing by setting the object
              isisSysSetOverload.
              If the state is waiting or overloaded, we
              originate LSPs with the Overload bit set."
         REFERENCE "{ISIS.aoi l1State (17)}"
     ::= { isisSysEntry 14 }

-- The following objects map those from the cLNSISISLevel2-P
-- Package

     isisSysOrigL2LSPBuffSize OBJECT-TYPE
         SYNTAX LSPBuffSize
         MAX-ACCESS read-create
         STATUS current
         DESCRIPTION
             "The maximum size of Level 2 LSPs and SNPs originated by
             this system. This object follows the
             replaceOnlyWhileDisabled behavior."
         REFERENCE "{ISIS.aoi originatingL2LSPBufferSize (26)}"
         DEFVAL { 1492 }
     ::= { isisSysEntry 15 }

     isisSysL2State OBJECT-TYPE
         SYNTAX LevelState
         MAX-ACCESS read-only
         STATUS current
         DESCRIPTION
             "The state of the Level 2 database.
              The value 'overloaded' indicates a database that is
              low on an essential resource, such as memory.
              The administrator may set the state to 'wait' when
              the router is initializing by setting the object
              isisSysSetOverload.
              If the state is waiting or overloaded, we
              originate LSPs with the Overload bit set."
         REFERENCE "{ISIS.aoi l2State (28)}"
     ::= { isisSysEntry 16 }
     isisSysLogAdjacencyChanges OBJECT-TYPE
         SYNTAX TruthValue
         MAX-ACCESS read-create
         STATUS current
         DESCRIPTION
             "If true, causes IS-IS to generate a log message when an
             IS-IS adjacency changes state (up or down)."
         DEFVAL { false }
     ::= { isisSysEntry 17 }

     isisSysMaxAreaCheck OBJECT-TYPE
         SYNTAX TruthValue
         MAX-ACCESS read-create
         STATUS current
         DESCRIPTION
             "When on, enables checking of maximum area
             addresses per IS version of ISO10589."
         DEFVAL { true }
     ::= { isisSysEntry 18 }

     isisSysNextCircIndex OBJECT-TYPE
         SYNTAX TestAndIncr
         MAX-ACCESS read-only
         STATUS current
         DESCRIPTION
             "This object is used to assign values to
             isisCircIndex as described in 'Textual
             Conventions for SNMPv2'.  The network manager
             reads this object, and then writes the value
             back as the isisCircIndex in a SET that creates
             a new instance of isisCircEntry.  If the SET
             fails with the code 'inconsistentValue', then
             the process must be repeated; If the SET succeeds,
             then the object is incremented, and the new
             isisCircuit is created according to the manager's
             directions."
     ::= { isisSysEntry 19 }

     isisSysExistState OBJECT-TYPE
         SYNTAX RowStatus
         MAX-ACCESS read-create
         STATUS current
         DESCRIPTION
             "The state of the ISIS router.  Turning this to
              state 'destroy' forces the router to forget all
              the current configuration.  Setting the state to
              'notInService' stops protocol processing, but
              retains the configuration."
         DEFVAL { active }
     ::= { isisSysEntry 20 }

     isisSysL2toL1Leaking OBJECT-TYPE
         SYNTAX TruthValue
         MAX-ACCESS read-create
         STATUS current
         DESCRIPTION
             "If true, allow the router to leak L2 routes into L1."
         DEFVAL { false }
     ::= { isisSysEntry 21 }

     isisSysSetOverload OBJECT-TYPE
         SYNTAX INTEGER
                 {
                   setL1Overload(1),
                   setL2Overload(2),
                   setL1L2Overload(3),
                   overloadClear(4)
                 }
         MAX-ACCESS read-create
         STATUS current
         DESCRIPTION
             "Administratively set the overload bit for each level.
              The overload bit will continue to be set if the
              implementation runs out of memory, independent of
              this variable"
         DEFVAL {overloadClear }
     ::= { isisSysEntry 22 }

     isisSysL1MetricStyle OBJECT-TYPE
         SYNTAX MetricStyle
         MAX-ACCESS read-create
         STATUS current
         DESCRIPTION
             "Which style of Metric do we generate in our L1 LSPs?
              This object follows the replaceOnlyWhileDisabled
              behavior."
         DEFVAL { narrow }
     ::= { isisSysEntry 23 }

     isisSysL1SPFConsiders OBJECT-TYPE
         SYNTAX MetricStyle
         MAX-ACCESS read-create
         STATUS current
         DESCRIPTION
             "Which style of Metric do we consider in our
              L1 SPF computation?"
         DEFVAL { narrow }
     ::= { isisSysEntry 24 }

     isisSysL2MetricStyle OBJECT-TYPE
         SYNTAX MetricStyle
         MAX-ACCESS read-create
         STATUS current
         DESCRIPTION
             "Which style of Metric do we generate in our L2 LSPs?
              This object follows the replaceOnlyWhileDisabled
              behavior."
         DEFVAL { narrow }
     ::= { isisSysEntry 25 }

     isisSysL2SPFConsiders OBJECT-TYPE
         SYNTAX MetricStyle
         MAX-ACCESS read-create
         STATUS current
         DESCRIPTION
             "Which style of Metric do we consider in our
              SPF computation?"
         DEFVAL { narrow }
     ::= { isisSysEntry 26 }

     isisSysTEEnabled OBJECT-TYPE
         SYNTAX ISLevel
         MAX-ACCESS read-create
         STATUS current
         DESCRIPTION
             "Do we do Traffic Engineering?  At which level?"
         DEFVAL { none }
     ::= { isisSysEntry 27 }

     isisSysMaxAge OBJECT-TYPE
         SYNTAX Integer32 (1200..65535)
         UNITS "seconds"
         MAX-ACCESS read-create
         STATUS current
         DESCRIPTION
             "Value to place in RemainingLifeTime field of
              the LSPs we generate.
              This is should be at least 300 seconds greater than
              isisSysMaxLSPGenInt."
         DEFVAL { 1200 }
     ::= { isisSysEntry 28 }

     isisSysReceiveLSPBufferSize OBJECT-TYPE
         SYNTAX Integer32 (1492..65535)
         UNITS "bytes"
         MAX-ACCESS read-create
         STATUS current
         DESCRIPTION
             "Size of the largest Buffer we can store.
              This should be at least as big as the maximum
              of isisSysOrigL2LSPBuffSize and isisSysOrigL1LSPBuffSize."
         DEFVAL { 1492 }
     ::= { isisSysEntry 29 }

---
-- The Level 1 Manual Area Address Table
-- contains the set of area addresses manually configured
-- for each instance of the Integrated IS-IS protocol.
-- At least one row in which the value of isisManAreaAddrExistState
-- is active must be present for each active instance of
-- the protocol The maximum number of rows in this table for
-- each instance of the protocol for which the object
-- isisManAreaAddrExistState has the value active is the value
-- of isisSysMaxAreaAddresses.
--     An attempt to create more than isisSysMaxAreaAddresses
-- rows of isisManAreaAddrEntry with state 'active' in one
-- instance of the IS-IS protocol should return
-- inconsistentValue.

     isisManAreaAddrTable OBJECT-TYPE
         SYNTAX SEQUENCE OF IsisManAreaAddrEntry
         MAX-ACCESS not-accessible
         STATUS current
         DESCRIPTION
             "The set of manual area addresses configured on this
             Intermediate System."
         REFERENCE "{ISIS.aoi manualAreaAddresses (10)}"
     ::= { isisSystem 2 }

     isisManAreaAddrEntry OBJECT-TYPE
         SYNTAX IsisManAreaAddrEntry
         MAX-ACCESS not-accessible
         STATUS current
         DESCRIPTION
             "Each entry contains one area address manually configured
             on this system"
         INDEX { isisSysInstance,
                 isisManAreaAddr }
     ::= { isisManAreaAddrTable 1 }

     IsisManAreaAddrEntry ::=
         SEQUENCE {
             isisManAreaAddr
                 OSINSAddress,
             isisManAreaAddrExistState
                 RowStatus
             }

     isisManAreaAddr OBJECT-TYPE
         SYNTAX OSINSAddress
         MAX-ACCESS not-accessible
         STATUS current
         DESCRIPTION
             "A manually configured area address for this system. This
              object follows the index behavior.

              Note: an index for the entry {1, {49.0001} active} in
              this table would be the ordered pair
              (1, (0x03 0x49 0x00 0x01)), as the length of an Octet
              string is part of the OID."

     ::= { isisManAreaAddrEntry 1 }

     isisManAreaAddrExistState OBJECT-TYPE
         SYNTAX RowStatus
         MAX-ACCESS read-create
         STATUS current
         DESCRIPTION
             "The state of the isisManAreaAddrEntry. This object
              follows the Row Status behavior. If the isisSysAdminState
              for this instance of the IS-IS protocol is 'on', and an
              attempt is made to set this object to the value 'destroy'
              or 'notInService' when this is the only isisManAreaAddrEntry
              in state 'active' for this instance of the IS-IS protocol
              should return  inconsistentValue."

         DEFVAL { active }
     ::= { isisManAreaAddrEntry 2 }

-- The Level 1 Area Address Table

-- The Level 1 Area Address Table contains the
-- union of the sets of relevant area addresses reported
-- in all Level 1 LSPs received by this Intermediate System.

     isisAreaAddrTable OBJECT-TYPE
         SYNTAX SEQUENCE OF IsisAreaAddrEntry
         MAX-ACCESS not-accessible
         STATUS current
         DESCRIPTION
            "The union of the sets of area addresses reported in all
             Level 1 LSPs with segment number zero received by this
             instance of the protocol from Intermediate Systems which
             are reachable via Level 1 routing."
         REFERENCE "{ISIS.aoi areaAddresses (18)}"
     ::= { isisSystem 3 }

     isisAreaAddrEntry OBJECT-TYPE
         SYNTAX IsisAreaAddrEntry
         MAX-ACCESS not-accessible
         STATUS current
         DESCRIPTION
             "Each entry contains one area address reported in a
              Level 1 LSP received by this instance of the IS-IS
              protocol."
         INDEX { isisSysInstance,
                 isisAreaAddr }
     ::= { isisAreaAddrTable 1 }

     IsisAreaAddrEntry ::=
         SEQUENCE {
             isisAreaAddr
                 OSINSAddress
             }

     isisAreaAddr OBJECT-TYPE
         SYNTAX OSINSAddress
         MAX-ACCESS read-only
         STATUS current
         DESCRIPTION
             "An area address reported in a Level 1 LSP received by
             this instance of the IS-IS protocol."
     ::= { isisAreaAddrEntry 1 }

-- The System Integrated Group

-- The System Integrated Group is present if the system
-- supports Integrated ISIS at Level 1.

-- The System Protocol Supported Table

-- The System Protocol Supported Table contains the manually
-- configured set of protocols supported by each
-- instance of the Integrated ISIS protocol.
--

     isisSysProtSuppTable OBJECT-TYPE
         SYNTAX SEQUENCE OF IsisSysProtSuppEntry
         MAX-ACCESS not-accessible
         STATUS current
         DESCRIPTION
             "This table contains the manually configured set of
              protocols supported by each instance of the Integrated
              ISIS protocol."
     ::= { isisSystem 4 }

     isisSysProtSuppEntry OBJECT-TYPE
         SYNTAX IsisSysProtSuppEntry
         MAX-ACCESS not-accessible
         STATUS current
         DESCRIPTION
             "Each entry contains one protocol supported by an
              instance of the Integrated ISIS protocol."

         INDEX {  isisSysInstance,
                  isisSysProtSuppProtocol }

     ::= { isisSysProtSuppTable 1 }

     IsisSysProtSuppEntry ::=
         SEQUENCE {
             isisSysProtSuppProtocol
                 SupportedProtocol,
             isisSysProtSuppExistState
                 RowStatus
             }

     isisSysProtSuppProtocol OBJECT-TYPE
         SYNTAX SupportedProtocol
         MAX-ACCESS not-accessible
         STATUS current
         DESCRIPTION
             "One supported protocol. This object follows the index
             behavior."
     ::= { isisSysProtSuppEntry 1 }

     isisSysProtSuppExistState OBJECT-TYPE
         SYNTAX RowStatus
         MAX-ACCESS read-create
         STATUS current
         DESCRIPTION
             "The state of the isisSysProtSuppEntry. This object
              follows the RowStatus behavior."
         DEFVAL { active }
     ::= { isisSysProtSuppEntry 2 }

-- The Summary Address Table

-- The Summary Address Table contains the set of summary
-- addresses manually configured for each instance of
-- IP Integrated ISIS on the system.

     isisSummAddrTable OBJECT-TYPE
         SYNTAX SEQUENCE OF IsisSummAddrEntry
         MAX-ACCESS not-accessible
         STATUS current
         DESCRIPTION
             "The set of IP summary addresses to use in forming
              summary TLVs originated by this Intermediate System.

              An administrator may use a summary address to combine
              and modify IP Reachability announcements.  If the
              Intermediate system can reach any subset of the summary
              address, the summary address will be announced instead,
              at the configured metric."
     ::= { isisSystem 5 }

     isisSummAddrEntry OBJECT-TYPE
         SYNTAX IsisSummAddrEntry
         MAX-ACCESS not-accessible
         STATUS current
         DESCRIPTION
             "Each entry contains one IP summary address."

         INDEX { isisSysInstance,
                 isisSummAddressType,
                 isisSummAddress,
                 isisSummAddrPrefixLen }
     ::= { isisSummAddrTable 1 }

     IsisSummAddrEntry ::=
         SEQUENCE {
             isisSummAddressType
                 InetAddressType,
             isisSummAddress
                 InetAddress,
             isisSummAddrPrefixLen
                 InetAddressPrefixLength,
             isisSummAddrExistState
                 RowStatus,
             isisSummAddrAdminState
                 INTEGER,
             isisSummAddrMetric
                 DefaultMetric
         }

     isisSummAddressType OBJECT-TYPE
         SYNTAX InetAddressType
         MAX-ACCESS not-accessible
         STATUS current
         DESCRIPTION
             "The Type of IP address for this summary address.
              This object follows the index behavior."
     ::= { isisSummAddrEntry 1 }

     isisSummAddress OBJECT-TYPE
         SYNTAX InetAddress (SIZE(4|16))
         MAX-ACCESS not-accessible
         STATUS current
         DESCRIPTION
             "The IP Address value for this summary address.
              This object follows the index behavior."
     ::= { isisSummAddrEntry 2 }

     isisSummAddrPrefixLen OBJECT-TYPE
         SYNTAX InetAddressPrefixLength (0..128)
         MAX-ACCESS not-accessible
         STATUS current
         DESCRIPTION
             "The Length of the IP NetMask for this summary address."
     ::= { isisSummAddrEntry 3 }

     isisSummAddrExistState OBJECT-TYPE
         SYNTAX RowStatus
         MAX-ACCESS read-create
         STATUS current
         DESCRIPTION
             "The existence state of this summary address. This object
              follows the row status behavior."
         DEFVAL { active }
     ::= { isisSummAddrEntry 4 }

     isisSummAddrAdminState OBJECT-TYPE
         SYNTAX INTEGER
                 {
                    summaryL1(1),
                    summaryL2(2),
                    summaryL1L2(3),
                    summaryOff(4)
                 }
         MAX-ACCESS read-create
         STATUS current
         DESCRIPTION
             "The administrative state of this entry.  When the
              administrative state changes, if the new value would
              cause the contents of LSPs originated by the system
              to change, then those new LSPs must be generated and
              sent as soon as is permitted by the ISIS protocol.

              A summary entry may exist but be disable (summaryOff).
              Or it may be used to generate reacability entries at
              a single level, such as Level 2 (summaryL2)."
         DEFVAL { summaryOff }
     ::= { isisSummAddrEntry 5 }

     isisSummAddrMetric OBJECT-TYPE
         SYNTAX DefaultMetric
         MAX-ACCESS read-create
         STATUS current
         DESCRIPTION
             "The metric value to announce this summary
              address with in LSPs generated by this system."
         DEFVAL { 20 }
     ::= { isisSummAddrEntry 6 }

-- System Stats

     isisSysStatsTable OBJECT-TYPE
         SYNTAX SEQUENCE OF IsisSysStatsEntry
         MAX-ACCESS not-accessible
         STATUS current
         DESCRIPTION
             "Statistics about system events."
     ::= { isisSystem 6 }

     isisSysStatsEntry OBJECT-TYPE
         SYNTAX IsisSysStatsEntry
         MAX-ACCESS not-accessible
         STATUS current
         DESCRIPTION
             "Statistics about one level of the protocol."

         INDEX { isisSysInstance,
                 isisSysStatLevel }
     ::= { isisSysStatsTable 1 }


     IsisSysStatsEntry ::=
         SEQUENCE {
             isisSysStatLevel
                 INTEGER,
             isisSysStatCorrLSPs
                 Counter32,
             isisSysStatAuthTypeFails
                 Counter32,
             isisSysStatAuthFails
                 Counter32,
             isisSysStatLSPDbaseOloads
                 Counter32,
             isisSysStatManAddrDropFromAreas
                 Counter32,
             isisSysStatAttmptToExMaxSeqNums
                 Counter32,
             isisSysStatSeqNumSkips
                 Counter32,
             isisSysStatOwnLSPPurges
                 Counter32,
             isisSysStatIDFieldLenMismatches
                 Counter32,
             isisSysStatMaxAreaAddrMismatches
                 Counter32,
             isisSysStatPartChanges
                 Counter32
        }

     isisSysStatLevel OBJECT-TYPE
         SYNTAX INTEGER {
             level1IS (1),
             level2IS (2)
             }
         MAX-ACCESS not-accessible
         STATUS current
         DESCRIPTION
             "The level that this entry describes."
     ::= { isisSysStatsEntry 1 }

     isisSysStatCorrLSPs OBJECT-TYPE
         SYNTAX Counter32
         UNITS "frames"
         MAX-ACCESS read-only
         STATUS current
         DESCRIPTION
             "Number of corrupted in-memory LSPs detected.

              LSPs received from the wire with a bad checksum
              are silently dropped and not counted."
         REFERENCE "{ISIS.aoi corruptedLSPsDetected (19)}"
     ::= { isisSysStatsEntry 2 }
     isisSysStatAuthTypeFails OBJECT-TYPE
         SYNTAX Counter32
         UNITS "frames"
         MAX-ACCESS read-only
         STATUS current
         DESCRIPTION
             "The number of authentication type mismatches recognized
              by this instance of the protocol."
     ::= { isisSysStatsEntry 3 }

     isisSysStatAuthFails OBJECT-TYPE
         SYNTAX Counter32
         UNITS "frames"
         MAX-ACCESS read-only
         STATUS current
         DESCRIPTION
             "The number of authentication failures recognized by this
              instance of the protocol."
     ::= { isisSysStatsEntry 4 }

     isisSysStatLSPDbaseOloads OBJECT-TYPE
         SYNTAX Counter32
         MAX-ACCESS read-only
         STATUS current
         DESCRIPTION
             "Number of times the LSP L1 database has become
             overloaded."
         REFERENCE "{ISIS.aoi lSPL1DatabaseOverloads (20)}"
     ::= { isisSysStatsEntry 5 }

     isisSysStatManAddrDropFromAreas OBJECT-TYPE
         SYNTAX Counter32
         MAX-ACCESS read-only
         STATUS current
         DESCRIPTION
             "Number of times a manual address has been dropped from
             the area."
         REFERENCE "{ISIS.aoi manualAddressesDroppedFromArea (21)}"
     ::= { isisSysStatsEntry 6 }

     isisSysStatAttmptToExMaxSeqNums OBJECT-TYPE
         SYNTAX Counter32
         MAX-ACCESS read-only
         STATUS current
         DESCRIPTION
             "Number of times the IS has attempted to exceed the
             maximum sequence number."
         REFERENCE "{ISIS.aoi
             attemptsToExceedmaximumSequenceNumber (22)}"
     ::= { isisSysStatsEntry 7 }

     isisSysStatSeqNumSkips OBJECT-TYPE
         SYNTAX Counter32
         MAX-ACCESS read-only
         STATUS current
         DESCRIPTION
             "Number of times a sequence number skip has occurred."
         REFERENCE "{ISIS.aoi sequenceNumberSkips (23)}"
     ::= { isisSysStatsEntry 8 }

     isisSysStatOwnLSPPurges OBJECT-TYPE
         SYNTAX Counter32
         MAX-ACCESS read-only
         STATUS current
         DESCRIPTION
             "Number of times a zero-aged copy of the system's own LSP
             is received from some other node."
         REFERENCE "{ISIS.aoi ownLSPPurges (24)}"
     ::= { isisSysStatsEntry 9 }

     isisSysStatIDFieldLenMismatches OBJECT-TYPE
         SYNTAX Counter32
         UNITS "frames"
         MAX-ACCESS read-only
         STATUS current
         DESCRIPTION
             "Number of times a PDU is received with a different value
             for ID field length to that of the receiving system."
         REFERENCE "{ISIS.aoi iDFieldLengthMismatches (25)}"
     ::= { isisSysStatsEntry 10 }

     isisSysStatMaxAreaAddrMismatches OBJECT-TYPE
         SYNTAX Counter32
         UNITS "frames"
         MAX-ACCESS read-only
         STATUS current
         DESCRIPTION
             "Number of times a PDU is received with a different value
             for MaximumAreaAddresses from that of the receiving
             system."
         REFERENCE "{ISIS.aoi MaximumAreaAddressesMismatches (118)}"
     ::= { isisSysStatsEntry 11 }

     isisSysStatPartChanges OBJECT-TYPE
         SYNTAX Counter32
         MAX-ACCESS read-only
         STATUS current
         DESCRIPTION
             "partition changes"
     ::= { isisSysStatsEntry 12 }

-- The Circuit Group

-- The Circuit Group is current

-- The Circuit Table
-- Each broadcast or point-to-point interface on the system
-- corresponds to one entry in the Circuit table. There may be
-- many X.25 DA circuit entries in the Circuit table for an
-- X.25 interface.

     isisCircTable OBJECT-TYPE
         SYNTAX SEQUENCE OF IsisCircEntry
         MAX-ACCESS not-accessible
         STATUS current
         DESCRIPTION
             "The table of circuits used by each instance of
             Integrated IS-IS on this system."
     ::= { isisCirc 1 }

     isisCircEntry OBJECT-TYPE
         SYNTAX IsisCircEntry
         MAX-ACCESS not-accessible
         STATUS current
         DESCRIPTION
             "An isisCircEntry exists for each circuit used by
             Integrated IS-IS on this system."
         INDEX { isisSysInstance,
                 isisCircIndex }
     ::= { isisCircTable 1 }

     IsisCircEntry ::=
         SEQUENCE {
             isisCircIndex
                 Integer32,
             isisCircIfIndex
                 Integer32,
             isisCircIfSubIndex
                 Integer32,
             isisCircLocalID
                 Integer32,
             isisCircAdminState
                 AdminState,
             isisCircExistState
                 RowStatus,
             isisCircType
                 INTEGER,
             isisCircExtDomain
                 TruthValue,
             isisCircAdjChanges
                 Counter32,
             isisCircInitFails
                 Counter32,
             isisCircRejAdjs
                 Counter32,
             isisCircOutCtrlPDUs
                 Counter32,
             isisCircInCtrlPDUs
                 Counter32,
             isisCircIDFieldLenMismatches
                 Counter32,
             isisCircLevel
                 INTEGER,
             isisCircMCAddr
                 INTEGER,
             isisCircPtToPtCircID
                 CircuitID,
             isisCircPassiveCircuit
                 TruthValue,
             isisCircMeshGroupEnabled
                 INTEGER,
             isisCircMeshGroup
                 Integer32,
             isisCircSmallHellos
                 AdminState,
             isisCircUpTime
                 UpTime
         }

     isisCircIndex OBJECT-TYPE
         SYNTAX Integer32 (1..2000000000)
         MAX-ACCESS not-accessible
         STATUS current
         DESCRIPTION
             "The identifier of this circuit, unique within the
              instance of the IS-IS protocol. This object follows
              the index behavior.  This is for SNMP Indexing
              purposes only and need not have any relation to
              any protocol value."
     ::= { isisCircEntry 1 }

     isisCircIfIndex OBJECT-TYPE
         SYNTAX Integer32
         MAX-ACCESS read-create
         STATUS current
         DESCRIPTION
             "The value of ifIndex for the interface to which this
             circuit corresponds.   This object cannot be modified
             after creation"
     ::= { isisCircEntry 2 }

     isisCircIfSubIndex OBJECT-TYPE
         SYNTAX Integer32
         MAX-ACCESS read-create
         STATUS current
         DESCRIPTION
             "A specifier for the part of the interface ifIndex to which
             this circuit corresponds, such as a DLCI or VPI/VCI.
             This object cannot be modified after creation"
     ::=    { isisCircEntry 3 }

     isisCircLocalID OBJECT-TYPE
         SYNTAX Integer32(0..255)
         MAX-ACCESS read-create
         STATUS current
         DESCRIPTION
             "An identification that can be used in protocol packets
             to identify a circuit.  Values of isisCircLocalID do
             not need to be unique.  They are only required to differ
             on LANs where the Intermediate System is the Designated
             Intermediate System."
     ::=    { isisCircEntry 4 }

     isisCircAdminState OBJECT-TYPE
         SYNTAX AdminState
         MAX-ACCESS read-create
         STATUS current
         DESCRIPTION
             "The administrative state of the circuit. This
              object follows the AdminState behavior."
         DEFVAL { off }
     ::= { isisCircEntry 5 }

     isisCircExistState OBJECT-TYPE
         SYNTAX RowStatus
         MAX-ACCESS read-create
         STATUS current
         DESCRIPTION
             "The existence state of this circuit. This object follows
              the Row Status behavior.  Setting the state to 'notInService'
              halts the generation and processing of IS-IS protocol PDUs
              on this circuit.  Setting the state to destroy will also
              erase any configuration associated with the circuit."
         DEFVAL { active }
     ::= { isisCircEntry 6 }

     isisCircType OBJECT-TYPE
         SYNTAX INTEGER {
             broadcast(1),
             ptToPt(2),
             staticIn(3),
             staticOut(4),
             dA(5)
             }
         MAX-ACCESS read-create
         STATUS current
         DESCRIPTION
             "The type of the circuit. This object follows the
             replaceOnlyWhileDisabled behavior. The type specified
             must be compatible with the type of the interface defined
             by the value of isisCircIfIndex."
         REFERENCE "{ISIS.aoi type (33)}"
     ::= { isisCircEntry 7 }

     isisCircExtDomain OBJECT-TYPE
         SYNTAX TruthValue
         MAX-ACCESS read-create
         STATUS current
         DESCRIPTION
             "If true, suppress normal transmission of and
             interpretation of Intra-domain ISIS PDUs on this
             circuit."
         REFERENCE "{ISIS.aoi externalDomain (46)}"
         DEFVAL { false }
     ::= { isisCircEntry 8 }

     isisCircAdjChanges OBJECT-TYPE
         SYNTAX Counter32
         MAX-ACCESS read-only
         STATUS current
         DESCRIPTION
             "The number of times an adjacency state change has
             occurred on this circuit."
         REFERENCE "{ISIS.aoi changesInAdjacencyState (40)}"
     ::= { isisCircEntry 9 }

     isisCircInitFails OBJECT-TYPE
         SYNTAX Counter32
         MAX-ACCESS read-only
         STATUS current
         DESCRIPTION
             "The number of times initialization of this circuit has
             failed."
         REFERENCE "{ISIS.aoi initializationFailures (41)}"
     ::= { isisCircEntry 10 }

     isisCircRejAdjs OBJECT-TYPE
         SYNTAX Counter32
         MAX-ACCESS read-only
         STATUS current
         DESCRIPTION
             "The number of times an adjacency has been rejected on
             this circuit."
         REFERENCE "{ISIS.aoi rejectedAdjacencies (42)}"
     ::= { isisCircEntry 11 }

     isisCircOutCtrlPDUs OBJECT-TYPE
         SYNTAX Counter32
         UNITS "frames"
         MAX-ACCESS read-only
         STATUS current
         DESCRIPTION
             "The number of IS-IS control PDUs sent on this circuit."
         REFERENCE "{ISIS.aoi iSISControlPDUsSent (43)}"
     ::= { isisCircEntry 12 }

     isisCircInCtrlPDUs OBJECT-TYPE
         SYNTAX Counter32
         UNITS "frames"
         MAX-ACCESS read-only
         STATUS current
         DESCRIPTION
             "The number of IS-IS control PDUs received on this
             circuit."
         REFERENCE "{ISIS.aoi controlPDUsReceived (44)}"
     ::= { isisCircEntry 13 }

     isisCircIDFieldLenMismatches OBJECT-TYPE
         SYNTAX Counter32
         UNITS "frames"
         MAX-ACCESS read-only
         STATUS current
         DESCRIPTION
             "The number of times an IS-IS control PDU with an ID
             field length different to that for this system has been
             received."
         REFERENCE "{ISIS.aoi iDFieldLengthMismatches (25)}"
     ::= { isisCircEntry 14 }

     isisCircLevel OBJECT-TYPE
         SYNTAX INTEGER
           {
             level1(1),
             level2(2),
             level1L2(3)
           }
         MAX-ACCESS read-create
         STATUS current
         DESCRIPTION
             "Indicates which type of packets will be sent and
              accepted on this circuit. The values used will be
              modified by the settings of isisSysType. This
              object follows the replaceOnlyWhileDisabled behavior."
         DEFVAL { level1L2 }
     ::= { isisCircEntry 15 }

     isisCircMCAddr OBJECT-TYPE
         SYNTAX INTEGER{
             group (1),
             functional (2)
             }
         MAX-ACCESS read-create
         STATUS current
         DESCRIPTION
             "Specifies which type of multicast address will
              be used for sending HELLO PDUs on this
              circuit.  This may be used in Token Ring networks.
              See section 8.4.8 of ISO 10589."
         DEFVAL { group }
     ::= { isisCircEntry 16 }

     isisCircPtToPtCircID OBJECT-TYPE
         SYNTAX CircuitID
         MAX-ACCESS read-only
         STATUS current
         DESCRIPTION
             "The ID of the circuit allocated during initialization.
             If no value has been negotiated (either because the
             adjacency is to an End System, or because initialization
             has not yet successfully completed), this object has the
             value which would be proposed for this circuit (i.e. the
             concatenation of the local system ID and the one octet
             local Circuit ID for this circuit."
         REFERENCE "{ISIS.aoi ptPtCircuitID (51)}"
     ::= { isisCircEntry 17 }

     isisCircPassiveCircuit OBJECT-TYPE
         SYNTAX TruthValue
         MAX-ACCESS read-create
         STATUS current
         DESCRIPTION
             "Should we include this interface in LSPs, even if
             it is not running the ISIS Protocol?"
         REFERENCE "{}"
         DEFVAL { false }
     ::= { isisCircEntry 18 }

     isisCircMeshGroupEnabled OBJECT-TYPE
         SYNTAX INTEGER {
                 inactive(1),
                 blocked(2),
                 set(3)
         }
         MAX-ACCESS read-create
         STATUS current
         DESCRIPTION
             "Is this port a member of a mesh group, or blocked?
             Circuits in the same mesh group act as a virtual
             multiaccess network.  LSPs seen on one circuit in
             a mesh group will not be flooded to another circuit
             in the same mesh group."
         REFERENCE "{}"
         DEFVAL { inactive }
     ::= { isisCircEntry 19 }

     isisCircMeshGroup OBJECT-TYPE
         SYNTAX Integer32 (1..2000000000)
         MAX-ACCESS read-create
         STATUS current
         DESCRIPTION
             "Circuits in the same mesh group act as a virtual
             multiaccess network.  LSPs seen on one circuit in
             a mesh group will not be flooded to another circuit
             in the same mesh group.  If isisCircMeshGroupEnabled
             is inactive, this value is ignored."
         REFERENCE "{}"
         DEFVAL { 1 }
     ::= { isisCircEntry 20 }

     isisCircSmallHellos OBJECT-TYPE
         SYNTAX AdminState
         MAX-ACCESS read-create
         STATUS current
         DESCRIPTION
             "Can we send unpadded hellos on LAN circuits?  Off means
              LAN Hellos must be padded.
              Implementations should allow the administrator to read
              this value.  An implementation need not be able to
              support unpadded hellos to be conformant."
          DEFVAL { off }
     ::= { isisCircEntry 21 }

     isisCircUpTime OBJECT-TYPE
         SYNTAX UpTime
         UNITS "seconds"
         MAX-ACCESS read-only
         STATUS current
         DESCRIPTION
             "If the circuit is up, the amount of time in seconds
             since this circuit entered state 'up'.  If the circuit
             is not up, the number of seconds since the circuit was
             up, or since the system started, if the circuit has
             never been up.

             Note: This can be implemented as start time less
             the current time."
     ::= { isisCircEntry 22 }

-- The Circuit Level Table
-- This table captures level-specific information about a circuit

     isisCircLevelTable OBJECT-TYPE
         SYNTAX SEQUENCE OF IsisCircLevelEntry
         MAX-ACCESS not-accessible
         STATUS current
         DESCRIPTION
             "Level specific information about circuits used by IS-IS"
     ::= { isisCircLevelValues 1 }

     isisCircLevelEntry OBJECT-TYPE
         SYNTAX IsisCircLevelEntry
         MAX-ACCESS not-accessible
         STATUS current
         DESCRIPTION
             "An isisCircLevelEntry exists for each level on
              each circuit used by Integrated IS-IS on this system."
         INDEX { isisSysInstance,
                 isisCircIndex,
                 isisCircLevelIndex }
     ::= { isisCircLevelTable 1 }
     IsisCircLevelEntry ::=
         SEQUENCE {
             isisCircLevelIndex
                 INTEGER,
             isisCircLevelMetric
                 DefaultMetric,
             isisCircLevelISPriority
                 ISPriority,
             -- isisCircLevelCircID    Removed: duplicates isisCircPtToPtCircID
             --    CircuitID,
             isisCircLevelDesIS
                 OCTET STRING,
             isisCircLevelLANDesISChanges
                 Counter32,
             isisCircLevelHelloMultiplier
                 Integer32,
             isisCircLevelHelloTimer
                 Integer32,
             isisCircLevelDRHelloTimer
                 Integer32,
             isisCircLevelLSPThrottle
                 Integer32,
             isisCircLevelMinLSPRetransInt
                 Integer32,
             isisCircLevelCSNPInterval
                 Integer32,
             isisCircLevelPartSNPInterval
                 Integer32
         }

     isisCircLevelIndex OBJECT-TYPE
         SYNTAX INTEGER {
             level1IS (1),
             level2IS (2)
             }
         MAX-ACCESS not-accessible
         STATUS current
         DESCRIPTION
             "The level that this entry describes."
     ::= { isisCircLevelEntry 1 }

     isisCircLevelMetric OBJECT-TYPE
         SYNTAX DefaultMetric
         MAX-ACCESS read-create
         STATUS current
         DESCRIPTION
             "The metric value of this circuit for this level."
         REFERENCE "{ISIS.aoi l1DefaultMetric (35)}"
         DEFVAL { 10 }
     ::= { isisCircLevelEntry 2 }

     isisCircLevelISPriority OBJECT-TYPE
         SYNTAX ISPriority
         MAX-ACCESS read-create
         STATUS current
         DESCRIPTION
             "The priority for becoming LAN Designated
             Intermediate System at this level."
         REFERENCE "{ISIS.aoi l2IntermediateSystemPriority (73)}"
         DEFVAL { 64 }
     ::= { isisCircLevelEntry 3 }

--   isisCircLevelCircID OBJECT-TYPE
--       SYNTAX CircuitID
--       MAX-ACCESS read-only
--       STATUS current
--       DESCRIPTION
--           "The ID of the circuit allocated during initialization.
--           If no value has been negotiated (either because the
--           adjacency is to an End System, or because initialization
--           has not yet successfully completed), this object has the
--           value which would be proposed for this circuit (i.e. the
--           concatenation of the local system ID and the one octet
--           local Circuit ID for this circuit."
--       REFERENCE "{ISIS.aoi ptPtCircuitID (51)}"
--   ::= { isisCircLevelEntry 4 }

     isisCircLevelDesIS OBJECT-TYPE
         SYNTAX OCTET STRING (SIZE(0..7))
         MAX-ACCESS read-only
         STATUS current
         DESCRIPTION
             "The ID of the LAN Designated Intermediate System
             on this circuit at this level. If, for any reason,
             this system is not partaking in the relevant
             Designated Intermediate System election process,
             then the value returned is the zero length OCTET STRING."
         REFERENCE "{ISIS.aoi l2DesignatedIntermediateSystem (75)}"
     ::= { isisCircLevelEntry 4 }

     isisCircLevelLANDesISChanges OBJECT-TYPE
         SYNTAX Counter32
         MAX-ACCESS read-only
         STATUS current
         DESCRIPTION
             "The number of times the LAN Designated
             Intermediate System has changed at this level."
         REFERENCE "{ISIS.aoi
             lanL2DesignatedIntermediateSystemChanges (76)}"
     ::= { isisCircLevelEntry 5 }

     isisCircLevelHelloMultiplier OBJECT-TYPE
         SYNTAX Integer32 (2..100)
         MAX-ACCESS read-create
         STATUS current
         DESCRIPTION
             "This value is multiplied by the corresponding HelloTimer
             and the result in seconds (rounded up) is used as the
             holding time in transmitted hellos, to be used by receivers
             of hello packets from this IS"
         REFERENCE "{ISIS.aoi iSISHelloTimer (45)}"
         DEFVAL { 10 }
     ::= { isisCircLevelEntry 6 }

     isisCircLevelHelloTimer OBJECT-TYPE
         SYNTAX Integer32 (10..600000)
         UNITS "milliseconds"
         MAX-ACCESS read-create
         STATUS current
         DESCRIPTION
             "Maximum period, in milliseconds, between IIH PDUs
              on multiaccess networks at this level for LANs.
              The value at level 1 is used as the period between
              Hellos on point to point circuits.  Setting this
              value at level 2 on a point to point circuit will
              result in an error of InconsistentValue.

              This object follows the resettingTimer behavior."
         REFERENCE "{ISIS.aoi iSISHelloTimer (45)}"
         DEFVAL { 3000 }
     ::= { isisCircLevelEntry 7 }

     isisCircLevelDRHelloTimer OBJECT-TYPE
         SYNTAX Integer32 (10..120000)
         UNITS "milliseconds"
         MAX-ACCESS read-create
         STATUS current
         DESCRIPTION
             "Period, in milliseconds, between Hello PDUs on
             multiaccess networks when this IS is the Designated
             Intermediate System.  This object follows the
             resettingTimer behavior."
         REFERENCE "{ISIS.aoi iSISHelloTimer (45)}"
         DEFVAL { 1000 }
     ::= { isisCircLevelEntry 8 }

     isisCircLevelLSPThrottle OBJECT-TYPE
         SYNTAX Integer32 (1..65535)
         UNITS "milliseconds"
         MAX-ACCESS read-create
         STATUS current
         DESCRIPTION
             "Minimal interval of time, in milliseconds, between
             transmissions of LSPs on an interface at this level."
         REFERENCE "{ISIS.aoi minimumBroadcastLSPTransmissionInterval (5)}"
         DEFVAL { 10 }
     ::= { isisCircLevelEntry 9 }

     isisCircLevelMinLSPRetransInt OBJECT-TYPE
         SYNTAX Integer32 (1..300)
         UNITS "seconds"
         MAX-ACCESS read-create
         STATUS current
         DESCRIPTION
             "Minimum interval, in seconds, between re-transmission of
             an LSP at this level. This object follows the resettingTimer
             behavior.

             Note that isisCircLevelLSPThrottle controls
             how fast we send back to back LSPs.  This variable
             controls how fast we re-send the same LSP."
         REFERENCE "{ISIS.aoi minimumLSPTransmissionInterval (5)}"
         DEFVAL { 5 }
     ::= { isisCircLevelEntry 10 }

     isisCircLevelCSNPInterval OBJECT-TYPE
         SYNTAX Integer32 (1..600)
         UNITS "seconds"
         MAX-ACCESS read-create
         STATUS current
         DESCRIPTION
             "Interval of time, in seconds, between transmission
             of CSNPs on multiaccess networks if this router is
             the designated router at this level."
         REFERENCE "{}"
         DEFVAL { 10 }
     ::= { isisCircLevelEntry 11 }

     isisCircLevelPartSNPInterval OBJECT-TYPE
         SYNTAX Integer32 (1..120)
         UNITS "seconds"
         MAX-ACCESS read-create
         STATUS current
         DESCRIPTION
             "Minimum interval in seconds between sending Partial Sequence
              Number PDUs at this level. This object follows the
              resettingTimer behavior."
         REFERENCE "{ISIS.aoi partialSNPInterval (14)}"
         DEFVAL { 2 }
     ::= { isisCircLevelEntry 12 }

-- isisPacketCountTable keeps track of the number of IS-IS
-- control packets sent and received at each level

     isisPacketCountTable OBJECT-TYPE
         SYNTAX SEQUENCE OF IsisPacketCountEntry
         MAX-ACCESS not-accessible
         STATUS current
         DESCRIPTION
             "Information about IS-IS packets sent and received"
     ::= { isisCircPDUCounters 1 }

     isisPacketCountEntry OBJECT-TYPE
         SYNTAX IsisPacketCountEntry
         MAX-ACCESS not-accessible
         STATUS current
         DESCRIPTION
             "Information about IS-IS protocol traffic at one level
              on one circuit in one direction"
         INDEX { isisSysInstance,
                 isisCircIndex,
                 isisPacketCountLevel,
                 isisPacketCountDirection }
     ::= { isisPacketCountTable 1 }

     IsisPacketCountEntry ::=
         SEQUENCE {
             isisPacketCountLevel
                 INTEGER,
             isisPacketCountDirection
                 INTEGER,
             isisPacketCountHello
                 Counter32,
             isisPacketCountLSP
                 Counter32,
             isisPacketCountCSNP
                 Counter32,
             isisPacketCountPSNP
                 Counter32
       }
     isisPacketCountLevel OBJECT-TYPE
         SYNTAX INTEGER
           {
             level1(1),
             level2(2)
           }
         MAX-ACCESS not-accessible
         STATUS current
         DESCRIPTION
             "The level at which these PDU counts have been collected."
     ::= { isisPacketCountEntry 1 }

     isisPacketCountDirection OBJECT-TYPE
         SYNTAX INTEGER
           {
             sending(1),
             receiving(2)
           }
         MAX-ACCESS not-accessible
         STATUS current
         DESCRIPTION
             "Were we sending or receiving these PDUs?"
     ::= { isisPacketCountEntry 2 }


     isisPacketCountHello OBJECT-TYPE
         SYNTAX Counter32
         UNITS "frames"
         MAX-ACCESS read-only
         STATUS current
         DESCRIPTION
             "The number of IS-IS Hello PDUs seen in this
              direction at this level."
         REFERENCE "{ISIS.aoi iSISControlPDUsSent (43)}"
     ::= { isisPacketCountEntry 3 }

     isisPacketCountLSP OBJECT-TYPE
         SYNTAX Counter32
         UNITS "frames"
         MAX-ACCESS read-only
         STATUS current
         DESCRIPTION
             "The number of IS-IS LSPs seen in this
              direction at this level."
         REFERENCE "{ISIS.aoi iSISControlPDUsSent (43)}"
     ::= { isisPacketCountEntry 4 }

     isisPacketCountCSNP OBJECT-TYPE
         SYNTAX Counter32
         UNITS "frames"
         MAX-ACCESS read-only
         STATUS current
         DESCRIPTION
             "The number of IS-IS CSNPs seen in this
              direction at this level."
         REFERENCE "{ISIS.aoi iSISControlPDUsSent (43)}"
     ::= { isisPacketCountEntry 5 }

     isisPacketCountPSNP OBJECT-TYPE
         SYNTAX Counter32
         UNITS "frames"
         MAX-ACCESS read-only
         STATUS current
         DESCRIPTION
             "The number of IS-IS PSNPs seen in this
              direction at this level."
         REFERENCE "{ISIS.aoi iSISControlPDUsSent (43)}"
     ::= { isisPacketCountEntry 6 }

-- The Circuit IS Group
--
-- The Circuit IS Group is present if the system supports the
-- IS functions of the ISO 9542 protocol.
-- The Circuit IS Table
--
-- This table is not implemented - jdp



-- The IS Adjacency Group
--
-- The IS Adjacency Group is current and contains information
-- about adjacencies to routers maintained by the Integrated
-- IS-IS protocol
--
-- The IS Adjacency Table
--
-- Each adjacency to an IS corresponds to one entry in this
-- table.

     isisISAdjTable OBJECT-TYPE
         SYNTAX SEQUENCE OF IsisISAdjEntry
         MAX-ACCESS not-accessible
         STATUS current
         DESCRIPTION
             "The table of adjacencies to Intermediate Systems."
     ::= { isisISAdj 1 }

     isisISAdjEntry OBJECT-TYPE
         SYNTAX IsisISAdjEntry
         MAX-ACCESS not-accessible
         STATUS current
         DESCRIPTION
             "Each entry corresponds to one adjacency to an
             Intermediate System on this system."
         INDEX { isisSysInstance,
                 isisCircIndex,
                 isisISAdjIndex }
     ::= { isisISAdjTable 1 }

     IsisISAdjEntry ::=
         SEQUENCE {
             isisISAdjIndex
                 Integer32,
             isisISAdjState
                 INTEGER,
             isisISAdjNeighSNPAAddress
                 OSINSAddress,
             isisISAdjNeighSysType
                 INTEGER,
             isisISAdjNeighSysID
                 OCTET STRING,
             isisISAdjUsage
                 INTEGER,
             isisISAdjHoldTimer
                 Integer32,
             isisISAdjNeighPriority
                 ISPriority,
             isisISAdjUpTime
                 UpTime
       }

     isisISAdjIndex OBJECT-TYPE
         SYNTAX Integer32 (1..2000000000)
         MAX-ACCESS not-accessible
         STATUS current
         DESCRIPTION
             "A unique value identifying the IS adjacency from all
             other such adjacencies on this circuit. This value is
             assigned by the system when the adjacency is created
             automatically."
     ::= { isisISAdjEntry 1 }

     isisISAdjState OBJECT-TYPE
         SYNTAX INTEGER {
             up (0),
             initializing (1),
             down (2),
             failed (3)
             }
         MAX-ACCESS read-only
         STATUS current
         DESCRIPTION
             "The state of the adjacency"
         REFERENCE "{ISIS.aoi adjacencyState (78)}"
     ::= { isisISAdjEntry 2 }

     isisISAdjNeighSNPAAddress OBJECT-TYPE
         SYNTAX OSINSAddress
         MAX-ACCESS read-only
         STATUS current
         DESCRIPTION
             "The SNPA address of the neighboring system."
         REFERENCE "{ISIS.aoi neighbourSNPAAddress (79)}"
     ::= { isisISAdjEntry 3 }

     isisISAdjNeighSysType OBJECT-TYPE
         SYNTAX INTEGER {
             l1IntermediateSystem(1),
             l2IntermediateSystem(2),
             l1L2IntermediateSystem(3),
             unknown(4)
             }
         MAX-ACCESS read-only
         STATUS current
         DESCRIPTION
             "The type of the neighboring system."
         REFERENCE "{ISIS.aoi neighbourSystemType (80)}"
     ::= { isisISAdjEntry 4 }

     isisISAdjNeighSysID OBJECT-TYPE
         SYNTAX OCTET STRING (SIZE(0..12))
         MAX-ACCESS read-only
         STATUS current
         DESCRIPTION
             "The system ID and 4 byte circuit ID of the
             neighboring Intermediate System set from
             the source ID field of the Three-Way-Handshake
             information from the neighbor's IIH PDUs."
         REFERENCE "{ISIS.aoi neighbourSystemIds (83)}"
     ::= { isisISAdjEntry 5 }

     isisISAdjUsage OBJECT-TYPE
         SYNTAX INTEGER {
             level1(1),
             level2(2),
             level1and2(3)
             }
         MAX-ACCESS read-only
         STATUS current
         DESCRIPTION
             "An adjacency of type level1 is used for level 1
              traffic only. An adjacency of type level2 is used
              for level 2 traffic only. An adjacency of type level1and2
              is used for both level 1 and level 2 traffic. There
              may be two adjacencies (of types level1 and level2)
              between the same pair of Intermediate Systems."
         REFERENCE "{ISIS.aoi adjacencyUsage (82)}"
     ::= { isisISAdjEntry 6 }

     isisISAdjHoldTimer OBJECT-TYPE
         SYNTAX Integer32 (1..65535)
         UNITS "seconds"
         MAX-ACCESS read-only
         STATUS current
         DESCRIPTION
             "The holding time in seconds for this adjacency.
              This value is based on received IIH PDUs and
              the elapsed time since receipt."
         REFERENCE "{ISIS.aoi holdingTimer (85)}"
     ::= { isisISAdjEntry 7 }

     isisISAdjNeighPriority OBJECT-TYPE
         SYNTAX ISPriority
         MAX-ACCESS read-only
         STATUS current
         DESCRIPTION
             "Priority of the neighboring Intermediate System for
             becoming the Designated Intermediate System."
         REFERENCE "{ISIS.aoi lANPriority (86)}"
     ::= { isisISAdjEntry 8 }

     isisISAdjUpTime OBJECT-TYPE
         SYNTAX UpTime
         UNITS "seconds"
         MAX-ACCESS read-only
         STATUS current
         DESCRIPTION
             "If the adjacency is up, the amount of time in seconds
             since this adjacency entered state 'up'.  If the adjacency
             is not up, the number of seconds since the adjacency was
             up, or since the system started, if the adjacency has
             never been up.

             Note: This can be implemented as start time less
             the current time."
     ::= { isisISAdjEntry 9 }

-- The IS Adjacency Area Address Table

-- The IS Adjacency Area Address Table contains the set of
-- Area Addresses of neighboring
-- Intermediate Systems as reported in IIH PDUs.

     isisISAdjAreaAddrTable OBJECT-TYPE
         SYNTAX SEQUENCE OF IsisISAdjAreaAddrEntry
         MAX-ACCESS not-accessible
         STATUS current
         DESCRIPTION
             "This table contains the set of Area Addresses of
             neighboring Intermediate Systems as reported in received
             IIH PDUs."
         REFERENCE "{ISIS.aoi areaAddressesOfNeighbour (84)}"
     ::= { isisISAdj 2 }

     isisISAdjAreaAddrEntry OBJECT-TYPE
         SYNTAX IsisISAdjAreaAddrEntry
         MAX-ACCESS not-accessible
         STATUS current
         DESCRIPTION
             "Each entry contains one Area Address reported by a
             neighboring Intermediate System in its IIH PDUs."
         INDEX { isisSysInstance,
                 isisCircIndex,
                 isisISAdjIndex,
                 isisISAdjAreaAddrIndex,
                 isisISAdjAreaAddress }
     ::= { isisISAdjAreaAddrTable 1 }

     IsisISAdjAreaAddrEntry ::=
         SEQUENCE {
             isisISAdjAreaAddrIndex
                 Integer32,
             isisISAdjAreaAddress
                 OSINSAddress
             }

    isisISAdjAreaAddrIndex OBJECT-TYPE
         SYNTAX Integer32 (1..2000000000)
         MAX-ACCESS not-accessible
         STATUS current
         DESCRIPTION
             "An index for the areas associated with one neighbor.
              This provides a simpler way to walk the table."
     ::= { isisISAdjAreaAddrEntry 1 }

     isisISAdjAreaAddress OBJECT-TYPE
         SYNTAX OSINSAddress
         MAX-ACCESS read-only
         STATUS current
         DESCRIPTION
             "One Area Address as reported in IIH PDUs received from
             the neighbor."
     ::= { isisISAdjAreaAddrEntry 2 }

-- The IS Adjacency IP Group

-- The IS Adjacency IP Group is present if the system supports
-- IP Integrated IS-IS

-- The IS Adjacency IP Address Table

-- The IS Adjacency IP Address Table contains the
-- set of IP Addresses of neighboring Intermediate Systems
-- as reported in received IIH PDUs.

     isisISAdjIPAddrTable OBJECT-TYPE
         SYNTAX SEQUENCE OF IsisISAdjIPAddrEntry
         MAX-ACCESS not-accessible
         STATUS current
         DESCRIPTION
             "This table contains the set of IP Addresses of
             neighboring Intermediate Systems as reported in received
             IIH PDUs."
     ::= { isisISAdj 3 }

     isisISAdjIPAddrEntry OBJECT-TYPE
         SYNTAX IsisISAdjIPAddrEntry
         MAX-ACCESS not-accessible
         STATUS current
         DESCRIPTION
             "Each entry contains one IP Address reported by a
             neighboring Intermediate System in its IIH PDUs."
         INDEX { isisSysInstance,
                 isisCircIndex,
                 isisISAdjIndex,
                 isisISAdjIPAddrIndex
                 }
     ::= { isisISAdjIPAddrTable 1 }

     IsisISAdjIPAddrEntry ::=
         SEQUENCE {
             isisISAdjIPAddrIndex
                 Integer32,
             isisISAdjIPAddressType
                  InetAddressType,
             isisISAdjIPAddress
                 InetAddress
         }

     isisISAdjIPAddrIndex OBJECT-TYPE
         SYNTAX Integer32 (1..2000000000)
         MAX-ACCESS not-accessible
         STATUS current
         DESCRIPTION
             "An index to this table which identifies the IP addresss
              to which this entry belongs."
     ::= { isisISAdjIPAddrEntry 1 }

     isisISAdjIPAddressType OBJECT-TYPE
         SYNTAX InetAddressType
         MAX-ACCESS read-only
         STATUS current
         DESCRIPTION
             "The type of one IP Address as reported in IIH PDUs
              received from the neighbor."
     ::= { isisISAdjIPAddrEntry 2 }

     isisISAdjIPAddress OBJECT-TYPE
         SYNTAX  InetAddress (SIZE(4|16))
         MAX-ACCESS read-only
         STATUS current
         DESCRIPTION
             "One IP Address as reported in IIH PDUs received from the
             neighbor."
     ::= { isisISAdjIPAddrEntry 3 }

-- The IS Adjacency Integrated Group
--
-- The IS Adjacency Integrated Group is present if the system
-- supports Integrated ISIS.
--
--
-- The IS Adjacency Protocol Supported Table
--
-- The IS Adjacency Protocol Supported Table contains the set of
-- protocols supported by neighboring
-- Intermediate Systems as reported in received IIH PDUs.
--
     isisISAdjProtSuppTable OBJECT-TYPE
         SYNTAX SEQUENCE OF IsisISAdjProtSuppEntry
         MAX-ACCESS not-accessible
         STATUS current
         DESCRIPTION
             "This table contains the set of protocols supported by
             neighboring Intermediate Systems as reported in received
             IIH PDUs."
     ::= { isisISAdj 4 }

     isisISAdjProtSuppEntry OBJECT-TYPE
         SYNTAX IsisISAdjProtSuppEntry
         MAX-ACCESS not-accessible
         STATUS current
         DESCRIPTION
             "Each entry contains one protocol supported by a
             neighboring Intermediate System as reported in its IIH
             PDUs."
         INDEX {  isisSysInstance,
             isisCircIndex,
             isisISAdjProtSuppIndex,
             isisISAdjProtSuppProtocol }
     ::= { isisISAdjProtSuppTable 1 }

     IsisISAdjProtSuppEntry ::=
         SEQUENCE {
             isisISAdjProtSuppIndex
                 Integer32,
             isisISAdjProtSuppProtocol
                 SupportedProtocol
         }

     isisISAdjProtSuppIndex OBJECT-TYPE
         SYNTAX Integer32 (1..2000000000)
         MAX-ACCESS not-accessible
         STATUS current
         DESCRIPTION
             "The identifier the IS adjacency to which this entry
             corresponds."
     ::= { isisISAdjProtSuppEntry 1 }

     isisISAdjProtSuppProtocol OBJECT-TYPE
         SYNTAX SupportedProtocol
         MAX-ACCESS read-only
         STATUS current
         DESCRIPTION
             "One supported protocol as reported in IIH PDUs received
             from the neighbor."
     ::= { isisISAdjProtSuppEntry 2 }
--
--
-- The ES Adjacency Group
--
-- The ES Adjacency Group is present if the system supports
-- reception of ES Hellos
-- The ES Adjacency Table
--
-- This table is not implemented - jdp
--
--
-- The Reachable Address Group
--
-- The Reachable Address Group is optional.
-- The Reachable Address Table
-- Each entry records information about a reachable address
-- (NSAP or address prefix) manually configured on the system
-- or learned through another protocol.

-- The IP Reachable Address Group

-- The IP Reachable Address Group is optional.


-- The IP Reachable Address Table

-- Each entry records information about one IP reachable
-- address manually configured on this system or learned from
-- another protocol.

     isisIPRATable OBJECT-TYPE
         SYNTAX SEQUENCE OF IsisIPRAEntry
         MAX-ACCESS not-accessible
         STATUS current
         DESCRIPTION
             "The table of IP Reachable Addresses to networks,
             subnetworks or hosts either manually configured or
             learned from another protocol."
     ::= { isisIPReachAddr 1 }

     isisIPRAEntry OBJECT-TYPE
         SYNTAX IsisIPRAEntry
         MAX-ACCESS not-accessible
         STATUS current
         DESCRIPTION
             "Each entry defines an IP Reachable Address to a network,
             subnetwork or host."
         INDEX {  isisSysInstance,
             isisIPRAType,
             isisIPRAIndex }
     ::= { isisIPRATable 1 }

     IsisIPRAEntry ::=
         SEQUENCE {
             isisIPRAIndex
                 Integer32,
             isisIPRAType
                 INTEGER,
             isisIPRADestType
                 InetAddressType,
             isisIPRADest
                 InetAddress,
             isisIPRADestPrefixLen
                 InetAddressPrefixLength,
             isisIPRAExistState
                 RowStatus,
             isisIPRAAdminState
                 AdminState,
             isisIPRAMetric
                 DefaultMetric,
             isisIPRAMetricType
                 MetricType,
             isisIPRASNPAAddress
                 OSINSAddress
         }

     isisIPRAIndex OBJECT-TYPE
         SYNTAX Integer32 (1..2000000000)
         MAX-ACCESS not-accessible
         STATUS current
         DESCRIPTION
             "The identifier for this isisIPRAEntry. This value must
             be unique amongst all IP Reachable Addresses on the same
             parent Circuit. This object follows the index and
             manualOrAutomatic behaviors."
     ::= { isisIPRAEntry 1 }

     isisIPRAType OBJECT-TYPE
         SYNTAX   INTEGER
             {
                 manual (1),
                 automatic (2)
             }
         MAX-ACCESS not-accessible
         STATUS current
         DESCRIPTION
             "The type of this IP Reachable Address. Those of type
             manual are created by the network manager. Those of type
             automatic are created through propagation of routing
             information from another routing protocol."
     ::= { isisIPRAEntry 2 }

     isisIPRADestType OBJECT-TYPE
         SYNTAX InetAddressType
         MAX-ACCESS read-create
         STATUS current
         DESCRIPTION
             "The type of this IP Reachable Address."
     ::= { isisIPRAEntry 3 }

     isisIPRADest OBJECT-TYPE
         SYNTAX InetAddress (SIZE(4|16))
         MAX-ACCESS read-create
         STATUS current
         DESCRIPTION
             "The destination of this IP Reachable Address. This is
             either a network address, subnetwork address or host
             address. This object follows the manualOrAutomatic
             behavior."
     ::= { isisIPRAEntry 4 }

     isisIPRADestPrefixLen OBJECT-TYPE
         SYNTAX InetAddressPrefixLength (0..128)
         MAX-ACCESS read-create
         STATUS current
         DESCRIPTION
             "The length of the IP Netmask for Reachability Address."
     ::= { isisIPRAEntry 5 }

     isisIPRAExistState OBJECT-TYPE
         SYNTAX RowStatus
         MAX-ACCESS read-create
         STATUS current
         DESCRIPTION
             "The state of this IP Reachable Address. This object
             follows the ExistenceState and manualOrAutomatic
             behaviors."
         DEFVAL { active }
     ::= { isisIPRAEntry 6 }

     isisIPRAAdminState OBJECT-TYPE
         SYNTAX AdminState
         MAX-ACCESS read-create
         STATUS current
         DESCRIPTION
             "The administrative state of the IP Reachable Address. This
             object follows the AdminState and manualOrAutomatic
             behaviors."
         DEFVAL { off }
     ::= { isisIPRAEntry 7 }

     isisIPRAMetric OBJECT-TYPE
         SYNTAX DefaultMetric
         MAX-ACCESS read-create
         STATUS current
         DESCRIPTION
             "The metric value for reaching the specified
             destination over this circuit. This object follows the
             manualOrAutomatic behavior."
         DEFVAL { 20 }
     ::= { isisIPRAEntry 8 }

     isisIPRAMetricType OBJECT-TYPE
         SYNTAX MetricType
         MAX-ACCESS read-create
         STATUS current
         DESCRIPTION
             "Indicates whether the metric is internal or
             external. This object follows the manualOrAutomatic
             behavior."
         DEFVAL { internal }
     ::= { isisIPRAEntry 9 }

     isisIPRASNPAAddress OBJECT-TYPE
         SYNTAX OSINSAddress
         MAX-ACCESS read-create
         STATUS current
         DESCRIPTION
             "The SNPA Address to which a PDU may be forwarded in
             order to reach a destination which matches this IP
             Reachable Address. This object follows the
             manualOrAutomatic behavior."
         DEFVAL { ''H }
     ::= { isisIPRAEntry 10 }

-- The Circuit CLNS Group
--
-- The Circuit CLNS Table contains objects controlling the
-- operation of the IS functions of the CLNS protocol
--
-- This table is not implemented - jdp
--

-- The IP Destination Group

-- The IP Destination Group is present if the system forwards
-- IP packets.


-- The IP Destination Table

-- The IP Destination Table records information about each
-- destination known to the Intermediate System

-- Removed: overlaps RFC 2096 - jdp


-- The ISIS Notification Table

-- The ISIS Notification Table records fields that are
-- required for notifications

    isisNotificationTable OBJECT-TYPE
         SYNTAX SEQUENCE OF IsisNotificationEntry
         MAX-ACCESS not-accessible
         STATUS current
         DESCRIPTION
                "Objects seen in the most recent notification
                 this instance of the IS-IS protocol."
    ::= { isisNotification 1 }

    isisNotificationEntry OBJECT-TYPE
         SYNTAX IsisNotificationEntry
         MAX-ACCESS not-accessible
         STATUS current
         DESCRIPTION
             "Each entry defines variables relevant to notifications
              for one instance of the IS-IS protocol."
         INDEX {  isisSysInstance }
     ::= { isisNotificationTable 1 }


-- Each entry records information about one IP reachable
-- address manually configured on this system or learned from
-- another protocol.

     IsisNotificationEntry ::=
        SEQUENCE {
             isisTrapLSPID
                LinkStatePDUID,
             isisSystemLevel
                ISLevel,
             isisPDUFragment
                IsisPDUHeader,
             isisFieldLen
                Integer32,
             isisMaxAreaAddress
                Integer32,
             isisProtocolVersion
                Integer32,
             isisLSPSize
                Integer32,
             isisOriginatingBufferSize
                Integer32,
             isisProtocolsSupported
                OCTET STRING
        }

     isisTrapLSPID OBJECT-TYPE
         SYNTAX LinkStatePDUID
         MAX-ACCESS read-only
         STATUS current
         DESCRIPTION
             "An Octet String that uniquely identifies
              a Link State PDU."
     ::= { isisNotificationEntry 1 }

     isisSystemLevel OBJECT-TYPE
         SYNTAX ISLevel
         MAX-ACCESS read-only
         STATUS current
         DESCRIPTION
             "Identifies the level the notification applies to."
     ::= { isisNotificationEntry 2 }

     isisPDUFragment OBJECT-TYPE
         SYNTAX IsisPDUHeader
         MAX-ACCESS read-only
         STATUS current
         DESCRIPTION
             "Holds up to the first 64 bytes of a PDU that
              triggered the notification."
     ::= { isisNotificationEntry 3 }

     isisFieldLen OBJECT-TYPE
         SYNTAX Integer32 (0..255)
         MAX-ACCESS read-only
         STATUS current
         DESCRIPTION
             "Holds the System ID length reported in PDU we recieved."
     ::= { isisNotificationEntry 4 }

     isisMaxAreaAddress OBJECT-TYPE
         SYNTAX Integer32 (0..255)
         MAX-ACCESS read-only
         STATUS current
         DESCRIPTION
             "Holds the Max Area Addresses reported in a PDU we recieved."
     ::= { isisNotificationEntry 5 }

     isisProtocolVersion OBJECT-TYPE
         SYNTAX Integer32 (0..255)
         MAX-ACCESS read-only
         STATUS current
         DESCRIPTION
             "Holds the Protocol version reported in PDU we received."
     ::= { isisNotificationEntry 6 }

     isisLSPSize OBJECT-TYPE
         SYNTAX Integer32 (1..2147483647)
         MAX-ACCESS read-only
         STATUS current
         DESCRIPTION
             "Holds the size of LSP we received that is too
              big to forward."
     ::= { isisNotificationEntry 7 }

     isisOriginatingBufferSize OBJECT-TYPE
         SYNTAX Integer32 (1..2147483647)
         MAX-ACCESS read-only
         STATUS current
         DESCRIPTION
             "Holds the size of isisSysOrigL1LSPBuffSize or
              isisSysOrigL2LSPBuffSize advertised by peer
              in TLV."
     ::= { isisNotificationEntry 8 }

     isisProtocolsSupported OBJECT-TYPE
         SYNTAX OCTET STRING (SIZE(0..255))
         MAX-ACCESS read-only
         STATUS current
         DESCRIPTION
             "The list of protocols supported by an
              adjacent system.  This may be empty."
     ::= { isisNotificationEntry 9 }

-- Type definitions

isisTrapPrefix        OBJECT IDENTIFIER ::= { isisNotifications 0 }

isisDatabaseOverload NOTIFICATION-TYPE
    OBJECTS {
        isisSystemLevel,
        isisSysL1State,
        isisSysL2State
    }
    STATUS  current
    DESCRIPTION
        "This notification is generated when the system
         enters or leaves the Overload state.  The number
         of times this has be generated and cleared is kept
         track of by isisSysLSPL1DbaseOloads and
         isisSysLSPL2DbaseOloads."

   ::= { isisTrapPrefix 1 }

isisManualAddressDrops NOTIFICATION-TYPE
    OBJECTS {
        isisManAreaAddrExistState
    }
    STATUS  current
    DESCRIPTION
        "This notification is generated when one of the
         manual areaAddresses assigned to this system is
         ignored when computing routes.  The object
         isisManAreaAddrExistState describes the area that
         has been dropped.

         The number of times this event has been generated
         is counted by isisSysManAddrDropFromAreas.

         This notification is edge triggered, and should not
         be regenerated until an address that was used in
         the previous computation has been dropped."

    ::= { isisTrapPrefix 2 }

isisCorruptedLSPDetected NOTIFICATION-TYPE
    OBJECTS {
        isisSystemLevel,
        isisTrapLSPID
    }
    STATUS  current
    DESCRIPTION
        "This notification is generated when we find that
         and LSP that was stored in memory has become
         corrupted.  The number of times this has been
         generated is counted by isisSysCorrLSPs.

         We forward an LSP ID.  We may have independent
         knowledge of the ID, but in some implementations
         there is a chance that the ID itself will be
         corrupted."

    ::= { isisTrapPrefix 3 }

isisAttemptToExceedMaxSequence NOTIFICATION-TYPE
    OBJECTS {
        isisSystemLevel,
        isisTrapLSPID
    }
    STATUS  current
    DESCRIPTION
        "When the sequence number on an LSP we generate
         wraps the 32 bit sequence counter, we purge and
         wait to re-announce this information.  This
         notification describes that event.  Since these
         should not be generated rapidly, we generate
         an event each time this happens.

         While the first 6 bytes of the LSPID are ours,
         the other two contain useful information."

    ::= { isisTrapPrefix 4 }

isisIDLenMismatch  NOTIFICATION-TYPE
    OBJECTS {
        isisFieldLen,
        isisCircIfIndex,
        isisPDUFragment
    }
    STATUS  current
    DESCRIPTION
        "A notification sent when we receive a PDU
         with a different value of the System ID Length.
         This notification includes the an index to identify
         the circuit where we saw the PDU and the header of
         the PDU which may help a network manager identify
         the source of the confusion.

         This should be an edge-triggered notification.
         We should not send a second notification about
         PDUs received from what seem to be the same source.
         This decision is up to the agent to make, and may
         be based on the circuit or on some MAC level
         information."

    ::= { isisTrapPrefix 5 }

isisMaxAreaAddressesMismatch NOTIFICATION-TYPE
    OBJECTS {
        isisMaxAreaAddress,
        isisCircIfIndex,
        isisPDUFragment
    }
    STATUS  current
    DESCRIPTION
        "A notification sent when we receive a PDU
         with a different value of the Maximum Area
         Addresses.  This notification includes the
         header of the packet, which may help a
         network manager identify the source of the
         confusion.

         This should be an edge-triggered notification.
         We should not send a second notification about
         PDUs received from what seem to be the same source."

    ::= { isisTrapPrefix 6 }

isisOwnLSPPurge NOTIFICATION-TYPE
    OBJECTS {
        isisCircIfIndex,
        isisTrapLSPID,
        isisSystemLevel
    }
    STATUS  current
    DESCRIPTION
        "A notification sent when we receive a PDU
         with our systemID and zero age.  This
         notification includes the circuit Index
         if available, which may help a network manager
         identify the source of the confusion."

    ::= { isisTrapPrefix 7 }

isisSequenceNumberSkip NOTIFICATION-TYPE
    OBJECTS {
        isisTrapLSPID,
        isisCircIfIndex,
        isisSystemLevel
    }
    STATUS  current
    DESCRIPTION
        "When we recieve an LSP with out System ID
         and different contents, we may need to reissue
         the LSP with a higher sequence number.

         We send this notification if we need to increase
         the sequence number by more than one.  If two
         Intermediate Systems are configured with the same
         System ID, this notification will fire."
    ::= { isisTrapPrefix 8 }

isisAuthenticationTypeFailure NOTIFICATION-TYPE
    OBJECTS {
        isisSystemLevel,
        isisPDUFragment,
        isisCircIfIndex
    }
    STATUS  current
    DESCRIPTION
        "A notification sent when we receive a PDU
         with the wrong  authentication type field.
         This notification includes the header of the
         packet, which may help a network manager
         identify the source of the confusion.

         This should be an edge-triggered notification.
         We should not send a second notification about
         PDUs received from what seem to be the same source."

    ::= { isisTrapPrefix 9 }

isisAuthenticationFailure NOTIFICATION-TYPE
    OBJECTS {
        isisSystemLevel,
        isisPDUFragment,
        isisCircIfIndex
    }
    STATUS  current
    DESCRIPTION
        "A notification sent when we receive a PDU
         with incorrent authentication information
         field.  This notification includes the header
         of the packet, which may help a network manager
         identify the source of the confusion.

         This should be an edge-triggered notification.
         We should not send a second notification about
         PDUs received from what seem to be the same source."

    ::= { isisTrapPrefix 10 }

isisVersionSkew NOTIFICATION-TYPE
    OBJECTS {
        isisProtocolVersion,
        isisSystemLevel,
        isisPDUFragment,
        isisCircIfIndex
    }
    STATUS  current
    DESCRIPTION
        "A notification sent when we receive a Hello
         PDU from an IS running a different version
         of the protocol. This notification includes
         the header of the packet, which may help a
         network manager identify the source of the
         confusion.

         This should be an edge-triggered notification.
         We should not send a second notification about
         PDUs received from what seem to be the same source.
         This decision is up to the agent to make, and may
         be based on the circuit or on some MAC level
         information."

    ::= { isisTrapPrefix 11 }

isisAreaMismatch NOTIFICATION-TYPE
    OBJECTS {
        isisLSPSize,
        isisSystemLevel,
        isisCircIfIndex,
        isisPDUFragment
    }
    STATUS  current
    DESCRIPTION
        "A notification sent when we receive a Hello
         PDU from an IS which does not share any
         area address. This notification includes
         the header of the packet, which may help a
         network manager identify the source of the
         confusion.

         This should be an edge-triggered notification.
         We should not send a second notification about
         PDUs received from what seem to be the same source.
         This decision is up to the agent to make, and may
         be based on the circuit or on some MAC level
         information."

    ::= { isisTrapPrefix 12 }

isisRejectedAdjacency NOTIFICATION-TYPE
    OBJECTS {
        isisSystemLevel,
        isisCircIfIndex
    }
    STATUS  current
    DESCRIPTION
        "A notification sent when we receive a Hello
         PDU from an IS, but do not establish an
         adjacency due to a lack of resources.

         This should be an edge-triggered notification.
         We should not send a second notification about
         PDUs received from the same source."

    ::= { isisTrapPrefix 13 }

isisLSPTooLargeToPropagate NOTIFICATION-TYPE
    OBJECTS {
        isisLSPSize,
        isisSystemLevel,
        isisTrapLSPID,
        isisCircIfIndex
    }
    STATUS  current
    DESCRIPTION
        "A notification sent when we attempt to propagate
         an LSP which is larger than the dataLinkBlockSize
         for a circuit.

         This should be an edge-triggered notification.
         We should not send a second notification about
         PDUs received from the same source."

    ::= { isisTrapPrefix 14 }

isisOriginatingLSPBufferSizeMismatch NOTIFICATION-TYPE
    OBJECTS {
        isisOriginatingBufferSize,
        isisSystemLevel,
        isisTrapLSPID,
        isisCircIfIndex
    }
    STATUS  current
    DESCRIPTION
        "A notification sent when a Level 1 LSP or Level
         2 LSP is received which is larger than the local
         value for originatingL1LSPBufferSize or
         originatingL2LSPBufferSize respectively, or when
         a Level 1 LSP or Level2 LSP is received containing
         the originatingLSPBufferSize option and the value in
         the PDU option field does not match the local value
         for originatingL1LSPBufferSize or originatingL2LSPBufferSize
         respectively.  We pass up the size from the option
         field or the size of the LSP that exceeds our
         configuration.

         This should be an edge-triggered notification.
         We should not send a second notification about
         PDUs received from the same source."

    ::= { isisTrapPrefix 15 }

isisProtocolsSupportedMismatch NOTIFICATION-TYPE
    OBJECTS {
        isisProtocolsSupported,
        isisSystemLevel,
        isisTrapLSPID,
        isisCircIfIndex
    }
    STATUS  current
    DESCRIPTION
        "A notification sent when a non-pseudonode
         segment 0 LSP is received that has no matching
         protocols supported.
         This may be because the system does not generate
         the field, or because there are no common elements.
         The list of protocols supported should be included
         in the notification: it may be empty if the TLV
         is not supported, or if the TLV is empty.

         This should be an edge-triggered notification.
         We should not send a second notification about
         PDUs received from the same source."

    ::= { isisTrapPrefix 16 }

-- Agent Conformance Definitions
-- We define the objects a conformant agent must define

isisGroups      OBJECT IDENTIFIER ::= { isisConformance 1 }
isisCompliances OBJECT IDENTIFIER ::= { isisConformance 2 }

-- compliance statements

isisCompliance MODULE-COMPLIANCE
    STATUS current
    DESCRIPTION
        "The compliance statement for agents that support
         the ISIS MIB"
    MODULE -- this module
        MANDATORY-GROUPS {
                isisSystemGroup,
                isisCircuitGroup,
                isisISAdjGroup,
                isisNotificationObjectGroup,
                isisISPDUCounterGroup,
                isisISIPRADestGroup,
                isisNotificationGroup
        }
        ::= { isisCompliances 1 }

-- MIB Grouping

        isisSystemGroup         OBJECT-GROUP
                OBJECTS {
                        isisSysVersion,
                        isisSysType,
                        isisSysID,
                        isisSysMaxPathSplits,
                        isisSysMaxLSPGenInt,
                        isisSysOrigL1LSPBuffSize,
                        isisSysMaxAreaAddresses,
                        isisSysMinL1LSPGenInt,
                        isisSysMinL2LSPGenInt,
                        isisSysPollESHelloRate,
                        isisSysWaitTime,
                        isisSysAdminState,
                        isisSysL1State,
                        isisSysOrigL2LSPBuffSize,
                        isisSysL2State,
                        isisSysLogAdjacencyChanges,
                        isisSysMaxAreaCheck,
                        isisSysNextCircIndex,
                        isisSysExistState,
                        isisSysL2toL1Leaking,
                        isisSysSetOverload,
                        isisSysL1MetricStyle,
                        isisSysL1SPFConsiders,
                        isisSysL2MetricStyle,
                        isisSysL2SPFConsiders,
                        isisSysTEEnabled,
                        isisSysMaxAge,
                        isisSysReceiveLSPBufferSize,
                        isisManAreaAddrExistState,
                        isisAreaAddr,
                        isisSysProtSuppExistState,
                        isisSummAddrExistState,
                        isisSummAddrAdminState,
                        isisSummAddrMetric,
                        isisSysStatCorrLSPs,
                        isisSysStatLSPDbaseOloads,
                        isisSysStatManAddrDropFromAreas,
                        isisSysStatAttmptToExMaxSeqNums,
                        isisSysStatSeqNumSkips,
                        isisSysStatOwnLSPPurges,
                        isisSysStatIDFieldLenMismatches,
                        isisSysStatMaxAreaAddrMismatches,
                        isisSysStatPartChanges,
                        isisSysStatAuthTypeFails,
                        isisSysStatAuthFails
                }
        STATUS current
        DESCRIPTION
                "The collections of objects used to manage an IS-IS router."
        ::= { isisGroups 1 }


        isisCircuitGroup         OBJECT-GROUP
                OBJECTS {
                        isisCircIfSubIndex,
                        isisCircLocalID,
                        isisCircAdminState,
                        isisCircExistState,
                        isisCircType,
                        isisCircExtDomain,
                        isisCircAdjChanges,
                        isisCircInitFails,
                        isisCircRejAdjs,
                        isisCircOutCtrlPDUs,
                        isisCircInCtrlPDUs,
                        isisCircIDFieldLenMismatches,
                        isisCircLevel,
                        isisCircMCAddr,
                        isisCircPtToPtCircID,
                        isisCircPassiveCircuit,
                        isisCircMeshGroupEnabled,
                        isisCircMeshGroup,
                        isisCircSmallHellos,
                        isisCircUpTime,
                        isisCircIfIndex,
                        isisCircLevelMetric,
                        isisCircLevelISPriority,
                        isisCircLevelDesIS,
                        isisCircLevelLANDesISChanges ,
                        isisCircLevelHelloMultiplier,
                        isisCircLevelHelloTimer,
                        isisCircLevelDRHelloTimer,
                        isisCircLevelLSPThrottle,
                        isisCircLevelMinLSPRetransInt,
                        isisCircLevelCSNPInterval,
                        isisCircLevelPartSNPInterval
                 }
        STATUS current
        DESCRIPTION
                "The collection of objects used to describe in IS-IS Circuit."
        ::= { isisGroups 2 }


        isisISAdjGroup                 OBJECT-GROUP
                OBJECTS {
                        isisISAdjState,
                        isisISAdjNeighSNPAAddress,
                        isisISAdjNeighSysType,
                        isisISAdjNeighSysID,
                        isisISAdjUsage,
                        isisISAdjHoldTimer,
                        isisISAdjNeighPriority,
                        isisISAdjUpTime,
                        isisISAdjAreaAddress,
                        isisISAdjIPAddressType,
                        isisISAdjIPAddress,
                        isisISAdjProtSuppProtocol
                }
        STATUS current
        DESCRIPTION
                "The collections of objects used to manage an IS-IS Adjacency."
        ::= { isisGroups 3 }


        isisNotificationObjectGroup OBJECT-GROUP
                OBJECTS {
                        isisSystemLevel,
                        isisTrapLSPID,
                        isisPDUFragment,
                        isisFieldLen,
                        isisMaxAreaAddress,
                        isisProtocolVersion,
                        isisLSPSize,
                        isisOriginatingBufferSize,
                        isisProtocolsSupported
                }
        STATUS current
        DESCRIPTION
                "The objects used to record notification parameters."
        ::= { isisGroups 4 }
        isisNotificationGroup        NOTIFICATION-GROUP
                NOTIFICATIONS {
                        isisDatabaseOverload,
                        isisManualAddressDrops,
                        isisCorruptedLSPDetected,
                        isisAttemptToExceedMaxSequence,
                        isisIDLenMismatch,
                        isisMaxAreaAddressesMismatch,
                        isisOwnLSPPurge,
                        isisSequenceNumberSkip,
                        isisAuthenticationTypeFailure,
                        isisAuthenticationFailure,
                        isisVersionSkew,
                        isisAreaMismatch,
                        isisRejectedAdjacency,
                        isisLSPTooLargeToPropagate,
                        isisOriginatingLSPBufferSizeMismatch,
                        isisProtocolsSupportedMismatch
                }
        STATUS current
        DESCRIPTION
                "The collections of notifications sent by an IS."
        ::= { isisGroups 5 }


        isisISPDUCounterGroup                 OBJECT-GROUP
                OBJECTS {
                        isisPacketCountHello,
                        isisPacketCountLSP,
                        isisPacketCountCSNP,
                        isisPacketCountPSNP
                }
        STATUS current
        DESCRIPTION
                "The collections of objects used to count protocol PDUs."
        ::= { isisGroups 6 }


        isisISIPRADestGroup                 OBJECT-GROUP
                OBJECTS {
                        isisIPRADestType,
                        isisIPRADest,
                        isisIPRADestPrefixLen,
                        isisIPRAExistState,
                        isisIPRAAdminState,
                        isisIPRAMetric,
                        isisIPRAMetricType,
                        isisIPRASNPAAddress
                }
        STATUS current
        DESCRIPTION
                "The collections of objects used to manage configured
                 IP addresses."
        ::= { isisGroups 8 }

END
