ALCATEL-ENT1-TIMETRA-LDP-MIB DEFINITIONS ::= BEGIN

IMPORTS
        MODULE-IDENTITY, OBJECT-TYPE, NOTIFICATION-TYPE,
        Unsigned32, Counter32, Gauge32,
        IpAddress
            FROM SNMPv2-SMI

        MODULE-COMPLIANCE, OBJECT-GROUP, NOTIFICATION-GROUP
            FROM SNMPv2-CONF

        RowStatus, TruthValue, TestAndIncr,
        TimeStamp, TimeInterval, TEXTUAL-CONVENTION
            FROM SNMPv2-TC

        InterfaceIndexOrZero
            FROM IF-MIB

        timetraSRMIBModules, tmnxSRObjs, tmnxSRNotifyPrefix,
        tmnxSRConfs
            FROM ALCATEL-ENT1-TIMETRA-GLOBAL-MIB

        vRtrID, vRtrLdpStatus
            FROM ALCATEL-ENT1-TIMETRA-VRTR-MIB

        TmnxAdminState, TmnxOperState, TPolicyStatementNameOrEmpty,
        TmnxServId, TmnxVcType, TmnxVcId,
        TNamedItemOrEmpty, TmnxVRtrMplsLspID
            FROM ALCATEL-ENT1-TIMETRA-TC-MIB

        MplsLdpIdentifier, MplsLsrIdentifier
            FROM MPLS-LDP-MIB

        ServType, SdpId, TdmOptionsSigPkts, TdmOptionsCasTrunkFraming
            FROM ALCATEL-ENT1-TIMETRA-SERV-MIB

        TFilterLogId, TFilterID
            FROM ALCATEL-ENT1-TIMETRA-FILTER-MIB
        ;

timetraLdpMIBModule MODULE-IDENTITY
        LAST-UPDATED    "0801010000Z"
        ORGANIZATION    "Alcatel"
        CONTACT-INFO
            "Alcatel 7x50 Support
             Web: http://www.alcatel.com/comps/pages/carrier_support.jhtml"
        DESCRIPTION
        "The MIB module to manage and provision the Alcatel 7x50 LDP
        protocol features.

        Copyright 2003-2008 Alcatel-Lucent. All rights reserved.
        Reproduction of this document is authorized on the condition that
        the foregoing copyright notice is included.

        This SNMP MIB module (Specification) embodies Alcatel's
        proprietary intellectual property.  Alcatel retains
        all title and ownership in the Specification, including any
        revisions.

        Alcatel grants all interested parties a non-exclusive
        license to use and distribute an unmodified copy of this
        Specification in connection with management of Alcatel
        products, and without fee, provided this copyright notice and
        license appear on all copies.

        This Specification is supplied 'as is', and Alcatel
        makes no warranty, either express or implied, as to the use,
        operation, condition, or performance of the Specification."
--
--  Revision History
--
        REVISION        "0801010000Z"
        DESCRIPTION     "Rev 6.0                01 Jan 2008 00:00
                         6.0 release of the TIMETRA-LDP-MIB."

        REVISION        "0701010000Z"
        DESCRIPTION     "Rev 5.0                01 Jan 2007 00:00
                         5.0 release of the TIMETRA-LDP-MIB."

        REVISION        "0603160000Z"
        DESCRIPTION     "Rev 4.0                16 Mar 2006 00:00
                         4.0 release of the TIMETRA-LDP-MIB."

        REVISION        "0508310000Z"
        DESCRIPTION     "Rev 3.0                31 Aug 2005 00:00
                         3.0 release of the TIMETRA-LDP-MIB."

        REVISION        "0501240000Z"
        DESCRIPTION     "Rev 2.1                24 Jan 2005 00:00
                         2.1 release of the TIMETRA-LDP-MIB."

        REVISION        "0401150000Z"
        DESCRIPTION     "Rev 2.0                15 Jan 2004 00:00
                         2.0 release of the TIMETRA-LDP-MIB."

        REVISION        "0308150000Z"
        DESCRIPTION     "Rev 1.2                15 Aug 2003 00:00
                         1.2 release of the TIMETRA-LDP-MIB."

        REVISION        "0301200000Z"
        DESCRIPTION     "Rev 1.0                20 Jan 2003 00:00
                         1.0 Release of the TIMETRA-LDP-MIB."

        REVISION        "0108010000Z"
        DESCRIPTION     "Rev 0.1                01 Aug 2001 00:00
                         Initial version of the TIMETRA-LDP-MIB."

        ::= { timetraSRMIBModules 8 }


--%%%%%%%%%%%%%%%%%%%%%%%%%%%%%%%%%%%%%%%%%%%%%%%%%%%%%%%%%%%%%%%%%%%%%%
--
--  LDP extensions
--

tmnxLdpObjs             OBJECT IDENTIFIER ::= { tmnxSRObjs 8 }
tmnxLdpConformance      OBJECT IDENTIFIER ::= { tmnxSRConfs 8 }
tmnxLdpNotifyPrefix    OBJECT IDENTIFIER ::= { tmnxSRNotifyPrefix 8 }
    tmnxLdpNotifications    OBJECT IDENTIFIER ::= { tmnxLdpNotifyPrefix 0 }


--
--      ALCATEL-ENT1-TIMETRA-LDP-MIB Textual Conventions
--
TmnxLdpKeepAliveFactor ::= TEXTUAL-CONVENTION
    STATUS    current
    DESCRIPTION
        "TmnxLdpKeepAliveFactor specifies the value by which the
         keepalive timeout should be divided to give the keepalive
         time i.e. the time interval, in seconds, between LDP
         Keepalive messages. LDP Keepalive messages are sent to
         keep the LDP session from timing out when no other LDP
         traffic is being sent between the neighbors."
    SYNTAX    Unsigned32 (1..255)

TmnxLdpKeepAliveTimeout ::= TEXTUAL-CONVENTION
    STATUS    current
    DESCRIPTION
        "TmnxLdpKeepAliveTimeout specifies the the time interval,
         in seconds, that LDP waits before tearing down a session.
         If no LDP messages are exchanged during this time interval,
         the LDP session is torn down. Generally the keepalive
         timeout interval should be configured to be 3 times the
         keepalive time (the time interval between successive LDP
         Keepalive messages)."
    SYNTAX    Unsigned32 (1..65535)

TmnxLdpHelloFactor ::= TEXTUAL-CONVENTION
    STATUS    current
    DESCRIPTION
        "TmnxLdpHelloFactor specifies the value by which the hello
         timeout should be divided to give the hello time i.e. the
         time interval, in seconds, between LDP Hello messages. LDP
         uses Hello messages to discover neighbors and to detect
         loss of connectivity with its neighbors."
    SYNTAX    Unsigned32 (1..255)

TmnxLdpHelloTimeout ::= TEXTUAL-CONVENTION
    STATUS    current
    DESCRIPTION
        "TmnxLdpHelloTimeout specifies the the time interval, in
         seconds, that LDP waits before declaring a neighbor to
         be down. Hello timeout is local to the system and is sent
         in the Hello messages to a neighbor. Hello timeout cannot
         be set to a value that is less than 3 times the hello time."
    SYNTAX    Unsigned32 (1..65535)

TmnxLdpBackoffTime ::= TEXTUAL-CONVENTION
    STATUS    current
    DESCRIPTION
        "TmnxLdpBackoffTime specifies the backoff interval (initial
         and maximum).
         The backoff interval is the time, in seconds, that LDP waits
         after an LDP session setup has failed before it attempts to
         setup the session again. After the LDP session startup fails
         the first time, the backoff interval is set to an initial
         value. Thereafter, if session startup fails again the backoff
         interval increases exponentially until it reaches a maximum
         value specified by the maximum backoff interval.
         If the maximum backoff interval is set to zero (0), then the
         backoff interval does not increase exponentially after the
         first session startup attempt fails. Instead it remains
         constant and LDP will keep retrying to establish a session
         until it succeeds."
    SYNTAX    Unsigned32 (0..2592000)

TmnxLdpFECPolicy ::= TEXTUAL-CONVENTION
    STATUS    current
    DESCRIPTION
        "TmnxLdpFECPolicy determines whether the LSR should generate
         FECs and which FECs it should generate.

         system(1) - LDP will distribute label bindings only for the
         router's system IP address

         interface(2) - LDP will distribute label bindings for all
         LDP interfaces

         all(3) - LDP will distribute label bindings for all prefixes
         in the routing table

         none(4) - LDP will not distribute any label bindings."
    SYNTAX    INTEGER {
                  system(1),
                  interface(2),
                  all(3),
                  none(4)
              }

TmnxLdpLabelDistMethod ::= TEXTUAL-CONVENTION
    STATUS    current
    DESCRIPTION
        "TmnxLdpLabelDistMethod describes the label distribution method used.

         When the value is 'downstreamOnDemand', label bindings are
         distributed to the upstream LSR only when a label request message
         is received.

         When the value is 'downstreamUnsolicited', label bindings are
         distributed to the upstream LSR, for each FEC, without requiring
         a request message for the FEC from the upstream LSR."
    SYNTAX    INTEGER {
                  downstreamOnDemand (1),
                  downstreamUnsolicited (2)
              }

TmnxLdpAdjacencyType ::= TEXTUAL-CONVENTION
    STATUS    current
    DESCRIPTION
        "TmnxLdpAdjacencyType describes the type of adjacency, either
         targeted or link, for a row in the vRtrLdpHelloAdjTable. It
         also describes the type of adjacencies in an LDP Session row
         in the vRtrLdpSessionTable."
    SYNTAX    INTEGER {
                  link(1),
                  targeted(2),
                  both(3)
              }

TmnxVpnId ::= TEXTUAL-CONVENTION
    STATUS    current
    DESCRIPTION
        "TmnxVpnId specifies the value of a VPN (Virtual Private Network)
         identifier. This is a 10 byte value - the VPN 'type' is stored
         in the first two bytes the TmnxVpnId. The next four bytes store
         an 'AS (Autonomous System) number'. A 'local identifier' for the
         VPN is stored as the last four bytes."
    SYNTAX    OCTET STRING (SIZE (10))

TmnxLabelStatus ::= TEXTUAL-CONVENTION
    STATUS    current
    DESCRIPTION
        "TmnxLabelStatus bit flags specifies the status of an ingress or
         egress label.

         Flags marked dummy* are not used and MUST be 0.

         'statusSignalingSupported' - indicates whether status signaling is
                       enabled or not.
         'inUsePush' - indicates that the label contains valid information
                       that is currently being used as a 'push' label.
         'inUseSwap' - indicates that the label contains valid information
                       that is currently being used as a 'swap' label.
         'inUsePop'  - indicates that the label contains valid information
                       that is currently being used as a 'pop' label.
         'released'  - indicates that the label is in the process of being
                       freed. With this flag set, no other flags will be set.
         'notInUse'  - indicates that the label contains valid information
                       but is currently not being used possibly because the
                       service is temporarily down.
         'withdrawn' - indicates that the label has not been sent (possibly
                       due to a mismatch in control word or status signaling)
         'controlWord' - indicates that the control word will be signaled"
    SYNTAX    BITS {
                  dummyB0 (0),
                  dummyB1 (1),
                  statusSignalingSupported (2),
                  inUsePush (3),
                  inUseSwap (4),
                  inUsePop (5),
                  released (6),
                  notInUse (7),
                  withdrawn (8),
                  controlWord (9)
              }

TmnxLabelSigStatus ::= TEXTUAL-CONVENTION
    STATUS    current
    DESCRIPTION
        "TmnxLabelSigStatus specifies the status of the pseudowire and attached
         circuit.  The values are defined in
         draft-ietf-pwe3-iana-allocation-07.txt."
    REFERENCE
        "IETF draft-ietf-pwe3-iana-allocation-07.txt, sections 2,3 and 4"
    SYNTAX    Unsigned32

TmnxLdpFECType ::= TEXTUAL-CONVENTION
    STATUS    current
    DESCRIPTION
        "TmnxLdpFECType determines the kind of FEC that the label
         mapping, withdraw, release and request messages are
         referring to."
    SYNTAX    INTEGER {
                  addrWildcard(1),
                  addrPrefix(2),
                  addrHost(3),
                  vll(128),
                  vpws(129),
                  vpls(130)
              }

TmnxLdpFECFlags ::= TEXTUAL-CONVENTION
    STATUS    current
    DESCRIPTION
        "TmnxLdpFECFlags bit flags define the characteristics of FEC.
         Flags marked dummy* are not used and MUST be 0.

         Flag 'egress':  this node is an egress for this FEC.
         Flag 'ingress': this node is a potential ingress for this FEC.
         Flag 'installedSwap': the label for this FEC has been programmed
                               as a 'swap' label.
         Flag 'installedPush': the label for this FEC has been programmed
                               as a 'push' label.
         Flag 'installedPop':  the label for this FEC has been programmed
                               as a 'pop' label.
         Flag 'local':   this FEC is local to this node.
         Flag 'nextHop': the nextHop for this FEC is known.
         Flag 'vcSwitching': vcSwitching is enabled for the FEC.
         Flag 'importTargPolicyRejected': targeted LDP import policy has
                                          rejected this FEC.
         Flag 'exportTargPolicyRejected': targeted LDP export policy has
                                          rejected this FEC."

    SYNTAX    BITS {
                  dummyB0 (0),
                  egress (1),
                  ingress (2),
                  installedSwap (3),
                  installedPush (4),
                  installedPop (5),
                  local (6),
                  nextHop (7),
                  importPolicyRejected (8),
                  exportPolicyAccepted (9),
                  installedStaticFec (10),
                  vcSwitching (11),
                  importTargPolicyRejected (12),
                  exportTargPolicyRejected (13)
              }

TmnxLdpGenOperDownReasonCode ::= TEXTUAL-CONVENTION
    STATUS    current
    DESCRIPTION
        "TmnxLdpGenOperDownReasonCode is an enumerated integer that specifies
         the reason that the LDP instance is operationally down."
    SYNTAX    INTEGER {
                  operUp (0),             -- Operationally up
                  adminDown (1),          -- Administratively down
                  noListenSocket (2),     -- No listen socket
                  noDiscoverySocket (3),  -- No discovery socket
                  noRtm (4),              -- No Route Table Manager (RTM)
                  noTtm (5),              -- No Tunnel Table Manager (TTM)
                  iomFailure (6),         -- IOM failure
                  recvFailure (7),        -- Failure while receiving packets
                  clearDown (8),          -- Clear command in progress
                  noResources (9),        -- No resources available
                  systemIpDown (10)       -- System IP interface is
                                          -- operationally down
              }

TmnxLdpIntTargOperDownReasonCode ::= TEXTUAL-CONVENTION
    STATUS    current
    DESCRIPTION
        "TmnxLdpIntTargOperDownReasonCode is an enumerated integer
         that specifies the reason that the LDP interface and targeted peer
         is operationally down."
    SYNTAX    INTEGER {
                  operUp (0),             -- Operationally up
                  adminDown (1),          -- Administratively down
                  noListenSocket (2),     -- No listen socket
                  noDiscoverySocket (3),  -- No discovery socket
                  noResources (4),        -- No resources available
                  addrFecDeprogram (5),   -- interface suspended while deprogramming FECs
                  svcFecDeprogram (6),    -- targeted session suspended while deprogramming FECs
                  clearDown (7),          -- clear command in progress
                  instanceDown (8),       -- LDP instance down
                  interfaceDown (9),      -- LDP interface down
                  targetIpInvalid (10),   -- Target Peer IP Invalid
                  interfaceInvalid (11)   -- LDP interface Invalid
              }

TmnxLdpFec129Tlv ::= TEXTUAL-CONVENTION
    STATUS    current
    DESCRIPTION
        "TmnxLdpFec129Tlv is a Type-Length-Value (Tlv) that specifies
         the value encoded as one-byte Type followed by one byte Length
         followed by the 'Length' size Value used for FEC-129 attribute."
    SYNTAX    OCTET STRING (SIZE (2..32))

--
--  The Virtual Router Label Distribution Protocol (LDP) General Table
--

vRtrLdpGeneralTable    OBJECT-TYPE
    SYNTAX      SEQUENCE OF VRtrLdpGeneralEntry
    MAX-ACCESS  not-accessible
    STATUS      current
    DESCRIPTION
        "vRtrLdpGeneralTable has an entry for each virtual router
         in the system capable of supporting an instance of the
         Label Distribution Protocol (LDP)."
    ::= { tmnxLdpObjs 1 }

vRtrLdpGeneralEntry    OBJECT-TYPE
    SYNTAX      VRtrLdpGeneralEntry
    MAX-ACCESS  not-accessible
    STATUS      current
    DESCRIPTION
        "Each row entry represents an instance of the Label Distribution
         Protocol (LDP) for a virtual router in the system.

         An entry in this table is created by the agent when vRtrLdpStatus
         in the vRtrConfTable is set to 'create'.
         The entry is destroyed when vRtrLdpStatus is set to 'delete' but
         only if vRtrLdpGenAdminState has a value of 'outOfService'."
    INDEX { vRtrID }
    ::= { vRtrLdpGeneralTable 1 }

VRtrLdpGeneralEntry ::= SEQUENCE {
    vRtrLdpGenLastChange                TimeStamp,
    vRtrLdpGenAdminState                TmnxAdminState,
    vRtrLdpGenOperState                 TmnxOperState,
    vRtrLdpGenLdpLsrId                  MplsLsrIdentifier,
    vRtrLdpGenProtocolVersion           Unsigned32,
    vRtrLdpGenDeaggregateFec            TruthValue,
    vRtrLdpGenKeepAliveFactor           TmnxLdpKeepAliveFactor,
    vRtrLdpGenKeepAliveTimeout          TmnxLdpKeepAliveTimeout,
    vRtrLdpGenHelloFactor               TmnxLdpHelloFactor,
    vRtrLdpGenHelloTimeout              TmnxLdpHelloTimeout,
    vRtrLdpGenRoutePreference           Unsigned32,
    vRtrLdpGenControlMode               INTEGER,
    vRtrLdpGenDistMethod                TmnxLdpLabelDistMethod,
    vRtrLdpGenRetentionMode             INTEGER,
    vRtrLdpGenTransportAddrType         INTEGER,
    vRtrLdpGenPropagatePolicy           TmnxLdpFECPolicy,
    vRtrLdpGenLoopDetectCapable         INTEGER,
    vRtrLdpGenHopLimit                  Unsigned32,
    vRtrLdpGenPathVectorLimit           Unsigned32,
    vRtrLdpGenBackoffTime               TmnxLdpBackoffTime,
    vRtrLdpGenMaxBackoffTime            TmnxLdpBackoffTime,
    vRtrLdpGenTargKeepAliveFactor       TmnxLdpKeepAliveFactor,
    vRtrLdpGenTargKeepAliveTimeout      TmnxLdpKeepAliveTimeout,
    vRtrLdpGenTargHelloFactor           TmnxLdpHelloFactor,
    vRtrLdpGenTargHelloTimeout          TmnxLdpHelloTimeout,
    vRtrLdpGenTargPassiveMode           TruthValue,
    vRtrLdpGenTargetedSessions          TruthValue,
    vRtrLdpGenCreateTime                TimeStamp,
    vRtrLdpGenUpTime                    TimeInterval,
    vRtrLdpGenImportPolicy1             TPolicyStatementNameOrEmpty,
    vRtrLdpGenImportPolicy2             TPolicyStatementNameOrEmpty,
    vRtrLdpGenImportPolicy3             TPolicyStatementNameOrEmpty,
    vRtrLdpGenImportPolicy4             TPolicyStatementNameOrEmpty,
    vRtrLdpGenImportPolicy5             TPolicyStatementNameOrEmpty,
    vRtrLdpGenExportPolicy1             TPolicyStatementNameOrEmpty,
    vRtrLdpGenExportPolicy2             TPolicyStatementNameOrEmpty,
    vRtrLdpGenExportPolicy3             TPolicyStatementNameOrEmpty,
    vRtrLdpGenExportPolicy4             TPolicyStatementNameOrEmpty,
    vRtrLdpGenExportPolicy5             TPolicyStatementNameOrEmpty,
    vRtrLdpGenTunnelDownDampTime        Unsigned32,
    vRtrLdpGenOperDownReason            TmnxLdpGenOperDownReasonCode,
    vRtrLdpGenTrustList                 TFilterID,
    vRtrLdpGenGracefulRestart           TruthValue,
    vRtrLdpGenGRNbrLiveTime             Unsigned32,
    vRtrLdpGenGRMaxRecoveryTime         Unsigned32
}

vRtrLdpGenLastChange    OBJECT-TYPE
    SYNTAX      TimeStamp
    MAX-ACCESS  read-only
    STATUS      current
    DESCRIPTION
        "The value of vRtrLdpGenLastChange specifies the sysUpTime
         when this row was last modified."
    ::= { vRtrLdpGeneralEntry 1 }

vRtrLdpGenAdminState    OBJECT-TYPE
    SYNTAX      TmnxAdminState
    MAX-ACCESS  read-create
    STATUS      current
    DESCRIPTION
        "The value of vRtrLdpGenAdminState specifies the desired
         administrative state for this LDP instance."
    DEFVAL { inService }
    ::= { vRtrLdpGeneralEntry 2 }

vRtrLdpGenOperState    OBJECT-TYPE
    SYNTAX      TmnxOperState
    MAX-ACCESS  read-only
    STATUS      current
    DESCRIPTION
        "The value of vRtrLdpGenOperState specifies the current
         operational state of this LDP instance."
    ::= { vRtrLdpGeneralEntry 3 }

vRtrLdpGenLdpLsrId    OBJECT-TYPE
    SYNTAX      MplsLsrIdentifier
    MAX-ACCESS  read-only
    STATUS      current
    DESCRIPTION
        "The value of vRtrLdpGenLdpLsrId is the Label Switch Router
         (LSR) identifier which is used as the first 4 bytes or the
         Router Id component of the Label Distribution Protocol (LDP)
         identifier."
    ::= { vRtrLdpGeneralEntry 4 }

vRtrLdpGenProtocolVersion    OBJECT-TYPE
    SYNTAX      Unsigned32
    MAX-ACCESS  read-only
    STATUS      current
    DESCRIPTION
        "The value of  vRtrLdpGenProtocolVersion specifies the
         version of the LDP protocol instance. A value of zero (0)
         indicates that the version of the protocol is unknown."
    ::= { vRtrLdpGeneralEntry 5 }

vRtrLdpGenDeaggregateFec    OBJECT-TYPE
    SYNTAX      TruthValue
    MAX-ACCESS  read-create
    STATUS      current
    DESCRIPTION
        "When vRtrLdpGenDeaggregateFec has a value of 'false', LDP
         aggregates multiple prefixes into a single Forwarding Equivalence
         Class (FEC) and advertises a single label for the FEC. When the
         value is 'true', LDP deaggregates prefixes into multiple
         FECs.

         This value is only applicable to LDP interfaces and not for
         targeted sessions."
    DEFVAL { false }
    ::= { vRtrLdpGeneralEntry 6 }

vRtrLdpGenKeepAliveFactor    OBJECT-TYPE
    SYNTAX      TmnxLdpKeepAliveFactor
    MAX-ACCESS  read-create
    STATUS      current
    DESCRIPTION
        "The value of vRtrLdpGenKeepAliveFactor specifies the value
         by which the keepalive timeout (vRtrLdpGenKeepAliveTimeout)
         should be divided to give the keepalive time i.e. the time
         interval, in seconds, between LDP keepalive messages. LDP
         keepalive messages are sent to keep the LDP session from timing
         out when no other LDP traffic is being sent between the neighbors.

         This value is only applicable to LDP interfaces and not for
         targeted sessions."
    DEFVAL { 3 }
    ::= { vRtrLdpGeneralEntry 7 }

vRtrLdpGenKeepAliveTimeout    OBJECT-TYPE
    SYNTAX      TmnxLdpKeepAliveTimeout
    UNITS       "seconds"
    MAX-ACCESS  read-create
    STATUS      current
    DESCRIPTION
        "The value of vRtrLdpGenKeepAliveTimeout specifies the time
         interval, in seconds, that LDP waits before tearing down a
         session. If no LDP messages are exchanged during this time
         interval, the LDP session is torn down. Generally the value of
         vRtrLdpGenKeepAliveTimeout is configured to be 3 times the
         keepalive time (the time interval between successive LDP
         keepalive messages).

         This value is only applicable to LDP interfaces and not for
         targeted sessions."
    DEFVAL { 30 }
    ::= { vRtrLdpGeneralEntry 8 }

vRtrLdpGenHelloFactor    OBJECT-TYPE
    SYNTAX      TmnxLdpHelloFactor
    MAX-ACCESS  read-create
    STATUS      current
    DESCRIPTION
        "The value of vRtrLdpGenHelloFactor specifies the value by
         which the hello timeout (vRtrLdpGenHelloTimeout) should be
         divided to give the hello time i.e. the time interval, in seconds,
         between LDP Hello messages. LDP uses hello messages to discover
         neighbors and to detect loss of connectivity with its neighbors.

         This value is only applicable to LDP interfaces and not for
         targeted sessions."
    DEFVAL { 3 }
    ::= { vRtrLdpGeneralEntry 9 }

vRtrLdpGenHelloTimeout    OBJECT-TYPE
    SYNTAX      TmnxLdpHelloTimeout
    UNITS       "seconds"
    MAX-ACCESS  read-create
    STATUS      current
    DESCRIPTION
        "The value of vRtrLdpGenHelloTimeout specifies the hello time
         also known as hold time. It is the time interval, in seconds, that
         LDP waits before declaring a neighbor to be down. Hello timeout
         is local to the system and is sent in the hello messages to a
         neighbor. Hello timeout cannot be set to a value that is less
         than 3 times the hello time.

         This value is only applicable to LDP interfaces and not for
         targeted sessions."
    DEFVAL { 15 }
    ::= { vRtrLdpGeneralEntry 10 }

vRtrLdpGenRoutePreference    OBJECT-TYPE
    SYNTAX      Unsigned32 (1..255)
    MAX-ACCESS  read-create
    STATUS      current
    DESCRIPTION
        "The value of vRtrLdpGenRoutePreference specifies the route
         preference assigned to LDP routes. When multiple routes are
         available to a destination, the route with the lowest preference
         will be used.

         This value is only applicable to LDP interfaces and not for
         targeted sessions."
    DEFVAL { 9 }
    ::= { vRtrLdpGeneralEntry 11 }

vRtrLdpGenControlMode    OBJECT-TYPE
    SYNTAX      INTEGER {
                    ordered (1),
                    independent (2)
                }
    MAX-ACCESS  read-only
    STATUS      current
    DESCRIPTION
        "The value of vRtrLdpGenControlMode specifies the mode used
         for distributing labels in response to label binding requests.

         When vRtrLdpGenControlMode has a value of 'ordered', label
         bindings are not distributed in response to a label request until
         a label binding has been received from the next hop for the
         destination.

         When vRtrLdpGenControlMode has a value of 'independent', label
         bindings are distributed immediately in response to a label
         request even if a label binding has not yet been received from
         the next hop for the destination."
    ::= { vRtrLdpGeneralEntry 12 }

vRtrLdpGenDistMethod    OBJECT-TYPE
    SYNTAX      TmnxLdpLabelDistMethod
    MAX-ACCESS  read-only
    STATUS      current
    DESCRIPTION
        "The value of vRtrLdpGenDistMethod specifies the label
         distribution method used.

         When vRtrLdpGenDistMethod has a value of 'downstreamOnDemand',
         label bindings are distributed to the upstream LSR, for each FEC,
         without requiring a request message for the FEC from the upstream
         LSR.

         When vRtrLdpGenDistMethod has a value of 'downstreamUnsolicited',
         label bindings are distributed to the upstream LSR only when a
         label request message is received."
    ::= { vRtrLdpGeneralEntry 13 }

vRtrLdpGenRetentionMode    OBJECT-TYPE
    SYNTAX      INTEGER {
                    conservative (1),
                    liberal (2)
                }
    MAX-ACCESS  read-only
    STATUS      current
    DESCRIPTION
        "The value of vRtrLdpGenRetentionMode specifies the label
         retention mode used.

         If the value of this object is 'conservative', then advertized
         label mappings are retained only if they will be used to forward
         packets, i.e. if the label came from a valid next hop.  Label
         bindings received from non-nexthops for each FEC are discarded.

         If the value of this object is 'liberal', then all advertized
         label mappings are retained whether they are from a valid next
         hop or not.  When vRtrLdpGenDistMethod has a value of
         'downstreamUnsolicited', a LSR may receive label bindings for
         the same destination for all its neighbors.  Labels for the
         non-nexthops for the FECs are retained in the software but not
         used.  When a network topology change occurs where a non-nexthop
         becomes a true next hop, the label received earlier is then used."
    ::= { vRtrLdpGeneralEntry 14 }

vRtrLdpGenTransportAddrType    OBJECT-TYPE
    SYNTAX      INTEGER {
                    interface (1),
                    system (2)
                }
    MAX-ACCESS  read-create
    STATUS      current
    DESCRIPTION
        "The value of vRtrLdpGenTransportAddrType specifies the source
         of the transport address to be used when setting up the LDP TCP
         sessions.  The transport address can be configured globally
         (applied to all interfaces) or per interface.

         When the value of this object is 'interface', the interface's
         IP address is used to setup the LDP session between neighbors.
         If multiple interfaces exist between two neighbors, the
         'interface' mode cannot be used since only one LDP session is
         actually set up between the two neighbors.

         When the value of this object is 'system', the system's IP address
         is used to set up the LDP session between neighbors.

         This value is only applicable to LDP interfaces and not for
         targeted sessions."
    DEFVAL { system }
    ::= { vRtrLdpGeneralEntry 15 }

vRtrLdpGenPropagatePolicy    OBJECT-TYPE
    SYNTAX      TmnxLdpFECPolicy
    MAX-ACCESS  read-create
    STATUS      current
    DESCRIPTION
        "The value of vRtrLdpGenPropagatePolicy determines whether the
         LSR should generate FECs and which FECs it should generate.

         When the value of this object is 'system', LDP will distribute
         label bindings only for the router's system IP address

         When the value of this object is 'interface', LDP will distribute
         label bindings for all LDP interfaces

         When the value of this object is 'all', LDP will distribute label
         bindings for all prefixes in the routing table

         When the value of this object is 'none', LDP will not distribute
         any label bindings.

         This value is only applicable to LDP interfaces and not for
         targeted sessions."
    DEFVAL { system }
    ::= { vRtrLdpGeneralEntry 16 }

vRtrLdpGenLoopDetectCapable    OBJECT-TYPE
    SYNTAX      INTEGER {
                    none (1),
                    other (2),
                    hopCount (3),
                    pathVector (4),
                    hopCountAndPathVector (5)
                }
    MAX-ACCESS  read-create
    STATUS      current
    DESCRIPTION
        "The value of vRtrLdpGenLoopDetectCapable indicate whether
         this LSR supports loop detection and if so, what type of loop
         detection is supported.

         When the value is 'none' loop detection is not supported on this
         LSR.

         When the value is 'other' Loop Detection is supported but by a
         method other than those listed below.

         When the value is 'hopCount' Loop Detection is supported by Hop
         Count only.

         When the value is 'pathVector' Loop Detection is supported by
         Path Vector only.

         When the value is 'hopCountAndPathVector' Loop Detection is
         supported by both Hop Count and Path Vector.

         Since Loop Detection is determined during Session Initialization,
         an individual session may not be running with loop detection.
         This object simply gives an indication of whether or not the
         LSR has the ability to support Loop Detection and which types."
    DEFVAL { none }
    ::= { vRtrLdpGeneralEntry 17 }

vRtrLdpGenHopLimit    OBJECT-TYPE
    SYNTAX       Unsigned32 (0..255)
    MAX-ACCESS   read-create
    STATUS       current
    DESCRIPTION
        "The value of vRtrLdpGenHopLimit specifies the maximum
         allowable value for the hop count.  The value of this object
         is valid and used only if vRtrLdpGenLoopDetectCapable has
         a value of either 'hopCount' or 'hopCountAndPathVector'."
    DEFVAL { 255 }
    ::= { vRtrLdpGeneralEntry 18 }

vRtrLdpGenPathVectorLimit  OBJECT-TYPE
    SYNTAX      Unsigned32 (0..255)
    MAX-ACCESS  read-create
    STATUS      current
    DESCRIPTION
        "The value of vRtrLdpGenPathVectorLimit specifies the maximum
         allowable value for the path vector count.  The value of this
         object is valid and used only if vRtrLdpGenLoopDetectCapable
         has a value of either 'pathVector' or 'hopCountAndPathVector'."
    DEFVAL { 255 }
    ::= { vRtrLdpGeneralEntry 19 }

vRtrLdpGenBackoffTime    OBJECT-TYPE
    SYNTAX      TmnxLdpBackoffTime (1..2592000)
    UNITS       "seconds"
    MAX-ACCESS  read-create
    STATUS      current
    DESCRIPTION
        "The value of vRtrLdpGenBackoffTime specifies the initial
         value for the backoff interval.

         The backoff interval is the time, in seconds, that LDP waits
         after an LDP session setup has failed before it attempts to
         setup the session again. After the LDP session startup fails
         the first time, the backoff interval is set to the value of
         vRtrLdpGenBackoffTime. Thereafter, if session startup
         fails again the backoff interval increases exponentially."
    DEFVAL { 15 }
    ::= { vRtrLdpGeneralEntry 20 }

vRtrLdpGenMaxBackoffTime    OBJECT-TYPE
    SYNTAX      TmnxLdpBackoffTime
    UNITS       "seconds"
    MAX-ACCESS  read-create
    STATUS      current
    DESCRIPTION
        "The value of vRtrLdpGenMaxBackoffTime specifies the maximum
         value for the backoff interval.

         For each successive failure of the LDP session startup, the
         backoff interval (the time for which the router waits before
         retrying) increases exponentially. If the backoff interval
         exceeds vRtrLdpGenMaxBackoffTime, the router will give
         up trying to establish the LDP session.

         If vRtrLdpGenMaxBackoffTime is set to zero (0), then the
         backoff interval does not increase exponentially after the
         first session startup attempt fails. Instead it remains
         constant and LDP will keep retrying to establish a session
         until it succeeds."
    DEFVAL { 120 }
    ::= { vRtrLdpGeneralEntry 21 }

vRtrLdpGenTargKeepAliveFactor    OBJECT-TYPE
    SYNTAX      TmnxLdpKeepAliveFactor
    MAX-ACCESS  read-create
    STATUS      current
    DESCRIPTION
        "The value of vRtrLdpGenTargKeepAliveFactor specifies the value
         by which the keepalive timeout (vRtrLdpGenTargKeepAliveTimeout)
         should be divided to give the keepalive time i.e. the time
         interval, in seconds, between LDP keepalive messages. LDP
         keepalive messages are sent to keep the LDP session from timing
         out when no other LDP traffic is being sent between the neighbors.

         This value is only applicable to targeted sessions and not to LDP
         interfaces."
    DEFVAL { 4 }
    ::= { vRtrLdpGeneralEntry 22 }

vRtrLdpGenTargKeepAliveTimeout    OBJECT-TYPE
    SYNTAX      TmnxLdpKeepAliveTimeout
    UNITS       "seconds"
    MAX-ACCESS  read-create
    STATUS      current
    DESCRIPTION
        "The value of vRtrLdpGenTargKeepAliveTimeout specifies the time
         interval, in seconds, that LDP waits before tearing down a session.
         If no LDP messages are exchanged during this time interval, the LDP
         session is torn down. Genly the value of
         vRtrLdpGenTargKeepAliveTimeout is configured to be 3 times the
         keepalive time (the time interval between successive LDP keepalive
         messages).

         This value is only applicable to targeted sessions and not to LDP
         interfaces."
    DEFVAL { 40 }
    ::= { vRtrLdpGeneralEntry 23 }

vRtrLdpGenTargHelloFactor    OBJECT-TYPE
    SYNTAX      TmnxLdpHelloFactor
    MAX-ACCESS  read-create
    STATUS      current
    DESCRIPTION
        "The value of vRtrLdpGenTargHelloFactor specifies the value by
         which the hello timeout (vRtrLdpGenTargHelloTimeout) should be
         divided to give the hello time i.e. the time interval, in seconds,
         between LDP Hello messages. LDP uses hello messages to discover
         neighbors and to detect loss of connectivity with its neighbors.

         This value is only applicable to targeted sessions and not to LDP
         interfaces."
    DEFVAL { 3 }
    ::= { vRtrLdpGeneralEntry 24 }

vRtrLdpGenTargHelloTimeout    OBJECT-TYPE
    SYNTAX      TmnxLdpHelloTimeout
    UNITS       "seconds"
    MAX-ACCESS  read-create
    STATUS      current
    DESCRIPTION
        "The value of vRtrLdpGenTargHelloTimeout specifies the hello time
         also known as hold time. It is the time interval, in seconds, that
         LDP waits before declaring a neighbor to be down. Hello timeout
         is local to the system and is sent in the hello messages to a
         neighbor. Hello timeout cannot be set to a value that is less
         than 3 times the hello time.

         This value is only applicable to targeted sessions and not to LDP
         interfaces."
    DEFVAL { 45 }
    ::= { vRtrLdpGeneralEntry 25 }

vRtrLdpGenTargPassiveMode  OBJECT-TYPE
    SYNTAX      TruthValue
    MAX-ACCESS  read-create
    STATUS      current
    DESCRIPTION
        "The value of vRtrLdpGenTargPassiveMode specifies the mode used
         for setting up LDP sessions. When it has a value of 'true', LDP
         responds only when it gets a connect request from a peer and will
         not attempt to actively connect to its neighbors. When it has a
         value of 'false', LDP actively tries to connect to its peers.

         This value is only applicable to targeted sessions and not to LDP
         interfaces."
    DEFVAL { false }
    ::= { vRtrLdpGeneralEntry 26 }

vRtrLdpGenTargetedSessions    OBJECT-TYPE
    SYNTAX      TruthValue
    MAX-ACCESS  read-create
    STATUS      current
    DESCRIPTION
        "The value of vRtrLdpGenTargetedSessions specifies whether or
         not targeted sessions are allowed.  Targeted sessions are LDP
         sessions between indirectly connected peers.  The discovery
         messages for an indirect LDP session are addressed to the
         specified peer instead of to the multicast address.  When this
         object has a value of 'true', targeted sessions are enabled.
         When its value is 'false', targeted sessions are disabled."
    DEFVAL { true }
    ::= { vRtrLdpGeneralEntry 27 }

vRtrLdpGenCreateTime OBJECT-TYPE
    SYNTAX       TimeStamp
    MAX-ACCESS   read-only
    STATUS       current
    DESCRIPTION
        "The value of vRtrLdpGenCreateTime specifies the sysUpTime
         when this LDP instance was created."
    ::= { vRtrLdpGeneralEntry 28 }

vRtrLdpGenUpTime OBJECT-TYPE
    SYNTAX       TimeInterval
    MAX-ACCESS   read-only
    STATUS       current
    DESCRIPTION
        "The value of vRtrLdpGenUpTime specifies the time, in
         hundreds of seconds, that the LDP instance has been
         operationally up."
    ::= { vRtrLdpGeneralEntry 29 }

vRtrLdpGenImportPolicy1 OBJECT-TYPE
    SYNTAX       TPolicyStatementNameOrEmpty
    MAX-ACCESS   read-create
    STATUS       current
    DESCRIPTION
        "The value of vRtrLdpGenImportPolicy1 specifies the first
         import policy used to filter LDP label bindings received
         from LDP peers."
    DEFVAL { ''H }
    ::= { vRtrLdpGeneralEntry 30 }

vRtrLdpGenImportPolicy2 OBJECT-TYPE
    SYNTAX       TPolicyStatementNameOrEmpty
    MAX-ACCESS   read-create
    STATUS       current
    DESCRIPTION
        "The value of vRtrLdpGenImportPolicy2 specifies the second
         import policy used to filter LDP label bindings received
         from LDP peers."
    DEFVAL { ''H }
    ::= { vRtrLdpGeneralEntry 31 }

vRtrLdpGenImportPolicy3 OBJECT-TYPE
    SYNTAX       TPolicyStatementNameOrEmpty
    MAX-ACCESS   read-create
    STATUS       current
    DESCRIPTION
        "The value of vRtrLdpGenImportPolicy3 specifies the third
         import policy used to filter LDP label bindings received
         from LDP peers."
    DEFVAL { ''H }
    ::= { vRtrLdpGeneralEntry 32 }

vRtrLdpGenImportPolicy4 OBJECT-TYPE
    SYNTAX       TPolicyStatementNameOrEmpty
    MAX-ACCESS   read-create
    STATUS       current
    DESCRIPTION
        "The value of vRtrLdpGenImportPolicy4 specifies the fourth
         import policy used to filter LDP label bindings received
         from LDP peers."
    DEFVAL { ''H }
    ::= { vRtrLdpGeneralEntry 33 }

vRtrLdpGenImportPolicy5 OBJECT-TYPE
    SYNTAX       TPolicyStatementNameOrEmpty
    MAX-ACCESS   read-create
    STATUS       current
    DESCRIPTION
        "The value of vRtrLdpGenImportPolicy5 specifies the fifth
         import policy used to filter LDP label bindings received
         from LDP peers."
    DEFVAL { ''H }
    ::= { vRtrLdpGeneralEntry 34 }

vRtrLdpGenExportPolicy1 OBJECT-TYPE
    SYNTAX       TPolicyStatementNameOrEmpty
    MAX-ACCESS   read-create
    STATUS       current
    DESCRIPTION
        "The value of vRtrLdpGenExportPolicy1 specifies the first
         export policy used to filter LDP label bindings advertised
         to LDP peers."
    DEFVAL { ''H }
    ::= { vRtrLdpGeneralEntry 35 }

vRtrLdpGenExportPolicy2 OBJECT-TYPE
    SYNTAX       TPolicyStatementNameOrEmpty
    MAX-ACCESS   read-create
    STATUS       current
    DESCRIPTION
        "The value of vRtrLdpGenExportPolicy2 specifies the second
         export policy used to filter LDP label bindings advertised
         to LDP peers."
    DEFVAL { ''H }
    ::= { vRtrLdpGeneralEntry 36 }

vRtrLdpGenExportPolicy3 OBJECT-TYPE
    SYNTAX       TPolicyStatementNameOrEmpty
    MAX-ACCESS   read-create
    STATUS       current
    DESCRIPTION
        "The value of vRtrLdpGenExportPolicy3 specifies the third
         export policy used to filter LDP label bindings advertised
         to LDP peers."
    DEFVAL { ''H }
    ::= { vRtrLdpGeneralEntry 37 }

vRtrLdpGenExportPolicy4 OBJECT-TYPE
    SYNTAX       TPolicyStatementNameOrEmpty
    MAX-ACCESS   read-create
    STATUS       current
    DESCRIPTION
        "The value of vRtrLdpGenExportPolicy4 specifies the fourth
         export policy used to filter LDP label bindings advertised
         to LDP peers."
    DEFVAL { ''H }
    ::= { vRtrLdpGeneralEntry 38 }

vRtrLdpGenExportPolicy5 OBJECT-TYPE
    SYNTAX       TPolicyStatementNameOrEmpty
    MAX-ACCESS   read-create
    STATUS       current
    DESCRIPTION
        "The value of vRtrLdpGenExportPolicy5 specifies the fifth
         export policy used to filter LDP label bindings advertised
         to LDP peers."
    DEFVAL { ''H }
    ::= { vRtrLdpGeneralEntry 39 }

vRtrLdpGenTunnelDownDampTime  OBJECT-TYPE
    SYNTAX       Unsigned32 (0..20)
    UNITS        "seconds"
    MAX-ACCESS   read-create
    STATUS       current
    DESCRIPTION
        "The value of vRtrLdpGenTunnelDownDampTime specifies the time
         interval, in seconds, that LDP waits before posting a
         tunnel down event to the Route Table Manager. If a tunnel
         up event is generated before the damping interval has
         elapsed, a tunnel modify event will be posted to the Route
         Table Manager (RTM). If this value is set to 0, then tunnel
         down events are not damped."
    DEFVAL { 3 }
    ::= { vRtrLdpGeneralEntry 40 }

vRtrLdpGenOperDownReason  OBJECT-TYPE
    SYNTAX       TmnxLdpGenOperDownReasonCode
    MAX-ACCESS   read-only
    STATUS       current
    DESCRIPTION
        "The value of vRtrLdpGenOperDownReason specifies the reason
         that the LDP instance is operationally down."
    ::= { vRtrLdpGeneralEntry 41 }

vRtrLdpGenTrustList     OBJECT-TYPE
    SYNTAX      TFilterID
    MAX-ACCESS  read-create
    STATUS      obsolete
    DESCRIPTION
        "The value of vRtrLdpGenTrustList specifies the IP filter ID used to
         verify trusted T-LDP peers. The IP filter specified by this object
         should contain a list of src-ip matches. The value '0' is not a valid
         IP filter ID, but it is used to indicate that there is no trust list.

         This object was obsoleted in release 5.0."
    DEFVAL { 0 }
    ::= { vRtrLdpGeneralEntry 42 }

vRtrLdpGenGracefulRestart  OBJECT-TYPE
    SYNTAX      TruthValue
    MAX-ACCESS  read-create
    STATUS      current
    DESCRIPTION
        "The value of vRtrLdpGenGracefulRestart specifies whether graceful
         restart helper is allowed.  When this object has a value of 'true',
         graceful restart helper is enabled.  When its value is 'false', graceful
         restart helper is disabled."
    DEFVAL { false }
    ::= { vRtrLdpGeneralEntry 43 }

vRtrLdpGenGRNbrLiveTime  OBJECT-TYPE
    SYNTAX       Unsigned32 (5..300)
    UNITS        "seconds"
    MAX-ACCESS   read-create
    STATUS       current
    DESCRIPTION
        "The value of vRtrLdpGenGRNbrLiveTime specifies the value for neighbor
         liveness timer.  The amount of time the Label Switching Router (LSR)
         keeps its stale label-FEC bindings is set to the lesser of the FT Reconnect
         Timeout, as was advertised by the  neighbor, and this local timer, called the
         Neighbor Liveness Timer.

         The LSR waits for the specified time till a LDP session re-establishes
         itself.  If within that time the LSR still does not establish an LDP session with
         the neighbor, all the stale bindings are deleted.  This object has meaning
         only when vRtrLdpGenGracefulRestart is 'true'."
    DEFVAL { 120 }
    ::= { vRtrLdpGeneralEntry 44 }

vRtrLdpGenGRMaxRecoveryTime OBJECT-TYPE
    SYNTAX       Unsigned32 (15..1800)
    UNITS        "seconds"
    MAX-ACCESS   read-create
    STATUS       current
    DESCRIPTION
        "The value of vRtrLdpGenGRMaxRecoveryTime specifies the local maximum
         recovery time.

         If the Label Switching Router (LSR)  determines that the neighbor was able
         to preserve its MPLS forwarding  state (as was indicated by the non-zero
         Recovery Time advertised by  the neighbor), the LSR should further keep
         the stale label-FEC  bindings, received from the neighbor, for as long
         as the lesser of the Recovery Time advertised by the neighbor, and a
         local configurable value, called Maximum Recovery Time, allows.  This object
         has meaning only when vRtrLdpGenGracefulRestart is 'true'."
    DEFVAL { 120 }
    ::= { vRtrLdpGeneralEntry 45 }

--
--  LDP Statistics table
--

vRtrLdpStatsTable    OBJECT-TYPE
    SYNTAX      SEQUENCE OF VRtrLdpStatsEntry
    MAX-ACCESS  not-accessible
    STATUS      current
    DESCRIPTION
        "vRtrLdpStatsTable is a read-only table. The purpose of this table
         is to keep statistical information about an LDP Instance.

         Use of AUGMENTS clause implies a one-to-one dependent
         relationship between the base table, vRtrLdpGeneralTable,
         and the augmenting table, vRtrLdpStatsTable. This in
         effect extends the vRtrLdpGeneralTable with additional
         columns.  Creation or deletion of a row in the
         vRtrLdpGeneralTable results in the same fate for the row
         in the vRtrLdpStatsTable."
    ::= { tmnxLdpObjs 2 }

vRtrLdpStatsEntry OBJECT-TYPE
    SYNTAX      VRtrLdpStatsEntry
    MAX-ACCESS  not-accessible
    STATUS      current
    DESCRIPTION
        "A row in this table represents statistical information about
         an LDP instance."
    AUGMENTS  { vRtrLdpGeneralEntry }
    ::= { vRtrLdpStatsTable 1 }

VRtrLdpStatsEntry ::= SEQUENCE {
    vRtrLdpStatsOperDownEvents                  Counter32,
    vRtrLdpStatsActiveSessions                  Gauge32,
    vRtrLdpStatsActiveAdjacencies               Gauge32,
    vRtrLdpStatsActiveInterfaces                Gauge32,
    vRtrLdpStatsInactiveInterfaces              Gauge32,
    vRtrLdpStatsActiveTargSessions              Gauge32,
    vRtrLdpStatsInactiveTargSessions            Gauge32,
    vRtrLdpStatsAddrFECRecv                     Gauge32,
    vRtrLdpStatsAddrFECSent                     Gauge32,
    vRtrLdpStatsSvcFECRecv                      Gauge32,
    vRtrLdpStatsSvcFECSent                      Gauge32,
    vRtrLdpStatsAttemptedSessions               Counter32,
    vRtrLdpStatsSessRejNoHelloErrors            Counter32,
    vRtrLdpStatsSessRejAdvErrors                Counter32,
    vRtrLdpStatsSessRejMaxPduErrors             Counter32,
    vRtrLdpStatsSessRejLabelRangeErrors         Counter32,
    vRtrLdpStatsBadLdpIdentifierErrors          Counter32,
    vRtrLdpStatsBadPduLengthErrors              Counter32,
    vRtrLdpStatsBadMessageLengthErrors          Counter32,
    vRtrLdpStatsBadTlvLengthErrors              Counter32,
    vRtrLdpStatsMalformedTlvValueErrors         Counter32,
    vRtrLdpStatsKeepAliveExpiredErrors          Counter32,
    vRtrLdpStatsShutdownNotifRecv               Counter32,
    vRtrLdpStatsShutdownNotifSent               Counter32
}

vRtrLdpStatsOperDownEvents    OBJECT-TYPE
    SYNTAX      Counter32
    MAX-ACCESS  read-only
    STATUS      current
    DESCRIPTION
        "The value of vRtrLdpStatsOperDownEvents specifies the number
         of times the LDP instance has gone operationally down since
         the instance was created."
    ::= { vRtrLdpStatsEntry 1 }

vRtrLdpStatsActiveSessions    OBJECT-TYPE
    SYNTAX      Gauge32
    MAX-ACCESS  read-only
    STATUS      current
    DESCRIPTION
        "The value of vRtrLdpStatsActiveSessions specifies the number
         of active sessions (i.e. session in some form of creation)
         associated with the LDP instance."
    ::= { vRtrLdpStatsEntry 2 }

vRtrLdpStatsActiveAdjacencies    OBJECT-TYPE
    SYNTAX      Gauge32
    MAX-ACCESS  read-only
    STATUS      current
    DESCRIPTION
        "The value of vRtrLdpStatsActiveAdjacencies specifies the
         number of active adjacencies (i.e. established sessions)
         associated with the LDP instance."
    ::= { vRtrLdpStatsEntry 3 }

vRtrLdpStatsActiveInterfaces    OBJECT-TYPE
    SYNTAX      Gauge32
    MAX-ACCESS  read-only
    STATUS      current
    DESCRIPTION
        "The value of vRtrLdpStatsActiveInterfaces specifies the
         number of active (i.e. operationally up) interfaces
         associated with the LDP instance."
    ::= { vRtrLdpStatsEntry 4 }

vRtrLdpStatsInactiveInterfaces    OBJECT-TYPE
    SYNTAX      Gauge32
    MAX-ACCESS  read-only
    STATUS      current
    DESCRIPTION
        "The value of vRtrLdpStatsInactiveInterfaces specifies the
         number of inactive (i.e. operationally down) interfaces
         associated with the LDP instance."
    ::= { vRtrLdpStatsEntry 5 }

vRtrLdpStatsActiveTargSessions    OBJECT-TYPE
    SYNTAX      Gauge32
    MAX-ACCESS  read-only
    STATUS      current
    DESCRIPTION
        "The value of vRtrLdpStatsActiveTargSessions specifies the
         number of active (i.e. operationally up) targeted sessions
         associated with the LDP instance."
    ::= { vRtrLdpStatsEntry 6 }

vRtrLdpStatsInactiveTargSessions    OBJECT-TYPE
    SYNTAX      Gauge32
    MAX-ACCESS  read-only
    STATUS      current
    DESCRIPTION
        "The value of vRtrLdpStatsInactiveTargSessions specifies the
         number of inactive (i.e. operationally down) targeted
         sessions associated with the LDP instance."
    ::= { vRtrLdpStatsEntry 7 }

vRtrLdpStatsAddrFECRecv    OBJECT-TYPE
    SYNTAX      Gauge32
    MAX-ACCESS  read-only
    STATUS      current
    DESCRIPTION
        "The value of vRtrLdpStatsAddrFECRecv specifies the number of
         Address FECs received by the LDP instance from its neighbors."
    ::= { vRtrLdpStatsEntry 8 }

vRtrLdpStatsAddrFECSent    OBJECT-TYPE
    SYNTAX      Gauge32
    MAX-ACCESS  read-only
    STATUS      current
    DESCRIPTION
        "The value of vRtrLdpStatsAddrFECSent specifies the number of
         Address FECs sent by the LDP instance to its neighbors."
    ::= { vRtrLdpStatsEntry 9 }

vRtrLdpStatsSvcFECRecv    OBJECT-TYPE
    SYNTAX      Gauge32
    MAX-ACCESS  read-only
    STATUS      current
    DESCRIPTION
        "The value of vRtrLdpStatsSvcFECRecv specifies the number of
         Service FECs received by the LDP instance from its neighbors."
    ::= { vRtrLdpStatsEntry 10 }

vRtrLdpStatsSvcFECSent    OBJECT-TYPE
    SYNTAX      Gauge32
    MAX-ACCESS  read-only
    STATUS      current
    DESCRIPTION
        "The value of vRtrLdpStatsSvcFECSent specifies the number of
         Service FECs sent by the LDP instance to its neighbors."
    ::= { vRtrLdpStatsEntry 11 }

vRtrLdpStatsAttemptedSessions    OBJECT-TYPE
    SYNTAX      Counter32
    MAX-ACCESS  read-only
    STATUS      current
    DESCRIPTION
        "The value of vRtrLdpStatsAttemptedSessions specifies the total number
         of attempted sessions for this LDP instance."
    ::= { vRtrLdpStatsEntry 12 }

vRtrLdpStatsSessRejNoHelloErrors    OBJECT-TYPE
    SYNTAX      Counter32
    MAX-ACCESS  read-only
    STATUS      current
    DESCRIPTION
        "The value of vRtrLdpStatsSessRejNoHelloErrors gives the total
         number of Session Rejected/No Hello Error Notification Messages
         sent or received by this LDP instance."
    ::= { vRtrLdpStatsEntry 13 }

vRtrLdpStatsSessRejAdvErrors    OBJECT-TYPE
    SYNTAX      Counter32
    MAX-ACCESS  read-only
    STATUS      current
    DESCRIPTION
        "The value of vRtrLdpStatsSessRejAdvErrors gives the total
         number of Session Rejected/Parameters Advertisement Mode Error
         Notification Messages sent or received by this LDP instance."
    ::= { vRtrLdpStatsEntry 14 }

vRtrLdpStatsSessRejMaxPduErrors    OBJECT-TYPE
    SYNTAX      Counter32
    MAX-ACCESS  read-only
    STATUS      current
    DESCRIPTION
        "The value of vRtrLdpStatsSessRejMaxPduErrors gives the total
         number of Session Rejected/Parameters Max Pdu Length Error
         Notification Messages sent or received by this LDP instance."
    ::= { vRtrLdpStatsEntry 15 }

vRtrLdpStatsSessRejLabelRangeErrors    OBJECT-TYPE
    SYNTAX      Counter32
    MAX-ACCESS  read-only
    STATUS      current
    DESCRIPTION
        "The value of vRtrLdpStatsSessRejLabelRangeErrors gives the total
         number of Session Rejected/Parameters Label Range Error
         Notification Messages sent or received by this LDP instance."
    ::= { vRtrLdpStatsEntry 16 }

vRtrLdpStatsBadLdpIdentifierErrors    OBJECT-TYPE
    SYNTAX      Counter32
    MAX-ACCESS  read-only
    STATUS      current
    DESCRIPTION
        "The value of vRtrLdpStatsBadLdpIdentifierErrors gives the number of
         Bad LDP Identifier Fatal Errors detected for sessions associated
         with this LDP instance."
    REFERENCE
       "LDP Specification, Section 3.5.1.2."
    ::= { vRtrLdpStatsEntry 17 }

vRtrLdpStatsBadPduLengthErrors    OBJECT-TYPE
    SYNTAX      Counter32
    MAX-ACCESS  read-only
    STATUS      current
    DESCRIPTION
        "The value of vRtrLdpStatsBadPduLengthErrors gives the number of
         Bad Pdu Length Fatal Errors detected for sessions associated
         with this LDP instance."
    REFERENCE
       "LDP Specification, Section 3.5.1.2."
    ::= { vRtrLdpStatsEntry 18 }

vRtrLdpStatsBadMessageLengthErrors    OBJECT-TYPE
    SYNTAX      Counter32
    MAX-ACCESS  read-only
    STATUS      current
    DESCRIPTION
        "The value of vRtrLdpStatsBadMessageLengthErrors gives the number of
         Bad Message Length Fatal Errors detected for sessions associated
         with this LDP instance."
    REFERENCE
       "LDP Specification, Section 3.5.1.2."
    ::= { vRtrLdpStatsEntry 19 }

vRtrLdpStatsBadTlvLengthErrors    OBJECT-TYPE
    SYNTAX      Counter32
    MAX-ACCESS  read-only
    STATUS      current
    DESCRIPTION
        "The value of vRtrLdpStatsBadTlvLengthErrors gives the number of
         Bad TLV Length Fatal Errors detected for sessions associated
         with this LDP instance."
    REFERENCE
       "LDP Specification, Section 3.5.1.2."
    ::= { vRtrLdpStatsEntry 20 }

vRtrLdpStatsMalformedTlvValueErrors    OBJECT-TYPE
    SYNTAX      Counter32
    MAX-ACCESS  read-only
    STATUS      current
    DESCRIPTION
        "The value of vRtrLdpStatsMalformedTlvValueErrors gives the number of
         Malformed TLV Value Fatal Errors detected for sessions associated
         with this LDP instance."
    REFERENCE
       "LDP Specification, Section 3.5.1.2."
    ::= { vRtrLdpStatsEntry 21 }

vRtrLdpStatsKeepAliveExpiredErrors    OBJECT-TYPE
    SYNTAX      Counter32
    MAX-ACCESS  read-only
    STATUS      current
    DESCRIPTION
       "The value of vRtrLdpStatsKeepAliveExpiredErrors gives the number of
        Session Keep Alive Timer Expired Errors detected for sessions
        associated with this LDP instance."
    REFERENCE
       "LDP Specification, Section 3.5.1.2."
    ::= { vRtrLdpStatsEntry 22 }

vRtrLdpStatsShutdownNotifRecv    OBJECT-TYPE
    SYNTAX      Counter32
    MAX-ACCESS  read-only
    STATUS      current
    DESCRIPTION
       "The value of vRtrLdpStatsShutdownNotifRecv gives the number of
        Shutdown Notifications received related to sessions associated
        with this LDP instance."
    ::= { vRtrLdpStatsEntry 23 }

vRtrLdpStatsShutdownNotifSent    OBJECT-TYPE
    SYNTAX      Counter32
    MAX-ACCESS  read-only
    STATUS      current
    DESCRIPTION
       "The value of vRtrLdpStatsShutdownNotifSent gives the number of
        Shutdown Notifications sent related to sessions associated with
        this LDP instance."
    ::= { vRtrLdpStatsEntry 24 }

--
--  LDP Policy Table
--

vRtrLdpPolicyTable    OBJECT-TYPE
    SYNTAX      SEQUENCE OF VRtrLdpPolicyEntry
    MAX-ACCESS  not-accessible
    STATUS      obsolete
    DESCRIPTION
        "vRtrLdpPolicyTable has an entry for each policy used by
         the LDP protocol instance running on the virtual router.

         This table is obsoleted in release 2.1."
    ::= { tmnxLdpObjs 3 }

vRtrLdpPolicyEntry    OBJECT-TYPE
    SYNTAX      VRtrLdpPolicyEntry
    MAX-ACCESS  not-accessible
    STATUS      obsolete
    DESCRIPTION
        "Each row entry represents a policy used by the LDP protocol
         instance.

         Entries can be created and deleted via SNMP SET operations
         to vRtrLdpPolicyRowStatus.

         This entry is obsoleted in release 2.1."
    INDEX  { vRtrID,
             vRtrLdpPolicyType,
             vRtrLdpPolicyIndex }
    ::= { vRtrLdpPolicyTable 1 }

VRtrLdpPolicyEntry ::= SEQUENCE {
    vRtrLdpPolicyType               INTEGER,
    vRtrLdpPolicyIndex              Unsigned32,
    vRtrLdpPolicyRowStatus          RowStatus,
    vRtrLdpPolicyName               TPolicyStatementNameOrEmpty
}

vRtrLdpPolicyType    OBJECT-TYPE
    SYNTAX      INTEGER {
                    import (1),
                    export (2),
                    ingress (3),
                    egress (4)
                }
    MAX-ACCESS  not-accessible
    STATUS      obsolete
    DESCRIPTION
        "The value of vRtrLdpPolicyType indicates the type of policy
         specified in this row entry.

         When vRtrLdpPolicyType has a value of 'import' this row
         entry represents the policy filter to be applied to the label
         binding received from a neighbor.

         When the value is 'export', this row entry represents the
         policy filter to determine the labels to be advertised to the
         neighbors.

         When the value is 'ingress', this row entry represents the
         policy filter to control the route prefixes that are advertised
         by LDP to the route table.  LDP will advertise label bindings
         of prefixes that are advertised into it.

         When the value is 'egress', this row entry represents the
         policy filter to control the route prefixes that are advertised
         into LDP from the route table.  LDP will advertise label bindings
         of prefixes that are advertised into it.

         This object is obsoleted in release 2.1."
    ::= { vRtrLdpPolicyEntry 1 }

vRtrLdpPolicyIndex    OBJECT-TYPE
    SYNTAX      Unsigned32 (1..5)
    MAX-ACCESS  not-accessible
    STATUS      obsolete
    DESCRIPTION
        "vRtrLdpPolicyIndex is used to control the order that the LDP
         policies are applied. If multiple entries exist in this table
         with the same vRtrID and vRtrLdpPolicyType indexes, they are
         evaluated in ascending numeric order of vRtrLdpPolicyIndex
         (gaps are allowed). The first policy that matches is applied.

         This object is obsoleted in release 2.1."
    ::= { vRtrLdpPolicyEntry 2 }

vRtrLdpPolicyRowStatus    OBJECT-TYPE
    SYNTAX      RowStatus
    MAX-ACCESS  read-create
    STATUS      obsolete
    DESCRIPTION
        "vRtrLdpPolicyRowStatus controls the creation and deletion of
         rows in the vRtrLdpPolicyTable.

         This object is obsoleted in release 2.1."
    ::= { vRtrLdpPolicyEntry 3 }

vRtrLdpPolicyName    OBJECT-TYPE
    SYNTAX      TPolicyStatementNameOrEmpty
    MAX-ACCESS  read-create
    STATUS      obsolete
    DESCRIPTION
        "The value of vRtrLdpPolicyName is the name of the policy filter
         to be used.  If this object has the value of the empty string,
         ''H, there is no policy specified at this level.

         This object is obsoleted in release 2.1."
    DEFVAL { ''H }
    ::= { vRtrLdpPolicyEntry 4 }

--
--  LDP Interface/Targeted Peer Table
--

vRtrLdpIfTableSpinlock    OBJECT-TYPE
    SYNTAX      TestAndIncr
    MAX-ACCESS  read-write
    STATUS      current
    DESCRIPTION
        "Voluntary serialization control for vRtrLdpIfTable.
         Primarily used by SNMP manager to coordinate changes to
         vRtrLdpIfInheritance."
    DEFVAL { 0 }
    ::= { tmnxLdpObjs 4 }

vRtrLdpIfTable    OBJECT-TYPE
    SYNTAX      SEQUENCE OF VRtrLdpIfEntry
    MAX-ACCESS  not-accessible
    STATUS      current
    DESCRIPTION
        "vRtrLdpIfTable provides an entry for each virtual router
         interface or targeted peer configured to be used with the Label
         Distribution Protocol (LDP)."
    ::= { tmnxLdpObjs 5 }

vRtrLdpIfEntry    OBJECT-TYPE
    SYNTAX      VRtrLdpIfEntry
    MAX-ACCESS  not-accessible
    STATUS      current
    DESCRIPTION
        "Each row entry represents an interface on this virtual router
         that participates in the LDP protocol.

         Row entries can be created or deleted via SNMP SET requests.
         A row with default attribute values is created by setting
         vRtrLdpIfRowStatus to 'createAndGo'. A row entry can be
         destroyed by setting vRtrLdpIfRowStatus to 'destroy'. An
         attempt to destroy a row will fail if vRtrLdpIfAdminState
         is not set to 'outOfService'."
   INDEX  { vRtrID,
            vRtrLdpIfIndex,
            vRtrLdpPeerAddress }
   ::= { vRtrLdpIfTable 1 }

VRtrLdpIfEntry ::= SEQUENCE {
    vRtrLdpIfIndex                  InterfaceIndexOrZero,
    vRtrLdpPeerAddress              IpAddress,
    vRtrLdpIfRowStatus              RowStatus,
    vRtrLdpIfLastChange             TimeStamp,
    vRtrLdpIfAdminState             TmnxAdminState,
    vRtrLdpIfOperState              TmnxOperState,
    vRtrLdpIfInheritance            Unsigned32,
    vRtrLdpIfKeepAliveFactor        TmnxLdpKeepAliveFactor,
    vRtrLdpIfKeepAliveTimeout       TmnxLdpKeepAliveTimeout,
    vRtrLdpIfHelloFactor            TmnxLdpHelloFactor,
    vRtrLdpIfHelloTimeout           TmnxLdpHelloTimeout,
    vRtrLdpIfBackoffTime            TmnxLdpBackoffTime,
    vRtrLdpIfMaxBackoffTime         TmnxLdpBackoffTime,
    vRtrLdpIfTransportAddrType      INTEGER,
    vRtrLdpIfPassiveMode            TruthValue,
    vRtrLdpIfAutoCreate             TruthValue,
    vRtrLdpIfOperDownReason         TmnxLdpIntTargOperDownReasonCode,
    vRtrLdpIfTunneling              TruthValue
}

vRtrLdpIfIndex    OBJECT-TYPE
    SYNTAX      InterfaceIndexOrZero
    MAX-ACCESS  not-accessible
    STATUS      current
    DESCRIPTION
        "vRtrLdpIfIndex is an index for the row entry and is used
         mutually exclusively with the vRtrLdpPeerAddress field. If
         the vRtrLdpPeerAddress field is 0.0.0.0, then vRtrLdpIfIndex
         is the index for the interface on the virtual router and
         must be non-zero. Otherwise, vRtrLdpPeerAddress refers to
         a targeted peer and its vRtrLdpIfIndex is 0."
    ::= { vRtrLdpIfEntry 1 }

vRtrLdpPeerAddress    OBJECT-TYPE
    SYNTAX      IpAddress
    MAX-ACCESS  not-accessible
    STATUS      current
    DESCRIPTION
        "vRtrLdpPeerAddress is an index for the row entry and is used
         mutually exclusively with the vRtrLdpIfIndex field. If the
         vRtrLdpIfIndex field is 0, then the vRtrLdpPeerAddress is the
         IP address of the targeted peer and must be non-zero.
         Otherwise, vRtrLdpIfIndex refers to the LDP interface index
         and its vRtrLdpPeerAddress is 0.0.0.0"
    ::= { vRtrLdpIfEntry 2 }

vRtrLdpIfRowStatus    OBJECT-TYPE
    SYNTAX      RowStatus
    MAX-ACCESS  read-create
    STATUS      current
    DESCRIPTION
        "vRtrLdpIfRowStatus is used to control the creation and deletion
         of rows in the vRtrLdpIfTable.

         A row can be created by setting vRtrLdpIfRowStatus to 'createAndGo'.
         The agent should assign the default attribute values and change
         the row status to 'active'.

         A row entry can be destroyed by setting vRtrLdpIfRowStatus to
         'destroy'. An attempt to destroy a row will fail if
         vRtrLdpIfAdminState is not set to 'outOfService'."
    ::= { vRtrLdpIfEntry 3 }

vRtrLdpIfLastChange    OBJECT-TYPE
    SYNTAX      TimeStamp
    MAX-ACCESS  read-only
    STATUS      current
    DESCRIPTION
        "The value of vRtrLdpIfLastChange specifies the sysUpTime when this
         row was last modified."
    ::= { vRtrLdpIfEntry 4 }

vRtrLdpIfAdminState    OBJECT-TYPE
    SYNTAX      TmnxAdminState
    MAX-ACCESS  read-create
    STATUS      current
    DESCRIPTION
        "The value of vRtrLdpIfAdminState indicates the desired administrative
         state for LDP on this interface or targeted peer."
    DEFVAL { inService }
    ::= { vRtrLdpIfEntry 5 }

vRtrLdpIfOperState    OBJECT-TYPE
    SYNTAX      TmnxOperState
    MAX-ACCESS  read-only
    STATUS      current
    DESCRIPTION
        "The value of vRtrLdpIfOperState specifies the current operational
         state of LDP on this interface or targeted peer."
    ::= { vRtrLdpIfEntry 6 }

vRtrLdpIfInheritance    OBJECT-TYPE
    SYNTAX      Unsigned32
    MAX-ACCESS  read-create
    STATUS      current
    DESCRIPTION
        "Some writable object in this row that can be configured to
         inherit its value from its corresponding object in the
         vRtrLdpGeneralTable for LDP interfaces or from the corresponding
         object in the vRtrLdpIfTable for targeted peers.
         vRtrLdpIfInheritance controls whether to inherit the operational
         value of that object, or use the administratively set value.

         This object is a bit-mask, with the following positions:
         vRtrLdpIfKeepAliveFactor       0x1
         vRtrLdpIfKeepAliveTimeout      0x2
         vRtrLdpIfHelloFactor           0x4
         vRtrLdpIfHelloTimeout          0x8
         vRtrLdpIfBackoffTime           0x10
         vRtrLdpIfMaxBackoffTime        0x20
         vRtrLdpIfTransportAddrType     0x40
         vRtrLdpIfPassiveMode           0x80

         When the bit for an object is set to one, then the object's
         administrative and operational value are whatever the DEFVAL
         or most recently SET value is.

         When the bit for an object is set to zero, then the object's
         administrative and operational value are inherited from the
         corresponding object in vRtrLdpGeneralTable for LDP interfaces
         or the vRtrLdpIfTable for targeted peers."
    DEFVAL { 0 } -- by default inherit everything
    ::= { vRtrLdpIfEntry 7 }

vRtrLdpIfKeepAliveFactor    OBJECT-TYPE
    SYNTAX      TmnxLdpKeepAliveFactor
    MAX-ACCESS  read-create
    STATUS      current
    DESCRIPTION
        "The value of vRtrLdpIfKeepAliveFactor specifies the value by which
         the keepalive timeout (vRtrLdpIfKeepAliveTimeout) should be divided
         to give the keepalive time i.e. the time interval, in seconds,
         between LDP keepalive messages. LDP keepalive messages are sent to
         keep the LDP session from timing out when no other LDP traffic is
         being sent between the neighbors."
    DEFVAL { 3 }
    ::= { vRtrLdpIfEntry 8 }

vRtrLdpIfKeepAliveTimeout    OBJECT-TYPE
    SYNTAX      TmnxLdpKeepAliveTimeout
    UNITS       "seconds"
    MAX-ACCESS  read-create
    STATUS      current
    DESCRIPTION
        "The value of vRtrLdpIfKeepAliveTimeout specifies the time interval,
         in seconds, that LDP waits before tearing down a session. If no LDP
         messages are exchanged during this time interval, the LDP session
         is torn down. Generally the value of vRtrLdpIfKeepAliveTimeout is
         configured to be 3 times the keepalive time (the time interval
         between successive LDP keepalive messages)."
    DEFVAL { 30 }
    ::= { vRtrLdpIfEntry 9 }

vRtrLdpIfHelloFactor    OBJECT-TYPE
    SYNTAX      TmnxLdpHelloFactor
    UNITS       "seconds"
    MAX-ACCESS  read-create
    STATUS      current
    DESCRIPTION
        "The value of vRtrLdpIfHelloFactor specifies the value by which
         the hello timeout (vRtrLdpIfHelloTimeout) should be divided to
         give the hello time i.e. the time interval, in seconds, between
         LDP Hello messages. LDP uses hello messages to discover neighbors
         and to detect loss of connectivity with its neighbors."
    DEFVAL { 3 }
    ::= { vRtrLdpIfEntry 10 }

vRtrLdpIfHelloTimeout    OBJECT-TYPE
    SYNTAX      TmnxLdpHelloTimeout
    UNITS       "seconds"
    MAX-ACCESS  read-create
    STATUS      current
    DESCRIPTION
        "The value of vRtrLdpIfHelloTimeout specifies the hello time also
         known as hold time. It is the time interval, in seconds, that
         LDP waits before declaring a neighbor to be down. Hello timeout
         is local to the system and is sent in the hello messages to a
         neighbor. Hello timeout cannot be set to a value that is less
         than 3 times the hello time."
    DEFVAL { 15 }
    ::= { vRtrLdpIfEntry 11 }

vRtrLdpIfBackoffTime    OBJECT-TYPE
    SYNTAX      TmnxLdpBackoffTime (1..2592000)
    UNITS       "seconds"
    MAX-ACCESS  read-create
    STATUS      current
    DESCRIPTION
        "The value of vRtrLdpIfBackoffTime specifies the initial value
         for the backoff interval.

         The backoff interval is the time, in seconds, that LDP waits
         after an LDP session setup has failed before it attempts to
         setup the session again. After the LDP session startup fails
         the first time, the backoff interval is set to the value of
         vRtrLdpIfBackoffTime. Thereafter, if session startup fails
         again the backoff interval increases exponentially."
    DEFVAL { 15 }
    ::= { vRtrLdpIfEntry 12 }

vRtrLdpIfMaxBackoffTime    OBJECT-TYPE
    SYNTAX      TmnxLdpBackoffTime
    UNITS       "seconds"
    MAX-ACCESS  read-create
    STATUS      current
    DESCRIPTION
        "The value of vRtrLdpIfMaxBackoffTime specifies the maximum
         value for the backoff interval.

         For each successive failure of the LDP session startup, the
         backoff interval (the time for which the router waits before
         retrying) increases exponentially. If the backoff interval
         exceeds vRtrLdpIfMaxBackoffTime, the router will give
         up trying to establish the LDP session.

         If vRtrLdpIfMaxBackoffTime is set to zero (0), then the
         backoff interval does not increase exponentially after the
         first session startup attempt fails. Instead it remains
         constant and LDP will keep retrying to establish a session
         until it succeeds."
    DEFVAL { 120 }
    ::= { vRtrLdpIfEntry 13 }

vRtrLdpIfTransportAddrType    OBJECT-TYPE
    SYNTAX      INTEGER {
                    interface (1),
                    system (2)
                }
    MAX-ACCESS  read-create
    STATUS      current
    DESCRIPTION
       "The value of vRtrLdpIfTransportAddrType specifies the source
        of the transport address to be used when setting up the LDP TCP
        sessions. This value is meaningful only in case of LDP
        interfaces and not for targeted peers.

        When the value of this object is 'interface', the interface's
        IP address is used to setup the LDP session between neighbors.
        If multiple interfaces exist between two neighbors, the
        'interface' mode cannot be used since only one LDP session is
        actually set up between the two neighbors.

        When the value of this object is 'system', the system's IP address
        is used to set up the LDP session between neighbors."
    DEFVAL { system }
    ::= { vRtrLdpIfEntry 14 }

vRtrLdpIfPassiveMode    OBJECT-TYPE
    SYNTAX      TruthValue
    MAX-ACCESS  read-create
    STATUS      current
    DESCRIPTION
        "The value of vRtrLdpIfPassiveMode specifies the mode used for
         setting up LDP sessions. This object is meaningful only in case
         of LDP targeted peers and not for interfaces. When it has a
         value of 'true', LDP responds only when it gets a connect request
         from a peer and will not attempt to actively connect to its
         neighbors. When it has a value of 'false', LDP actively tries to
         connect to its peers."
    DEFVAL { false }
    ::= { vRtrLdpIfEntry 15 }

vRtrLdpIfAutoCreate    OBJECT-TYPE
    SYNTAX      TruthValue
    MAX-ACCESS  read-only
    STATUS      current
    DESCRIPTION
        "The value of vRtrLdpIfAutoCreate specifies whether or not the
         row entry represents a targeted peer that was automatically
         created through Service Manager.  For an LDP interface, this
         value is always false."
    ::= { vRtrLdpIfEntry 16 }

vRtrLdpIfOperDownReason    OBJECT-TYPE
    SYNTAX      TmnxLdpIntTargOperDownReasonCode
    MAX-ACCESS  read-only
    STATUS      current
    DESCRIPTION
        "The value of vRtrLdpIfOperDownReason specifies the reason
         that the LDP interface or targeted peer is operationally
         down."
    ::= { vRtrLdpIfEntry 17 }

vRtrLdpIfTunneling  OBJECT-TYPE
     SYNTAX      TruthValue
     MAX-ACCESS  read-create
     STATUS      current
     DESCRIPTION
         "The value of vRtrLdpIfTunneling specifies whether tunneling
          of LDP over tunnels is enabled.  When this object has a value of
          'true', tunneling is enabled.  When its value is 'false',
           tunneling is disabled."
     DEFVAL { false }
     ::= { vRtrLdpIfEntry 18 }

--
-- LDP Interface/Targeted Peer Statistics Table
--

vRtrLdpIfStatsTable    OBJECT-TYPE
    SYNTAX      SEQUENCE OF VRtrLdpIfStatsEntry
    MAX-ACCESS  not-accessible
    STATUS      current
    DESCRIPTION
        "vRtrLdpIfStatsTable is a read-only table. The purpose of this
         table is to keep statistical information about the LDP Interfaces
         and Targeted peers on the LSR.

         Use of AUGMENTS clause implies a one-to-one dependent relationship
         between the base table, vRtrLdpIfTable, and the augmenting table,
         vRtrLdpIfStatsTable. This in effect extends the vRtrLdpIfTable
         with additional columns. Creation or deletion of a row in the
         vRtrLdpIfTable results in the same fate for the row in the
         vRtrLdpIfStatsTable."
    ::= { tmnxLdpObjs 6 }

vRtrLdpIfStatsEntry OBJECT-TYPE
    SYNTAX      VRtrLdpIfStatsEntry
    MAX-ACCESS  not-accessible
    STATUS      current
    DESCRIPTION
        "A row in this table contains statistical information about an LDP
        Interface or Targeted peer.

        Some counters contained in a row are for fatal errors received
        during a former LDP Session associated with this entry. For example,
        an LDP Pdu received on a TCP connection during an LDP Session
        contains a fatal error.  That error is counted here, because the
        session is terminated.

        If the error is NOT fatal (i.e. and the Session remains), then the
        error is counted in the vRtrLdpSessionStatsEntry."
    AUGMENTS  { vRtrLdpIfEntry }
    ::= { vRtrLdpIfStatsTable 1 }

VRtrLdpIfStatsEntry ::= SEQUENCE {
    vRtrLdpIfExistingAdjacencies                Gauge32
}

vRtrLdpIfExistingAdjacencies    OBJECT-TYPE
    SYNTAX      Gauge32
    MAX-ACCESS  read-only
    STATUS      current
    DESCRIPTION
        "The value of vRtrLdpIfExistingAdjacencies gives a count of the total
         active adjacencies on this LDP interface or with this targeted peer."
    ::= { vRtrLdpIfStatsEntry 1 }


--
-- LDP Hello Adjacency Table
--

vRtrLdpHelloAdjTable    OBJECT-TYPE
    SYNTAX      SEQUENCE OF VRtrLdpHelloAdjEntry
    MAX-ACCESS  not-accessible
    STATUS      current
    DESCRIPTION
        "vRtrLdpHelloAdjTable is a read-only table. The purpose of this
         table is to keep information about Hello Adjacencies for Sessions.
         A hello adjacency can be associated with an LDP interface or with
         a targeted peer. The index includes both the interface index and
         the peer IP address thus referring to the LDP interface or
         targeted peer."
    ::= { tmnxLdpObjs 7 }

vRtrLdpHelloAdjEntry    OBJECT-TYPE
    SYNTAX      VRtrLdpHelloAdjEntry
    MAX-ACCESS  not-accessible
    STATUS      current
    DESCRIPTION
        "Each row represents a single LDP Hello Adjacency. An LDP Session
         can have one or more Hello adjacencies."
    INDEX  { vRtrID,
             vRtrLdpPeerLdpId,
             vRtrLdpIfIndex,
             vRtrLdpPeerAddress }
    ::= { vRtrLdpHelloAdjTable 1 }

VRtrLdpHelloAdjEntry ::= SEQUENCE {
    vRtrLdpPeerLdpId                            MplsLdpIdentifier,
    vRtrLdpHelloAdjLocalLdpId                   MplsLdpIdentifier,
    vRtrLdpHelloAdjEntityIndex                  Unsigned32,
    vRtrLdpHelloAdjIndex                        Unsigned32,
    vRtrLdpHelloAdjHoldTimeRemaining            Unsigned32,
    vRtrLdpHelloAdjType                         TmnxLdpAdjacencyType,
    vRtrLdpHelloAdjRemoteConfSeqNum             Unsigned32,
    vRtrLdpHelloAdjRemoteIpAddress              IpAddress,
    vRtrLdpHelloAdjUpTime                       TimeInterval,
    vRtrLdpHelloAdjLocalConfSeqNum              Unsigned32,
    vRtrLdpHelloAdjLocalIpAddress               IpAddress,
    vRtrLdpHelloAdjInHelloMsgCount              Counter32,
    vRtrLdpHelloAdjOutHelloMsgCount             Counter32,
    vRtrLdpHelloAdjLocalHelloTimeout            TmnxLdpHelloTimeout,
    vRtrLdpHelloAdjRemoteHelloTimeout           TmnxLdpHelloTimeout
}

vRtrLdpPeerLdpId    OBJECT-TYPE
    SYNTAX      MplsLdpIdentifier
    MAX-ACCESS  not-accessible
    STATUS      current
    DESCRIPTION
        "vRtrLdpPeerLdpId is an index for the row entry. It specifies the
         LDP identifier of the peer."
    ::= { vRtrLdpHelloAdjEntry 1 }

vRtrLdpHelloAdjLocalLdpId    OBJECT-TYPE
    SYNTAX      MplsLdpIdentifier
    MAX-ACCESS  read-only
    STATUS      current
    DESCRIPTION
        "The value of vRtrLdpHelloAdjLocalLdpId specifies the local LDP
         identifier for this specific adjacency."
    ::= { vRtrLdpHelloAdjEntry 2 }

vRtrLdpHelloAdjEntityIndex    OBJECT-TYPE
    SYNTAX      Unsigned32 (1..4294967295)
    MAX-ACCESS  read-only
    STATUS      current
    DESCRIPTION
        "The value of vRtrLdpHelloAdjEntityIndex specifies the Entity index
         which is an index for the mplsLdpHelloAdjacencyEntry defined
         in MPLS-LDP-MIB."
    ::= { vRtrLdpHelloAdjEntry 3 }

vRtrLdpHelloAdjIndex    OBJECT-TYPE
    SYNTAX      Unsigned32 (1..4294967295)
    MAX-ACCESS  read-only
    STATUS      current
    DESCRIPTION
        "The value of vRtrLdpHelloAdjIndex gives the Hello adjacency index
         which is an index for the mplsLdpHelloAdjacencyEntry defined
         in MPLS-LDP-MIB."
    ::= { vRtrLdpHelloAdjEntry 4 }

vRtrLdpHelloAdjHoldTimeRemaining    OBJECT-TYPE
    SYNTAX      Unsigned32
    UNITS       "seconds"
    MAX-ACCESS  read-only
    STATUS      current
    DESCRIPTION
        "The value of vRtrLdpHelloAdjHoldTimeRemaining specifies the hold
         time remaining for this Hello Adjacency. This interval will change
         when the next Hello message which corresponds to this Hello
         Adjacency is received."
    ::= { vRtrLdpHelloAdjEntry 5 }

vRtrLdpHelloAdjType    OBJECT-TYPE
    SYNTAX      TmnxLdpAdjacencyType
    MAX-ACCESS  read-only
    STATUS      current
    DESCRIPTION
        "The value of vRtrLdpHelloAdjType specifies the type of this Hello
         Adjacency. If this value is 'link' then this adjacency is a result
         of a Link Hello. If this value is 'hello', then the adjacency is a
         result of a Targeted Hello."
    ::= { vRtrLdpHelloAdjEntry 6 }

vRtrLdpHelloAdjRemoteConfSeqNum    OBJECT-TYPE
    SYNTAX      Unsigned32
    MAX-ACCESS  read-only
    STATUS      current
    DESCRIPTION
        "The value of vRtrLdpHelloAdjRemoteConfSeqNum specifies the
         Configuration sequence number that was in the Hello received when
         this adjacency started up. This configuration sequence number
         changes when there is a change of configuration."
    ::= { vRtrLdpHelloAdjEntry 7 }

vRtrLdpHelloAdjRemoteIpAddress    OBJECT-TYPE
    SYNTAX      IpAddress
    MAX-ACCESS  read-only
    STATUS      current
    DESCRIPTION
        "The value of vRtrLdpHelloAdjRemoteIpAddress specifies the peer
         IP address of the interface/targeted session that sent hellos
         for this specific adjacency."
    ::= { vRtrLdpHelloAdjEntry 8 }

vRtrLdpHelloAdjUpTime    OBJECT-TYPE
    SYNTAX      TimeInterval
    MAX-ACCESS  read-only
    STATUS      current
    DESCRIPTION
        "The value of vRtrLdpHelloAdjUpTime specifies the time, in hundreds
         of seconds, that this adjacency has been up."
    ::= { vRtrLdpHelloAdjEntry 9 }

vRtrLdpHelloAdjLocalConfSeqNum    OBJECT-TYPE
    SYNTAX      Unsigned32
    MAX-ACCESS  read-only
    STATUS      current
    DESCRIPTION
        "The value of vRtrLdpHelloAdjLocalConfSeqNum specifies the
         Configuration sequence number that was used in the Hello sent
         when this adjacency started up. This configuration sequence
         number changes when there is a change of configuration."
    ::= { vRtrLdpHelloAdjEntry 10 }

vRtrLdpHelloAdjLocalIpAddress    OBJECT-TYPE
    SYNTAX      IpAddress
    MAX-ACCESS  read-only
    STATUS      current
    DESCRIPTION
        "The value of vRtrLdpHelloAdjLocalIpAddress specifies the local
         IP address of the interface/targeted session used in Hellos sent
         for this specific adjacency."
    ::= { vRtrLdpHelloAdjEntry 11 }

vRtrLdpHelloAdjInHelloMsgCount    OBJECT-TYPE
    SYNTAX      Counter32
    MAX-ACCESS  read-only
    STATUS      current
    DESCRIPTION
        "The value of vRtrLdpHelloAdjInHelloMsgCount specifies the number
         of Hello messages that have been received for this adjacency."
    ::= { vRtrLdpHelloAdjEntry 12 }

vRtrLdpHelloAdjOutHelloMsgCount    OBJECT-TYPE
    SYNTAX      Counter32
    MAX-ACCESS  read-only
    STATUS      current
    DESCRIPTION
        "The value of vRtrLdpHelloAdjOutHelloMsgCount specifies the number
         of Hello messages that have been sent for this adjacency."
    ::= { vRtrLdpHelloAdjEntry 13 }

vRtrLdpHelloAdjLocalHelloTimeout    OBJECT-TYPE
    SYNTAX      TmnxLdpHelloTimeout
    MAX-ACCESS  read-only
    STATUS      current
    DESCRIPTION
        "The value of vRtrLdpHelloAdjLocalHelloTimeout specifies the hello
         timeout used in the Hellos sent for this specific adjacency."
    ::= { vRtrLdpHelloAdjEntry 14 }

vRtrLdpHelloAdjRemoteHelloTimeout    OBJECT-TYPE
    SYNTAX      TmnxLdpHelloTimeout
    MAX-ACCESS  read-only
    STATUS      current
    DESCRIPTION
        "The value of vRtrLdpHelloAdjRemoteHelloTimeout specifies the hello
         timeout used by the remote end that sent Hellos for this specific
         adjacency."
    ::= { vRtrLdpHelloAdjEntry 15 }

--
-- Alcatel 7x50 SR series Hello Adjacency Mapping Table
--

vRtrLdpHelloAdjMapTable    OBJECT-TYPE
    SYNTAX      SEQUENCE OF VRtrLdpHelloAdjMapEntry
    MAX-ACCESS  not-accessible
    STATUS      current
    DESCRIPTION
        "vRtrLdpHelloAdjMapTable is a read-only table which maps to the
         vRtrLdpHelloAdjTable. This table has the same indexes as the
         vRtrLdpHelloAdjTable but the order in which these indexes are
         specified is different for the two tables."
    ::= { tmnxLdpObjs 8 }

vRtrLdpHelloAdjMapEntry    OBJECT-TYPE
    SYNTAX      VRtrLdpHelloAdjMapEntry
    MAX-ACCESS  not-accessible
    STATUS      current
    DESCRIPTION
        "Each row represents a single LDP Hello Adjacency. An LDP Session
         can have one or more Hello adjacencies."
    INDEX  { vRtrID,
             vRtrLdpIfIndex,
             vRtrLdpPeerAddress,
             vRtrLdpHelloAdjMapLdpId }
    ::= { vRtrLdpHelloAdjMapTable 1 }

VRtrLdpHelloAdjMapEntry ::= SEQUENCE {
    vRtrLdpHelloAdjMapLdpId               MplsLdpIdentifier
}

vRtrLdpHelloAdjMapLdpId    OBJECT-TYPE
    SYNTAX      MplsLdpIdentifier
    MAX-ACCESS  read-only
    STATUS      current
    DESCRIPTION
        "vRtrLdpHelloAdjMapLdpId is an index for the row entry. It specifies
         the LDP identifier of the peer."
    ::= { vRtrLdpHelloAdjMapEntry 1 }


--
-- LDP Session Table
--

vRtrLdpSessionTable    OBJECT-TYPE
    SYNTAX      SEQUENCE OF VRtrLdpSessionEntry
    MAX-ACCESS  not-accessible
    STATUS      current
    DESCRIPTION
        "vRtrLdpSessionTable is a read-only table which parallels the
         mplsLdpSessionTable in the MPLS-LDP-MIB. The purpose of this
         table is to keep information about a single session between
         an LDP entity and an LDP Peer."
    ::= { tmnxLdpObjs 9 }

vRtrLdpSessionEntry OBJECT-TYPE
    SYNTAX      VRtrLdpSessionEntry
    MAX-ACCESS  not-accessible
    STATUS      current
    DESCRIPTION
        "A row in this table represents information about a  single
         session between an LDP entity and an LDP Peer."
    INDEX  { vRtrID,
             vRtrLdpPeerLdpId }
    ::= { vRtrLdpSessionTable 1 }

VRtrLdpSessionEntry ::= SEQUENCE {
    vRtrLdpSessLocalLdpId                    MplsLdpIdentifier,
    vRtrLdpSessEntityIndex                   Unsigned32,
    vRtrLdpSessLabelDistMethod               TmnxLdpLabelDistMethod,
    vRtrLdpSessLoopDetectForPV               INTEGER,
    vRtrLdpSessPathVectorLimit               Unsigned32,
    vRtrLdpSessState                         INTEGER,
    vRtrLdpSessAdjacencyType                 TmnxLdpAdjacencyType,
    vRtrLdpSessProtocolVersion               Unsigned32,
    vRtrLdpSessLocalUdpPort                  Unsigned32,
    vRtrLdpSessPeerUdpPort                   Unsigned32,
    vRtrLdpSessLocalTcpPort                  Unsigned32,
    vRtrLdpSessPeerTcpPort                   Unsigned32,
    vRtrLdpSessLocalAddress                  IpAddress,
    vRtrLdpSessPeerAddress                   IpAddress,
    vRtrLdpSessKAHoldTimeRemaining           TimeInterval,
    vRtrLdpSessMaxPduLength                  Unsigned32,
    vRtrLdpSessUpTime                        TimeInterval,
    vRtrLdpSessLocalKATimeout                TmnxLdpKeepAliveTimeout,
    vRtrLdpSessPeerKATimeout                 TmnxLdpKeepAliveTimeout,
    vRtrLdpSessAdvertise                     INTEGER,
    vRtrLdpSessRestartHelperState            TruthValue,
    vRtrLdpSessPeerNumRestart                Counter32,
    vRtrLdpSessLastRestartTime               TimeStamp,
    vRtrLdpSessFtReconnectTimeNego           Unsigned32,
    vRtrLdpSessFtRecoveryTimeNego            Unsigned32,
    vRtrLdpSessFtReconTimeRemaining          Unsigned32,
    vRtrLdpSessFtRecovTimeRemaining          Unsigned32
}

vRtrLdpSessLocalLdpId    OBJECT-TYPE
    SYNTAX      MplsLdpIdentifier
    MAX-ACCESS  read-only
    STATUS      current
    DESCRIPTION
        "The value of vRtrLdpSessLocalLdpId specifies the local LDP
         identifier for this LDP session."
    ::= { vRtrLdpSessionEntry 1 }

vRtrLdpSessEntityIndex    OBJECT-TYPE
    SYNTAX      Unsigned32 (1..4294967295)
    MAX-ACCESS  read-only
    STATUS      current
    DESCRIPTION
        "The value of vRtrLdpSessEntityIndex specifies the Entity index
         for the LDP entity represented in this session."
    ::= { vRtrLdpSessionEntry 2 }

vRtrLdpSessLabelDistMethod    OBJECT-TYPE
    SYNTAX      TmnxLdpLabelDistMethod
    MAX-ACCESS  read-only
    STATUS      current
    DESCRIPTION
        "The value of vRtrLdpSessLabelDistMethod specifies the label
         distribution method used for this LDP session."
    ::= { vRtrLdpSessionEntry 3 }

vRtrLdpSessLoopDetectForPV    OBJECT-TYPE
    SYNTAX      INTEGER {
                    disabled(0),
                    enabled(1)
                }
    MAX-ACCESS  read-only
    STATUS      current
    DESCRIPTION
        "The value of vRtrLdpSessLoopDetectForPV indicates whether
         loop detection based on path vectors is disabled or enabled
         for this LDP session.

         If this object has a value of disabled(0), then loop detection
         is disabled.  Otherwise, if this object has a value of enabled(1),
         then loop detection based on path vectors is enabled."
    ::= { vRtrLdpSessionEntry 4 }

vRtrLdpSessPathVectorLimit    OBJECT-TYPE
    SYNTAX      Unsigned32 (0..255)
    MAX-ACCESS  read-only
    STATUS      current
    DESCRIPTION
        "If the value of vRtrLdpSessLoopDetectForPV for this entry
         is 'enabled', then the value of vRtrLdpSessPathVectorLimit
         represents the Path Vector Limit for this LDP Session.

         If the value of vRtrLdpSessLoopDetectForPV for this entry
         is 'disabled', then the value of vRtrLdpSessPathVectorLimit
         be 0 (zero)."
    ::= { vRtrLdpSessionEntry 5 }

vRtrLdpSessState    OBJECT-TYPE
    SYNTAX      INTEGER {
                    nonexistent(1),
                    initialized(2),
                    openrec(3),
                    opensent(4),
                    operational(5)
                }
    MAX-ACCESS  read-only
    STATUS      current
    DESCRIPTION
        "The value of vRtrLdpSessState specifies the current state
         of the LDP session. All of the states 1 - 5 are based on the
         state machine for session negotiation behavior."
    ::= { vRtrLdpSessionEntry 6 }

vRtrLdpSessAdjacencyType    OBJECT-TYPE
    SYNTAX      TmnxLdpAdjacencyType
    MAX-ACCESS  read-only
    STATUS      current
    DESCRIPTION
        "The value of vRtrLdpSessAdjacencyType specifies the adjacency
         type(s) supporting this LDP Session."
    ::= { vRtrLdpSessionEntry 7 }

vRtrLdpSessProtocolVersion    OBJECT-TYPE
    SYNTAX      Unsigned32
    MAX-ACCESS  read-only
    STATUS      current
    DESCRIPTION
        "The value of vRtrLdpSessProtocolVersion specifies the version
         of the LDP Protocol used by this session."
    ::= { vRtrLdpSessionEntry 8 }

vRtrLdpSessLocalUdpPort    OBJECT-TYPE
    SYNTAX      Unsigned32 (0..65535)
    MAX-ACCESS  read-only
    STATUS      current
    DESCRIPTION
        "The value of vRtrLdpSessLocalUdpPort specifies the UDP port
         used locally for LDP discovery."
    ::= { vRtrLdpSessionEntry 9 }

vRtrLdpSessPeerUdpPort    OBJECT-TYPE
    SYNTAX      Unsigned32 (0..65535)
    MAX-ACCESS  read-only
    STATUS      current
    DESCRIPTION
        "The value of vRtrLdpSessPeerUdpPort specifies the UDP port
         used on the remote end for LDP discovery."
    ::= { vRtrLdpSessionEntry 10 }

vRtrLdpSessLocalTcpPort    OBJECT-TYPE
    SYNTAX      Unsigned32 (0..65535)
    MAX-ACCESS  read-only
    STATUS      current
    DESCRIPTION
        "The value of vRtrLdpSessLocalTcpPort specifies the TCP port
         used locally for the LDP Session."
    ::= { vRtrLdpSessionEntry 11 }

vRtrLdpSessPeerTcpPort    OBJECT-TYPE
    SYNTAX      Unsigned32 (0..65535)
    MAX-ACCESS  read-only
    STATUS      current
    DESCRIPTION
        "The value of vRtrLdpSessPeerTcpPort specifies the TCP port
         used on the remote end for the LDP Session."
    ::= { vRtrLdpSessionEntry 12 }

vRtrLdpSessLocalAddress    OBJECT-TYPE
    SYNTAX      IpAddress
    MAX-ACCESS  read-only
    STATUS      current
    DESCRIPTION
        "The value of vRtrLdpSessLocalAddress specifies the IP address
         used locally for the LDP Session."
    ::= { vRtrLdpSessionEntry 13 }

vRtrLdpSessPeerAddress    OBJECT-TYPE
    SYNTAX      IpAddress
    MAX-ACCESS  read-only
    STATUS      current
    DESCRIPTION
        "The value of vRtrLdpSessPeerAddress specifies the IP address
         used on the remote end for the LDP Session."
    ::= { vRtrLdpSessionEntry 14 }

vRtrLdpSessKAHoldTimeRemaining    OBJECT-TYPE
    SYNTAX      TimeInterval
    MAX-ACCESS  read-only
    STATUS      current
    DESCRIPTION
        "The value of vRtrLdpSessKAHoldTimeRemaining specifies the
         keep alive hold time remaining, in hundredths of seconds, for
         this LDP session."
    ::= { vRtrLdpSessionEntry 15 }

vRtrLdpSessMaxPduLength    OBJECT-TYPE
    SYNTAX      Unsigned32 (1..65535)
    MAX-ACCESS  read-only
    STATUS      current
    DESCRIPTION
        "The value of vRtrLdpSessMaxPduLength specifies the maximum
         allowable length for LDP PDUs for this session. This value may
         have been negotiated during Session Initialization."
    ::= { vRtrLdpSessionEntry 16 }

vRtrLdpSessUpTime    OBJECT-TYPE
    SYNTAX      TimeInterval
    MAX-ACCESS  read-only
    STATUS      current
    DESCRIPTION
        "The value of vRtrLdpSessUpTime specifies the time, in hundreds
         of seconds, since the session was established."
    ::= { vRtrLdpSessionEntry 17 }

vRtrLdpSessLocalKATimeout    OBJECT-TYPE
    SYNTAX      TmnxLdpKeepAliveTimeout
    MAX-ACCESS  read-only
    STATUS      current
    DESCRIPTION
        "The value of vRtrLdpSessLocalKATimeout specifies the keepalive
         timeout used locally for the LDP Session."
    ::= { vRtrLdpSessionEntry 18 }

vRtrLdpSessPeerKATimeout    OBJECT-TYPE
    SYNTAX      TmnxLdpKeepAliveTimeout
    MAX-ACCESS  read-only
    STATUS      current
    DESCRIPTION
        "The value of vRtrLdpSessPeerKATimeout specifies the keepalive
         timeout used at the remote end of the LDP Session."
    ::= { vRtrLdpSessionEntry 19 }

vRtrLdpSessAdvertise    OBJECT-TYPE
    SYNTAX      INTEGER {
                   address (1),
                   service (2),
                   addressAndService (3)
                }
    MAX-ACCESS  read-only
    STATUS      current
    DESCRIPTION
        "The value of vRtrLdpSessAdvertise indicates the type of FECs
         that will be transported by the session."
    ::= { vRtrLdpSessionEntry 20 }

vRtrLdpSessRestartHelperState    OBJECT-TYPE
    SYNTAX      TruthValue
    MAX-ACCESS  read-only
    STATUS      current
    DESCRIPTION
        "The value of vRtrLdpSessRestartHelperState indicates whether the
         entity session is capable of supporting graceful restart.  This is
         negotiated between peers during the session initialization setup."
    ::= { vRtrLdpSessionEntry 21 }

vRtrLdpSessPeerNumRestart    OBJECT-TYPE
    SYNTAX      Counter32
    MAX-ACCESS  read-only
    STATUS      current
    DESCRIPTION
        "The value of vRtrLdpSessPeerNumRestart indicates the number of
         times graceful restart helper was initiated for this session."
    ::= { vRtrLdpSessionEntry 22 }

vRtrLdpSessLastRestartTime    OBJECT-TYPE
    SYNTAX      TimeStamp
    MAX-ACCESS  read-only
    STATUS      current
    DESCRIPTION
        "The value of vRtrLdpSessLastRestartTime indicates the last time
         graceful restart helper was initiated."
    ::= { vRtrLdpSessionEntry 23 }

vRtrLdpSessFtReconnectTimeNego OBJECT-TYPE
    SYNTAX      Unsigned32
    UNITS       "seconds"
    MAX-ACCESS  read-only
    STATUS      current
    DESCRIPTION
       "The value of vRtrLdpSessFtReconnectTimeNego indicates the session's
        Fault Tolerant(FT) Reconnect Timeout, it is set to  the lesser of
        the neighbor advertised FT Reconnect Timeout,
        vRtrLdpSessFtReconTimeRemaining and the local timer Neighbor Liveness
        Time, vRtrLdpGenGRNbrLiveTime.  It is within this period that the
        transport session is expected to re-establish, failure to do so
        will cause the teardown of the LDP session and deletion of stale
        bindings."
    ::= { vRtrLdpSessionEntry 24 }

vRtrLdpSessFtRecoveryTimeNego OBJECT-TYPE
    SYNTAX      Unsigned32
    UNITS       "seconds"
    MAX-ACCESS  read-only
    STATUS      current
    DESCRIPTION
       "The value of vRtrLdpSessFtRecoveryTimeNego indicates the session's
        Fault Tolerant(FT) recovery timeout, it is set to the lesser of the
        neighbor advertised FT recovery timeout,
        vRtrLdpSessFtRecovTimeRemaining  and the local timer
        maximum recovery time, vRtrLdpGenGRMaxRecoveryTime.  It is within
        this period that label-FEC binding message exchanges are expected
        to complete.  Any stale FEC entries left after this time will be
        deleted from the FEC table."
    ::= { vRtrLdpSessionEntry 25 }

vRtrLdpSessFtReconTimeRemaining  OBJECT-TYPE
    SYNTAX      Unsigned32
    UNITS       "seconds"
    MAX-ACCESS  read-only
    STATUS      current
    DESCRIPTION
       "The value of vRtrLdpSessFtReconTimeRemaining indicates the amount
        of time left before the session's Fault Tolerant(FT) reconnect
        timeout,vRtrLdpSessFtReconnectTimeNego expires."
    ::= { vRtrLdpSessionEntry 26 }

vRtrLdpSessFtRecovTimeRemaining OBJECT-TYPE
    SYNTAX      Unsigned32
    UNITS       "seconds"
    MAX-ACCESS  read-only
    STATUS      current
    DESCRIPTION
       "This value indicates the amount of time left before session's
        Fault Tolerant(FT) recovery timeout, vRtrLdpSessFtRecoveryTimeNego
        expires."
    ::= { vRtrLdpSessionEntry 27 }

--
-- LDP Session Statistics table
--

vRtrLdpSessionStatsTable    OBJECT-TYPE
    SYNTAX      SEQUENCE OF VRtrLdpSessionStatsEntry
    MAX-ACCESS  not-accessible
    STATUS      current
    DESCRIPTION
        "vRtrLdpSessionStatsTable is a read-only table. The purpose of this
         table is to keep statistical information about a single session
         between an LDP entity and an LDP Peer.

         Use of AUGMENTS clause implies a one-to-one dependent relationship
         between the base table, vRtrLdpSessionTable, and the augmenting
         table, vRtrLdpSessionStatsTable. This in effect extends the
         vRtrLdpSessionTable with additional columns. Creation or deletion
         of a row in the vRtrLdpSessionTable results in the same fate for
         the row in the vRtrLdpSessionStatsTable."
    ::= { tmnxLdpObjs 10 }

vRtrLdpSessionStatsEntry OBJECT-TYPE
    SYNTAX      VRtrLdpSessionStatsEntry
    MAX-ACCESS  not-accessible
    STATUS      current
    DESCRIPTION
        "A row in this table represents statistical information about a
         single session between an LDP entity and an LDP Peer."
    AUGMENTS  { vRtrLdpSessionEntry }
    ::= { vRtrLdpSessionStatsTable 1 }

VRtrLdpSessionStatsEntry ::= SEQUENCE {
    vRtrLdpSessStatsTargAdj           Gauge32,
    vRtrLdpSessStatsLinkAdj           Gauge32,
    vRtrLdpSessStatsFECRecv           Counter32,
    vRtrLdpSessStatsFECSent           Counter32,
    vRtrLdpSessStatsHelloIn           Counter32,
    vRtrLdpSessStatsHelloOut          Counter32,
    vRtrLdpSessStatsKeepaliveIn       Counter32,
    vRtrLdpSessStatsKeepaliveOut      Counter32,
    vRtrLdpSessStatsInitIn            Counter32,
    vRtrLdpSessStatsInitOut           Counter32,
    vRtrLdpSessStatsLabelMappingIn    Counter32,
    vRtrLdpSessStatsLabelMappingOut   Counter32,
    vRtrLdpSessStatsLabelRequestIn    Counter32,
    vRtrLdpSessStatsLabelRequestOut   Counter32,
    vRtrLdpSessStatsLabelReleaseIn    Counter32,
    vRtrLdpSessStatsLabelReleaseOut   Counter32,
    vRtrLdpSessStatsLabelWithdrawIn   Counter32,
    vRtrLdpSessStatsLabelWithdrawOut  Counter32,
    vRtrLdpSessStatsLabelAbortIn      Counter32,
    vRtrLdpSessStatsLabelAbortOut     Counter32,
    vRtrLdpSessStatsAddrIn            Counter32,
    vRtrLdpSessStatsAddrOut           Counter32,
    vRtrLdpSessStatsAddrWithdrawIn    Counter32,
    vRtrLdpSessStatsAddrWithdrawOut   Counter32,
    vRtrLdpSessStatsNotificationIn    Counter32,
    vRtrLdpSessStatsNotificationOut   Counter32
}

vRtrLdpSessStatsTargAdj    OBJECT-TYPE
    SYNTAX      Gauge32
    MAX-ACCESS  read-only
    STATUS      current
    DESCRIPTION
        "The value of vRtrLdpSessStatsTargAdj specifies the number of
         targeted adjacencies for this session."
    ::= { vRtrLdpSessionStatsEntry 1 }

vRtrLdpSessStatsLinkAdj    OBJECT-TYPE
    SYNTAX      Gauge32
    MAX-ACCESS  read-only
    STATUS      current
    DESCRIPTION
        "The value of vRtrLdpSessStatsLinkAdj specifies the number of
         link adjacencies for this session."
    ::= { vRtrLdpSessionStatsEntry 2 }

vRtrLdpSessStatsFECRecv    OBJECT-TYPE
    SYNTAX      Counter32
    MAX-ACCESS  read-only
    STATUS      current
    DESCRIPTION
        "The value of vRtrLdpSessStatsFECRecv counts the number of
         FECs received for this session."
    ::= { vRtrLdpSessionStatsEntry 3 }

vRtrLdpSessStatsFECSent    OBJECT-TYPE
    SYNTAX      Counter32
    MAX-ACCESS  read-only
    STATUS      current
    DESCRIPTION
        "The value of vRtrLdpSessStatsFECSent counts the number of
         FECs sent for this session."
    ::= { vRtrLdpSessionStatsEntry 4 }

vRtrLdpSessStatsHelloIn    OBJECT-TYPE
    SYNTAX      Counter32
    MAX-ACCESS  read-only
    STATUS      current
    DESCRIPTION
        "The value of vRtrLdpSessStatsHelloIn counts the number of
         Hello Messages that have been received during this session."
    ::= { vRtrLdpSessionStatsEntry 5 }

vRtrLdpSessStatsHelloOut    OBJECT-TYPE
    SYNTAX      Counter32
    MAX-ACCESS  read-only
    STATUS      current
    DESCRIPTION
        "The value of vRtrLdpSessStatsHelloOut counts the number of
         Hello Messages that have been sent during this session."
    ::= { vRtrLdpSessionStatsEntry 6 }

vRtrLdpSessStatsKeepaliveIn    OBJECT-TYPE
    SYNTAX      Counter32
    MAX-ACCESS  read-only
    STATUS      current
    DESCRIPTION
        "The value of vRtrLdpSessStatsKeepaliveIn counts the number of
         Keepalive Messages that have been received during this session."
    ::= { vRtrLdpSessionStatsEntry 7 }

vRtrLdpSessStatsKeepaliveOut    OBJECT-TYPE
    SYNTAX      Counter32
    MAX-ACCESS  read-only
    STATUS      current
    DESCRIPTION
        "The value of vRtrLdpSessStatsKeepaliveOut counts the number of
         Keepalive Messages that have been sent during this session."
    ::= { vRtrLdpSessionStatsEntry 8 }

vRtrLdpSessStatsInitIn    OBJECT-TYPE
    SYNTAX      Counter32
    MAX-ACCESS  read-only
    STATUS      current
    DESCRIPTION
        "The value of vRtrLdpSessStatsInitIn counts the number of
         Init Messages that have been received during this session."
    ::= { vRtrLdpSessionStatsEntry 9 }

vRtrLdpSessStatsInitOut    OBJECT-TYPE
    SYNTAX      Counter32
    MAX-ACCESS  read-only
    STATUS      current
    DESCRIPTION
        "The value of vRtrLdpSessStatsInitOut counts the number of
         Init Messages that have been sent during this session."
    ::= { vRtrLdpSessionStatsEntry 10 }

vRtrLdpSessStatsLabelMappingIn    OBJECT-TYPE
    SYNTAX      Counter32
    MAX-ACCESS  read-only
    STATUS      current
    DESCRIPTION
        "The value of vRtrLdpSessStatsLabelMappingIn counts the number of
         Label Mapping Messages that have been received during this session."
    ::= { vRtrLdpSessionStatsEntry 11 }

vRtrLdpSessStatsLabelMappingOut    OBJECT-TYPE
    SYNTAX      Counter32
    MAX-ACCESS  read-only
    STATUS      current
    DESCRIPTION
        "The value of vRtrLdpSessStatsLabelMappingOut counts the number of
         Label Mapping Messages that have been sent during this session."
    ::= { vRtrLdpSessionStatsEntry 12 }

vRtrLdpSessStatsLabelRequestIn    OBJECT-TYPE
    SYNTAX      Counter32
    MAX-ACCESS  read-only
    STATUS      current
    DESCRIPTION
        "The value of vRtrLdpSessStatsLabelRequestIn counts the number of
         Label Request Messages that have been received during this session."
    ::= { vRtrLdpSessionStatsEntry 13 }

vRtrLdpSessStatsLabelRequestOut    OBJECT-TYPE
    SYNTAX      Counter32
    MAX-ACCESS  read-only
    STATUS      current
    DESCRIPTION
        "The value of vRtrLdpSessStatsLabelRequestOut counts the number of
         Label Request Messages that have been sent during this session."
    ::= { vRtrLdpSessionStatsEntry 14 }

vRtrLdpSessStatsLabelReleaseIn    OBJECT-TYPE
    SYNTAX      Counter32
    MAX-ACCESS  read-only
    STATUS      current
    DESCRIPTION
        "The value of vRtrLdpSessStatsLabelReleaseIn counts the number of
         Label Release Messages that have been received during this session."
    ::= { vRtrLdpSessionStatsEntry 15 }

vRtrLdpSessStatsLabelReleaseOut    OBJECT-TYPE
    SYNTAX      Counter32
    MAX-ACCESS  read-only
    STATUS      current
    DESCRIPTION
        "The value of vRtrLdpSessStatsLabelReleaseOut counts the number of
         Label Release Messages that have been sent during this session."
    ::= { vRtrLdpSessionStatsEntry 16 }

vRtrLdpSessStatsLabelWithdrawIn    OBJECT-TYPE
    SYNTAX      Counter32
    MAX-ACCESS  read-only
    STATUS      current
    DESCRIPTION
        "The value of vRtrLdpSessStatsLabelWithdrawIn counts the number of
         Label Withdraw Messages that have been received during this session."
    ::= { vRtrLdpSessionStatsEntry 17 }

vRtrLdpSessStatsLabelWithdrawOut    OBJECT-TYPE
    SYNTAX      Counter32
    MAX-ACCESS  read-only
    STATUS      current
    DESCRIPTION
        "The value of vRtrLdpSessStatsLabelWithdrawOut counts the number of
         Label Withdraw Messages that have been sent during this session."
    ::= { vRtrLdpSessionStatsEntry 18 }

vRtrLdpSessStatsLabelAbortIn    OBJECT-TYPE
    SYNTAX      Counter32
    MAX-ACCESS  read-only
    STATUS      current
    DESCRIPTION
        "The value of vRtrLdpSessStatsLabelAbortIn counts the number of
         Label Abort Messages that have been received during this session."
    ::= { vRtrLdpSessionStatsEntry 19 }

vRtrLdpSessStatsLabelAbortOut    OBJECT-TYPE
    SYNTAX      Counter32
    MAX-ACCESS  read-only
    STATUS      current
    DESCRIPTION
        "The value of vRtrLdpSessStatsLabelAbortOut counts the number of
         Label Abort Messages that have been sent during this session."
    ::= { vRtrLdpSessionStatsEntry 20 }

vRtrLdpSessStatsAddrIn    OBJECT-TYPE
    SYNTAX      Counter32
    MAX-ACCESS  read-only
    STATUS      current
    DESCRIPTION
        "The value of vRtrLdpSessStatsAddrIn counts the number of
         Address Messages that have been received during this session."
    ::= { vRtrLdpSessionStatsEntry 21 }

vRtrLdpSessStatsAddrOut    OBJECT-TYPE
    SYNTAX      Counter32
    MAX-ACCESS  read-only
    STATUS      current
    DESCRIPTION
        "The value of vRtrLdpSessStatsAddrOut counts the number of
         Address Messages that have been sent during this session."
    ::= { vRtrLdpSessionStatsEntry 22 }

vRtrLdpSessStatsAddrWithdrawIn    OBJECT-TYPE
    SYNTAX      Counter32
    MAX-ACCESS  read-only
    STATUS      current
    DESCRIPTION
        "The value of vRtrLdpSessStatsAddrWithdrawIn counts the number of
         Address Withdraw Messages that have been received during this
         session."
    ::= { vRtrLdpSessionStatsEntry 23 }

vRtrLdpSessStatsAddrWithdrawOut    OBJECT-TYPE
    SYNTAX      Counter32
    MAX-ACCESS  read-only
    STATUS      current
    DESCRIPTION
        "The value of vRtrLdpSessStatsAddrWithdrawOut counts the number of
         Address Withdraw Messages that have been sent during this session."
    ::= { vRtrLdpSessionStatsEntry 24 }

vRtrLdpSessStatsNotificationIn    OBJECT-TYPE
    SYNTAX      Counter32
    MAX-ACCESS  read-only
    STATUS      current
    DESCRIPTION
        "The value of vRtrLdpSessStatsNotificationIn counts the number of
         Notification Messages that have been received during this session."
    ::= { vRtrLdpSessionStatsEntry 25 }

vRtrLdpSessStatsNotificationOut    OBJECT-TYPE
    SYNTAX      Counter32
    MAX-ACCESS  read-only
    STATUS      current
    DESCRIPTION
        "The value of vRtrLdpSessStatsNotificationOut counts the number of
         Notification Messages that have been sent during this session."
    ::= { vRtrLdpSessionStatsEntry 26 }


--
--  Alcatel 7x50 SR series LDP Service FEC Table
--

vRtrLdpServFecTable    OBJECT-TYPE
    SYNTAX      SEQUENCE OF VRtrLdpServFecEntry
    MAX-ACCESS  not-accessible
    STATUS      current
    DESCRIPTION
        "vRtrLdpServFecTable is a read-only table that represents all
         service FECs either sent to or received from an LDP peer known
         to the Virtual Router."
    ::= { tmnxLdpObjs 11 }

vRtrLdpServFecEntry    OBJECT-TYPE
    SYNTAX      VRtrLdpServFecEntry
    MAX-ACCESS  not-accessible
    STATUS      current
    DESCRIPTION
        "Each row entry represents an instance of a service FEC sent to
         or received from an LDP peer."
    INDEX  { vRtrID,
             vRtrLdpServFecFecType,
             vRtrLdpServFecVcType,
             vRtrLdpServFecVcId,
             vRtrLdpPeerLdpId }
    ::= { vRtrLdpServFecTable 1 }

VRtrLdpServFecEntry ::= SEQUENCE {
    vRtrLdpServFecFecType               TmnxLdpFECType,
    vRtrLdpServFecVcType                TmnxVcType,
    vRtrLdpServFecVcId                  TmnxVcId,
    vRtrLdpServFecServType              ServType,
    vRtrLdpServFecServId                TmnxServId,
    vRtrLdpServFecVpnId                 TmnxVpnId,
    vRtrLdpServFecFlags                 TmnxLdpFECFlags,
    vRtrLdpServFecNumInLabels           Unsigned32,
    vRtrLdpServFecNumOutLabels          Unsigned32,
    vRtrLdpServFecInLabel1              Unsigned32,
    vRtrLdpServFecInLabelStatus1        TmnxLabelStatus,
    vRtrLdpServFecInLabel2              Unsigned32,
    vRtrLdpServFecInLabelStatus2        TmnxLabelStatus,
    vRtrLdpServFecInLabel3              Unsigned32,
    vRtrLdpServFecInLabelStatus3        TmnxLabelStatus,
    vRtrLdpServFecInLabel4              Unsigned32,
    vRtrLdpServFecInLabelStatus4        TmnxLabelStatus,
    vRtrLdpServFecInLabel5              Unsigned32,
    vRtrLdpServFecInLabelStatus5        TmnxLabelStatus,
    vRtrLdpServFecOutLabel1             Unsigned32,
    vRtrLdpServFecOutLabelStatus1       TmnxLabelStatus,
    vRtrLdpServFecOutLabel2             Unsigned32,
    vRtrLdpServFecOutLabelStatus2       TmnxLabelStatus,
    vRtrLdpServFecOutLabel3             Unsigned32,
    vRtrLdpServFecOutLabelStatus3       TmnxLabelStatus,
    vRtrLdpServFecOutLabel4             Unsigned32,
    vRtrLdpServFecOutLabelStatus4       TmnxLabelStatus,
    vRtrLdpServFecOutLabel5             Unsigned32,
    vRtrLdpServFecOutLabelStatus5       TmnxLabelStatus,
    vRtrLdpServFecSdpId                 SdpId,
    vRtrLdpServFecLocalMTU              Unsigned32,
    vRtrLdpServFecRemoteMTU             Unsigned32,
    vRtrLdpServFecLocalVlanTag          Unsigned32,
    vRtrLdpServFecRemoteVlanTag         Unsigned32,
    vRtrLdpServFecLocalMaxCellConcat    Unsigned32,
    vRtrLdpServFecRemoteMaxCellConcat   Unsigned32,
    vRtrLdpServFecInLabelSigStatus1     TmnxLabelSigStatus,
    vRtrLdpServFecInLabelSigStatus2     TmnxLabelSigStatus,
    vRtrLdpServFecInLabelSigStatus3     TmnxLabelSigStatus,
    vRtrLdpServFecInLabelSigStatus4     TmnxLabelSigStatus,
    vRtrLdpServFecInLabelSigStatus5     TmnxLabelSigStatus,
    vRtrLdpServFecOutLabelSigStatus1    TmnxLabelSigStatus,
    vRtrLdpServFecOutLabelSigStatus2    TmnxLabelSigStatus,
    vRtrLdpServFecOutLabelSigStatus3    TmnxLabelSigStatus,
    vRtrLdpServFecOutLabelSigStatus4    TmnxLabelSigStatus,
    vRtrLdpServFecOutLabelSigStatus5    TmnxLabelSigStatus,
    vRtrLdpServFecMateEndpointVcId      TmnxVcId,
    vRtrLdpServFecMateEndpointSdpId     SdpId
}

vRtrLdpServFecFecType    OBJECT-TYPE
    SYNTAX      TmnxLdpFECType
    MAX-ACCESS  not-accessible
    STATUS      current
    DESCRIPTION
        "The value of vRtrLdpServFecFecType specifies the FEC type."
    ::= { vRtrLdpServFecEntry 1 }

vRtrLdpServFecVcType    OBJECT-TYPE
    SYNTAX      TmnxVcType
    MAX-ACCESS  not-accessible
    STATUS      current
    DESCRIPTION
        "The value of vRtrLdpServFecVcType specifies the VC type
         associated with this service FEC."
    ::= { vRtrLdpServFecEntry 2 }

vRtrLdpServFecVcId    OBJECT-TYPE
    SYNTAX      TmnxVcId
    MAX-ACCESS  not-accessible
    STATUS      current
    DESCRIPTION
        "The value of vRtrLdpServFecVcId specifies the VC identifier
         associated with this service FEC."
    ::= { vRtrLdpServFecEntry 3 }

vRtrLdpServFecServType    OBJECT-TYPE
    SYNTAX      ServType
    MAX-ACCESS  read-only
    STATUS      current
    DESCRIPTION
        "The value of vRtrLdpServFecServType specifies the Service type
         associated with this service FEC."
    ::= { vRtrLdpServFecEntry 4 }

vRtrLdpServFecServId    OBJECT-TYPE
    SYNTAX      TmnxServId (1..2147483647)
    MAX-ACCESS  read-only
    STATUS      current
    DESCRIPTION
        "The value of vRtrLdpServFecServId specifies the Service identifier
         associated with this service FEC."
    ::= { vRtrLdpServFecEntry 5 }

vRtrLdpServFecVpnId    OBJECT-TYPE
    SYNTAX      TmnxVpnId
    MAX-ACCESS  read-only
    STATUS      current
    DESCRIPTION
        "The value of vRtrLdpServFecVpnId identifies the VPN associated
         with the FEC."
    ::= { vRtrLdpServFecEntry 6 }

vRtrLdpServFecFlags    OBJECT-TYPE
    SYNTAX      TmnxLdpFECFlags
    MAX-ACCESS  read-only
    STATUS      current
    DESCRIPTION
        "The bit flags of vRtrLdpServFecFlags specify the characteristics
         of the FEC."
    ::= { vRtrLdpServFecEntry 7 }

vRtrLdpServFecNumInLabels    OBJECT-TYPE
    SYNTAX      Unsigned32
    MAX-ACCESS  read-only
    STATUS      current
    DESCRIPTION
        "The value of vRtrLdpServFecNumInLabels gives the number of
         labels that have been sent to the peer associated with this
         FEC. This value also indicates which of the following
         vRtrLdpServFecInLabel1 thru vRtrLdpServFecInLabel5
         entries contain valid information i.e. if the value of
         vRtrLdpServFecNumInLabels is 3 then vRtrLdpServFecInLabel1,
         vRtrLdpServFecInLabel2 and vRtrLdpServFecInLabel3 will
         contain valid label information."
    ::= { vRtrLdpServFecEntry 8 }

vRtrLdpServFecNumOutLabels    OBJECT-TYPE
    SYNTAX      Unsigned32
    MAX-ACCESS  read-only
    STATUS      current
    DESCRIPTION
        "The value of vRtrLdpServFecNumOutLabels gives the number of
         labels that have been received from the peer associated with this
         FEC. This value also indicates which of the following
         vRtrLdpServFecOutLabel1 thru vRtrLdpServFecOutLabel5
         entries contain valid information i.e. if the value of
         vRtrLdpServFecNumOutLabels is 3, then vRtrLdpServFecOutLabel1,
         vRtrLdpServFecOutLabel2 and vRtrLdpServFecOutLabel3 will
         contain valid label information."
    ::= { vRtrLdpServFecEntry 9 }

vRtrLdpServFecInLabel1    OBJECT-TYPE
    SYNTAX      Unsigned32
    MAX-ACCESS  read-only
    STATUS      current
    DESCRIPTION
        "The value of vRtrLdpServFecInLabel1 specifies the first
         ingress label exchanged"
    ::= { vRtrLdpServFecEntry 10 }

vRtrLdpServFecInLabelStatus1    OBJECT-TYPE
    SYNTAX      TmnxLabelStatus
    MAX-ACCESS  read-only
    STATUS      current
    DESCRIPTION
        "The value of vRtrLdpServFecInLabelStatus1 specifies the
         status of the ingress label 1"
    ::= { vRtrLdpServFecEntry 11 }

vRtrLdpServFecInLabel2    OBJECT-TYPE
    SYNTAX      Unsigned32
    MAX-ACCESS  read-only
    STATUS      current
    DESCRIPTION
        "The value of vRtrLdpServFecInLabel2 specifies the second
         ingress label (if at all) exchanged."
    ::= { vRtrLdpServFecEntry 12 }

vRtrLdpServFecInLabelStatus2    OBJECT-TYPE
    SYNTAX      TmnxLabelStatus
    MAX-ACCESS  read-only
    STATUS      current
    DESCRIPTION
        "The value of vRtrLdpServFecInLabelStatus2 specifies the
         status of the ingress label 2"
    ::= { vRtrLdpServFecEntry 13 }

vRtrLdpServFecInLabel3    OBJECT-TYPE
    SYNTAX      Unsigned32
    MAX-ACCESS  read-only
    STATUS      current
    DESCRIPTION
        "The value of vRtrLdpServFecInLabel3 specifies the third
         ingress label (if at all) exchanged."
    ::= { vRtrLdpServFecEntry 14 }

vRtrLdpServFecInLabelStatus3    OBJECT-TYPE
    SYNTAX      TmnxLabelStatus
    MAX-ACCESS  read-only
    STATUS      current
    DESCRIPTION
        "The value of vRtrLdpServFecInLabelStatus3 specifies the
         status of the ingress label 3"
    ::= { vRtrLdpServFecEntry 15 }

vRtrLdpServFecInLabel4    OBJECT-TYPE
    SYNTAX      Unsigned32
    MAX-ACCESS  read-only
    STATUS      current
    DESCRIPTION
        "The value of vRtrLdpServFecInLabel4 specifies the fourth
         ingress label (if at all) exchanged."
    ::= { vRtrLdpServFecEntry 16 }

vRtrLdpServFecInLabelStatus4    OBJECT-TYPE
    SYNTAX      TmnxLabelStatus
    MAX-ACCESS  read-only
    STATUS      current
    DESCRIPTION
        "The value of vRtrLdpServFecInLabelStatus4 specifies the
         status of the ingress label 4"
    ::= { vRtrLdpServFecEntry 17 }

vRtrLdpServFecInLabel5    OBJECT-TYPE
    SYNTAX      Unsigned32
    MAX-ACCESS  read-only
    STATUS      current
    DESCRIPTION
        "The value of vRtrLdpServFecInLabel5 specifies the fifth
         ingress label (if at all) exchanged."
    ::= { vRtrLdpServFecEntry 18 }

vRtrLdpServFecInLabelStatus5    OBJECT-TYPE
    SYNTAX      TmnxLabelStatus
    MAX-ACCESS  read-only
    STATUS      current
    DESCRIPTION
        "The value of vRtrLdpServFecInLabelStatus5 specifies the
         status of the ingress label 5"
    ::= { vRtrLdpServFecEntry 19 }

vRtrLdpServFecOutLabel1    OBJECT-TYPE
    SYNTAX      Unsigned32
    MAX-ACCESS  read-only
    STATUS      current
    DESCRIPTION
        "The value of vRtrLdpServFecOutLabel1 specifies the first
         egress label exchanged."
    ::= { vRtrLdpServFecEntry 20 }

vRtrLdpServFecOutLabelStatus1    OBJECT-TYPE
    SYNTAX      TmnxLabelStatus
    MAX-ACCESS  read-only
    STATUS      current
    DESCRIPTION
        "The value of vRtrLdpServFecOutLabelStatus1 specifies the
         status of the egress label 1"
    ::= { vRtrLdpServFecEntry 21 }

vRtrLdpServFecOutLabel2    OBJECT-TYPE
    SYNTAX      Unsigned32
    MAX-ACCESS  read-only
    STATUS      current
    DESCRIPTION
        "The value of vRtrLdpServFecOutLabel2 specifies the second
         egress label (if at all) exchanged."
    ::= { vRtrLdpServFecEntry 22 }

vRtrLdpServFecOutLabelStatus2    OBJECT-TYPE
    SYNTAX      TmnxLabelStatus
    MAX-ACCESS  read-only
    STATUS      current
    DESCRIPTION
        "The value of vRtrLdpServFecOutLabelStatus2 specifies the
         status of the egress label 2"
    ::= { vRtrLdpServFecEntry 23 }

vRtrLdpServFecOutLabel3    OBJECT-TYPE
    SYNTAX      Unsigned32
    MAX-ACCESS  read-only
    STATUS      current
    DESCRIPTION
        "The value of vRtrLdpServFecOutLabel3 specifies the third
         egress label (if at all) exchanged."
    ::= { vRtrLdpServFecEntry 24 }

vRtrLdpServFecOutLabelStatus3    OBJECT-TYPE
    SYNTAX      TmnxLabelStatus
    MAX-ACCESS  read-only
    STATUS      current
    DESCRIPTION
        "The value of vRtrLdpServFecOutLabelStatus3 specifies the
         status of the egress label 3"
    ::= { vRtrLdpServFecEntry 25 }

vRtrLdpServFecOutLabel4    OBJECT-TYPE
    SYNTAX      Unsigned32
    MAX-ACCESS  read-only
    STATUS      current
    DESCRIPTION
        "The value of vRtrLdpServFecOutLabel4 specifies the fourth
         egress label (if at all) exchanged."
    ::= { vRtrLdpServFecEntry 26 }

vRtrLdpServFecOutLabelStatus4    OBJECT-TYPE
    SYNTAX      TmnxLabelStatus
    MAX-ACCESS  read-only
    STATUS      current
    DESCRIPTION
        "The value of vRtrLdpServFecOutLabelStatus4 specifies the
         status of the egress label 4"
    ::= { vRtrLdpServFecEntry 27 }

vRtrLdpServFecOutLabel5    OBJECT-TYPE
    SYNTAX      Unsigned32
    MAX-ACCESS  read-only
    STATUS      current
    DESCRIPTION
        "The value of vRtrLdpServFecOutLabel5 specifies the fifth
         egress label (if at all) exchanged."
    ::= { vRtrLdpServFecEntry 28 }

vRtrLdpServFecOutLabelStatus5    OBJECT-TYPE
    SYNTAX      TmnxLabelStatus
    MAX-ACCESS  read-only
    STATUS      current
    DESCRIPTION
        "The value of vRtrLdpServFecOutLabelStatus5 specifies the
         status of the egress label 5"
    ::= { vRtrLdpServFecEntry 29 }

vRtrLdpServFecSdpId    OBJECT-TYPE
    SYNTAX      SdpId
    MAX-ACCESS  read-only
    STATUS      current
    DESCRIPTION
        "The value of vRtrLdpServFecSdpId identifies the SDP associated
         with this peer."
    ::= { vRtrLdpServFecEntry 30 }

vRtrLdpServFecLocalMTU    OBJECT-TYPE
    SYNTAX      Unsigned32
    MAX-ACCESS  read-only
    STATUS      current
    DESCRIPTION
        "The value of vRtrLdpServFecLocalMTU specifies the largest
         service frame size (in octets) that can be handled by the
         local ESR."
    ::= { vRtrLdpServFecEntry 31 }

vRtrLdpServFecRemoteMTU    OBJECT-TYPE
    SYNTAX      Unsigned32
    MAX-ACCESS  read-only
    STATUS      current
    DESCRIPTION
        "The value of vRtrLdpServFecRemoteMTU specifies the largest
         service frame size (in octets) that can be handled by the
         remote ESR."
    ::= { vRtrLdpServFecEntry 32 }

vRtrLdpServFecLocalVlanTag    OBJECT-TYPE
    SYNTAX      Unsigned32
    MAX-ACCESS  read-only
    STATUS      current
    DESCRIPTION
        "The value of vRtrLdpServFecLocalVlanTag specifies the local
         tag on a VLAN VC type SDP binding."
    ::= { vRtrLdpServFecEntry 33 }

vRtrLdpServFecRemoteVlanTag    OBJECT-TYPE
    SYNTAX      Unsigned32
    MAX-ACCESS  read-only
    STATUS      current
    DESCRIPTION
        "The value of vRtrLdpServFecRemoteVlanTag specifies the remote
         tag on a VLAN VC type SDP binding."
    ::= { vRtrLdpServFecEntry 34 }

vRtrLdpServFecLocalMaxCellConcat    OBJECT-TYPE
    SYNTAX      Unsigned32
    MAX-ACCESS  read-only
    STATUS      current
    DESCRIPTION
        "The value of vRtrLdpServFecLocalMaxCellConcat specifies the local
         maximum number of ATM cells to concatenate on a ATM cell-mode VC
         type SDP binding."
    ::= { vRtrLdpServFecEntry 35 }

vRtrLdpServFecRemoteMaxCellConcat    OBJECT-TYPE
    SYNTAX      Unsigned32
    MAX-ACCESS  read-only
    STATUS      current
    DESCRIPTION
        "The value of vRtrLdpServFecRemoteMaxCellConcat specifies the remote
         maximum number of ATM cells to concatenate on a ATM cell-mode VC
         type SDP binding."
    ::= { vRtrLdpServFecEntry 36 }

vRtrLdpServFecInLabelSigStatus1     OBJECT-TYPE
    SYNTAX      TmnxLabelSigStatus
    MAX-ACCESS  read-only
    STATUS      current
    DESCRIPTION
        "The value of vRtrLdpServFecInLabelSigStatus1 indicates the signaling
         status for vRtrLdpServFecInLabel1."
    ::= { vRtrLdpServFecEntry 37 }

vRtrLdpServFecInLabelSigStatus2     OBJECT-TYPE
    SYNTAX      TmnxLabelSigStatus
    MAX-ACCESS  read-only
    STATUS      current
    DESCRIPTION
        "The value of vRtrLdpServFecInLabelSigStatus2 indicates the signaling
         status for vRtrLdpServFecInLabel2."
    ::= { vRtrLdpServFecEntry 38 }

vRtrLdpServFecInLabelSigStatus3     OBJECT-TYPE
    SYNTAX      TmnxLabelSigStatus
    MAX-ACCESS  read-only
    STATUS      current
    DESCRIPTION
        "The value of vRtrLdpServFecInLabelSigStatus3 indicates the signaling
         status for vRtrLdpServFecInLabel3."
    ::= { vRtrLdpServFecEntry 39 }

vRtrLdpServFecInLabelSigStatus4     OBJECT-TYPE
    SYNTAX      TmnxLabelSigStatus
    MAX-ACCESS  read-only
    STATUS      current
    DESCRIPTION
        "The value of vRtrLdpServFecInLabelSigStatus4 indicates the signaling
         status for vRtrLdpServFecInLabel4."
    ::= { vRtrLdpServFecEntry 40 }

vRtrLdpServFecInLabelSigStatus5     OBJECT-TYPE
    SYNTAX      TmnxLabelSigStatus
    MAX-ACCESS  read-only
    STATUS      current
    DESCRIPTION
        "The value of vRtrLdpServFecInLabelSigStatus5 indicates the signaling
         status for vRtrLdpServFecInLabel5."
    ::= { vRtrLdpServFecEntry 41 }

vRtrLdpServFecOutLabelSigStatus1     OBJECT-TYPE
    SYNTAX      TmnxLabelSigStatus
    MAX-ACCESS  read-only
    STATUS      current
    DESCRIPTION
        "The value of vRtrLdpServFecOutLabelSigStatus1 indicates the signaling
         status for vRtrLdpServFecOutLabel1."
    ::= { vRtrLdpServFecEntry 42 }

vRtrLdpServFecOutLabelSigStatus2     OBJECT-TYPE
    SYNTAX      TmnxLabelSigStatus
    MAX-ACCESS  read-only
    STATUS      current
    DESCRIPTION
        "The value of vRtrLdpServFecOutLabelSigStatus2 indicates the signaling
         status for vRtrLdpServFecOutLabel2."
    ::= { vRtrLdpServFecEntry 43 }

vRtrLdpServFecOutLabelSigStatus3     OBJECT-TYPE
    SYNTAX      TmnxLabelSigStatus
    MAX-ACCESS  read-only
    STATUS      current
    DESCRIPTION
        "The value of vRtrLdpServFecOutLabelSigStatus3 indicates the signaling
         status for vRtrLdpServFecOutLabel3."
    ::= { vRtrLdpServFecEntry 44 }

vRtrLdpServFecOutLabelSigStatus4     OBJECT-TYPE
    SYNTAX      TmnxLabelSigStatus
    MAX-ACCESS  read-only
    STATUS      current
    DESCRIPTION
        "The value of vRtrLdpServFecOutLabelSigStatus4 indicates the signaling
         status for vRtrLdpServFecOutLabel4."
    ::= { vRtrLdpServFecEntry 45 }

vRtrLdpServFecOutLabelSigStatus5     OBJECT-TYPE
    SYNTAX      TmnxLabelSigStatus
    MAX-ACCESS  read-only
    STATUS      current
    DESCRIPTION
        "The value of vRtrLdpServFecOutLabelSigStatus5 indicates the signaling
         status for vRtrLdpServFecOutLabel5."
    ::= { vRtrLdpServFecEntry 46 }

vRtrLdpServFecMateEndpointVcId    OBJECT-TYPE
    SYNTAX      TmnxVcId
    MAX-ACCESS  read-only
    STATUS      current
    DESCRIPTION
        "The value of vRtrLdpServFecMateEndpointVcId specifies the VC identifier
         associated with this service FEC mate endpoint for vc-switching."
    ::= { vRtrLdpServFecEntry 47 }

vRtrLdpServFecMateEndpointSdpId    OBJECT-TYPE
    SYNTAX      SdpId
    MAX-ACCESS  read-only
    STATUS      current
    DESCRIPTION
        "The value of vRtrLdpServFecMateEndpointSdpId identifies the SDP
         associated with this service FEC mate endpoint for vc-switching."
    ::= { vRtrLdpServFecEntry 48 }

--
--  Alcatel 7x50 SR series LDP Service FEC Mapping Table
--

vRtrLdpServFecMapTable    OBJECT-TYPE
    SYNTAX      SEQUENCE OF VRtrLdpServFecMapEntry
    MAX-ACCESS  not-accessible
    STATUS      obsolete
    DESCRIPTION
        "vRtrLdpServFecMapTable is a read-only table which maps to the
         vRtrLdpServFecTable. This table has the same indexes as the
         vRtrLdpServFecTable but the order in which these indexes are
         specified is different for the two tables."
    ::= { tmnxLdpObjs 12 }

vRtrLdpServFecMapEntry    OBJECT-TYPE
    SYNTAX      VRtrLdpServFecMapEntry
    MAX-ACCESS  not-accessible
    STATUS      obsolete
    DESCRIPTION
        "Each row entry represents an instance of a service FEC sent to
         or received from an LDP peer."
    INDEX  { vRtrID,
             vRtrLdpPeerLdpId,
             vRtrLdpServFecMapFecType,
             vRtrLdpServFecMapVcType,
             vRtrLdpServFecMapVcId }

    ::= { vRtrLdpServFecMapTable 1 }

VRtrLdpServFecMapEntry ::= SEQUENCE {
    vRtrLdpServFecMapFecType               TmnxLdpFECType,
    vRtrLdpServFecMapVcType                TmnxVcType,
    vRtrLdpServFecMapVcId                  TmnxVcId
}

vRtrLdpServFecMapFecType    OBJECT-TYPE
    SYNTAX      TmnxLdpFECType
    MAX-ACCESS  read-only
    STATUS      obsolete
    DESCRIPTION
        "The value of vRtrLdpServFecMapFecType specifies the FEC type."
    ::= { vRtrLdpServFecMapEntry 1 }

vRtrLdpServFecMapVcType    OBJECT-TYPE
    SYNTAX      TmnxVcType
    MAX-ACCESS  read-only
    STATUS      obsolete
    DESCRIPTION
        "The value of vRtrLdpServFecMapVcType specifies the VC type
         associated with this service FEC."
    ::= { vRtrLdpServFecMapEntry 2 }

vRtrLdpServFecMapVcId    OBJECT-TYPE
    SYNTAX      TmnxVcId
    MAX-ACCESS  read-only
    STATUS      obsolete
    DESCRIPTION
        "The value of vRtrLdpServFecMapVcId specifies the VC identifier
         associated with this service FEC."
    ::= { vRtrLdpServFecMapEntry 3 }


--
--  Alcatel 7x50 SR series LDP Address FEC Table
--

vRtrLdpAddrFecTable    OBJECT-TYPE
    SYNTAX      SEQUENCE OF VRtrLdpAddrFecEntry
    MAX-ACCESS  not-accessible
    STATUS      current
    DESCRIPTION
        "vRtrLdpAddrFecTable is a read-only table that represents all
         address FECs either sent to or received from an LDP peer known
         to the Virtual Router."
    ::= { tmnxLdpObjs 13 }

vRtrLdpAddrFecEntry    OBJECT-TYPE
    SYNTAX      VRtrLdpAddrFecEntry
    MAX-ACCESS  not-accessible
    STATUS      current
    DESCRIPTION
        "Each row entry represents an instance of an address FEC sent
         to or received from an LDP peer."
    INDEX  { vRtrID,
             vRtrLdpAddrFecFecType,
             vRtrLdpAddrFecIpPrefix,
             vRtrLdpAddrFecIpMask,
             vRtrLdpPeerLdpId }
    ::= { vRtrLdpAddrFecTable 1 }

VRtrLdpAddrFecEntry ::= SEQUENCE {
    vRtrLdpAddrFecFecType               TmnxLdpFECType,
    vRtrLdpAddrFecIpPrefix              IpAddress,
    vRtrLdpAddrFecIpMask                IpAddress,
    vRtrLdpAddrFecFlags                 TmnxLdpFECFlags,
    vRtrLdpAddrFecNumInLabels           Unsigned32,
    vRtrLdpAddrFecNumOutLabels          Unsigned32,
    vRtrLdpAddrFecInLabel1              Unsigned32,
    vRtrLdpAddrFecInLabelStatus1        TmnxLabelStatus,
    vRtrLdpAddrFecInLabelIfIndex1       InterfaceIndexOrZero,
    vRtrLdpAddrFecInLabel2              Unsigned32,
    vRtrLdpAddrFecInLabelStatus2        TmnxLabelStatus,
    vRtrLdpAddrFecInLabelIfIndex2       InterfaceIndexOrZero,
    vRtrLdpAddrFecInLabel3              Unsigned32,
    vRtrLdpAddrFecInLabelStatus3        TmnxLabelStatus,
    vRtrLdpAddrFecInLabelIfIndex3       InterfaceIndexOrZero,
    vRtrLdpAddrFecInLabel4              Unsigned32,
    vRtrLdpAddrFecInLabelStatus4        TmnxLabelStatus,
    vRtrLdpAddrFecInLabelIfIndex4       InterfaceIndexOrZero,
    vRtrLdpAddrFecInLabel5              Unsigned32,
    vRtrLdpAddrFecInLabelStatus5        TmnxLabelStatus,
    vRtrLdpAddrFecInLabelIfIndex5       InterfaceIndexOrZero,
    vRtrLdpAddrFecOutLabel1             Unsigned32,
    vRtrLdpAddrFecOutLabelStatus1       TmnxLabelStatus,
    vRtrLdpAddrFecOutLabelIfIndex1      InterfaceIndexOrZero,
    vRtrLdpAddrFecOutLabelNextHop1      IpAddress,
    vRtrLdpAddrFecOutLabel2             Unsigned32,
    vRtrLdpAddrFecOutLabelStatus2       TmnxLabelStatus,
    vRtrLdpAddrFecOutLabelIfIndex2      InterfaceIndexOrZero,
    vRtrLdpAddrFecOutLabelNextHop2      IpAddress,
    vRtrLdpAddrFecOutLabel3             Unsigned32,
    vRtrLdpAddrFecOutLabelStatus3       TmnxLabelStatus,
    vRtrLdpAddrFecOutLabelIfIndex3      InterfaceIndexOrZero,
    vRtrLdpAddrFecOutLabelNextHop3      IpAddress,
    vRtrLdpAddrFecOutLabel4             Unsigned32,
    vRtrLdpAddrFecOutLabelStatus4       TmnxLabelStatus,
    vRtrLdpAddrFecOutLabelIfIndex4      InterfaceIndexOrZero,
    vRtrLdpAddrFecOutLabelNextHop4      IpAddress,
    vRtrLdpAddrFecOutLabel5             Unsigned32,
    vRtrLdpAddrFecOutLabelStatus5       TmnxLabelStatus,
    vRtrLdpAddrFecOutLabelIfIndex5      InterfaceIndexOrZero,
    vRtrLdpAddrFecOutLabelNextHop5      IpAddress,
    vRtrLdpAddrFecLspId                 TmnxVRtrMplsLspID
}

vRtrLdpAddrFecFecType    OBJECT-TYPE
    SYNTAX      TmnxLdpFECType
    MAX-ACCESS  not-accessible
    STATUS      current
    DESCRIPTION
        "The value of vRtrLdpAddrFecFecType specifies the FEC type."
    ::= { vRtrLdpAddrFecEntry 1 }

vRtrLdpAddrFecIpPrefix    OBJECT-TYPE
    SYNTAX      IpAddress
    MAX-ACCESS  not-accessible
    STATUS      current
    DESCRIPTION
        "The value of vRtrLdpAddrFecIpPrefix specifies the IP Address
         Prefix for this address FEC."
    ::= { vRtrLdpAddrFecEntry 2 }

vRtrLdpAddrFecIpMask    OBJECT-TYPE
    SYNTAX      IpAddress
    MAX-ACCESS  not-accessible
    STATUS      current
    DESCRIPTION
        "The value of vRtrLdpAddrFecIpMask specifies the IP Address
         Mask for this address FEC."
    ::= { vRtrLdpAddrFecEntry 3 }

vRtrLdpAddrFecFlags    OBJECT-TYPE
    SYNTAX      TmnxLdpFECFlags
    MAX-ACCESS  read-only
    STATUS      current
    DESCRIPTION
        "The bit flags of vRtrLdpAddrFecFlags specify the characteristics
         of the FEC."
    ::= { vRtrLdpAddrFecEntry 4 }

vRtrLdpAddrFecNumInLabels    OBJECT-TYPE
    SYNTAX      Unsigned32
    MAX-ACCESS  read-only
    STATUS      current
    DESCRIPTION
        "The value of vRtrLdpAddrFecNumInLabels gives the number of
         labels that have been sent to the peer associated with this
         FEC. This value also indicates which of the following
         vRtrLdpAddrFecInLabel1 thru vRtrLdpAddrFecInLabel5
         entries contain valid information i.e. if the value of
         vRtrLdpAddrFecNumInLabels is 3 then vRtrLdpAddrFecInLabel1,
         vRtrLdpAddrFecInLabel2 and vRtrLdpAddrFecInLabel3 will
         contain valid label information."
    ::= { vRtrLdpAddrFecEntry 5 }

vRtrLdpAddrFecNumOutLabels    OBJECT-TYPE
    SYNTAX      Unsigned32
    MAX-ACCESS  read-only
    STATUS      current
    DESCRIPTION
        "The value of vRtrLdpAddrFecNumOutLabels gives the number of
         labels that have been received from the peer associated with this
         FEC. This value also indicates which of the following
         vRtrLdpAddrFecOutLabel1 thru vRtrLdpAddrFecOutLabel5
         entries contain valid information i.e. if the value of
         vRtrLdpAddrFecNumOutLabels is 3, then vRtrLdpAddrFecOutLabel1,
         vRtrLdpAddrFecOutLabel2 and vRtrLdpAddrFecOutLabel3 will
         contain valid label information."
    ::= { vRtrLdpAddrFecEntry 6 }

vRtrLdpAddrFecInLabel1    OBJECT-TYPE
    SYNTAX      Unsigned32
    MAX-ACCESS  read-only
    STATUS      current
    DESCRIPTION
        "The value of vRtrLdpAddrFecInLabel1 specifies the first
         ingress label exchanged"
    ::= { vRtrLdpAddrFecEntry 7 }

vRtrLdpAddrFecInLabelStatus1    OBJECT-TYPE
    SYNTAX      TmnxLabelStatus
    MAX-ACCESS  read-only
    STATUS      current
    DESCRIPTION
        "The value of vRtrLdpAddrFecInLabelStatus1 specifies the
         status of the ingress label 1"
    ::= { vRtrLdpAddrFecEntry 8 }

vRtrLdpAddrFecInLabelIfIndex1    OBJECT-TYPE
    SYNTAX      InterfaceIndexOrZero
    MAX-ACCESS  read-only
    STATUS      current
    DESCRIPTION
        "The value of vRtrLdpAddrFecInLabelIfIndex1 specifies the
         interface index for ingress label 1"
    ::= { vRtrLdpAddrFecEntry 9 }

vRtrLdpAddrFecInLabel2    OBJECT-TYPE
    SYNTAX      Unsigned32
    MAX-ACCESS  read-only
    STATUS      current
    DESCRIPTION
        "The value of vRtrLdpAddrFecInLabel2 specifies the second
         ingress label (if at all) exchanged."
    ::= { vRtrLdpAddrFecEntry 10 }

vRtrLdpAddrFecInLabelStatus2    OBJECT-TYPE
    SYNTAX      TmnxLabelStatus
    MAX-ACCESS  read-only
    STATUS      current
    DESCRIPTION
        "The value of vRtrLdpAddrFecInLabelStatus2 specifies the
         status of the ingress label "
    ::= { vRtrLdpAddrFecEntry 11 }

vRtrLdpAddrFecInLabelIfIndex2    OBJECT-TYPE
    SYNTAX      InterfaceIndexOrZero
    MAX-ACCESS  read-only
    STATUS      current
    DESCRIPTION
        "The value of vRtrLdpAddrFecInLabelIfIndex2 specifies the
         interface index for ingress label 2"
    ::= { vRtrLdpAddrFecEntry 12 }

vRtrLdpAddrFecInLabel3    OBJECT-TYPE
    SYNTAX      Unsigned32
    MAX-ACCESS  read-only
    STATUS      current
    DESCRIPTION
        "The value of vRtrLdpAddrFecInLabel3 specifies the third
         ingress label (if at all) exchanged."
    ::= { vRtrLdpAddrFecEntry 13 }

vRtrLdpAddrFecInLabelStatus3    OBJECT-TYPE
    SYNTAX      TmnxLabelStatus
    MAX-ACCESS  read-only
    STATUS      current
    DESCRIPTION
        "The value of vRtrLdpAddrFecInLabelStatus3 specifies the
         status of the ingress label 3"
    ::= { vRtrLdpAddrFecEntry 14 }

vRtrLdpAddrFecInLabelIfIndex3    OBJECT-TYPE
    SYNTAX      InterfaceIndexOrZero
    MAX-ACCESS  read-only
    STATUS      current
    DESCRIPTION
        "The value of vRtrLdpAddrFecInLabelIfIndex3 specifies the
         interface index for ingress label 3"
    ::= { vRtrLdpAddrFecEntry 15 }

vRtrLdpAddrFecInLabel4    OBJECT-TYPE
    SYNTAX      Unsigned32
    MAX-ACCESS  read-only
    STATUS      current
    DESCRIPTION
        "The value of vRtrLdpAddrFecInLabel4 specifies the fourth
         ingress label (if at all) exchanged."
    ::= { vRtrLdpAddrFecEntry 16 }

vRtrLdpAddrFecInLabelStatus4    OBJECT-TYPE
    SYNTAX      TmnxLabelStatus
    MAX-ACCESS  read-only
    STATUS      current
    DESCRIPTION
        "The value of vRtrLdpAddrFecInLabelStatus4 specifies the
         status of the ingress label 4"
    ::= { vRtrLdpAddrFecEntry 17 }

vRtrLdpAddrFecInLabelIfIndex4    OBJECT-TYPE
    SYNTAX      InterfaceIndexOrZero
    MAX-ACCESS  read-only
    STATUS      current
    DESCRIPTION
        "The value of vRtrLdpAddrFecInLabelIfIndex4 specifies the
         interface index for ingress label 4"
    ::= { vRtrLdpAddrFecEntry 18 }

vRtrLdpAddrFecInLabel5    OBJECT-TYPE
    SYNTAX      Unsigned32
    MAX-ACCESS  read-only
    STATUS      current
    DESCRIPTION
        "The value of vRtrLdpAddrFecInLabel5 specifies the fifth
         ingress label (if at all) exchanged."
    ::= { vRtrLdpAddrFecEntry 19 }

vRtrLdpAddrFecInLabelStatus5    OBJECT-TYPE
    SYNTAX      TmnxLabelStatus
    MAX-ACCESS  read-only
    STATUS      current
    DESCRIPTION
        "The value of vRtrLdpAddrFecInLabelStatus5 specifies the
         status of the ingress label 5"
    ::= { vRtrLdpAddrFecEntry 20 }

vRtrLdpAddrFecInLabelIfIndex5    OBJECT-TYPE
    SYNTAX      InterfaceIndexOrZero
    MAX-ACCESS  read-only
    STATUS      current
    DESCRIPTION
        "The value of vRtrLdpAddrFecInLabelIfIndex5 specifies the
         interface index for ingress label 5"
    ::= { vRtrLdpAddrFecEntry 21 }

vRtrLdpAddrFecOutLabel1    OBJECT-TYPE
    SYNTAX      Unsigned32
    MAX-ACCESS  read-only
    STATUS      current
    DESCRIPTION
        "The value of vRtrLdpAddrFecOutLabel1 specifies the first
         egress label exchanged"
    ::= { vRtrLdpAddrFecEntry 22 }

vRtrLdpAddrFecOutLabelStatus1    OBJECT-TYPE
    SYNTAX      TmnxLabelStatus
    MAX-ACCESS  read-only
    STATUS      current
    DESCRIPTION
        "The value of vRtrLdpAddrFecOutLabelStatus1 specifies the
         status of the egress label 1"
    ::= { vRtrLdpAddrFecEntry 23 }

vRtrLdpAddrFecOutLabelIfIndex1    OBJECT-TYPE
    SYNTAX      InterfaceIndexOrZero
    MAX-ACCESS  read-only
    STATUS      current
    DESCRIPTION
        "The value of vRtrLdpAddrFecOutLabelIfIndex1 specifies the
         interface index for egress label 1"
    ::= { vRtrLdpAddrFecEntry 24 }

vRtrLdpAddrFecOutLabelNextHop1    OBJECT-TYPE
    SYNTAX      IpAddress
    MAX-ACCESS  read-only
    STATUS      current
    DESCRIPTION
        "The value of vRtrLdpAddrFecOutLabelNextHop1 specifies the
         IP address of the next hop for egress label 1"
    ::= { vRtrLdpAddrFecEntry 25 }

vRtrLdpAddrFecOutLabel2    OBJECT-TYPE
    SYNTAX      Unsigned32
    MAX-ACCESS  read-only
    STATUS      current
    DESCRIPTION
        "The value of vRtrLdpAddrFecOutLabel2 specifies the second
         egress label (if at all) exchanged."
    ::= { vRtrLdpAddrFecEntry 26 }

vRtrLdpAddrFecOutLabelStatus2    OBJECT-TYPE
    SYNTAX      TmnxLabelStatus
    MAX-ACCESS  read-only
    STATUS      current
    DESCRIPTION
        "The value of vRtrLdpAddrFecOutLabelStatus2 specifies the
         status of the egress label 2"
    ::= { vRtrLdpAddrFecEntry 27 }

vRtrLdpAddrFecOutLabelIfIndex2    OBJECT-TYPE
    SYNTAX      InterfaceIndexOrZero
    MAX-ACCESS  read-only
    STATUS      current
    DESCRIPTION
        "The value of vRtrLdpAddrFecOutLabelIfIndex2 specifies the
         interface index for egress label 2"
    ::= { vRtrLdpAddrFecEntry 28 }

vRtrLdpAddrFecOutLabelNextHop2    OBJECT-TYPE
    SYNTAX      IpAddress
    MAX-ACCESS  read-only
    STATUS      current
    DESCRIPTION
        "The value of vRtrLdpAddrFecOutLabelNextHop2 specifies the
         IP address of the next hop for egress label 2"
    ::= { vRtrLdpAddrFecEntry 29 }

vRtrLdpAddrFecOutLabel3    OBJECT-TYPE
    SYNTAX      Unsigned32
    MAX-ACCESS  read-only
    STATUS      current
    DESCRIPTION
        "The value of vRtrLdpAddrFecOutLabel3 specifies the third
         egress label (if at all) exchanged."
    ::= { vRtrLdpAddrFecEntry 30 }

vRtrLdpAddrFecOutLabelStatus3    OBJECT-TYPE
    SYNTAX      TmnxLabelStatus
    MAX-ACCESS  read-only
    STATUS      current
    DESCRIPTION
        "The value of vRtrLdpAddrFecOutLabelStatus3 specifies the
         status of the egress label 3"
    ::= { vRtrLdpAddrFecEntry 31 }

vRtrLdpAddrFecOutLabelIfIndex3    OBJECT-TYPE
    SYNTAX      InterfaceIndexOrZero
    MAX-ACCESS  read-only
    STATUS      current
    DESCRIPTION
        "The value of vRtrLdpAddrFecOutLabelIfIndex3 specifies the
         interface index for egress label 3"
    ::= { vRtrLdpAddrFecEntry 32 }

vRtrLdpAddrFecOutLabelNextHop3    OBJECT-TYPE
    SYNTAX      IpAddress
    MAX-ACCESS  read-only
    STATUS      current
    DESCRIPTION
        "The value of vRtrLdpAddrFecOutLabelNextHop3 specifies the
         IP address of the next hop for egress label 3"
    ::= { vRtrLdpAddrFecEntry 33 }

vRtrLdpAddrFecOutLabel4    OBJECT-TYPE
    SYNTAX      Unsigned32
    MAX-ACCESS  read-only
    STATUS      current
    DESCRIPTION
        "The value of vRtrLdpAddrFecOutLabel4 specifies the fourth
         egress label (if at all) exchanged."
    ::= { vRtrLdpAddrFecEntry 34 }

vRtrLdpAddrFecOutLabelStatus4    OBJECT-TYPE
    SYNTAX      TmnxLabelStatus
    MAX-ACCESS  read-only
    STATUS      current
    DESCRIPTION
        "The value of vRtrLdpAddrFecOutLabelStatus4 specifies the
         status of the egress label 4"
    ::= { vRtrLdpAddrFecEntry 35 }

vRtrLdpAddrFecOutLabelIfIndex4    OBJECT-TYPE
    SYNTAX      InterfaceIndexOrZero
    MAX-ACCESS  read-only
    STATUS      current
    DESCRIPTION
        "The value of vRtrLdpAddrFecOutLabelIfIndex4 specifies the
         interface index for egress label 4"
    ::= { vRtrLdpAddrFecEntry 36 }

vRtrLdpAddrFecOutLabelNextHop4    OBJECT-TYPE
    SYNTAX      IpAddress
    MAX-ACCESS  read-only
    STATUS      current
    DESCRIPTION
        "The value of vRtrLdpAddrFecOutLabelNextHop4 specifies the
         IP address of the next hop for egress label 4"
    ::= { vRtrLdpAddrFecEntry 37 }

vRtrLdpAddrFecOutLabel5    OBJECT-TYPE
    SYNTAX      Unsigned32
    MAX-ACCESS  read-only
    STATUS      current
    DESCRIPTION
        "The value of vRtrLdpAddrFecOutLabel5 specifies the fifth
         egress label (if at all) exchanged."
    ::= { vRtrLdpAddrFecEntry 38 }

vRtrLdpAddrFecOutLabelStatus5    OBJECT-TYPE
    SYNTAX      TmnxLabelStatus
    MAX-ACCESS  read-only
    STATUS      current
    DESCRIPTION
        "The value of vRtrLdpAddrFecOutLabelStatus5 specifies the
         status of the egress label 5"
    ::= { vRtrLdpAddrFecEntry 39 }

vRtrLdpAddrFecOutLabelIfIndex5    OBJECT-TYPE
    SYNTAX      InterfaceIndexOrZero
    MAX-ACCESS  read-only
    STATUS      current
    DESCRIPTION
        "The value of vRtrLdpAddrFecOutLabelIfIndex5 specifies the
         interface index for egress label 5"
    ::= { vRtrLdpAddrFecEntry 40 }

vRtrLdpAddrFecOutLabelNextHop5    OBJECT-TYPE
    SYNTAX      IpAddress
    MAX-ACCESS  read-only
    STATUS      current
    DESCRIPTION
        "The value of vRtrLdpAddrFecOutLabelNextHop5 specifies the
         IP address of the next hop for egress label 5"
    ::= { vRtrLdpAddrFecEntry 41 }

vRtrLdpAddrFecLspId    OBJECT-TYPE
    SYNTAX      TmnxVRtrMplsLspID
    MAX-ACCESS  read-only
    STATUS      current
    DESCRIPTION
        "The value of vRtrLdpAddrFecLspId indicates the LSP id of the LSP
         associated with the specified service FEC."
    ::= { vRtrLdpAddrFecEntry 42 }


--
--  Alcatel 7x50 SR series LDP Address FEC Mapping Table
--

vRtrLdpAddrFecMapTable    OBJECT-TYPE
    SYNTAX      SEQUENCE OF VRtrLdpAddrFecMapEntry
    MAX-ACCESS  not-accessible
    STATUS      current
    DESCRIPTION
        "vRtrLdpAddrFecMapTable is a read-only table which maps to the
         vRtrLdpAddrFecTable. This table has the same indexes as the
         vRtrLdpAddrFecTable but the order in which these indexes are
         specified is different for the two tables."
    ::= { tmnxLdpObjs 14 }

vRtrLdpAddrFecMapEntry    OBJECT-TYPE
    SYNTAX      VRtrLdpAddrFecMapEntry
    MAX-ACCESS  not-accessible
    STATUS      current
    DESCRIPTION
        "Each row entry represents an instance of an address FEC sent
         to or received from an LDP peer."
    INDEX  { vRtrID,
             vRtrLdpPeerLdpId,
             vRtrLdpAddrFecMapFecType,
             vRtrLdpAddrFecMapIpPrefix,
             vRtrLdpAddrFecMapIpMask }
    ::= { vRtrLdpAddrFecMapTable 1 }

VRtrLdpAddrFecMapEntry ::= SEQUENCE {
    vRtrLdpAddrFecMapFecType               TmnxLdpFECType,
    vRtrLdpAddrFecMapIpPrefix              IpAddress,
    vRtrLdpAddrFecMapIpMask                IpAddress
}

vRtrLdpAddrFecMapFecType    OBJECT-TYPE
    SYNTAX      TmnxLdpFECType
    MAX-ACCESS  read-only
    STATUS      current
    DESCRIPTION
        "The value of vRtrLdpAddrFecMapFecType specifies the FEC type."
    ::= { vRtrLdpAddrFecMapEntry 1 }

vRtrLdpAddrFecMapIpPrefix    OBJECT-TYPE
    SYNTAX      IpAddress
    MAX-ACCESS  read-only
    STATUS      current
    DESCRIPTION
        "The value of vRtrLdpAddrFecMapIpPrefix specifies the IP Address
         Prefix for this address FEC."
    ::= { vRtrLdpAddrFecMapEntry 2 }

vRtrLdpAddrFecMapIpMask    OBJECT-TYPE
    SYNTAX      IpAddress
    MAX-ACCESS  read-only
    STATUS      current
    DESCRIPTION
        "The value of vRtrLdpAddrFecMapIpMask specifies the IP Address
         Mask for this address FEC."
    ::= { vRtrLdpAddrFecMapEntry 3 }


--
-- LDP Adjacency Backoff Table
--

vRtrLdpAdjBackoffTable    OBJECT-TYPE
    SYNTAX      SEQUENCE OF VRtrLdpAdjBackoffEntry
    MAX-ACCESS  not-accessible
    STATUS      current
    DESCRIPTION
        "vRtrLdpAdjBackoffTable is a read-only table which augments
         the vRtrLdpHelloAdjTable. The purpose of this table is to
         keep backoff information about the LDP Hello Adjacencies on
         the virtual router.

         Use of AUGMENTS clause implies a one-to-one dependent
         relationship between the base table, vRtrLdpHelloAdjTable,
         and the augmenting table vRtrLdpAdjBackoffTable. This in
         effect extends the vRtrLdpHelloAdjTable with additional
         columns.  Creation or deletion of a row in the
         vRtrLdpHelloAdjTable results in the same fate for the row
         in the vRtrLdpAdjBackoffTable."
    ::= { tmnxLdpObjs 15 }

vRtrLdpAdjBackoffEntry    OBJECT-TYPE
    SYNTAX      VRtrLdpAdjBackoffEntry
    MAX-ACCESS  not-accessible
    STATUS      current
    DESCRIPTION
        "A row in this table contains backoff information about an
         LDP adjacency.

         When an LDP session startup fails for the first time, the
         LDP entity waits for a certain time interval before it tries
         to setup the session again. This interval is the backoff
         interval. The initial value for the backoff interval is set
         to the value of vRtrLdpAdjInitBackoff. After waiting for the
         backoff interval, LDP retries to setup the LDP session. If
         it fails again the backoff interval increases exponentially
         and this repeats for each successive LDP session startup
         failure. If the backoff interval exceeds vRtrLdpAdjMaxBackoff,
         LDP will not backoff anymore and will give up trying to
         establish the LDP session."
    AUGMENTS  { vRtrLdpHelloAdjEntry }
    ::= { vRtrLdpAdjBackoffTable 1 }

VRtrLdpAdjBackoffEntry ::= SEQUENCE {
    vRtrLdpAdjInitBackoff        Unsigned32,
    vRtrLdpAdjMaxBackoff         Unsigned32,
    vRtrLdpAdjCurrentBackoff     Unsigned32,
    vRtrLdpAdjWaitingTime        Unsigned32,
    vRtrLdpAdjBackoffStatus      TruthValue
}

vRtrLdpAdjInitBackoff    OBJECT-TYPE
    SYNTAX      Unsigned32 (1..2592000)
    UNITS       "seconds"
    MAX-ACCESS  read-only
    STATUS      current
    DESCRIPTION
        "The value of vRtrLdpAdjInitBackoff specifies the initial
         backoff time. After a LDP session setup has failed, the
         value of vRtrLdpAdjInitBackoff is the time interval, in
         seconds, that the LDP entity waits before attempting to
         setup the session again. This interval is the backoff
         interval. This variable indicates the initial value for
         backoff interval when the LDP session startup first fails.
         Thereafter, if session startup fails again the backoff
         interval increases exponentially."
    ::= { vRtrLdpAdjBackoffEntry 1 }

vRtrLdpAdjMaxBackoff    OBJECT-TYPE
    SYNTAX      Unsigned32 (0..2592000)
    UNITS       "seconds"
    MAX-ACCESS  read-only
    STATUS      current
    DESCRIPTION
        "The value of vRtrLdpAdjMaxBackoff specifies the maximum
         backoff time. For each successive failure of the LDP
         session startup, the backoff interval (the time for which
         the router waits before retrying) increases exponentially.
         If the backoff interval exceeds vRtrLdpAdjMaxBackoff, the
         router will not backoff anymore and will give up trying
         to establish the LDP session. A value of 0 for
         vRtrLdpAdjMaxBackoff indicates that the backoff interval
         remains constant and will not increase exponentially. In
         effect the router will try to establish an LDP session
         till it succeeds"
    ::= { vRtrLdpAdjBackoffEntry 2 }

vRtrLdpAdjCurrentBackoff    OBJECT-TYPE
    SYNTAX      Unsigned32
    UNITS       "seconds"
    MAX-ACCESS  read-only
    STATUS      current
    DESCRIPTION
        "This value of vRtrLdpAdjCurrentBackoff specifies the current
         value of the backoff interval."
    ::= { vRtrLdpAdjBackoffEntry 3 }

vRtrLdpAdjWaitingTime    OBJECT-TYPE
    SYNTAX      Unsigned32
    UNITS       "seconds"
    MAX-ACCESS  read-only
    STATUS      current
    DESCRIPTION
        "The value of vRtrLdpAdjWaitingTime specifies the time for
         which the entity has been waiting in backoff state."
    ::= { vRtrLdpAdjBackoffEntry 4 }

vRtrLdpAdjBackoffStatus OBJECT-TYPE
    SYNTAX      TruthValue
    MAX-ACCESS  read-only
    STATUS      current
    DESCRIPTION
        "The value of vRtrLdpAdjBackoffStatus indicates whether or
         not the entity is in backoff state. If this value is 'true',
         then the entity is in a backoff state and if the value is
         'false' then the entity is not in a backoff state"
    ::= { vRtrLdpAdjBackoffEntry 5 }

--
--  LDP Peer Parameter Table
--

vRtrLdpPeerParamsTable    OBJECT-TYPE
    SYNTAX      SEQUENCE OF VRtrLdpPeerParamsEntry
    MAX-ACCESS  not-accessible
    STATUS      current
    DESCRIPTION
        "vRtrLdpPeerParamsTable has an entry for an LDP peer. This table
         is used to configure parmaters specific to the peer whether it
         is an interface or a targeted peer."
    ::= { tmnxLdpObjs 16 }

vRtrLdpPeerParamsEntry    OBJECT-TYPE
    SYNTAX      VRtrLdpPeerParamsEntry
    MAX-ACCESS  not-accessible
    STATUS      current
    DESCRIPTION
        "Each row entry represents a peer that participates in the LDP
         protocol on this virtual router.

         Row entries can be created or deleted via SNMP SET requests.
         A row with default attribute values is created by setting
         vRtrLdpPeerRowStatus to 'createAndGo'. A row entry can be
         destroyed by setting vRtrLdpPeerRowStatus to 'destroy'.

         A row entry with vRtrLdpPeerAddress of 0.0.0.0 represents the
         default LDP parameters used for all peers that do not have a
         corresponding entry in this table."
   INDEX  { vRtrID,
            vRtrLdpPeerAddress }
   ::= { vRtrLdpPeerParamsTable 1 }

VRtrLdpPeerParamsEntry ::= SEQUENCE {
    vRtrLdpPeerRowStatus        RowStatus,
    vRtrLdpPeerAuth             TruthValue,
    vRtrLdpPeerAuthKey          OCTET STRING,
    vRtrLdpPeerMinTTLValue      Unsigned32,
    vRtrLdpPeerTTLLogId         TFilterLogId,
    vRtrLdpPeerAuthKeyChain     TNamedItemOrEmpty
}

vRtrLdpPeerRowStatus    OBJECT-TYPE
    SYNTAX      RowStatus
    MAX-ACCESS  read-create
    STATUS      current
    DESCRIPTION
        "vRtrLdpPeerRowStatus is used to control the creation and deletion
         of rows in the vRtrLdpPeerParamsTable.

         A row can be created by setting vRtrLdpPeerRowStatus to 'createAndGo'.
         The agent should assign the default attribute values and change
         the row status to 'active'.

         A row entry can be destroyed by setting vRtrLdpPeerRowStatus to
         'destroy'."
    ::= { vRtrLdpPeerParamsEntry 1 }

vRtrLdpPeerAuth    OBJECT-TYPE
    SYNTAX      TruthValue
    MAX-ACCESS  read-create
    STATUS      current
    DESCRIPTION
        "When the value of vRtrLdpPeerAuth is 'true', authentication
         using MD5 message based digest protocol is enabled.  When 'false',
         no authentication is used."
    DEFVAL { false }
    ::= { vRtrLdpPeerParamsEntry 2 }

vRtrLdpPeerAuthKey    OBJECT-TYPE
    SYNTAX      OCTET STRING (SIZE(0..16))
    MAX-ACCESS  read-create
    STATUS      current
    DESCRIPTION
        "The string specified in vRtrLdpPeerAuthKey is the authentication
         key to be used between LDP neighbors before establishing sessions.
         Authentication is done using the MD-5 message based digest protocol.
         The authentication key can be any combination of letters or numbers.
         Note that the string may contain embedded nulls.

         An SNMP Get request on this object should return an OCTET STRING of
         length 0."
    DEFVAL { ''H }   -- the empty string
    ::= { vRtrLdpPeerParamsEntry 3 }

vRtrLdpPeerMinTTLValue  OBJECT-TYPE
    SYNTAX      Unsigned32 (0 | 1..255)
    MAX-ACCESS  read-create
    STATUS      current
    DESCRIPTION
        "The value of vRtrLdpPeerMinTTLValue specifies the minimum
         TTL value for an incoming LDP packet.

         If vRtrLdpPeerMinTTLValue is set to zero (0), the
         TTL Security feature is disabled."
    DEFVAL { 0 }
    ::= { vRtrLdpPeerParamsEntry 4 }

vRtrLdpPeerTTLLogId  OBJECT-TYPE
    SYNTAX      TFilterLogId
    MAX-ACCESS  read-create
    STATUS      current
    DESCRIPTION
        "The value of vRtrLdpPeerTTLLogId specifies the filter
         log to use for packets that fail TTL security check.
         The value zero indicates that logging is disabled."
    DEFVAL { 0 }
    ::= { vRtrLdpPeerParamsEntry 5 }

vRtrLdpPeerAuthKeyChain  OBJECT-TYPE
    SYNTAX      TNamedItemOrEmpty
    MAX-ACCESS  read-create
    STATUS      current
    DESCRIPTION
        "The value of vRtrLdpPeerAuthKeyChain specifies the
        keychain which will be used to sign and/or authenticate  the BGP
        protocol stream.

        The keychain name is defined by tmnxKeyChainName and is the index for
        TIMETRA-SECURITY-MIB::tmnxKeyChainTable"
    DEFVAL { ''H }
    ::= { vRtrLdpPeerParamsEntry 6 }

--
--  Alcatel 7x50 SR series LDP Static Prefix FEC Table
--

vRtrLdpStaticFecTable    OBJECT-TYPE
    SYNTAX      SEQUENCE OF VRtrLdpStaticFecEntry
    MAX-ACCESS  not-accessible
    STATUS      current
    DESCRIPTION
        "vRtrLdpStaticFecTable has an entry for each static prefix FEC
         configured on the virtual router."
    ::= { tmnxLdpObjs 18 }

vRtrLdpStaticFecEntry    OBJECT-TYPE
    SYNTAX      VRtrLdpStaticFecEntry
    MAX-ACCESS  not-accessible
    STATUS      current
    DESCRIPTION
        "Each row entry represents a static prefix FEC configured
         on the virtual router.

         Entries can be created and deleted via SNMP SET operations
         to vRtrLdpStaticFecRowStatus.

         An entry is created by setting vRtrLdpStaticFecRowStatus
         to 'createAndWait'. The row status can be set to 'active'
         only after a next-hop entry corresponding to this prefix
         has been created in the vRtrLdpStaticFecNHTable.

         An entry is deleted by setting vRtrLdpStaticFecRowStatus
         to 'destroy'. For deletion to succeed, there must be no
         next-hop entries corresponding to this prefix in the
         vRtrLdpStaticFecNHTable i.e. vRtrLdpStaticFecNumNH must have
         a value of 0."
    INDEX  { vRtrID,
             vRtrLdpStaticFecIpPrefix,
             vRtrLdpStaticFecIpMask }
    ::= { vRtrLdpStaticFecTable 1 }

VRtrLdpStaticFecEntry ::= SEQUENCE {
    vRtrLdpStaticFecIpPrefix            IpAddress,
    vRtrLdpStaticFecIpMask              IpAddress,
    vRtrLdpStaticFecRowStatus           RowStatus,
    vRtrLdpStaticFecNextNHIndex         Unsigned32,
    vRtrLdpStaticFecIngLabel            Unsigned32,
    vRtrLdpStaticFecNumNH               Gauge32,
    vRtrLdpStaticFecOperIngLabel        Unsigned32
}

vRtrLdpStaticFecIpPrefix    OBJECT-TYPE
    SYNTAX      IpAddress
    MAX-ACCESS  not-accessible
    STATUS      current
    DESCRIPTION
        "The value of vRtrLdpStaticFecIpPrefix specifies the IP Address
         Prefix for this static FEC."
    ::= { vRtrLdpStaticFecEntry 1 }

vRtrLdpStaticFecIpMask    OBJECT-TYPE
    SYNTAX      IpAddress
    MAX-ACCESS  not-accessible
    STATUS      current
    DESCRIPTION
        "The value of vRtrLdpStaticFecIpMask specifies the IP Address
         Mask for this static FEC."
    ::= { vRtrLdpStaticFecEntry 2 }

vRtrLdpStaticFecRowStatus    OBJECT-TYPE
    SYNTAX      RowStatus
    MAX-ACCESS  read-create
    STATUS      current
    DESCRIPTION
        "vRtrLdpStaticFecRowStatus is used to create, delete or
         control entries in the vRtrLdpStaticFecTable.

         To create a row entry, set vRtrLdpStaticFecRowStatus to
         'createAndWait'. Before the row can be placed in the
         'active' state, a next-hop entry corresponding to this
         prefix must exist in the vRtrLdpStaticFecNHTable.

         To delete a row entry, set vRtrLdpStaticFecRowStatus to
         'destroy'. For deletion to succeed, no next-hop entry
         corresponding to this prefix must exist in the
         vRtrLdpStaticFecNHTable i.e. vRtrLdpStaticFecNumNH must
         have a value of 0."
    ::= { vRtrLdpStaticFecEntry 3 }

vRtrLdpStaticFecNextNHIndex    OBJECT-TYPE
    SYNTAX      Unsigned32
    MAX-ACCESS  read-only
    STATUS      current
    DESCRIPTION
        "The value of vRtrLdpStaticFecNextNHIndex is used to
         assign values to vRtrLdpStaticFecNHIndex when creating
         rows in the vRtrLdpStaticFecNHTable. The network manager
         reads this object and uses it in the SET request that
         creates a new row entry in the vRtrLdpStaticFecNHTable.
         If the SET fails with the code 'inconsistentValue', the
         process must be repeated. If the SET succeeds, then this
         object will be incremented and the new instance is
         created according to the manager's directions."
    ::= { vRtrLdpStaticFecEntry 4 }

vRtrLdpStaticFecIngLabel    OBJECT-TYPE
    SYNTAX      Unsigned32 (32..1023|4294967295)
    MAX-ACCESS  read-create
    STATUS      current
    DESCRIPTION
        "The value of vRtrLdpStaticFecIngLabel specifies the label
         that is advertised to the upstream peer. If this variable
         is set to the default value of 4294967295, the ingress
         label will be dynamically assigned by the label manager."
    DEFVAL { 4294967295 }
    ::= { vRtrLdpStaticFecEntry 5 }

vRtrLdpStaticFecNumNH    OBJECT-TYPE
    SYNTAX      Gauge32
    MAX-ACCESS  read-only
    STATUS      current
    DESCRIPTION
        "The value of vRtrLdpStaticFecNumNH specifies the number
         of next-hops that are associated with the static prefix
         FEC represented by this row entry. This is also the number
         of row entries configured in the vRtrLdpStaticFecNHTable
         for this static prefix FEC.

         If the static FEC has no next-hops associated with it,
         this value will be 0 and the row entry will be placed in
         the 'notReady' state. Deletion of the row entry will be
         allowed only if vRtrLdpStaticFecNumNH is 0."
    ::= { vRtrLdpStaticFecEntry 6 }

vRtrLdpStaticFecOperIngLabel    OBJECT-TYPE
    SYNTAX      Unsigned32
    MAX-ACCESS  read-only
    STATUS      current
    DESCRIPTION
        "The value of vRtrLdpStaticFecOperIngLabel specifies the
         actual or operational value of the label that was advertised
         to the upstream peer."
    ::= { vRtrLdpStaticFecEntry 7 }


--
--  Alcatel 7x50 SR series LDP Static Prefix FEC Next-hop Table
--

vRtrLdpStaticFecNHTable    OBJECT-TYPE
    SYNTAX      SEQUENCE OF VRtrLdpStaticFecNHEntry
    MAX-ACCESS  not-accessible
    STATUS      current
    DESCRIPTION
        "vRtrLdpStaticFecNHTable has an entry for each next-hop
         configured for a static prefix FEC on the virtual router."
    ::= { tmnxLdpObjs 19 }

vRtrLdpStaticFecNHEntry    OBJECT-TYPE
    SYNTAX      VRtrLdpStaticFecNHEntry
    MAX-ACCESS  not-accessible
    STATUS      current
    DESCRIPTION
        "Each row entry represents a next-hop configured for a
         static prefix FEC on the virtual router. The static prefix
         FEC corresponding to a next-hop entry must exist as a
         row entry in the vRtrLdpStaticFecTable.

         Entries can be created and deleted via SNMP SET operations
         to vRtrLdpStaticFecNHRowStatus.

         An entry is created by setting vRtrLdpStaticFecNHRowStatus
         to 'createAndWait' or 'createAndGo'. Before the row can be
         placed in the 'active' state, vRtrLdpStaticFecNHType must
         be set to a valid value.

         An entry is deleted by setting vRtrLdpStaticFecNHRowStatus
         to 'destroy'."
    INDEX  { vRtrID,
             vRtrLdpStaticFecIpPrefix,
             vRtrLdpStaticFecIpMask,
             vRtrLdpStaticFecNHIndex }
    ::= { vRtrLdpStaticFecNHTable 1 }

VRtrLdpStaticFecNHEntry ::= SEQUENCE {
    vRtrLdpStaticFecNHIndex             Unsigned32,
    vRtrLdpStaticFecNHRowStatus         RowStatus,
    vRtrLdpStaticFecNHType              INTEGER,
    vRtrLdpStaticFecNHIpAddr            IpAddress,
    vRtrLdpStaticFecNHEgrLabel          Unsigned32
}

vRtrLdpStaticFecNHIndex    OBJECT-TYPE
    SYNTAX      Unsigned32
    MAX-ACCESS  not-accessible
    STATUS      current
    DESCRIPTION
        "The value of vRtrLdpStaticFecNHIndex is used to identify
         the next-hop associated with a static prefix FEC. This
         value is unique amongst next-hop entries for the same
         static prefix FEC."
    ::= { vRtrLdpStaticFecNHEntry 1 }

vRtrLdpStaticFecNHRowStatus    OBJECT-TYPE
    SYNTAX      RowStatus
    MAX-ACCESS  read-create
    STATUS      current
    DESCRIPTION
        "vRtrLdpStaticFecNHRowStatus is used to create, delete or
         control entries in the vRtrLdpStaticFecNHTable.

         An entry is created by setting vRtrLdpStaticFecNHRowStatus
         to 'createAndWait' or 'createAndGo'. Before the row can be
         placed in the 'active' state, vRtrLdpStaticFecNHType must
         be set to a valid value.

         An entry is deleted by setting vRtrLdpStaticFecNHRowStatus
         to 'destroy'."
    ::= { vRtrLdpStaticFecNHEntry 2 }

vRtrLdpStaticFecNHType    OBJECT-TYPE
    SYNTAX      INTEGER {
                    unknown (0),
                    ipAddress (1),
                    pop (2)
                }
    MAX-ACCESS  read-create
    STATUS      current
    DESCRIPTION
        "The value of vRtrLdpStaticFecNHType specifies the type of
         next-hop represented by this row entry.

         unknown (0)    - the next-hop type has not been set.
         ipAddress (1)  - the next-hop is an IP address.
         pop (2)        - there is no next-hop i.e. pop the label and route
        "
    DEFVAL { unknown }
    ::= { vRtrLdpStaticFecNHEntry 3 }

vRtrLdpStaticFecNHIpAddr    OBJECT-TYPE
    SYNTAX      IpAddress
    MAX-ACCESS  read-create
    STATUS      current
    DESCRIPTION
        "If vRtrLdpStaticFecNHType is set to 'ipAddress', the value
         of vRtrLdpStaticFecNHIpAddr specifies the IP address of
         the next-hop. In this case, this variable must be set to
         a valid value before the row be placed in an active state.

         If vRtrLdpStaticFecNHType is set to 'pop', this value of
         vRtrLdpStaticFecNHIpAddr will be 0.0.0.0"
    DEFVAL { '00000000'h }
    ::= { vRtrLdpStaticFecNHEntry 4 }

vRtrLdpStaticFecNHEgrLabel    OBJECT-TYPE
    SYNTAX      Unsigned32 (16..1048575|4294967295)
    MAX-ACCESS  read-create
    STATUS      current
    DESCRIPTION
        "The value of vRtrLdpStaticFecNHEgrLabel specifies the egress
         label associated with this next-hop entry. The LSR will swap
         the incoming label with the configured egress label. If this
         egress label has a value of 4294967295, the LSR will pop the
         incoming label."
    DEFVAL { 4294967295 }
    ::= { vRtrLdpStaticFecNHEntry 5 }

--
--  The Label Distribution Protocol (LDP) Targeted Session Export-Import Table
--

vRtrLdpTargTable    OBJECT-TYPE
    SYNTAX      SEQUENCE OF VRtrLdpTargEntry
    MAX-ACCESS  not-accessible
    STATUS      current
    DESCRIPTION
         "vRtrLdpTargTable keeps information about the export and import
          prefixes for a targeted LDP session.

          Use of AUGMENTS clause implies a one-to-one dependent
          relationship between the base table, vRtrLdpGeneralTable,
          and the augmenting table, vRtrLdpTargTable. This in
          effect extends the vRtrLdpGeneralTable with additional
          columns.  Creation or deletion of a row in the
          vRtrLdpGeneralTable results in the same fate for the row
          in the vRtrLdpTargTable."
    ::= { tmnxLdpObjs 20 }

vRtrLdpTargEntry    OBJECT-TYPE
    SYNTAX      VRtrLdpTargEntry
    MAX-ACCESS  not-accessible
    STATUS      current
    DESCRIPTION
        "A row in this table represents information about the targeted
         LDP session."
    AUGMENTS  { vRtrLdpGeneralEntry }
    ::= { vRtrLdpTargTable 1 }

VRtrLdpTargEntry ::= SEQUENCE {
    vRtrLdpTargImportPolicy1         TPolicyStatementNameOrEmpty,
    vRtrLdpTargImportPolicy2         TPolicyStatementNameOrEmpty,
    vRtrLdpTargImportPolicy3         TPolicyStatementNameOrEmpty,
    vRtrLdpTargImportPolicy4         TPolicyStatementNameOrEmpty,
    vRtrLdpTargImportPolicy5         TPolicyStatementNameOrEmpty,
    vRtrLdpTargExportPolicy1         TPolicyStatementNameOrEmpty,
    vRtrLdpTargExportPolicy2         TPolicyStatementNameOrEmpty,
    vRtrLdpTargExportPolicy3         TPolicyStatementNameOrEmpty,
    vRtrLdpTargExportPolicy4         TPolicyStatementNameOrEmpty,
    vRtrLdpTargExportPolicy5         TPolicyStatementNameOrEmpty,
    vRtrLdpTargTunnelPreference      TruthValue
}

vRtrLdpTargImportPolicy1 OBJECT-TYPE
    SYNTAX       TPolicyStatementNameOrEmpty
    MAX-ACCESS   read-create
    STATUS       current
    DESCRIPTION
        "The value of vRtrLdpTargImportPolicy1 specifies the import
         route policy to determine which routes are accepted from targeted
         LDP neighbors.  A maximum of 5 policies can be specified.
         vRtrLdpTargImportPolicy1 specifies the first policy."
    DEFVAL { ''H }
    ::= { vRtrLdpTargEntry 3 }

vRtrLdpTargImportPolicy2 OBJECT-TYPE
    SYNTAX       TPolicyStatementNameOrEmpty
    MAX-ACCESS   read-create
    STATUS       current
    DESCRIPTION
        "The value of vRtrLdpTargImportPolicy2 specifies the second
         import policy used to determine which routes are accepted from targeted
         LDP neighbors."
    DEFVAL { ''H }
    ::= { vRtrLdpTargEntry 4 }

vRtrLdpTargImportPolicy3 OBJECT-TYPE
    SYNTAX       TPolicyStatementNameOrEmpty
    MAX-ACCESS   read-create
    STATUS       current
    DESCRIPTION
        "The value of vRtrLdpTargImportPolicy3 specifies the third
         import policy used to determine which routes are accepted from targeted
         LDP neighbors."
    DEFVAL { ''H }
    ::= { vRtrLdpTargEntry 5 }

vRtrLdpTargImportPolicy4 OBJECT-TYPE
    SYNTAX       TPolicyStatementNameOrEmpty
    MAX-ACCESS   read-create
    STATUS       current
    DESCRIPTION
        "The value of vRtrLdpTargImportPolicy4 specifies the fourth
         import policy to determine which routes are accepted from targeted
         LDP neighbors."
    DEFVAL { ''H }
    ::= { vRtrLdpTargEntry 6 }

vRtrLdpTargImportPolicy5 OBJECT-TYPE
    SYNTAX       TPolicyStatementNameOrEmpty
    MAX-ACCESS   read-create
    STATUS       current
    DESCRIPTION
        "The value of vRtrLdpTargImportPolicy5 specifies the fifth
         import policy used to determine which routes are accepted from targeted
         LDP neighbors."
    DEFVAL { ''H }
    ::= { vRtrLdpTargEntry 7 }

vRtrLdpTargExportPolicy1 OBJECT-TYPE
    SYNTAX       TPolicyStatementNameOrEmpty
    MAX-ACCESS   read-create
    STATUS       current
    DESCRIPTION
        "The value of vRtrLdpTargExportPolicy1 specifies the export
         route policy used to determine which routes are exported to this
         targeted LDP session.  A maximum of 5 policies can be specified.
         vRtrLdpTargExportPolicy1 specifies the first policy."
    DEFVAL { ''H }
    ::= { vRtrLdpTargEntry 8 }

vRtrLdpTargExportPolicy2 OBJECT-TYPE
    SYNTAX       TPolicyStatementNameOrEmpty
    MAX-ACCESS   read-create
    STATUS       current
    DESCRIPTION
        "The value of vRtrLdpTargExportPolicy2 specifies the second
         export policy used to determine which routes are exported to this
         targeted LDP session"
    DEFVAL { ''H }
    ::= { vRtrLdpTargEntry 9 }

vRtrLdpTargExportPolicy3 OBJECT-TYPE
    SYNTAX       TPolicyStatementNameOrEmpty
    MAX-ACCESS   read-create
    STATUS       current
    DESCRIPTION
        "The value of vRtrLdpTargExportPolicy3 specifies the third
         export policy used to determine which routes are exported to this
         targeted LDP session."
    DEFVAL { ''H }
    ::= { vRtrLdpTargEntry 10 }

vRtrLdpTargExportPolicy4 OBJECT-TYPE
    SYNTAX       TPolicyStatementNameOrEmpty
    MAX-ACCESS   read-create
    STATUS       current
    DESCRIPTION
        "The value of vRtrLdpTargExportPolicy4 specifies the fourth
         export policy used to determine which routes are exported to this
         targeted LDP session."
    DEFVAL { ''H }
    ::= { vRtrLdpTargEntry 11 }

vRtrLdpTargExportPolicy5 OBJECT-TYPE
    SYNTAX       TPolicyStatementNameOrEmpty
    MAX-ACCESS   read-create
    STATUS       current
    DESCRIPTION
        "The value of vRtrLdpTargExportPolicy5 specifies the fifth
         export policy used to determine which routes are exported to this
         targeted LDP session."
    DEFVAL { ''H }
    ::= { vRtrLdpTargEntry 12 }

vRtrLdpTargTunnelPreference OBJECT-TYPE
    SYNTAX      TruthValue
    MAX-ACCESS  read-create
    STATUS      current
    DESCRIPTION
        "The value of vRtrLdpTargTunnelPreference indicates whether LDP
         over tunnel is preferred when link-level LDP bindings are also
         available. If this value is 'true', then LDP tunnels are
         preferred and if the value is 'false' then LDP over tunnel is
         preferred.

         By default LDP tunnels are preferred."
    DEFVAL { true }
    ::= { vRtrLdpTargEntry 13 }

--
--  The Label Distribution Protocol (LDP) Peer Tunneling Lsp Table
--

vRtrLdpIfTunnelingLspTable  OBJECT-TYPE
     SYNTAX      SEQUENCE OF VRtrLdpIfTunnelingLspEntry
     MAX-ACCESS  not-accessible
     STATUS      current
     DESCRIPTION
         "vRtrLdpIfTunnelingLspTable keeps the list of LDP-over-RSVP LSP
          ids which are currently supported by the application.

          Each LSP ID in the list corresponds to the vRtrMplsLspIndex of
          the given MPLS LSP."
     ::= { tmnxLdpObjs 21 }

vRtrLdpIfTunnelingLspEntry OBJECT-TYPE
    SYNTAX      VRtrLdpIfTunnelingLspEntry
    MAX-ACCESS  not-accessible
    STATUS      current
    DESCRIPTION
        "A row in this table contains the LSP id information about an LDP
         interface or targeted peer.

         Row entries can be created or deleted via SNMP SET requests.
         A row is created by setting vRtrLdpIfLspRowStatus to 'createAndGo'
         provided the corresponding LSP id exists as an MPLS lsp.
         A row entry can be destroyed by setting vRtrLdpIfLspRowStatus to
         'destroy'."
    INDEX  { vRtrID,
             vRtrLdpIfIndex,
             vRtrLdpPeerAddress,
             vRtrLdpIfLspId }
    ::= { vRtrLdpIfTunnelingLspTable 1 }

VRtrLdpIfTunnelingLspEntry ::= SEQUENCE {
    vRtrLdpIfLspId                     TmnxVRtrMplsLspID,
    vRtrLdpIfLspRowStatus              RowStatus
}

vRtrLdpIfLspId    OBJECT-TYPE
    SYNTAX      TmnxVRtrMplsLspID
    MAX-ACCESS  not-accessible
    STATUS      current
    DESCRIPTION
        "The value of vRtrLdpIfLspId specifies the LSP id of the LSP
         associated with the specified interface or targeted peer."
    ::= { vRtrLdpIfTunnelingLspEntry 1 }

vRtrLdpIfLspRowStatus  OBJECT-TYPE
    SYNTAX      RowStatus
    MAX-ACCESS  read-create
    STATUS      current
    DESCRIPTION
        "vRtrLdpIfLspRowStatus is used to create, delete or
         control entries in the vRtrLdpIfTunnelingLspTable.

         An entry is created by setting vRtrLdpIfLspRowStatus
         to 'createAndGo'.

         An entry is deleted by setting vRtrLdpIfLspRowStatus
         to 'destroy'."
    ::= { vRtrLdpIfTunnelingLspEntry 2 }

--
--  Alcatel 7x50 SR series LDP CEP/TDM FEC Table
--

vRtrLdpCepTdmFecTable    OBJECT-TYPE
    SYNTAX      SEQUENCE OF VRtrLdpCepTdmFecEntry
    MAX-ACCESS  not-accessible
    STATUS      current
    DESCRIPTION
        "vRtrLdpCepTdmFecTable is a read-only table that represents all
         CEP/TDM FECs either sent to or received from an LDP peer known
         to the Virtual Router.
         The CEP/TDM Sub-TLVs are defined in RFC 4446:

         Parameter Id    Description
         0x04            CEP/TDM Payload Bytes
         0x07            CEP/TDM bit-rate
         0x0B            TDM Options."
    ::= { tmnxLdpObjs 22 }

vRtrLdpCepTdmFecEntry    OBJECT-TYPE
    SYNTAX      VRtrLdpCepTdmFecEntry
    MAX-ACCESS  not-accessible
    STATUS      current
    DESCRIPTION
        "Each row entry represents an instance of a service FEC sent to
         or received from an LDP peer.

         Use of AUGMENTS clause implies a one-to-one dependent relationship
         between the base table, vRtrLdpServFecTable, and the augmenting
         table, vRtrLdpCepTdmFecTable.  This in effect extends the
         vRtrLdpServFecTable with additional columns.

          Creation or deletion of a row in the vRtrLdpServFecTable results
          in the same fate for the row in the VRtrLdpCepTdmFecEntry."
    AUGMENTS  { vRtrLdpServFecEntry }
    ::= { vRtrLdpCepTdmFecTable 1 }

VRtrLdpCepTdmFecEntry ::= SEQUENCE {
    vRtrLdpCepTdmLocalPayloadSize         Unsigned32,
    vRtrLdpCepTdmRemotePayloadSize        Unsigned32,
    vRtrLdpCepTdmLocalBitrate             Unsigned32,
    vRtrLdpCepTdmRemoteBitrate            Unsigned32,
    vRtrLdpCepTdmLocalRtpHeader           TruthValue,
    vRtrLdpCepTdmRemoteRtpHeader          TruthValue,
    vRtrLdpCepTdmLocalDiffTimestamp       TruthValue,
    vRtrLdpCepTdmRemoteDiffTimestamp      TruthValue,
    vRtrLdpCepTdmLocalSigPkts             TdmOptionsSigPkts,
    vRtrLdpCepTdmRemoteSigPkts            TdmOptionsSigPkts,
    vRtrLdpCepTdmLocalCasTrunk            TdmOptionsCasTrunkFraming,
    vRtrLdpCepTdmRemoteCasTrunk           TdmOptionsCasTrunkFraming,
    vRtrLdpCepTdmLocalTimestampFreq       Unsigned32,
    vRtrLdpCepTdmRemoteTimestampFreq      Unsigned32,
    vRtrLdpCepTdmLocalPayloadType         Unsigned32,
    vRtrLdpCepTdmRemotePayloadType        Unsigned32,
    vRtrLdpCepTdmLocalSsrcId              Unsigned32,
    vRtrLdpCepTdmRemoteSsrcId             Unsigned32
}

vRtrLdpCepTdmLocalPayloadSize  OBJECT-TYPE
    SYNTAX      Unsigned32
    UNITS       "bytes"
    MAX-ACCESS  read-only
    STATUS      current
    DESCRIPTION
        "The value of vRtrLdpCepTdmLocalPayloadSize indicates the local
         payload size."
    ::= { vRtrLdpCepTdmFecEntry 4 }

vRtrLdpCepTdmRemotePayloadSize  OBJECT-TYPE
    SYNTAX      Unsigned32
    UNITS       "bytes"
    MAX-ACCESS  read-only
    STATUS      current
    DESCRIPTION
        "The value of vRtrLdpCepTdmRemotePayloadSize indicates the remote
         payload size."
    ::= { vRtrLdpCepTdmFecEntry 5 }

vRtrLdpCepTdmLocalBitrate  OBJECT-TYPE
    SYNTAX      Unsigned32
    UNITS       "64 Kbits/s"
    MAX-ACCESS  read-only
    STATUS      current
    DESCRIPTION
        "The value of vRtrLdpCepTdmLocalBitrate indicates the local
         bitrate."
    ::= { vRtrLdpCepTdmFecEntry 6 }

vRtrLdpCepTdmRemoteBitrate  OBJECT-TYPE
    SYNTAX      Unsigned32
    UNITS       "64 Kbits/s"
    MAX-ACCESS  read-only
    STATUS      current
    DESCRIPTION
        "The value of vRtrLdpCepTdmRemoteBitrate indicates the remote
         bitrate."
    ::= { vRtrLdpCepTdmFecEntry 7 }

vRtrLdpCepTdmLocalRtpHeader OBJECT-TYPE
    SYNTAX      TruthValue
    MAX-ACCESS  read-only
    STATUS      current
    DESCRIPTION
        "The value of vRtrLdpCepTdmLocalRtpHeader indicates the local
         RTP header usage bit."
    ::= { vRtrLdpCepTdmFecEntry 8 }

vRtrLdpCepTdmRemoteRtpHeader OBJECT-TYPE
    SYNTAX      TruthValue
    MAX-ACCESS  read-only
    STATUS      current
    DESCRIPTION
        "The value of vRtrLdpCepTdmRemoteRtpHeader indicates the remote
         RTP header usage bit."
    ::= { vRtrLdpCepTdmFecEntry 9 }

vRtrLdpCepTdmLocalDiffTimestamp OBJECT-TYPE
    SYNTAX      TruthValue
    MAX-ACCESS  read-only
    STATUS      current
    DESCRIPTION
        "The value of vRtrLdpCepTdmLocalDiffTimestamp indicates the local
         differential (or dynamic) timestamping mode bit."
    ::= { vRtrLdpCepTdmFecEntry 10 }

vRtrLdpCepTdmRemoteDiffTimestamp OBJECT-TYPE
    SYNTAX      TruthValue
    MAX-ACCESS  read-only
    STATUS      current
    DESCRIPTION
        "The value of vRtrLdpCepTdmRemoteDiffTimestamp indicates the remote
         differential (or dynamic) timestamping mode bit."
    ::= { vRtrLdpCepTdmFecEntry 11 }

vRtrLdpCepTdmLocalSigPkts OBJECT-TYPE
    SYNTAX      TdmOptionsSigPkts
    MAX-ACCESS  read-only
    STATUS      current
    DESCRIPTION
        "The value of vRtrLdpCepTdmLocalSigPkts indicates the local
         CE application signalling packets mode."
    ::= { vRtrLdpCepTdmFecEntry 12 }

vRtrLdpCepTdmRemoteSigPkts OBJECT-TYPE
    SYNTAX      TdmOptionsSigPkts
    MAX-ACCESS  read-only
    STATUS      current
    DESCRIPTION
        "The value of vRtrLdpCepTdmRemoteSigPkts indicates the remote
         CE application signalling packets mode."
    ::= { vRtrLdpCepTdmFecEntry 13 }

vRtrLdpCepTdmLocalCasTrunk OBJECT-TYPE
    SYNTAX      TdmOptionsCasTrunkFraming
    MAX-ACCESS  read-only
    STATUS      current
    DESCRIPTION
        "The value of vRtrLdpCepTdmLocalCasTrunk indicates the local
         CE application signalling packets mode."
    ::= { vRtrLdpCepTdmFecEntry 14 }

vRtrLdpCepTdmRemoteCasTrunk OBJECT-TYPE
    SYNTAX      TdmOptionsCasTrunkFraming
    MAX-ACCESS  read-only
    STATUS      current
    DESCRIPTION
        "The value of vRtrLdpCepTdmRemoteCasTrunk indicates the remote
         CE application signalling packets mode."
    ::= { vRtrLdpCepTdmFecEntry 15 }

vRtrLdpCepTdmLocalTimestampFreq OBJECT-TYPE
    SYNTAX      Unsigned32
    UNITS       "8 KHz"
    MAX-ACCESS  read-only
    STATUS      current
    DESCRIPTION
        "The value of vRtrLdpCepTdmLocalTimestampFreq indicates the local
         CE application signalling packets mode."
    ::= { vRtrLdpCepTdmFecEntry 16 }

vRtrLdpCepTdmRemoteTimestampFreq OBJECT-TYPE
    SYNTAX      Unsigned32
    UNITS       "8 KHz"
    MAX-ACCESS  read-only
    STATUS      current
    DESCRIPTION
        "The value of vRtrLdpCepTdmRemoteTimestampFreq indicates the remote
         CE application signalling packets mode."
    ::= { vRtrLdpCepTdmFecEntry 17 }

vRtrLdpCepTdmLocalPayloadType OBJECT-TYPE
    SYNTAX      Unsigned32
    MAX-ACCESS  read-only
    STATUS      current
    DESCRIPTION
        "The value of vRtrLdpCepTdmLocalPayloadType indicates the local
         payload type."
    ::= { vRtrLdpCepTdmFecEntry 18 }

vRtrLdpCepTdmRemotePayloadType OBJECT-TYPE
    SYNTAX      Unsigned32
    MAX-ACCESS  read-only
    STATUS      current
    DESCRIPTION
        "The value of vRtrLdpCepTdmRemotePayloadType indicates the remote
         payload type."
    ::= { vRtrLdpCepTdmFecEntry 19 }

vRtrLdpCepTdmLocalSsrcId OBJECT-TYPE
    SYNTAX      Unsigned32
    MAX-ACCESS  read-only
    STATUS      current
    DESCRIPTION
        "The value of vRtrLdpCepTdmLocalSsrcId indicates the local
         value of SSRC ID."
    ::= { vRtrLdpCepTdmFecEntry 20 }

vRtrLdpCepTdmRemoteSsrcId OBJECT-TYPE
    SYNTAX      Unsigned32
    MAX-ACCESS  read-only
    STATUS      current
    DESCRIPTION
        "The value of vRtrLdpCepTdmRemoteSsrcId indicates the remote
         value of SSRC ID."
    ::= { vRtrLdpCepTdmFecEntry 21 }

--
--  Alcatel 7x50 SR series LDP Service FEC-129 Table
--

vLdpServFec129Table    OBJECT-TYPE
    SYNTAX      SEQUENCE OF VLdpServFec129Entry
    MAX-ACCESS  not-accessible
    STATUS      current
    DESCRIPTION
        "vLdpServFec129Table is a read-only table that represents all
         service FEC-129s either sent to or received from an LDP peer known
         to the Virtual Router."
    ::= { tmnxLdpObjs 23 }

vLdpServFec129Entry    OBJECT-TYPE
    SYNTAX      VLdpServFec129Entry
    MAX-ACCESS  not-accessible
    STATUS      current
    DESCRIPTION
        "Each row entry represents an instance of a service FEC-129 sent to
         or received from an LDP peer."
    INDEX  { vRtrID,
             vRtrLdpServFecVcType,
             vLdpServFec129AgiTlv,
             vLdpServFec129SrcAiiTlv,
             vLdpServFec129TgtAiiTlv,
             vRtrLdpPeerLdpId }
    ::= { vLdpServFec129Table 1 }

VLdpServFec129Entry ::= SEQUENCE {
    vLdpServFec129AgiTlv                TmnxLdpFec129Tlv,
    vLdpServFec129SrcAiiTlv             TmnxLdpFec129Tlv,
    vLdpServFec129TgtAiiTlv             TmnxLdpFec129Tlv,
    vLdpServFec129ServType              ServType,
    vLdpServFec129ServId                TmnxServId,
    vLdpServFec129VpnId                 TmnxVpnId,
    vLdpServFec129Flags                 TmnxLdpFECFlags,
    vLdpServFec129NumInLabels           Unsigned32,
    vLdpServFec129NumOutLabels          Unsigned32,
    vLdpServFec129InLabel1              Unsigned32,
    vLdpServFec129InLabelStatus1        TmnxLabelStatus,
    vLdpServFec129OutLabel1             Unsigned32,
    vLdpServFec129OutLabelStatus1       TmnxLabelStatus,
    vLdpServFec129SdpId                 SdpId,
    vLdpServFec129LocalMTU              Unsigned32,
    vLdpServFec129RemoteMTU             Unsigned32,
    vLdpServFec129LocalVlanTag          Unsigned32,
    vLdpServFec129RemoteVlanTag         Unsigned32,
    vLdpServFec129LocalMaxCellConcat    Unsigned32,
    vLdpServFec129RemoteMaxCellConcat   Unsigned32,
    vLdpServFec129InLabelSigStatus1     TmnxLabelSigStatus,
    vLdpServFec129OutLabelSigStatus1    TmnxLabelSigStatus
}

vLdpServFec129AgiTlv    OBJECT-TYPE
    SYNTAX      TmnxLdpFec129Tlv
    MAX-ACCESS  not-accessible
    STATUS      current
    DESCRIPTION
        "The value of vLdpServFec129AgiTlv specifies the Attachment Group
         Identifier TLV associated with this service FEC."
    ::= { vLdpServFec129Entry 1 }

vLdpServFec129SrcAiiTlv    OBJECT-TYPE
    SYNTAX      TmnxLdpFec129Tlv
    MAX-ACCESS  not-accessible
    STATUS      current
    DESCRIPTION
        "The value of vLdpServFec129SrcAiiTlv specifies the Source Attachment
         Individual Identifier TLV associated with this service FEC."
    ::= { vLdpServFec129Entry 2 }

vLdpServFec129TgtAiiTlv    OBJECT-TYPE
    SYNTAX      TmnxLdpFec129Tlv
    MAX-ACCESS  not-accessible
    STATUS      current
    DESCRIPTION
        "The value of vLdpServFec129TgtAiiTlv specifies the Target Attachment
         Individual Identifier TLV associated with this service FEC."
    ::= { vLdpServFec129Entry 3 }

vLdpServFec129ServType    OBJECT-TYPE
    SYNTAX      ServType
    MAX-ACCESS  read-only
    STATUS      current
    DESCRIPTION
        "The value of vLdpServFec129ServType specifies the Service type
         associated with this service FEC."
    ::= { vLdpServFec129Entry 4 }

vLdpServFec129ServId    OBJECT-TYPE
    SYNTAX      TmnxServId (1..2147483647)
    MAX-ACCESS  read-only
    STATUS      current
    DESCRIPTION
        "The value of vLdpServFec129ServId specifies the Service identifier
         associated with this service FEC."
    ::= { vLdpServFec129Entry 5 }

vLdpServFec129VpnId    OBJECT-TYPE
    SYNTAX      TmnxVpnId
    MAX-ACCESS  read-only
    STATUS      current
    DESCRIPTION
        "The value of vLdpServFec129VpnId identifies the VPN associated
         with the FEC."
    ::= { vLdpServFec129Entry 6 }

vLdpServFec129Flags    OBJECT-TYPE
    SYNTAX      TmnxLdpFECFlags
    MAX-ACCESS  read-only
    STATUS      current
    DESCRIPTION
        "The bit flags of vLdpServFec129Flags specify the characteristics
         of the FEC."
    ::= { vLdpServFec129Entry 7 }

vLdpServFec129NumInLabels    OBJECT-TYPE
    SYNTAX      Unsigned32
    MAX-ACCESS  read-only
    STATUS      current
    DESCRIPTION
        "The value of vLdpServFec129NumInLabels gives the number of
         labels that have been sent to the peer associated with this
         FEC. This value also indicates whether vLdpServFec129InLabel1 entry
         contain valid information i.e. if the value of
         vLdpServFec129NumInLabels is 1 then vLdpServFec129InLabel1
         will contain valid label information."
    ::= { vLdpServFec129Entry 8 }

vLdpServFec129NumOutLabels    OBJECT-TYPE
    SYNTAX      Unsigned32
    MAX-ACCESS  read-only
    STATUS      current
    DESCRIPTION
        "The value of vLdpServFec129NumOutLabels gives the number of
         labels that have been received from the peer associated with this
         FEC. This value also indicates whether vLdpServFec129OutLabel1
         entry contain valid information i.e. if the value of
         vLdpServFec129NumOutLabels is 1, then vLdpServFec129OutLabel1
         will contain valid label information."
    ::= { vLdpServFec129Entry 9 }

vLdpServFec129InLabel1    OBJECT-TYPE
    SYNTAX      Unsigned32
    MAX-ACCESS  read-only
    STATUS      current
    DESCRIPTION
        "The value of vLdpServFec129InLabel1 specifies the first
         ingress label exchanged"
    ::= { vLdpServFec129Entry 10 }

vLdpServFec129InLabelStatus1    OBJECT-TYPE
    SYNTAX      TmnxLabelStatus
    MAX-ACCESS  read-only
    STATUS      current
    DESCRIPTION
        "The value of vLdpServFec129InLabelStatus1 specifies the
         status of the ingress label 1"
    ::= { vLdpServFec129Entry 11 }

vLdpServFec129OutLabel1    OBJECT-TYPE
    SYNTAX      Unsigned32
    MAX-ACCESS  read-only
    STATUS      current
    DESCRIPTION
        "The value of vLdpServFec129OutLabel1 specifies the first
         egress label exchanged."
    ::= { vLdpServFec129Entry 20 }

vLdpServFec129OutLabelStatus1    OBJECT-TYPE
    SYNTAX      TmnxLabelStatus
    MAX-ACCESS  read-only
    STATUS      current
    DESCRIPTION
        "The value of vLdpServFec129OutLabelStatus1 specifies the
         status of the egress label 1"
    ::= { vLdpServFec129Entry 21 }

vLdpServFec129SdpId    OBJECT-TYPE
    SYNTAX      SdpId
    MAX-ACCESS  read-only
    STATUS      current
    DESCRIPTION
        "The value of vLdpServFec129SdpId identifies the SDP associated
         with this peer."
    ::= { vLdpServFec129Entry 22 }

vLdpServFec129LocalMTU    OBJECT-TYPE
    SYNTAX      Unsigned32
    MAX-ACCESS  read-only
    STATUS      current
    DESCRIPTION
        "The value of vLdpServFec129LocalMTU specifies the largest
         service frame size (in octets) that can be handled by the
         local ESR."
    ::= { vLdpServFec129Entry 23 }

vLdpServFec129RemoteMTU    OBJECT-TYPE
    SYNTAX      Unsigned32
    MAX-ACCESS  read-only
    STATUS      current
    DESCRIPTION
        "The value of vLdpServFec129RemoteMTU specifies the largest
         service frame size (in octets) that can be handled by the
         remote ESR."
    ::= { vLdpServFec129Entry 24 }

vLdpServFec129LocalVlanTag    OBJECT-TYPE
    SYNTAX      Unsigned32
    MAX-ACCESS  read-only
    STATUS      current
    DESCRIPTION
        "The value of vLdpServFec129LocalVlanTag specifies the local
         tag on a VLAN VC type SDP binding."
    ::= { vLdpServFec129Entry 25 }

vLdpServFec129RemoteVlanTag    OBJECT-TYPE
    SYNTAX      Unsigned32
    MAX-ACCESS  read-only
    STATUS      current
    DESCRIPTION
        "The value of vLdpServFec129RemoteVlanTag specifies the remote
         tag on a VLAN VC type SDP binding."
    ::= { vLdpServFec129Entry 26 }

vLdpServFec129LocalMaxCellConcat    OBJECT-TYPE
    SYNTAX      Unsigned32
    MAX-ACCESS  read-only
    STATUS      current
    DESCRIPTION
        "The value of vLdpServFec129LocalMaxCellConcat specifies the local
         maximum number of ATM cells to concatenate on a ATM cell-mode VC
         type SDP binding."
    ::= { vLdpServFec129Entry 27 }

vLdpServFec129RemoteMaxCellConcat    OBJECT-TYPE
    SYNTAX      Unsigned32
    MAX-ACCESS  read-only
    STATUS      current
    DESCRIPTION
        "The value of vLdpServFec129RemoteMaxCellConcat specifies the remote
         maximum number of ATM cells to concatenate on a ATM cell-mode VC
         type SDP binding."
    ::= { vLdpServFec129Entry 28 }

vLdpServFec129InLabelSigStatus1     OBJECT-TYPE
    SYNTAX      TmnxLabelSigStatus
    MAX-ACCESS  read-only
    STATUS      current
    DESCRIPTION
        "The value of vLdpServFec129InLabelSigStatus1 indicates the signaling
         status for vLdpServFec129InLabel1."
    ::= { vLdpServFec129Entry 29 }

vLdpServFec129OutLabelSigStatus1     OBJECT-TYPE
    SYNTAX      TmnxLabelSigStatus
    MAX-ACCESS  read-only
    STATUS      current
    DESCRIPTION
        "The value of vLdpServFec129OutLabelSigStatus1 indicates the signaling
         status for vLdpServFec129OutLabel1."
    ::= { vLdpServFec129Entry 30 }

--
--  Alcatel 7x50 SR series LDP Service FEC Mapping Table
--

vLdpServFec129MapTable    OBJECT-TYPE
    SYNTAX      SEQUENCE OF VLdpServFec129MapEntry
    MAX-ACCESS  not-accessible
    STATUS      obsolete
    DESCRIPTION
        "vLdpServFec129MapTable is a read-only table which maps to the
         vLdpServFec129Table. This table has the same indexes as the
         vLdpServFec129Table but the order in which these indexes are
         specified is different for the two tables."
    ::= { tmnxLdpObjs 24 }

vLdpServFec129MapEntry    OBJECT-TYPE
    SYNTAX      VLdpServFec129MapEntry
    MAX-ACCESS  not-accessible
    STATUS      obsolete
    DESCRIPTION
        "Each row entry represents an instance of a service FEC sent to
         or received from an LDP peer."
    INDEX  { vRtrID,
             vRtrLdpPeerLdpId,
             vLdpServFec129MapVcType,
             vLdpServFec129MapAgiTlv,
             vLdpServFec129MapSrcAiiTlv,
             vLdpServFec129MapTgtAiiTlv
             }

    ::= { vLdpServFec129MapTable 1 }

VLdpServFec129MapEntry ::= SEQUENCE {
    vLdpServFec129MapVcType                TmnxVcType,
    vLdpServFec129MapAgiTlv                TmnxLdpFec129Tlv,
    vLdpServFec129MapSrcAiiTlv             TmnxLdpFec129Tlv,
    vLdpServFec129MapTgtAiiTlv             TmnxLdpFec129Tlv
}

vLdpServFec129MapVcType    OBJECT-TYPE
    SYNTAX      TmnxVcType
    MAX-ACCESS  read-only
    STATUS      obsolete
    DESCRIPTION
        "The value of vLdpServFec129MapVcType specifies the VC type
         associated with this service FEC."
    ::= { vLdpServFec129MapEntry 1 }

vLdpServFec129MapAgiTlv    OBJECT-TYPE
    SYNTAX      TmnxLdpFec129Tlv
    MAX-ACCESS  read-only
    STATUS      obsolete
    DESCRIPTION
        "The value of vLdpServFec129MapAgiTlv specifies the Attachment Group
         Identifier TLV associated with this service FEC."
    ::= { vLdpServFec129MapEntry 2 }

vLdpServFec129MapSrcAiiTlv    OBJECT-TYPE
    SYNTAX      TmnxLdpFec129Tlv
    MAX-ACCESS  read-only
    STATUS      obsolete
    DESCRIPTION
        "The value of vLdpServFec129MapSrcAiiTlv specifies the Source
         Attachment Individual Identifier TLV associated with this service FEC."
    ::= { vLdpServFec129MapEntry 3 }

vLdpServFec129MapTgtAiiTlv    OBJECT-TYPE
    SYNTAX      TmnxLdpFec129Tlv
    MAX-ACCESS  read-only
    STATUS      obsolete
    DESCRIPTION
        "The value of vLdpServFec129MapTgtAiiTlv specifies the Target
         Attachment Individual Identifier TLV associated with this service FEC."
    ::= { vLdpServFec129MapEntry 4 }


--
--  Alcatel 7x50 SR series LDP CEP/TDM FEC Table
--

vLdpCepTdmFec129Table    OBJECT-TYPE
    SYNTAX      SEQUENCE OF VLdpCepTdmFec129Entry
    MAX-ACCESS  not-accessible
    STATUS      current
    DESCRIPTION
        "vLdpCepTdmFec129Table is a read-only table that represents all
         CEP/TDM FECs either sent to or received from an LDP peer known
         to the Virtual Router.
         The CEP/TDM Sub-TLVs are defined in RFC 4446:

         Parameter Id    Description
         0x04            CEP/TDM Payload Bytes
         0x07            CEP/TDM bit-rate
         0x0B            TDM Options."
    ::= { tmnxLdpObjs 25 }

vLdpCepTdmFec129Entry    OBJECT-TYPE
    SYNTAX      VLdpCepTdmFec129Entry
    MAX-ACCESS  not-accessible
    STATUS      current
    DESCRIPTION
        "Each row entry represents an instance of a service FEC sent to
         or received from an LDP peer.

         Use of AUGMENTS clause implies a one-to-one dependent relationship
         between the base table, vRtrLdpServFecTable, and the augmenting
         table, vLdpCepTdmFec129Table.  This in effect extends the
         vRtrLdpServFecTable with additional columns.

          Creation or deletion of a row in the vRtrLdpServFecTable results
          in the same fate for the row in the VLdpCepTdmFec129Entry."
    AUGMENTS  { vLdpServFec129Entry }
    ::= { vLdpCepTdmFec129Table 1 }

VLdpCepTdmFec129Entry ::= SEQUENCE {
    vLdpCepTdmFec129LocalPayloadSize         Unsigned32,
    vLdpCepTdmFec129RemotePayloadSize        Unsigned32,
    vLdpCepTdmFec129LocalBitrate             Unsigned32,
    vLdpCepTdmFec129RemoteBitrate            Unsigned32,
    vLdpCepTdmFec129LocalRtpHeader           TruthValue,
    vLdpCepTdmFec129RemoteRtpHeader          TruthValue,
    vLdpCepTdmFec129LocalDiffTimestamp       TruthValue,
    vLdpCepTdmFec129RemoteDiffTimestamp      TruthValue,
    vLdpCepTdmFec129LocalSigPkts             TdmOptionsSigPkts,
    vLdpCepTdmFec129RemoteSigPkts            TdmOptionsSigPkts,
    vLdpCepTdmFec129LocalCasTrunk            TdmOptionsCasTrunkFraming,
    vLdpCepTdmFec129RemoteCasTrunk           TdmOptionsCasTrunkFraming,
    vLdpCepTdmFec129LocalTimestampFreq       Unsigned32,
    vLdpCepTdmFec129RemoteTimestampFreq      Unsigned32,
    vLdpCepTdmFec129LocalPayloadType         Unsigned32,
    vLdpCepTdmFec129RemotePayloadType        Unsigned32,
    vLdpCepTdmFec129LocalSsrcId              Unsigned32,
    vLdpCepTdmFec129RemoteSsrcId             Unsigned32
}

vLdpCepTdmFec129LocalPayloadSize  OBJECT-TYPE
    SYNTAX      Unsigned32
    UNITS       "bytes"
    MAX-ACCESS  read-only
    STATUS      current
    DESCRIPTION
        "The value of vLdpCepTdmFec129LocalPayloadSize indicates the local
         payload size."
    ::= { vLdpCepTdmFec129Entry 4 }

vLdpCepTdmFec129RemotePayloadSize  OBJECT-TYPE
    SYNTAX      Unsigned32
    UNITS       "bytes"
    MAX-ACCESS  read-only
    STATUS      current
    DESCRIPTION
        "The value of vLdpCepTdmFec129RemotePayloadSize indicates the remote
         payload size."
    ::= { vLdpCepTdmFec129Entry 5 }

vLdpCepTdmFec129LocalBitrate  OBJECT-TYPE
    SYNTAX      Unsigned32
    UNITS       "64 Kbits/s"
    MAX-ACCESS  read-only
    STATUS      current
    DESCRIPTION
        "The value of vLdpCepTdmFec129LocalBitrate indicates the local
         bitrate."
    ::= { vLdpCepTdmFec129Entry 6 }

vLdpCepTdmFec129RemoteBitrate  OBJECT-TYPE
    SYNTAX      Unsigned32
    UNITS       "64 Kbits/s"
    MAX-ACCESS  read-only
    STATUS      current
    DESCRIPTION
        "The value of vLdpCepTdmFec129RemoteBitrate indicates the remote
         bitrate."
    ::= { vLdpCepTdmFec129Entry 7 }

vLdpCepTdmFec129LocalRtpHeader OBJECT-TYPE
    SYNTAX      TruthValue
    MAX-ACCESS  read-only
    STATUS      current
    DESCRIPTION
        "The value of vLdpCepTdmFec129LocalRtpHeader indicates the local
         RTP header usage bit."
    ::= { vLdpCepTdmFec129Entry 8 }

vLdpCepTdmFec129RemoteRtpHeader OBJECT-TYPE
    SYNTAX      TruthValue
    MAX-ACCESS  read-only
    STATUS      current
    DESCRIPTION
        "The value of vLdpCepTdmFec129RemoteRtpHeader indicates the remote
         RTP header usage bit."
    ::= { vLdpCepTdmFec129Entry 9 }

vLdpCepTdmFec129LocalDiffTimestamp OBJECT-TYPE
    SYNTAX      TruthValue
    MAX-ACCESS  read-only
    STATUS      current
    DESCRIPTION
        "The value of vLdpCepTdmFec129LocalDiffTimestamp indicates the local
         differential (or dynamic) timestamping mode bit."
    ::= { vLdpCepTdmFec129Entry 10 }

vLdpCepTdmFec129RemoteDiffTimestamp OBJECT-TYPE
    SYNTAX      TruthValue
    MAX-ACCESS  read-only
    STATUS      current
    DESCRIPTION
        "The value of vLdpCepTdmFec129RemoteDiffTimestamp indicates the remote
         differential (or dynamic) timestamping mode bit."
    ::= { vLdpCepTdmFec129Entry 11 }

vLdpCepTdmFec129LocalSigPkts OBJECT-TYPE
    SYNTAX      TdmOptionsSigPkts
    MAX-ACCESS  read-only
    STATUS      current
    DESCRIPTION
        "The value of vLdpCepTdmFec129LocalSigPkts indicates the local
         CE application signalling packets mode."
    ::= { vLdpCepTdmFec129Entry 12 }

vLdpCepTdmFec129RemoteSigPkts OBJECT-TYPE
    SYNTAX      TdmOptionsSigPkts
    MAX-ACCESS  read-only
    STATUS      current
    DESCRIPTION
        "The value of vLdpCepTdmFec129RemoteSigPkts indicates the remote
         CE application signalling packets mode."
    ::= { vLdpCepTdmFec129Entry 13 }

vLdpCepTdmFec129LocalCasTrunk OBJECT-TYPE
    SYNTAX      TdmOptionsCasTrunkFraming
    MAX-ACCESS  read-only
    STATUS      current
    DESCRIPTION
        "The value of vLdpCepTdmFec129LocalCasTrunk indicates the local
         CE application signalling packets mode."
    ::= { vLdpCepTdmFec129Entry 14 }

vLdpCepTdmFec129RemoteCasTrunk OBJECT-TYPE
    SYNTAX      TdmOptionsCasTrunkFraming
    MAX-ACCESS  read-only
    STATUS      current
    DESCRIPTION
        "The value of vLdpCepTdmFec129RemoteCasTrunk indicates the remote
         CE application signalling packets mode."
    ::= { vLdpCepTdmFec129Entry 15 }

vLdpCepTdmFec129LocalTimestampFreq OBJECT-TYPE
    SYNTAX      Unsigned32
    UNITS       "8 KHz"
    MAX-ACCESS  read-only
    STATUS      current
    DESCRIPTION
        "The value of vLdpCepTdmFec129LocalTimestampFreq indicates the local
         CE application signalling packets mode."
    ::= { vLdpCepTdmFec129Entry 16 }

vLdpCepTdmFec129RemoteTimestampFreq OBJECT-TYPE
    SYNTAX      Unsigned32
    UNITS       "8 KHz"
    MAX-ACCESS  read-only
    STATUS      current
    DESCRIPTION
        "The value of vLdpCepTdmFec129RemoteCasTrunk indicates the remote
         CE application signalling packets mode."
    ::= { vLdpCepTdmFec129Entry 17 }

vLdpCepTdmFec129LocalPayloadType OBJECT-TYPE
    SYNTAX      Unsigned32
    MAX-ACCESS  read-only
    STATUS      current
    DESCRIPTION
        "The value of vLdpCepTdmFec129LocalPayloadType indicates the local
         payload type."
    ::= { vLdpCepTdmFec129Entry 18 }

vLdpCepTdmFec129RemotePayloadType OBJECT-TYPE
    SYNTAX      Unsigned32
    MAX-ACCESS  read-only
    STATUS      current
    DESCRIPTION
        "The value of vLdpCepTdmFec129RemotePayloadType indicates the remote
         payload type."
    ::= { vLdpCepTdmFec129Entry 19 }

vLdpCepTdmFec129LocalSsrcId OBJECT-TYPE
    SYNTAX      Unsigned32
    MAX-ACCESS  read-only
    STATUS      current
    DESCRIPTION
        "The value of vLdpCepTdmFec129LocalSsrcId indicates the local
         value of SSRC ID."
    ::= { vLdpCepTdmFec129Entry 20 }

vLdpCepTdmFec129RemoteSsrcId OBJECT-TYPE
    SYNTAX      Unsigned32
    MAX-ACCESS  read-only
    STATUS      current
    DESCRIPTION
        "The value of vLdpCepTdmFec129RemoteSsrcId indicates the remote
         value of SSRC ID."
    ::= { vLdpCepTdmFec129Entry 21 }

--
-- Notification Information
--

tmnxLdpNotificationObjects OBJECT IDENTIFIER ::= { tmnxLdpObjs 17 }

-- Trap control objects
--

vRtrLdpInstanceNotifyReasonCode    OBJECT-TYPE
    SYNTAX       INTEGER {
                    adminUp (1),
                    adminDown (2),
                    operUp (3),
                    operDown (4)
                 }
    MAX-ACCESS   accessible-for-notify
    STATUS       current
    DESCRIPTION
        "Used by vRtrLdpInstanceStateChange, the value indicates the reason
         for the LDP instance state change."
    ::= { tmnxLdpNotificationObjects 1 }

vRtrLdpIfNotifyReasonCode    OBJECT-TYPE
    SYNTAX       INTEGER {
                    adminUp (1),
                    adminDown (2),
                    operUp (3),
                    operDown (4),
                    sysIpUp (5),
                    sysIpDown (6)
                 }
    MAX-ACCESS   accessible-for-notify
    STATUS       current
    DESCRIPTION
        "Used by vRtrLdpIfStateChange, the value indicates the reason for the
         LSP interface state change."
    ::= { tmnxLdpNotificationObjects 2 }

vRtrLdpNotifyLocalServiceID     OBJECT-TYPE
    SYNTAX      TmnxServId (1..2147483647)
    MAX-ACCESS  accessible-for-notify
    STATUS      obsolete
    DESCRIPTION
        "Used by vRtrLdpSvcIdMismatch, the value indicates the local
         Service ID."
    ::= { tmnxLdpNotificationObjects 3 }

vRtrLdpNotifyRemoteServiceID      OBJECT-TYPE
    SYNTAX      TmnxServId (1..2147483647)
    MAX-ACCESS  accessible-for-notify
    STATUS      obsolete
    DESCRIPTION
        "Used by vRtrLdpSvcIdMismatch, the value indicates the remote
         Service ID."
    ::= { tmnxLdpNotificationObjects 4 }

vRtrLdpNotifyLocalGroupID     OBJECT-TYPE
    SYNTAX      TmnxVcId
    MAX-ACCESS  accessible-for-notify
    STATUS      current
    DESCRIPTION
        "Used by vRtrLdpGroupIdMismatch, the value indicates the local
         Group ID."
    ::= { tmnxLdpNotificationObjects 5 }

vRtrLdpNotifyRemoteGroupID      OBJECT-TYPE
    SYNTAX      TmnxVcId
    MAX-ACCESS  accessible-for-notify
    STATUS      current
    DESCRIPTION
        "Used by vRtrLdpGroupIdMismatch, the value indicates the remote
         Group ID."
    ::= { tmnxLdpNotificationObjects 6 }

--
-- Notification Definitions
--

vRtrLdpStateChange  NOTIFICATION-TYPE
    OBJECTS     { vRtrLdpStatus }
    STATUS      current
    DESCRIPTION
        "The vRtrLdpStateChange notification is generated when the LDP
         protocol is created or deleted in the router."
    ::= { tmnxLdpNotifications 1 }

vRtrLdpInstanceStateChange NOTIFICATION-TYPE
   OBJECTS     { vRtrLdpGenAdminState,
                 vRtrLdpGenOperState,
                 vRtrLdpInstanceNotifyReasonCode }
   STATUS      current
   DESCRIPTION
       "The vRtrLdpInstanceStateChange notification is generated when the LDP
        module changes state either administratively or operationally."
   ::= { tmnxLdpNotifications 2 }

vRtrLdpIfStateChange NOTIFICATION-TYPE
   OBJECTS     { vRtrLdpIfAdminState,
                 vRtrLdpIfOperState,
                 vRtrLdpIfNotifyReasonCode }
   STATUS      current
   DESCRIPTION
       "The vRtrLdpIfStateChange notification is generated when the LDP
        interface changes state either administratively or operationally."
   ::= { tmnxLdpNotifications 3 }

vRtrLdpSvcIdMismatch    NOTIFICATION-TYPE
    OBJECTS     { vRtrLdpNotifyLocalServiceID,
                  vRtrLdpNotifyRemoteServiceID }
    STATUS      obsolete
    DESCRIPTION
        "The vRtrLdpSvcIdMismatch notification is generated when there is
         a mismatch of local and remote service IDs."
    ::= { tmnxLdpNotifications 4 }

vRtrLdpGroupIdMismatch    NOTIFICATION-TYPE
    OBJECTS     { vRtrLdpNotifyLocalGroupID,
                  vRtrLdpNotifyRemoteGroupID }
    STATUS      current
    DESCRIPTION
        "The vRtrLdpGroupIdMismatch notification is generated when there is
         a mismatch of local and remote group IDs."
    ::= { tmnxLdpNotifications 5 }

--
-- Conformance Information
--
tmnxLdpCompliances OBJECT IDENTIFIER ::= { tmnxLdpConformance 1 }
tmnxLdpGroups      OBJECT IDENTIFIER ::= { tmnxLdpConformance 2 }

-- compliance statements

-- tmnxLdpCompliance  MODULE-COMPLIANCE
--    ::= { tmnxLdpCompliances 1 }

-- tmnxLdpR2r1Compliance  MODULE-COMPLIANCE
--    ::= { tmnxLdpCompliances 2 }

-- tmnxLdpV3v0Compliance  MODULE-COMPLIANCE
--    ::= { tmnxLdpCompliances 3 }

tmnxLdpV4v0Compliance  MODULE-COMPLIANCE
    STATUS  obsolete
    DESCRIPTION
            "The compliance statement for management of extended LDP
             on Alcatel 7x50 SR series systems 4.0 release."
    MODULE  -- this module
        MANDATORY-GROUPS {
            tmnxLdpGlobalV3v0Group,
            tmnxLdpIfV3v0Group,
            tmnxLdpAdjR2r1Group,
            tmnxLdpSessionR2r1Group,
            tmnxLdpServFecV4v0Group,
            tmnxLdpAddrFecGroup,
            tmnxLdpNotificationGroup,
            tmnxLdpStaticFecV3v0Group
            -- tmnxLdpAdjBackoffGroup
        }
    ::= { tmnxLdpCompliances 4 }

tmnxLdpV5v0Compliance  MODULE-COMPLIANCE
    STATUS  obsolete
    DESCRIPTION
            "The compliance statement for management of extended LDP
             on Alcatel 7x50 SR series systems 5.0 release."
    MODULE  -- this module
        MANDATORY-GROUPS {
            tmnxLdpGlobalV5v0Group,
            tmnxLdpIfV5v0Group,
            tmnxLdpAdjR2r1Group,
            tmnxLdpSessionV5v0Group,
            tmnxLdpServFecV5v0Group,
            tmnxLdpAddrFecV5v0Group,
            tmnxLdpNotificationGroup,
            tmnxLdpStaticFecV3v0Group
            -- tmnxLdpAdjBackoffGroup
        }
    ::= { tmnxLdpCompliances 5 }

tmnxLdpV6v0Compliance  MODULE-COMPLIANCE
    STATUS  current
    DESCRIPTION
            "The compliance statement for management of extended LDP
             on Alcatel 7x50 SR series systems 6.0 release."
    MODULE  -- this module
        MANDATORY-GROUPS {
            tmnxLdpGlobalV5v0Group,
            tmnxLdpIfV5v0Group,
            tmnxLdpAdjR2r1Group,
            tmnxLdpSessionV5v0Group,
            tmnxLdpServFecV6v0Group,
            tmnxLdpServFec129V6v0Group,
            tmnxLdpAddrFecV5v0Group,
            tmnxLdpNotificationGroup,
            tmnxLdpStaticFecV3v0Group,
            -- tmnxLdpAdjBackoffGroup
            tmnxLdpCepTdmFecV6v0Group
        }
    ::= { tmnxLdpCompliances 6 }

-- units of conformance

-- tmnxLdpGlobalGroup   OBJECT-GROUP
--    ::= { tmnxLdpGroups 1 }

-- tmnxLdpIfGroup     OBJECT-GROUP
--    ::= { tmnxLdpGroups 2 }

-- tmnxLdpAdjGroup     OBJECT-GROUP
--    ::= { tmnxLdpGroups 3 }

-- tmnxLdpSessionGroup     OBJECT-GROUP
--    ::= { tmnxLdpGroups 4 }

-- tmnxLdpServFecGroup     OBJECT-GROUP
--    ::= { tmnxLdpGroups 5 }

tmnxLdpAddrFecGroup     OBJECT-GROUP
    OBJECTS {   vRtrLdpAddrFecFlags,
                vRtrLdpAddrFecNumInLabels,
                vRtrLdpAddrFecNumOutLabels,
                vRtrLdpAddrFecInLabel1,
                vRtrLdpAddrFecInLabelStatus1,
                vRtrLdpAddrFecInLabelIfIndex1,
                vRtrLdpAddrFecInLabel2,
                vRtrLdpAddrFecInLabelStatus2,
                vRtrLdpAddrFecInLabelIfIndex2,
                vRtrLdpAddrFecInLabel3,
                vRtrLdpAddrFecInLabelStatus3,
                vRtrLdpAddrFecInLabelIfIndex3,
                vRtrLdpAddrFecInLabel4,
                vRtrLdpAddrFecInLabelStatus4,
                vRtrLdpAddrFecInLabelIfIndex4,
                vRtrLdpAddrFecInLabel5,
                vRtrLdpAddrFecInLabelStatus5,
                vRtrLdpAddrFecInLabelIfIndex5,
                vRtrLdpAddrFecOutLabel1,
                vRtrLdpAddrFecOutLabelStatus1,
                vRtrLdpAddrFecOutLabelIfIndex1,
                vRtrLdpAddrFecOutLabelNextHop1,
                vRtrLdpAddrFecOutLabel2,
                vRtrLdpAddrFecOutLabelStatus2,
                vRtrLdpAddrFecOutLabelIfIndex2,
                vRtrLdpAddrFecOutLabelNextHop2,
                vRtrLdpAddrFecOutLabel3,
                vRtrLdpAddrFecOutLabelStatus3,
                vRtrLdpAddrFecOutLabelIfIndex3,
                vRtrLdpAddrFecOutLabelNextHop3,
                vRtrLdpAddrFecOutLabel4,
                vRtrLdpAddrFecOutLabelStatus4,
                vRtrLdpAddrFecOutLabelIfIndex4,
                vRtrLdpAddrFecOutLabelNextHop4,
                vRtrLdpAddrFecOutLabel5,
                vRtrLdpAddrFecOutLabelStatus5,
                vRtrLdpAddrFecOutLabelIfIndex5,
                vRtrLdpAddrFecOutLabelNextHop5,
                vRtrLdpAddrFecMapFecType,
                vRtrLdpAddrFecMapIpPrefix,
                vRtrLdpAddrFecMapIpMask
            }
    STATUS      obsolete
    DESCRIPTION
        "The group of objects supporting management of extended LDP
         address FECs sent to or received from an LDP peer
         on Alcatel 7x50 SR series systems."
    ::= { tmnxLdpGroups 6 }

tmnxLdpNotifyObjsGroup   OBJECT-GROUP
    OBJECTS {   vRtrLdpInstanceNotifyReasonCode,
                vRtrLdpIfNotifyReasonCode,
                vRtrLdpNotifyLocalGroupID,
                vRtrLdpNotifyRemoteGroupID
            }
    STATUS      current
    DESCRIPTION
        "The group of objects supporting extended LDP notifications
         on Alcatel 7x50 SR series systems."
    ::= { tmnxLdpGroups 7 }

tmnxLdpNotificationGroup NOTIFICATION-GROUP
    NOTIFICATIONS   {   vRtrLdpStateChange,
                        vRtrLdpInstanceStateChange,
                        vRtrLdpIfStateChange,
                        vRtrLdpGroupIdMismatch
                    }
    STATUS      current
    DESCRIPTION
        "The group of notifications supporting the extended LDP feature
         on Alcatel 7x50 SR series systems."
    ::= { tmnxLdpGroups 8 }

-- tmnxLdpPolicyGroup  OBJECT-GROUP
--    ::= { tmnxLdpGroups 9 }

tmnxLdpAdjBackoffGroup  OBJECT-GROUP
    OBJECTS {   vRtrLdpAdjInitBackoff,
                vRtrLdpAdjMaxBackoff,
                vRtrLdpAdjCurrentBackoff,
                vRtrLdpAdjWaitingTime,
                vRtrLdpAdjBackoffStatus
            }
    STATUS      current
    DESCRIPTION
        "The group of objects supporting general management of extended LDP
         adjacency backoff on Alcatel 7x50 SR series systems.
         The vRtrLdpAdjBackoffTable is not yet supported by a TiMOS release."
    ::= { tmnxLdpGroups 10 }

tmnxLdpObsoleteObjsGroup   OBJECT-GROUP
    OBJECTS {   vRtrLdpNotifyLocalServiceID,
                vRtrLdpNotifyRemoteServiceID,
                vRtrLdpPolicyRowStatus,
                vRtrLdpPolicyName
            }
    STATUS      current
    DESCRIPTION
        "The group of obsolete objects for the extended LDP feature
         on Alcatel 7x50 SR series
         systems."
    ::= { tmnxLdpGroups 11 }

tmnxLdpObsoleteNotificationGroup NOTIFICATION-GROUP
    NOTIFICATIONS   {   vRtrLdpSvcIdMismatch
                    }
    STATUS      current
    DESCRIPTION
        "The group of obsolete notifications for the extended LDP feature
         on Alcatel 7x50 SR series systems."
    ::= { tmnxLdpGroups 12 }

-- tmnxLdpGlobalR2r1Group   OBJECT-GROUP
--    ::= { tmnxLdpGroups 13 }

-- tmnxLdpIfR2r1Group     OBJECT-GROUP
--    ::= { tmnxLdpGroups 14 }

tmnxLdpAdjR2r1Group     OBJECT-GROUP
    OBJECTS {   vRtrLdpHelloAdjMapLdpId,
                vRtrLdpHelloAdjLocalLdpId,
                vRtrLdpHelloAdjEntityIndex,
                vRtrLdpHelloAdjIndex,
                vRtrLdpHelloAdjHoldTimeRemaining,
                vRtrLdpHelloAdjType,
                vRtrLdpHelloAdjRemoteConfSeqNum,
                vRtrLdpHelloAdjRemoteIpAddress,
                vRtrLdpHelloAdjUpTime,
                vRtrLdpHelloAdjLocalConfSeqNum,
                vRtrLdpHelloAdjLocalIpAddress,
                vRtrLdpHelloAdjInHelloMsgCount,
                vRtrLdpHelloAdjOutHelloMsgCount,
                vRtrLdpHelloAdjLocalHelloTimeout,
                vRtrLdpHelloAdjRemoteHelloTimeout
            }
    STATUS      current
    DESCRIPTION
        "The group of objects supporting management of extended LDP
         Adjacencies for LDP sessions on Alcatel 7x50 SR series systems
         2.1 Release."
    ::= { tmnxLdpGroups 15 }

tmnxLdpSessionR2r1Group     OBJECT-GROUP
    OBJECTS {   vRtrLdpSessLocalLdpId,
                vRtrLdpSessEntityIndex,
                vRtrLdpSessLabelDistMethod,
                vRtrLdpSessLoopDetectForPV,
                vRtrLdpSessPathVectorLimit,
                vRtrLdpSessState,
                vRtrLdpSessAdjacencyType,
                vRtrLdpSessProtocolVersion,
                vRtrLdpSessLocalUdpPort,
                vRtrLdpSessPeerUdpPort,
                vRtrLdpSessLocalTcpPort,
                vRtrLdpSessPeerTcpPort,
                vRtrLdpSessLocalAddress,
                vRtrLdpSessPeerAddress,
                vRtrLdpSessKAHoldTimeRemaining,
                vRtrLdpSessMaxPduLength,
                vRtrLdpSessUpTime,
                vRtrLdpSessLocalKATimeout,
                vRtrLdpSessPeerKATimeout,
                vRtrLdpSessStatsTargAdj,
                vRtrLdpSessStatsLinkAdj,
                vRtrLdpSessStatsFECRecv,
                vRtrLdpSessStatsFECSent,
                vRtrLdpSessStatsHelloIn,
                vRtrLdpSessStatsHelloOut,
                vRtrLdpSessStatsKeepaliveIn,
                vRtrLdpSessStatsKeepaliveOut,
                vRtrLdpSessStatsInitIn,
                vRtrLdpSessStatsInitOut,
                vRtrLdpSessStatsLabelMappingIn,
                vRtrLdpSessStatsLabelMappingOut,
                vRtrLdpSessStatsLabelRequestIn,
                vRtrLdpSessStatsLabelRequestOut,
                vRtrLdpSessStatsLabelReleaseIn,
                vRtrLdpSessStatsLabelReleaseOut,
                vRtrLdpSessStatsLabelWithdrawIn,
                vRtrLdpSessStatsLabelWithdrawOut,
                vRtrLdpSessStatsLabelAbortIn,
                vRtrLdpSessStatsLabelAbortOut,
                vRtrLdpSessStatsAddrIn,
                vRtrLdpSessStatsAddrOut,
                vRtrLdpSessStatsAddrWithdrawIn,
                vRtrLdpSessStatsAddrWithdrawOut,
                vRtrLdpSessStatsNotificationIn,
                vRtrLdpSessStatsNotificationOut
            }
    STATUS      obsolete
    DESCRIPTION
        "The group of objects supporting management of extended LDP
         Sessions on Alcatel 7x50 SR series systems 2.1 Release."
    ::= { tmnxLdpGroups 16 }

tmnxLdpStaticFecV3v0Group    OBJECT-GROUP
    OBJECTS {    vRtrLdpStaticFecRowStatus,
                 vRtrLdpStaticFecNextNHIndex,
                 vRtrLdpStaticFecIngLabel,
                 vRtrLdpStaticFecNumNH,
                 vRtrLdpStaticFecOperIngLabel,
                 vRtrLdpStaticFecNHRowStatus,
                 vRtrLdpStaticFecNHType,
                 vRtrLdpStaticFecNHIpAddr,
                 vRtrLdpStaticFecNHEgrLabel
            }
    STATUS      current
    DESCRIPTION
        "The group of objects supporting management of LDP Static
         FECs on Alcatel 7x50 SR series systems 3.0 release."
    ::= { tmnxLdpGroups 17 }

-- tmnxLdpServFecV3v0Group     OBJECT-GROUP
--    ::= { tmnxLdpGroups 18 }

tmnxLdpIfV3v0Group     OBJECT-GROUP
    OBJECTS {   vRtrLdpIfTableSpinlock,
                vRtrLdpIfRowStatus,
                vRtrLdpIfLastChange,
                vRtrLdpIfAdminState,
                vRtrLdpIfOperState,
                vRtrLdpIfInheritance,
                vRtrLdpIfKeepAliveFactor,
                vRtrLdpIfKeepAliveTimeout,
                vRtrLdpIfHelloFactor,
                vRtrLdpIfHelloTimeout,
                vRtrLdpIfBackoffTime,
                vRtrLdpIfMaxBackoffTime,
                vRtrLdpIfTransportAddrType,
                vRtrLdpIfPassiveMode,
                vRtrLdpIfAutoCreate,
                vRtrLdpIfOperDownReason,
                vRtrLdpIfExistingAdjacencies,
                vRtrLdpPeerRowStatus,
                vRtrLdpPeerAuth,
                vRtrLdpPeerAuthKey,
                vRtrLdpPeerMinTTLValue,
                vRtrLdpPeerTTLLogId
            }
    STATUS      obsolete
    DESCRIPTION
        "The group of objects supporting management of extended LDP
         interfaces and targeted peers on Alcatel 7x50 SR series systems
         3.0 release."
    ::= { tmnxLdpGroups 19 }

tmnxLdpGlobalV3v0Group   OBJECT-GROUP
    OBJECTS {   vRtrLdpGenLastChange,
                vRtrLdpGenAdminState,
                vRtrLdpGenOperState,
                vRtrLdpGenLdpLsrId,
                vRtrLdpGenProtocolVersion,
                vRtrLdpGenDeaggregateFec,
                vRtrLdpGenKeepAliveFactor,
                vRtrLdpGenKeepAliveTimeout,
                vRtrLdpGenHelloFactor,
                vRtrLdpGenHelloTimeout,
                vRtrLdpGenRoutePreference,
                vRtrLdpGenControlMode,
                vRtrLdpGenDistMethod,
                vRtrLdpGenRetentionMode,
                vRtrLdpGenTransportAddrType,
                vRtrLdpGenPropagatePolicy,
                vRtrLdpGenLoopDetectCapable,
                vRtrLdpGenHopLimit,
                vRtrLdpGenPathVectorLimit,
                vRtrLdpGenBackoffTime,
                vRtrLdpGenMaxBackoffTime,
                vRtrLdpGenTargKeepAliveFactor,
                vRtrLdpGenTargKeepAliveTimeout,
                vRtrLdpGenTargHelloFactor,
                vRtrLdpGenTargHelloTimeout,
                vRtrLdpGenTargPassiveMode,
                vRtrLdpGenTargetedSessions,
                vRtrLdpGenCreateTime,
                vRtrLdpGenUpTime,
                vRtrLdpGenImportPolicy1,
                vRtrLdpGenImportPolicy2,
                vRtrLdpGenImportPolicy3,
                vRtrLdpGenImportPolicy4,
                vRtrLdpGenImportPolicy5,
                vRtrLdpGenExportPolicy1,
                vRtrLdpGenExportPolicy2,
                vRtrLdpGenExportPolicy3,
                vRtrLdpGenExportPolicy4,
                vRtrLdpGenExportPolicy5,
                vRtrLdpGenTunnelDownDampTime,
                vRtrLdpGenOperDownReason,
                vRtrLdpGenTrustList,
                vRtrLdpStatsOperDownEvents,
                vRtrLdpStatsActiveSessions,
                vRtrLdpStatsActiveAdjacencies,
                vRtrLdpStatsActiveInterfaces,
                vRtrLdpStatsInactiveInterfaces,
                vRtrLdpStatsActiveTargSessions,
                vRtrLdpStatsInactiveTargSessions,
                vRtrLdpStatsAddrFECRecv,
                vRtrLdpStatsAddrFECSent,
                vRtrLdpStatsSvcFECRecv,
                vRtrLdpStatsSvcFECSent,
                vRtrLdpStatsAttemptedSessions,
                vRtrLdpStatsSessRejNoHelloErrors,
                vRtrLdpStatsSessRejAdvErrors,
                vRtrLdpStatsSessRejMaxPduErrors,
                vRtrLdpStatsSessRejLabelRangeErrors,
                vRtrLdpStatsBadLdpIdentifierErrors,
                vRtrLdpStatsBadPduLengthErrors,
                vRtrLdpStatsBadMessageLengthErrors,
                vRtrLdpStatsBadTlvLengthErrors,
                vRtrLdpStatsMalformedTlvValueErrors,
                vRtrLdpStatsKeepAliveExpiredErrors,
                vRtrLdpStatsShutdownNotifRecv,
                vRtrLdpStatsShutdownNotifSent
            }
    STATUS      obsolete
    DESCRIPTION
        "The group of objects supporting general management of extended LDP
         on Alcatel 7x50 SR series systems 3.0 release."
    ::= { tmnxLdpGroups 20 }

tmnxLdpServFecV4v0Group     OBJECT-GROUP
    OBJECTS {   vRtrLdpServFecServType,
                vRtrLdpServFecServId,
                vRtrLdpServFecVpnId,
                vRtrLdpServFecFlags,
                vRtrLdpServFecNumInLabels,
                vRtrLdpServFecNumOutLabels,
                vRtrLdpServFecInLabel1,
                vRtrLdpServFecInLabelStatus1,
                vRtrLdpServFecInLabel2,
                vRtrLdpServFecInLabelStatus2,
                vRtrLdpServFecInLabel3,
                vRtrLdpServFecInLabelStatus3,
                vRtrLdpServFecInLabel4,
                vRtrLdpServFecInLabelStatus4,
                vRtrLdpServFecInLabel5,
                vRtrLdpServFecInLabelStatus5,
                vRtrLdpServFecOutLabel1,
                vRtrLdpServFecOutLabelStatus1,
                vRtrLdpServFecOutLabel2,
                vRtrLdpServFecOutLabelStatus2,
                vRtrLdpServFecOutLabel3,
                vRtrLdpServFecOutLabelStatus3,
                vRtrLdpServFecOutLabel4,
                vRtrLdpServFecOutLabelStatus4,
                vRtrLdpServFecOutLabel5,
                vRtrLdpServFecOutLabelStatus5,
                vRtrLdpServFecSdpId,
                vRtrLdpServFecLocalMTU,
                vRtrLdpServFecRemoteMTU,
                vRtrLdpServFecLocalVlanTag,
                vRtrLdpServFecRemoteVlanTag,
                vRtrLdpServFecLocalMaxCellConcat,
                vRtrLdpServFecRemoteMaxCellConcat,
                vRtrLdpServFecMapFecType,
                vRtrLdpServFecMapVcType,
                vRtrLdpServFecMapVcId,
                vRtrLdpServFecInLabelSigStatus1,
                vRtrLdpServFecInLabelSigStatus2,
                vRtrLdpServFecInLabelSigStatus3,
                vRtrLdpServFecInLabelSigStatus4,
                vRtrLdpServFecInLabelSigStatus5,
                vRtrLdpServFecOutLabelSigStatus1,
                vRtrLdpServFecOutLabelSigStatus2,
                vRtrLdpServFecOutLabelSigStatus3,
                vRtrLdpServFecOutLabelSigStatus4,
                vRtrLdpServFecOutLabelSigStatus5
              }
    STATUS      obsolete
    DESCRIPTION
        "The group of objects supporting management of extended LDP
         service FECs sent to or received from an LDP peer
         on Alcatel 7x50 SR series systems release 4.0."
    ::= { tmnxLdpGroups 21 }

tmnxLdpGlobalV5v0Group   OBJECT-GROUP
    OBJECTS {   vRtrLdpGenLastChange,
                vRtrLdpGenAdminState,
                vRtrLdpGenOperState,
                vRtrLdpGenLdpLsrId,
                vRtrLdpGenProtocolVersion,
                vRtrLdpGenDeaggregateFec,
                vRtrLdpGenKeepAliveFactor,
                vRtrLdpGenKeepAliveTimeout,
                vRtrLdpGenHelloFactor,
                vRtrLdpGenHelloTimeout,
                vRtrLdpGenRoutePreference,
                vRtrLdpGenControlMode,
                vRtrLdpGenDistMethod,
                vRtrLdpGenRetentionMode,
                vRtrLdpGenTransportAddrType,
                vRtrLdpGenPropagatePolicy,
                vRtrLdpGenLoopDetectCapable,
                vRtrLdpGenHopLimit,
                vRtrLdpGenPathVectorLimit,
                vRtrLdpGenBackoffTime,
                vRtrLdpGenMaxBackoffTime,
                vRtrLdpGenTargKeepAliveFactor,
                vRtrLdpGenTargKeepAliveTimeout,
                vRtrLdpGenTargHelloFactor,
                vRtrLdpGenTargHelloTimeout,
                vRtrLdpGenTargPassiveMode,
                vRtrLdpGenTargetedSessions,
                vRtrLdpGenCreateTime,
                vRtrLdpGenUpTime,
                vRtrLdpGenImportPolicy1,
                vRtrLdpGenImportPolicy2,
                vRtrLdpGenImportPolicy3,
                vRtrLdpGenImportPolicy4,
                vRtrLdpGenImportPolicy5,
                vRtrLdpGenExportPolicy1,
                vRtrLdpGenExportPolicy2,
                vRtrLdpGenExportPolicy3,
                vRtrLdpGenExportPolicy4,
                vRtrLdpGenExportPolicy5,
                vRtrLdpGenTunnelDownDampTime,
                vRtrLdpGenOperDownReason,
                vRtrLdpGenGracefulRestart,
                vRtrLdpGenGRNbrLiveTime,
                vRtrLdpGenGRMaxRecoveryTime,
                vRtrLdpTargImportPolicy1,
                vRtrLdpTargImportPolicy2,
                vRtrLdpTargImportPolicy3,
                vRtrLdpTargImportPolicy4,
                vRtrLdpTargImportPolicy5,
                vRtrLdpTargExportPolicy1,
                vRtrLdpTargExportPolicy2,
                vRtrLdpTargExportPolicy3,
                vRtrLdpTargExportPolicy4,
                vRtrLdpTargExportPolicy5,
                vRtrLdpTargTunnelPreference,
                vRtrLdpStatsOperDownEvents,
                vRtrLdpStatsActiveSessions,
                vRtrLdpStatsActiveAdjacencies,
                vRtrLdpStatsActiveInterfaces,
                vRtrLdpStatsInactiveInterfaces,
                vRtrLdpStatsActiveTargSessions,
                vRtrLdpStatsInactiveTargSessions,
                vRtrLdpStatsAddrFECRecv,
                vRtrLdpStatsAddrFECSent,
                vRtrLdpStatsSvcFECRecv,
                vRtrLdpStatsSvcFECSent,
                vRtrLdpStatsAttemptedSessions,
                vRtrLdpStatsSessRejNoHelloErrors,
                vRtrLdpStatsSessRejAdvErrors,
                vRtrLdpStatsSessRejMaxPduErrors,
                vRtrLdpStatsSessRejLabelRangeErrors,
                vRtrLdpStatsBadLdpIdentifierErrors,
                vRtrLdpStatsBadPduLengthErrors,
                vRtrLdpStatsBadMessageLengthErrors,
                vRtrLdpStatsBadTlvLengthErrors,
                vRtrLdpStatsMalformedTlvValueErrors,
                vRtrLdpStatsKeepAliveExpiredErrors,
                vRtrLdpStatsShutdownNotifRecv,
                vRtrLdpStatsShutdownNotifSent
            }
    STATUS      current
    DESCRIPTION
        "The group of objects supporting general management of extended LDP
         on Alcatel 7x50 SR series systems 5.0 release."
    ::= { tmnxLdpGroups 22 }

tmnxLdpIfV5v0Group     OBJECT-GROUP
    OBJECTS {   vRtrLdpIfTableSpinlock,
                vRtrLdpIfRowStatus,
                vRtrLdpIfLastChange,
                vRtrLdpIfAdminState,
                vRtrLdpIfOperState,
                vRtrLdpIfInheritance,
                vRtrLdpIfKeepAliveFactor,
                vRtrLdpIfKeepAliveTimeout,
                vRtrLdpIfHelloFactor,
                vRtrLdpIfHelloTimeout,
                vRtrLdpIfBackoffTime,
                vRtrLdpIfMaxBackoffTime,
                vRtrLdpIfTransportAddrType,
                vRtrLdpIfPassiveMode,
                vRtrLdpIfAutoCreate,
                vRtrLdpIfOperDownReason,
                vRtrLdpIfExistingAdjacencies,
                vRtrLdpIfTunneling,
                vRtrLdpIfLspRowStatus,
                vRtrLdpPeerRowStatus,
                vRtrLdpPeerAuth,
                vRtrLdpPeerAuthKey,
                vRtrLdpPeerMinTTLValue,
                vRtrLdpPeerTTLLogId,
                vRtrLdpPeerAuthKeyChain
            }
    STATUS      current
    DESCRIPTION
        "The group of objects supporting management of extended LDP
         interfaces and targeted peers on Alcatel 7x50 SR series systems
         5.0 release."
    ::= { tmnxLdpGroups 23 }

tmnxLdpServFecV5v0Group     OBJECT-GROUP
    OBJECTS {   vRtrLdpServFecServType,
                vRtrLdpServFecServId,
                vRtrLdpServFecVpnId,
                vRtrLdpServFecFlags,
                vRtrLdpServFecNumInLabels,
                vRtrLdpServFecNumOutLabels,
                vRtrLdpServFecInLabel1,
                vRtrLdpServFecInLabelStatus1,
                vRtrLdpServFecInLabel2,
                vRtrLdpServFecInLabelStatus2,
                vRtrLdpServFecInLabel3,
                vRtrLdpServFecInLabelStatus3,
                vRtrLdpServFecInLabel4,
                vRtrLdpServFecInLabelStatus4,
                vRtrLdpServFecInLabel5,
                vRtrLdpServFecInLabelStatus5,
                vRtrLdpServFecOutLabel1,
                vRtrLdpServFecOutLabelStatus1,
                vRtrLdpServFecOutLabel2,
                vRtrLdpServFecOutLabelStatus2,
                vRtrLdpServFecOutLabel3,
                vRtrLdpServFecOutLabelStatus3,
                vRtrLdpServFecOutLabel4,
                vRtrLdpServFecOutLabelStatus4,
                vRtrLdpServFecOutLabel5,
                vRtrLdpServFecOutLabelStatus5,
                vRtrLdpServFecSdpId,
                vRtrLdpServFecLocalMTU,
                vRtrLdpServFecRemoteMTU,
                vRtrLdpServFecLocalVlanTag,
                vRtrLdpServFecRemoteVlanTag,
                vRtrLdpServFecLocalMaxCellConcat,
                vRtrLdpServFecRemoteMaxCellConcat,
                vRtrLdpServFecMapFecType,
                vRtrLdpServFecMapVcType,
                vRtrLdpServFecMapVcId,
                vRtrLdpServFecInLabelSigStatus1,
                vRtrLdpServFecInLabelSigStatus2,
                vRtrLdpServFecInLabelSigStatus3,
                vRtrLdpServFecInLabelSigStatus4,
                vRtrLdpServFecInLabelSigStatus5,
                vRtrLdpServFecOutLabelSigStatus1,
                vRtrLdpServFecOutLabelSigStatus2,
                vRtrLdpServFecOutLabelSigStatus3,
                vRtrLdpServFecOutLabelSigStatus4,
                vRtrLdpServFecOutLabelSigStatus5,
                vRtrLdpServFecMateEndpointVcId,
                vRtrLdpServFecMateEndpointSdpId
              }
    STATUS      obsolete
    DESCRIPTION
        "The group of objects supporting management of extended LDP
         service FECs sent to or received from an LDP peer
         on Alcatel 7x50 SR series systems release 5.0."
    ::= { tmnxLdpGroups 24 }

tmnxLdpAddrFecV5v0Group     OBJECT-GROUP
    OBJECTS {   vRtrLdpAddrFecFlags,
                vRtrLdpAddrFecNumInLabels,
                vRtrLdpAddrFecNumOutLabels,
                vRtrLdpAddrFecInLabel1,
                vRtrLdpAddrFecInLabelStatus1,
                vRtrLdpAddrFecInLabelIfIndex1,
                vRtrLdpAddrFecInLabel2,
                vRtrLdpAddrFecInLabelStatus2,
                vRtrLdpAddrFecInLabelIfIndex2,
                vRtrLdpAddrFecInLabel3,
                vRtrLdpAddrFecInLabelStatus3,
                vRtrLdpAddrFecInLabelIfIndex3,
                vRtrLdpAddrFecInLabel4,
                vRtrLdpAddrFecInLabelStatus4,
                vRtrLdpAddrFecInLabelIfIndex4,
                vRtrLdpAddrFecInLabel5,
                vRtrLdpAddrFecInLabelStatus5,
                vRtrLdpAddrFecInLabelIfIndex5,
                vRtrLdpAddrFecOutLabel1,
                vRtrLdpAddrFecOutLabelStatus1,
                vRtrLdpAddrFecOutLabelIfIndex1,
                vRtrLdpAddrFecOutLabelNextHop1,
                vRtrLdpAddrFecOutLabel2,
                vRtrLdpAddrFecOutLabelStatus2,
                vRtrLdpAddrFecOutLabelIfIndex2,
                vRtrLdpAddrFecOutLabelNextHop2,
                vRtrLdpAddrFecOutLabel3,
                vRtrLdpAddrFecOutLabelStatus3,
                vRtrLdpAddrFecOutLabelIfIndex3,
                vRtrLdpAddrFecOutLabelNextHop3,
                vRtrLdpAddrFecOutLabel4,
                vRtrLdpAddrFecOutLabelStatus4,
                vRtrLdpAddrFecOutLabelIfIndex4,
                vRtrLdpAddrFecOutLabelNextHop4,
                vRtrLdpAddrFecOutLabel5,
                vRtrLdpAddrFecOutLabelStatus5,
                vRtrLdpAddrFecOutLabelIfIndex5,
                vRtrLdpAddrFecOutLabelNextHop5,
                vRtrLdpAddrFecLspId,
                vRtrLdpAddrFecMapFecType,
                vRtrLdpAddrFecMapIpPrefix,
                vRtrLdpAddrFecMapIpMask
            }
    STATUS      current
    DESCRIPTION
        "The group of objects supporting management of extended LDP
         address FECs sent to or received from an LDP peer
         on Alcatel 7x50 SR series systems for release 5.0."
    ::= { tmnxLdpGroups 25 }

tmnxLdpSessionV5v0Group     OBJECT-GROUP
    OBJECTS {   vRtrLdpSessLocalLdpId,
                vRtrLdpSessEntityIndex,
                vRtrLdpSessLabelDistMethod,
                vRtrLdpSessLoopDetectForPV,
                vRtrLdpSessPathVectorLimit,
                vRtrLdpSessState,
                vRtrLdpSessAdjacencyType,
                vRtrLdpSessProtocolVersion,
                vRtrLdpSessLocalUdpPort,
                vRtrLdpSessPeerUdpPort,
                vRtrLdpSessLocalTcpPort,
                vRtrLdpSessPeerTcpPort,
                vRtrLdpSessLocalAddress,
                vRtrLdpSessPeerAddress,
                vRtrLdpSessKAHoldTimeRemaining,
                vRtrLdpSessMaxPduLength,
                vRtrLdpSessUpTime,
                vRtrLdpSessLocalKATimeout,
                vRtrLdpSessPeerKATimeout,
                vRtrLdpSessAdvertise,
                vRtrLdpSessRestartHelperState,
                vRtrLdpSessPeerNumRestart,
                vRtrLdpSessLastRestartTime,
                vRtrLdpSessFtReconnectTimeNego,
                vRtrLdpSessFtRecoveryTimeNego,
                vRtrLdpSessFtReconTimeRemaining,
                vRtrLdpSessFtRecovTimeRemaining,
                vRtrLdpSessStatsTargAdj,
                vRtrLdpSessStatsLinkAdj,
                vRtrLdpSessStatsFECRecv,
                vRtrLdpSessStatsFECSent,
                vRtrLdpSessStatsHelloIn,
                vRtrLdpSessStatsHelloOut,
                vRtrLdpSessStatsKeepaliveIn,
                vRtrLdpSessStatsKeepaliveOut,
                vRtrLdpSessStatsInitIn,
                vRtrLdpSessStatsInitOut,
                vRtrLdpSessStatsLabelMappingIn,
                vRtrLdpSessStatsLabelMappingOut,
                vRtrLdpSessStatsLabelRequestIn,
                vRtrLdpSessStatsLabelRequestOut,
                vRtrLdpSessStatsLabelReleaseIn,
                vRtrLdpSessStatsLabelReleaseOut,
                vRtrLdpSessStatsLabelWithdrawIn,
                vRtrLdpSessStatsLabelWithdrawOut,
                vRtrLdpSessStatsLabelAbortIn,
                vRtrLdpSessStatsLabelAbortOut,
                vRtrLdpSessStatsAddrIn,
                vRtrLdpSessStatsAddrOut,
                vRtrLdpSessStatsAddrWithdrawIn,
                vRtrLdpSessStatsAddrWithdrawOut,
                vRtrLdpSessStatsNotificationIn,
                vRtrLdpSessStatsNotificationOut
            }
    STATUS      current
    DESCRIPTION
        "The group of objects supporting management of extended LDP
         Sessions on Alcatel 7x50 SR series systems 5.0 Release."
    ::= { tmnxLdpGroups 26 }

tmnxLdpObsoletedV5v0Group     OBJECT-GROUP
    OBJECTS {
                vRtrLdpGenTrustList
            }
    STATUS      current
    DESCRIPTION
        "The group of objects obsoleted on Alcatel 7x50 SR series
         systems 5.0 Release."
    ::= { tmnxLdpGroups 27 }

tmnxLdpCepTdmFecV6v0Group     OBJECT-GROUP
    OBJECTS {
                vRtrLdpCepTdmLocalPayloadSize,
                vRtrLdpCepTdmRemotePayloadSize,
                vRtrLdpCepTdmLocalBitrate,
                vRtrLdpCepTdmRemoteBitrate,
                vRtrLdpCepTdmLocalRtpHeader,
                vRtrLdpCepTdmRemoteRtpHeader,
                vRtrLdpCepTdmLocalDiffTimestamp,
                vRtrLdpCepTdmRemoteDiffTimestamp,
                vRtrLdpCepTdmLocalSigPkts,
                vRtrLdpCepTdmRemoteSigPkts,
                vRtrLdpCepTdmLocalCasTrunk,
                vRtrLdpCepTdmRemoteCasTrunk,
                vRtrLdpCepTdmLocalTimestampFreq,
                vRtrLdpCepTdmRemoteTimestampFreq,
                vRtrLdpCepTdmLocalPayloadType,
                vRtrLdpCepTdmRemotePayloadType,
                vRtrLdpCepTdmLocalSsrcId,
                vRtrLdpCepTdmRemoteSsrcId,
                vLdpCepTdmFec129LocalPayloadSize,
                vLdpCepTdmFec129RemotePayloadSize,
                vLdpCepTdmFec129LocalBitrate,
                vLdpCepTdmFec129RemoteBitrate,
                vLdpCepTdmFec129LocalRtpHeader,
                vLdpCepTdmFec129RemoteRtpHeader,
                vLdpCepTdmFec129LocalDiffTimestamp,
                vLdpCepTdmFec129RemoteDiffTimestamp,
                vLdpCepTdmFec129LocalSigPkts,
                vLdpCepTdmFec129RemoteSigPkts,
                vLdpCepTdmFec129LocalCasTrunk,
                vLdpCepTdmFec129RemoteCasTrunk,
                vLdpCepTdmFec129LocalTimestampFreq,
                vLdpCepTdmFec129RemoteTimestampFreq,
                vLdpCepTdmFec129LocalPayloadType,
                vLdpCepTdmFec129RemotePayloadType,
                vLdpCepTdmFec129LocalSsrcId,
                vLdpCepTdmFec129RemoteSsrcId
     }
    STATUS      current
    DESCRIPTION
        "The group of objects supporting management of extended LDP
         CEP/TDM FECs sent to or received from an LDP peer
         on Alcatel 7x50 SR series systems release 6.0."
    ::= { tmnxLdpGroups 28 }

tmnxLdpServFecV6v0Group     OBJECT-GROUP
    OBJECTS {   vRtrLdpServFecServType,
                vRtrLdpServFecServId,
                vRtrLdpServFecVpnId,
                vRtrLdpServFecFlags,
                vRtrLdpServFecNumInLabels,
                vRtrLdpServFecNumOutLabels,
                vRtrLdpServFecInLabel1,
                vRtrLdpServFecInLabelStatus1,
                vRtrLdpServFecInLabel2,
                vRtrLdpServFecInLabelStatus2,
                vRtrLdpServFecInLabel3,
                vRtrLdpServFecInLabelStatus3,
                vRtrLdpServFecInLabel4,
                vRtrLdpServFecInLabelStatus4,
                vRtrLdpServFecInLabel5,
                vRtrLdpServFecInLabelStatus5,
                vRtrLdpServFecOutLabel1,
                vRtrLdpServFecOutLabelStatus1,
                vRtrLdpServFecOutLabel2,
                vRtrLdpServFecOutLabelStatus2,
                vRtrLdpServFecOutLabel3,
                vRtrLdpServFecOutLabelStatus3,
                vRtrLdpServFecOutLabel4,
                vRtrLdpServFecOutLabelStatus4,
                vRtrLdpServFecOutLabel5,
                vRtrLdpServFecOutLabelStatus5,
                vRtrLdpServFecSdpId,
                vRtrLdpServFecLocalMTU,
                vRtrLdpServFecRemoteMTU,
                vRtrLdpServFecLocalVlanTag,
                vRtrLdpServFecRemoteVlanTag,
                vRtrLdpServFecLocalMaxCellConcat,
                vRtrLdpServFecRemoteMaxCellConcat,
                vRtrLdpServFecInLabelSigStatus1,
                vRtrLdpServFecInLabelSigStatus2,
                vRtrLdpServFecInLabelSigStatus3,
                vRtrLdpServFecInLabelSigStatus4,
                vRtrLdpServFecInLabelSigStatus5,
                vRtrLdpServFecOutLabelSigStatus1,
                vRtrLdpServFecOutLabelSigStatus2,
                vRtrLdpServFecOutLabelSigStatus3,
                vRtrLdpServFecOutLabelSigStatus4,
                vRtrLdpServFecOutLabelSigStatus5,
                vRtrLdpServFecMateEndpointVcId,
                vRtrLdpServFecMateEndpointSdpId
              }
    STATUS      current
    DESCRIPTION
        "The group of objects supporting management of extended LDP
         service FECs sent to or received from an LDP peer
         on Alcatel 7x50 SR series systems release 6.0."
    ::= { tmnxLdpGroups 29 }

tmnxLdpServFec129V6v0Group     OBJECT-GROUP
    OBJECTS {
             vLdpServFec129ServType,
             vLdpServFec129ServId,
             vLdpServFec129VpnId,
             vLdpServFec129Flags,
             vLdpServFec129NumInLabels,
             vLdpServFec129NumOutLabels,
             vLdpServFec129InLabel1,
             vLdpServFec129InLabelStatus1,
             vLdpServFec129OutLabel1,
             vLdpServFec129OutLabelStatus1,
             vLdpServFec129SdpId,
             vLdpServFec129LocalMTU,
             vLdpServFec129RemoteMTU,
             vLdpServFec129LocalVlanTag,
             vLdpServFec129RemoteVlanTag,
             vLdpServFec129LocalMaxCellConcat,
             vLdpServFec129RemoteMaxCellConcat,
             vLdpServFec129InLabelSigStatus1,
             vLdpServFec129OutLabelSigStatus1
     }
    STATUS      current
    DESCRIPTION
        "The group of objects supporting management of LDP
         FEC-129s sent to or received from an LDP peer
         on Alcatel 7x50 SR series systems release 6.0."
    ::= { tmnxLdpGroups 30 }

tmnxLdpServFecObsoletedV6v0Group     OBJECT-GROUP
    OBJECTS {
             vRtrLdpServFecMapFecType,
             vRtrLdpServFecMapVcType,
             vRtrLdpServFecMapVcId,
             vLdpServFec129MapVcType,
             vLdpServFec129MapAgiTlv,
             vLdpServFec129MapSrcAiiTlv,
             vLdpServFec129MapTgtAiiTlv
     }
    STATUS      current
    DESCRIPTION
        "The group of objects supporting management of obsoleted LDP
         FEC objects on Alcatel 7x50 SR series systems release 6.0."
    ::= { tmnxLdpGroups 31 }

END
