CT-DS0ent-MIB DEFINITIONS ::= BEGIN

        --  ct-dsoent-mib.txt
        --  Revision: 01.00.00
        --  Part Number:
        --  Date: February 8, 1999

        --  Cabletron Systems, Inc.
        --  35 Industrial Way, P.O. Box 5005
        --  Rochester, NH 03867-0505
        --  (603) 332-9400
        --  support@ctron.com

        --  This module provides authoritative definitions for Cabletron's
        --  enterprise DS0 mib.
        --
        --  This module will be extended, as required.
        --

        --  Cabletron Systems reserves the right to make changes in
        --  specification and other information contained in this document
        --  without prior notice.  The reader should consult Cabletron
        --  Systems to determine whether any such changes have been made.
        --
        --  In no event shall Cabletron Systems be liable for any
        --  incidental, indirect, special, or consequential damages
        --  whatsoever (including but not limited to lost profits) arising
        --  out of or related to this document or the information contained
        --  in it, even if Cabletron Systems has been advised of, known,
        --  or should have known, the possibility of such damages.
        --
        --  Cabletron grants vendors, end-users, and other interested
        --  parties a non-exclusive license to use this Specification in
        --  connection with the management of Cabletron products.

        --  Copyright (c)1998 Cabletron Systems

 IMPORTS

    OBJECT-TYPE			FROM RFC-1212

    Counter, Gauge, TimeTicks	FROM RFC1155-SMI

    PhysAddress, DisplayString		FROM SNMPv2-TC

    cabletron			FROM CTRON-OIDS;

ctSSA OBJECT IDENTIFIER ::= { cabletron 4497 }

ctDs0Mib OBJECT IDENTIFIER ::= { ctSSA 20 }

ctDsx0Mib OBJECT IDENTIFIER ::= { ctSSA 21 }

InterfaceIndex ::= INTEGER
-- TEXTUAL-CONVENTION
--  DspHint
--    d
--  Status
--    mandatory
--  Descr
--    A unique value, greater than zero, for each interface
--    or interface sub-layer in the managed system.  It is
--    recommended that values are assigned contiguously
--    starting from 1.  The value for each interface sub-
--    layer must remain constant at least from one re-
--    initialization of the entity's network management
--    system to the next re-initialization.

ctDs0ifNumber OBJECT-TYPE
    SYNTAX INTEGER
    ACCESS read-only
    STATUS mandatory
    DESCRIPTION
        "The number of network interfaces (regardless of their
        current state) present on this system."
    ::= { ctDs0Mib 1 }

ctDs0ifTable OBJECT-TYPE
    SYNTAX SEQUENCE OF CtDs0ifEntry
    ACCESS not-accessible
    STATUS mandatory
    DESCRIPTION
        "A list of interface entries.  The number of entries
        is given by the value of ctDs0ifNumber."
    ::= { ctDs0Mib 2 }

ctDs0ifEntry OBJECT-TYPE
    SYNTAX CtDs0ifEntry
    ACCESS not-accessible
    STATUS mandatory
    DESCRIPTION
        "An entry containing management information applicable
        to a particular interface."
    INDEX { ctDs0ifIndex }
    ::= { ctDs0ifTable 1 }

CtDs0ifEntry ::= SEQUENCE {
    ctDs0ifIndex InterfaceIndex,
    ctDs0ifDescr DisplayString,
    ctDs0ifType IANActDs0ifType,
    ctDs0ifMtu INTEGER,
    ctDs0ifSpeed Gauge,
    ctDs0ifPhysAddress PhysAddress,
    ctDs0ifAdminStatus INTEGER,
    ctDs0ifOperStatus INTEGER,
    ctDs0ifLastChange TimeTicks,
    ctDs0ifInOctets Counter,
    ctDs0ifInUcastPkts Counter,
    ctDs0ifInNUcastPkts Counter,
    ctDs0ifInDiscards Counter,
    ctDs0ifInErrors Counter,
    ctDs0ifInUnknownProtos Counter,
    ctDs0ifOutOctets Counter,
    ctDs0ifOutUcastPkts Counter,
    ctDs0ifOutNUcastPkts Counter,
    ctDs0ifOutDiscards Counter,
    ctDs0ifOutErrors Counter,
    ctDs0ifOutQLen Gauge,
    ctDs0ifSpecific OBJECT IDENTIFIER
    }

ctDs0ifIndex OBJECT-TYPE
    SYNTAX InterfaceIndex(0..2147483647)
--    Rsyntax INTEGER(0..2147483647)
    ACCESS read-only
    STATUS mandatory
    DESCRIPTION
        "A unique value, greater than zero, for each
        interface.  It is recommended that values are assigned
        contiguously starting from 1.  The value for each
        interface sub-layer must remain constant at least from
        one re-initialization of the entity's network
        management system to the next re-initialization."
    ::= { ctDs0ifEntry 1 }

ctDs0ifDescr OBJECT-TYPE
    SYNTAX DisplayString(SIZE(0..255))
--    Rsyntax OCTET STRING(SIZE(0..255))
    ACCESS read-only
    STATUS mandatory
    DESCRIPTION
        "A textual string containing information about the
        interface.  This string should include the name of the
        manufacturer, the product name and the version of the
        interface hardware/software."
    ::= { ctDs0ifEntry 2 }

ctDs0ifType OBJECT-TYPE
    SYNTAX IANActDs0ifType
--    Rsyntax INTEGER {
--        other(1),
--        regular1822(2),
--        hdh1822(3),
--        ddnX25(4),
--        rfc877x25(5),
--        ethernetCsmacd(6),
--        iso88023Csmacd(7),
--        iso88024TokenBus(8),
--        iso88025TokenRing(9),
--        iso88026Man(10),
--        starLan(11),
--        proteon10Mbit(12),
--        proteon80Mbit(13),
--        hyperchannel(14),
--        fddi(15),
--        lapb(16),
--        sdlc(17),
--        ds1(18),
--        e1(19),
--        basicISDN(20),
--        primaryISDN(21),
--        propPointToPointSerial(22),
--        ppp(23),
--        softwareLoopback(24),
--        eon(25),
--        ethernet3Mbit(26),
--        nsip(27),
--        slip(28),
--        ultra(29),
--        ds3(30),
--        sip(31),
--        frameRelay(32),
--        rs232(33),
--        para(34),
--        arcnet(35),
--        arcnetPlus(36),
--        atm(37),
--        miox25(38),
--        sonet(39),
--        x25ple(40),
--        iso88022llc(41),
--        localTalk(42),
--        smdsDxi(43),
--        frameRelayService(44),
--        v35(45),
--        hssi(46),
--        hippi(47),
--        modem(48),
--        aal5(49),
--        sonetPath(50),
--        sonetVT(51),
--        smdsIcip(52),
--        propVirtual(53),
--        propMultiplexor(54)
--        }
    ACCESS read-only
    STATUS mandatory
    DESCRIPTION
        "The type of interface.  Additional values for ctDs0ifType
        are assigned by the Internet Assigned Numbers
        Authority (IANA), through updating the syntax of the
        IANAifType textual convention."
    ::= { ctDs0ifEntry 3 }

ctDs0ifMtu OBJECT-TYPE
    SYNTAX INTEGER
    ACCESS read-only
    STATUS mandatory
    DESCRIPTION
        "The size of the largest packet which can be
        sent/received on the interface, specified in octets.
        For interfaces that are used for transmitting network
        datagrams, this is the size of the largest network
        datagram that can be sent on the interface."
    ::= { ctDs0ifEntry 4 }

ctDs0ifSpeed OBJECT-TYPE
    SYNTAX Gauge
    ACCESS read-only
    STATUS mandatory
    DESCRIPTION
        "An estimate of the interface's current bandwidth in
        bits per second.  For interfaces which do not vary in
        bandwidth or for those where no accurate estimation
        can be made, this object should contain the nominal
        bandwidth.  If the bandwidth of the interface is
        greater than the maximum value reportable by this
        object then this object should report its maximum
        value (4,294,967,295) and ctDs0ifHighSpeed must be used to
        report the interace's speed.  For a sub-layer which
        has no concept of bandwidth, this object should be
        zero."
    ::= { ctDs0ifEntry 5 }

ctDs0ifPhysAddress OBJECT-TYPE
    SYNTAX PhysAddress
--    Rsyntax OCTET STRING
    ACCESS read-only
    STATUS mandatory
    DESCRIPTION
        "The interface's address at its protocol sub-layer.
        The interface's media-specific MIB must define the bit
        and byte ordering and format of the value contained by
        this object.  For interfaces which do not have such an
        address (e.g., a serial line), this object should
        contain an octet string of zero length."
    ::= { ctDs0ifEntry 6 }

ctDs0ifAdminStatus OBJECT-TYPE
    SYNTAX INTEGER {
        up(1),
        down(2),
        testing(3)
        }
    ACCESS read-write
    STATUS mandatory
    DESCRIPTION
        "The desired state of the interface.  The testing(3)
        state indicates that no operational packets can be
        passed.  When a managed system initializes, all
        interfaces start with ctDs0ifAdminStatus in the down(2)
        state.  As a result of either explicit management
        action or per configuration information retained by
        the managed system, ctDs0ifAdminStatus is then changed to
        either the up(1) or testing(3) states (or remains in
        the down(2) state)."
    ::= { ctDs0ifEntry 7 }

ctDs0ifOperStatus OBJECT-TYPE
    SYNTAX INTEGER {
        up(1),
        down(2),
        testing(3),
        unknown(4),
        dormant(5)
        }
    ACCESS read-only
    STATUS mandatory
    DESCRIPTION
        "The current operational state of the interface.  The
        testing(3) state indicates that no operational packets
        can be passed.  If ctDs0ifAdminStatus is down(2) then
        ctDs0ifOperStatus should be down(2).  If ctDs0ifAdminStatus is
        changed to up(1) then ctDs0ifOperStatus should change to
        up(1) if the interface is ready to transmit and
        receive network traffic; it should change to
        dormant(5) if the interface is waiting for external
        actions (such as a serial line waiting for an
        incomming connection); it should remain in the down(2)
        state if and only if there is a fault that prevents if
        from going to the up(1) state."
    ::= { ctDs0ifEntry 8 }

ctDs0ifLastChange OBJECT-TYPE
    SYNTAX TimeTicks
    ACCESS read-only
    STATUS mandatory
    DESCRIPTION
        "The value of sysUpTime at the time the interface
        entered its current operational state.  If the current
        state was entered prior to the last re-initialization
        of the local network management subsystem, then this
        object contains a zero value."
    ::= { ctDs0ifEntry 9 }

ctDs0ifInOctets OBJECT-TYPE
    SYNTAX Counter
    ACCESS read-only
    STATUS mandatory
    DESCRIPTION
        "The total number of octets received on the interface,
        including framing characters."
    ::= { ctDs0ifEntry 10 }

ctDs0ifInUcastPkts OBJECT-TYPE
    SYNTAX Counter
    ACCESS read-only
    STATUS mandatory
    DESCRIPTION
        "The number of packets, delivered by this sub-layer to
        a higher (sub-)layer, which were not addressed to a
        multicast or broadcast address at this sub-layer."
    ::= { ctDs0ifEntry 11 }

ctDs0ifInNUcastPkts OBJECT-TYPE
    SYNTAX Counter
    ACCESS read-only
    STATUS deprecated
    DESCRIPTION
        "The number of packets, delivered by this sub-layer to
        a higher (sub-)layer, which were addressed to a
        multicast or broadcast address at this sub-layer.
        This object is deprecated in favour of
        ctDs0ifInMulticastPkts and ctDs0ifInBroadcastPkts."
    ::= { ctDs0ifEntry 12 }

ctDs0ifInDiscards OBJECT-TYPE
    SYNTAX Counter
    ACCESS read-only
    STATUS mandatory
    DESCRIPTION
        "The number of inbound packets which were chosen to be
        discarded even though no errors had been detected to
        prevent their being deliverable to a higher-layer
        protocol.  One possible reason for discarding such a
        packet could be to free up buffer space."
    ::= { ctDs0ifEntry 13 }

ctDs0ifInErrors OBJECT-TYPE
    SYNTAX Counter
    ACCESS read-only
    STATUS mandatory
    DESCRIPTION
        "For packet-oriented interfaces, the number of inbound
        packets that contained errors preventing them from
        being deliverable to a higher-layer protocol.  For
        character-oriented or fixed-length interfaces, the
        number of inbound transmission units that contained
        errors preventing them from being deliverable to a
        higher-layer protocol."
    ::= { ctDs0ifEntry 14 }

ctDs0ifInUnknownProtos OBJECT-TYPE
    SYNTAX Counter
    ACCESS read-only
    STATUS mandatory
    DESCRIPTION
        "For packet-oriented interfaces, the number of packets
        received via the interface which were discarded
        because of an unknown or unsupported protocol.  For
        character-oriented or fixed-length interfaces which
        support protocol multiplexing the number of
        transmission units received via the interface which
        were discarded because of an unknown or unsupported
        protocol.  For any interface which does not support
        protocol multiplexing, this counter will always be 0."
    ::= { ctDs0ifEntry 15 }

ctDs0ifOutOctets OBJECT-TYPE
    SYNTAX Counter
    ACCESS read-only
    STATUS mandatory
    DESCRIPTION
        "The total number of octets transmitted out of the
        interface, including framing characters."
    ::= { ctDs0ifEntry 16 }

ctDs0ifOutUcastPkts OBJECT-TYPE
    SYNTAX Counter
    ACCESS read-only
    STATUS mandatory
    DESCRIPTION
        "The total number of packets that higher-level
        protocols requested be transmitted, and which were not
        addressed to a multicast or broadcast address at this
        sub-layer, including those that were discarded or not
        sent."
    ::= { ctDs0ifEntry 17 }

ctDs0ifOutNUcastPkts OBJECT-TYPE
    SYNTAX Counter
    ACCESS read-only
    STATUS deprecated
    DESCRIPTION
        "The total number of packets that higher-level
        protocols requested be transmitted, and which were
        addressed to a multicast or broadcast address at this
        sub-layer, including those that were discarded or not
        sent.

        This object is deprecated in favour of
        ctDs0ifOutMulticastPkts and ctDs0ifOutBroadcastPkts."
    ::= { ctDs0ifEntry 18 }

ctDs0ifOutDiscards OBJECT-TYPE
    SYNTAX Counter
    ACCESS read-only
    STATUS mandatory
    DESCRIPTION
        "The number of outbound packets which were chosen to
        be discarded even though no errors had been detected
        to prevent their being transmitted.  One possible
        reason for discarding such a packet could be to free
        up buffer space."
    ::= { ctDs0ifEntry 19 }

ctDs0ifOutErrors OBJECT-TYPE
    SYNTAX Counter
    ACCESS read-only
    STATUS mandatory
    DESCRIPTION
        "For packet-oriented interfaces, the number of
        outbound packets that could not be transmitted because
        of errors.  For character-oriented or fixed-length
        interfaces, the number of outbound transmission units
        that could not be transmitted because of errors."
    ::= { ctDs0ifEntry 20 }

ctDs0ifOutQLen OBJECT-TYPE
    SYNTAX Gauge
    ACCESS read-only
    STATUS deprecated
    DESCRIPTION
        "The length of the output packet queue (in packets)."
    ::= { ctDs0ifEntry 21 }

ctDs0ifSpecific OBJECT-TYPE
    SYNTAX OBJECT IDENTIFIER
    ACCESS read-only
    STATUS deprecated
    DESCRIPTION
        "A reference to MIB definitions specific to the
        particular media being used to realize the interface.
        It is recommended that this value point to an instance
        of a MIB object in the media-specific MIB, i.e., that
        this object have the semantics associated with the
        InstancePointer textual convention defined in RFC
        1443.  In fact, it is recommended that the media-
        specific MIB specify what value ifSpecific should/can
        take for values of ifType.  If no MIB definitions
        specific to the particular media are available, the
        value should be set to the OBJECT IDENTIFIER { 0 0 }."
    ::= { ctDs0ifEntry 22 }

IANActDs0ifType ::= INTEGER {
        other(1),
        regular1822(2),
        hdh1822(3),
        ddnX25(4),
        rfc877x25(5),
        ethernetCsmacd(6),
        iso88023Csmacd(7),
        iso88024TokenBus(8),
        iso88025TokenRing(9),
        iso88026Man(10),
        starLan(11),
        proteon10Mbit(12),
        proteon80Mbit(13),
        hyperchannel(14),
        fddi(15),
        lapb(16),
        sdlc(17),
        ds1(18),
        e1(19),
        basicISDN(20),
        primaryISDN(21),
        propPointToPointSerial(22),
        ppp(23),
        softwareLoopback(24),
        eon(25),
        ethernet3Mbit(26),
        nsip(27),
        slip(28),
        ultra(29),
        ds3(30),
        sip(31),
        frameRelay(32),
        rs232(33),
        para(34),
        arcnet(35),
        arcnetPlus(36),
        atm(37),
        miox25(38),
        sonet(39),
        x25ple(40),
        iso88022llc(41),
        localTalk(42),
        smdsDxi(43),
        frameRelayService(44),
        v35(45),
        hssi(46),
        hippi(47),
        modem(48),
        aal5(49),
        sonetPath(50),
        sonetVT(51),
        smdsIcip(52),
        propVirtual(53),
        propMultiplexor(54)
        }
-- TEXTUAL-CONVENTION
--  Status
--    mandatory
--  Descr
--    This data type is used as the syntax of the ifType
--    object in the (updated) definition of MIB-II's
--    ifTable.
--
--    The definition of this textual convention with the
--    addition of newly assigned values is published
--    periodically by the IANA, in either the Assigned
--    Numbers RFC, or some derivative of it specific to
--    Internet Network Management number assignments.  (The
--    latest arrangements can be obtained by contacting the
--    IANA.)
--
--    Requests for new values should be made to IANA via
--    email (iana@isi.edu).
--
--    The relationship between the assignment of ifType
--    values and of OIDs to particular media-specific MIBs
--    is solely the purview of IANA and is subject to change
--    without notice.  Quite often, a media-specific MIB's
--    OID-subtree assignment within MIB-II's 'transmission'
--    subtree will be the same as its ifType value.
--    However, in some circumstances this will not be the
--    case, and implementors must not pre-assume any
--    specific relationship between ifType values and
--    transmission subtree OIDs.

ctDsx0ConfigTable OBJECT-TYPE
    SYNTAX  SEQUENCE OF CtDsx0ConfigEntry
    ACCESS  not-accessible
    STATUS  mandatory
    DESCRIPTION
           "ISDN lapd table containing configuration and
             operational parameters for all ISDN signaling
             channels on this managed device."
    ::= { ctDsx0Mib  1 }

ctDsx0ConfigEntry OBJECT-TYPE
    SYNTAX  CtDsx0ConfigEntry
    ACCESS  not-accessible
    STATUS  mandatory
    DESCRIPTION
           "An entry in the ISDN Lapd Table."
    INDEX   { ctDs0ifIndex }
    ::= { ctDsx0ConfigTable  1 }

CtDsx0ConfigEntry ::=
    SEQUENCE {
        ctDsx0ConfigLineId
            DisplayString,

        ctDsx0ConfigAdminStatus
            INTEGER,

        ctDsx0ConfigOperStatus
            INTEGER
    }

ctDsx0ConfigLineId OBJECT-TYPE
    SYNTAX  DisplayString
    ACCESS  read-only
    STATUS  mandatory
    DESCRIPTION
           "Line id of the Isdn Lapd table entry"
    ::= { ctDsx0ConfigEntry  1 }

ctDsx0ConfigAdminStatus OBJECT-TYPE
    SYNTAX  INTEGER {
       up(1),
       down(2),
       testing(3),
       unknown(4),
       dormant(5),
       notPresent(6),
       lowerLayerDown(7)
    }
    ACCESS  read-write
    STATUS  mandatory
    DESCRIPTION
           "Administration status for the Isdn Lapd table entry."
    ::= { ctDsx0ConfigEntry  2 }

ctDsx0ConfigOperStatus OBJECT-TYPE
    SYNTAX  INTEGER {
       up(1),
       down(2),
       testing(3),
       unknown(4),
       dormant(5),
       notPresent(6),
       lowerLayerDown(7)
    }
    ACCESS  read-only
    STATUS  mandatory
    DESCRIPTION
           "Operational status for the Isdn Lapd table entry."
    ::= { ctDsx0ConfigEntry  3 }

END
