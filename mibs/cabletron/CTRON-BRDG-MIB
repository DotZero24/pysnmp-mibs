CTRON-BRDG-MIB DEFINITIONS ::= BEGIN

    --  ctron-brdg-mib.txt
    --  Revision: 1.00
    --  Date: August 14, 1992

    --  Cabletron Systems, Inc.
    --  35 Industrial Way, P.O. Box 5005
    --  Rochester, NH 03867-0505
    --  (603) 332-9400
    --  support@ctron.com

    --  This module provides authoritative definitions for Cabletron's
    --  enterprise-specific bridge MIB.
    --
    --  This module will be extended, as required.
    --

    --  Cabletron Systems reserves the right to make changes in
    --  specification and other information contained in this document
    --  without prior notice.  The reader should consult Cabletron Systems
    --  to determine whether any such changes have been made.
    --
    --  In no event shall Cabletron Systems be liable for any incidental,
    --  indirect, special, or consequential damages whatsoever (including
    --  but not limited to lost profits) arising out of or related to this
    --  document or the information contained in it, even if Cabletron
    --  Systems has been advised of, known, or should have known, the
    --  possibility of such damages.
    --
    --  Cabletron grants vendors, end-users, and other interested parties
    --  a non-exclusive license to use this Specification in connection
    --  with the management of Cabletron products.

    --  Copyright August 92 Cabletron Systems

    IMPORTS
             OBJECT-TYPE         FROM RFC-1212

             Counter             FROM RFC-1155-SMI;





    cabletron              OBJECT IDENTIFIER ::= { enterprises 52 }

    mibs                   OBJECT IDENTIFIER ::= { cabletron 4 }

    ctron                  OBJECT IDENTIFIER ::= { mibs 1 }

    ctdatalink             OBJECT IDENTIFIER ::= { ctron 2 }

    ctBridge               OBJECT IDENTIFIER ::= { ctdatalink  3 }


    ------ group definitions ------


    ctBridgeSr             OBJECT IDENTIFIER ::= { ctBridge 3 }

    ctBridgeTp             OBJECT IDENTIFIER ::= { ctBridge 4 }

    ctBridgeSdbEnet        OBJECT IDENTIFIER ::= { ctBridge 5 }

    ctBridgeSdbTr          OBJECT IDENTIFIER ::= { ctBridge 6 }




    ----------        ctBridgeSr group            -------------



    ctBridgeSrPortPairTable OBJECT-TYPE
         SYNTAX  SEQUENCE OF CtBridgeSrPortPairEntry
         ACCESS  not-accessible
         STATUS  mandatory
         DESCRIPTION
             "A table containing information of source and
              destination port pairs for source routing"
         ::= { ctBridgeSr 1 }

    ctBridgeSrPortPairEntry OBJECT-TYPE
         SYNTAX  CtBridgeSrPortPairEntry
         ACCESS  not-accessible
         STATUS  mandatory
         DESCRIPTION
             "An entry consisting of objects specifying information
              for the source and destination port pairs used for source
              routing."

         INDEX    { ctBridgeSrPortPairSrcPort, ctBridgeSrPortPairDestPort }
         ::= { ctBridgeSrPortPairTable 1 }

    CtBridgeSrPortPairEntry ::=
         SEQUENCE {
             ctBridgeSrPortPairSrcPort
                  INTEGER,
             ctBridgeSrPortPairDestPort
                  INTEGER,
             ctBridgeSrPortPairPackets
                  Counter,
             ctBridgeSrPortPairState
                  INTEGER
         }

    ctBridgeSrPortPairSrcPort OBJECT-TYPE
         SYNTAX  INTEGER
         ACCESS  read-only
         STATUS  mandatory
         DESCRIPTION
             "The source port (ie the port which received the packets)
              for which this entry has source routing information."
         ::= { ctBridgeSrPortPairEntry 1 }

    ctBridgeSrPortPairDestPort OBJECT-TYPE
         SYNTAX  INTEGER
         ACCESS  read-only
         STATUS  mandatory
         DESCRIPTION
             "The destination port (ie the port which transmitted the
              packets) for which this entry has source routing information."
         ::= { ctBridgeSrPortPairEntry 2 }

    ctBridgeSrPortPairPackets OBJECT-TYPE
         SYNTAX  Counter
         ACCESS  read-only
         STATUS  mandatory
         DESCRIPTION
             "The number of packets forward by the source route bridge
              from the SrcPort to the DestPort."
         ::= { ctBridgeSrPortPairEntry 3 }

    ctBridgeSrPortPairState OBJECT-TYPE
         SYNTAX  INTEGER {
                     enabled(1),
                     disabled(2)
                 }
         ACCESS  read-write
         STATUS  mandatory
         DESCRIPTION
             "The state of source route bridging on this port pair.
              This is the desired state of the administrator.  The
              operational state of the port pair is determined by this
              state along with the states of dot1dStpPortState within
              the IETF Bridge MIB and ifOperStatus of the IETF MIB II
              for each port."
         ::= { ctBridgeSrPortPairEntry 4 }




    ----------        ctBridgeTp group            -------------



    ctBridgeTpPortFwdTable OBJECT-TYPE
         SYNTAX  SEQUENCE OF CtBridgeTpPortFwdEntry
         ACCESS  not-accessible
         STATUS  mandatory
         DESCRIPTION
             "A table containing information of source and
              destination port transparent MAC layer forwarding."
         ::= { ctBridgeTp 1 }

    ctBridgeTpPortFwdEntry OBJECT-TYPE
         SYNTAX  CtBridgeTpPortFwdEntry
         ACCESS  not-accessible
         STATUS  mandatory
         DESCRIPTION
             "An entry consisting of objects specifying the source and
              destination port transparent MAC layer forwarding
              information."

         INDEX    { ctBridgeTpPortFwdSrcPort, ctBridgeTpPortFwdDestPort }
         ::= { ctBridgeTpPortFwdTable 1 }

    CtBridgeTpPortFwdEntry ::=
         SEQUENCE {
             ctBridgeTpPortFwdSrcPort
                  INTEGER,
             ctBridgeTpPortFwdDestPort
                  INTEGER,
             ctBridgeTpPortFwdPackets
                  Counter
         }

    ctBridgeTpPortFwdSrcPort OBJECT-TYPE
         SYNTAX  INTEGER
         ACCESS  read-only
         STATUS  mandatory
         DESCRIPTION
             "The source port (ie the port which received the packets)
              for which this entry has transparent bridge forwarding
              information."
         ::= { ctBridgeTpPortFwdEntry 1 }

    ctBridgeTpPortFwdDestPort OBJECT-TYPE
         SYNTAX  INTEGER
         ACCESS  read-only
         STATUS  mandatory
         DESCRIPTION
             "The destination port (ie the port which the packets
              were transmitted out) for which this entry has
              transparent bridge forwarding information."
         ::= { ctBridgeTpPortFwdEntry 2 }

    ctBridgeTpPortFwdPackets OBJECT-TYPE
         SYNTAX  Counter
         ACCESS  read-only
         STATUS  mandatory
         DESCRIPTION
             "The number of packets transparently forwarded by the bridge
              from the SrcPort to the DestPort."
         ::= { ctBridgeTpPortFwdEntry 3 }


    ctBridgeTpPortStateTable OBJECT-TYPE
         SYNTAX  SEQUENCE OF CtBridgeTpPortStateEntry
         ACCESS  not-accessible
         STATUS  mandatory
         DESCRIPTION
             "A table which allows the network administrator to enable/
              disable transparent bridging on a particular port."
         ::= { ctBridgeTp 2 }

    ctBridgeTpPortStateEntry OBJECT-TYPE
         SYNTAX  CtBridgeTpPortStateEntry
         ACCESS  not-accessible
         STATUS  mandatory
         DESCRIPTION
             "An entry containing the transparent bridge state of
              a particular port."

         INDEX    { ctBridgeTpPortStatePort }
         ::= { ctBridgeTpPortStateTable 1 }

    CtBridgeTpPortStateEntry ::=
         SEQUENCE {
             ctBridgeTpPortStatePort
                  INTEGER,
             ctBridgeTpPortState
                  INTEGER
         }

    ctBridgeTpPortStatePort OBJECT-TYPE
         SYNTAX  INTEGER
         ACCESS  read-only
         STATUS  mandatory
         DESCRIPTION
             "The port for which this entry has transparent bridge
              state information."

         ::= { ctBridgeTpPortStateEntry 1 }

    ctBridgeTpPortState OBJECT-TYPE
         SYNTAX  INTEGER {
                     enabled(1),
                     disabled(2)
                 }
         ACCESS  read-write
         STATUS  mandatory
         DESCRIPTION
             "The state of transparent bridging on this port.  This is
              the desired state of the administrator.  The operational
              state of the port is determined by this state along with
              the state of dot1dStpPortState within the IETF Bridge MIB
              and ifOperStatus of the IETF MIB II."
         ::= { ctBridgeTpPortStateEntry 2 }






    ----------        ctBridgeSdbEnet group       -------------



    ctBridgeSdbEnetTotFtrs OBJECT-TYPE
         SYNTAX  INTEGER
         ACCESS  read-only
         STATUS  mandatory
         DESCRIPTION
             "The total number of Ethernet filters in the special
              database."
         ::= { ctBridgeSdbEnet 1 }


    ctBridgeSdbEnetNoMatch OBJECT-TYPE
         SYNTAX  INTEGER {
                     filter(1),
                     forward(2),
                     searchFDB(3)
                 }
         ACCESS  read-write
         STATUS  mandatory
         DESCRIPTION
             "The process to be performed if no match is found
              in the Ethernet special database.  The process of
              filtering or forwarding is for all ports.  searchFDB
              results in searching the IEEE 802.1D transparent filter
              database referenced by the IETF Bridge MIB. "
         ::= { ctBridgeSdbEnet 2 }


    ctBridgeSdbEnetTable OBJECT-TYPE
         SYNTAX  SEQUENCE OF CtBridgeSdbEnetEntry
         ACCESS  not-accessible
         STATUS  mandatory
         DESCRIPTION
             "A table containing filtering information configured into
              the bridge by (local or network) management specifying
              the specific packet string (destination address, source
              address, type/length field as well as a window of 64 bytes
              of packet data beginning at a data offset) to be used
              for filtering decisions.  The filters are to be searched in
              the order of incrementing filter number."
         ::= { ctBridgeSdbEnet 3 }

    ctBridgeSdbEnetEntry OBJECT-TYPE
         SYNTAX  CtBridgeSdbEnetEntry
         ACCESS  not-accessible
         STATUS  mandatory
         DESCRIPTION
             "Filtering information which extends the filtering
              capability of IEEE 802.1d."
         REFERENCE
              " IETF RFC:1286 "
         INDEX    { ctBridgeSdbEnetFtrNo }
         ::= { ctBridgeSdbEnetTable 1 }

    CtBridgeSdbEnetEntry ::=
         SEQUENCE {
             ctBridgeSdbEnetFtrNo
                  INTEGER,
             ctBridgeSdbEnetState
                  INTEGER,
             ctBridgeSdbEnetFtrData
                  OCTET STRING,
             ctBridgeSdbEnetDataOffset
                  INTEGER
         }

    ctBridgeSdbEnetFtrNo OBJECT-TYPE
         SYNTAX  INTEGER
         ACCESS  read-only
         STATUS  mandatory
         DESCRIPTION
             "The Filter number for which this entry contains
              filtering information."
         ::= { ctBridgeSdbEnetEntry 1 }

    ctBridgeSdbEnetState OBJECT-TYPE
         SYNTAX  INTEGER {
                     enabled(1),
                     disabled(2)
                 }
         ACCESS  read-write
         STATUS  mandatory
         DESCRIPTION
             "The state of the filter for which this entry contains
              filtering information."
         ::= { ctBridgeSdbEnetEntry 2 }

    ctBridgeSdbEnetFtrData OBJECT-TYPE
         SYNTAX  OCTET STRING
         ACCESS  read-write
         STATUS  mandatory
         DESCRIPTION
             "The specific packet string representing the
              destination address, source address, type/length
              field and a window of 64 bytes of packet data
              beginning at DataOffset to be used for filtering
              decisions. Each ASCII character of the string
              represents a nibble of packet data, therefore the
              packet string should be (14+64) * 2 = 156 characters
              long.  A value of 'x' in the packet string is
              used to indicate a 'Don't care' and no filtering is
              to be performed on that nibble."
         ::= { ctBridgeSdbEnetEntry 3 }

    ctBridgeSdbEnetDataOffset OBJECT-TYPE
         SYNTAX  INTEGER
         ACCESS  read-write
         STATUS  mandatory
         DESCRIPTION
             "The offset into a packet from which the bridge begins
              its filtering decisions on the 64 byte data window. The
              value '0' indicates that the window begins at the first
              byte after the Ethernet MAC header. The largest value of
              DataOffset is 1514 - 14 - 63 = 1437."
         ::= { ctBridgeSdbEnetEntry 4 }


    ctBridgeSdbEnetIOTable OBJECT-TYPE
         SYNTAX  SEQUENCE OF CtBridgeSdbEnetIOEntry
         ACCESS  not-accessible
         STATUS  mandatory
         DESCRIPTION
             "A table containing the set of ports to which
              frames received from specific ports and containing the
              specific packet string (destination address, source address,
              type/length field as well as a window of 64 bytes of
              packet data beginning at a data offset) of the corresponding
              filter number of SdbEnetTable are allowed to be forwarded.
              The value of '0' in this table as the RcvPort is used to
              specify all ports which are not already specified in this
              table for a particular entry."
         ::= { ctBridgeSdbEnet 4 }


    ctBridgeSdbEnetIOEntry OBJECT-TYPE
         SYNTAX  CtBridgeSdbEnetIOEntry
         ACCESS  not-accessible
         STATUS  mandatory
         DESCRIPTION
             "The set of ports to which frames received by the RcvPort
              and containing the specific packet string of the
              corresponding filter number of SdbEnetTable are allowed
              to be forwarded."
         INDEX    { ctBridgeSdbEnetIOFtrNo, ctBridgeSdbEnetIORcvPort }
         ::= { ctBridgeSdbEnetIOTable 1 }

    CtBridgeSdbEnetIOEntry ::=
         SEQUENCE {
             ctBridgeSdbEnetIOFtrNo
                  INTEGER,
             ctBridgeSdbEnetIORcvPort
                  INTEGER,
             ctBridgeSdbEnetIOAllowedToGoTo
                  OCTET STRING,
             ctBridgeSdbEnetIODelEntry
                  INTEGER
         }

    ctBridgeSdbEnetIOFtrNo OBJECT-TYPE
         SYNTAX  INTEGER
         ACCESS  read-write
         STATUS  mandatory
         DESCRIPTION
             "The Filter number for which this entry contains
              filtering information."
         ::= { ctBridgeSdbEnetIOEntry 1 }

    ctBridgeSdbEnetIORcvPort OBJECT-TYPE
         SYNTAX  INTEGER
         ACCESS  read-write
         STATUS  mandatory
         DESCRIPTION
             "Either the value '0', or the port number of the port
              from which a frame must be received in order for this
              entry's filtering information to apply.  A value of
              '0' indicates that this entry applies on all ports of
              the bridge for which there is no other applicable entry."
         ::= { ctBridgeSdbEnetIOEntry 2 }

    ctBridgeSdbEnetIOAllowedToGoTo OBJECT-TYPE
         SYNTAX  INTEGER
         ACCESS  read-write
         STATUS  mandatory
         DESCRIPTION
             "The set of ports to which frames received from a
              specific port and containing the specific packet
              string of the corresponding filter number are allowed
              to be forwarded.  Each octet within the value of this
              object specifies a set of eight ports, with the first
              octet specifying ports 1 through 8, the second octet
              specifying ports 9 through 16, etc.  Within each octet,
              the most significant bit represents the lowest numbered
              port, and the least significant bit represents the
              highest numbered port.  Thus, each port of the bridge is
              represented by a single bit within the value of this
              object.  If that bit has a value of '1' then that port
              is included in the set of ports; the port is not
              included if its bit has a value of '0'.  (Note that the
              setting of the bit corresponding to the port from which
              a frame is received is irrelevant.)"
         ::= { ctBridgeSdbEnetIOEntry 3 }


    ctBridgeSdbEnetIODelEntry OBJECT-TYPE
         SYNTAX  INTEGER {
                     deleteEntry(1)
                 }
         ACCESS  read-write
         STATUS  mandatory
         DESCRIPTION
             "Writing a '1' to this object deletes this entry from the
              Ethernet special database. This object will always return
              a '1' when read."
         ::= { ctBridgeSdbEnetIOEntry 4 }




    ----------        ctBridgeSdbTr group       -------------



    ctBridgeSdbTrTotFtrs OBJECT-TYPE
         SYNTAX  INTEGER
         ACCESS  read-only
         STATUS  mandatory
         DESCRIPTION
             "The total number of Token Ring filters in the special
              database."
         ::= { ctBridgeSdbTr 1 }


    ctBridgeSdbTrNoMatch OBJECT-TYPE
         SYNTAX  INTEGER {
                     filter(1),
                     forward(2),
                     searchFDB(3)
                 }
         ACCESS  read-write
         STATUS  mandatory
         DESCRIPTION
             "The process to be performed if no match is found
              in the Token Ring special database.  The process of
              filtering or forwarding is for all ports. searchFDB
              results in searching the IEEE 802.1D transparent filter
              database referenced by the IETF Bridge MIB. "
         ::= { ctBridgeSdbTr 2 }


    ctBridgeSdbTrTable OBJECT-TYPE
         SYNTAX  SEQUENCE OF CtBridgeSdbTrEntry
         ACCESS  not-accessible
         STATUS  mandatory
         DESCRIPTION
             "A table containing filtering information configured into
              the bridge by (local or network) management specifying
              the specific packet string (AC, FC, destination address,
              source address, as well as a window of 64 bytes of packet
              data beginning at a data offset) to be used for filtering
              decisions.  The filters are to be searched in the order of
              incrementing filter number."
         ::= { ctBridgeSdbTr 3 }

    ctBridgeSdbTrEntry OBJECT-TYPE
         SYNTAX  CtBridgeSdbTrEntry
         ACCESS  not-accessible
         STATUS  mandatory
         DESCRIPTION
             "Filtering information which extends the filtering
              capability of IEEE 802.1d."
         REFERENCE
              " IETF RFC:1286 "
         INDEX    { ctBridgeSdbTrFtrNo }
         ::= { ctBridgeSdbTrTable 1 }

    CtBridgeSdbTrEntry ::=
         SEQUENCE {
             ctBridgeSdbTrFtrNo
                  INTEGER,
             ctBridgeSdbTrState
                  INTEGER,
             ctBridgeSdbTrFtrData
                  OCTET STRING,
             ctBridgeSdbTrDataOffset
                  INTEGER
         }

    ctBridgeSdbTrFtrNo OBJECT-TYPE
         SYNTAX  INTEGER
         ACCESS  read-only
         STATUS  mandatory
         DESCRIPTION
             "The Filter number for which this entry contains
              filtering information."
         ::= { ctBridgeSdbTrEntry 1 }

    ctBridgeSdbTrState OBJECT-TYPE
         SYNTAX  INTEGER {
                     enabled(1),
                     disabled(2)
                 }
         ACCESS  read-write
         STATUS  mandatory
         DESCRIPTION
             "The state of the filter for which this entry contains
              filtering information."
         ::= { ctBridgeSdbTrEntry 2 }

    ctBridgeSdbTrFtrData OBJECT-TYPE
         SYNTAX  OCTET STRING
         ACCESS  read-write
         STATUS  mandatory
         DESCRIPTION
             "The specific packet string consisting of the AC, FC,
              destination address, source address, and a window of
              64 bytes of packet data beginning at DataOffset
              to be used for filtering decisions.  Each ASCII
              character of the string represents a nibble of
              packet data, therefore the packet string should be
              (14+64) * 2 = 156 characters long.  A value of 'x' in
              the packet string is used to indicate a 'Don't care'
              and no filtering is to be performed on that nibble."
         ::= { ctBridgeSdbTrEntry 3 }

    ctBridgeSdbTrDataOffset OBJECT-TYPE
         SYNTAX  INTEGER
         ACCESS  read-write
         STATUS  mandatory
         DESCRIPTION
             "The offset into a packet from which the bridge begins
              its filtering decisions on the 64 byte data window. The
              value '0' indicates that the window begins at the first
              byte after the Token Ring MAC header. The largest value of
              DataOffset is 17800 - 14 - 63 = 17723."
         ::= { ctBridgeSdbTrEntry 4 }


    ctBridgeSdbTrIOTable OBJECT-TYPE
         SYNTAX  SEQUENCE OF CtBridgeSdbTrIOEntry
         ACCESS  not-accessible
         STATUS  mandatory
         DESCRIPTION
             "A table containing the set of ports to which frames
              received from specific ports and containing the specific
              packet string (AC, FC, destination address, source address,
              as well as a window of 64 bytes of packet data beginning
              at a data offset) of the corresponding filter number of
              SdbTrTable are allowed to be forwarded.  The value of '0'
              in this table as the RcvPort is used to specify all ports
              which are not already specified in this table for a
              particular entry."
         ::= { ctBridgeSdbTr 4 }


    ctBridgeSdbTrIOEntry OBJECT-TYPE
         SYNTAX  CtBridgeSdbTrIOEntry
         ACCESS  not-accessible
         STATUS  mandatory
         DESCRIPTION
             "The set of ports to which frames received by the RcvPort
              and containing the specific packet string of the
              corresponding filter number of SdbTrTable are allowed
              to be forwarded."
         INDEX    { ctBridgeSdbTrIOFtrNo, ctBridgeSdbTrIORcvPort }
         ::= { ctBridgeSdbTrIOTable 1 }

    CtBridgeSdbTrIOEntry ::=
         SEQUENCE {
             ctBridgeSdbTrIOFtrNo
                  INTEGER,
             ctBridgeSdbTrIORcvPort
                  INTEGER,
             ctBridgeSdbTrIOAllowedToGoTo
                  OCTET STRING,
             ctBridgeSdbTrIODelEntry
                  INTEGER
         }

    ctBridgeSdbTrIOFtrNo OBJECT-TYPE
         SYNTAX  INTEGER
         ACCESS  read-write
         STATUS  mandatory
         DESCRIPTION
             "The Filter number for which this entry contains
              filtering information."
         ::= { ctBridgeSdbTrIOEntry 1 }

    ctBridgeSdbTrIORcvPort OBJECT-TYPE
         SYNTAX  INTEGER
         ACCESS  read-write
         STATUS  mandatory
         DESCRIPTION
             "Either the value '0', or the port number of the port
              from which a frame must be received in order for this
              entry's filtering information to apply.  A value of
              '0' indicates that this entry applies on all ports of
              the bridge for which there is no other applicable entry."
         ::= { ctBridgeSdbTrIOEntry 2 }

    ctBridgeSdbTrIOAllowedToGoTo OBJECT-TYPE
         SYNTAX  INTEGER
         ACCESS  read-write
         STATUS  mandatory
         DESCRIPTION
             "The set of ports to which frames received from a
              specific port and containing the specific packet
              string of the corresponding filter number are allowed
              to be forwarded.  Each octet within the value of this
              object specifies a set of eight ports, with the first
              octet specifying ports 1 through 8, the second octet
              specifying ports 9 through 16, etc.  Within each octet,
              the most significant bit represents the lowest numbered
              port, and the least significant bit represents the
              highest numbered port.  Thus, each port of the bridge is
              represented by a single bit within the value of this
              object.  If that bit has a value of '1' then that port
              is included in the set of ports; the port is not
              included if its bit has a value of '0'.  (Note that the
              setting of the bit corresponding to the port from which
              a frame is received is irrelevant.)"
         ::= { ctBridgeSdbTrIOEntry 3 }

    ctBridgeSdbTrIODelEntry OBJECT-TYPE
         SYNTAX  INTEGER {
                     deleteEntry(1)
                 }
         ACCESS  read-write
         STATUS  mandatory
         DESCRIPTION
             "Writing a '1' to this object deletes this entry from the
              Token Ring special database. This object will always return
              a '1' when read."
         ::= { ctBridgeSdbTrIOEntry 4 }

    END
