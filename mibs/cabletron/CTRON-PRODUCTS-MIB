CTRON-PRODUCTS-MIB DEFINITIONS ::= BEGIN

IMPORTS
    enterprises
            FROM RFC1155-SMI;

cabletron OBJECT IDENTIFIER ::= { enterprises 52 }
--    Cabletron Systems, Inc.
--  ContactInfo
--    Cabletron Systems, Inc.
--     35 Industrial Way, P.O. Box 5005
--     Rochester, NH 03867-0505
--     (603) 332-9400
--     support@ctron.com
--  Descr
--    ctron-products-mib.txt
-- 	Revision: 1.00.00
--    Part Number:
--    Date: December 27, 1999
--
--    This module provides authoritative definitions for part
--    of the naming tree below:
--
--    cabletron { enterprises 52 }
--
--    This module will be extended, as additional sub-sections
--    of this naming tree are defined.
--
--    Cabletron Systems reserves the right to make changes in
--    specification and other information contained in this document
--    without prior notice.  The reader should consult Cabletron Systems
--    to determine whether any such changes have been made.
--
--    In no event shall Cabletron Systems be liable for any incidental,
--    indirect, special, or consequential damages whatsoever (including
--    but not limited to lost profits) arising out of or related to this
--    document or the information contained in it, even if Cabletron
--    Systems has been advised of, known, or should have known, the
--    possibility of such damages.
--
--    Cabletron grants vendors, end-users, and other interested parties
--    a non-exclusive license to use this Specification in connection
--    with the management of Cabletron products.
--
--    Copyright December 99 Cabletron Systems
--
--    The assigned enterprise MIB tree for Cabletron System

ctronProducts OBJECT IDENTIFIER ::= { cabletron 10 }
-- OBJECT-IDENTITY
--  Status
--    mandatory
--  Descr
--  All Cabletron identification object identifiers.
--  This information is a follow on to ctron-oids and is product specific.

ssr3000 OBJECT IDENTIFIER ::= { ctronProducts 1 }
-- OBJECT-IDENTITY
--   Status
--     mandatory
--   Descr
--	Replacement for ssr2000

ssr32000 OBJECT IDENTIFIER ::= { ctronProducts 2 }
-- OBJECT-IDENTITY
--   Status
--     mandatory
--   Descr
--	32 Slot Chassis for SSR modules.



END
