CT-DAWAN-MIB DEFINITIONS ::= BEGIN
IMPORTS

    Gauge, TimeTicks
            FROM RFC1155-SMI

    OBJECT-TYPE
            FROM RFC-1212

    cabletron
	    FROM CTRON-OIDS;

   ctSSA OBJECT IDENTIFIER ::= { cabletron 4497 }

   ctDAWanDevices OBJECT IDENTIFIER ::= { ctSSA 16 }

   DisplayString ::= OCTET STRING
   TimeStamp ::= TimeTicks

   ctDAWanDeviceNumDevices OBJECT-TYPE
       SYNTAX      INTEGER
       ACCESS      read-only
       STATUS      mandatory
       DESCRIPTION
               "This is the total number of devices currently
                in the local system cache."
       ::= { ctDAWanDevices 1 }

   ctDAWanDevicesTable OBJECT-TYPE
       SYNTAX      SEQUENCE OF CtDAWanDeviceEntry
       ACCESS      not-accessible
       STATUS      mandatory
       DESCRIPTION
               "A list of Demand Access remote WAN devices.
                This list reflects the contents of the local
                system cache.  The local cache maintains an account
                for each device.  Each entry in the local cache
                is a conceptual row in the SNMP table."
       ::= { ctDAWanDevices 2}

   ctDAWanDeviceEntry OBJECT-TYPE
       SYNTAX      CtDAWanDeviceEntry
       ACCESS      not-accessible
       STATUS      mandatory
       DESCRIPTION
               "An entry containing wan device information
                and statistics."
       INDEX   { ctDAWanDeviceIndex }
       ::= { ctDAWanDevicesTable 1 }

   CtDAWanDeviceEntry ::=
       SEQUENCE {
           ctDAWanDeviceIndex                INTEGER,
           ctDAWanDeviceIfIndex              INTEGER,
           ctDAWanDeviceSessionID            Gauge,
           ctDAWanDeviceState                INTEGER,
           ctDAWanDeviceDescr                DisplayString,
           ctDAWanDeviceConnectControl       INTEGER,
           ctDAWanDeviceConnectType          INTEGER,
           ctDAWanDeviceL2Encapsulation      INTEGER,
           ctDAWanDeviceNumConnections       INTEGER,
           ctDAWanDeviceCurrentBandwidth     Gauge,
           ctDAWanDeviceInitialBandwidth     Gauge,
           ctDAWanDeviceMaxBandwidth         Gauge,
           ctDAWanDeviceH0Support            INTEGER,
           ctDAWanDeviceChargedUnits         Gauge,
           ctDAWanDeviceSuccessCalls         Gauge,
           ctDAWanDeviceFailCalls            Gauge,
           ctDAWanDeviceAcceptCalls          Gauge,
           ctDAWanDeviceRefuseCalls          Gauge,
           ctDAWanDeviceConnectTime          TimeStamp,
           ctDAWanDeviceConnectDirection     INTEGER,
           ctDAWanDeviceLastDisconnectTime       TimeStamp,
           ctDAWanDeviceLastDisconnectDirection  INTEGER,
           ctDAWanDeviceLastDisconnectCause      OCTET STRING,
           ctDAWanDeviceLastDisconnectText       DisplayString
       }

   ctDAWanDeviceIndex OBJECT-TYPE
       SYNTAX      INTEGER(0..2147483647)
       ACCESS      read-only
       STATUS      mandatory
       DESCRIPTION
               "This is the index into this table.  This index
                uniquely identifies the device."
       ::= { ctDAWanDeviceEntry 1 }

   ctDAWanDeviceIfIndex OBJECT-TYPE
       SYNTAX      INTEGER
       ACCESS      read-only
       STATUS      mandatory
       DESCRIPTION
            "This is the ifIndex value of the wan connection group.
             If the ifIndex value is unknown, the value of this object
             will be zero."
       ::= { ctDAWanDeviceEntry 2 }

   ctDAWanDeviceSessionID OBJECT-TYPE
       SYNTAX      Gauge
       ACCESS      read-only
       STATUS      mandatory
       DESCRIPTION
            "This is the unique identifier of the last session
             when a wan device was in the active state."
       ::= { ctDAWanDeviceEntry 3 }

   ctDAWanDeviceState OBJECT-TYPE
       SYNTAX INTEGER {
         inactive(1),     -- the device is not actively connected
         connecting(2),   -- the device is actively being connected
         active(3),       -- the device is actively connected
         disconnecting(4) -- the device is in the process of being disconnected
        }
       ACCESS      read-only
       STATUS      mandatory
       DESCRIPTION
               "This is the state of the device."
       ::= { ctDAWanDeviceEntry 4 }

   ctDAWanDeviceDescr OBJECT-TYPE
       SYNTAX      DisplayString (SIZE (0..255))
       ACCESS      read-only
       STATUS      mandatory
       DESCRIPTION
               "A textual string that identifies the peer device."
       ::= { ctDAWanDeviceEntry 5 }

   ctDAWanDeviceConnectControl OBJECT-TYPE
       SYNTAX      INTEGER {
                        connect(1),      -- initiates the connect action
                        disconnect(2),   -- initiates the disconnect action
                        unknown(3)
              }
       ACCESS      read-write
       STATUS      mandatory
       DESCRIPTION
               "This object controls the desired state of the wan device.
                Setting this object to connect(1) will initiate the
                set of actions to bring the wan device to the active
                state.  Only set the object to connect(1) when the current
                value of ctDAWanDeviceState is inactive.  Setting this object
                to disconnect(2) will initiate the set of actions to bring
                the wan device to the inactive state.  Only set this object
                to disconnect(2) when the ctDAWanDeviceState is active.
                After setting the device to connect(1) or disconnect(2),
                refer to ctDAWanDeviceState to determine the state of the
                wan device.  Queries to ctDAWanDeviceConnectControl return
                unknown results."
       ::= { ctDAWanDeviceEntry 6 }


   ctDAWanDeviceConnectType OBJECT-TYPE
       SYNTAX      INTEGER{
                        digitalCircuit(1),
                        analogCircuit(2)
                        }
       ACCESS      read-only
       STATUS      mandatory
       DESCRIPTION
               "This specifies the type of the wan connection."
       ::= { ctDAWanDeviceEntry 7 }

   ctDAWanDeviceL2Encapsulation OBJECT-TYPE
       SYNTAX      INTEGER{
                        unknown(1),
                        ppp(2)
              }
       ACCESS      read-only
       STATUS      mandatory
       DESCRIPTION
               "This is the type of layer 2 encapsulation used when
                connecting to this device."
       ::= { ctDAWanDeviceEntry 8 }

   ctDAWanDeviceNumConnections OBJECT-TYPE
       SYNTAX      INTEGER(0..2147483647)
       ACCESS      read-only
       STATUS      mandatory
       DESCRIPTION
               "This is the current number of wan connections
                to this device."
       ::= { ctDAWanDeviceEntry 9 }

   ctDAWanDeviceCurrentBandwidth OBJECT-TYPE
       SYNTAX      Gauge
       ACCESS      read-only
       STATUS      mandatory
       DESCRIPTION
               "This is the aggregate bandwidth of all current connections."
       ::= { ctDAWanDeviceEntry 10 }

   ctDAWanDeviceInitialBandwidth OBJECT-TYPE
       SYNTAX      Gauge
       ACCESS      read-only
       STATUS      mandatory
       DESCRIPTION
               "This is the desired initial bandwidth in bits per second used
                when calling this peer object.  The system will bring up enough
                connections to meet the bandwidth requirement.  The value only
                represents dial type connections.  It does not include leased circuits."
       ::= { ctDAWanDeviceEntry 11 }

   ctDAWanDeviceMaxBandwidth OBJECT-TYPE
       SYNTAX      Gauge
       ACCESS      read-only
       STATUS      mandatory
       DESCRIPTION
               "This is the maximum amount of bandwidth in bits per seconde used when
                calling this peer wan device object.  This value only represents dial
                type connections.  It does not include leased line circuits."
       ::= { ctDAWanDeviceEntry 12 }

   ctDAWanDeviceH0Support OBJECT-TYPE
       SYNTAX      INTEGER {
                       true(1),     -- the device supports H0
                       false(2)     -- the device does not support H0
                   }
       ACCESS      read-only
       STATUS      mandatory
       DESCRIPTION
               "Indicates whether an H0 connection can be used when calling this
                peer wan device object."
       ::= { ctDAWanDeviceEntry 13 }

   ctDAWanDeviceChargedUnits OBJECT-TYPE
       SYNTAX      Gauge
       ACCESS      read-only
       STATUS      mandatory
       DESCRIPTION
            "The total number of charging units applying to this
             peer device since this row was created. Only the
             charging units applying to the local interface,i.e.
             for originated calls or for calls with 'Reverse
             charging' being active, will be counted here."
        ::= { ctDAWanDeviceEntry 14 }

   ctDAWanDeviceSuccessCalls OBJECT-TYPE
       SYNTAX      Gauge
       ACCESS      read-only
       STATUS      mandatory
       DESCRIPTION
            "Number of completed calls to this peer device."
        ::= { ctDAWanDeviceEntry 15 }

   ctDAWanDeviceFailCalls OBJECT-TYPE
       SYNTAX      Gauge
       ACCESS      read-only
       STATUS      mandatory
       DESCRIPTION
            "Number of failed call attempts to this peer device since the
             row was created."
        ::= { ctDAWanDeviceEntry 16 }

   ctDAWanDeviceAcceptCalls OBJECT-TYPE
       SYNTAX      Gauge
       ACCESS      read-only
       STATUS      mandatory
       DESCRIPTION
            "Number of calls from this peer device accepted since the
             row was created."
        ::= { ctDAWanDeviceEntry 17 }

   ctDAWanDeviceRefuseCalls OBJECT-TYPE
       SYNTAX      Gauge
       ACCESS      read-only
       STATUS      mandatory
       DESCRIPTION
            "Number of calls from this peer device refused since the
             row was created."
        ::= { ctDAWanDeviceEntry 18 }

   ctDAWanDeviceConnectTime OBJECT-TYPE
       SYNTAX      TimeStamp
       ACCESS      read-only
       STATUS      mandatory
       DESCRIPTION
            "The value of sysUpTime at the time when the device entered
             its current active state. This object will be 0 if the
             device is currently inactive.  This object will be upctDAted whenever
             there is a state transition to the active state."
        ::= { ctDAWanDeviceEntry 19 }

   ctDAWanDeviceConnectDirection OBJECT-TYPE
        SYNTAX      INTEGER
                      {
                        in(1),
                        out(2)
                      }
       ACCESS   read-only
       STATUS   mandatory
       DESCRIPTION
            "The direction from which the last connect occurred."
        ::= { ctDAWanDeviceEntry 20 }

   ctDAWanDeviceLastDisconnectTime OBJECT-TYPE
       SYNTAX      TimeStamp
       ACCESS      read-only
       STATUS      mandatory
       DESCRIPTION
            "The value of sysUpTime when the last call to this peer
             device was disconnected.  This object will be upctDAted whenever
             a call is disconnected."
        ::= { ctDAWanDeviceEntry 21 }

   ctDAWanDeviceLastDisconnectDirection OBJECT-TYPE
        SYNTAX      INTEGER
                      {
                        in(1),
                        out(2)
                      }
       ACCESS   read-only
       STATUS   mandatory
       DESCRIPTION
            "The direction from which the last disconnect occurred."
       ::= { ctDAWanDeviceEntry 22 }

   ctDAWanDeviceLastDisconnectCause OBJECT-TYPE
       SYNTAX   OCTET STRING (SIZE (0..4))
       ACCESS   read-only
       STATUS   mandatory
       DESCRIPTION
            "The encoded network cause value associated with the last call. This object
             will be upctDAted whenever a call is started or cleared. The value of this
             object will depend on the interface type as well as on the protocol and
             protocol version being used on this interface."
       ::= { ctDAWanDeviceEntry 23 }

   ctDAWanDeviceLastDisconnectText OBJECT-TYPE
       SYNTAX   DisplayString (SIZE (0..255))
       ACCESS   read-only
       STATUS   mandatory
       DESCRIPTION
            "ASCII text describing the reason for the last call termination. This object
             exists because it would be impossible for a management station to store all
             possible cause values for all types of interfaces. It should be used only if
             a management station is unable to decode the value of
             ctDAWanDeviceLastDisconnectCause. This object will be upctDAted whenever a
             call is started or cleared."
       ::= { ctDAWanDeviceEntry 24 }

   ctDAWanTNListTable OBJECT-TYPE
       SYNTAX      SEQUENCE OF CtDAWanTNListEntry
       ACCESS      not-accessible
       STATUS      mandatory
       DESCRIPTION
               "A list of telephone numbers accessible to the
                wan device."
       ::= { ctDAWanDevices 3}

   ctDAWanTNListEntry OBJECT-TYPE
       SYNTAX      CtDAWanTNListEntry
       ACCESS      not-accessible
       STATUS      mandatory
       DESCRIPTION
               "An entry containing a telephone number."
       INDEX   { ctDAWanDeviceIndex, ctDAWanTNListIndex}
       ::= { ctDAWanTNListTable 1 }

   CtDAWanTNListEntry ::=
       SEQUENCE {
           ctDAWanTNListIndex                INTEGER,
           ctDAWanTN                         DisplayString
       }

   ctDAWanTNListIndex OBJECT-TYPE
       SYNTAX      INTEGER(0..2147483647)
       ACCESS      read-only
       STATUS      mandatory
       DESCRIPTION
               "This is the index into this table.  This index
                uniquely identifies the telephone number."
       ::= { ctDAWanTNListEntry 1 }

   ctDAWanTN OBJECT-TYPE
       SYNTAX      DisplayString (SIZE (0..255))
       ACCESS      read-only
       STATUS      mandatory
       DESCRIPTION
               "This is a telephone number for this wan device."
       ::= { ctDAWanTNListEntry 2 }
END
