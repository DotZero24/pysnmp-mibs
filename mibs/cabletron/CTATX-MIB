CTATX-MIB DEFINITIONS ::= BEGIN

        --  ctATX-mib.txt
        --  Revision: 01.01.00
        --  Part Number:
        --  Date: March 26, 1997

        --  Cabletron Systems, Inc.
        --  35 Industrial Way, P.O. Box 5005
        --  Rochester, NH 03867-0505
        --  (603) 332-9400
        --  support@ctron.com

        --  This module provides authoritative definitions for Cabletron's
        --  ATX mib.
        --
        --  This module will be extended, as required.
        --

        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.

        --  Copyright (c)1996 Cabletron Systems

IMPORTS

      OBJECT-TYPE
                  FROM RFC-1212

      DisplayString
                FROM RFC1213-MIB

      Counter, Gauge, IpAddress,
      TimeTicks, enterprises
                FROM RFC1155-SMI;

--=========================================================

      Boolean    ::= INTEGER { true(1), false(2) }

--=========================================================


 sigma              OBJECT IDENTIFIER ::= { enterprises 97 }
 sys                OBJECT IDENTIFIER ::= { sigma 1 }
 ecs-1              OBJECT IDENTIFIER ::= { sigma 3 }
 atext              OBJECT IDENTIFIER ::= { sigma 6 }
 hw                 OBJECT IDENTIFIER ::= { ecs-1 1 }
 sw                 OBJECT IDENTIFIER ::= { ecs-1 2 }
 admin              OBJECT IDENTIFIER ::= { ecs-1 3 }
 config             OBJECT IDENTIFIER ::= { admin 1 }
 lma                OBJECT IDENTIFIER ::= { admin 2 }
 ppe                OBJECT IDENTIFIER ::= { admin 3 }
 st                 OBJECT IDENTIFIER ::= { admin 4 }
 mesh               OBJECT IDENTIFIER ::= { admin 5 }
 atextsystem        OBJECT IDENTIFIER ::= { atext 1 }
 atextport          OBJECT IDENTIFIER ::= { atext 2 }
 swdis              OBJECT IDENTIFIER ::= { ecs-1 4 }
 addr               OBJECT IDENTIFIER ::= { ecs-1 5 }

 snmpsmt            OBJECT IDENTIFIER ::= { ecs-1 6 }
 sinterfaces        OBJECT IDENTIFIER ::= { ecs-1 7 }
 sfddi              OBJECT IDENTIFIER ::= { ecs-1 8 }
 suart              OBJECT IDENTIFIER ::= { ecs-1 9 }
 filter             OBJECT IDENTIFIER ::= { ecs-1 10 }
 reboot             OBJECT IDENTIFIER ::= { ecs-1 11 }
 debug              OBJECT IDENTIFIER ::= { ecs-1 12 }
 lpbk               OBJECT IDENTIFIER ::= { ecs-1 13 }
 swan               OBJECT IDENTIFIER ::= { ecs-1 14 }

 -- srptr OBJECT IDENTIFIER ::= { ecs-1 15 } OBSOLETE

 srepeater          OBJECT IDENTIFIER ::= { ecs-1 16 }
 sproto             OBJECT IDENTIFIER ::= { ecs-1 17 }
 sipx               OBJECT IDENTIFIER ::= { ecs-1 18 }
 sipxsfGrp          OBJECT IDENTIFIER ::= { sipx 6 }
 sipxsrGrp          OBJECT IDENTIFIER ::= { sipx 7}
 srtrdisc           OBJECT IDENTIFIER ::= { ecs-1 19 }
 sipm               OBJECT IDENTIFIER ::= { ecs-1 20 }
 sipmroute          OBJECT IDENTIFIER ::= { sipm 1 }
 sipmgroup          OBJECT IDENTIFIER ::= { sipm 2 }
 sipmneighbor       OBJECT IDENTIFIER ::= { sipm 3 }
 sipmstat           OBJECT IDENTIFIER ::= { sipm 4 }
 sipckt             OBJECT IDENTIFIER ::= { ecs-1 21 }
 ssecure            OBJECT IDENTIFIER ::= { ecs-1 23 }
 spvc               OBJECT IDENTIFIER ::= { ecs-1 24 }
 strunk             OBJECT IDENTIFIER ::= { ecs-1 25 }
 ipMRouteMIB        OBJECT IDENTIFIER ::= { ecs-1 26 }  -- to be assigned by the IANA
 igmpMIB            OBJECT IDENTIFIER ::= { ecs-1 27 }  -- to be assigned by IANA

 ipMRouteMIBObjects OBJECT IDENTIFIER ::= { ipMRouteMIB 1 }
 ipMRoute           OBJECT IDENTIFIER ::= { ipMRouteMIBObjects 1 }
 igmpMIBObjects     OBJECT IDENTIFIER ::= { igmpMIB 1 }
 igmp               OBJECT IDENTIFIER ::= { igmpMIBObjects 1 }
 slog               OBJECT IDENTIFIER ::= { ecs-1 28 }
 strap              OBJECT IDENTIFIER ::= { ecs-1 29 }
 smirror            OBJECT IDENTIFIER ::= { ecs-1 30 }
 sworkgroup         OBJECT IDENTIFIER ::= { ecs-1 31 }
 sping              OBJECT IDENTIFIER ::= { ecs-1 32 }
 strace             OBJECT IDENTIFIER ::= { ecs-1 33 }
 srtb               OBJECT IDENTIFIER ::= { ecs-1 34 }
 nbcache            OBJECT IDENTIFIER ::= { ecs-1 35 }


 -- the IP Multicast Routing MIB-Group
 --
 -- a collection of objects providing information about
 -- IP Multicast Groups

  ipMRouteEnable OBJECT-TYPE
      SYNTAX     INTEGER { enabled(1), disabled(2) }
      ACCESS read-write
      STATUS     mandatory
      DESCRIPTION
              "The enabled status of IP Multicast routing on this router."
      ::= { ipMRoute 1 }


  ipMRouteTable OBJECT-TYPE
      SYNTAX     SEQUENCE OF IpMRouteEntry
      ACCESS not-accessible
      STATUS     mandatory
      DESCRIPTION
              "The (conceptual) table containg multicast routing
              information for IP datagrams sent by particular sources to
              the IP multicast groups known to this router."
      ::= { ipMRoute 2 }

  ipMRouteEntry OBJECT-TYPE
      SYNTAX     IpMRouteEntry
      ACCESS not-accessible
      STATUS     mandatory
      DESCRIPTION
              "An entry (conceptual row) containing the multicast routing
              information for IP datagrams from a particular source and
              addressed to a particular IP multicast group address."
      INDEX      { ipMRouteGroup, ipMRouteSource, ipMRouteSourceMask }
      ::= { ipMRouteTable 1 }



  IpMRouteEntry ::= SEQUENCE {
      ipMRouteGroup        IpAddress,
      ipMRouteSource       IpAddress,
      ipMRouteSourceMask   IpAddress,
      ipMRouteRpfNeighbor  IpAddress,
      ipMRouteInIfIndex    INTEGER,
      ipMRouteOutList      OCTET STRING,
      ipMRouteUpTime       TimeTicks,
      ipMRouteExpiryTime   TimeTicks,
      ipMRoutePkts         Counter,
      ipMRouteRpfFails     Counter,
      ipMRouteOctets       Counter,
      ipMRouteNextHopState INTEGER
  }

  ipMRouteGroup OBJECT-TYPE
      SYNTAX     IpAddress
      ACCESS     read-only
      STATUS     mandatory
      DESCRIPTION
              "The IP multicast group address for which this entry
              contains multicast routing information."
      ::= { ipMRouteEntry 1 }

  ipMRouteSource OBJECT-TYPE
      SYNTAX     IpAddress
      ACCESS     read-only
      STATUS     mandatory
      DESCRIPTION
              "The source network address for which this entry contains
              multicast routing information."
      ::= { ipMRouteEntry 2 }

  ipMRouteSourceMask OBJECT-TYPE
      SYNTAX     IpAddress
      ACCESS     read-only
      STATUS     mandatory
      DESCRIPTION
              "The network mask of the source address for which this entry
              contains multicast routing information."
      ::= { ipMRouteEntry 3 }

  ipMRouteRpfNeighbor OBJECT-TYPE
      SYNTAX     IpAddress
      ACCESS read-only
      STATUS     mandatory
      DESCRIPTION
              "The address of the RPF neighbor from which IP datagrams
              from this source to this multicast address are received."
      ::= { ipMRouteEntry 4 }

  ipMRouteInIfIndex OBJECT-TYPE
      SYNTAX     INTEGER
      ACCESS read-only
      STATUS     mandatory
      DESCRIPTION
              "The value of ifIndex for the interface on which IP
              datagrams sent by this source to this multicast address are
              received."
      ::= { ipMRouteEntry 5 }

  ipMRouteOutList OBJECT-TYPE
      SYNTAX     OCTET STRING
      ACCESS read-only
      STATUS     mandatory
      DESCRIPTION
              "The value of ipMRouteNextHopList which identifies the list
              of entries in the ipMRouteNextHopTable representing outgoing
              interfaces to which IP datagrams from this source to this
              multicast group address are forwarded."
      ::= { ipMRouteEntry 6 }

  ipMRouteUpTime OBJECT-TYPE
      SYNTAX     TimeTicks
      ACCESS read-only
      STATUS     mandatory
      DESCRIPTION
              "The time since the multicast routing information
              represented by this entry was learned by the router."
      ::= { ipMRouteEntry 7 }

  ipMRouteExpiryTime OBJECT-TYPE
      SYNTAX     TimeTicks
      ACCESS read-write
      STATUS     mandatory
      DESCRIPTION
              "The minimum amount of time remaining before this entry will
              be aged out."
      ::= { ipMRouteEntry 8 }

  ipMRoutePkts OBJECT-TYPE
      SYNTAX     Counter
      ACCESS read-only
      STATUS     mandatory
      DESCRIPTION
              "The number of packets which this router has received from
              this source and addressed to this multicast group address."
      ::= { ipMRouteEntry 9 }

  ipMRouteRpfFails OBJECT-TYPE
      SYNTAX     Counter
      ACCESS read-only
      STATUS     mandatory
      DESCRIPTION
              "The number of packets which this router has received from
              this source and addressed to this multicast group address,
              which were not received from the interface indicated by
              ipMRouteInIfIndex."
      ::= { ipMRouteEntry 10 }

  ipMRouteOctets OBJECT-TYPE
      SYNTAX     Counter
      ACCESS read-only
      STATUS     mandatory
      DESCRIPTION
              "The number of octets contained in IP datagrams which were
              received from this source and addressed to this multicast
              group address, and which were forwarded by this router."
      ::= { ipMRouteEntry 11 }

  ipMRouteNextHopState OBJECT-TYPE
      SYNTAX     INTEGER { pruned(1), forwarding(2) }
      ACCESS read-only
      STATUS     mandatory
      DESCRIPTION
              "An indication of whether the outgoing interface and next
              hop represented by this entry is currently being used to
              forward IP datagrams. The value 'forwarding' indicates it
              is currently being used; the value 'pruned' indicates it is
              not."
      ::= { ipMRouteEntry 12 }


  --
  --  The Multicast Routing Interface Table
  --

  ipMRouteInterfaceTable OBJECT-TYPE
      SYNTAX     SEQUENCE OF IpMRouteInterfaceEntry
      ACCESS not-accessible
      STATUS     mandatory
      DESCRIPTION
              "The (conceptual) table containg multicast routing
              information specific to interfaces."
      ::= { ipMRoute 3 }

  ipMRouteInterfaceEntry OBJECT-TYPE
      SYNTAX     IpMRouteInterfaceEntry
      ACCESS not-accessible
      STATUS     mandatory
      DESCRIPTION
              "An entry (conceptual row) containing the multicast routing
              information for a particular interface."
      INDEX      { ipMRouteInterfaceIfIndex }
      ::= { ipMRouteInterfaceTable 1 }

  IpMRouteInterfaceEntry ::= SEQUENCE {
      ipMRouteInterfaceIfIndex  INTEGER,
      ipMRouteInterfaceTtl    INTEGER
  }

  ipMRouteInterfaceIfIndex OBJECT-TYPE
      SYNTAX     INTEGER
      ACCESS     read-only
      STATUS     mandatory
      DESCRIPTION
              "The ifIndex value of the interface for which this entry
              contains information."
      ::= { ipMRouteInterfaceEntry 1 }

  ipMRouteInterfaceTtl OBJECT-TYPE
      SYNTAX     INTEGER
      ACCESS read-write
      STATUS     mandatory
      DESCRIPTION
              "The datagram TTL threshold for the interface. Any IP
              multicast datagrams with a TTL less than this threshold will
              not be forwarded out the interface. The default value of 0
              means all multicast packets are forwarded out interface."
      ::= { ipMRouteInterfaceEntry 2 }


  --
  --  The IGMP Interface Table
  --

  igmpInterfaceTable OBJECT-TYPE
      SYNTAX     SEQUENCE OF IgmpInterfaceEntry
      ACCESS   not-accessible
      STATUS     mandatory
      DESCRIPTION
              "The (conceptual) table listing the interfaces on which IGMP
              is enabled."
      ::= { igmp 1 }

  igmpInterfaceEntry OBJECT-TYPE
      SYNTAX     IgmpInterfaceEntry
      ACCESS   not-accessible
      STATUS     mandatory
      DESCRIPTION
              "An entry (conceptual row) representing an interface on
              which IGMP is enabled."
      INDEX      { igmpInterfaceIfIndex }
      ::= { igmpInterfaceTable 1 }

  IgmpInterfaceEntry ::= SEQUENCE {
      igmpInterfaceIfIndex        INTEGER,
      igmpInterfaceQueryInterval  INTEGER,
      igmpInterfaceStatus         INTEGER -- RowStatus
  }

  igmpInterfaceIfIndex OBJECT-TYPE
      SYNTAX     INTEGER
      ACCESS     read-only
      STATUS     mandatory
      DESCRIPTION
              "The interface for which IGMP is enabled."
      ::= { igmpInterfaceEntry 1 }

  igmpInterfaceQueryInterval OBJECT-TYPE
      SYNTAX     INTEGER
      ACCESS read-write
      STATUS     mandatory
      DESCRIPTION
              "The frequency at which IGMP Host-Query packets are
              transmitted on this interface."
      -- DEFVAL     { 60 }
      ::= { igmpInterfaceEntry 2 }

  igmpInterfaceStatus OBJECT-TYPE
      SYNTAX     INTEGER -- RowStatus
      ACCESS read-write
      STATUS     mandatory
      DESCRIPTION
              "The activation of a row enables IGMP on the interface. The
              destruction of a row disables IGMP on the interface."
      ::= { igmpInterfaceEntry 3 }


  --
  --  The IGMP Cache Group Table
  --

  igmpCacheTable OBJECT-TYPE
      SYNTAX     SEQUENCE OF IgmpCacheEntry
      ACCESS not-accessible
      STATUS     mandatory
      DESCRIPTION
              "The (conceptual) table listing the IP multicast groups for
              which there are members on a particular interface."
      ::= { igmp 2 }

  igmpCacheEntry OBJECT-TYPE
      SYNTAX     IgmpCacheEntry
      ACCESS not-accessible
      STATUS     mandatory
      DESCRIPTION
              "An entry (conceptual row) in the igmpCacheTable."
      INDEX      { igmpCacheAddress, igmpCacheIfIndex }
      ::= { igmpCacheTable 1 }

  IgmpCacheEntry ::= SEQUENCE {
      igmpCacheAddress        IpAddress,
      igmpCacheIfIndex        INTEGER,
      igmpCacheSelf           INTEGER, -- TruthValue
      igmpCacheLastReporter   IpAddress,
      igmpCacheUpTime         TimeTicks,
      igmpCacheExpiryTime     TimeTicks,
      igmpCacheStatus         INTEGER -- RowStatus
  }

  igmpCacheAddress OBJECT-TYPE
      SYNTAX     IpAddress
      ACCESS     read-only
      STATUS     mandatory
      DESCRIPTION
              "The IP multicast group address for which this entry
              contains information."
      ::= { igmpCacheEntry 1 }

  igmpCacheIfIndex OBJECT-TYPE
      SYNTAX     INTEGER
      ACCESS     read-only
      STATUS     mandatory
      DESCRIPTION
              "The interface for which this entry contains information for
              an IP multicast group address."
      ::= { igmpCacheEntry 2 }

  igmpCacheSelf OBJECT-TYPE
      SYNTAX     INTEGER   -- TruthValue
      ACCESS read-write
      STATUS     mandatory
      DESCRIPTION
              "An indication of whether the local system is a member of
              this group address on this interface."
      -- DEFVAL     { true }
      ::= { igmpCacheEntry 3 }

  igmpCacheLastReporter OBJECT-TYPE
      SYNTAX     IpAddress
      ACCESS read-only
      STATUS     mandatory
      DESCRIPTION
              "The IP address of the source of the last membership report
              received for this IP Multicast group address on this
              interface. If no membership report has been received, this
              object has the value 0.0.0.0."
      ::= { igmpCacheEntry 4 }

  igmpCacheUpTime OBJECT-TYPE
      SYNTAX     TimeTicks
      ACCESS read-only
      STATUS     mandatory
      DESCRIPTION
              "The time since the system joined this group address, or
              zero if the system is not currently a member."
      ::= { igmpCacheEntry 5 }

  igmpCacheExpiryTime OBJECT-TYPE
      SYNTAX     TimeTicks
      ACCESS read-only
      STATUS     mandatory
      DESCRIPTION
              "The minimum amount of time remaining before this entry will
              be aged out."
      ::= { igmpCacheEntry 6 }

  igmpCacheStatus OBJECT-TYPE
      SYNTAX     INTEGER -- RowStatus
      ACCESS read-write
      STATUS     mandatory
      DESCRIPTION
              "The status of this entry."
      ::= { igmpCacheEntry 7 }

 -- SMC MIB
 -- System group

 sysID OBJECT-TYPE
  SYNTAX INTEGER {
     es-1-bridge-router(1),
     es-1-atx-br-router(3)
    }
  ACCESS read-only
  STATUS mandatory
      DESCRIPTION
          "An integer which serves to identify the type of ES/1."
  ::= { sys 1 }

 sysReset OBJECT-TYPE
  SYNTAX TimeTicks
  ACCESS read-write
  STATUS mandatory
      DESCRIPTION
          "The time, in centiseconds, before the ES/1 should reboot.
           A GetResponse value of zero indicates that no reboot time
           has been specified."
  ::= { sys 2 }

 sysTrapAck OBJECT-TYPE
  SYNTAX INTEGER {
     traps-need-acks(1),
     traps-not-acked(2)
    }
  ACCESS read-write
  STATUS mandatory
      DESCRIPTION
          "Whether the NMS will acknowledge the enterprise specific
           traps."
  ::= { sys 3 }

 sysTrapTime OBJECT-TYPE
  SYNTAX TimeTicks
  ACCESS read-write
  STATUS mandatory
      DESCRIPTION
          "The time, in centiseconds, which should expire between
           the sending of traps. This value is used when no ICMP
           source quench datagrams have been received. The ES/1 uses
           sysTrapTime if any SNMP requests from the NMS has been
           received within the previous sixty seconds. If no requests
           have been received, then the ES/1 reverts to its default
           of a fifteen second wait between the sending of traps."
  ::= { sys 4 }

 sysTrapRetry OBJECT-TYPE
  SYNTAX TimeTicks
  ACCESS read-write
  STATUS mandatory
      DESCRIPTION
           "The time, in centiseconds, which should expire before an
            unacknowledged Trap is re-transmitted."
  ::= { sys 5 }

 sysTrapPort OBJECT-TYPE
  SYNTAX INTEGER
  ACCESS read-write
  STATUS mandatory
      DESCRIPTION
           "Zero, or the UDP port number to which a second copy of
            SNMP traps should be sent. Valid values are zero through
            65535."
  ::= { sys 6 }


 -- Trojan HW Configuration Group


 hwNumber OBJECT-TYPE
  SYNTAX INTEGER
  ACCESS read-only
  STATUS mandatory
      DESCRIPTION
           "The number of slots available for hardware modules,
            regardless of whether or not the slots are currently
            populated. This number is fixed as 7."
  ::= { hw 1 }

 hwSlotTable OBJECT-TYPE
  SYNTAX SEQUENCE OF HwEntry
  ACCESS not-accessible
  STATUS mandatory
      DESCRIPTION
           "A list of the most recent occupants of the slots; one
            per slot."
  ::= { hw 2 }

 hwEntry OBJECT-TYPE
  SYNTAX HwEntry
  ACCESS not-accessible
  STATUS mandatory
      DESCRIPTION
           "A set of objects for each slot."
  INDEX { hwIndex }
  ::= { hwSlotTable 1 }

 HwEntry ::= SEQUENCE {
   hwIndex
    INTEGER,
   hwType
    INTEGER,
   hwUseMod
    INTEGER,
   hwDefType
    INTEGER,
   hwDiagStatus
    INTEGER,
   hwInuse
    INTEGER,
   hwDiagCode
    INTEGER,
   hwManufData
    OCTET STRING,
   hwPortType
    OCTET STRING,
   hwPortStatus
    OCTET STRING,
   hwUsePort
    OCTET STRING,
   hwDefPortType
    OCTET STRING,
   hwAddr1
    OCTET STRING,
   hwAddr2
    OCTET STRING,
   hwAddr3
    OCTET STRING,
   hwAddr4
    OCTET STRING,
   hwTempOK
    INTEGER,
   hwFirstPort
    INTEGER,
   hwFatalErr
    OCTET STRING,
   hwRptrPorts
    OCTET STRING,
   hwPortSubType
    OCTET STRING,
   hwAddr5
    OCTET STRING,
   hwAddr6
    OCTET STRING,
   hwAddr7
    OCTET STRING,
   hwAddr8
    OCTET STRING
   }

 hwIndex OBJECT-TYPE
  SYNTAX INTEGER
  ACCESS read-only
  STATUS mandatory
      DESCRIPTION
           "The slot number, beginning with 1 for the top-most slot.
            This number always matches the instance of the hwEntry.
            For example, {hwIndex 3} contains the value '3'."
  ::= { hwEntry 1 }

 hwType OBJECT-TYPE
  SYNTAX INTEGER {
     vacant(1),
     unknown(2),
     packet-processing-engine(3),
     turbo(4),
     csma-iom(5),
     hssi-iom(6),
     tpr-iom(7),
     fddi-iom(8),
     ifddi-iom(9),
     ttpr-iom(10),
     eiom8-iom(11),
     feiom-iom(12)
    }
  ACCESS read-only
  STATUS mandatory
      DESCRIPTION
           "The module type of the slot's most recent occupant
            since the ES/1 was started. The values for hwType
            correspond to the values for hwPortType."
  ::= { hwEntry 2 }

 hwUseMod OBJECT-TYPE
  SYNTAX INTEGER {
     reset(1),
     run-diagnostics(2),
     run(3)
    }
  ACCESS read-write
  STATUS mandatory
      DESCRIPTION
           "Whether to use this module, not applicable for the
            Packet Processing Engine. The value of hwUseMod is not
            saved if the ES/1 reboots. If the module fails
            diagnostics, it will not be used, regardless of
            hwUseMod."
  ::= { hwEntry 3 }

 hwDefType OBJECT-TYPE
  SYNTAX INTEGER {
     vacant(1),
     unknown(2),
     packet-processing-engine(3),
     turbo(4),
     csma-iom(5),
     hssi-iom(6),
     tpr-iom(7),
     fddi-iom(8),
     ifddi-iom(9),
     ttpr-iom(10),
     eiom8-iom(11),
     feiom-iom(12)
    }
  ACCESS read-only
  STATUS mandatory
      DESCRIPTION
           "The module type defined for the slot. Certain
            pre-defined relationships exist. Slot 1 always contains
            the Packet Processing Engine board. Slots 2-6 are either
            unoccupied, or contain IOM boards. Slot 7 is either
            unoccupied or contains the Turbo processor board. If
            hwDefType does not match hwType, then the module will
            not be used, regardless of the value of hwUseMod. Note
            that hwDefType can only be changed by rebooting the
            ES/1. "
  ::= { hwEntry 4 }

 hwDiagStatus OBJECT-TYPE
  SYNTAX INTEGER {
     diag-failed(1),
     diag-not-present(2),
     diag-passed(3)
    }
  ACCESS read-only
  STATUS mandatory
      DESCRIPTION
           "Results of diagnostics, when diagnostics were last
            performed on the module (whenever a module is released
            from reset, which is usually at power-up)."
  ::= { hwEntry 5 }

 hwInuse OBJECT-TYPE
  SYNTAX INTEGER { true(1), false(2) }
  ACCESS read-only
  STATUS mandatory
      DESCRIPTION
           "Whether the module is currently executing its operational
            software."
  ::= { hwEntry 6 }

 hwDiagCode OBJECT-TYPE
  SYNTAX INTEGER
  ACCESS read-only
  STATUS mandatory
      DESCRIPTION
           "Additional diagnostics information concerning the slot's
            module. The meaning of hwDiagCode depends upon the slot's
            module type described by the hwType parameter. For the
            Packet Processing Engine board, any error (except where
            noted otherwise) will prevent the ES/1 from booting.
            For the Turbo processor board, FDDI IOM board (FIOM),
            the intelligent FDDI IOM board (IFIOM), the Ethernet/802.3
            IOM boards,  the Token-Ring/802.5 IOM boards, the HSSI IOM
            board, any error will prevent the board from being used."
  ::= { hwEntry 7 }

 hwManufData OBJECT-TYPE
  SYNTAX OCTET STRING
  ACCESS read-only
  STATUS mandatory
      DESCRIPTION
           "This is a 24 byte array which contains the part number,
            serial number and hardware revision level of this
            module. The Turbo's hwManufData will be all blanks since
            it is manufactured as part of the Packet Processing
            Engine module."
  ::= { hwEntry 8 }

 hwPortType OBJECT-TYPE
  SYNTAX OCTET STRING
  ACCESS read-only
  STATUS mandatory
      DESCRIPTION
           "This is a variable-length byte array, where each element
            represents the port types belonging to this module. The
            Packet Processing Engine's ports are fixed as 'uart' for
            the first port, and 'none' for any other ports. The Turbo's
            ports are fixed as 'none' for all ports. The following port
            types are supported:
            none (0) there is no port
            csma (1) Ethernet or 802.3 port
            fddi-das (2)   FDDI DAS port
            fddi-sas (3)   FDDI SAS port
            tpr (4)  Token Passing Ring port
            wan (5)  Wide Area Network port
            uart (6) UART port"
  ::= { hwEntry 9 }

 hwPortStatus OBJECT-TYPE
  SYNTAX OCTET STRING
  ACCESS read-only
  STATUS mandatory
      DESCRIPTION
           "This is a variable-length byte array, where each element
            represents the status of the port belonging to this module.
            Values of 01 (status-good) or hex ff (status-bad) are supported.
            For the Packet Processing Engine, the first byte is the status of
            the UART port."
  ::= { hwEntry 10 }

 hwUsePort OBJECT-TYPE
  SYNTAX OCTET STRING
  ACCESS read-write
  STATUS mandatory
	  		 DESCRIPTION ""
  ::= { hwEntry 11 }

 hwDefPortType OBJECT-TYPE
  SYNTAX OCTET STRING
  ACCESS read-only
  STATUS mandatory
      DESCRIPTION
           "This is a variable-length byte array, where each element
            represents the port types defined for the module. If
            hwDefPortType does not match hwPortType, then the port
            will not be used.  Note that hwDefPortType can only be
            changed by rebooting the ES/1."
  ::= { hwEntry 12 }

 hwAddr1 OBJECT-TYPE
  SYNTAX OCTET STRING
  ACCESS read-only
  STATUS mandatory
      DESCRIPTION
           "The unique hard-wired 48 bit MAC address for the module's
            1st port. For the Packet Processing Engine, it's a unique
            MAC address to be used as part of the ES/1's Spanning
            Tree Bridge Identifier. For the Turbo, not applicable."
  ::= { hwEntry 13 }

 hwAddr2 OBJECT-TYPE
  SYNTAX OCTET STRING
  ACCESS read-only
  STATUS mandatory
      DESCRIPTION
           "The unique hard-wired 48 bit MAC address for the module's
            2nd port, only applicable for IOMs."
  ::= { hwEntry 14 }

 hwAddr3 OBJECT-TYPE
  SYNTAX OCTET STRING
  ACCESS read-only
  STATUS mandatory
      DESCRIPTION
           "The unique hard-wired 48 bit MAC address for the module's
            3rd port, only applicable for IOMs."
  ::= { hwEntry 15 }

 hwAddr4 OBJECT-TYPE
  SYNTAX OCTET STRING
  ACCESS read-only
  STATUS mandatory
      DESCRIPTION
           "The unique hard-wired 48 bit MAC address for the module's
            4th port, only applicable for IOMs."
  ::= { hwEntry 16 }

 hwTempOK OBJECT-TYPE
  SYNTAX INTEGER {
     temperature-normal(1),
     temperature-too-hot(2)
    }
  ACCESS read-only
  STATUS mandatory
      DESCRIPTION
           "The temperature condition of the module, where True
            indicates temperature okay, and False indicates
            temperature too hot."
  ::= { hwEntry 17 }

 hwFirstPort OBJECT-TYPE
  SYNTAX INTEGER
  ACCESS read-only
  STATUS mandatory
      DESCRIPTION
           "The ifIndex number of the first port which resides within
            this module. [Not applicable for the Turbo.] "
  ::= { hwEntry 18 }

 hwFatalErr OBJECT-TYPE
  SYNTAX OCTET STRING
  ACCESS read-only
  STATUS mandatory
      DESCRIPTION
           "This is a 32 byte array which contains information about
            the cause of the module's last unexpected self-reset,
            since the ES/1 booted.For the Packet Processing
            Engine and Turbo, this will always be all zeroes, since
            failure of such a module will cause the ES/1 to reboot.
            For the other modules, this field either contains all
            zeroes (if the module has not self-reset), or it contains
            values according to the format of configFatalErr, with a
            first byte of either 'Watchdog Timeout' (1) or 'Fatal
            Error' (3)."
  ::= { hwEntry 19 }

 hwRptrPorts OBJECT-TYPE
  SYNTAX OCTET STRING
  ACCESS read-only
  STATUS mandatory
      DESCRIPTION
           "This is a variable-length byte array, where each element
            represents the repeater capability of the port belonging
            to this module. The element value is zero if the port is
            not present or does not have any repeater capability;
            otherwise, the element value indicates the number of
            repeater ports at that port."
  ::= { hwEntry 20 }

 hwPortSubType OBJECT-TYPE
  SYNTAX OCTET STRING
  ACCESS read-only
  STATUS mandatory
      DESCRIPTION
           "This is a variable-length byte array, where each element
            represents additional port type information."
  ::= { hwEntry 21 }

 hwAddr5 OBJECT-TYPE
  SYNTAX OCTET STRING
  ACCESS read-only
  STATUS mandatory
	  		 DESCRIPTION ""
  ::= { hwEntry 22 }

 hwAddr6 OBJECT-TYPE
  SYNTAX OCTET STRING
  ACCESS read-only
  STATUS mandatory
	  		 DESCRIPTION ""
  ::= { hwEntry 23 }

 hwAddr7 OBJECT-TYPE
  SYNTAX OCTET STRING
  ACCESS read-only
  STATUS mandatory
	  		 DESCRIPTION ""
  ::= { hwEntry 24 }

 hwAddr8 OBJECT-TYPE
  SYNTAX OCTET STRING
  ACCESS read-only
  STATUS mandatory
	  		 DESCRIPTION ""
  ::= { hwEntry 25 }


 hwSysBus OBJECT-TYPE
  SYNTAX INTEGER {
     bus-800-mbit(1),
     bus-1p6-gbit(2)
    }
  ACCESS read-only
  STATUS mandatory
	  		 DESCRIPTION ""
  ::= { hw 3 }

 hwPpeType OBJECT-TYPE
  SYNTAX INTEGER {
     ppe2(1),
     ppe3(2)
    }
  ACCESS read-only
  STATUS mandatory
	  		 DESCRIPTION ""
  ::= { hw 4 }

 hwSysProcessor OBJECT-TYPE
  SYNTAX INTEGER {
     dual-29000(1),
     dual-29030(2)
    }
  ACCESS read-only
  STATUS mandatory
	  		 DESCRIPTION ""
  ::= { hw 5 }

 -- Trojan SW Configuration Group

 swNumber OBJECT-TYPE
  SYNTAX INTEGER
  ACCESS read-only
  STATUS mandatory
      DESCRIPTION
           "The number of file sets. This number is fixed as 2."
  ::= { sw 1 }

 swFilesetTable OBJECT-TYPE
  SYNTAX SEQUENCE OF SwFileset
  ACCESS not-accessible
  STATUS mandatory
      DESCRIPTION
           "A list of the software file sets stored in the ES/1. The
            first file set refers to the file set that was used when
            the ES/1 last booted. The second file set refers to the
            file set that will be used when the ES/1 reboots or
            reloads any hardware module."
  ::= { sw 2 }

 swFileset OBJECT-TYPE
  SYNTAX SwFileset
  ACCESS not-accessible
  STATUS mandatory
      DESCRIPTION
           "A set of objects for each file set."
  INDEX { swIndex }
  ::= { swFilesetTable 1 }

 SwFileset ::= SEQUENCE {
   swIndex
    INTEGER,
   swDesc
    DisplayString,
   swCount
    INTEGER,
   swTypes
    OCTET STRING,
   swSizes
    OCTET STRING,
   swStarts
    OCTET STRING,
   swBases
    OCTET STRING,
   swFlashBank
    INTEGER
   }

 swIndex OBJECT-TYPE
  SYNTAX INTEGER {
     currently-executing(1),
     next-boot(2)
    }
  ACCESS read-only
  STATUS mandatory
      DESCRIPTION
           "The file set number, beginning with 1 for the first file
            set. This number always matches the instance of the swFiles.
            For example, {swIndex 2} contains the value '2'."
  ::= { swFileset 1 }

-- swValid OBJECT-TYPE
--  ::= { swFileset 2 }

 swDesc OBJECT-TYPE
  SYNTAX DisplayString
  ACCESS read-only
  STATUS mandatory
      DESCRIPTION
           "The description (0-255 bytes) of the software file set."
  ::= { swFileset 3 }

 swCount OBJECT-TYPE
  SYNTAX INTEGER
  ACCESS read-only
  STATUS mandatory
      DESCRIPTION
           "The number of files in the file set. This number may range
            from 1 to 255."
  ::= { swFileset 4 }

 swTypes OBJECT-TYPE
  SYNTAX OCTET STRING
  ACCESS read-only
  STATUS mandatory
      DESCRIPTION
           "The types of the files within the file set.The size of
            swFileTypes may be determined by swCount. The possible
            file types are
            none (0) File not present
            ppe-turbo (1)  Packet Processing Engine and/or Turbo Code
            ppe-only(2) Packet Processing Engine Code
            turbo-only (3) Turbo Code
            eiom (4) EIOM Code (for many Ethernet/802.3 IOMs)
            hiom (5) HSSI IOM Code
            tiom (6) Token Ring IOM Code
            fiom (7) FIOM Code
            ifiom (8)   Intelligent FIOM Code
            ttiom (9)   Turbo Token Ring IOM Code
            eiom8 (10)  Octal EIOM Code
   feiom (11)  Fast Ethernet IOM code."
  ::= { swFileset 5 }

 swSizes OBJECT-TYPE
  SYNTAX OCTET STRING
  ACCESS read-only
  STATUS mandatory
      DESCRIPTION
           "An array (4 octets per file), containing the size of each
            of the files. Each size is encoded as a series of 4 bytes,
            which should be converted into a 32 bit integer."
  ::= { swFileset 6 }

 swStarts OBJECT-TYPE
  SYNTAX OCTET STRING
  ACCESS read-only
  STATUS mandatory
      DESCRIPTION
           "An array (4 octets per file), containing the software's
            execution starting address of each of the files. Each
            address is encoded as a series of 4 bytes, which should
            be converted into a 32 bit integer."
  ::= { swFileset 7 }

 swBases OBJECT-TYPE
  SYNTAX OCTET STRING
  ACCESS read-only
  STATUS mandatory
      DESCRIPTION
           "An array (4 octets per file), containing the software's
            base loading address of each of the files. Each address
            is encoded as a series of 4 bytes, which should be
            converted into a 32 bit integer."
  ::= { swFileset 8 }

 swFlashBank OBJECT-TYPE
  SYNTAX INTEGER {
     first-bank(1),
     second-bank(2)
    }
  ACCESS read-only
  STATUS mandatory
      DESCRIPTION
           "The bank number where the software file set resides."
  ::= { swFileset 9 }

 -- Configuration Status Group

 configFatalErr OBJECT-TYPE
  SYNTAX OCTET STRING
  ACCESS read-only
  STATUS mandatory
      DESCRIPTION
           "This is a 32 byte array which contains information about
            the cause of the previous system reset. This will
            describe the circumstances which forced the system
            software to perform a reboot. The values in the first
            byte have the following meanings (0) Power failure, (1)
            Watchdog Timeout, (2) NMS Requested Shutdown, (3-255)
            Fatal Error (next byte contains the hwIndex of the module
            which encountered the error; remaining 30 bytes contain
            additional information)."
  ::= { config 1 }

 configAnyPass OBJECT-TYPE
  SYNTAX OCTET STRING
  ACCESS read-write
  STATUS mandatory
      DESCRIPTION
           "The authentication password (0-24 bytes) which must match
            the community name in an SNMP PDU, in order for the
            operation to be performed. A zero length password
            indicates that any community name is acceptable."
  ::= { config 2 }

 configGetPass OBJECT-TYPE
  SYNTAX OCTET STRING
  ACCESS read-write
  STATUS mandatory
      DESCRIPTION
           "The authentication password (0-24 bytes) which must match
            the community name in an SNMP Get PDU (except for Debug
            or password parameters). A zero length password indicates
            that any community name is acceptable. Alternatively, it
            is acceptable if the community name matches
            configAnyPass."
  ::= { config 3 }

 configNMSAddress OBJECT-TYPE
  SYNTAX IpAddress
  ACCESS read-write
  STATUS mandatory
      DESCRIPTION
           "The address of the NMS to which Trap PDUs are to be sent.
            A value of zero indicates that Trap PDUs should be sent
            to the NMS last heard from."
  ::= { config 4 }

 configFunctions OBJECT-TYPE
  SYNTAX INTEGER
  ACCESS read-only
  STATUS mandatory
      DESCRIPTION
           "A bit field which describes the software functions
            supported by this ES/1. The possible values are:
            0x0001   NMS, 0x0002   TBRIDGE, 0x0004   SBRIDGE,
            0x0008   MESH, 0x0010   IPROUTER, 0x0020   NO_BPDU,
            0x0040   RIP, 0x0100   PROXY, 0x0200   OSPF,
            0x0400   IPX."
  ::= { config 5 }

 configPowerAc1 OBJECT-TYPE
  SYNTAX INTEGER {
     ac-good(1),
     ac-bad(2)
    }
  ACCESS read-only
  STATUS mandatory
      DESCRIPTION
           "Whether the first power supply has AC input."
  ::= { config 6 }

 configPowerAc2 OBJECT-TYPE
  SYNTAX INTEGER {
     ac-good(1),
     ac-bad(2)
    }
  ACCESS read-only
  STATUS mandatory
      DESCRIPTION
           "Whether the second power supply has AC input."
  ::= { config 7 }

 configPowerDc1 OBJECT-TYPE
  SYNTAX INTEGER {
     dc-good(1),
     dc-bad(2)
    }
  ACCESS read-only
  STATUS mandatory
      DESCRIPTION
           "Whether the first power supply provides DC voltage."
  ::= { config 8 }

 configPowerDc2 OBJECT-TYPE
  SYNTAX INTEGER {
     dc-good(1),
     dc-bad(2)
    }
  ACCESS read-only
  STATUS mandatory
      DESCRIPTION
           "Whether the second power supply provides DC voltage."
  ::= { config 9 }

 configPowerPresent1 OBJECT-TYPE
  SYNTAX INTEGER {
     supply-present(1),
     supply-absent(2)
    }
  ACCESS read-only
  STATUS mandatory
      DESCRIPTION
           "Whether the first power supply is present."
  ::= { config 10 }

 configPowerPresent2 OBJECT-TYPE
  SYNTAX INTEGER {
     supply-present(1),
     supply-absent(2)
    }
  ACCESS read-only
  STATUS mandatory
      DESCRIPTION
           "Whether the second power supply is present."
  ::= { config 11 }

 configAlarmDynamic OBJECT-TYPE
  SYNTAX INTEGER { true(1), false(2) }
  ACCESS read-write
  STATUS mandatory
      DESCRIPTION
           "Whether changes in dynamic parameters (except for the
            dynamically learned addresses) should cause enterprise
            specific trap PDUs to be generated."
  ::= { config 12 }

 configAlarmAddresses OBJECT-TYPE
  SYNTAX INTEGER { true(1), false(2) }
  ACCESS read-write
  STATUS mandatory
      DESCRIPTION
           "Whether changes in the dynamically learned addresses
            should cause enterprise specific trap PDUs to be
            generated."
  ::= { config 13 }

 configStorageFailure OBJECT-TYPE
  SYNTAX INTEGER { true(1), false(2) }
  ACCESS read-only
  STATUS mandatory
      DESCRIPTION
           "Whether the ES/1's storage facility for its configuration
            parameters has failed (the ES/1 may not be able to reboot
            after such a failure)."
  ::= { config 14 }

 configAuthenticationFailure OBJECT-TYPE
  SYNTAX IpAddress
  ACCESS read-only
  STATUS mandatory
      DESCRIPTION
           "All nulls, or the IP source address within the last SNMP
            PDU which caused an SNMP authentication failure."
  ::= { config 15 }

 configFddiPriority OBJECT-TYPE
  SYNTAX INTEGER
  ACCESS read-write
  STATUS mandatory
      DESCRIPTION
           "Priority to use when forwarding packets to any FDDI port
            from any non-FDDI port."
  ::= { config 16 }

 configTprPriority OBJECT-TYPE
  SYNTAX INTEGER
  ACCESS read-write
  STATUS mandatory
      DESCRIPTION
           "Priority to use when forwarding packets to any Token-Ring
            port from any non-Token-Ring port."
  ::= { config 17 }

   configDumpModule  OBJECT-TYPE
      SYNTAX   INTEGER
      ACCESS   read-write
      STATUS   mandatory
      DESCRIPTION
   "Flag to select the module to dump on a crash.
    If set to a value of 1 to 7 the relevant module's
    memory will be sent to the UART port on detecting
    a fatal error situation. A value of zero will
    disable the dump option. A value of 1 selects the
    ME, 7 selects the TURBO, and 2-6 select IOMs. "
      ::= { config 19 }

   configDumpStart   OBJECT-TYPE
      SYNTAX   INTEGER
      ACCESS   read-write
      STATUS   mandatory
  DESCRIPTION
   "Starting address of memory to dump upon detecting
    a fatal error. "
      ::= { config 20 }

   configDumpEnd     OBJECT-TYPE
      SYNTAX   INTEGER
      ACCESS   read-write
      STATUS   mandatory
  DESCRIPTION
         "Ending address of memory to dump upon detecting
          a fatal error."
      ::= { config 21 }



 -- LMA Configuration Group



 lmaAllAddr OBJECT-TYPE
  SYNTAX OCTET STRING
  ACCESS read-write
  STATUS mandatory
  DESCRIPTION
           "The IEEE All LANs Bridge Management Group Address
            01-80-c2-00-00-10. Changing lmaAllAddr will not take
            effect until the ES/1 reboots."
  ::= { lma 1 }

 lmaAnyAddr OBJECT-TYPE
  SYNTAX OCTET STRING
  ACCESS read-write
  STATUS mandatory
  DESCRIPTION
           "A spare LMA address, which is always all zeroes. Changing
            lmaAllAny will not take effect until the ES/1 reboots."
  ::= { lma 2 }


 -- PPE Configuration Group

 ppeLrgUxRxCnt OBJECT-TYPE
  SYNTAX INTEGER
  ACCESS read-write
  STATUS mandatory
  DESCRIPTION
           "The number of large data buffers to allocate for the PPE
            to create packets. This value may be changed
            automatically by the ES/1 as a result of enabling IPX
            routing. The ES/1 will calculate the minimum number of
            such buffers that are needed for the number of configured
            ports and may adjust this count upward if needed."
  ::= { ppe 1 }

 ppeSmlUxRxCnt OBJECT-TYPE
  SYNTAX INTEGER
  ACCESS read-write
  STATUS mandatory
  DESCRIPTION
           "The number of small data buffers to allocate for the PPE
            to create packets."
  ::= { ppe 2 }

 ppeUxTxCnt OBJECT-TYPE
  SYNTAX INTEGER
  ACCESS read-write
  STATUS mandatory
  DESCRIPTION
           "The maximum number of received packets destined to the
            ES/1 itself (versus those received packets to be
            forwarded) which can be stored, until the PPE is able to
            process them."
  ::= { ppe 3 }

 ppeSmlBuffSize OBJECT-TYPE
  SYNTAX INTEGER
  ACCESS read-write
  STATUS mandatory
  DESCRIPTION
           "The size (in bytes) of the PPE's small data buffers."
  ::= { ppe 4 }

 ppeBridgingMemory OBJECT-TYPE
  SYNTAX INTEGER
  ACCESS read-only
  STATUS mandatory
  DESCRIPTION
           "The percentage (1 - 99) of the PPE's memory that is
            allocated for MAC bridging. The PPE's remaining memory
            will be used for communicating with the NMS and for
            routing. Operationally, a value between 70 percent and
            99 percent will be treated as 70 percent. This allows for
            approximately 8000 learned addresses (bridging) and
            either 1600 TCP/IP routes or 1200 IPX RIP/SAP pairs.
            To increase the space available for routing, set
            rebootBridgingMemory to a value less than 70 percent."
  ::= { ppe 5 }

 ppeExtendStats OBJECT-TYPE
  SYNTAX INTEGER { true(1), false(2) }
  ACCESS read-write
  STATUS mandatory
  DESCRIPTION
           "Whether the PPE should accumulate extended statistics.
            Extended statistics are tallies, such as byte counts,
            which are not essential for everyday ES/1 management,
            and which may have a slightly detrimental effect on
            performance."
  ::= { ppe 6 }

 ppeBAddrLimit OBJECT-TYPE
  SYNTAX INTEGER
  ACCESS read-write
  STATUS mandatory
  DESCRIPTION
           "The maximum number of addresses that the PPE should learn
            for bridging purposes. The remaining address entries will
            be used for routing related addresses."
  ::= { ppe 7 }

 ppeTxCongests OBJECT-TYPE
  SYNTAX Counter
  ACCESS read-only
  STATUS mandatory
  DESCRIPTION
           "Number of packets not received due to internal buffer
            congestion."
  ::= { ppe 8 }

 ppeArpEntries OBJECT-TYPE
  SYNTAX Counter
  ACCESS read-only
  STATUS mandatory
  DESCRIPTION
           "The number of ARP entries for all interfaces."
  ::= { ppe 9 }

 ppeArpStatics OBJECT-TYPE
  SYNTAX Counter
  ACCESS read-only
  STATUS mandatory
  DESCRIPTION
           "The number of statically defined ARP entries for all
            interfaces."
  ::= { ppe 10 }

 ppeArpOverflows OBJECT-TYPE
  SYNTAX Counter
  ACCESS read-only
  STATUS mandatory
  DESCRIPTION
           "The number of times a ARP entry could not be learned due
            to insufficient address table space."
  ::= { ppe 11 }

 ppeIpEntries OBJECT-TYPE
  SYNTAX Counter
  ACCESS read-only
  STATUS mandatory
  DESCRIPTION
           "The number of IP Routing Database entries."
  ::= { ppe 12 }

 ppeIpStatics OBJECT-TYPE
  SYNTAX Counter
  ACCESS read-only
  STATUS mandatory
  DESCRIPTION
           "The number of statically defined IP Routing Database
            entries."
  ::= { ppe 13 }

 ppeStaticPreference OBJECT-TYPE
  SYNTAX INTEGER
  ACCESS read-write
  STATUS mandatory
  DESCRIPTION
           "The value to assign to ipRouteMetric2, when adding a
            statically-defined entry to the IP Routing Table."
  ::= { ppe 14 }

 ppeOspfPreference OBJECT-TYPE
  SYNTAX INTEGER
  ACCESS read-write
  STATUS mandatory
  DESCRIPTION
           "The value to assign to ipRouteMetric2, when adding an
            OSPF-learned entry to the IP Routing Table."
  ::= { ppe 15 }

 ppeRipPreference OBJECT-TYPE
  SYNTAX INTEGER
  ACCESS read-write
  STATUS mandatory
  DESCRIPTION
           "The value to assign to ipRouteMetric2, when adding a
            RIP-learned entry to the IP Routing Table."
  ::= { ppe 16 }

 ppeEgpPreference OBJECT-TYPE
  SYNTAX INTEGER
  ACCESS read-write
  STATUS mandatory
  DESCRIPTION
           "The value to assign to ipRouteMetric2, when adding an
            EGP-learned entry to the IP Routing Table."
  ::= { ppe 17 }

 ppeCpuUtilization OBJECT-TYPE
  SYNTAX INTEGER { low-cpu(1), medium-cpu(2), high-cpu(3) }
  ACCESS read-only
  STATUS mandatory
  DESCRIPTION
           "The current CPU utilization on the Packet Processing
            Engine."
  ::= { ppe 18 }

 ppeRipRouteDiscards OBJECT-TYPE
  SYNTAX Counter
  ACCESS read-only
  STATUS mandatory
  DESCRIPTION
           "The number of times a route learned via RIP was not added
            to the IP Routing Table due to insufficient Routing Table
            space."
  ::= { ppe 19 }

 ppeOspfRouteDiscards OBJECT-TYPE
  SYNTAX Counter
  ACCESS read-only
  STATUS mandatory
  DESCRIPTION
           "The number of times a route learned via OSPF was not
            added to the IP Routing Table due to insufficient Routing
            Table space (currently always zero)."
  ::= { ppe 20 }

 ppeRouteMemorySize OBJECT-TYPE
  SYNTAX Counter
  ACCESS read-only
  STATUS mandatory
  DESCRIPTION
        "The number of bytes originally given to the routing table
         heap."
  ::= { ppe 21 }

 ppeRouteMemoryAvail OBJECT-TYPE
  SYNTAX Counter
  ACCESS read-only
  STATUS mandatory
  DESCRIPTION
        "The number of bytes currently available in the routing table
         heap."
  ::= { ppe 22 }

 ppeRouteMemoryFailures OBJECT-TYPE
  SYNTAX Counter
  ACCESS read-only
  STATUS mandatory
  DESCRIPTION
        "The number of unsuccessful attempts to allocate from the
         routing table heap."
  ::= { ppe 23 }

 ppePacketMemorySize OBJECT-TYPE
  SYNTAX Counter
  ACCESS read-only
  STATUS mandatory
  DESCRIPTION
        "The number of bytes originally given to the packet heap."
  ::= { ppe 24 }

 ppePacketMemoryAvail OBJECT-TYPE
  SYNTAX Counter
  ACCESS read-only
  STATUS mandatory
  DESCRIPTION
        "The number of bytes currently available in the packet heap."
  ::= { ppe 25 }

 ppePacketMemoryFailures OBJECT-TYPE
  SYNTAX Counter
  ACCESS read-only
  STATUS mandatory
  DESCRIPTION
        "The number of unsuccessful attempts to allocate from the
         packet heap."
  ::= { ppe 26 }

ppeOspfPduMemoryFailures OBJECT-TYPE
 SYNTAX Counter
 ACCESS read-only
 STATUS mandatory
 DESCRIPTION
     "Number of unsuccessful attempts to allocate memory for an OSPF
      PDU."
 ::= { ppe 27 }

ppeOspfPduMemoryAllocs OBJECT-TYPE
 SYNTAX Counter
 ACCESS read-only
 STATUS mandatory
 DESCRIPTION
  "Number of times memory was allocated for an OSPF PDU."
 ::= { ppe 28 }

ppeIcmpPduMemoryFailures OBJECT-TYPE
 SYNTAX Counter
 ACCESS read-only
 STATUS mandatory
 DESCRIPTION
    "Number of unsuccessful attempts to allocate memory for an ICMP
     PDU."
 ::= { ppe 29 }

ppeIcmpPduMemoryAllocs OBJECT-TYPE
 SYNTAX Counter
 ACCESS read-only
 STATUS mandatory
 DESCRIPTION
  "Number of times memory was allocated for an ICMP PDU."
 ::= { ppe 30 }

ppeRipPduMemoryFailures OBJECT-TYPE
 SYNTAX Counter
 ACCESS read-only
 STATUS mandatory
 DESCRIPTION
     "Number of unsuccessful attempts to allocate memory for a
      RIP PDU."
 ::= { ppe 31 }

ppeRipPduMemoryAllocs OBJECT-TYPE
 SYNTAX Counter
 ACCESS read-only
 STATUS mandatory
 DESCRIPTION
  "Number of times memory was allocated for a RIP PDU."
 ::= { ppe 32 }

ppeBootpPduMemoryFailures OBJECT-TYPE
 SYNTAX Counter
 ACCESS read-only
 STATUS mandatory
 DESCRIPTION
     "Number of unsuccessful attempts to allocate memory for a BOOTP
       PDU."
 ::= { ppe 33 }

ppeBootpPduMemoryAllocs OBJECT-TYPE
 SYNTAX Counter
 ACCESS read-only
 STATUS mandatory
 DESCRIPTION
  "Number of times memory was allocated for a BOOTP PDU."
 ::= { ppe 34 }

ppeSnmpPduMemoryFailures OBJECT-TYPE
 SYNTAX Counter
 ACCESS read-only
 STATUS mandatory
 DESCRIPTION
  "Number of unsuccessful attempts to allocate memory for an SNMP
       PDU."
 ::= { ppe 35 }

ppeSnmpPduMemoryAllocs OBJECT-TYPE
 SYNTAX Counter
 ACCESS read-only
 STATUS mandatory
 DESCRIPTION
  "Number of times memory was allocated for an SNMP PDU."
 ::= { ppe 36 }

ppeTftpPduMemoryFailures OBJECT-TYPE
 SYNTAX Counter
 ACCESS read-only
 STATUS mandatory
 DESCRIPTION
     "Number of unsuccessful attempts to allocate memory for a
      TFTP PDU."
 ::= { ppe 37 }

ppeTftpPduMemoryAllocs OBJECT-TYPE
 SYNTAX Counter
 ACCESS read-only
 STATUS mandatory
 DESCRIPTION
  "Number of times memory was allocated for a TFTP PDU."
 ::= { ppe 38 }

ppeTraceroutePduMemoryFailures OBJECT-TYPE
 SYNTAX Counter
 ACCESS read-only
 STATUS mandatory
 DESCRIPTION
  "Number of unsuccessful attempts to allocate memory for a
       TraceRoute PDU."
 ::= { ppe 39 }


ppeTraceroutePduMemoryAllocs OBJECT-TYPE
 SYNTAX Counter
 ACCESS read-only
 STATUS mandatory
 DESCRIPTION
  "Number of times memory was allocated for a TraceRoute PDU."
 ::= { ppe 40 }

ppeArpPduMemoryFailures OBJECT-TYPE
 SYNTAX Counter
 ACCESS read-only
 STATUS mandatory
 DESCRIPTION
  "Number of unsuccessful attempts to allocate memory for a ARP PDU."
 ::= { ppe 41 }

ppeArpPduMemoryAllocs OBJECT-TYPE
 SYNTAX Counter
 ACCESS read-only
 STATUS mandatory
 DESCRIPTION
  "Number of times memory was allocated for a ARP PDU."
 ::= { ppe 42 }

ppeIgmpPduMemoryFailures OBJECT-TYPE
 SYNTAX Counter
 ACCESS read-only
 STATUS mandatory
 DESCRIPTION
  "Number of unsuccessful attempts to allocate memory for a IGMP PDU."
 ::= { ppe 43 }

ppeIgmpPduMemoryAllocs OBJECT-TYPE
 SYNTAX Counter
 ACCESS read-only
 STATUS mandatory
 DESCRIPTION
  "Number of times memory was allocated for a IGMP PDU."
 ::= { ppe 44 }

ppeAresAsStes OBJECT-TYPE
 SYNTAX INTEGER { true(1), false(2) }
 ACCESS read-write
 STATUS mandatory
 DESCRIPTION
  "If true, all-routes-explorers will be treated as if they were
         spanning-tree-explorers."
  ::= { ppe 45 }

ppeRoutePercent OBJECT-TYPE
 SYNTAX INTEGER
 ACCESS read-only
 STATUS mandatory
	  		 DESCRIPTION ""
 ::= { ppe 46 }

ppeMgtMemorySize OBJECT-TYPE
 SYNTAX Counter
 ACCESS read-only
 STATUS mandatory
 DESCRIPTION
    "The number of bytes originally given to the local management
     agent heap."
 ::= { ppe 48 }

ppeMgtMemoryAvail OBJECT-TYPE
 SYNTAX Counter
 ACCESS read-only
 STATUS mandatory
 DESCRIPTION
    "The number of bytes currently available in the local management
     agent heap."
 ::= { ppe 49 }

ppeMgtMemoryFailures OBJECT-TYPE
 SYNTAX Counter
 ACCESS read-only
 STATUS mandatory
 DESCRIPTION
    "The number of unsuccessful attempts to allocate from the
     local management agent heap."
 ::= { ppe 50 }

 -- Spanning Tree Group

 stGroupAddr OBJECT-TYPE
  SYNTAX OCTET STRING
  ACCESS read-write
  STATUS mandatory
    DESCRIPTION
        "The Spanning Tree Group address, normally 01-80-c2-00-00-00.
     Changing stGroupAddr will not take effect until the ES/1
         reboots."
  ::= { st 1 }

 stResAddr OBJECT-TYPE
  SYNTAX OCTET STRING
  ACCESS read-write
  STATUS mandatory
    DESCRIPTION
        "A series of 90 octets containing the Spanning Tree's 15
         reserved addres 01-80-c2-00-00-01 through 01-80-c2-00-00-0f).
         Changing stResAddr will not take effect until the ES/1
         reboots."
  ::= { st 2 }

 stBridgeId OBJECT-TYPE
  SYNTAX OCTET STRING
  ACCESS read-write
  STATUS mandatory
	  		 DESCRIPTION ""
  ::= { st 3 }

 stRootMaxAge OBJECT-TYPE
  SYNTAX TimeTicks
  ACCESS read-write
  STATUS mandatory
	  		 DESCRIPTION ""
  ::= { st 4 }

 stRootHello OBJECT-TYPE
  SYNTAX TimeTicks
  ACCESS read-write
  STATUS mandatory
	  		 DESCRIPTION ""
  ::= { st 5 }

 stRootDelay OBJECT-TYPE
  SYNTAX TimeTicks
  ACCESS read-write
  STATUS mandatory
	  		 DESCRIPTION ""
  ::= { st 6 }

 stRootID OBJECT-TYPE
  SYNTAX OCTET STRING
  ACCESS read-only
  STATUS mandatory
	  		 DESCRIPTION ""
  ::= { st 7 }

 stRootCost OBJECT-TYPE
  SYNTAX INTEGER
  ACCESS read-only
  STATUS mandatory
	  		 DESCRIPTION ""
  ::= { st 8 }

 stRootPort OBJECT-TYPE
  SYNTAX INTEGER
  ACCESS read-only
  STATUS mandatory
	  		 DESCRIPTION ""
  ::= { st 9 }

 stTopChange OBJECT-TYPE
  SYNTAX INTEGER { true(1), false(2) }
  ACCESS read-only
  STATUS mandatory
    DESCRIPTION
        "Whether a topology change is currently in progress."
  ::= { st 10 }

 stActMaxAge OBJECT-TYPE
  SYNTAX TimeTicks
  ACCESS read-only
  STATUS mandatory
	  		 DESCRIPTION ""
  ::= { st 11 }

 stActHello OBJECT-TYPE
  SYNTAX TimeTicks
  ACCESS read-only
  STATUS mandatory
	  		 DESCRIPTION ""
  ::= { st 12 }

 stActDelay OBJECT-TYPE
  SYNTAX TimeTicks
  ACCESS read-only
  STATUS mandatory
	  		 DESCRIPTION ""
  ::= { st 13 }

 stTopChangeCount OBJECT-TYPE
  SYNTAX INTEGER
  ACCESS read-write
  STATUS mandatory
    DESCRIPTION
        "The number of spanning tree topology changes which have
         occurred, since the ES/1 was last booted (or this parameter
         was last reset by the NMS)."
  ::= { st 14 }

 stTopChangeTime OBJECT-TYPE
  SYNTAX TimeTicks
  ACCESS read-only
  STATUS mandatory
    DESCRIPTION
        "If stTopChange is True, then the time since stTopChange
         changed from False to True. If stTopChange is False, then
         the time since stTopChange changed from True to False."
  ::= { st 15 }

 stAgeTime OBJECT-TYPE
  SYNTAX INTEGER
  ACCESS read-write
  STATUS mandatory
	  		 DESCRIPTION ""
  ::= { st 16 }

 -- Mesh Group

 meshCostPercent OBJECT-TYPE
  SYNTAX INTEGER
  ACCESS read-write
  STATUS mandatory
	  		 DESCRIPTION ""
  ::= { mesh 1 }

 meshCost OBJECT-TYPE
  SYNTAX INTEGER
  ACCESS read-write
  STATUS mandatory
	  		 DESCRIPTION ""
  ::= { mesh 2 }

 meshCostChange OBJECT-TYPE
  SYNTAX INTEGER { true(1), false(2) }
  ACCESS read-only
  STATUS mandatory
	  		 DESCRIPTION ""
  ::= { mesh 3 }

 meshCostChangeCount OBJECT-TYPE
  SYNTAX INTEGER
  ACCESS read-write
  STATUS mandatory
	  		 DESCRIPTION ""
  ::= { mesh 4 }

 meshCostChangeTime OBJECT-TYPE
  SYNTAX TimeTicks
  ACCESS read-only
  STATUS mandatory
	  		 DESCRIPTION ""
  ::= { mesh 5 }

 meshSubnet OBJECT-TYPE
  SYNTAX OCTET STRING
  ACCESS read-only
  STATUS mandatory
	  		 DESCRIPTION ""
  ::= { mesh 6 }

 -- Software Distribution Group

 swdisDesc OBJECT-TYPE
  SYNTAX OCTET STRING
  ACCESS read-only
  STATUS mandatory
    DESCRIPTION
        "The description (0-32 bytes) of the software set currently
         being downloaded, or a description of the software set last
         downloaded since the ES/1 booted."
  ::= { swdis 1 }

 swdisAccess OBJECT-TYPE
  SYNTAX INTEGER {
     protected(1),
     any-software(2)
    }
  ACCESS read-write
  STATUS mandatory
    DESCRIPTION
        "The version of software that may be downloaded. Attempts to
         download other versions of software will be rejected. The
         value for swdisAccess is embedded within the software files
         that are to be distributed via TFTP. Its value may be
         derived from the names of the software files. the NMS operator
         may wish to use the following special values:
         protected (1)  No software downloads will be accepted
         any-software (2)  A software download of any version of new
         software will be accepted - this is the factory default"
  ::= { swdis 2 }

 swdisWriteStatus OBJECT-TYPE
  SYNTAX INTEGER {
     in-progress(1),
     success(2),
     config-error(3),
     flash-error(4),
     config-and-flash-errors(5)
    }
  ACCESS read-only
  STATUS mandatory
    DESCRIPTION
        "The status of the erase/write operation."
  ::= { swdis 3 }

 swdisConfigIp OBJECT-TYPE
  SYNTAX IpAddress
  ACCESS read-write
  STATUS mandatory
    DESCRIPTION
        "The IP address of the NMS (i.e., any IP host) that is allowed
         to use TFTP to send/retrieve the configuration file of the
         ES/1. A value of 0.0.0.0 (which is the factory specified
         default) prevents any NMS from obtaining access, while a
         value of 255.255.255.255 gives every NMS permission."
  ::= { swdis 4 }

 swdisConfigRetryTime OBJECT-TYPE
  SYNTAX INTEGER
  ACCESS read-write
  STATUS mandatory
    DESCRIPTION
        "The number of seconds that the ES/1 will wait for an
         acknowledgment before it retransmits an unacknowledged TFTP
         data block. The factory specified default is 5 seconds."
  ::= { swdis 5 }

 swdisConfigTotalTimeout OBJECT-TYPE
  SYNTAX INTEGER
  ACCESS read-write
  STATUS mandatory
    DESCRIPTION
        "The number of seconds that the ES/1 will wait for an
         acknowledgment to a data block before it cancels a TFTP
         session. The factory specified default is 25 seconds."
  ::= { swdis 6 }

 -- Address Configuration

 addrStatics OBJECT-TYPE
  SYNTAX  Counter
  ACCESS read-only
  STATUS mandatory
    DESCRIPTION
        "The number of static addresses which are currently stored in
         the ES/1."
  ::= { addr 1 }

 addrDynamics OBJECT-TYPE
  SYNTAX Counter
  ACCESS read-only
  STATUS mandatory
    DESCRIPTION
        "The number of learned addresses in the address table."
  ::= { addr 2 }

 addrDynamicMax OBJECT-TYPE
  SYNTAX Gauge
  ACCESS read-write
  STATUS mandatory
    DESCRIPTION
        "The maximum number of spanning tree addresses which have
         been learned since the ES/1 was last booted (or this
         parameter was last reset by the NMS)."
  ::= { addr 3 }

 addrMeshs OBJECT-TYPE
  SYNTAX  Counter
  ACCESS read-only
  STATUS mandatory
    DESCRIPTION
        "The number of ATM, Frame Relay, and/or SMDS addresses in the
         address table. These addresses are not reflected within
         addrStatics nor addrDynamics. [ATM, Frame Relay, and SMDS
         are not yet implemented.]"
  ::= { addr 4 }

 addrDynamicOverflows OBJECT-TYPE
  SYNTAX Counter
  ACCESS read-only
  STATUS mandatory
    DESCRIPTION
        "The number times an address was not learned due to
         insufficient address table space."
  ::= { addr 5 }


 addrMeshOverflows OBJECT-TYPE
  SYNTAX Counter
  ACCESS read-only
  STATUS mandatory
    DESCRIPTION
        "The number of times an ATM, Frame Relay, or SMDS address
         could not be learned due to insufficient address table space.
         [ATM, Frame Relay, and SMDS are not yet implemented.]"
  ::= { addr 6 }

 addrFlags OBJECT-TYPE
  SYNTAX INTEGER
  ACCESS read-write
  STATUS mandatory
    DESCRIPTION
        "Flags to describe the use and control of this address entry.
         Each bit has a different meaning. The NMS must always set
         either entry-static, entry-none, or entry-mesh; however, for
         GetRequests, the NMS will see either no bits set (if the
         entry does not exist), or exactly one of the following bits
         set: entry-dynamic-local = 30,entry-dynamic-remote = 29,
         entry-static = 28,  entry-other = 27, entry-none = 26,
         entry-mesh = 25, entry-statistics = 24,Bit 31 is reserved.

         Any combination of the restriction bits (bits 23-21) may be
         set for any type of entry, except entry-other or entry-mesh:
   entry-no-source = 23, entry-no-multi = 22, Bit 21 is reserved,
   Bits 20-18 are reserved.

         Exactly one of the special entry bits (bits 17-10) must be
         set for entry-other entries, and none of the bits may be set
         for other than entry-other entries: entry-all-lmas = 17,
         entry-any-lma = 16, entry-lma = 15, entry-port = 14,
         entry-bpdu = 13, entry-reserved = 12, Bits 11-10 are
         reserved for future expansion. Bits 9-0 are reserved. "
  ::= { addr 7 }

 addrMAC OBJECT-TYPE
  SYNTAX OCTET STRING
  ACCESS read-write
  STATUS mandatory
    DESCRIPTION
        "The MAC address for this address definition."
  ::= { addr 8 }

 addrPort OBJECT-TYPE
  SYNTAX INTEGER
  ACCESS read-write
  STATUS mandatory
    DESCRIPTION
        "The port through which this address is connected to the ES/1
         (only valid for entry-dynamic-local, entry-statistics, and
         entry-port entries)."
  ::= { addr 9 }

 addrPortMap OBJECT-TYPE
  SYNTAX OCTET STRING
  ACCESS read-write
  STATUS obsolete -- deprecated in favor of dot1d_static
    DESCRIPTION
        "This is a bitmap of up to 32 sets of 32 bits each (128
         octets), which defines which source ports are allowed to
         forward packets to which destination ports. Within each set
         of four octets, each bit is set if a packet with a matching
         destination address may be forwarded to that port.Since only
         the ES/1's ports 2 through 21 are available for bridging,
         all unused bits as well as the first 8 octets as well as the
         last 40 octets are meaningless."
  ::= { addr 10 }

    -- { addr 11 } through { addr 40 } are not used

 addrOperation OBJECT-TYPE
  SYNTAX INTEGER {
     read-random(1),
     read-next(2),
     zero-stats(3),
     update(4),
     delete(5),
     read-block(6)
    }
  ACCESS read-write
  STATUS mandatory
    DESCRIPTION
        "The operation to be performed upon the described address.
         The possibilities include: read-random (1), read-next (2),
         zero-stats (3), update (4), delete (5), read-block (6)."
  ::= { addr 41 }

 addrIndex OBJECT-TYPE
  SYNTAX INTEGER
  ACCESS read-write
  STATUS mandatory
    DESCRIPTION
        "The index number to be used for read-next and read-block
         operations. When the ES/1 boots, addrIndex is initialized
         to -1."
  ::= { addr 42 }

    -- { addr 43 } is not used

 addrNext OBJECT-TYPE
  SYNTAX INTEGER
  ACCESS read-write
  STATUS mandatory
    DESCRIPTION
        "The next value to use for addrIndex, when you use read-next
         or read-block operations to read the address table. When the
         ES/1 boots, addrNext is initialized to -1."
  ::= { addr 44 }

 addrAge OBJECT-TYPE
  SYNTAX TimeTicks
  ACCESS read-write
  STATUS mandatory
    DESCRIPTION
        "The time, in centiseconds, since a packet was last received
         from the address on a port that was in Spanning Tree
         learning or forwarding state. If no packets have been
         received, then addrAge contains the time that the address
         was created on the ES/1."
  ::= { addr 45 }

 addrRxPkts OBJECT-TYPE
  SYNTAX Counter
  ACCESS read-write
  STATUS mandatory
    DESCRIPTION
        "The number of packets received from the address on a port
         that was in Spanning Tree learning or forwarding state (can
         be zeroed by zero-stats)."
  ::= { addr 46 }

 addrRxChars OBJECT-TYPE
  SYNTAX Counter
  ACCESS read-write
  STATUS mandatory
    DESCRIPTION
        "The number of characters in the packets received from the
         address on a port that was in Spanning Tree Learning or
         Forwarding state (can be zeroed by zero-stats)."
  ::= { addr 47 }

 addrRxMultiPkts OBJECT-TYPE
  SYNTAX Counter
  ACCESS read-write
  STATUS mandatory
    DESCRIPTION
        "The number of multicast packets received from the address on
         a port that was in Spanning Tree Learning or Forwarding
         state (can be zeroed by zero-stats)."
  ::= { addr 48 }

 addrRxFwdPkts OBJECT-TYPE
  SYNTAX Counter
  ACCESS read-write
  STATUS mandatory
    DESCRIPTION
        "The number of packets received from the address which were
     forwarded (can be zeroed by zero-stats). This includes packets
         that were MAC-layer bridged because they were received on a
         port that was in Spanning Tree forwarding state, and packets
         that were routed regardless of the port's Spanning Tree
         state."
  ::= { addr 49 }

 addrTxPkts OBJECT-TYPE
  SYNTAX Counter
  ACCESS read-write
  STATUS mandatory
    DESCRIPTION
        "The number of packets transmitted to the address (can be zeroed
         by zero-stats)."
  ::= { addr 50 }

 addrTxChars OBJECT-TYPE
  SYNTAX Counter
  ACCESS read-write
  STATUS mandatory
    DESCRIPTION
        "The number of characters in the packets transmitted to the
         address (can be zeroed by zero-stats)."
  ::= { addr 51 }

 addrBlockSize OBJECT-TYPE
  SYNTAX INTEGER
  ACCESS read-write
  STATUS mandatory
    DESCRIPTION
        "The number of addresses contained by addrBlock.This parameter is
         only used for dumping blocks of MAC addresses."
  ::= { addr 52 }

 addrBlock OBJECT-TYPE
  SYNTAX OCTET STRING
  ACCESS read-write
  STATUS mandatory
    DESCRIPTION
        "A series of 0-700 octets, which represents 0-100 addresses.
         Each address consists of a 6 octet MacAddress followed by a
         1 byte port number. If the port number is zero, then the
         address is that of a specially configured address; otherwise,
         the address is a dynamically learned address. This parameter
         is only used for dumping blocks of MAC addresses."
  ::= { addr 53 }

 addrAlarmMAC OBJECT-TYPE
  SYNTAX OCTET STRING
  ACCESS read-only
  STATUS mandatory
    DESCRIPTION
        "The MAC address for an address entry. This parameter is only
         used by the ES/1's enterprise specific trap mechanism."
  ::= { addr 54 }

 addrRptrPort OBJECT-TYPE
  SYNTAX INTEGER
  ACCESS read-write
  STATUS mandatory
    DESCRIPTION
        "The repeater port through which this address is connected to
         the port indicated by addrPort. This parameter is only valid
         if the port's srepeaterExtendedStats is enabled, and if the
         ES/1's ppeExtendStats is true."
  ::= { addr 55 }

 -- SNMP/SMT Support Group

 snmpsmtUpstreamReq OBJECT-TYPE
  SYNTAX OCTET STRING
  ACCESS read-write
  STATUS mandatory
	  		 DESCRIPTION ""
  ::= { snmpsmt 1 }

 snmpsmtUpstreamRsp OBJECT-TYPE
  SYNTAX OCTET STRING
  ACCESS read-only
  STATUS mandatory
  	  		 DESCRIPTION ""
::= { snmpsmt 2 }

 snmpsmtUpstreamDescriptor OBJECT-TYPE
  SYNTAX OCTET STRING
  ACCESS read-only
  STATUS mandatory
	  		 DESCRIPTION ""
  ::= { snmpsmt 3 }

 snmpsmtUpstreamState OBJECT-TYPE
  SYNTAX OCTET STRING
  ACCESS read-only
  STATUS mandatory
	  		 DESCRIPTION ""
  ::= { snmpsmt 4 }

   fddismtTable OBJECT-TYPE
      SYNTAX   SEQUENCE OF FddismtEntry
      ACCESS   not-accessible
      STATUS   mandatory
    DESCRIPTION
        "A list of snmpsmt entries, one per FDDI board."
      ::= { snmpsmt 5 }

   fddismtEntry OBJECT-TYPE
      SYNTAX   FddismtEntry
      ACCESS   not-accessible
      STATUS   mandatory
    DESCRIPTION
        "A set of objects for an interface entry."
      INDEX { fddismtIndex }
      ::= { fddismtTable 1 }

   FddismtEntry ::= SEQUENCE {
         fddismtIndex
            INTEGER,
         fddismtUpstreamReq
            OCTET STRING,
         fddismtUpstreamRsp
            OCTET STRING,
         fddismtUpstreamDescriptor
            OCTET STRING,
         fddismtUpstreamState
            OCTET STRING
         }

   fddismtIndex OBJECT-TYPE
      SYNTAX   INTEGER
      ACCESS   read-only
      STATUS   mandatory
    DESCRIPTION
        "A unique value for each SMT. It represents the sequence number
    of the FDDI board in ES/1."
      ::= { fddismtEntry 1 }

   fddismtUpstreamReq   OBJECT-TYPE
      SYNTAX   OCTET STRING
      ACCESS   read-write
      STATUS   mandatory
    DESCRIPTION
        "When this variable is written, the ES/1 converts it into a
         big-endian FDDI address and issues an SMT NIF request to
         determine that address's upstream neighbor. When the NIF
         response is received, snmpsmtUpstreamRsp will hold the
         address of the upstream neighbor and a trap will be sent to
         the NMS."
      ::= { fddismtEntry 2 }

   fddismtUpstreamRsp   OBJECT-TYPE
      SYNTAX   OCTET STRING
      ACCESS   read-only
      STATUS   mandatory
    DESCRIPTION
        "The address of the upstream neighbor of the ES/1 whose
         address was written into snmpsmtUpstreamReq. If the address
         has not yet been learned, then an address of all zeroes is
         returned."
      ::= { fddismtEntry 3 }

   fddismtUpstreamDescriptor  OBJECT-TYPE
      SYNTAX   OCTET STRING
      ACCESS   read-only
      STATUS   mandatory
    DESCRIPTION
        "A four byte string containing the upstream neighbor's
         Station Descriptor parameter, as defined by the SMT frame
         protocols. If the upstream neighbor has not yet been
         learned, then a string of all zeroes is returned."
      ::= { fddismtEntry 4 }

   fddismtUpstreamState OBJECT-TYPE
      SYNTAX   OCTET STRING
      ACCESS   read-only
      STATUS   mandatory
    DESCRIPTION
        "A four byte string containing the upstream neighbor's
         Station State parameter, as defined by the SMT frame
         protocols. If the upstream neighbor has not yet been
         learned, then a string of all zeroes is returned."
      ::= { fddismtEntry 5 }


 -- SMC Interfaces Group

sifUX OBJECT-TYPE
 SYNTAX INTEGER
 ACCESS read-only
 STATUS mandatory
   DESCRIPTION
     "The maximum number of receive data buffers supported by the
      ES/1. The sum of sifSmlRxCnt and sifLrgRxCnt for all ports,
      plus ppeSmlRxCnt and ppeLrgRxCnt must be less than or equal to
      sifUX."
 ::= { sinterfaces 1 }

sifTable OBJECT-TYPE
 SYNTAX SEQUENCE OF SifEntry
 ACCESS not-accessible
 STATUS mandatory
   DESCRIPTION
     "A list of interface entries; one per port."
 ::= { sinterfaces 2 }

sifEntry OBJECT-TYPE
 SYNTAX SifEntry
 ACCESS not-accessible
 STATUS mandatory
   DESCRIPTION
     "A set of objects for an interface entry."
 INDEX { sifIndex }
::= { sifTable 1 }

SifEntry ::= SEQUENCE {
  sifIndex
   INTEGER,
  sifSmlRxCnt
   INTEGER,
  sifLrgRxCnt
   INTEGER,
  sifUxTxCnt
   INTEGER,
  sifThreshold
   INTEGER,
  sifThresholdTime
   INTEGER,
  sifRxQueueThresh
   INTEGER,
  sifRxQueueThreshTime
   INTEGER,
  sifTxStormCnt
   INTEGER,
  sifTxStormTime
   TimeTicks,
  sifFilterFlags
   INTEGER,
  sifCongestTime
   TimeTicks,
  sifQueueTime
   TimeTicks,
  sifPortCost
   INTEGER,
  sifStPriority
   INTEGER,
  sifFunctions
   INTEGER,
  sifCongested
   INTEGER,
  sifState
   INTEGER,
  sifDesigCost
   INTEGER,
  sifDesigRoot
   OCTET STRING,
  sifDesigBridge
   OCTET STRING,
  sifDesigPort
   OCTET STRING,
  sifRxPackets
   OCTET STRING,
  sifRxChar0s
   Counter,
  sifRxChar1s
   Counter,
  sifRxSizeErrors
   Counter,
  sifRxHwFCSs
   Counter,
  sifRxQueues
   Counter,
  sifTxPackets
   OCTET STRING,
  sifTxCongests
   Counter,
  sifTxStorms
   Counter,
  sifTxDests
   Counter,
  sifErrorsFlag
   INTEGER,
  sifTxStormFlag
   INTEGER,
  sifTxSizes
   Counter,
  sifTxAddr
   OCTET STRING,
  sifLan
   INTEGER,
  sifStatisticsTime
   TimeTicks,
  sifIpAddress
   IpAddress,
  sifIpGroupAddress
   IpAddress,
  sifMaxPacketSize
   INTEGER,
  sifExpectSqe
   INTEGER,
  sifFilterLocal
   INTEGER,
  sifInQLen
   Gauge,
  sifFrameSwitching
   INTEGER,
  sifRingDrops
   Counter,
  sifAdapterChecks
   Counter,
  sifIpRipPortMetric
   INTEGER,
  sifDescr
   OCTET STRING
  }

sifIndex OBJECT-TYPE
 SYNTAX INTEGER
 ACCESS read-only
 STATUS mandatory
   DESCRIPTION
     "The port number, beginning with 1 for the first port."
 ::= { sifEntry 1 }

sifSmlRxCnt OBJECT-TYPE
 SYNTAX INTEGER
 ACCESS read-only
 STATUS mandatory
   DESCRIPTION
     "The number of small data buffers for receiving packets."
 ::= { sifEntry 2 }

sifLrgRxCnt OBJECT-TYPE
 SYNTAX INTEGER
 ACCESS read-write
 STATUS mandatory
   DESCRIPTION
     "The number of large data buffers for receiving packets; must be
      zero for CSMA and UART ports."
 ::= { sifEntry 3 }

sifUxTxCnt OBJECT-TYPE
 SYNTAX INTEGER
 ACCESS read-write
 STATUS mandatory
   DESCRIPTION
     "The maximum size of the port's transmit queue, i.e., the number
      of packets that can be in the port's transmit queue, waiting to
      be transmitted."
 ::= { sifEntry 4 }

sifThreshold OBJECT-TYPE
 SYNTAX INTEGER
 ACCESS read-write
 STATUS mandatory
   DESCRIPTION
     "Maximum number of combined receive and transmit packet hardware
      errors before an alarm should be generated."
 ::= { sifEntry 5 }

sifThresholdTime OBJECT-TYPE
 SYNTAX INTEGER
 ACCESS read-write
 STATUS mandatory
   DESCRIPTION
     "The time period (in seconds) to which sifThreshold applies. A
      value of zero will disable the sifThreshold alarm."
 ::= { sifEntry 6 }

sifRxQueueThresh OBJECT-TYPE
 SYNTAX INTEGER
 ACCESS read-write
 STATUS mandatory
   DESCRIPTION
     "Maximum number of receive packet queue overflow errors before
      an alarm should be generated."
 ::= { sifEntry 7 }

sifRxQueueThreshTime OBJECT-TYPE
 SYNTAX INTEGER
 ACCESS read-write
 STATUS mandatory
   DESCRIPTION
     "The time period (in seconds) to which sifRxQueueThresh applies.
      A value of zero will disable the sifRxQueueThresh alarm."
 ::= { sifEntry 8 }

sifTxStormCnt OBJECT-TYPE
 SYNTAX INTEGER
 ACCESS read-write
 STATUS mandatory
   DESCRIPTION
     "The maximum number of multicasts to transmit with a certain
      period of time (not applicable for UART ports)."
 ::= { sifEntry 9 }

sifTxStormTime OBJECT-TYPE
 SYNTAX TimeTicks
 ACCESS read-write
 STATUS mandatory
   DESCRIPTION
     "The period of time, in centiseconds, which qualifies
      sifTxStormCnt (not applicable for UART ports)."
 ::= { sifEntry 10 }

sifFilterFlags OBJECT-TYPE
 SYNTAX INTEGER
 ACCESS read-write
 STATUS mandatory
   DESCRIPTION
     "Special filter flags; any combination of the following bits:
      0x0001   NO_SOURCE_SAME, 0x0002   NO_SOURCE_LEARNT, 0x0004
      NO_LEARNING, 0x0008   NO_DEST_LEARNT "
 ::= { sifEntry 11 }

sifCongestTime OBJECT-TYPE
 SYNTAX TimeTicks
 ACCESS read-write
 STATUS mandatory
   DESCRIPTION
     "When a port becomes congested, the PPE will discard any packets
      destined to the port for this many centiseconds following the
      congestion alarm. Possible values 0 through 5 minutes, except
      for port 1 (the out-of-band management port) which is always 0."
 ::= { sifEntry 12 }

sifQueueTime OBJECT-TYPE
 SYNTAX TimeTicks
 ACCESS read-write
 STATUS mandatory
   DESCRIPTION
     "The time, in centiseconds, after which an element in a transmit
      queue will be flushed."
 ::= { sifEntry 13 }

sifPortCost OBJECT-TYPE
 SYNTAX INTEGER
 ACCESS read-write
 STATUS mandatory
	  		 DESCRIPTION ""
 ::= { sifEntry 14 }

sifStPriority OBJECT-TYPE
 SYNTAX INTEGER
 ACCESS read-write
 STATUS mandatory
 	  		 DESCRIPTION ""
::= { sifEntry 15 }

sifFunctions OBJECT-TYPE
 SYNTAX INTEGER
 ACCESS read-only
 STATUS mandatory
   DESCRIPTION
     "The current functional state (protocols which have been
      activated and are operational) of the port. The following
      values or combinations are supported:
      0x0001   NMS,       0x0002   TBRIDGE, 0x0004   SBRIDGE,
      0x0006   SRTBRIDGE, 0x0008   MESH,    0x0010   IPROUTE,
      0x0020   NO_BPDU,   0x0040   RIP,     0x0080   SRSPAN,
      0x0100   PROXY,     0x0200   OSPF.

      These values can be configured through the sprotoTable.
  Combining TBRIDGE and SBRIDGE always produces SRTBRIDGE."
 ::= { sifEntry 16 }

sifCongested OBJECT-TYPE
 SYNTAX INTEGER { true(1), false(2) }
 ACCESS read-only
 STATUS mandatory
   DESCRIPTION
     "Whether the port is out-bound congested."
 ::= { sifEntry 17 }

sifState OBJECT-TYPE
 SYNTAX INTEGER {
    spanning-tree-disabled(1),
    spanning-tree-listening(2),
    spanning-tree-learning(3),
    spanning-tree-forwarding(4),
    spanning-tree-blocking(5)
   }
 ACCESS read-only
 STATUS mandatory
 	  		 DESCRIPTION ""
::= { sifEntry 18 }

sifDesigCost OBJECT-TYPE
 SYNTAX INTEGER
 ACCESS read-only
 STATUS mandatory
 	  		 DESCRIPTION ""
::= { sifEntry 19 }

sifDesigRoot OBJECT-TYPE
 SYNTAX OCTET STRING
 ACCESS read-only
 STATUS mandatory
 	  		 DESCRIPTION ""
::= { sifEntry 20 }

sifDesigBridge OBJECT-TYPE
 SYNTAX OCTET STRING
 ACCESS read-only
 STATUS mandatory
 	  		 DESCRIPTION ""
::= { sifEntry 21 }

sifDesigPort OBJECT-TYPE
 SYNTAX OCTET STRING
 ACCESS read-only
 STATUS mandatory
 	  		 DESCRIPTION ""
::= { sifEntry 22 }

sifRxPackets OBJECT-TYPE
 SYNTAX OCTET STRING
 ACCESS read-only
 STATUS mandatory
   DESCRIPTION
     "A 100 byte array, containing the number of received packets
      broken down into 25 categories. The number of packets in each
      category is encoded as a series of 4 bytes, which should be
      converted into a 32 bit counter. The 25 categories are
      determined by combining each possible DEST_xxx value with each
      possible OUTCOME_xxx value, as listed below: DEST_UBRIDGE = 0,
      DEST_MBRIDGE = 1, DEST_KNOWN = 2,  DEST_UNKNOWN = 3,
      DEST_MULTI = 4, OUTCOME_FWD = 0, OUTCOME_LOCAL = 5,
      OUTCOME_BLOCK = 10, OUTCOME_SOURCE = 15,  OUTCOME_DEST = 20"
 ::= { sifEntry 23 }

sifRxChar0s OBJECT-TYPE
 SYNTAX Counter
 ACCESS read-only
 STATUS mandatory
   DESCRIPTION
     "Number of characters in the forwarded received packets."
 ::= { sifEntry 24 }

sifRxChar1s OBJECT-TYPE
 SYNTAX Counter
 ACCESS read-only
 STATUS mandatory
   DESCRIPTION
     "Number of characters in the filtered received packets."
 ::= { sifEntry 25 }

sifRxSizeErrors OBJECT-TYPE
 SYNTAX Counter
 ACCESS read-only
 STATUS mandatory
   DESCRIPTION
     "Number of received packets discarded due to size errors."
 ::= { sifEntry 26 }

sifRxHwFCSs OBJECT-TYPE
 SYNTAX Counter
 ACCESS read-only
 STATUS mandatory
   DESCRIPTION
     "Number of received packets discarded due to FCS errors."
 ::= { sifEntry 27 }

sifRxQueues OBJECT-TYPE
 SYNTAX Counter
 ACCESS read-only
 STATUS mandatory
   DESCRIPTION
     "Number of received packets lost because of insufficient receive
      buffers.(For certain interfaces with multi-packet FIFO hardware,
      this count might be approximate.)"
 ::= { sifEntry 28 }

   -- { sifEntry 29 } is not used

sifTxPackets OBJECT-TYPE
 SYNTAX OCTET STRING
 ACCESS read-only
 STATUS mandatory
   DESCRIPTION
     "A 20 byte array, containing the number of transmitted packets
      broken down into 5 categories. The number of packets in each
      category is encoded as a series of 4 bytes, which should be
      converted into a 32 bit counter."
 ::= { sifEntry 30 }

sifTxCongests OBJECT-TYPE
 SYNTAX Counter
 ACCESS read-only
 STATUS obsolete     -- see ifOutDiscards
 	  		 DESCRIPTION ""
::= { sifEntry 31 }

sifTxStorms OBJECT-TYPE
 SYNTAX Counter
 ACCESS read-only
 STATUS mandatory
   DESCRIPTION
     "Number of packets not sent due to protection against a
      multicast storm."
 ::= { sifEntry 32 }

sifTxDests OBJECT-TYPE
 SYNTAX Counter
 ACCESS read-only
 STATUS mandatory
   DESCRIPTION
     "Number of packets not sent due to a destination port filtering
      restriction."
 ::= { sifEntry 33 }

sifErrorsFlag OBJECT-TYPE
 SYNTAX INTEGER { true(1), false(2) }
 ACCESS read-only
 STATUS mandatory
   DESCRIPTION
     "Whether the port has exceeded the limits specified by
      sifThreshold and sifThresholdTime."
 ::= { sifEntry 34 }

sifTxStormFlag OBJECT-TYPE
 SYNTAX INTEGER { true(1), false(2) }
 ACCESS read-only
 STATUS mandatory
   DESCRIPTION
     "Whether PPE has invoked multicast storm protection."
 ::= { sifEntry 35 }

sifTxSizes OBJECT-TYPE
 SYNTAX Counter
 ACCESS read-only
 STATUS mandatory
   DESCRIPTION
     "Number of packets not sent due to size limitations."
 ::= { sifEntry 36 }

sifTxAddr OBJECT-TYPE
 SYNTAX OCTET STRING
 ACCESS read-only
 STATUS mandatory
   DESCRIPTION
     "A series of 16 MAC addresses (96 octets in total), of the
      source addresses of the last 16 packets that were not sent due
      to packet size limitations. If fewer than 16 packets were not
      sent, then the unspecified MAC addresses will be all zeroes."
 ::= { sifEntry 37 }

sifLan OBJECT-TYPE
 SYNTAX INTEGER
 ACCESS read-write
 STATUS mandatory
   DESCRIPTION
     "Up to four group identifiers assigned to the port. The sifLan
      identifier is only used by combination filter testing, i.e.,
      for comparisons against filterSrcLan. Possible values are 0
      through 255, for each of the parameter's four bytes."
 ::= { sifEntry 38 }

sifStatisticsTime OBJECT-TYPE
 SYNTAX TimeTicks
 ACCESS read-only
 STATUS mandatory
   DESCRIPTION
     "Length of time during which statistics were collected. In
      particular, the following statistics may be examined to
      determine the exact utilization rate of a port:
      ifInOctets,  ifInUcastPkts,  ifInNUcastPkts
      ifOutOctets, ifOutUcastPkts, ifOutNUcastPkts
      sifRxChar0s, sifRxChar1s."
 ::= { sifEntry 39 }

sifIpAddress OBJECT-TYPE
 SYNTAX IpAddress
 ACCESS read-write
 STATUS mandatory
   DESCRIPTION
     "The IP address assigned to the port. If this is zero, then the
      port must learn its IP address via Reverse ARP or PPP's IPCP."
 ::= { sifEntry 40 }

sifIpGroupAddress OBJECT-TYPE
 SYNTAX IpAddress
 ACCESS read-write
 STATUS mandatory
   DESCRIPTION
     "Zero, or an IP Group address assigned to the port."
 ::= { sifEntry 41 }

sifMaxPacketSize OBJECT-TYPE
 SYNTAX INTEGER
 ACCESS read-write
 STATUS mandatory
   DESCRIPTION
     "The maximum packet size, in bytes (octets), which may be
      transmitted through this port. This parameter may not be
      changed, except for PPP ports, in which case, changing
      sifMaxPacketSize automatically causes ifMtu and pppLinkLocalMRU
      to change."
 ::= { sifEntry 42 }

sifExpectSqe OBJECT-TYPE
 SYNTAX INTEGER { true(1), false(2) }
 ACCESS read-write
 STATUS mandatory
   DESCRIPTION
     "Whether the port should expect SQE, also known as heartbeat
   (not applicable for ports other than CSMA/CD ports)."
 ::= { sifEntry 43 }

sifFilterLocal OBJECT-TYPE
 SYNTAX INTEGER { true(1), false(2) }
 ACCESS read-write
 STATUS mandatory
   DESCRIPTION
     "Whether the port should attempt to filter local traffic,
      bypassing all statistics accumulation, rather than passing the
      local traffic to the Packet Processing Engine. Filtering local
      traffic is not available for UART and WAN ports."
 ::= { sifEntry 44 }

sifInQLen OBJECT-TYPE
 SYNTAX Gauge
 ACCESS read-write
 STATUS mandatory
   DESCRIPTION
     "The maximum length ever obtained by the port's inbound packet
      queue (in packets). The size of a port's inbound packet queue
      is periodically polled (rather than recalculated whenever a
      packet is added), so sifInQLen is an approximation of the
      maximum length."
 ::= { sifEntry 45 }

sifFrameSwitching OBJECT-TYPE
    SYNTAX  INTEGER { enabled(1), disabled(2) }
 ACCESS read-write
 STATUS mandatory
    DESCRIPTION
       "Valid only for Token Ring ports. Options include:
        enabled (1), disabled (2).Defaults to disabled(2). If
        enabled, frames may be bridged between token ring ports on
        the same board at higher throughput and lower latency than is
        otherwise possible. Address statistics will not
        reflect any frames forwarded in this manner.
        This applies only to transparent bridging, and
        must be enabled on both the entry and the exit
        port."
 ::= { sifEntry 46 }

sifRingDrops OBJECT-TYPE
 SYNTAX Counter
 ACCESS read-only
 STATUS mandatory
 DESCRIPTION
  "Only valid for 802.5 token ring. Number of times
  the ring left the open state."
 ::= { sifEntry 47 }

sifAdapterChecks OBJECT-TYPE
 SYNTAX Counter
 ACCESS read-only
 STATUS mandatory
 DESCRIPTION
  "Only valid for 802.5 token ring. Number of times
       the MAC chip experienced an internal hardware failure
       and had to be reset."
 ::= { sifEntry 48 }

sifIpRipPortMetric OBJECT-TYPE
 SYNTAX INTEGER
 ACCESS read-write
 STATUS mandatory
 DESCRIPTION
  "Port metric for backup RIP interface."
 ::= { sifEntry 49 }

sifDescr OBJECT-TYPE
 SYNTAX OCTET STRING
 ACCESS read-write
 STATUS mandatory
 DESCRIPTION
  "A textual string containing information about the
  interface.  This string should include the name of
  the manufacturer, the product name and the version
  of the hardware interface."
 ::= { sifEntry 50 }

sifUtilInterval OBJECT-TYPE
 SYNTAX INTEGER
 ACCESS read-only
 STATUS mandatory
   DESCRIPTION
     "The number of seconds in each utilization sample."
 ::= { sinterfaces 3 }

sifUtilCount OBJECT-TYPE
 SYNTAX INTEGER
 ACCESS read-only
 STATUS mandatory
   DESCRIPTION
     "The number of same-kind peak samples per physical port accumulated in
      sifUtilPortPeakTable or sifUtilSysPeakTable."
 ::= { sinterfaces 4 }

sifUtilPortPeakReset OBJECT-TYPE
 SYNTAX INTEGER { true(1) }
 ACCESS read-write
 STATUS mandatory
   DESCRIPTION
     "This object is set to true (1) to erase earlier per-physical-port
      utilization samples on all specified port(s)."
 ::= { sinterfaces 5 }

sifUtilPortPeakTable OBJECT-TYPE
 SYNTAX SEQUENCE OF SifUtilPortPeakEntry
 ACCESS not-accessible
 STATUS mandatory
   DESCRIPTION
     "A list of interface utilization entries; one per sifUtilCount per
      physical port, plus one per physical port for the most recently
      completed samples."
 ::= { sinterfaces 6 }

sifUtilPortPeakEntry OBJECT-TYPE
 SYNTAX SifUtilPortPeakEntry
 ACCESS not-accessible
 STATUS mandatory
   DESCRIPTION
     "A set of utilization statistics recorded for an interface entry at
      per-port throughput peaks."
 INDEX { sifUtilPortPeakIndex, sifUtilPortPeakOrdinal }
 ::= { sifUtilPortPeakTable 1 }

SifUtilPortPeakEntry ::= SEQUENCE {
  sifUtilPortPeakIndex
   INTEGER,
  sifUtilPortPeakOrdinal
   INTEGER,
  sifUtilPortPeakBRTimestamp
   TimeTicks,
  sifUtilPortPeakTBitRate
   INTEGER,
  sifUtilPortPeakRBitRate
   INTEGER
  }

sifUtilPortPeakIndex OBJECT-TYPE
 SYNTAX INTEGER
 ACCESS read-only
 STATUS mandatory
   DESCRIPTION
     "The port number."
 ::= { sifUtilPortPeakEntry 1 }

sifUtilPortPeakOrdinal OBJECT-TYPE
 SYNTAX INTEGER
 ACCESS read-only
 STATUS mandatory
   DESCRIPTION
     "The ordinal of the entry, with 1 representing 'Now' (i.e. the sample
      most recently accumulated), with 2 representing the sample taken at the
      highest per-port throughput peak, 3 at the next highest, and so on."
 ::= { sifUtilPortPeakEntry 2 }

sifUtilPortPeakBRTimestamp OBJECT-TYPE
 SYNTAX TimeTicks
 ACCESS read-only
 STATUS mandatory
   DESCRIPTION
     "The value of sysUpTime associated with the end of the sample period for
      the associated sifUtilPortPeakTBitRate/sifUtilPortPeakRBitRate sample,
      or the most recent timestamp for the sample currently being accumulated.
      This will be 0 for any ports for which utilization statistics are not
      kept, or where statistics have been reset too recently to have
      accumulated an appropriate sample."
 ::= { sifUtilPortPeakEntry 3 }

sifUtilPortPeakTBitRate OBJECT-TYPE
 SYNTAX INTEGER (0..99)
 ACCESS read-only
 STATUS mandatory
   DESCRIPTION
     "The ratio of the number of bits transmitted per second during the
      per-physical-port sample interval to the linespeed in bits per second,
      expressed in integer units of 1/100, maximum 99.  This will be 0 for any
      ports for which utilization statistics are not kept, or where statistics
      have been reset too recently to have accumulated an appropriate sample."
 ::= { sifUtilPortPeakEntry 4 }

sifUtilPortPeakRBitRate OBJECT-TYPE
 SYNTAX INTEGER (0..99)
 ACCESS read-only
 STATUS mandatory
   DESCRIPTION
     "The ratio of the number of bits received per second during the
      per-physical-port sample interval to the linespeed in bits per second,
      expressed in integer units of 1/100, maximum 99, and excluding some or
      all locally-filtered traffic per sifFilterLocal.  This will be 0 for
      any ports for which utilization statistics are not kept, or where
      statistics have been reset too recently to have accumulated an
      appropriate sample."
 ::= { sifUtilPortPeakEntry 5 }

sifUtilSysPeakReset OBJECT-TYPE
 SYNTAX INTEGER { true(1) }
 ACCESS read-write
 STATUS mandatory
   DESCRIPTION
     "This object is set to true (1) to erase earlier per-system utilization
      samples."
 ::= { sinterfaces 7 }

sifUtilSysPeakTable OBJECT-TYPE
-- SYNTAX SEQUENCE OF SifUtilEntry - FIXED 01/14/97 cmf -
 SYNTAX SEQUENCE OF SifUtilSysPeakEntry
 ACCESS not-accessible
 STATUS mandatory
   DESCRIPTION
     "A list of interface utilization entries; one per sifUtilCount per
      physical port, plus one per physical port for the most recently
      completed samples."
 ::= { sinterfaces 8 }

sifUtilSysPeakEntry OBJECT-TYPE
 SYNTAX SifUtilSysPeakEntry
 ACCESS not-accessible
 STATUS mandatory
   DESCRIPTION
     "A set of utilization statistics recorded for an interface entry at
      overall system throughput peaks."
 INDEX { sifUtilSysPeakIndex, sifUtilSysPeakOrdinal }
 ::= { sifUtilSysPeakTable 1 }

SifUtilSysPeakEntry ::= SEQUENCE {
  sifUtilSysPeakIndex
   INTEGER,
  sifUtilSysPeakOrdinal
   INTEGER,
--  sifUtilSysTimestamp - FIXED 01/14/97 cmf -
   sifUtilSysPeakTimestamp
   TimeTicks,
--  sifUtilSysTBitRate - FIXED 01/14/97 cmf -
   sifUtilSysPeakTBitRate
   INTEGER,
--  sifUtilSysRBitRate - FIXED 01/14/97 cmf -
  sifUtilSysPeakRBitRate
   INTEGER
  }

sifUtilSysPeakIndex OBJECT-TYPE
 SYNTAX INTEGER
 ACCESS read-only
 STATUS mandatory
   DESCRIPTION
     "The port number."
 ::= { sifUtilSysPeakEntry 1 }

sifUtilSysPeakOrdinal OBJECT-TYPE
 SYNTAX INTEGER
 ACCESS read-only
 STATUS mandatory
   DESCRIPTION
     "The ordinal of the entry, with 1 representing 'Now' (i.e. the sample
      most recently accumulated), with 2 representing the sample taken at the
      highest peak system throughput, 3 at the next highest, and so on."
 ::= { sifUtilSysPeakEntry 2 }

sifUtilSysPeakTimestamp OBJECT-TYPE
 SYNTAX TimeTicks
 ACCESS read-only
 STATUS mandatory
   DESCRIPTION
     "The value of sysUpTime associated with the end of the sample period for
      the associated sifUtilSysPeakTBitRate/sifUtilSysPeakRBitRate sample, or
      the most recent timestamp for the sample currently being accumulated.
      This will be 0 for any ports for which utilization statistics are not
      kept, or where statistics have been reset too recently to have
      accumulated an appropriate sample."
 ::= { sifUtilSysPeakEntry 3 }

sifUtilSysPeakTBitRate OBJECT-TYPE
 SYNTAX INTEGER (0..99)
 ACCESS read-only
 STATUS mandatory
   DESCRIPTION
     "The ratio of the number of bits transmitted per second during the
      per-system-peak sample interval to the linespeed in bits per second,
      expressed in integer units of 1/100, maximum 99.  This will be 0 for any
      ports for which utilization statistics are not kept, or where statistics
      have been reset too recently to have accumulated an appropriate sample."
 ::= { sifUtilSysPeakEntry 4 }

sifUtilSysPeakRBitRate OBJECT-TYPE
 SYNTAX INTEGER (0..99)
 ACCESS read-only
 STATUS mandatory
   DESCRIPTION
     "The ratio of the number of bits received per second during the
      per-system-peak sample interval to the linespeed in bits per second,
      expressed in integer units of 1/100, maximum 99, and excluding some or
      all locally-filtered traffic per sifFilterLocal.  This will be 0 for any
      ports for which utilization statistics are not kept, or where statistics
      have been reset too recently to have accumulated an appropriate sample."
 ::= { sifUtilSysPeakEntry 5 }

 -- SMC FDDI Interfaces Group

 sfddiTable OBJECT-TYPE
  SYNTAX SEQUENCE OF SfddiEntry
  ACCESS not-accessible
  STATUS mandatory
      DESCRIPTION
        "A list of interface entries; one per FDDI port."
  ::= { sfddi 1 }

 sfddiEntry OBJECT-TYPE
  SYNTAX SfddiEntry
  ACCESS not-accessible
  STATUS mandatory
      DESCRIPTION
        "A set of objects for an interface entry."
  INDEX { sfddiIndex }
  ::= { sfddiTable 1 }

 SfddiEntry ::= SEQUENCE {
    sfddiIndex
     INTEGER,
    sfddiRxHwAborts
     Counter,
    sfddiRxParitys
     Counter,
    sfddiRxShorts
     Counter,
    sfddiDpcErrCnts
     Counter,
    sfddiDpcErrValue
     INTEGER,
    sfddiRbcErrCnts
     Counter,
    sfddiRbcErrValue
     INTEGER,
    sfddiTxAsync
     INTEGER,
    sfddiShortAddressing
     INTEGER,
    sfddiSmtConditions
     INTEGER,
    sfddiSrfConditions
     INTEGER,
    sfddiSmtConditionsStatus
     INTEGER,
    sfddiSrfConditionsStatus
     INTEGER,
    sfddiSrfReportLimit
     INTEGER,
    sfddiFrameErrorThreshold
     INTEGER,
    sfddiNotCopiedThreshold
     INTEGER,
    sfddiSBFlag
     INTEGER,
    sfddiRxEbits
     Counter,
    sfddiOBSFuseBad
     INTEGER,
    sfddiThruB
     INTEGER,
    sfddiStationDescriptor
     OCTET STRING,
    sfddiStationState
     OCTET STRING,
    sfddiDownstreamNbr
     OCTET STRING,
    sfddiSMTBufferSize
     INTEGER
    }
 sfddiIndex OBJECT-TYPE
  SYNTAX INTEGER
  ACCESS read-only
  STATUS mandatory
      DESCRIPTION
        "The ES/1's port number of the port."
  ::= { sfddiEntry 1 }

 sfddiRxHwAborts OBJECT-TYPE
  SYNTAX Counter
  ACCESS read-write
  STATUS mandatory
      DESCRIPTION
        "The number of packets that were discarded due to receive
         abort errors."
  ::= { sfddiEntry 2 }

 sfddiRxParitys OBJECT-TYPE
  SYNTAX Counter
  ACCESS read-write
  STATUS mandatory
      DESCRIPTION
        "The number of packets that were discarded due to parity
         errors."
  ::= { sfddiEntry 3 }

 sfddiRxShorts OBJECT-TYPE
  SYNTAX Counter
  ACCESS read-write
  STATUS mandatory
      DESCRIPTION
        "The number of packets that were discarded because they were
         too short."
  ::= { sfddiEntry 4 }

 sfddiDpcErrCnts OBJECT-TYPE
  SYNTAX Counter
  ACCESS read-write
  STATUS mandatory
      DESCRIPTION
        "The number of DPC errors."
  ::= { sfddiEntry 5 }

 sfddiDpcErrValue OBJECT-TYPE
  SYNTAX INTEGER
  ACCESS read-write
  STATUS mandatory
      DESCRIPTION
        "Detailed status of the last DPC error."
  ::= { sfddiEntry 6 }

 sfddiRbcErrCnts OBJECT-TYPE
  SYNTAX Counter
  ACCESS read-write
  STATUS mandatory
      DESCRIPTION
        "The number of RBC errors."
  ::= { sfddiEntry 7 }

 sfddiRbcErrValue OBJECT-TYPE
  SYNTAX INTEGER
  ACCESS read-write
  STATUS mandatory
      DESCRIPTION
        "Detailed status of the last RBC error. (FIOM MIB only)"
  ::= { sfddiEntry 8 }

 sfddiTxAsync OBJECT-TYPE
  SYNTAX INTEGER
  ACCESS read-write
  STATUS mandatory
      DESCRIPTION
        "Number of bytes to reserve in the DPC Buffer Memory for
         transmitting asynchronous packets."
  ::= { sfddiEntry 9 }

 sfddiShortAddressing OBJECT-TYPE
  SYNTAX INTEGER { true(1), false(2) }
  ACCESS read-only
  STATUS mandatory
      DESCRIPTION
        "Whether any packets were received with 16 bit MAC
         addresses."
  ::= { sfddiEntry 10 }

 sfddiSmtConditions OBJECT-TYPE
  SYNTAX INTEGER
  ACCESS read-write
  STATUS mandatory
      DESCRIPTION
        "SMT conditions which should be reported to the NMS via SNMP
         Traps. Possible values are any combination of the following
         bits:
         ring = 0x00000001, claim = 0x00000002, beacon = 0x00000004,
         tvx = 0x00000008, trt = 0x00000010, phy-invalid = 0x00000020,
         reset = 0x00000040, overflow = 0x00000080, dup = 0x00000100,
         lost = 0x00000200, restricted = 0x00000400,
         congestion = 0x00000800, token = 0x00001000, t4 = 0x00002000."
  ::= { sfddiEntry 11 }

 sfddiSrfConditions OBJECT-TYPE
  SYNTAX INTEGER
  ACCESS read-write
  STATUS mandatory
      DESCRIPTION
        "SRF conditions which should be reported to the NMS via SNMP
         Traps. Possible values are any combination of the following
         bits:
         srf-frame-error = 0x00000001,  srf-port-ler = 0x00000002,
         srf-not-copied = 0x00000004,srf-dup-addr = 0x00000008,
         srf-eb-error = 0x00000010,srf-config = 0x00000020,
         srf-connect = 0x00000040, srf-trace = 0x00000080,
         srf-neighbor = 0x00000100,srf-peer-wrap = 0x00000400,
         srf-path-change = 0x00000800 "
  ::= { sfddiEntry 12 }

 sfddiSmtConditionsStatus OBJECT-TYPE
  SYNTAX INTEGER
  ACCESS read-write
  STATUS mandatory
      DESCRIPTION
        "Requested SMT conditions which are currently present.
         Writing to sfddiSmtConditionsStatus is used to acknowledge
         the SNMP traps."
  ::= { sfddiEntry 13 }

 sfddiSrfConditionsStatus OBJECT-TYPE
  SYNTAX INTEGER
  ACCESS read-write
  STATUS mandatory
      DESCRIPTION
        "Requested SRF conditions which are currently present.
         Writing to sfddiSrfConditionsStatus is used to acknowledge
         the SNMP traps."
  ::= { sfddiEntry 14 }

 sfddiSrfReportLimit OBJECT-TYPE
  SYNTAX INTEGER
  ACCESS read-write
  STATUS mandatory
	  		 DESCRIPTION ""
  ::= { sfddiEntry 15 }

 sfddiFrameErrorThreshold OBJECT-TYPE
  SYNTAX INTEGER
  ACCESS read-write
  STATUS mandatory
  	  		 DESCRIPTION ""
::= { sfddiEntry 16 }

 sfddiNotCopiedThreshold OBJECT-TYPE
  SYNTAX INTEGER
  ACCESS read-write
  STATUS mandatory
      DESCRIPTION
        "Value for the fddiMACNotCopiedThreshold variable."
  ::= { sfddiEntry 17 }

 sfddiSBFlag OBJECT-TYPE
  SYNTAX INTEGER { true(1), false(2) }
  ACCESS read-only
  STATUS mandatory
      DESCRIPTION
        "Whether the ECM's optical bypass is stuck, i.e., the current
         value of the SMT SB_Flag variable."
  ::= { sfddiEntry 18 }

 sfddiRxEbits OBJECT-TYPE
  SYNTAX Counter
  ACCESS read-only
  STATUS mandatory
      DESCRIPTION
        "The number of packets that were discarded because another
    station had already set the E bit."
  ::= { sfddiEntry 19 }

 sfddiOBSFuseBad OBJECT-TYPE
  SYNTAX INTEGER { true(1), false(2) }
  ACCESS read-only
  STATUS mandatory
      DESCRIPTION
        "Whether the fuse to the FDDI port's optical bypass is bad."
  ::= { sfddiEntry 20 }

 sfddiThruB OBJECT-TYPE
  SYNTAX INTEGER { true(1), false(2) }
  ACCESS read-write
  STATUS mandatory
      DESCRIPTION
        "Whether to connect to the FDDI port B (not applicable for
         SAS)."
  ::= { sfddiEntry 21 }

 sfddiStationDescriptor OBJECT-TYPE
  SYNTAX OCTET STRING
  ACCESS read-only
  STATUS mandatory
      DESCRIPTION
        "A four byte string containing the FDDI port's Station
        Descriptor parameter, as defined by the SMT frame protocols."
  ::= { sfddiEntry 22 }

 sfddiStationState OBJECT-TYPE
  SYNTAX OCTET STRING
  ACCESS read-only
  STATUS mandatory
      DESCRIPTION
        "A four byte string containing the FDDI port's Station State
         parameter, as defined by the SMT frame protocols."
  ::= { sfddiEntry 23 }

 sfddiDownstreamNbr OBJECT-TYPE
  SYNTAX OCTET STRING
  ACCESS read-only
  STATUS mandatory
      DESCRIPTION
        "The MAC address of the FDDI port's downstream neighbor."
  ::= { sfddiEntry 24 }

 sfddiSMTBufferSize OBJECT-TYPE
  SYNTAX INTEGER
  ACCESS read-write
  STATUS mandatory
      DESCRIPTION
        "The amount of packet buffer space to reserve for processing
         SMT frames. Possible values 9000 - 18000. (FIOM MIB only)"
  ::= { sfddiEntry 25 }

 -- SMC UART Interface Group

 suartTable OBJECT-TYPE
  SYNTAX SEQUENCE OF SuartEntry
  ACCESS not-accessible
  STATUS mandatory
      DESCRIPTION
        "A list of interface entries; one per UART port."
  ::= { suart 1 }

 suartEntry OBJECT-TYPE
  SYNTAX SuartEntry
  ACCESS not-accessible
  STATUS mandatory
      DESCRIPTION
        "A set of objects for an interface entry. "
  INDEX { suartIndex }
      ::= { suartTable 1 }

 SuartEntry ::= SEQUENCE {
    suartIndex
     INTEGER,
    suartBaud
     INTEGER,
    suartModem
     INTEGER,
    suartIpNeighborAddress
     IpAddress,
    suartPPPActive
     INTEGER,
    suartAlignmentErrors
     Counter,
    suartOverrunErrors
     Counter
    }

 suartIndex OBJECT-TYPE
  SYNTAX INTEGER
  ACCESS read-only
  STATUS mandatory
      DESCRIPTION
        "The ES/1's port number of the port."
  ::= { suartEntry 1 }

 suartBaud OBJECT-TYPE
  SYNTAX INTEGER {
     external-clock(1),
     b1200-baud(2),
     b2400-baud(3),
     b4800-baud(4),
     b9600-baud(5),
     b19200-baud(6),
     b38400-baud(7),
     b56-kilobits(8),
     b1544-kilobits(9),
     b2048-kilobits(10),
     b45-megabits(11)
    }
  ACCESS read-write
  STATUS mandatory
      DESCRIPTION
        "This is the desired baud rate. Only 1200 baud through 19,200
         baud are supported by the ES/1."
  ::= { suartEntry 2 }

 suartModem OBJECT-TYPE
  SYNTAX INTEGER
  ACCESS read-write
  STATUS mandatory
      DESCRIPTION
        "The expected modem signals; definitions of the different
         values are TBD."
  ::= { suartEntry 3 }

 suartIpNeighborAddress OBJECT-TYPE
  SYNTAX IpAddress
  ACCESS read-write
  STATUS mandatory
	  		 DESCRIPTION ""
  ::= { suartEntry 4 }

 suartPPPActive OBJECT-TYPE
  SYNTAX INTEGER { true(1), false(2) }
  ACCESS read-write
  STATUS mandatory
  	  		 DESCRIPTION ""
::= { suartEntry 5 }

 suartAlignmentErrors OBJECT-TYPE
  SYNTAX Counter
  ACCESS read-only
  STATUS mandatory
      DESCRIPTION
        "Number of received packets with frame alignment errors,
         since the port was last enabled."
  ::= { suartEntry 6 }

 suartOverrunErrors OBJECT-TYPE
  SYNTAX Counter
  ACCESS read-only
  STATUS mandatory
      DESCRIPTION
        "Number of received packets with data overrun errors, since
         the port was last enabled."
  ::= { suartEntry 7 }

 -- Filter Group

 filterMaxCount OBJECT-TYPE
  SYNTAX INTEGER
  ACCESS read-only
  STATUS mandatory
      DESCRIPTION
        "The maximum number of combination filters that may be
         defined for the ES/1. This is always 100."
  ::= { filter 1 }

 filterCurrentCount OBJECT-TYPE
  SYNTAX INTEGER
  ACCESS read-only
  STATUS mandatory
      DESCRIPTION
        "The number of combination filters currently defined for the
         ES/1."
  ::= { filter 2 }

 filterDeleteID OBJECT-TYPE
  SYNTAX INTEGER
  ACCESS read-write
  STATUS mandatory
      DESCRIPTION
        "A filter identifier used for deleting filters. After the NMS
         sets this field, the ES/1 deletes the filterEntry that has a
         matching filter ID field, and resets this field to zero. The
         ES/1 then updates filterCurrentCount, filterNextID, and the
         entire filterTable."
  ::= { filter 3 }

 filterNextID OBJECT-TYPE
  SYNTAX INTEGER
  ACCESS read-only
  STATUS mandatory
      DESCRIPTION
        "A filter identifier used for adding filters."
  ::= { filter 4 }

 filterAddID OBJECT-TYPE
  SYNTAX INTEGER
  ACCESS read-write
  STATUS mandatory
      DESCRIPTION
        "A filter identifier used for adding filters. After the NMS
         sets this field, the ES/1 adds the filterEntry indexed by
         filterAddIndex. The ES/1 then updates filterCurrentCount,
         filterNextID, and the entire filterTable. Note that if
         filterAddID does not match filterNextID, then the ES/1 will
         not add the entry, since the SetRequest for filterAddID must
         have been a duplicate packet."
  ::= { filter 5 }

 filterAddIndex OBJECT-TYPE
  SYNTAX INTEGER
  ACCESS read-write
  STATUS mandatory
      DESCRIPTION
        "The index within filterTable, after which a filter should be
        added. If filterAddIndex contains zero, then the filter
        should be added as the first filterEntry within filterTable."
  ::= { filter 6 }

 filterTable OBJECT-TYPE
  SYNTAX SEQUENCE OF FilterEntry
  ACCESS not-accessible
  STATUS mandatory
      DESCRIPTION
        "A list of combination filters; one per defined filter. If
         fewer than filterMaxCount filters have been defined, then an
         additional filterEntry exists, which is used as part of the
         sequence for defining a new filter."
  ::= { filter 7 }

 filterEntry OBJECT-TYPE
  SYNTAX FilterEntry
  ACCESS not-accessible
  STATUS mandatory
      DESCRIPTION
        "A set of objects for a combination filter."
  INDEX { filterIndex }
  ::= { filterTable 1 }

 FilterEntry ::= SEQUENCE {
   filterIndex
    INTEGER,
   filterID
    INTEGER,
   filterPortNo
    INTEGER,
   filterComboType
    INTEGER,
   filterFlags
    INTEGER,
   filterFrame
    INTEGER,
   filterSource
    OCTET STRING,
   filterSourceEnd
    OCTET STRING,
   filterDest
    OCTET STRING,
   filterDestEnd
    OCTET STRING,
   filterSourceMask
    OCTET STRING,
   filterDestMask
    OCTET STRING,
   filterSrcLan
    INTEGER,
   filterOffset
    INTEGER,
   filterField
    OCTET STRING,
   filterMask
    OCTET STRING,
   filterThreshold
    INTEGER,
   filterThreshTime
    INTEGER,
   filterThreshFlag
    INTEGER,
   filterPktCnts
    Counter,
   filterLastSrc
    OCTET STRING
   }

 filterIndex OBJECT-TYPE
  SYNTAX INTEGER
  ACCESS read-only
  STATUS mandatory
      DESCRIPTION
        "This number always matches the instance of the filterEntry."
  ::= { filterEntry 1 }

 filterID OBJECT-TYPE
  SYNTAX INTEGER
  ACCESS read-only
  STATUS mandatory
      DESCRIPTION
        "Identifier assigned to the filter, used for obtaining the
         value for filterDeleteID so that the filter can be deleted."
  ::= { filterEntry 2 }

 filterPortNo OBJECT-TYPE
  SYNTAX INTEGER
  ACCESS read-write
  STATUS mandatory
      DESCRIPTION
        "The port number related to this filter."
  ::= { filterEntry 3 }

 filterComboType OBJECT-TYPE
  SYNTAX INTEGER
  ACCESS read-write
  STATUS mandatory
      DESCRIPTION
        "Whether this is an entry filter (0), an  exit filter(1),
         a port mirror entry filter (3), or a port mirror exit
         filter (4)."
  ::= { filterEntry 4 }

 filterFlags OBJECT-TYPE
  SYNTAX INTEGER
  ACCESS read-write
  STATUS mandatory
      DESCRIPTION
        "A set of flag bits which control the operation of the filter.
         Filters will not prevent packets from being accepted by the
         ES/1 as a final destination. The following bits are used:
         bit 13,  bit 12,  bit 11,  bit 10. bits 9-8 used for
         filterFrame. bits 7-6 used for filterSource, filterSourceEnd,
         and filterSourceMask. bits 5-4 used for filterDest,
         filterDestEnd, and filterDestMask. bits 3-2 used for
         filterSrcLan. bits 1-0 used for filterField, filterOffset,
         and filterMask."
  ::= { filterEntry 5 }

 filterFrame OBJECT-TYPE
  SYNTAX INTEGER  -- { any-llc(1), any-ethernet(2), else explicit frame value }
  ACCESS read-write
  STATUS mandatory
      DESCRIPTION
        "Ethernet protocol type (1501-65535), or one (1) to indicate
         any 802 frame, or two (2) to indicate any Ethernet frame,
         Note that a specific Ethernet protocol type may appear in
         either Ethernet format frames, or encapsulated within 802
         format frames."
  ::= { filterEntry 6 }

 filterSource OBJECT-TYPE
  SYNTAX OCTET STRING
  ACCESS read-write
  STATUS mandatory
      DESCRIPTION
        "Beginning source address."
  ::= { filterEntry 7 }

 filterSourceEnd OBJECT-TYPE
  SYNTAX OCTET STRING
  ACCESS read-write
  STATUS mandatory
      DESCRIPTION
        "Ending source address."
  ::= { filterEntry 8 }

 filterDest OBJECT-TYPE
  SYNTAX OCTET STRING
  ACCESS read-write
  STATUS mandatory
      DESCRIPTION
        "Beginning destination address."
  ::= { filterEntry 9 }

 filterDestEnd OBJECT-TYPE
  SYNTAX OCTET STRING
  ACCESS read-write
  STATUS mandatory
      DESCRIPTION
        "Ending destination address."
  ::= { filterEntry 10 }

 filterSourceMask OBJECT-TYPE
  SYNTAX OCTET STRING
  ACCESS read-write
  STATUS mandatory
      DESCRIPTION
        "A bitmask to be applied to the packet's source address
        before checking it against filterSource and filterSourceEnd."
  ::= { filterEntry 11 }

 filterDestMask OBJECT-TYPE
  SYNTAX OCTET STRING
  ACCESS read-write
  STATUS mandatory
      DESCRIPTION
        "A bitmask to be applied to the packet's destination address
         before checking it against filterDest and filterDestEnd."
  ::= { filterEntry 12 }

 filterSrcLan OBJECT-TYPE
  SYNTAX INTEGER
  ACCESS read-write
  STATUS mandatory
      DESCRIPTION
        "Either the port number from which the packet is received, or
         the value of any one of the group identifiers defined by
         sifLan for that port."
  ::= { filterEntry 13 }

 filterOffset OBJECT-TYPE
  SYNTAX INTEGER
  ACCESS read-write
  STATUS mandatory
      DESCRIPTION
        "Zero-based offset of an arbitrary field within the packet.
         Depending upon the value of filterFlags, the offset is
         relative to the start of the translated packet, beginning
         with the big endian MAC addresses; or, the offset is
         relative to the start of the data past the IP header (and,
         the packet must be an IP packet with a valid IP header); or,
         the offset is relative to the start of the data past the
         Source Routing information (presence of Source Routing
         information is optional). "
  ::= { filterEntry 14 }

 filterField OBJECT-TYPE
  SYNTAX OCTET STRING
  ACCESS read-write
  STATUS mandatory
      DESCRIPTION
        "An 8 octet value to be compared to the contents of the
    arbitrary field within the packet."
  ::= { filterEntry 15 }

 filterMask OBJECT-TYPE
  SYNTAX OCTET STRING
  ACCESS read-write
  STATUS mandatory
      DESCRIPTION
        "An 8 octet mask to be applied to the arbitrary field within
         the packet, before comparing it to filterField."
  ::= { filterEntry 16 }

 filterThreshold OBJECT-TYPE
  SYNTAX INTEGER
  ACCESS read-write
  STATUS mandatory
      DESCRIPTION
        "The number of filter invocations at which an alarm to the
         NMS should be generated."
  ::= { filterEntry 17 }

 filterThreshTime OBJECT-TYPE
  SYNTAX INTEGER
  ACCESS read-write
  STATUS mandatory
      DESCRIPTION
        "The length of time, in seconds, to which filterThreshold
         applies. A value of zero indicates that no alarms should be
         sent to the NMS. Values greater than 3600 (i.e., one hour)
         are not allowed."
  ::= { filterEntry 18 }

 filterThreshFlag OBJECT-TYPE
  SYNTAX INTEGER { true(1), false(2) }
  ACCESS read-only
  STATUS mandatory
      DESCRIPTION
        "Whether usage of this filter has exceeded the limits
         specified by filterThreshold and filterThreshTime, and the
         NMS has not yet acknowledged the alarm. Therefore, whenever
         the NMS reads this value, it will always be False; however,
         the NMS may receive alarms with this value set to True."
  ::= { filterEntry 19 }

 filterPktCnts OBJECT-TYPE
  SYNTAX Counter
  ACCESS read-only
  STATUS mandatory
      DESCRIPTION
        "The total number of packets which were discarded due to this
         filter."
  ::= { filterEntry 20 }

 filterLastSrc OBJECT-TYPE
  SYNTAX OCTET STRING
  ACCESS read-only
  STATUS mandatory
      DESCRIPTION
        "The source MAC address of the last packet which was
         discarded due to this filter "
  ::= { filterEntry 21 }

    -- { filterEntry 22 } is not used

 -- Change Reboot Characteristics Command Group

 rebootBridgingMemory OBJECT-TYPE
  SYNTAX INTEGER
  ACCESS read-write
  STATUS mandatory
      DESCRIPTION
        "The percentage (1 - 99) of the PPE's memory to be allocated
         for MAC bridging. The PPE's remaining memory will be used
         for communicating with the NMS and for routing. "
  ::= { reboot 1 }

 rebootSlotTable OBJECT-TYPE
  SYNTAX SEQUENCE OF RebootEntry
  ACCESS not-accessible
  STATUS mandatory
      DESCRIPTION
        "A list of the desired occupants of the slots; one per slot."
  ::= { reboot 2 }

 rebootEntry OBJECT-TYPE
  SYNTAX RebootEntry
  ACCESS not-accessible
  STATUS mandatory
      DESCRIPTION
        "A set of objects for each slot."
  INDEX { rebootIndex }
  ::= { rebootSlotTable 1 }

 RebootEntry ::= SEQUENCE {
   rebootIndex
    INTEGER,
   rebootType
    INTEGER,
   rebootUseMod
    INTEGER,
   rebootPortType
    OCTET STRING
   }
 rebootIndex OBJECT-TYPE
  SYNTAX INTEGER
  ACCESS read-only
  STATUS mandatory
      DESCRIPTION
        "The slot number, beginning with 1 for the first slot. This
         number always matches the instance of the rebootEntry."
  ::= { rebootEntry 1 }

 rebootType OBJECT-TYPE
  SYNTAX INTEGER {
     vacant(1),
     unknown(2),
     packet-processing-engine(3),
     turbo(4),
     csma-iom(5),
     hssi-iom(6),
     tpr-iom(7),
     fddi-iom(8),
     ifddi-iom(9),
     ttpr-iom(10),
     eiom8-iom(11),
     feiom-iom(12)
    }
  ACCESS read-write
  STATUS mandatory
      DESCRIPTION
        "The desired module type of the slot."
  ::= { rebootEntry 2 }

 rebootUseMod OBJECT-TYPE
  SYNTAX INTEGER {
     reset(1),
     run(3)
    }
  ACCESS read-write
  STATUS mandatory
      DESCRIPTION
        "Whether to use this module, not applicable for the Packet
         Processing Engine."
  ::= { rebootEntry 3 }

 rebootPortType OBJECT-TYPE
  SYNTAX OCTET STRING
  ACCESS read-write
  STATUS mandatory
      DESCRIPTION
        "This is a variable-length byte array where each element
         represents the types of the ports belonging to this module."
  ::= { rebootEntry 4 }

 rebootConfig OBJECT-TYPE
  SYNTAX INTEGER {
     no-change(1),
     tftp-config(2),
     revert-to-defaults(3)
    }
  ACCESS read-write
  STATUS mandatory
      DESCRIPTION
        "The configuration file that will be used when the ES/1
         reboots. This parameter is normally automatically set by the
         ES/1; however, an NMS may explicitly set it to either
         no-change (1) or revert-to-defaults (3)."
  ::= { reboot 3 }

 rebootRouteMemory OBJECT-TYPE
  SYNTAX INTEGER
  ACCESS read-write
  STATUS mandatory
    DESCRIPTION
        "Percentage of non-bridging memory to allocate for routing
         tables. The remainder will be used for transient packets
         such as ARP and RIP."
  ::= { reboot 4 }

 -- Debug Command Group

 debugStringID OBJECT-TYPE
  SYNTAX INTEGER
  ACCESS read-only
  STATUS mandatory
      DESCRIPTION
        "The number of debug text strings sent by the ES/1. This
         parameter is used by the ES/1's enterprise specific trap
         mechanism."
  ::= { debug 1 }

 debugString OBJECT-TYPE
  SYNTAX OCTET STRING
  ACCESS read-only
  STATUS mandatory
      DESCRIPTION
        "The last debug text string (0-80 bytes) sent by the ES/1."
  ::= { debug 2 }

 debugTable OBJECT-TYPE
  SYNTAX SEQUENCE OF DebugEntry
  ACCESS not-accessible
  STATUS mandatory
      DESCRIPTION
        "A list of the modules which may be debugged, with one module
         per slot defined by hwSlotTable."
  ::= { debug 3 }

 debugEntry OBJECT-TYPE
  SYNTAX DebugEntry
  ACCESS not-accessible
  STATUS mandatory
      DESCRIPTION
        "A set of objects for each module."
  INDEX { debugIndex }
  ::= { debugTable 1 }

 DebugEntry ::= SEQUENCE {
   debugIndex
    INTEGER,
   debugOperation
    INTEGER,
   debugBase
    INTEGER,
   debugLength
    INTEGER,
   debugData
    OCTET STRING
   }

 debugIndex OBJECT-TYPE
  SYNTAX INTEGER
  ACCESS read-only
  STATUS mandatory
      DESCRIPTION
        "The module number, beginning with 1 for the module in the
         first slot. This number always matches the instance of the
         debugEntry."
  ::= { debugEntry 1 }

 debugOperation OBJECT-TYPE
  SYNTAX INTEGER {
     examine(1),
     modify(2)
    }
  ACCESS read-write
  STATUS mandatory
      DESCRIPTION
        "Type of debug operation requested."
  ::= { debugEntry 2 }

 debugBase OBJECT-TYPE
  SYNTAX INTEGER
  ACCESS read-write
  STATUS mandatory
      DESCRIPTION
        "The base address of the memory region to be examined or
         modified."
  ::= { debugEntry 3 }

 debugLength OBJECT-TYPE
  SYNTAX INTEGER
  ACCESS read-write
  STATUS mandatory
      DESCRIPTION
        "The desired length, in words, of the memory region to be
         examined or modified. After the ES/1 performs the operation,
         debugLength is updated to indicate the length of memory that
         was actually examined or modified. If debugLength is updated
         to contain zero, then the module was not operational."
  ::= { debugEntry 4 }

 debugData OBJECT-TYPE
  SYNTAX OCTET STRING
  ACCESS read-write
  STATUS mandatory
      DESCRIPTION
        "A series of 0-64 octets, which represents 0-16 words (this may
         change in the future, if the ES/1 has processors with word
         sizes of other than 4 bytes per word). When this variable is
         read, the LMA will use the values in debugBase and
         debugLength to return the contents of a specified memory
         range to the NMS. Similarly, when this variable is written,
         a specified area of memory will be overwritten with data
         supplied by the NMS."
  ::= { debugEntry 5 }

 -- Loopback Command Group

 lpbkTable OBJECT-TYPE
  SYNTAX SEQUENCE OF LpbkEntry
  ACCESS not-accessible
  STATUS mandatory
      DESCRIPTION
        "A list of interface entries; one per port."
  ::= { lpbk 1 }

 lpbkEntry OBJECT-TYPE
  SYNTAX LpbkEntry
  ACCESS not-accessible
  STATUS mandatory
      DESCRIPTION
        "A set of objects for an interface entry."
  INDEX { lpbkIndex }
  ::= { lpbkTable 1 }

 LpbkEntry ::= SEQUENCE {
   lpbkIndex
    INTEGER,
   lpbkOperation
    INTEGER,
   lpbkDestAddr
    OCTET STRING,
   lpbkPktNum
    INTEGER,
   lpbkInterval
    TimeTicks,
   lpbkPktLength
    INTEGER,
   lpbkIncrements
    INTEGER,
   lpbkGoods
    Counter,
   lpbkErrorNoReceives
    Counter,
   lpbkErrorBadReceives
    Counter,
   lpbkErrorSize
    INTEGER,
   lpbkErrorSent
    OCTET STRING,
   lpbkErrorReceived
    OCTET STRING,
   lpbkErrorOffset
    INTEGER
   }

lpbkIndex OBJECT-TYPE
 SYNTAX INTEGER
 ACCESS read-only
 STATUS mandatory
   DESCRIPTION
     "The port number, beginning with 1 for the first port."
 ::= { lpbkEntry 1 }

lpbkOperation OBJECT-TYPE
 SYNTAX INTEGER {
    loopback-off(1),
    loopback-local(2),
    loopback-remote(3)
   }
 ACCESS read-write
 STATUS mandatory
   DESCRIPTION
     "The type of loopback being performed. Setting lpbkOperation to
      loopback-off causes loop back operation to terminate. Setting
      lpbkOperation to loopback-local or loopback-remote causes
      loopback operation to commence, and the ES/1 automatically
      resets lpbkOperation to loopback-off when the loopback operation
      has completed."
 ::= { lpbkEntry 2 }

lpbkDestAddr OBJECT-TYPE
 SYNTAX OCTET STRING
 ACCESS read-write
 STATUS mandatory
   DESCRIPTION
     "The MAC address of the target device, only needed for remote
      loopback."
 ::= { lpbkEntry 3 }

lpbkPktNum OBJECT-TYPE
 SYNTAX INTEGER
 ACCESS read-write
 STATUS mandatory
   DESCRIPTION
     "The number of loopback packets to be transmitted."
 ::= { lpbkEntry 4 }

lpbkInterval OBJECT-TYPE
 SYNTAX TimeTicks
 ACCESS read-write
 STATUS mandatory
   DESCRIPTION
     "The desired time delay between the reception of a looped back
      packet, and the transmission of the next packet to be looped
      back."
 ::= { lpbkEntry 5 }

lpbkPktLength OBJECT-TYPE
 SYNTAX INTEGER
 ACCESS read-write
 STATUS mandatory
   DESCRIPTION
     "The length (in octets) of the loopback packet. The values of
      the data itself are automatically selected by the ES/1."
 ::= { lpbkEntry 6 }

lpbkIncrements OBJECT-TYPE
 SYNTAX INTEGER
 ACCESS read-write
 STATUS mandatory
   DESCRIPTION
     "The number of bytes of data to be added to the loopback packet
      after each successful loopback packet transmission and
      reception. When the port's maximum packet size has been reached,
      the ES/1 automatically begins again, starting with
      lpbkPktLength."
 ::= { lpbkEntry 7 }

lpbkGoods OBJECT-TYPE
 SYNTAX Counter
 ACCESS read-only
 STATUS mandatory
   DESCRIPTION
     "The number of packets successfully looped back. This number is
      automatically reset to zero, whenever loopback operation is
     initiated."
 ::= { lpbkEntry 8 }

lpbkErrorNoReceives OBJECT-TYPE
 SYNTAX Counter
 ACCESS read-only
 STATUS mandatory
   DESCRIPTION
     "The number of packets which were transmitted, but not received.
      This number is automatically reset to zero, whenever loopback
      operation is initiated."
 ::= { lpbkEntry 9 }

lpbkErrorBadReceives OBJECT-TYPE
 SYNTAX Counter
 ACCESS read-only
 STATUS mandatory
   DESCRIPTION
     "The number of transmitted packets which were received with
      different data patterns. This number is automatically reset to
      zero, whenever loopback operation is initiated. "
 ::= { lpbkEntry 10 }

lpbkErrorSize OBJECT-TYPE
 SYNTAX INTEGER
 ACCESS read-only
 STATUS mandatory
   DESCRIPTION
     "The length of the last loopback packet which caused either
      lpbkErrorNoReceives or lpbkErrorBadReceives to be incremented.
      This number is automatically reset to zero, whenever loopback
      operation is initiated."
 ::= { lpbkEntry 11 }

lpbkErrorSent OBJECT-TYPE
 SYNTAX OCTET STRING
 ACCESS read-only
 STATUS mandatory
   DESCRIPTION
     "The transmitted bytes (0-4) of data within the last loopback
      packet which caused lpbkErrorBadReceives to be incremented.
      This parameter is automatically reset to the null string,
      whenever loopback operation is initiated."
 ::= { lpbkEntry 12 }

lpbkErrorReceived OBJECT-TYPE
 SYNTAX OCTET STRING
 ACCESS read-only
 STATUS mandatory
   DESCRIPTION
     "The received bytes (0-4) of data within the last loopback
      packet which caused lpbkErrorBadReceives to be incremented.
      This parameter is automatically reset to the null string,
      whenever loopback operation is initiated."
 ::= { lpbkEntry 13 }

lpbkErrorOffset OBJECT-TYPE
 SYNTAX INTEGER
 ACCESS read-only
 STATUS mandatory
   DESCRIPTION
     "The byte offset (one being the first byte) within the loopback
      packet where lpbkErrorSent begins. This number is automatically
      reset to zero, whenever loopback operation is initiated."
 ::= { lpbkEntry 14 }

 -- SMC WAN Interface Group

swanTable OBJECT-TYPE
 SYNTAX SEQUENCE OF SwanEntry
 ACCESS not-accessible
 STATUS mandatory
   DESCRIPTION
     "A list of interface entries; one per WAN port."
 ::= { swan 1 }

swanEntry OBJECT-TYPE
 SYNTAX SwanEntry
 ACCESS not-accessible
 STATUS mandatory
   DESCRIPTION
     "A set of objects for an interface entry."
 INDEX { swanIndex }
 ::= { swanTable 1 }

SwanEntry ::= SEQUENCE {
   swanIndex
    INTEGER,
   swanDesiredSpeed
    INTEGER,
   swanActualSpeed
    INTEGER,
   swanIpNeighborAddress
    IpAddress,
   swanPPPActive
    INTEGER,
   swanAlignmentErrors
    Counter,
   swanOverrunErrors
    Counter,
   swanPortType
    INTEGER,
   swanLinkCost
    INTEGER,
   swanMeshState
    INTEGER,
   swanLinkSubnet
    OCTET STRING,
   swanLinkBridge
    OCTET STRING,
   swanLinkPort
    INTEGER,
   swanNegotiate
    INTEGER,
   swanSwitches
    INTEGER,
   swanDCEDrops
    Counter,
   swanOutPacketType
    INTEGER,
   swanLinkErrorPercentage
    INTEGER,
   swanLinkErrorDuration
    INTEGER,
   swanLinkErrorFailPeriods
    INTEGER,
   swanLinkErrorMaxPeriods
    INTEGER,
   swanLinkRestartTime
    INTEGER,
   swanPreserveFCS
    INTEGER
   }

swanIndex OBJECT-TYPE
 SYNTAX INTEGER
 ACCESS read-only
 STATUS mandatory
   DESCRIPTION
     "The ES/1's port number of the port."
 ::= { swanEntry 1 }

swanDesiredSpeed OBJECT-TYPE
 SYNTAX INTEGER
 ACCESS read-write
 STATUS mandatory
	  		 DESCRIPTION ""
 ::= { swanEntry 2 }

swanActualSpeed OBJECT-TYPE
 SYNTAX INTEGER {
    b1200-baud(2),
    b2400-baud(3),
    b4800-baud(4),
    b9600-baud(5),
    b19200-baud(6),
    b38400-baud(7),
    b56-kilobits(8),
    b1544-kilobits(9),
    b2048-kilobits(10),
    b45-megabits(11)
   }
 ACCESS read-only
 STATUS mandatory
   DESCRIPTION
     "This is the actual line speed. The possible values are defined
      by suartSpeed. For HSSI, the speed is 45-megabits(11). If the
      RS-449 interface is being used on the HSSI IOM, the speed is
      always reported as 1.544-megabits(9); however, the external
      clock may be generating a slower speed."
 ::= { swanEntry 3 }

swanIpNeighborAddress OBJECT-TYPE
 SYNTAX IpAddress
 ACCESS read-write
 STATUS mandatory
   DESCRIPTION
     "Zero, or an IP address to assign to the port's neighbor."
 ::= { swanEntry 4 }

swanPPPActive OBJECT-TYPE
 SYNTAX INTEGER { true(1), false(2) }
 ACCESS read-write
 STATUS mandatory
	  		 DESCRIPTION ""
 ::= { swanEntry 5 }

swanAlignmentErrors OBJECT-TYPE
 SYNTAX Counter
 ACCESS read-only
 STATUS mandatory
 	  		 DESCRIPTION ""
::= { swanEntry 6 }

swanOverrunErrors OBJECT-TYPE
 SYNTAX Counter
 ACCESS read-only
 STATUS mandatory
   DESCRIPTION
     "Number of received packets with data overrun errors, since the
      port was last enabled."
 ::= { swanEntry 7 }

swanPortType OBJECT-TYPE
 SYNTAX INTEGER {
    wan-unknown(1),
    wan-v11(2),
    wan-v24(3),
    wan-v35(4),
    wan-e1(5),
    wan-t1(6),
    wan-rs530(7),
    wan-t3(8)
   }
 ACCESS read-only
 STATUS mandatory
 	  		 DESCRIPTION ""
::= { swanEntry 8 }

swanLinkCost OBJECT-TYPE
 SYNTAX INTEGER
 ACCESS read-only
 STATUS mandatory
 	  		 DESCRIPTION ""
::= { swanEntry 9 }

swanMeshState OBJECT-TYPE
 SYNTAX INTEGER { true(1), false(2) }
 ACCESS read-only
 STATUS mandatory
 	  		 DESCRIPTION ""
::= { swanEntry 10 }

swanLinkSubnet OBJECT-TYPE
 SYNTAX OCTET STRING
 ACCESS read-only
 STATUS mandatory
 	  		 DESCRIPTION ""
::= { swanEntry 11 }

swanLinkBridge OBJECT-TYPE
 SYNTAX OCTET STRING
 ACCESS read-only
 STATUS mandatory
 	  		 DESCRIPTION ""
::= { swanEntry 12 }

swanLinkPort OBJECT-TYPE
 SYNTAX INTEGER
 ACCESS read-only
 STATUS mandatory
 	  		 DESCRIPTION ""
::= { swanEntry 13 }

swanNegotiate OBJECT-TYPE
 SYNTAX INTEGER { true(1), false(2) }
 ACCESS read-write
 STATUS mandatory
 	  		 DESCRIPTION ""
::= { swanEntry 14 }

swanSwitches OBJECT-TYPE
 SYNTAX INTEGER {
    wan-hssi(1),
    wan-t1(2),
    wan-hssi-switching-disabled(3),
    wan-t1-switching-disabled(4)
   }
 ACCESS read-write
 STATUS mandatory
   DESCRIPTION
     "Current port selected."
 ::= { swanEntry 15 }

swanDCEDrops OBJECT-TYPE
 SYNTAX Counter
 ACCESS read-only
 STATUS mandatory
   DESCRIPTION
     "Number of instances when loss of DCE has been detected."
 ::= { swanEntry 16 }

swanOutPacketType  OBJECT-TYPE
  SYNTAX  INTEGER {
                token-ring-without-FCS(1),
                token-ring-with-FCS(2),
                ethernet-without-FCS(3),
                ethernet-with-FCS(4)
   }
  ACCESS  read-write
  STATUS  mandatory
  DESCRIPTION
   "The type of out going packet to generate on the HSSI link."
        -- DEFVAL     { Ethernet with FCS(4) }
 ::= { swanEntry 17 }

swanLinkErrorPercentage  OBJECT-TYPE
  SYNTAX  INTEGER (0..10000)
  ACCESS  read-write
  STATUS  mandatory
  DESCRIPTION
   "The percentage of acceptible errors in hundreths of percent. "
        -- DEFVAL 20
 ::= { swanEntry 18 }

swanLinkErrorDuration  OBJECT-TYPE
  SYNTAX  INTEGER (0..10000)
  ACCESS  read-write
  STATUS  mandatory
  DESCRIPTION
   "The time period in hundredths of a second over which the error
             percentage should be applied. "
        -- DEFVAL 500
 ::= { swanEntry 19 }

swanLinkErrorFailPeriods  OBJECT-TYPE
  SYNTAX  INTEGER (1..20)
  ACCESS  read-write
  STATUS  mandatory
  DESCRIPTION
   "The maximum number of periods allowed to contain the error
             percentage before the link quality is determined to have failed."
        -- DEFVAL 2
 ::= { swanEntry 20 }

swanLinkErrorMaxPeriods  OBJECT-TYPE
  SYNTAX  INTEGER (1..20)
  ACCESS  read-write
  STATUS  mandatory
  DESCRIPTION
   "The maximum number of periods to be used for calculation of link
             quality. Default is 10."
        -- DEFVAL 10
 ::= { swanEntry 21 }

swanLinkRestartTime  OBJECT-TYPE
  SYNTAX  INTEGER (0..10000)
  ACCESS  read-write
  STATUS  mandatory
  DESCRIPTION
   "The time period in centiseconds which must contain error free
             LQR operation before restarting link. "
        -- DEFVAL 1000
 ::= { swanEntry 22 }

swanPreserveFCS  OBJECT-TYPE
  SYNTAX  INTEGER {
                    true(1),
                    false(2)
             }
  ACCESS  read-write
  STATUS   mandatory
  DESCRIPTION
   "Preserve received FCS if true, else regenerate FCS on packet
             transmission. "
        -- DEFVAL 1
 ::= { swanEntry 23 }


-- SMC Repeater Interface Group

srepeaterTable OBJECT-TYPE
 SYNTAX   SEQUENCE OF SrepeaterEntry
 ACCESS   not-accessible
 STATUS   mandatory
 DESCRIPTION
  "SMC-specific status information and control variables for a
  collection of repeater groups in a particular system."
 ::= { srepeater 1 }

srepeaterEntry OBJECT-TYPE
 SYNTAX   SrepeaterEntry
 ACCESS   not-accessible
 STATUS   mandatory
 DESCRIPTION
  "SMC-specific status information and control variables for a
  particular repeater domain (group) in the system."
 INDEX  { srepeaterGroupID }
 ::= { srepeaterTable 1 }

SrepeaterEntry ::=
 SEQUENCE {
  srepeaterGroupID
   INTEGER,
  srepeaterLinkStatusMask
   INTEGER,
  srepeaterExtendedStats
   INTEGER
 }

srepeaterGroupID OBJECT-TYPE
 SYNTAX   INTEGER (1..1024)
 ACCESS   read-only
 STATUS   mandatory
 DESCRIPTION
  "The value of srepeaterGroupID is assigned so as to uniquely
  identify a repeater domain (group) in a system where a single
  agent manages multiple repeater domains."
 ::= { srepeaterEntry 1 }

srepeaterLinkStatusMask OBJECT-TYPE
 SYNTAX   INTEGER
 ACCESS   read-only
 STATUS   mandatory
 DESCRIPTION
   "This mask provides quick access to the general
    connectivity of the repeater. Each bit
    corresponds to the link status of a repeater
    port. If the bit is set to 1 then link pulses are
    being received, as per the IEEE specification. A
    bit value of zero indicates one of four
    conditions:
    - There is nothing physically attached to the port.
    - The port is not configured for twisted-pair. The
      AUI interface, for example, does not generate or
      test for link pulses.
    - The device attached to the port does not generate
      the link pulses specified by the IEEE standard.
      STARLAN devices, for example, do not generate
      such pulses.
    - The port is configured to ignore link pulses (see
      srepeaterPortLinkPulse).
    The least significant bit in the mask corresponds
    to repeater port 1; the high-order eight bits are
    always zero."
 ::= { srepeaterEntry 2 }

srepeaterExtendedStats OBJECT-TYPE
 SYNTAX   INTEGER { enabled(1), disabled(2) }
 ACCESS   read-write
 STATUS   mandatory
 DESCRIPTION
  "When enabled(1), the rptrMonitorGroup, rptrMonitorPort,
  and rptrAddrTrack tables are available, and the CEIOM
  maintains frame-by-frame tallies for the repeater in
  order to support these tables. Bridging performance may
  be slightly degraded due to the extra processing required,
  although the effect will not ordinarily be noticeable.
  When disabled(2), the rptrMonitorGroup, rptrMonitorPort,
  and rptrAddrTrack tables are not available."
 ::= { srepeaterEntry 3 }

srepeaterPortTable OBJECT-TYPE
 SYNTAX   SEQUENCE OF SrepeaterPortEntry
 ACCESS   not-accessible
 STATUS   mandatory
 DESCRIPTION
  "SMC-specific status information and control variables for a
  collection of repeater ports in a particular system."
 ::= { srepeater 2 }

srepeaterPortEntry OBJECT-TYPE
 SYNTAX   SrepeaterPortEntry
 ACCESS   not-accessible
 STATUS   mandatory
 DESCRIPTION
  "SMC-specific status information and control variables for a
  particular repeater port in the system."
 INDEX  { srepeaterPortGroupID, srepeaterPortPortID }
 ::= { srepeaterPortTable 1 }

SrepeaterPortEntry ::=
 SEQUENCE {
  srepeaterPortGroupID
   INTEGER,
  srepeaterPortPortID
   INTEGER,
  srepeaterPortLinkPulse
   INTEGER
 }

srepeaterPortGroupID OBJECT-TYPE
 SYNTAX   INTEGER (1..1024)
 ACCESS   read-only
 STATUS   mandatory
 DESCRIPTION
  "The value of srepeaterPortGroupID is assigned so as to uniquely
  identify a group (repeater ID) in a system where a single
  agent manages multiple repeater groups. This corresponds to
  ifIndex, as well as rptr...GroupIndex.

  As with the standard rptr MIB, this table treats a CEIOM, which
  is actually a complete repeater domain, as a repeater group."
 ::= { srepeaterPortEntry 1 }

srepeaterPortPortID OBJECT-TYPE
 SYNTAX   INTEGER
 ACCESS   read-only
 STATUS   mandatory
 DESCRIPTION
  "Identifies a repeater port within a repeater group/domain.
  Values correspond to physical connector position on the CEIOM.
  For the CEIOM-24, the leftmost position is port 1, the
  rightmost port 24."
 ::= { srepeaterPortEntry 2 }

srepeaterPortLinkPulse OBJECT-TYPE
 SYNTAX   INTEGER { enabled(1), disabled(2) }
 ACCESS   read-write
 STATUS   mandatory
 DESCRIPTION
  "When enabled (the default), the repeater port generates and
  expects to receive a link pulse, as per 10BaseT specification.
  When disabled, the port does not generate or expect link
  pulse, in order to accommodate pre-10BaseT twisted-pair
  Ethernet attachments."
 ::= { srepeaterPortEntry 3 }


 -- SMC Protocols Group

sprotoTable OBJECT-TYPE
  SYNTAX  SEQUENCE OF SprotoEntry
  ACCESS  not-accessible
  STATUS  mandatory
  DESCRIPTION
    "This table contains configuration information specifying
    the types of protocols used to bridge, route, translate,
    and filter frames for each port."
  ::= { sproto 1 }

sprotoEntry OBJECT-TYPE
  SYNTAX  SprotoEntry
  ACCESS  not-accessible
  STATUS  mandatory
  DESCRIPTION
    "Each entry in this table specifies which protocols are
    used by a particular port in the ES/1."
  INDEX { sprotoIfIndex }
  ::= { sprotoTable 1 }

SprotoEntry ::=
  SEQUENCE {
    sprotoIfIndex
    INTEGER,
    sprotoBridge
    INTEGER,
    sprotoSuppressBpdus
    INTEGER,
    sprotoIpRoute
    INTEGER,
    sprotoIpxRoute
    INTEGER,
    sprotoAppleRoute
    INTEGER,
    sprotoArpTranslate
    INTEGER,
    sprotoArpSourceRoute
    INTEGER,
    sprotoIpxTranslate
    INTEGER,
    sprotoAppleTranslate
    INTEGER,
    sprotoIbmLlcTranslate
    INTEGER,
    sprotoRip
    INTEGER,
    sprotoEgp
    INTEGER,
    sprotoOspf
    INTEGER,
    sprotoArpProxy
    INTEGER,
    sprotoIbm8209Lsaps
    OCTET STRING,
    sprotoBootpRelay
    INTEGER,
    sprotoNetbiosTranslate
    INTEGER,
    sprotoIpMulticast
    INTEGER,
    sprotoTrunking
    INTEGER,
    sprotoIpxSrTranslate
    INTEGER,
    sprotoAllTranslate
    INTEGER,
    sprotoSteHopCountAppliedRule
    INTEGER
  }

sprotoIfIndex OBJECT-TYPE
  SYNTAX  INTEGER
  ACCESS  read-only
  STATUS  mandatory
  DESCRIPTION
    "Identifies the interface (port) to which this entry's
    information belongs. The value of this variable
    corresponds to ifIndex, as well as most of the other
    port identification values in related MIBs."
  ::= { sprotoEntry 1 }

sprotoBridge OBJECT-TYPE
  SYNTAX  INTEGER { transparent(1), sr(2), srt(3), none(4) }
  ACCESS  read-write
  STATUS  mandatory
  DESCRIPTION
    "Defines the bridging method to be applied to frames
    received at, or destined for, this port. Ethernet and
    FDDI ports may be configured for transparent, srt, or
    none.  Token Ring ports may be configured for any of
    the four options. The UART may only be configured to
    none."
  ::= { sprotoEntry 2 }

sprotoSuppressBpdus OBJECT-TYPE
  SYNTAX  INTEGER { normal(1), suppressed(2) }
  ACCESS  read-write
  STATUS  mandatory
  DESCRIPTION
    "Allows transmission of spanning tree protocol packets
    to be suppressed.  If normal(1), 802.1d spanning tree
    packets and source-routing spanning tree packets are
    transmitted as usual. If suppressed(2), these packets
    are not transmitted. This option may be needed for in-
    teroperability with non-802.1d spanning tree protocols
    (e.g., DEC LanBridge 100)."
  ::= { sprotoEntry 3 }

sprotoIpRoute OBJECT-TYPE
  SYNTAX  INTEGER { enabled(1), disabled(2) }
  ACCESS  read-write
  STATUS  mandatory
  DESCRIPTION
    "Specifies whether or not this port is to be used for
    IP routing."
  ::= { sprotoEntry 4 }

sprotoIpxRoute OBJECT-TYPE
  SYNTAX  INTEGER { enabled(1), disabled(2), ipxsr(3) }
  ACCESS  read-write
  STATUS  mandatory
  DESCRIPTION
    "Specifies whether or not this port is to be used for
    Novell NetWare IPX routing."
  ::= { sprotoEntry 5 }

sprotoAppleRoute OBJECT-TYPE
  SYNTAX  INTEGER { enabled(1), disabled(2) }
  ACCESS  read-write
  STATUS  mandatory
  DESCRIPTION
    "Specifies whether or not this port is to be used for
    AppleTalk (tm) routing."
  ::= { sprotoEntry 6 }

sprotoArpTranslate OBJECT-TYPE
  SYNTAX  INTEGER { none(1), bitswap1(2), bitswap6(3), bitswap61(4), oneto6(5), oneto6swap(6) }
  ACCESS  read-write
  STATUS  mandatory
  DESCRIPTION
    "These options are intended to compensate for any like-
    ly implementation of internet ARP on 802.5 token ring.
    If set to bitswap1(2), then embedded MAC addresses for
    ARP packets with hardwareType 1 (Ethernet) will be
    bitswapped. If bitswap6(3) then embedded MAC addresses
    for ARP packets with hardware type 6 (IEEE 802) will be
    bitswapped. If bitswap61(4) then both type-1 and type-6
    ARP packets will be bitswapped. If oneto6(5), then in-
    coming type-6 ARP packets will be changed to type-1 and
    outgoing type-1 ARP packets will be changed to type-6,
    both without bitswapping. If oneto6swap(6), then incom-
    ing type-6 ARP packets will be converted to type-1 and
    outgoing type-1 to type-6, with embedded addresses
    bitswapped.

    This option only applies to token ring ports. The fac-
    tory default for all ports is none(1)."
  ::= { sprotoEntry 7 }

sprotoArpSourceRoute OBJECT-TYPE
  SYNTAX  INTEGER { passRif(1), stripRif(2), passBoth(3), none(4) }
  ACCESS  read-write
  STATUS  mandatory
  DESCRIPTION
    "Specifies whether, when bridging TCP/IP ARP packets
    which are source-routing explorer frames, the routing
    information is to be stripped or propagated. If pass-
    Rif(1), the frame is bridged as is, with route-
    discovery proceeding as expected. If stripRif(2), then
    the routing information field is stripped before being
    propagated. This option allows non-source-routing
    (e.g., Ethernet) IP hosts to communicate tran-
    sparently. If passBoth(3), then both the original
    source-routed frame and the transparent equivalent are
    propagated. This choice provides maximum connectivity
    at some expense in network traffic. None(4) is identical
    to passRif.

    This option applies only to token ring ports."
  ::= { sprotoEntry 8 }

sprotoIpxTranslate OBJECT-TYPE
  SYNTAX  INTEGER { enabled(1), disabled(2) }
  ACCESS  read-write
  STATUS  mandatory
  DESCRIPTION
    "Specifies whether, when bridging Novell IPX frames,
    they are to be translated to Ethernet-like frame for-
    mat.

    This option applies only to token ring ports."
  ::= { sprotoEntry 9 }

sprotoAppleTranslate OBJECT-TYPE
  SYNTAX  INTEGER { enabled(1), disabled(2) }
  ACCESS  read-write
  STATUS  mandatory
  DESCRIPTION
    "Specifies whether, when bridging AppleTalk ELAP, TLAP,
    and AARP frames, those frames are to be translated
    between token ring and Ethernet format before being
    forwarded.

    This option applies only to token ring ports."
  ::= { sprotoEntry 10 }

sprotoIbmLlcTranslate OBJECT-TYPE
  SYNTAX  INTEGER { enabled(1), disabled(2) }
  ACCESS  read-write
  STATUS  mandatory
  DESCRIPTION
    "Specifies whether, when bridging IBM LLC frames, an
    8209-style translation between token ring and Ethernet
    format is to be performed before being forwarded.

    This option applies only to token ring ports."
  ::= { sprotoEntry 11 }

sprotoRip OBJECT-TYPE
  SYNTAX  INTEGER { enabled(1), disabled(2) }
  ACCESS  read-write
  STATUS  mandatory
  DESCRIPTION
    "Specifies whether the internet Routing Information
    Protocol (RFC-1058) is to be used over this port. Only
    valid if sprotoIpRoute is enabled."
  ::= { sprotoEntry 12 }

sprotoEgp OBJECT-TYPE
  SYNTAX  INTEGER { enabled(1), disabled(2) }
  ACCESS  read-write
  STATUS  mandatory
  DESCRIPTION
    "Specifies whether the internet External Gateway Proto-
    col (RFC-904) is to be used over this port. Only valid
    if sprotoIpRoute is enabled."
  ::= { sprotoEntry 13 }

sprotoOspf OBJECT-TYPE
  SYNTAX  INTEGER { enabled(1), disabled(2) }
  ACCESS  read-write
  STATUS  mandatory
  DESCRIPTION
    "Specifies whether the internet Open Shortest Path
    First protocol (RFC-1247) is to be used over this port.
    Only valid if sprotoIpRoute is enabled."
  ::= { sprotoEntry 14 }

sprotoArpProxy OBJECT-TYPE
  SYNTAX  INTEGER { enabled(1), disabled(2) }
  ACCESS  read-write
  STATUS  mandatory
  DESCRIPTION
    "Specifies whether the port is to respond to internet
    ARP requests for which the unit is the next hop in a
    routed path. Only valid if sprotoIpRoute is enabled."
  ::= { sprotoEntry 15 }

sprotoIbm8209Lsaps OBJECT-TYPE
  SYNTAX  OCTET STRING
  ACCESS  read-write
  STATUS  mandatory
  DESCRIPTION
    "Specifies up to eight LSAPs for which IBM 8209-style
    token-ring-to-Ethernet encapsulation is to be performed.
    Only valid if sprotoIbmLLcTranslate is enabled.

    This option applies only to token ring ports."
  ::= { sprotoEntry 16 }

sprotoBootpRelay OBJECT-TYPE
  SYNTAX  INTEGER { enabled(1), disabled(2) }
  ACCESS  read-write
  STATUS  mandatory
  DESCRIPTION
   "Specifies whether or not this port is to
    relay BOOTP packets, as described in RFC-951
    and subsequent internet-drafts. Only valid if
    IP routing is also enabled for this interface."
  ::= { sprotoEntry 17 }

sprotoNetbiosTranslate OBJECT-TYPE
  SYNTAX  INTEGER { passRif(1), stripRif(2), passBoth(3), none(4) }
  ACCESS  read-write
  STATUS  mandatory
  DESCRIPTION
  "Specifies whether, when bridging Netbios packets
  which are source-routing explorer frames, the routing
  information is to be stripped or propagated. If pass-
  Rif(1), the frame is bridged as is, with route-
  discovery proceeding as expected. If stripRif(2), then
  the routing information field is stripped before being
  propagated. This option allows non-source-routing
  (e.g., Ethernet) Netbios hosts to communicate tran-
  sparently. If passBoth(3), then both the original
  source-routed frame and the transparent equivalent are
  propagated. This choice provides maximum connectivity
  at some expense in network traffic. None(4) is identical
  to passRif.

  This option applies only to token ring ports."
  ::= { sprotoEntry 18 }

sprotoIpMulticast OBJECT-TYPE
  SYNTAX  INTEGER { enabled(1), disabled(2) }
  ACCESS  read-write
  STATUS  mandatory
  DESCRIPTION
    "Specifies whether the internet Multicast Routing
    Protocol (RFC-1075) is to be used over this port. Only
    valid if sprotoIpRoute is enabled."
  ::= { sprotoEntry 19 }

sprotoTrunking OBJECT-TYPE
  SYNTAX  INTEGER { enabled(1), disabled(2) }
  ACCESS  read-write
  STATUS  mandatory
  DESCRIPTION
    "Specifies whether SMC's trunking protocol (an extension
    to the standard Spanning Tree) is to be used over this port."
  ::= { sprotoEntry 20 }


sprotoIpxSrTranslate OBJECT-TYPE
    SYNTAX   INTEGER { passRif(1), stripRif(2), passBoth(3), none(4) }
    ACCESS   read-write
    STATUS   mandatory
    DESCRIPTION
      "Specifies whether, when bridging IPX packets
      which are source-routing explorer frames, the routing
      information is to be stripped or propagated. If pass-
      Rif(1), the frame is bridged as is, with route-
      discovery proceeding as expected. If stripRif(2), then
      the routing information field is stripped before being
      propagated. This option allows non-source-routing
      (e.g., Ethernet) IPX hosts to communicate tran-
      sparently. If passBoth(3), then both the original
      source-routed frame and the transparent equivalent are
      propagated. This choice provides maximum connectivity
      at some expense in network traffic. None(4) is identical
      to passRif.

      This option applies only to token ring ports."
    ::= { sprotoEntry 22 }

sprotoAllTranslate OBJECT-TYPE
    SYNTAX   INTEGER { passRif(1), stripRif(2), passBoth(3), none(4) }
    ACCESS   read-write
    STATUS   mandatory
    DESCRIPTION
      "Specifies whether, when bridging any source-routed
      explorer frames, the routing information is to be
	  stripped or propagated. If passRif(1), the frame is bridged
	  as is, with route-discovery proceeding as expected.
	  If stripRif(2), then the routing information field is stripped
	  before being propagated. This option allows non-source-routing
      (e.g., Ethernet) IPX hosts to communicate tran-
      sparently. If passBoth(3), then both the original
      source-routed frame and the transparent equivalent are
      propagated. This choice provides maximum connectivity
      at some expense in network traffic. None(4) is identical
      to passRif.

      This option applies only to token ring ports."
    ::= { sprotoEntry 23 }

sprotoSteHopCountAppliedRule OBJECT-TYPE
             SYNTAX   INTEGER { hopcountnotapplied(1), hopcountapplied(2) }
             ACCESS   read-write
             STATUS   mandatory
             DESCRIPTION
               "hopcountnotapplied(1), STE hop count rules are not
          applied to STE frames. Default for SR ports.
                Follows IBM's specifications. hopcountapplied(2),
                STE hop count rules are applied to STE frames.
         Default SRT ports. Follows IEEE specifications."
             ::= { sprotoEntry 24 }

sprotoIpxDot3Framing OBJECT-TYPE
  SYNTAX  INTEGER { ethernet8023(1), ethernet2(2), ethernet8022(3) }
  ACCESS  read-write
  STATUS  mandatory
  DESCRIPTION
  "If sprotoIpxRoute or sprotoIpxTranslate is enabled,
  specifies the type of framing to be used for NetWare
  IPX packets on 802.3 networks. ethernet8023(1) speci-
  fies that the 802.3 header is to be used without an
  802.2 header.  ethernet2(2) specifies that Ethernet-2
  framing is to be used, with etherType 8137. ether-
  net8022(3) specifies that an LLC header e0,e0,03 is to
  be used in conjunction with the 802.3 header."
  ::= { sproto 2 }


sipxIfTable OBJECT-TYPE
 SYNTAX  SEQUENCE OF SipxIfEntry
 ACCESS  not-accessible
 STATUS  mandatory
 DESCRIPTION
  "Describes per-interface attributes of IPX routing."
 ::= { sipx 1 }

sipxIfEntry OBJECT-TYPE
 SYNTAX  SipxIfEntry
 ACCESS  not-accessible
 STATUS  mandatory
 DESCRIPTION
  "For a particular interface, defines the IPX routing
  information."
 INDEX { sipxIfIndex }
 ::= { sipxIfTable 1 }

SipxIfEntry ::=
 SEQUENCE {
  sipxIfIndex
   INTEGER,
  sipxIfNetwork
   OCTET STRING,
  sipxIfFraming
   INTEGER,
  sipxIfInRipPkts
   Counter,
  sipxIfOutRipPkts
   Counter,
  sipxIfInSapPkts
   Counter,
  sipxIfOutSapPkts
   Counter
 }

sipxIfIndex OBJECT-TYPE
 SYNTAX  INTEGER
 ACCESS  read-only
 STATUS  mandatory
 DESCRIPTION
  "Used to index through the interfaces (ports) on the ES/1,
  when used as an IPX router. Identical to ifIndex. Entries
  exist for all external interfaces, whether or not they
  are actually populated or configured for IPX routing."
 ::= { sipxIfEntry 1 }

sipxIfNetwork OBJECT-TYPE
 SYNTAX  OCTET STRING
 ACCESS  read-write
 STATUS  mandatory
 DESCRIPTION
  "The IPX network number associated with this interface."
 ::= { sipxIfEntry 2 }

sipxIfFraming OBJECT-TYPE
 SYNTAX  INTEGER { ethernet8023(1), ethernet2(2), ieee8022(3), snap(4), rawfddi(5), ppp(6) }
 ACCESS  read-write
 STATUS  mandatory
 DESCRIPTION
  "Defines the link-level framing to be used for this interface.
  Options 1-4 are available for Ethernet; options 3 and 4 are
  valid for token ring; options 3-5 are valid for FDDI links."
 ::= { sipxIfEntry 3 }

sipxIfInRipPkts OBJECT-TYPE
 SYNTAX  Counter
 ACCESS  read-only
 STATUS  mandatory
 DESCRIPTION
  "Number of IPX Routing Information Protocol packets
  received on this interface."
 ::= { sipxIfEntry 4 }

sipxIfOutRipPkts OBJECT-TYPE
 SYNTAX  Counter
 ACCESS  read-only
 STATUS  mandatory
 DESCRIPTION
  "Number of IPX Routing Information Protocol packets
  transmitted on this interface."
 ::= { sipxIfEntry 5 }

sipxIfInSapPkts OBJECT-TYPE
 SYNTAX  Counter
 ACCESS  read-only
 STATUS  mandatory
 DESCRIPTION
  "Number of IPX Service Advertising Protocol packets
  received on this interface."
 ::= { sipxIfEntry 6 }

sipxIfOutSapPkts OBJECT-TYPE
 SYNTAX  Counter
 ACCESS  read-only
 STATUS  mandatory
 DESCRIPTION
  "Number of IPX Service Advertising Protocol packets
  transmitted on this interface."
 ::= { sipxIfEntry 7 }


-- the SMC IPX routing table

-- The IPX routing table contains an entry for each route
-- presently known to this router.


sipxRouteTable OBJECT-TYPE
 SYNTAX  SEQUENCE OF SipxRouteEntry
 ACCESS  not-accessible
 STATUS  mandatory
 DESCRIPTION
  "This router's IPX Routing table."
 ::= { sipx 2 }

sipxRouteEntry OBJECT-TYPE
 SYNTAX  SipxRouteEntry
 ACCESS  not-accessible
 STATUS  mandatory
 DESCRIPTION
  "A route to a particular destination."
 INDEX  { sipxRouteDest }
 ::= { sipxRouteTable 1 }

SipxRouteEntry ::=
 SEQUENCE {
  sipxRouteDest
   OCTET STRING,
  sipxRouteIfIndex
   INTEGER,
  sipxRouteTickCount
   INTEGER,
  sipxRouteHopCount
   INTEGER,
  sipxRouteNextHop
   OCTET STRING,
  sipxRouteAge
   INTEGER
 }

sipxRouteDest OBJECT-TYPE
 SYNTAX  OCTET STRING
 ACCESS  read-only
 STATUS  mandatory
 DESCRIPTION
  "The destination network address of this route."
 ::= { sipxRouteEntry 1 }

sipxRouteIfIndex OBJECT-TYPE
 SYNTAX  INTEGER
 ACCESS  read-only
 STATUS  mandatory
 DESCRIPTION
  "The index value which uniquely identifies the
  local interface through which the next hop of this
  route should be reached. The interface identified
  by a particular value of this index is the same
  interface as identified by the same value of
  ifIndex."
 ::= { sipxRouteEntry 2 }

sipxRouteTickCount OBJECT-TYPE
 SYNTAX  INTEGER
 ACCESS  read-only
 STATUS  mandatory
 DESCRIPTION
  "The primary routing metric for this route, which is an
  estimate of the number of 55 millisecond ticks that are
  needed to reach the destination."
 ::= { sipxRouteEntry 3 }

sipxRouteHopCount OBJECT-TYPE
 SYNTAX  INTEGER
 ACCESS  read-only
 STATUS  mandatory
 DESCRIPTION
  "The secondary routing metric for this route, which is the
  number of routers that must be traversed to reach the
  destination."
 ::= { sipxRouteEntry 4 }

sipxRouteNextHop OBJECT-TYPE
 SYNTAX  OCTET STRING
 ACCESS  read-only
 STATUS  mandatory
 DESCRIPTION
  "The IPX node address of the next hop of this route,
  if indirect. If direct, the address of the local
  interface."
 ::= { sipxRouteEntry 5 }

sipxRouteAge OBJECT-TYPE
 SYNTAX  INTEGER
 ACCESS  read-only
 STATUS  mandatory
 DESCRIPTION
  "The number of seconds since this route was last
  updated."
 ::= { sipxRouteEntry 6 }

-- the SMC IPX service table

-- The IPX service table contains an entry for each SAP-cache
-- service presently known to this router.


sipxSapTable OBJECT-TYPE
 SYNTAX  SEQUENCE OF SipxSapEntry
 ACCESS  not-accessible
 STATUS  mandatory
 DESCRIPTION
  "This router's IPX service advertising cache table."
 ::= { sipx 3 }

sipxSapEntry OBJECT-TYPE
 SYNTAX  SipxSapEntry
 ACCESS  not-accessible
 STATUS  mandatory
 DESCRIPTION
  "An IPX service definition, as advertised by the SAP
  protocol and distributed through the SAP cache of
  this router."
 INDEX  { sipxSapIndex }
 ::= { sipxSapTable 1 }

SipxSapEntry ::=
 SEQUENCE {
  sipxSapIndex
   INTEGER,
  sipxSapType
   INTEGER,
  sipxSapName
   OCTET STRING,
  sipxSapNetwork
   OCTET STRING,
  sipxSapNodeId
   OCTET STRING,
  sipxSapSocket
   INTEGER,
  sipxSapHopCount
   INTEGER
 }

sipxSapIndex OBJECT-TYPE
 SYNTAX  INTEGER
 ACCESS  read-only
 STATUS  mandatory
 DESCRIPTION
  "Used only as an artificial index to this table. Has no
  independent meaning."
 ::= { sipxSapEntry 1 }

sipxSapType OBJECT-TYPE
 SYNTAX  INTEGER
 ACCESS  read-only
 STATUS  mandatory
 DESCRIPTION
  "Identifies the type of service provided by the server.
  Values range 0..ffff, and are defined by Novell."
 ::= { sipxSapEntry 2 }

sipxSapName OBJECT-TYPE
 SYNTAX  OCTET STRING
 ACCESS  read-only
 STATUS  mandatory
 DESCRIPTION
  "Server Name."
 ::= { sipxSapEntry 3 }

sipxSapNetwork OBJECT-TYPE
 SYNTAX  OCTET STRING
 ACCESS  read-only
 STATUS  mandatory
 DESCRIPTION
  "The IPX network address of the server providing the
  indicated service."
 ::= { sipxSapEntry 4 }

sipxSapNodeId OBJECT-TYPE
 SYNTAX  OCTET STRING
 ACCESS  read-only
 STATUS  mandatory
 DESCRIPTION
  "The IPX node address of the server. With NetWare 2.x,
  this corresponds to a physical MAC address, represented
  here in canonical (little-endian) bit order. With
  NetWare 3.x, it is typically 00:00:00:00:00:01."
 ::= { sipxSapEntry 5 }

sipxSapSocket OBJECT-TYPE
 SYNTAX  INTEGER
 ACCESS  read-only
 STATUS  mandatory
 DESCRIPTION
  "The socket number to which service requests should be
  addressed."
 ::= { sipxSapEntry 6 }

sipxSapHopCount OBJECT-TYPE
 SYNTAX  INTEGER
 ACCESS  read-only
 STATUS  mandatory
 DESCRIPTION
  "A count of the number of routers that must be traversed
  to reach this server."
 ::= { sipxSapEntry 7 }

sipxDiscardedRoutes OBJECT-TYPE
 SYNTAX  Counter
 ACCESS  read-only
 STATUS  mandatory
 DESCRIPTION
  "A count of the number of received routes that were lost
  due to insufficient resources."
 ::= { sipx 4 }

sipxDiscardedServices OBJECT-TYPE
 SYNTAX  Counter
 ACCESS  read-only
 STATUS  mandatory
 DESCRIPTION
  "A count of the number of received SAP services that were
  lost due to insufficient resources."
 ::= { sipx 5 }

-- IPX SAP Filter
-- SAP filtering is configured by a table. Index to each row
-- is identified by a simple integer. The table defines the service
-- name, service type and a set of filtering criteria to be applied.
-- The filter also includes a list of port and network numbers to
-- which the service should be advertised or prohibited.

--sipxsfGrp OBJECT-TYPE
--  SYNTAX  INTEGER
--  ACCESS  not-accessible
--  STATUS  mandatory
--  DESCRIPTION
--   "NetWare SAP filter group."
--  ::= { sipx 6 }

sipxsfNextIndex OBJECT-TYPE
  SYNTAX  INTEGER
  ACCESS  read-only
  STATUS  mandatory
  DESCRIPTION
   "Next available filter index for adding filters.
   Starting with 1, in sequetianl ascending order."
  ::= { sipxsfGrp 1 }

sipxsfTable OBJECT-TYPE
  SYNTAX  SEQUENCE OF SipxsfEntry
  ACCESS  not-accessible
  STATUS  mandatory
  DESCRIPTION
   "This table defines the filtering criteria to be
   applied to Netware service advertisements. There can
   be no more than one filter per service name. Each
   filter is identified by a simple integer, which
   is more concise than the name if it were to be
   used as an index."
  ::= { sipxsfGrp 2 }

sipxsfEntry OBJECT-TYPE
  SYNTAX  SipxsfEntry
  ACCESS  not-accessible
  STATUS  mandatory
  DESCRIPTION
   "Defines the filtering criteria to be applied to a
   particular service name."
  INDEX { sipxsfIndex }
  ::= { sipxsfTable 1 }

SipxsfEntry ::=
  SEQUENCE {
   sipxsfIndex
    INTEGER,
   sipxsfSAPName
    OCTET STRING,
   sipxsfSAPType
    INTEGER,
   sipxsfAccessMode
    INTEGER,
   sipxsfFilterType
    INTEGER,
   sipxsfPortMap
    OCTET STRING,
   sipxsfNetworks   -- ignored in the first version
    OCTET STRING,
   sipxsfFiltered
    Counter
  }

sipxsfIndex OBJECT-TYPE
  SYNTAX  INTEGER
  ACCESS  read-write
  STATUS  mandatory
  DESCRIPTION
   "Assigned by the configurer to identify this filter.
   This index has no relationship to sipxSapIndex."
  ::= { sipxsfEntry 1 }

sipxsfSAPName OBJECT-TYPE
  SYNTAX  OCTET STRING
  ACCESS  read-write
  STATUS  mandatory
  DESCRIPTION
   "The service name. `*' can be used as wild card character
   which match all names."
  ::= { sipxsfEntry 2 }

sipxsfSAPType OBJECT-TYPE
  SYNTAX  INTEGER
  ACCESS  read-write
  STATUS  mandatory
  DESCRIPTION
   "The service type. Minus one or 65535 indicates all services
    of this name. Otherwise, the values are defined by Novell
   and other service providers (e.g., file server = 4)."
  ::= { sipxsfEntry 3 }

sipxsfAccessMode OBJECT-TYPE
  SYNTAX  INTEGER { permitted(1), denied(2), invalid(3) }
  ACCESS  read-write
  STATUS  mandatory
  DESCRIPTION
   "Permitted(1) allows the service name to be accepted or
   broadcasted. Denied(2) ignores the service name.
   Invalid(3) invalidates the filter entry."
  ::= { sipxsfEntry 4 }

sipxsfFilterType OBJECT-TYPE
  SYNTAX  INTEGER { entry(1), exit(2) }
  ACCESS  read-write
  STATUS  mandatory
  DESCRIPTION
   "If entry(1), filter is for the incoming named service.
   If exit(2), filter is for the outgoing named service."
  ::= { sipxsfEntry 5 }

sipxsfPortMap OBJECT-TYPE
  SYNTAX  OCTET STRING
  ACCESS  read-write
  STATUS  mandatory
  DESCRIPTION
   "A bit map defining port numbers to which the filter
   is applied. Octet 1 specifies port 1 to 8, octet 2
   specifies port 9 to 16, and so on. Within each octet,
   the MSB maps to the lowerest port, and LSB maps to the
   highest port.
   For filters with FilterType entry(1), this parameter
   is ignored."
  ::= { sipxsfEntry 6 }

sipxsfNetworks OBJECT-TYPE
  SYNTAX  OCTET STRING
  ACCESS  read-write
  STATUS  mandatory
  DESCRIPTION
   "A list of network addresses to which the filter is
   applied. Each network address consists of 4 octets
   (i.e. a LONG word). For filter with FilterType
   entry(1), this parameter is ignored. Initial
   implementation also ignores this parameter."
  ::= { sipxsfEntry 7 }

sipxsfFiltered OBJECT-TYPE
  SYNTAX  Counter
  ACCESS  read-only
  STATUS  mandatory
  DESCRIPTION
   "Number of times the service has been filtered."
  ::= { sipxsfEntry 8 }


-- IPXSR (IPX with source route)

-- sipxsrGrp OBJECT-TYPE
-- SYNTAX INTEGER
-- ACCESS not-accessible
-- STATUS mandatory
-- DESCRIPTION
--  "NetWare IPX with Source Routing."
-- ::= { sipx 7 }

sipxsrAgingTime OBJECT-TYPE
 SYNTAX INTEGER
 ACCESS read-write
 STATUS mandatory
 DESCRIPTION
  "IPX source route cache age time, in seconds."
 ::= { sipxsrGrp 1 }

sipxsrExplorerTable OBJECT-TYPE
 SYNTAX SEQUENCE OF SipxsrExplorerEntry
 ACCESS not-accessible
 STATUS mandatory
 DESCRIPTION
  "IPX SR explorer configuration Table."
 ::= { sipxsrGrp 2 }

sipxsrExplorerEntry OBJECT-TYPE
 SYNTAX SipxsrExplorerEntry
 ACCESS not-accessible
 STATUS mandatory
 DESCRIPTION
  "IPX SR explorer configuration for each port."
 INDEX { sipxsrPort }
 ::= { sipxsrExplorerTable 1 }

SipxsrExplorerEntry ::=
 SEQUENCE {
  sipxsrPort
   INTEGER,
  sipxsrStatus
   INTEGER,
  sipxsrExplorerType
   INTEGER
 }

sipxsrPort OBJECT-TYPE
 SYNTAX INTEGER
 ACCESS read-write
 STATUS mandatory
 DESCRIPTION
  "Port number."
 ::= { sipxsrExplorerEntry 1 }

sipxsrStatus OBJECT-TYPE
 SYNTAX INTEGER { valid(1), invalid(2) }
 ACCESS read-write
 STATUS mandatory
 DESCRIPTION
  "valid(1) to configure explorer type; invalid(2) to remove
   explorer configuration and default to STE."
 ::= { sipxsrExplorerEntry 2 }

sipxsrExplorerType OBJECT-TYPE
 SYNTAX INTEGER { are(1), ste(2) }
 ACCESS read-write
 STATUS mandatory
 DESCRIPTION
  "use ARE or STE for explorer frame."
 ::= { sipxsrExplorerEntry 3 }

srtrdiscTable OBJECT-TYPE
     SYNTAX  SEQUENCE OF SrtrdiscEntry
     ACCESS  not-accessible
     STATUS  mandatory
     DESCRIPTION
          "This table contains configuration information controlling
           operation of the router discovery protocol (RFC-1256)."
     ::= { srtrdisc 1 }

srtrdiscEntry OBJECT-TYPE
     SYNTAX  SrtrdiscEntry
     ACCESS  not-accessible
     STATUS  mandatory
     DESCRIPTION
          "Each entry in this table configures the router discovery
           protocol for the particular interface."
     INDEX { srtrdiscIfIndex }
     ::= { srtrdiscTable 1 }

SrtrdiscEntry ::=
     SEQUENCE {
          srtrdiscIfIndex
             INTEGER,
          srtrdiscState
             INTEGER,
          srtrdiscAdvertisementAddress
             INTEGER,
          srtrdiscAdvertisementInterval
             INTEGER,
          srtrdiscLifetime
             INTEGER,
          srtrdiscPreference
             INTEGER
     }

srtrdiscIfIndex OBJECT-TYPE
     SYNTAX  INTEGER
     ACCESS  read-only
     STATUS  mandatory
     DESCRIPTION
          "Identifies the interface (port) to which this entry's
          information belongs. The value of this variable
          corresponds to ifIndex, as well as most of the other
          port identification values in related MIBs."
     ::= { srtrdiscEntry 1 }

srtrdiscState OBJECT-TYPE
     SYNTAX  INTEGER { enabled(1), disabled(2) }
     ACCESS  read-write
     STATUS  mandatory
     DESCRIPTION
          "Specifies whether or not the router discovery protocol is
           in use for this interface. Defaults to disabled(2)."
     ::= { srtrdiscEntry 2 }

srtrdiscAdvertisementAddress OBJECT-TYPE
     SYNTAX  INTEGER { multicast(1), broadcast(2) }
     ACCESS  read-write
     STATUS  mandatory
     DESCRIPTION
          "The IP address to be used for multicast router advertisements
           for this interface. If multicast(1), the all-systems multicast
           224.0.0.1 is used. If broadcast, the limited-broadcast
           255.255.255.255 is used."
     ::= { srtrdiscEntry 3 }

srtrdiscAdvertisementInterval OBJECT-TYPE
     SYNTAX  INTEGER
     ACCESS  read-write
     STATUS  mandatory
     DESCRIPTION
          "The interval at which multicast router advertisements are to be
           transmitted, in seconds. Allowable values range between 4
           and 1800."
     ::= { srtrdiscEntry 4 }

srtrdiscLifetime OBJECT-TYPE
     SYNTAX  INTEGER
     ACCESS  read-write
     STATUS  mandatory
     DESCRIPTION
          "The value to be used for the Lifetime field of router
           advertisements. Values range from srtrdiscAdvertisementInterval to
           9000."
     ::= { srtrdiscEntry 5 }

srtrdiscPreference OBJECT-TYPE
     SYNTAX  INTEGER
     ACCESS  read-write
     STATUS  mandatory
     DESCRIPTION
          "The preferability of this interface's address as a default router,
           relative to other routers on the same subnet."
     ::= { srtrdiscEntry 6 }

    --
    --  The IPM Routing Table
    --

    sipmRouteTable OBJECT-TYPE
        SYNTAX     SEQUENCE OF SipmRouteEntry
        ACCESS   not-accessible
        STATUS     mandatory
        DESCRIPTION
                "The (conceptual) table listing the origin routes that this
                router learns from neighboring routers and from initial
                installations of directly-connected routes. Origin is
                defined to be the subnetwork that can originate multicast
                packets."
        ::= { sipmroute 1 }

    sipmRouteEntry OBJECT-TYPE
        SYNTAX     SipmRouteEntry
        ACCESS   not-accessible
        STATUS     mandatory
        DESCRIPTION
                "An entry (conceptual row) representing information on an
                origin route when IPM is enabled."
        INDEX      { sipmRouteOrigin, sipmRouteOriginMask }
        ::= { sipmRouteTable 1 }

    SipmRouteEntry ::= SEQUENCE {
        sipmRouteOrigin              IpAddress,
        sipmRouteOriginMask          IpAddress,
        sipmRouteGateway             IpAddress,
        sipmRouteMetric              INTEGER,
        sipmRouteAge                 TimeTicks,
        sipmRouteParents             OCTET STRING
    }

    sipmRouteOrigin OBJECT-TYPE
        SYNTAX     IpAddress
        ACCESS read-only
        STATUS     mandatory
        DESCRIPTION
                "The subnetwork address of the origin."
        ::= { sipmRouteEntry 1 }

    sipmRouteOriginMask OBJECT-TYPE
        SYNTAX     IpAddress
        ACCESS read-only
        STATUS     mandatory
        DESCRIPTION
                "The subnetwork mask of the origin."
        ::= { sipmRouteEntry 2 }

    sipmRouteGateway OBJECT-TYPE
        SYNTAX     IpAddress
        ACCESS read-only
        STATUS     mandatory
        DESCRIPTION
                "The next hop gateway toward the origin. This
                object has the value 0.0.0.0 for directly-connected routes."
        ::= { sipmRouteEntry 3 }

    sipmRouteMetric OBJECT-TYPE
        SYNTAX     INTEGER
        ACCESS read-only
        STATUS     mandatory
        DESCRIPTION
                "The distance to this origin in number of hops."
        ::= { sipmRouteEntry 4 }

    sipmRouteAge OBJECT-TYPE
        SYNTAX     TimeTicks
        ACCESS read-write
        STATUS     mandatory
        DESCRIPTION
                "The time left for this origin route before aged out."
        ::= { sipmRouteEntry 5 }

    sipmRouteParents OBJECT-TYPE
        SYNTAX     OCTET STRING
        ACCESS read-only
        STATUS     mandatory
        DESCRIPTION
                "The bitmapped incoming port(s) for which this origin is
                learned. This is an octet string of length 8. The least
                significant bit of the eighth octet is port 0. The least
                significant bit of the seventh octet is port 9 and so on
                up to a maximum of 64 ports."
        ::= { sipmRouteEntry 6 }



    --
    --  The IPM Neighbor Table
    --

    sipmNeighborTable OBJECT-TYPE
        SYNTAX     SEQUENCE OF SipmNeighborEntry
        ACCESS   not-accessible
        STATUS     mandatory
        DESCRIPTION
                "The (conceptual) table listing the neighboring routers
                on each interface port."
        ::= { sipmneighbor 1 }

    sipmNeighborEntry OBJECT-TYPE
        SYNTAX     SipmNeighborEntry
        ACCESS   not-accessible
        STATUS     mandatory
        DESCRIPTION
                "An entry (conceptual row) all neighbors which are learned
                from this local interface port."
        INDEX      { sipmNeighborIfIndex, sipmNeighbors }
        ::= { sipmNeighborTable 1 }

    SipmNeighborEntry ::= SEQUENCE {
        sipmNeighborIfIndex          INTEGER,
        sipmNeighbors                IpAddress,
        sipmNeighborLastHeard        TimeTicks
    }

    sipmNeighborIfIndex OBJECT-TYPE
        SYNTAX     INTEGER
        ACCESS     read-only
        STATUS     mandatory
        DESCRIPTION
                "The ifIndex value of the interface for which this entry
                contains information."
        ::= { sipmNeighborEntry 1 }

    sipmNeighbors OBJECT-TYPE
        SYNTAX     IpAddress
        ACCESS read-only
        STATUS     mandatory
        DESCRIPTION
                "The neighbor's IP address which was learned."
        ::= { sipmNeighborEntry 2 }

    sipmNeighborLastHeard OBJECT-TYPE
        SYNTAX     TimeTicks
        ACCESS read-only
        STATUS     mandatory
        DESCRIPTION
                "The elapsed time since the neighbor was last heard."
        ::= { sipmNeighborEntry 3 }


    --
    --  The IPM Error Statistics
    --

    sipmOutOfMemory OBJECT-TYPE
        SYNTAX     Counter
        ACCESS read-write
        STATUS     mandatory
        DESCRIPTION
                "The number of times IP Multicast routines try to allocate
                memory for routes which failed."
        ::= { sipmstat 1 }

    sipmStatTable OBJECT-TYPE
        SYNTAX     SEQUENCE OF SipmStatEntry
        ACCESS not-accessible
        STATUS     mandatory
        DESCRIPTION
                "The (conceptual) table containing multicast routing
                statistics for IP datagrams on a per port basis."
        ::= { sipmstat 2 }

    sipmStatEntry OBJECT-TYPE
        SYNTAX     SipmStatEntry
        ACCESS not-accessible
        STATUS     mandatory
        DESCRIPTION
                "An entry (conceptual row) containing the multicast routing
                statistic for IP datagrams on a particular port."
        INDEX      { sipmStatIfIndex }
        ::= { sipmStatTable 1 }


    SipmStatEntry ::= SEQUENCE {
        sipmStatIfIndex       INTEGER,
        sipmInBadPackets      Counter,
        sipmCacheMiss         Counter
    }

   sipmStatIfIndex OBJECT-TYPE
        SYNTAX     INTEGER
        ACCESS read-only
        STATUS     mandatory
        DESCRIPTION
                "The interface port number on which corresponding IPM
                statistics gather."
        ::= { sipmStatEntry 1 }

   sipmInBadPackets OBJECT-TYPE
        SYNTAX     Counter
        ACCESS read-write
        STATUS     mandatory
        DESCRIPTION
                "The number of bad packets received which may include
                unknown DVMRP/IGMP messages, short packets, and checksum
                errors."
        ::= { sipmStatEntry 2 }

    sipmCacheMiss OBJECT-TYPE
        SYNTAX     Counter
        ACCESS read-write
        STATUS     mandatory
        DESCRIPTION
                "The number of times IP Multicast packets need to lookup
                a route at the IP layer for determining forwarding path."
        ::= { sipmStatEntry 3 }

    --
    --  The sipckt Table
    --

    sipcktTable OBJECT-TYPE
       SYNTAX    SEQUENCE OF SipcktEntry
       ACCESS    not-accessible
       STATUS    mandatory
       DESCRIPTION
          "Defines attributes of IP circuits. A circuit is defined
           as a binding of a network number to a physical interface."
        ::= { sipckt 1 }

    sipcktEntry OBJECT-TYPE
       SYNTAX    SipcktEntry
       ACCESS    not-accessible
       STATUS    mandatory
       DESCRIPTION
          "Defines the attributes of a binding of IP address and network to
           physical interface."
       INDEX { sipcktIndex, sipcktIpAddress }
       ::= { sipcktTable 1 }

    SipcktEntry ::=
       SEQUENCE {
          sipcktIndex
             INTEGER,
          sipcktIpAddress
             IpAddress,
          sipcktState
             INTEGER,
          sipcktNetMask
             IpAddress,
          sipcktSourceRoute
             INTEGER
        }

    sipcktIndex OBJECT-TYPE
       SYNTAX    INTEGER
       ACCESS    read-write
       STATUS    mandatory
       DESCRIPTION
          "Identifies the physical interface. Identical to ifIndex."
       ::= { sipcktEntry 1 }

    sipcktIpAddress OBJECT-TYPE
       SYNTAX    IpAddress
       ACCESS    read-write
       STATUS    mandatory
       DESCRIPTION
          "Identifies the IP network that is bound to this interface."
       ::= { sipcktEntry 2 }

    sipcktState OBJECT-TYPE
       SYNTAX    INTEGER { valid(1), invalid(2), invalid-all(3), netmask-conflict(4) }
       ACCESS    read-write
       STATUS    mandatory
       DESCRIPTION
          "The status of this binding."
       ::= { sipcktEntry 3 }

    sipcktNetMask OBJECT-TYPE
       SYNTAX    IpAddress
       ACCESS    read-write
       STATUS    mandatory
       DESCRIPTION
          "The subnet mask for the network associated with this address
           binding. If set to 0.0.0.0, will default to standard class
           A/B/C mask, depending on the value of sipcktIpAddress."
       ::= { sipcktEntry 4 }

    sipcktSourceRoute OBJECT-TYPE
       SYNTAX    INTEGER { default(1), sr(2), no-sr(3), both(4) }
       ACCESS    read-write
       STATUS    mandatory
       DESCRIPTION
          "Specifies the behavior of IP routing with respect to (link-layer)
           source routing for this circuit. If default(1) then behavior depends
           on whether the port is token ring or not. If token ring then
           ARP requests are sent both as source-routing explorers and as
           local frames; if not token ring then only local frames are sent.
           If sr(2) then ARP requests are sent as source-routing explorers
           only. If no-sr(3) then ARP requests are sent as local frames only.
           If both(4), ARP requests are sent both as source-routing explorers
           and as local frames.
           Default(1) should be adequate for most uses unless either source
           routing is being used on FDDI, or the ARP traffic is excessive on
           token ring."
       ::= { sipcktEntry 5 }

-- Contains extensions to the standard ipNetToMedia table.
-- Ordinarily, the ipNetToMedia table reflects the ARP
-- cache. Here, it is extended to include other attributes
-- of the ARP cache, notably the token ring source-route.
-- This table is indexed in the same manner as ipNetToMedia,
-- and is meant to be read in parallel with it. As yet,
-- there is no provision in the ES/1 for static definition
-- of source routes, so this table is read-only.

sipNetToMediaTable OBJECT-TYPE
--    SYNTAX  SEQUENCE OF IpNetToMediaEntry - FIXED 01/14/97 cmf -
    SYNTAX  SEQUENCE OF SipNetToMediaEntry
    ACCESS  not-accessible
    STATUS  mandatory
    DESCRIPTION
            "An extension to the standard ipNetToMedia table,
             containing other ARP cache attributes,
             specifically the current source route to the
             destination."
    ::= { ecs-1 22 }

sipNetToMediaEntry OBJECT-TYPE
--    SYNTAX  IpNetToMediaEntry - FIXED 01/14/97 cmf -
    SYNTAX  SipNetToMediaEntry
    ACCESS  not-accessible
    STATUS  mandatory
    DESCRIPTION
            "Each entry contains one IpAddress to `physical'
            address equivalence. Entries in this table exist
            even when there is no source route attached."
    INDEX   { sipNetToMediaIfIndex, sipNetToMediaNetAddress }
    ::= { sipNetToMediaTable 1 }

SipNetToMediaEntry ::=
    SEQUENCE {
        sipNetToMediaIfIndex
            INTEGER,
        sipNetToMediaNetAddress
            IpAddress,
        sipNetToMediaSourceRoute
            OCTET STRING,
        sipNetToMediaAge
            INTEGER
    }

sipNetToMediaIfIndex OBJECT-TYPE
    SYNTAX  INTEGER
    ACCESS  read-only
    STATUS  mandatory
    DESCRIPTION
            "The interface on which this entry's equivalence
            is effective. The interface identified by a
            particular value of this index is the same
            interface as identified by the same value of
            ifIndex."
    ::= { sipNetToMediaEntry 1 }

sipNetToMediaNetAddress OBJECT-TYPE
    SYNTAX  IpAddress
    ACCESS  read-only
    STATUS  mandatory
    DESCRIPTION
            "The IpAddress corresponding to the media-
            dependent `physical' address."
    ::= { sipNetToMediaEntry 2 }

sipNetToMediaSourceRoute OBJECT-TYPE
    SYNTAX  OCTET STRING
    ACCESS  read-only
    STATUS  mandatory
    DESCRIPTION
            "The source route to this destination."
    ::= { sipNetToMediaEntry 3 }

sipNetToMediaAge OBJECT-TYPE
    SYNTAX  INTEGER
    ACCESS  read-only
    STATUS  mandatory
    DESCRIPTION
            "The age, in seconds, of the entry to this destination."
    ::= { sipNetToMediaEntry 4 }

-- SMC SECURE Group

profileTable OBJECT-TYPE
    SYNTAX  SEQUENCE OF ProfileEntry
    ACCESS  not-accessible
    STATUS  mandatory
	  		 DESCRIPTION ""
    ::= { ssecure 1 }

profileEntry OBJECT-TYPE
    SYNTAX  ProfileEntry
    ACCESS  not-accessible
    STATUS  mandatory
    DESCRIPTION
         "There may be up to 16,368 entries.
          A profile consists of up to 16 entries, all with
          the same value for profileIndex.
          and there may be no more than 1,023 profiles.
          Entries are added by setting the profileType
          field to valid(1) - the variables with no
          defval clause will be automatically assigned
          a value based on the key.
          Entries are removed by setting the profileType
          field to invalid(2).  Entries may not be modified
          other than by being added or removed completely."
    INDEX { profileIndex, profileSourceStart, profileSourceEnd, profileDestStart, profileDestEnd }
    ::= { profileTable 1 }

ProfileEntry ::= SEQUENCE {
        profileIndex
            INTEGER,
        profileSourceStart
            INTEGER,
        profileSourceEnd
            INTEGER,
        profileDestStart
            INTEGER,
        profileDestEnd
            INTEGER,
        profileType
            INTEGER
        }

profileIndex OBJECT-TYPE
    SYNTAX  INTEGER
    ACCESS  read-only
    STATUS  mandatory
    DESCRIPTION
         "A value from 1 to 1,023.  All entries with the
          same profileIndex are part of the same profile."
    ::= { profileEntry 1 }

profileSourceStart OBJECT-TYPE
    SYNTAX  INTEGER (1..65535)
    ACCESS  read-only
    STATUS  mandatory
    DESCRIPTION
         "Acceptable lowest value for the source port of
          a UDP or TCP packet."
    ::= { profileEntry 2 }

profileSourceEnd OBJECT-TYPE
    SYNTAX  INTEGER (1..65535)
    ACCESS  read-only
    STATUS  mandatory
    DESCRIPTION
         "Acceptable highest value for the source port of
          a UDP or TCP packet."
    ::= { profileEntry 3 }

profileDestStart OBJECT-TYPE
    SYNTAX  INTEGER (1..65535)
    ACCESS  read-only
    STATUS  mandatory
    DESCRIPTION
         "Acceptable lowest value for the destination port of
          a UDP or TCP packet."
    ::= { profileEntry 4 }

profileDestEnd OBJECT-TYPE
    SYNTAX  INTEGER (1..65535)
    ACCESS  read-only
    STATUS  mandatory
    DESCRIPTION
         "Acceptable highest value for the destination port of
          a UDP or TCP packet."
    ::= { profileEntry 5 }

profileType OBJECT-TYPE
    SYNTAX  INTEGER { valid(1), invalid(2) }
    ACCESS  read-write
    STATUS  mandatory
    -- DEFVAL  { valid(1) }
    	  		 DESCRIPTION ""
::= { profileEntry 6 }

ruleTable OBJECT-TYPE
    SYNTAX  SEQUENCE OF RuleEntry
    ACCESS  not-accessible
    STATUS  mandatory
    	  		 DESCRIPTION ""
::= { ssecure 2 }

ruleEntry OBJECT-TYPE
    SYNTAX  RuleEntry
    ACCESS  not-accessible
    STATUS  mandatory
    DESCRIPTION
         "There may be up to 8,000 entries.
          Rules with 255.255.255.255 for both
          masks are accessed quickly;  other
          rules are accessed less quickly.
          When adding a rule, at least one field
          must be specified, since there
          are defval clauses for most of
          the other fields (the fields without
          defval clauses will be obtained from
          the key itself)."
    INDEX { ruleIndex, ruleSourceIp, ruleDestIp, ruleSourceIpMask, ruleDestIpMask }
    ::= { ruleTable 1 }

RuleEntry ::= SEQUENCE {
        ruleIndex
            INTEGER,
        ruleSourceIp
            IpAddress,
        ruleDestIp
            IpAddress,
        ruleSourceIpMask
            IpAddress,
        ruleDestIpMask
            IpAddress,
        ruleType
            INTEGER,
        ruleUdpProfile
            INTEGER,
        ruleTcpProfile
            INTEGER,
        ruleTcpEstProfile
            INTEGER,
        ruleFilterUdpFragment
            Boolean,
        ruleFilterTcpFragment
            Boolean,
        ruleFilterIpOption
            Boolean,
        ruleAllowIcmp
            Boolean,
        ruleAllowIpWithinIp
            Boolean,
        ruleAllowEgp
            Boolean,
        ruleAllowIgp
            Boolean,
        ruleAllowIgrp
            Boolean,
        ruleAllowOspf
            Boolean,
        ruleAllowAnyOther
            Boolean
        }

ruleIndex OBJECT-TYPE
    SYNTAX  INTEGER
    ACCESS  read-only
    STATUS  mandatory
    DESCRIPTION
         "An ES/1 port number."
    ::= { ruleEntry 1 }

ruleSourceIp OBJECT-TYPE
    SYNTAX  IpAddress
    ACCESS  read-only
    STATUS  mandatory
    DESCRIPTION
         "Source IP address."
    ::= { ruleEntry 2 }

ruleDestIp OBJECT-TYPE
    SYNTAX  IpAddress
    ACCESS  read-only
    STATUS  mandatory
    DESCRIPTION
         "Destination IP address."
    ::= { ruleEntry 3 }

ruleSourceIpMask OBJECT-TYPE
    SYNTAX  IpAddress
    ACCESS  read-only
    STATUS  mandatory
    DESCRIPTION
         "Mask to apply to the packet before comparing to ruleSourceIp."
    ::= { ruleEntry 4 }

ruleDestIpMask OBJECT-TYPE
    SYNTAX  IpAddress
    ACCESS  read-only
    STATUS  mandatory
    DESCRIPTION
         "Mask to apply to the packet before comparing to ruleSourceIp."
    ::= { ruleEntry 5 }

ruleType OBJECT-TYPE
    SYNTAX  INTEGER { valid(1), invalid(2) }
    ACCESS  read-write
    STATUS  mandatory
    -- DEFVAL  { valid(1) }
	  		 DESCRIPTION ""
    ::= { ruleEntry 6 }

ruleUdpProfile OBJECT-TYPE
    SYNTAX  INTEGER (0..1023)
    ACCESS  read-write
    STATUS  mandatory
    DESCRIPTION
         "Which profile to use (i.e., the value of profileIndex) for
          UDP packets.  A value of 0 means no profile, i.e., filter
          all packets.  This rule only applies to packets with a
          fragment offset of zero."
    -- DEFVAL  { 0 }
    ::= { ruleEntry 7 }

ruleTcpProfile OBJECT-TYPE
    SYNTAX  INTEGER (0..1023)
    ACCESS  read-write
    STATUS  mandatory
    DESCRIPTION
         "Which profile to use (i.e., the value of profileIndex) for
          TCP packets for non-established sessions.  A non-established
          session is indicated by neither the ACK nor RST bit being set
          in the TCP packet.  A value of 0 means no profile, i.e., filter
          all packets.  This rule only applies to packets with a
          fragment offset of zero."
    -- DEFVAL  { 0 }
    ::= { ruleEntry 8 }

ruleTcpEstProfile OBJECT-TYPE
    SYNTAX  INTEGER (0..1023)
    ACCESS  read-write
    STATUS  mandatory
    DESCRIPTION
         "Which profile to use (i.e., the value of profileIndex) for
          TCP packets for established sessions.  An established session
          is indicated by the ACK or RST bit being set in the TCP
          packet.  A value of 0 means no profile, i.e., filter
          all packets.  This rule only applies to packets with a
          fragment offset of zero."
    -- DEFVAL  { 0 }
    ::= { ruleEntry 9 }

ruleFilterUdpFragment OBJECT-TYPE
    SYNTAX  Boolean
    ACCESS  read-write
    STATUS  mandatory
    DESCRIPTION
         "Whether to filter UDP packets with a non-zero IP fragment offset."
    -- DEFVAL  { true(1) }
    ::= { ruleEntry 10 }

ruleFilterTcpFragment OBJECT-TYPE
    SYNTAX  Boolean
    ACCESS  read-write
    STATUS  mandatory
    DESCRIPTION
         "Whether to filter TCP packets with a non-zero IP fragment offset."
    -- DEFVAL  { true(1) }
    ::= { ruleEntry 11 }

ruleFilterIpOption OBJECT-TYPE
    SYNTAX  Boolean
    ACCESS  read-write
    STATUS  mandatory
    DESCRIPTION
         "Whether to filter packets with an IP header length of other
          than 5."
    -- DEFVAL  { true(1) }
    ::= { ruleEntry 12 }

ruleAllowIcmp OBJECT-TYPE
    SYNTAX  Boolean
    ACCESS  read-write
    STATUS  mandatory
    DESCRIPTION
         "Whether to forward ICMP packets (IP protocol 1)."
    -- DEFVAL  { true(1) }
    ::= { ruleEntry 13 }

ruleAllowIpWithinIp OBJECT-TYPE
    SYNTAX  Boolean
    ACCESS  read-write
    STATUS  mandatory
    DESCRIPTION
         "Whether to forward IP encapsulated within IP packets
          (IP protocol 4)."
    -- DEFVAL  { false(2) }
    ::= { ruleEntry 14 }

ruleAllowEgp OBJECT-TYPE
    SYNTAX  Boolean
    ACCESS  read-write
    STATUS  mandatory
    DESCRIPTION
         "Whether to forward EGP packets (IP protocol 8)."
    -- DEFVAL  { false(2) }
    ::= { ruleEntry 15 }

ruleAllowIgp OBJECT-TYPE
    SYNTAX  Boolean
    ACCESS  read-write
    STATUS  mandatory
    DESCRIPTION
         "Whether to forward IGP packets (IP protocol 9)."
    -- DEFVAL  { false(2) }
    ::= { ruleEntry 16 }

ruleAllowIgrp OBJECT-TYPE
    SYNTAX  Boolean
    ACCESS  read-write
    STATUS  mandatory
    DESCRIPTION
         "Whether to forward IGP packets (IP protocol 88)."
    -- DEFVAL  { false(2) }
    ::= { ruleEntry 17 }

ruleAllowOspf OBJECT-TYPE
    SYNTAX  Boolean
    ACCESS  read-write
    STATUS  mandatory
    DESCRIPTION
         "Whether to forward OSPF packets (IP protocol 89)."
    -- DEFVAL  { false(2) }
    ::= { ruleEntry 18 }

ruleAllowAnyOther OBJECT-TYPE
    SYNTAX  Boolean
    ACCESS  read-write
    STATUS  mandatory
    DESCRIPTION
         "Whether to forward all other types of IP packets
          (i.e., other than UDP, TCP, ICMP, IP encapsulated,
          EGP, IGP, IGRP, and OSPF)."
    -- DEFVAL  { false(2) }
    ::= { ruleEntry 19 }


-- SMC PVC Group

spvcTable OBJECT-TYPE
 SYNTAX SEQUENCE OF SpvcEntry
 ACCESS not-accessible
 STATUS mandatory
 DESCRIPTION
  "This table maps pseudo-port indices to permanent virtual
   circuits."
 ::= { spvc 1 }

spvcEntry OBJECT-TYPE
 SYNTAX SpvcEntry
 ACCESS not-accessible
 STATUS mandatory
 DESCRIPTION
  "Each entry in this table describes one permanent virtual
  circuit."
 INDEX { spvcIfIndex }
 ::= { spvcTable 1 }

SpvcEntry ::=
 SEQUENCE {
  spvcIfIndex
   INTEGER,
  spvcPathRX
   INTEGER,
  spvcCircuitRX
   INTEGER,
  spvcPathTX
   INTEGER,
  spvcCircuitTX
   INTEGER,
  spvcState
   INTEGER,
  spvcPhysPort
   INTEGER
  }

spvcIfIndex OBJECT-TYPE
 SYNTAX INTEGER
 ACCESS read-only
 STATUS mandatory
 DESCRIPTION
  "Identifies the virtual interface (port) on which this
  virtual circuit exists. The value of this variable
  corresponds to ifIndex, as well as most of the other
  port identification values in related MIBs."
 ::= { spvcEntry 1 }

spvcPathRX OBJECT-TYPE
 SYNTAX INTEGER
 ACCESS read-write
 STATUS mandatory
 DESCRIPTION
  "Where virtual circuit identifiers are split into two
  parts, as in ATM, this is the most-significant part, and
  is identical to the ATM virtual path identifier."
 ::= { spvcEntry 2 }

spvcCircuitRX OBJECT-TYPE
 SYNTAX INTEGER
 ACCESS read-write
 STATUS mandatory
 DESCRIPTION
  "Where virtual circuit identifiers are split into two
  parts, as in ATM, this is the least-significant part, and
  is identical to the ATM virtual circuit identifier."
 ::= { spvcEntry 3 }

spvcPathTX OBJECT-TYPE
 SYNTAX INTEGER
 ACCESS read-write
 STATUS mandatory
 DESCRIPTION
  "Where virtual circuit identifiers are split into two
  parts, as in ATM, this is the most-significant part, and
  is identical to the ATM virtual path identifier."
 ::= { spvcEntry 4 }

spvcCircuitTX OBJECT-TYPE
 SYNTAX INTEGER
 ACCESS read-write
 STATUS mandatory
 DESCRIPTION
  "Where virtual circuit identifiers are split into two
  parts, as in ATM, this is the least-significant part, and
  is identical to the ATM virtual circuit identifier."
 ::= { spvcEntry 5 }

spvcState OBJECT-TYPE
 SYNTAX INTEGER { exists(1), removed(2) }
 ACCESS read-write
 STATUS mandatory
 DESCRIPTION
  "Controls the existence of this table entry."
 ::= { spvcEntry 6 }

spvcPhysPort OBJECT-TYPE
 SYNTAX INTEGER
 ACCESS read-only
 STATUS mandatory
 DESCRIPTION
  "Identifies the physical interface (port) on which this
  virtual circuit exists. The value of this variable
  corresponds to ifIndex, as well as most of the other
  port identification values in related MIBs."
 ::= { spvcEntry 7 }

spvcMinPort OBJECT-TYPE
 SYNTAX INTEGER
 ACCESS read-only
 STATUS mandatory
 DESCRIPTION
  "The lowest-numbered PVC pseudo-port number."
 ::= { spvc 2 }

spvcMaxPort OBJECT-TYPE
 SYNTAX INTEGER
 ACCESS read-only
 STATUS mandatory
 DESCRIPTION
  "The highest-numbered PVC pseudo-port number."
 ::= { spvc 3 }



-- SMC Trunking Group


strunkTable OBJECT-TYPE
 SYNTAX SEQUENCE OF StrunkEntry
 ACCESS not-accessible
 STATUS mandatory
 DESCRIPTION
  "This table describes the trunking status and attributes of
   the interfaces that are configured for bridge trunking."
 ::= { strunk 1 }

strunkEntry OBJECT-TYPE
 SYNTAX StrunkEntry
 ACCESS not-accessible
 STATUS mandatory
 DESCRIPTION
  "An entry exists in this table for each physical interface
   (port) that is configured for trunking."
 INDEX { strunkIfIndex }
 ::= { strunkTable 1 }

 StrunkEntry ::=
  SEQUENCE {
   strunkIfIndex
    INTEGER,
   strunkState
    INTEGER,
   strunkRemoteBridgeAddr
    OCTET STRING,
   strunkRemoteIp
    IpAddress,
   strunkLastError
    INTEGER,
   strunkLinkOrdinal
    INTEGER,
   strunkLinkCount
    INTEGER,
   strunkLastChange
    INTEGER
   }

strunkIfIndex OBJECT-TYPE
 SYNTAX INTEGER
 ACCESS read-only
 STATUS mandatory
 DESCRIPTION
  "Identifies a physical interface (port) which is
  configured for LAN trunking. The value of this variable
  corresponds to ifIndex, as well as most of the other
  port identification values in related MIBs."
 ::= { strunkEntry 1 }

strunkState OBJECT-TYPE
 SYNTAX INTEGER { off(1),
                      closed(2),
                      oneway(3),
                      joined(4),
                      perturbed(5),
                      helddown(6),
                      broken(7) }
 ACCESS read-only
 STATUS mandatory
 DESCRIPTION
   "If off(1) then this link has not been enabled for trunking.
   If closed(2) then this link has not yet received any Trunking
   PDUs. If oneway(3) then incoming Trunking PDUs do not indicate
   that our PDUs are being successfully received by the far end.
   If joined(4) then this link is actively participating in the
   trunk group. If perturbed(5) then this link is actively
         participating in the trunk group; however, the transmission of
         data packets has been temporarily stopped due to a change in
         membership of the group. If helddown(6) then an error has been
   detected and the link is being held out-of-service until the error
   clears. If broken(7) then this link has been configured for trunking,
         but the port is physically non-operational."
 ::= { strunkEntry 2 }

strunkRemoteBridgeAddr OBJECT-TYPE
 SYNTAX OCTET STRING
 ACCESS read-only
 STATUS mandatory
 DESCRIPTION
  "The MAC address portion of the bridge ID of the remote bridge."
 ::= { strunkEntry 3 }

strunkRemoteIp OBJECT-TYPE
 SYNTAX IpAddress
 ACCESS read-only
 STATUS mandatory
 DESCRIPTION
  "The IP address of the remote bridge, as reported by that
   bridge for administrative purposes."
 ::= { strunkEntry 4 }

strunkLastError OBJECT-TYPE
 SYNTAX INTEGER { none(1),
                      in-bpdu(2),
                      multiple-bridges(3),
                      ack-lost(4),
                      standby(5),
                      too-many-groups(6),
                      no-ack(7),
                      perturbed-threshold(8),
       self-connect(9),
        port-moved(10),
        multiple-lan-types(11) }
 ACCESS read-only
 STATUS mandatory
 DESCRIPTION
  "The last reason for failure when the link is in closed, oneway, or
         helddown state."
 ::= { strunkEntry 5 }

strunkLinkOrdinal OBJECT-TYPE
 SYNTAX INTEGER
 ACCESS read-only
 STATUS mandatory
 DESCRIPTION
  "The position of this link within the trunk group."
 ::= { strunkEntry 6 }

strunkLinkCount OBJECT-TYPE
 SYNTAX INTEGER
 ACCESS read-only
 STATUS mandatory
 DESCRIPTION
  "The number of links within the trunk group."
 ::= { strunkEntry 7 }

strunkLastChange OBJECT-TYPE
 SYNTAX INTEGER
 ACCESS read-only
 STATUS mandatory
 DESCRIPTION
  "The number of seconds since strunkState changed."
 ::= { strunkEntry 8 }

-- SMC AppleTalk extension MIB

atextsysOperState OBJECT-TYPE
 SYNTAX INTEGER {
      off(1),
      on(2)
 }
 ACCESS read-write
 STATUS mandatory
 DESCRIPTION
 "The operational state of AppleTalk routing."
 ::= { atextsystem 1 }

atextportTable OBJECT-TYPE
 SYNTAX SEQUENCE OF AtextportEntry
 ACCESS not-accessible
 STATUS mandatory
 DESCRIPTION
     "A list of AppleTalk ports for this entity."
 ::= { atextport 1 }

atextportEntry OBJECT-TYPE
 SYNTAX AtextportEntry
 ACCESS not-accessible
 STATUS mandatory
 DESCRIPTION
     "The description of one of the AppleTalk
     ports on this entity."
 INDEX { atextportIndex }
 ::= { atextportTable 1 }

AtextportEntry ::= SEQUENCE {
 atextportIndex        INTEGER,
 atextportNetStart     OCTET STRING,
 atextportNetEnd       OCTET STRING,
 atextportNetAddress   OCTET STRING,
 atextportZone  OCTET STRING
}

atextportIndex OBJECT-TYPE
 SYNTAX INTEGER
 ACCESS read-only
 STATUS mandatory
 DESCRIPTION
     "A unique value for each AppleTalk port.
     Its value is between 1 and the total number of
     AppleTalk ports. The value for each port must
     remain constant at least from the
     re-initialization of the entity's network
     management system to the next
     re-initialization."
 ::= { atextportEntry 1 }

atextportNetStart OBJECT-TYPE
 SYNTAX OCTET STRING
 ACCESS read-only
 STATUS mandatory
 DESCRIPTION
     "The first AppleTalk network address in the
     configured range for this port. This is a two octet
     DDP network address in network byte order."
 ::= { atextportEntry 2 }

atextportNetEnd OBJECT-TYPE
 SYNTAX OCTET STRING
 ACCESS read-only
 STATUS mandatory
 DESCRIPTION
     "The last AppleTalk network address in the
     configured range for this port. This is a two octet
     DDP network address in network byte order. "
 ::= { atextportEntry 3 }

atextportNetAddress OBJECT-TYPE
 SYNTAX OCTET STRING
 ACCESS read-only
 STATUS mandatory
 DESCRIPTION
     "The AppleTalk network address configured for this
     port."
 ::= { atextportEntry 4 }

atextportZone OBJECT-TYPE
 SYNTAX OCTET STRING
 ACCESS read-only
 STATUS mandatory
 DESCRIPTION
     "The default zone name configured for this AppleTalk
     port."
 ::= { atextportEntry 5 }

atextportzipTable OBJECT-TYPE
 SYNTAX SEQUENCE OF AtextportzipEntry
 ACCESS not-accessible
 STATUS mandatory
 DESCRIPTION
     "The table of zone information configured
     for a port."
 ::= { atextport 2 }

atextportzipEntry OBJECT-TYPE
 SYNTAX AtextportzipEntry
 ACCESS not-accessible
 STATUS mandatory
 DESCRIPTION
     "An entry of zone information for a particular
     zone and port combination."
 INDEX { atextportZonePort, atextportZoneIndex }
 ::= { atextportzipTable 1 }

-- Atextportzipentry ::= SEQUENCE { - FIXED 01/14/97 cmf -
AtextportzipEntry ::= SEQUENCE {
    atextportZonePort     INTEGER,
    atextportZoneIndex    INTEGER,
    atextportZoneName     OCTET STRING
}

atextportZonePort OBJECT-TYPE
 SYNTAX INTEGER
 ACCESS read-only
 STATUS mandatory
 DESCRIPTION
     "A unique value for each AppleTalk port."
 ::= { atextportzipEntry 1 }

atextportZoneIndex OBJECT-TYPE
 SYNTAX INTEGER
 ACCESS read-only
 STATUS mandatory
 DESCRIPTION
     "An integer that is unique to the ZoneName
     that is present in this entry. For any given
     zone name, every Entry that has an equal zone
     name will have the same ZoneIndex."
 ::= { atextportzipEntry 2 }

atextportZoneName OBJECT-TYPE
 SYNTAX OCTET STRING
 ACCESS read-only
 STATUS mandatory
 DESCRIPTION
     "The ASCII zone name of this entry."
 ::= { atextportzipEntry 3 }

-- Event logging group

slogFilter OBJECT-TYPE
 SYNTAX OCTET STRING
 ACCESS read-write
 STATUS mandatory
 DESCRIPTION
  "The current event logging filter, represented as a bitmask."
 ::= { slog 1 }

slogTrap OBJECT-TYPE
 SYNTAX INTEGER { enabled(1), disabled(2) }
 ACCESS read-write
 STATUS mandatory
 DESCRIPTION
  "When enabled, logging entries will cause SNMP traps to be generated."
 ::= { slog 2 }

slogOverwrite OBJECT-TYPE
 SYNTAX INTEGER { enabled (1), disabled(2) }
 ACCESS read-write
 STATUS mandatory
 DESCRIPTION
  "When enabled, logging entries will be overwritten in the logging queue.
   When disabled, the entries in the logging queue will not be overwritten
   until someone reads them."
 ::= { slog 3 }

slogEntryNumber OBJECT-TYPE
 SYNTAX INTEGER
 ACCESS read-only
 STATUS mandatory
 DESCRIPTION
  "The number of entries in the logging entry table."
 ::= { slog 4 }

slogEntryTable OBJECT-TYPE
 SYNTAX SEQUENCE OF SlogEntry
 ACCESS not-accessible
 STATUS mandatory
 DESCRIPTION
  "This table contains the event logging entries."
 ::= { slog 5 }

slogEntry  OBJECT-TYPE
 SYNTAX  SlogEntry
 ACCESS not-accessible
 STATUS mandatory
	  		 DESCRIPTION ""
 INDEX { slogIndex }
 ::= { slogEntryTable 1 }

SlogEntry ::= SEQUENCE {
 slogIndex
  INTEGER,
    slogEntryTimeStamp
  TimeTicks,
 slogEntryMessageText
  DisplayString,
 slogEntryName
  DisplayString
 }

slogIndex OBJECT-TYPE
 SYNTAX INTEGER
 ACCESS read-only
 STATUS mandatory
 DESCRIPTION
  "The index of the logging entry in the logging entry table."
 ::= { slogEntry 1 }

slogEntryTimeStamp OBJECT-TYPE
 SYNTAX TimeTicks
 ACCESS read-only
 STATUS mandatory
 DESCRIPTION
  "The time at which the event logging entry was generated."
 ::= { slogEntry 2 }

slogEntryMessageText OBJECT-TYPE
 SYNTAX  DisplayString
 ACCESS  read-only
 STATUS mandatory
 DESCRIPTION
  "The text of the eventlogging entry message."
 ::= { slogEntry 3 }

slogEntryName OBJECT-TYPE
 SYNTAX  DisplayString
 ACCESS  read-only
 STATUS mandatory
 DESCRIPTION
  "The name of the event logging entry."
 ::= { slogEntry 4 }

    -- Trap Management MIB

strapControlTable OBJECT-TYPE
 SYNTAX   SEQUENCE OF StrapControl
 ACCESS  not-accessible
 STATUS  mandatory
 DESCRIPTION
  "This table contains information about the severity of each trap
  and whether the trap is currently enabled."
    ::= { strap 1 }

strapControl OBJECT-TYPE
 SYNTAX  StrapControl
    ACCESS   not-accessible
 STATUS  mandatory
	  		 DESCRIPTION ""
 INDEX  { strapIndex }
 ::= { strapControlTable 1 }

StrapControl ::= SEQUENCE {
 strapIndex
  INTEGER,
 strapEnabled
  INTEGER,
 strapSeverity
  INTEGER,
 strapText
  DisplayString
}

strapIndex OBJECT-TYPE
 SYNTAX  INTEGER
 ACCESS  read-only
 STATUS  mandatory
 DESCRIPTION
  "The specific trap number."
    ::= { strapControl 1 }

strapEnabled OBJECT-TYPE
 SYNTAX  INTEGER { true(1), false(2) }
 ACCESS  read-write
 STATUS  mandatory
 DESCRIPTION
  "Enable or disable the generation of this trap."
    ::= { strapControl 2 }

strapSeverity OBJECT-TYPE
 SYNTAX  INTEGER {
   informational(1),
   warning(2),
   minor(3),
   major(4),
   critical(5) }
 ACCESS  read-write
 STATUS  mandatory
 DESCRIPTION
  "A user-definable severity, indicating the importance of the
   trap."
 ::= { strapControl 3 }

strapText OBJECT-TYPE
 SYNTAX  DisplayString
 ACCESS  read-only
 STATUS  mandatory
 DESCRIPTION
  "A description of the trap."
 ::= { strapControl 4 }

strapSeverityControlTable OBJECT-TYPE
 SYNTAX   SEQUENCE OF StrapSeverityControl
 ACCESS  not-accessible
 STATUS  mandatory
 DESCRIPTION
  "This table contains information about the whether a class of
  traps of a particular severity are enabled or disabled."
 ::= { strap 2 }

strapSeverityControl OBJECT-TYPE
 SYNTAX  StrapSeverityControl
 ACCESS   not-accessible
 STATUS  mandatory
 	  		 DESCRIPTION ""
 INDEX  { strapSeveritySeverity }
::= { strapSeverityControlTable 1 }

StrapSeverityControl ::= SEQUENCE {
 strapSeveritySeverity
  INTEGER,
 strapSeverityEnable
  INTEGER
}

strapSeveritySeverity OBJECT-TYPE
 SYNTAX  INTEGER {
   informational(1),
   warning(2),
   minor(3),
   major(4),
   critical(5) }
 ACCESS  read-only
 STATUS  mandatory
 DESCRIPTION
  "A user-definable severity, indicating the importance of the
   trap."
 ::= { strapSeverityControl 1 }

strapSeverityEnable OBJECT-TYPE
 SYNTAX  INTEGER { enabled(1), disabled(2) }
 ACCESS  read-write
 STATUS  mandatory
 DESCRIPTION
  "Enable or disable all traps of a given severity level."
    ::= { strapSeverityControl 2 }

strapIncludeText OBJECT-TYPE
 SYNTAX   INTEGER { true(1), false(2) }
 ACCESS   read-write
 STATUS  mandatory
 DESCRIPTION
  "Whether or not a formatted text string is included in the trap
  PDU."
    ::= { strap 3 }

strapTime OBJECT-TYPE
 SYNTAX  TimeTicks
    ACCESS  read-write
 STATUS  mandatory
 DESCRIPTION
  "(This MIB variable replaces sysTrapTime). The time, in
  centiseconds, which should expire between the sending of traps."
 -- DEFVAL {100}
 ::= { strap 4 }

strapRetry OBJECT-TYPE
 SYNTAX  INTEGER
 ACCESS  read-write
 STATUS  mandatory
 DESCRIPTION
  "The number of times any enterprise-specific trap is to be sent
  for a given event. PDUs are retried using a truncated
  exponential backoff: 2 seconds, 4 seconds, 8 seconds, 16 seconds,
  and then 32 seconds for all succeeding intervals."
 -- DEFVAL {1}
 ::= { strap 5 }

strapEntryNumber OBJECT-TYPE
 SYNTAX  INTEGER
 ACCESS  read-only
 STATUS  mandatory
 DESCRIPTION
     "The number of traps that are in the strapTable."
    ::= { strap 6 }

strapTable OBJECT-TYPE
 SYNTAX   SEQUENCE OF StrapEntry
 ACCESS  not-accessible
 STATUS  mandatory
 DESCRIPTION
  "This table contains the latest traps that have been generated."
 ::= { strap 7 }

strapEntry OBJECT-TYPE
 SYNTAX  StrapEntry
 ACCESS   not-accessible
    STATUS  mandatory
 	  		 DESCRIPTION ""
 INDEX  { strapEntryIndex }
 ::= { strapTable 1 }

StrapEntry ::= SEQUENCE {
 strapEntryIndex
  INTEGER,
 strapEntryTimeStamp
  TimeTicks,
 strapEntryText
  DisplayString,
 strapNumber
  INTEGER,
 strapEntrySeverity
  INTEGER
}

strapEntryIndex OBJECT-TYPE
 SYNTAX  INTEGER
 ACCESS  read-only
    STATUS  mandatory
 DESCRIPTION
  "A number representing the order in which the trap occurred
  in time. This 32 bit number can wrap."
    ::= { strapEntry 1 }

strapEntryTimeStamp OBJECT-TYPE
 SYNTAX  TimeTicks
 ACCESS  read-only
 STATUS  mandatory
 DESCRIPTION
  "The time at which the trap occurred."
 ::= { strapEntry 2 }

strapEntryText OBJECT-TYPE
 SYNTAX  DisplayString
 ACCESS  read-only
 STATUS  mandatory
 DESCRIPTION
  "A description of the trap."
 ::= { strapEntry 3 }

strapNumber OBJECT-TYPE
 SYNTAX   INTEGER
 ACCESS  read-only
 STATUS  mandatory
 DESCRIPTION
  "The specific-trap number, as specified in the TRAP PDU."
 ::= { strapEntry 4 }

strapEntrySeverity OBJECT-TYPE
 SYNTAX  INTEGER {
   informational(1),
   warning(2),
   minor(3),
   major(4),
   critical(5) }
 ACCESS  read-only
 STATUS  mandatory
 DESCRIPTION
  "A user-definable severity, indicating the importance of the
   trap."
 ::= { strapEntry 5 }

--  smirror specifies the ATX port mirroring configuration.
--
--  For local mirroring, the diagnostic port must be a valid port number
--  that is greater than 1.
--  For mirroring to a remote ATX, a valid IP address must be specified,
--  and the diagnostic port should be 0.
--  On  the remote receiving ATX, both IP address and target ports should
--  be  zero, and the diagnostic port must be a  valid  port number that is
--  greater 1.

smirrorStatus OBJECT-TYPE
     SYNTAX INTEGER { invalid(1), local(2), remote(3) }
     ACCESS read-write
     STATUS mandatory
     DESCRIPTION
          "invalid(1) to turn off port mirroring.
           local(2) to mirror either to a local port or to a remote ATX.
           remote(3) to mirror traffics from a remote ATX to a local
           port."
     ::= { smirror 1 }

smirrorDiagPort OBJECT-TYPE
     SYNTAX INTEGER
     ACCESS read-write
     STATUS mandatory
     DESCRIPTION
          "This entry defines the diagnostic port to output
           mirrored packets.  It can be one of the Ethernet,
           Token Ring or FDDI interfaces in the ATX."
     ::= { smirror 2 }

smirrorIPaddr OBJECT-TYPE
     SYNTAX IpAddress
     ACCESS read-write
     STATUS mandatory
     DESCRIPTION
          "This entry defines the IP address for remote
           mirroring.  It must be a valid host address."
     ::= { smirror 3 }

smirrorTargetPortLists OBJECT-TYPE
     SYNTAX OCTET STRING
     ACCESS read-write
     STATUS mandatory
     DESCRIPTION
          "An octet string specifies the list of ports to be
           mirrored, with each octet representing a  single port
           number."
     ::= { smirror 4 }

smirrorOversizePkt OBJECT-TYPE
     SYNTAX INTEGER { discard(1), truncate(2) }
     ACCESS read-write
     STATUS mandatory
     DESCRIPTION
            "Specified   whether  to  discard  or   truncate oversized
            mirrored packets."
     ::= { smirror 5 }

smirrorEntryMirroredPkts OBJECT-TYPE
     SYNTAX Counter
     ACCESS read-only
     STATUS mandatory
     DESCRIPTION
          "Number of entry packets mirrored."
     ::= { smirror 6 }

smirrorExitMirroredPkts OBJECT-TYPE
     SYNTAX Counter
     ACCESS read-only
     STATUS mandatory
     DESCRIPTION
          "Number of exit packets mirrored."
   ::= { smirror 7 }

smirrorNotreadyDroppedPkts OBJECT-TYPE
     SYNTAX Counter
     ACCESS read-only
     STATUS mandatory
     DESCRIPTION
          "Number of packets not mirrored either because the
           diagnostic port is not ready (local mirroring) or
           the  tunnel  to remote ATX is not ready  (remote
     mirroring)."
     ::= { smirror 8 }


smirrorOversizeDroppedPkts OBJECT-TYPE
     SYNTAX  Counter
     ACCESS read-only
     STATUS mandatory
     DESCRIPTION
          "Number of oversized packets not mirrored."
     ::= { smirror 9 }

smirrorEntryFilteredPkts OBJECT-TYPE
     SYNTAX Counter
     ACCESS read-only
     STATUS mandatory
     DESCRIPTION
          "Number of entry packets filtered."
     ::= { smirror 10 }

smirrorExitFilteredPkts OBJECT-TYPE
     SYNTAX Counter
     ACCESS read-only
     STATUS mandatory
     DESCRIPTION
          "Number of exit packets filtered."
     ::= { smirror 11 }

smirrorCongestionDroppedPkts OBJECT-TYPE
     SYNTAX Counter
     ACCESS read-only
     STATUS mandatory
     DESCRIPTION
          "Number of packets not mirrored due to exit port
           congestion."
     ::= { smirror 12 }

smirrorNowrapperDroppedPkts OBJECT-TYPE
     SYNTAX Counter
     ACCESS read-only
     STATUS mandatory
     DESCRIPTION
          "Number of packets not mirrored due to shortage of
           wrapper  buffers (in mirroring frames to  remote ATX)."
     ::= { smirror 13 }

smirrorRemoteStatus OBJECT-TYPE
     SYNTAX INTEGER {
          mirrorOff(0),
          handshakeInProgress(1),
          arpRefreshInProgress(2),
          remoteHostUnreachable(3),
          mirroring(6),
          versionIncompatible(7),
          remoteDiagnosticPortBroken(8),
          remoteMirrorNotOn(9)
     }
     ACCESS read-only
     STATUS mandatory
     DESCRIPTION
          "Status when mirroring to remote ATX."
     ::= { smirror 14 }

smirrorRemoteExitPort OBJECT-TYPE
     SYNTAX INTEGER
     ACCESS read-only
     STATUS mandatory
     DESCRIPTION
          "Mirrored packets exit port number to remote ATX."
     ::= { smirror 15 }


    -- SMC Workgroup Group

sWorkGroupNextNumber OBJECT-TYPE
    SYNTAX  INTEGER
    ACCESS  read-only
    STATUS  mandatory
    DESCRIPTION
        "The next available workgroup number to be used.  When creating
         a new workgroup, it is recommended to read the value of the variable
         and use it to key into the workgroup table."
    ::= { sworkgroup 1 }

sWorkGroupCurrentCount OBJECT-TYPE
    SYNTAX  INTEGER
    ACCESS  read-only
    STATUS  mandatory
    DESCRIPTION
        "The total number of workgroups currently defined."
    ::= { sworkgroup 2 }

sWorkGroupMaxCount OBJECT-TYPE
    SYNTAX  INTEGER
    ACCESS  read-only
    STATUS  mandatory
    DESCRIPTION
        "The maximum number of workgroups allowed."
    ::= { sworkgroup 3 }

sWorkGroupTable OBJECT-TYPE
    SYNTAX  SEQUENCE OF SWorkGroupEntry
    ACCESS  not-accessible
    STATUS  mandatory
    DESCRIPTION
        "This table contains work group definitions for the interfaces."
    ::= { sworkgroup 4 }

sWorkGroupEntry OBJECT-TYPE
    SYNTAX  SWorkGroupEntry
    ACCESS  not-accessible
    STATUS  mandatory
    DESCRIPTION
        "Each entry in this table contains a definition of a work group."
    INDEX   { sWorkGroupNumber }
    ::= { sWorkGroupTable 1 }

    SWorkGroupEntry ::=
        SEQUENCE {
            sWorkGroupNumber
                INTEGER,
            sWorkGroupName
                DisplayString,
            sWorkGroupPorts
                OCTET STRING,
            sWorkGroupType
                INTEGER,
            sWorkGroupIpAddress
                IpAddress,
            sWorkGroupIpMask
                IpAddress,
            sWorkGroupIpxNetwork
                OCTET STRING
            }

sWorkGroupNumber OBJECT-TYPE
    SYNTAX  INTEGER
    ACCESS  read-write
    STATUS  mandatory
    DESCRIPTION
        "An integer that identifies the work group, used as an index
         to this table."
    ::= { sWorkGroupEntry 1 }

sWorkGroupName OBJECT-TYPE
    SYNTAX  DisplayString
    ACCESS  read-write
    STATUS  mandatory
    DESCRIPTION
        "A 1-16 character work group name."
    ::= { sWorkGroupEntry 2 }

sWorkGroupPorts OBJECT-TYPE
    SYNTAX  OCTET STRING
    ACCESS  read-write
    STATUS  mandatory
    DESCRIPTION
        "A list of all ports within the group.  The first
         octet specified ports 1-8, the second 9-16, etc."
    ::= { sWorkGroupEntry 3 }

sWorkGroupType OBJECT-TYPE
    SYNTAX  INTEGER { ip(1),
                      ipx(2),
                      all(3), -- all broadcast packets
                      invalid(4) } -- to delete this group
    ACCESS  read-write
    STATUS  mandatory
    DESCRIPTION
        "The type of work group:
         all - no additional information needs to be supplied.
         ip - the IP network (and optionally, IP mask) must be supplied.
         ipx - the IPX network number may be supplied, or else all IPX
               network number will be assumed."
    ::= { sWorkGroupEntry 4 }

sWorkGroupIpAddress OBJECT-TYPE
    SYNTAX  IpAddress
    ACCESS  read-write
    STATUS  mandatory
    DESCRIPTION
        "The IP network address."
    ::= { sWorkGroupEntry 5 }

sWorkGroupIpMask OBJECT-TYPE
    SYNTAX  IpAddress
    ACCESS  read-write
    STATUS  mandatory
    DESCRIPTION
        "The IP network mask, if set to 0, the default network mask is applied."
    ::= { sWorkGroupEntry 6 }

sWorkGroupIpxNetwork OBJECT-TYPE
    SYNTAX  OCTET STRING
    ACCESS  read-write
    STATUS  mandatory
    DESCRIPTION
        "The IPX network number, 0 means all networks."
    ::= { sWorkGroupEntry 7 }

    -- SMC Ping Group

spingDataTimeout OBJECT-TYPE
    SYNTAX  TimeTicks
    ACCESS  read-write
    STATUS  mandatory
    DESCRIPTION
        "The time, in centiseconds, from the last ping activity (a send
         or receive of an ECHO_RESPONSE or ECHO_REQUEST message), to when
         the spingEntry information for that ping request will be deleted."
    ::= { sping 1 }

spingTable OBJECT-TYPE
    SYNTAX  SEQUENCE OF SpingEntry
    ACCESS  not-accessible
    STATUS  mandatory
    DESCRIPTION
        "The set of information describing the active ping requests and
         their results."
    ::= { sping 2 }

spingEntry OBJECT-TYPE
    SYNTAX  SpingEntry
    ACCESS  not-accessible
    STATUS  mandatory
    DESCRIPTION
        "The parameters, state and results of a ping request."
    INDEX {spingNMSAddr, spingDestAddr }
    ::= { spingTable 1 }

SpingEntry ::= SEQUENCE {
    spingNMSAddr
        IpAddress,
    spingDestAddr
        IpAddress,
    spingState
        INTEGER,
    spingCount
        INTEGER,
    spingDataSize
        INTEGER,
    spingWait
        TimeTicks,
--    spingTimeOut - FIXED 01/14/97 cmf -
    spingTimeout
        TimeTicks,
    spingOperation
        INTEGER,
    spingMin
        TimeTicks,
    spingMax
        TimeTicks,
    spingAvg
        TimeTicks,
    spingNumTransmitted
        INTEGER,
    spingNumReceived
        INTEGER
    }

spingNMSAddr OBJECT-TYPE
    SYNTAX  IpAddress
 ACCESS  read-only
 STATUS  mandatory
 DESCRIPTION
     "The IP address of the NMS, used to determine which ping
   request to return information on."
 ::= { spingEntry 1 }

spingDestAddr OBJECT-TYPE
 SYNTAX  IpAddress
 ACCESS  read-write
 STATUS  mandatory
 DESCRIPTION
  "The IP address which is to be the destination of the ping
  ECHO_REQUEST. This variable cannot be set while
  spingOperation is on."
 ::= { spingEntry 2 }

spingState OBJECT-TYPE
 SYNTAX  INTEGER {
  not-started(0),
  active(1),
     timed-out(2),
  completed(3) }
 ACCESS  read-only
 STATUS  mandatory
 DESCRIPTION
  "The current state of the ping request. "
 ::= { spingEntry 3 }

spingCount OBJECT-TYPE
 SYNTAX  INTEGER
 ACCESS  read-write
 STATUS  mandatory
 DESCRIPTION
  "The number of ping requests which are to be sent. This
  variable cannot be set while spingOperation is on."
 ::= { spingEntry 4 }

spingDataSize OBJECT-TYPE
 SYNTAX  INTEGER
 ACCESS  read-write
 STATUS  mandatory
 DESCRIPTION
  "The datagram packet size which will be sent with the
  ECHO_REQUEST, in bytes. This variable cannot be set while
  spingOperation is on."
 ::= { spingEntry 5 }

spingWait OBJECT-TYPE
 SYNTAX  TimeTicks
 ACCESS  read-write
 STATUS  mandatory
 DESCRIPTION
  "The time, in centiseconds, between the sending of each
  ECHO_REQUEST message. This variable cannot be set while
  spingOperation is on."
 ::= { spingEntry 6 }

spingTimeout OBJECT-TYPE
 SYNTAX  TimeTicks
 ACCESS  read-write
 STATUS  mandatory
 DESCRIPTION
  "The time, in centiseconds, since the last ECHO_RESPONSE
  was received (or the last ECHO_REQUEST was sent, if there
  have been no responses) when the ping request will time out.
  This variable cannot be set while spingOperation is on."
 ::= { spingEntry 7 }

spingOperation OBJECT-TYPE
 SYNTAX   INTEGER { on(1), off(2) }
 ACCESS  read-write
 STATUS  mandatory
 DESCRIPTION
  "Setting spingOperation to on will begin the ping request.
  Setting spingOperation to off will terminate the ping request."
 ::= { spingEntry 8 }

spingMin OBJECT-TYPE
 SYNTAX  TimeTicks
 ACCESS  read-only
 STATUS  mandatory
 DESCRIPTION
  "The minimum round trip time for the ping requests and
  responses, in centiseconds."
    ::= { spingEntry 9 }

spingMax OBJECT-TYPE
 SYNTAX  TimeTicks
 ACCESS  read-only
 STATUS  mandatory
 DESCRIPTION
  "The maximum round trip for the ping requests and
  responses, in centiseconds."
    ::= { spingEntry 10 }

spingAvg OBJECT-TYPE
 SYNTAX  TimeTicks
 ACCESS  read-only
 STATUS  mandatory
 DESCRIPTION
  "The average round trip time for the ping requests and
  responses, in centiseconds."
 ::= { spingEntry 11 }

spingNumTransmitted OBJECT-TYPE
 SYNTAX  INTEGER
 ACCESS  read-only
 STATUS  mandatory
 DESCRIPTION
  "The number of ICMP ECHO_REQUEST messages that have
  been transmitted during this ping request."
 ::= { spingEntry 12 }

spingNumReceived OBJECT-TYPE
 SYNTAX   INTEGER
 ACCESS  read-only
 STATUS  mandatory
 DESCRIPTION
  "The number of ICMP ECHO_RESPONSE messages that have
  been received as a result of this ping request."
 ::= { spingEntry 13 }

    -- SMC Traceroute Group

straceDataTimeout OBJECT-TYPE
  SYNTAX  TimeTicks
 ACCESS  read-write
 STATUS  mandatory
 DESCRIPTION
  "The time, in centiseconds, from the last traceroute activity (the
  response to or timeout of the last probe sent), to when the
  straceEntry information for that traceroute request will be
  deleted."
  ::= { strace 1 }

straceTable OBJECT-TYPE
 SYNTAX   SEQUENCE OF StraceEntry
 ACCESS  not-accessible
 STATUS  mandatory
 DESCRIPTION
  "The set of information describing the active traceroute requests
  and their results."
 ::= { strace 2 }

straceEntry OBJECT-TYPE
 SYNTAX  StraceEntry
 ACCESS   not-accessible
 STATUS  mandatory
 DESCRIPTION
  "The parameters, state, and results of a traceroute request."
 INDEX  { straceNMSAddr, straceDestAddr, straceHop, straceProbe }
 ::= { straceTable 1 }

StraceEntry ::= SEQUENCE {
 straceNMSAddr
  IpAddress,
 straceDestAddr
  IpAddress,
 straceMaxTTL
  INTEGER,
 straceDataSize
  INTEGER,
 straceNumProbes
  INTEGER,
 straceWait
  TimeTicks,
 straceOperation
  INTEGER,
 straceHop
  INTEGER,
-- straceHopAddr - FIXED 01/14/97 cmf -
 straceHopAddress
  IpAddress,
 straceProbe
  INTEGER,
 straceState
  INTEGER,
 straceTime
  TimeTicks
}

straceNMSAddr OBJECT-TYPE
 SYNTAX  IpAddress
 ACCESS  read-only
 STATUS  mandatory
 DESCRIPTION
  "The IP address of the NMS, used to determine which traceroute
  request to return information on."
 ::= { straceEntry 1 }

straceDestAddr OBJECT-TYPE
 SYNTAX  IpAddress
 ACCESS  read-write
 STATUS  mandatory
 DESCRIPTION
  "The IP address which is to be the destination of the traceroute
  request.This variable cannot be set while straceOperation is on."
 ::= { straceEntry 2 }

straceMaxTTL OBJECT-TYPE
 SYNTAX  INTEGER
 ACCESS  read-write
 STATUS  mandatory
 DESCRIPTION
  "The maximum time-to-live for outgoing traceroute probe
  packets. This determines the number of hops that can be in a
  traceroute. This variable cannot be set while straceOperation
  is on."
    ::= { straceEntry 3 }

straceDataSize OBJECT-TYPE
 SYNTAX  INTEGER
 ACCESS  read-write
 STATUS  mandatory
 DESCRIPTION
  "The size of the datagram sent with each probe. This variable
  cannot be set while straceOperation is on."
 ::= { straceEntry 4 }

straceNumProbes OBJECT-TYPE
 SYNTAX  INTEGER
 ACCESS  read-write
 STATUS   mandatory
 DESCRIPTION
  "The number of probes which are sent for each hop. This
  variable cannot be set while straceOperation is on."
 ::= { straceEntry 5 }

straceWait OBJECT-TYPE
 SYNTAX  TimeTicks
 ACCESS  read-write
 STATUS  mandatory
 DESCRIPTION
  "The time to wait in response to a probe. This variable cannot be
  set while straceOperation is on."
 ::= { straceEntry 6 }

straceOperation OBJECT-TYPE
 SYNTAX   INTEGER { on(1), off(2) }
 ACCESS  read-write
 STATUS  mandatory
 DESCRIPTION
  "Setting straceOperation to on will begin the traceroute request.
  Setting straceOperation to off will terminate the traceroute
  request."
 ::= { straceEntry 7 }

straceHop OBJECT-TYPE
 SYNTAX  INTEGER
 ACCESS  read-only
 STATUS  mandatory
 DESCRIPTION
  "The hop count for a set of probes with a particular TTL."
 ::= { straceEntry 8 }

straceHopAddress OBJECT-TYPE
 SYNTAX  IpAddress
 ACCESS  read-only
 STATUS  mandatory
 DESCRIPTION
  "The IP address of the host which responded for a probe with a
  particular TTL."
 ::= { straceEntry 9 }

straceProbe OBJECT-TYPE
 SYNTAX  INTEGER
 ACCESS  read-only
 STATUS  mandatory
 DESCRIPTION
  "The probe instance for a particular hop."
    ::= { straceEntry 10 }

straceState OBJECT-TYPE
 SYNTAX  INTEGER {
      not-started(0),
      active(1),
      time-exceeded(2),
      host-unreachable(3),
      net-unreachable(4),
      completed(5) }
 ACCESS  read-only
 STATUS  mandatory
 DESCRIPTION
  "The current state of the trace probe."
    ::= { straceEntry 11 }

straceTime OBJECT-TYPE
 SYNTAX  TimeTicks
 ACCESS  read-only
 STATUS  mandatory
 DESCRIPTION
  "Round trip time of a probe for a particular hop."
 ::= { straceEntry 12 }

srtbProto OBJECT-TYPE
 SYNTAX  INTEGER { off(0), ip(1), ipx(2), others(3), all(7) }
 ACCESS  read-write
 STATUS  mandatory
 DESCRIPTION
  "Bit mapped representation of srtb protocol configuration."
 ::= { srtb 1}

srtbExplorer OBJECT-TYPE
 SYNTAX  INTEGER { are(1), ste(2) }
 ACCESS  read-write
 STATUS  mandatory
 DESCRIPTION
  "Type of explorer to transmit."
 ::= { srtb 2 }

srtbAgingTime OBJECT-TYPE
 SYNTAX  INTEGER
 ACCESS  read-only
 STATUS  mandatory
 DESCRIPTION
  "RIF aging time value."
 ::= { srtb 3 }

-- Netbios Interface Group
--
-- Consists of
-- tables:  Interface.

nbCacheifTable OBJECT-TYPE
 SYNTAX  SEQUENCE OF NbCacheifEntry
 ACCESS  not-accessible
 STATUS  mandatory
 	  		 DESCRIPTION ""
 ::= { nbcache 3 }

nbCacheifEntry OBJECT-TYPE
 SYNTAX  NbCacheifEntry
 ACCESS  not-accessible
 STATUS  mandatory
  	  		 DESCRIPTION ""
INDEX { nbCacheIfIndex }
 ::= {nbCacheifTable 1 }

NbCacheifEntry ::= SEQUENCE {
    nbCacheIfIndex
            INTEGER,
    nbCacheIfOperStatus
            INTEGER
             }

nbCacheIfIndex OBJECT-TYPE
 SYNTAX  INTEGER
 ACCESS  read-only
 STATUS  mandatory
 DESCRIPTION
  "This is the primary index into the Netbios Interface
   Table.  It is the port number which you intend to
   enable/disable Netbios Caching."
 ::= { nbCacheifEntry 1 }

nbCacheIfOperStatus OBJECT-TYPE
 SYNTAX  INTEGER    { enabled(1), disabled(2) }
 ACCESS  read-write
 STATUS  mandatory
 DESCRIPTION
  "Indicates the operating state of netbios name caching
  for this port."
 ::= { nbCacheifEntry 2 }





END
