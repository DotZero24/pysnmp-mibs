-- *****************************************************************
-- Moxa CN2600 MIB
--
-- Copyright (c) 2006 by Moxa Inc.
-- All rights reserved.

-- Version: 4.2
-- Date: 2010/03/04
-- *****************************************************************

MOXA-CN2600-MIB DEFINITIONS ::= BEGIN
    IMPORTS
        enterprises, IpAddress, OBJECT-TYPE
        	FROM SNMPv2-SMI
        DateAndTime, TEXTUAL-CONVENTION, MacAddress, DisplayString
        	FROM SNMPv2-TC;

    moxa 				OBJECT IDENTIFIER ::= { enterprises 8691 }	-- 1.3.6.1.4.1.8691

    nport OBJECT IDENTIFIER ::= { moxa 2 }			-- 1.3.6.1.4.1.8691.2

    cn2600   MODULE-IDENTITY
	    LAST-UPDATED "201003040000Z"
	    ORGANIZATION "Moxa Inc."
	    CONTACT-INFO
	            "Email: support@moxa.com
    			 Tel  : +886 2 89191230 ext.300"

	    DESCRIPTION
	            "The MIB module for Moxa Terminal Server CN2600 series specific information."

	    ::= { nport 11 }    -- 1.3.6.1.4.1.8691.2.11

-- -------------------------------------------------------------
-- groups in the MOXA-CN2600-2AC MIB
-- -------------------------------------------------------------

swMgmt		OBJECT IDENTIFIER ::= { cn2600 1 }			-- 1.3.6.1.4.1.8691.2.11.1

-- -------------------------------------------------------------
-- Textual Conventions
-- -------------------------------------------------------------

PortList ::= TEXTUAL-CONVENTION
	STATUS			current
	DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

-- -------------------------------------------------------------
-- swMgmt group
-- -------------------------------------------------------------

-- -------------------------------------------------------------
-- Overview
-- -------------------------------------------------------------

	overview OBJECT IDENTIFIER ::= { swMgmt 1 }		-- 1.3.6.1.4.1.8691.2.11.1.1

    modelName OBJECT-TYPE
        SYNTAX DisplayString
        MAX-ACCESS read-only
        STATUS current
        DESCRIPTION
            "The model name of the CN2600."
        ::= { overview 1 }							-- 1.3.6.1.4.1.8691.2.11.1.1.1

    serialNumber OBJECT-TYPE
        SYNTAX INTEGER
        MAX-ACCESS read-only
        STATUS current
        DESCRIPTION
            "The serial number of the CN2600. Every Terminal Server CN2600
            series is assigned a unique serial
            number before it is shipped."
        ::= { overview 2 }

    firmwareVersion OBJECT-TYPE
        SYNTAX DisplayString
        MAX-ACCESS read-only
        STATUS current
        DESCRIPTION
            "The version of the firmware currently running on the CN2600."
        ::= { overview 3 }

    viewLan1IpAddress OBJECT-TYPE
        SYNTAX IpAddress
        MAX-ACCESS read-only
        STATUS current
        DESCRIPTION
            "The IP address of the CN2600's LAN1 interface."
        ::= { overview 4 }

    viewLan1MacAddress OBJECT-TYPE
        SYNTAX MacAddress
        MAX-ACCESS read-only
        STATUS current
        DESCRIPTION
            "The MAC address of the CN2600's LAN1 interface."
        ::= { overview 5 }

    viewLan1Speed OBJECT-TYPE
        SYNTAX DisplayString
        MAX-ACCESS read-only
        STATUS current
        DESCRIPTION
            "The current speed and link status of the CN2600's built-in
            LAN1 port. The possible values are 'No link',
            '10M/Link,' or '100M/Link.'"
        ::= { overview 6 }

    viewLan2IpAddress OBJECT-TYPE
        SYNTAX IpAddress
        MAX-ACCESS read-only
        STATUS current
        DESCRIPTION
            "The IP address of the CN2600's LAN2 interface."
        ::= { overview 7 }

    viewLan2MacAddress OBJECT-TYPE
        SYNTAX MacAddress
        MAX-ACCESS read-only
        STATUS current
        DESCRIPTION
            "The MAC address of the CN2600's LAN2 interface."
        ::= { overview 8 }

    viewLan2Speed OBJECT-TYPE
        SYNTAX DisplayString
        MAX-ACCESS read-only
        STATUS current
        DESCRIPTION
            "The current speed and link status of the CN2600's built-in
            LAN2 port. The possible values are 'No link',
            '10M/Link,' or '100M/Link.'"
        ::= { overview 9 }

	upTime OBJECT-TYPE
        SYNTAX DisplayString
        MAX-ACCESS read-only
        STATUS current
        DESCRIPTION
            "The time (in human-readable notation) since the
            system was  was last re-initialized."
        ::= { overview 10 }

	power1Status  OBJECT-TYPE
        SYNTAX INTEGER {
        	power-off(0),
        	power-on(1)
        }
        MAX-ACCESS read-only
        STATUS current
        DESCRIPTION
            "The on/off status of power 1"
		::= { overview 11 }

	power2Status  OBJECT-TYPE
        SYNTAX INTEGER {
        	power-off(0),
        	power-on(1)
        }
        MAX-ACCESS read-only
        STATUS current
        DESCRIPTION
            "The on/off status of power 2 for 2AC model"
		::= { overview 12 }

-- -------------------------------------------------------------
-- Basic settings
-- -------------------------------------------------------------

	basicSetting OBJECT IDENTIFIER ::= { swMgmt 2}			-- 1.3.6.1.4.1.8691.2.11.1.2

-- -------------------------------------------------------------
-- Basic settings -> Server settings
-- -------------------------------------------------------------

	serverSetting OBJECT IDENTIFIER ::= { basicSetting 1 }	-- 1.3.6.1.4.1.8691.2.11.1.2.1

	serverName OBJECT-TYPE
        SYNTAX DisplayString
        MAX-ACCESS read-write
        STATUS current
        DESCRIPTION
            "A text string used to identify the CN2600."
        ::= { serverSetting 1 }

    serverLocation OBJECT-TYPE
        SYNTAX DisplayString
        MAX-ACCESS read-write
        STATUS current
        DESCRIPTION
            "A text string used to identify the location of the CN2600. This
            option is useful for specifying the location or
            application of different CN2600."
        ::= { serverSetting 2 }

-- -------------------------------------------------------------
-- Basic settings -> Time settings
-- -------------------------------------------------------------

	timeSetting OBJECT IDENTIFIER ::= { basicSetting 2 }	-- 1.3.6.1.4.1.8691.2.11.1.2.2

    timeZone OBJECT-TYPE
        SYNTAX INTEGER
        MAX-ACCESS read-write
        STATUS current
        DESCRIPTION
            "The time-zone index of the CN2600."
        ::= { timeSetting 1 }

    localTime OBJECT-TYPE
        SYNTAX DateAndTime
        MAX-ACCESS read-write
        STATUS current
        DESCRIPTION
            "The system time in seconds since 1970/1/1."
        ::= { timeSetting 2 }

    timeServer OBJECT-TYPE
        SYNTAX DisplayString
        MAX-ACCESS read-write
        STATUS current
        DESCRIPTION
            "The Terminal Server CN2600 series uses SNTP
            (RFC-1769) for auto time calibration.
            Input the correct 'Time server' IP address or domain
            name. Once the Terminal Server CN2600 series is
            configured with the correct Time server address, it
            will request time information from the Time server
            every 10 minutes."
        ::= { timeSetting 3 }

-- -------------------------------------------------------------
-- Network settings -> Basic
-- -------------------------------------------------------------

    networkSetting OBJECT IDENTIFIER ::= { swMgmt 3 }		-- 1.3.6.1.4.1.8691.2.11.1.3

    lan1IpConfiguration OBJECT-TYPE
        SYNTAX INTEGER { static(0), dhcp(1), dhcp-BOOTP(2), bootp(3), pppoe(4)}
        MAX-ACCESS read-write
        STATUS current
        DESCRIPTION
            "The IP configuration mode of the CN2600. You can
            choose from four possible IP configuration modes:
            Static, DHCP, DHCP/BOOTP, BOOTP, and PPPoE."
        ::= { networkSetting 1 }

    lan1IpAddress OBJECT-TYPE
        SYNTAX IpAddress
        MAX-ACCESS read-write
        STATUS current
        DESCRIPTION
            "An IP address is a number assigned to a network
            device (such as a computer) as a permanent address
            on the network. Computers use the IP address to
            identify and talk to each other over the network.
            Choose a proper IP address that is unique and valid
            in your network environment."
        ::= { networkSetting 2 }

    lan1NetMask OBJECT-TYPE
        SYNTAX IpAddress
        MAX-ACCESS read-write
        STATUS current
        DESCRIPTION
            "A subnet mask represents all of the network hosts
            at one geographic location, in one building, or on
            the same local area network. When a packet is sent
            out over the network, the Terminal Server CN2600 series device
            server will use the subnet mask to check whether the
            TCP/IP host specified in the packet is on
            the local network segment. If the address is on the
            same network segment as the Terminal Server CN2600 series device
            server, a connection is established directly from
            the Terminal Server CN2600 series device server. Otherwise, the
            connection is established through the given default
            gateway."
        ::= { networkSetting 3 }

    lan1DefaultGateway OBJECT-TYPE
        SYNTAX IpAddress
        MAX-ACCESS read-only
        STATUS current
        DESCRIPTION
            "A gateway is a network computer that acts as an
            entrance to another network. Usually, the computers
            that control traffic within the network or at the
            local Internet service provider are gateway nodes.
            The Terminal Server CN2600 series needs to know
            the IP address of the default gateway computer in
            order to communicate with the hosts outside the
            local network environment. For correct gateway IP
            address information, consult with the network
            administrator."
        ::= { networkSetting 4 }

    lan1Speed OBJECT-TYPE
        SYNTAX INTEGER {
        	auto-Negation(0),
        	tenMbps-Half(1),
        	tenMbps-Full(2),
        	hundredMbps-Half(3),
        	hundredMbps-Full(4)
        }
        MAX-ACCESS read-write
        STATUS current
        DESCRIPTION
            "IEEE802.3 Ethernet supports the auto negotiation
            speed function to get suitable speeds. However, for
            connecting to some switches/hubs, the communication
            speed must be fixed at 100 Mbps or 10 Mbps. Users can
            use this function to fix the communication speed."
        ::= { networkSetting 5 }

    lan1PppoeUserAccount OBJECT-TYPE
        SYNTAX DisplayString
        MAX-ACCESS read-write
        STATUS current
        DESCRIPTION
            "The user account used by the CN2600 to access
            the Internet using PPPoE. For dynamic broad band
            networks such as xDSL or Cable Modem, users must
            enter the username and password that they
            received from their ISP to establish a network
            connection."
        ::= { networkSetting 6 }

    lan1PppoePassword OBJECT-TYPE
        SYNTAX DisplayString
        MAX-ACCESS read-write
        STATUS current
        DESCRIPTION
            "The password used by the CN2600 to access the Internet
            using PPPoE. For dynamic broad band networks such as
            xDSL or Cable Modem, users must enter the
            username and password that they received from their
            ISP to establish a network connection."
        ::= { networkSetting 7 }

    lan2IpConfiguration OBJECT-TYPE
        SYNTAX INTEGER { static(0), dhcp(1), dhcp-BOOTP(2), bootp(3), pppoe(4)}
        MAX-ACCESS read-write
        STATUS current
        DESCRIPTION
            "The IP configuration mode of the CN2600. You can
            choose from four possible IP configuration modes:
            Static, DHCP, DHCP/BOOTP, BOOTP, and PPPoE."
        ::= { networkSetting 8 }

    lan2IpAddress OBJECT-TYPE
        SYNTAX IpAddress
        MAX-ACCESS read-write
        STATUS current
        DESCRIPTION
            "An IP address is a number assigned to a network
            device (such as a computer) as a permanent address
            on the network. Computers use the IP address to
            identify and talk to each other over the network.
            Choose a proper IP address that is unique and valid
            in your network environment."
        ::= { networkSetting 9 }

    lan2NetMask OBJECT-TYPE
        SYNTAX IpAddress
        MAX-ACCESS read-write
        STATUS current
        DESCRIPTION
            "A subnet mask represents all of the network hosts
            at one geographic location, in one building, or on
            the same local area network. When a packet is sent
            out over the network, the Terminal Server CN2600 series device
            server will use the subnet mask to check whether the
            TCP/IP host specified in the packet is on
            the local network segment. If the address is on the
            same network segment as the Terminal Server CN2600 series device
            server, a connection is established directly from
            the Terminal Server CN2600 series device server. Otherwise, the
            connection is established through the given default
            gateway."
        ::= { networkSetting 10 }

    lan2DefaultGateway OBJECT-TYPE
        SYNTAX IpAddress
        MAX-ACCESS read-only
        STATUS current
        DESCRIPTION
            "A gateway is a network computer that acts as an
            entrance to another network. Usually, the computers
            that control traffic within the network or at the
            local Internet service provider are gateway nodes.
            The Terminal Server CN2600 series needs to know
            the IP address of the default gateway computer in
            order to communicate with the hosts outside the
            local network environment. For correct gateway IP
            address information, consult with the network
            administrator."
        ::= { networkSetting 11 }

    lan2Speed OBJECT-TYPE
        SYNTAX INTEGER {
        	auto-Negation(0),
        	tenMbps-Half(1),
        	tenMbps-Full(2),
        	hundredMbps-Half(3),
        	hundredMbps-Full(4)
        }
        MAX-ACCESS read-write
        STATUS current
        DESCRIPTION
            "IEEE802.3 Ethernet supports the auto negotiation
            speed function to get suitable speeds. However, for
            connecting to some switches/hubs, the communication
            speed must be fixed at 100 Mbps or 10 Mbps. Users can
            use this function to fix the communication speed."
        ::= { networkSetting 12 }

    lan2PppoeUserAccount OBJECT-TYPE
        SYNTAX DisplayString
        MAX-ACCESS read-write
        STATUS current
        DESCRIPTION
            "The user account used by the CN2600 to access
            the Internet using PPPoE. For dynamic broad band
            networks such as xDSL or Cable Modem, users must
            enter the username and password that they
            received from their ISP to establish a network
            connection."
        ::= { networkSetting 13 }

    lan2PppoePassword OBJECT-TYPE
        SYNTAX DisplayString
        MAX-ACCESS read-write
        STATUS current
        DESCRIPTION
            "The password used by the CN2600 to access the Internet
            using PPPoE. For dynamic broad band networks such as
            xDSL or Cable Modem, users must enter the
            username and password that they received from their
            ISP to establish a network connection."
        ::= { networkSetting 14 }

    dnsServer1IpAddr OBJECT-TYPE
        SYNTAX IpAddress
        MAX-ACCESS read-write
        STATUS current
        DESCRIPTION
            "The first DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 15 }

    dnsServer2IpAddr OBJECT-TYPE
        SYNTAX IpAddress
        MAX-ACCESS read-write
        STATUS current
        DESCRIPTION
            "The second DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 16 }

    winsFunction OBJECT-TYPE
        SYNTAX INTEGER { disable(0), enable(1)}
        MAX-ACCESS read-write
        STATUS current
        DESCRIPTION
            "Enable or disable the WINS server."
        ::= { networkSetting 17 }

    winsServer OBJECT-TYPE
        SYNTAX IpAddress
        MAX-ACCESS read-write
        STATUS current
        DESCRIPTION
            "If a WINS Server is connected to the network, use
            this field to record the WINS Server’s IP address.
            TCP/IP uses IP addresses to identify hosts, but
            users often use symbolic names, such as computer
            names. The WINS Server, which uses NetBIOS over
            TCP/IP, contains a dynamic database to map computer
            names to IP addresses."
        ::= { networkSetting 18 }

-- -------------------------------------------------------------
-- Network settings -> Advanced
-- -------------------------------------------------------------

    routingProtocol OBJECT-TYPE
        SYNTAX INTEGER { none(0), rip-1(1), rip-2(2)}
        MAX-ACCESS read-write
        STATUS current
        DESCRIPTION
            "The routing protocol used by the CN2600. This value
            could be none, RIP-1, or RIP-2."
        ::= { networkSetting 19 }

    gratuitousArp OBJECT-TYPE
        SYNTAX INTEGER { disable(0), enable(1)}
        MAX-ACCESS read-write
        STATUS current
        DESCRIPTION
            "Enable or disable the gratuitous ARP function. For some
            applications, users need the Terminal Server CN2600 series
            to send broadcast packets to update
            the ARP table on the server. If the customer enables
            this function and sets the send period, the Terminal Server CN2600
            series will send broadcast
            packets periodically."
        ::= { networkSetting 20 }

    gratuitousArpSendPeriod  OBJECT-TYPE
        SYNTAX INTEGER
        MAX-ACCESS read-write
        STATUS current
        DESCRIPTION
            "The send period of the gratuitous ARP function."
        ::= { networkSetting 21 }

-- -------------------------------------------------------------
-- Serial port settings
-- -------------------------------------------------------------

    portSetting OBJECT IDENTIFIER ::= { swMgmt 4 }			-- 1.3.6.1.4.1.8691.2.11.1.2.4

-- -------------------------------------------------------------
-- Serial port settings -> Operation Modes settings
-- -------------------------------------------------------------

	opModeSetting OBJECT IDENTIFIER ::= { portSetting 1 }	-- 1.3.6.1.4.1.8691.2.11.1.2.4.1

-- --------------------------------------------------------------------------------------
-- Serial port settings -> Operation Modes settings -> Operation Modes
-- --------------------------------------------------------------------------------------

	opMode OBJECT IDENTIFIER ::= { opModeSetting 1 }		-- 1.3.6.1.4.1.8691.2.11.1.2.4.1.1

	opModePortTable OBJECT-TYPE
        SYNTAX SEQUENCE OF OpModePortEntry
        MAX-ACCESS not-accessible
        STATUS current
        DESCRIPTION
            "The serial ports' operation mode table."
        ::= { opMode 1 }

    opModePortEntry OBJECT-TYPE
        SYNTAX OpModePortEntry
        MAX-ACCESS not-accessible
        STATUS current
        DESCRIPTION
            "The serial port's operation mode entry."
        INDEX { portIndex }
        ::= { opModePortTable 1 }

    OpModePortEntry ::=
        SEQUENCE {
        	portIndex
        		INTEGER,
            portApplication
                INTEGER,
            portMode
            	INTEGER
        }

    portIndex OBJECT-TYPE
        SYNTAX INTEGER
        MAX-ACCESS read-only
        STATUS current
        DESCRIPTION
            "The serial port index."
        ::= { opModePortEntry 1 }

	portApplication OBJECT-TYPE
        SYNTAX INTEGER {
        	disable(0),
        	device-Control(4),
			socket(11),
			redundant-Com(5),
			drdas(9),
			terminal(2),
			reverse-Terminal(3),
			dial-InOut(1)
        }
        MAX-ACCESS read-write
        STATUS current
        DESCRIPTION
            "The application of the serial port.
            Note that changing this setting may also change the
            operation mode."
        ::= { opModePortEntry 2 }

    portMode OBJECT-TYPE
        SYNTAX INTEGER {
        	real-Com(2),
			slip(4),
			slipd(5),
			ppp(6),
			disable(7),
			telnetd(8),
			dynamic(9),
			tcp-Server(10),
			tcp-Client(13),
			udp(14),
			pppd(15),
			term-ASC(16),
			term-BIN(17),
			rfc-2217(20),
			redundant-Com(22),
			drdas-Real-Com(23),
			drdas-Tcp-Server(24),
        }
        MAX-ACCESS read-write
        STATUS current
        DESCRIPTION
            "The operation mode of the serial port. Note that
            changing this setting may also change the application."
        ::= { opModePortEntry 3 }


-- --------------------------------------------------------------------------------------
-- Serial port settings -> Operation Modes settings -> Application
-- --------------------------------------------------------------------------------------

	application OBJECT IDENTIFIER ::= { opModeSetting 2 }

-- --------------------------------------------------------------------------------------
-- Serial port settings -> Operation Modes settings -> Application -> Device Control
-- --------------------------------------------------------------------------------------

	deviceControl OBJECT IDENTIFIER ::= { application 1 }

	deviceControlTable OBJECT-TYPE
        SYNTAX SEQUENCE OF DeviceControlEntry
        MAX-ACCESS not-accessible
        STATUS current
        DESCRIPTION
            "The Device Control application table."
        ::= { deviceControl 1 }

    deviceControlEntry OBJECT-TYPE
        SYNTAX DeviceControlEntry
        MAX-ACCESS not-accessible
        STATUS current
        DESCRIPTION
            "The Device Control application entry."
        INDEX { portIndex }
        ::= { deviceControlTable 1 }

    DeviceControlEntry ::=
        SEQUENCE {
        	deviceControlTcpAliveCheck
            	INTEGER,
            deviceControlMaxConnection
            	INTEGER,
            deviceControlIgnoreJammedIp
            	INTEGER,
            deviceControlAllowDriverControl
            	INTEGER,
            deviceControlConnectionDownRTS
            	INTEGER,
            deviceControlConnectionDownDTR
            	INTEGER
        }

	deviceControlTcpAliveCheck OBJECT-TYPE
        SYNTAX INTEGER
        MAX-ACCESS read-write
        STATUS current
        DESCRIPTION
            "The TCP alive check time.
            0 min: TCP connection will not be closed when the
            TCP connection is idle.
            1 to 99 min: The Terminal Server CN2600 series device server
            automatically closes the TCP connection if there is
            no TCP activity for the given time. After the
            connection is closed, the Terminal Server CN2600 series device
            server starts listening for another Real COM driver
            Connection."
        ::= { deviceControlEntry 1 }

    deviceControlMaxConnection OBJECT-TYPE
        SYNTAX INTEGER
        MAX-ACCESS read-write
        STATUS current
        DESCRIPTION
            "Max connection is usually used when the user needs
            to receive data from different hosts simultaneously.
            The factory default is 1. In this case, only one
            specific host can access this port of the Terminal Server CN2600
            series device server, and the Real COM driver on that
            host will have full control over the port.
            Max. connection = 1:
            Allows only a single host’s Real COM driver to open
            the specific Terminal Server CN2600 series device server’s
            serial port.
            Max connection = 2 to 8:
            Allows 2 to 8 hosts’ Real COM drivers to open the
            specific Terminal Server CN2600 series device server’s serial
            port, at the same time. When multiple hosts’ Real
            COM drivers open the serial port at the same time,
            the COM driver only provides a pure data tunnel
            without control ability. The serial port parameter
            will use the firmware settings instead of getting
            the settings from your application program (AP)."
        ::= { deviceControlEntry 2 }

    deviceControlIgnoreJammedIp OBJECT-TYPE
        SYNTAX INTEGER { no(0), yes(1) }
        MAX-ACCESS read-write
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { deviceControlEntry 3 }

    deviceControlAllowDriverControl OBJECT-TYPE
        SYNTAX INTEGER { no(0), yes(1) }
        MAX-ACCESS read-write
        STATUS current
        DESCRIPTION
            "If Max connection is greater than 1, CN2600 will
            ignore driver control commands from all connected
            hosts. However, if you set Allow driver control to
            YES, control commands will be accepted. Note that
            since the Terminal Server CN2600 series may get
            configuration changes from multiple hosts, the most
            recent command received will take precedence."
        ::= { deviceControlEntry 4 }

	deviceControlConnectionDownRTS OBJECT-TYPE
        SYNTAX INTEGER { always-low(1), always-high(0) }
        MAX-ACCESS read-write
        STATUS current
        DESCRIPTION
            "For some applications, serial devices must obtain
            the Ethernet link status by reading the RTS signal from the
            Terminal Server CN2600 series device server. If this setting is
            set to 'always low,' RTS will change its state to
            low if the Ethernet link is off."
        ::= { deviceControlEntry 5 }

    deviceControlConnectionDownDTR OBJECT-TYPE
        SYNTAX INTEGER { always-low(1), always-high(0) }
        MAX-ACCESS read-write
        STATUS current
        DESCRIPTION
            "For some applications, serial devices must obtain
            the Ethernet link status by reading the DTR signal from the
            Terminal Server CN2600 series device server. If this setting is
            set to 'goes low,' DTR will change its state to
            low if the Ethernet link is off."
        ::= { deviceControlEntry 6 }


-- --------------------------------------------------------------------------------------
-- Serial port settings -> Operation Modes settings -> Application -> Socket
-- --------------------------------------------------------------------------------------

	socket OBJECT IDENTIFIER ::= { application 2 }

	socketTable OBJECT-TYPE
        SYNTAX SEQUENCE OF SocketEntry
        MAX-ACCESS not-accessible
        STATUS current
        DESCRIPTION
            "The Socket application table."
        ::= { socket 1 }

    socketEntry OBJECT-TYPE
        SYNTAX SocketEntry
        MAX-ACCESS not-accessible
        STATUS current
        DESCRIPTION
            "The Socket application entry."
        INDEX { portIndex }
        ::= { socketTable 1 }

    SocketEntry ::=
        SEQUENCE {
        	socketTcpAliveCheck
            	INTEGER,
            socketInactivityTime
            	INTEGER,
            socketMaxConnection
            	INTEGER,
            socketIgnoreJammedIp
            	INTEGER,
            socketAllowDriverControl
            	INTEGER,
            socketTcpPort
            	INTEGER,
            socketCmdPort
            	INTEGER,
            socketTcpServerConnectionDownRTS
            	INTEGER,
            socketTcpServerConnectionDownDTR
            	INTEGER,
            socketTcpClientDestinationAddress1
                DisplayString,
            socketTcpClientDestinationPort1
                INTEGER,
            socketTcpClientDestinationAddress2
                DisplayString,
            socketTcpClientDestinationPort2
            	INTEGER,
            socketTcpClientDestinationAddress3
                DisplayString,
            socketTcpClientDestinationPort3
            	INTEGER,
            socketTcpClientDestinationAddress4
                DisplayString,
            socketTcpClientDestinationPort4
            	INTEGER,
            socketTcpClientDesignatedLocalPort1
            	INTEGER,
            socketTcpClientDesignatedLocalPort2
            	INTEGER,
            socketTcpClientDesignatedLocalPort3
            	INTEGER,
            socketTcpClientDesignatedLocalPort4
            	INTEGER,
            socketTcpClientConnectionControl
            	INTEGER,
            socketUdpDestinationAddress1Begin
            	IpAddress,
            socketUdpDestinationAddress1End
            	IpAddress,
            socketUdpDestinationPort1
            	INTEGER,
            socketUdpDestinationAddress2Begin
            	IpAddress,
            socketUdpDestinationAddress2End
            	IpAddress,
            socketUdpDestinationPort2
            	INTEGER,
            socketUdpDestinationAddress3Begin
            	IpAddress,
            socketUdpDestinationAddress3End
            	IpAddress,
            socketUdpDestinationPort3
            	INTEGER,
            socketUdpDestinationAddress4Begin
            	IpAddress,
            socketUdpDestinationAddress4End
            	IpAddress,
            socketUdpDestinationPort4
            	INTEGER,
            socketUdpLocalListenPort
            	INTEGER
        }

	socketTcpAliveCheck OBJECT-TYPE
        SYNTAX INTEGER
        MAX-ACCESS read-write
        STATUS current
        DESCRIPTION
            "The TCP alive check time.
            0 min: TCP connection will not be closed when the
            TCP connection is idle.
            1 to 99 min: The Terminal Server CN2600 series device server
            automatically closes the TCP connection if there is
            no TCP activity for the given time. After the
            connection is closed, the Terminal Server CN2600 series device
            server starts listening for another connection."
        ::= { socketEntry 1 }

    socketInactivityTime OBJECT-TYPE
        SYNTAX INTEGER
        MAX-ACCESS read-write
        STATUS current
        DESCRIPTION
            "0 ms: TCP connection is not closed when the
            serial line is idle.
            1-65535 ms: The Terminal Server CN2600 series device server
            automatically closes the TCP connection if there is
            no serial data activity for the given time. After
            the connection is closed, the Terminal Server CN2600 series
            starts listening for another
            TCP connection."
        ::= { socketEntry 2 }

    socketMaxConnection OBJECT-TYPE
        SYNTAX INTEGER
        MAX-ACCESS read-write
        STATUS current
        DESCRIPTION
            "Max connection is usually used when the user needs
            to receive data from different hosts simultaneously.
            The factory default is 1. In this case, only one
            specific host can access this port of the Terminal Server CN2600
            series device server.
            Max. connection 1:
            Allows only a single host to open
            the specific Terminal Server CN2600 series device server’s
            serial port.
            Max connection 2 to 8:
            Allows 2 to 8 hosts to open the
            specific Terminal Server CN2600 series device server’s serial
            port at the same time."
        ::= { socketEntry 3 }

    socketIgnoreJammedIp OBJECT-TYPE
        SYNTAX INTEGER { no(0), yes(1) }
        MAX-ACCESS read-write
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { socketEntry 4 }

    socketAllowDriverControl OBJECT-TYPE
        SYNTAX INTEGER { no(0), yes(1) }
        MAX-ACCESS read-write
        STATUS current
        DESCRIPTION
            "If Max connection is greater than 1, CN2600 will
            ignore driver control commands from all connected
            hosts. However, if you set Allow driver control to
            YES, control commands will be accepted. Note that
            since the Terminal Server CN2600 series may get
            configuration changes from multiple hosts, the most
            recent command received will take precedence."
        ::= { socketEntry 5 }

    socketTcpPort OBJECT-TYPE
        SYNTAX INTEGER
        MAX-ACCESS read-write
        STATUS current
        DESCRIPTION
            "The 'TCP port' is the TCP port that the Terminal Server CN2600
            series uses to listen to
            connections, and that other devices must use to
            contact the Terminal Server CN2600 series device server."
        ::= { socketEntry 6 }

    socketCmdPort OBJECT-TYPE
        SYNTAX INTEGER
        MAX-ACCESS read-write
        STATUS current
        DESCRIPTION
            "The 'Command port' is a TCP port used to listen for
            IP-Serial Lib commands from the host. In order to
            prevent a TCP port conflict with other applications,
            the user can set the Command port to another port
            if needed. IP-Serial Lib will automatically check
            the Command Port on the Terminal Server CN2600 series device
            server to avoid the need for the user to configure
            the program."
        ::= { socketEntry 7 }

    socketTcpServerConnectionDownRTS OBJECT-TYPE
        SYNTAX INTEGER { always-low(1), always-high(0) }
        MAX-ACCESS read-write
        STATUS current
        DESCRIPTION
            "For some applications, serial devices must obtain
            the Ethernet link status from the RTS signal sent by the
            Terminal Server CN2600 series device server. If this setting is
            set to 'goes low,' RTS will change the state to
            low if the Ethernet link is off."
        ::= { socketEntry 8 }

    socketTcpServerConnectionDownDTR OBJECT-TYPE
        SYNTAX INTEGER { always-low(1), always-high(0) }
        MAX-ACCESS read-write
        STATUS current
        DESCRIPTION
            "For some applications, serial devices must obtain
            the Ethernet link status from the DTR signal sent by the
            Terminal Server CN2600 series device server. If this setting is
            set to 'goes low,' DTR will change the state to
            low if the Ethernet link is off."
        ::= { socketEntry 9 }

    socketTcpClientDestinationAddress1 OBJECT-TYPE
		SYNTAX DisplayString
		MAX-ACCESS read-write
		STATUS current
		DESCRIPTION
			"The Terminal Server CN2600 series can
                         connect actively to a remote host that
                         has this IP address."
		::= { socketEntry 10 }

	socketTcpClientDestinationPort1 OBJECT-TYPE
		SYNTAX INTEGER
		MAX-ACCESS read-write
		STATUS current
		DESCRIPTION
			"The Terminal Server CN2600 series can
			connect actively to a remote host that has this
                        TCP port number."
		::= { socketEntry 11 }

	socketTcpClientDestinationAddress2 OBJECT-TYPE
		SYNTAX DisplayString
		MAX-ACCESS read-write
		STATUS current
		DESCRIPTION
			"The Terminal Server CN2600 series can
			connect actively to a remote host that has this IP
			address."
		::= { socketEntry 12 }

	socketTcpClientDestinationPort2 OBJECT-TYPE
		SYNTAX INTEGER
		MAX-ACCESS read-write
		STATUS current
		DESCRIPTION
			"The Terminal Server CN2600 series can
			connect actively to a remote host that
			has this TCP port number."
		::= { socketEntry 13 }

	socketTcpClientDestinationAddress3 OBJECT-TYPE
		SYNTAX DisplayString
		MAX-ACCESS read-write
		STATUS current
		DESCRIPTION
			"The Terminal Server CN2600 series can
			connect actively to a remote host that
                        has this IP address."
		::= { socketEntry 14 }

	socketTcpClientDestinationPort3 OBJECT-TYPE
		SYNTAX INTEGER
		MAX-ACCESS read-write
		STATUS current
		DESCRIPTION
			"The Terminal Server CN2600 series can
			connect actively to a remote host that
                        has this port number."
		::= { socketEntry 15 }

	socketTcpClientDestinationAddress4 OBJECT-TYPE
		SYNTAX DisplayString
		MAX-ACCESS read-write
		STATUS current
		DESCRIPTION
			"The Terminal Server CN2600 series can
			connect actively to a remote host that
                        has this IP address."
		::= { socketEntry 16 }

	socketTcpClientDestinationPort4 OBJECT-TYPE
		SYNTAX INTEGER
		MAX-ACCESS read-write
		STATUS current
		DESCRIPTION
			"The Terminal Server CN2600 series can
			connect actively to a remote host that
                        has this port number."
		::= { socketEntry 17 }

	socketTcpClientDesignatedLocalPort1 OBJECT-TYPE
		SYNTAX INTEGER
		MAX-ACCESS read-write
		STATUS current
		DESCRIPTION
			"The local TCP port used to connect actively to the
			remote host."
		::= { socketEntry 18 }

	socketTcpClientDesignatedLocalPort2 OBJECT-TYPE
		SYNTAX INTEGER
		MAX-ACCESS read-write
		STATUS current
		DESCRIPTION
			"The local TCP port used to connect actively to the
			remote host."
		::= { socketEntry 19 }

	socketTcpClientDesignatedLocalPort3 OBJECT-TYPE
		SYNTAX INTEGER
		MAX-ACCESS read-write
		STATUS current
		DESCRIPTION
			"The local TCP port used to connect actively to the
			remote host."
		::= { socketEntry 20 }

	socketTcpClientDesignatedLocalPort4 OBJECT-TYPE
		SYNTAX INTEGER
		MAX-ACCESS read-write
		STATUS current
		DESCRIPTION
			"The local TCP port used to connect actively to the
			remote host."
		::= { socketEntry 21 }

	socketTcpClientConnectionControl OBJECT-TYPE
		SYNTAX INTEGER {
			startup-None(257),
			anyCharacter-None(258),
			anyCharacter-InactivityTime(514),
			dsrOn-DSR-Off(1028),
			dsrOn-None(260),
			dcdOn-DCD-Off(2056),
			dcdOn-None(264)
		}
		MAX-ACCESS read-write
		STATUS current
		DESCRIPTION
			"Events that cause the TCP client to drop the
			connection."
		::= { socketEntry 22 }

	socketUdpDestinationAddress1Begin OBJECT-TYPE
		SYNTAX IpAddress
		MAX-ACCESS read-write
		STATUS current
		DESCRIPTION
			"The Terminal Server CN2600 series can actively send
			UDP packets to remote hosts whose IP
			addresses are in the range between this parameter and
			socketUdpDestinationAddress1End."
		::= { socketEntry 23 }

	socketUdpDestinationAddress1End OBJECT-TYPE
		SYNTAX IpAddress
		MAX-ACCESS read-write
		STATUS current
		DESCRIPTION
			"The Terminal Server CN2600 series can actively send
			UDP packets to remote hosts whose IP
			addresses are in the range between
			socketUdpDestinationAddress1Begin and this parameter."
		::= { socketEntry 24 }

	socketUdpDestinationPort1 OBJECT-TYPE
		SYNTAX INTEGER
		MAX-ACCESS read-write
		STATUS current
		DESCRIPTION
			"The Terminal Server CN2600 series can actively send
			UDP packets to remote hosts that have this port
			number."
		::= { socketEntry 25 }

	socketUdpDestinationAddress2Begin OBJECT-TYPE
		SYNTAX IpAddress
		MAX-ACCESS read-write
		STATUS current
		DESCRIPTION
			"The Terminal Server CN2600 series can actively send
			UDP packets to remote hosts whose IP
			addresses are in the range between this parameter and
			socketUdpDestinationAddress2End."
		::= { socketEntry 26 }

	socketUdpDestinationAddress2End OBJECT-TYPE
		SYNTAX IpAddress
		MAX-ACCESS read-write
		STATUS current
		DESCRIPTION
			"The Terminal Server CN2600 series can actively send
			UDP packets to the remote hosts whose IP
			addresses are in the range between
			socketUdpDestinationAddress2Begin and this parameter."
		::= { socketEntry 27 }

	socketUdpDestinationPort2 OBJECT-TYPE
		SYNTAX INTEGER
		MAX-ACCESS read-write
		STATUS current
		DESCRIPTION
			"The Terminal Server CN2600 series can actively send
			UDP packets to the remote hosts that have this
                        TCP port number."
		::= { socketEntry 28 }

	socketUdpDestinationAddress3Begin OBJECT-TYPE
		SYNTAX IpAddress
		MAX-ACCESS read-write
		STATUS current
		DESCRIPTION
			"The Terminal Server CN2600 series can actively send
			UDP packets to remote hosts whose IP
			addresses are in the range between this parameter and
			socketUdpDestinationAddress3End."
		::= { socketEntry 29 }

	socketUdpDestinationAddress3End OBJECT-TYPE
		SYNTAX IpAddress
		MAX-ACCESS read-write
		STATUS current
		DESCRIPTION
			"The Terminal Server CN2600 series can actively send
			UDP packets to remote hosts whose IP
			addresses are in the range between
			socketUdpDestinationAddress3Begin and this parameter."
		::= { socketEntry 30 }

	socketUdpDestinationPort3 OBJECT-TYPE
		SYNTAX INTEGER
		MAX-ACCESS read-write
		STATUS current
		DESCRIPTION
			"The Terminal Server CN2600 series can actively send
			UDP packets to remote hosts that have this
                        TCP port number."
		::= { socketEntry 31 }

	socketUdpDestinationAddress4Begin OBJECT-TYPE
		SYNTAX IpAddress
		MAX-ACCESS read-write
		STATUS current
		DESCRIPTION
			"The Terminal Server CN2600 series can actively send
			UDP packets to remote hosts whose IP
			addresses are in the range between this parameter and
			socketUdpDestinationAddress4End."
		::= { socketEntry 32 }

	socketUdpDestinationAddress4End OBJECT-TYPE
		SYNTAX IpAddress
		MAX-ACCESS read-write
		STATUS current
		DESCRIPTION
			"The Terminal Server CN2600 series can actively send
			UDP packets to remote hosts whose IP
			addresses are in the range between
			socketUdpDestinationAddress4Begin and this parameter."
		::= { socketEntry 33 }

	socketUdpDestinationPort4 OBJECT-TYPE
		SYNTAX INTEGER
		MAX-ACCESS read-write
		STATUS current
		DESCRIPTION
			"The Terminal Server CN2600 series can actively send
			UDP packets to remote hosts that have this
                        TCP port number."
		::= { socketEntry 34 }

	socketUdpLocalListenPort OBJECT-TYPE
		SYNTAX INTEGER
		MAX-ACCESS read-write
		STATUS current
		DESCRIPTION
			"The UDP port that the Terminal Server CN2600 series device
			server listens to and that other devices must use
			to contact the Terminal Server CN2600 series device server."
		::= { socketEntry 35 }

-- --------------------------------------------------------------------------------------
-- Serial port settings -> Operation Modes settings -> Redundant COM
-- --------------------------------------------------------------------------------------

	redundantCom OBJECT IDENTIFIER ::= { application 3 }

	redundantComTable OBJECT-TYPE
        SYNTAX SEQUENCE OF RedundantComEntry
        MAX-ACCESS not-accessible
        STATUS current
        DESCRIPTION
            "The Redundant COM table."
        ::= { redundantCom 1 }

    redundantComEntry OBJECT-TYPE
        SYNTAX RedundantComEntry
        MAX-ACCESS not-accessible
        STATUS current
        DESCRIPTION
            "The Redundant COM entry."
        INDEX { portIndex }
        ::= { redundantComTable 1 }

    RedundantComEntry ::=
        SEQUENCE {
            redundantComMaxConnection
            	INTEGER,
            redundantComIgnoreJammedIp
            	INTEGER,
            redundantComAllowDriverControl
            	INTEGER,
            redundantComConnectionDownRTS
            	INTEGER,
            redundantComConnectionDownDTR
            	INTEGER
        }

    redundantComMaxConnection OBJECT-TYPE
        SYNTAX INTEGER
        MAX-ACCESS read-write
        STATUS current
        DESCRIPTION
            "Max connection is usually used when the user needs
            to receive data from different hosts simultaneously.
            The factory default is 1. In this case, only one
            specific host can access this port of the Terminal Server CN2600
            series device server, and the Redundant COM driver on that
            host will have full control over the port.
            Max. connection = 1:
            Allows only a single host’s Redundant COM driver to open
            the specific Terminal Server CN2600 series device server’s
            serial port.
            Max connection = 2 to 4:
            Allows 2 to 4 hosts’ Redundant COM drivers to open the
            specific Terminal Server CN2600 series device server’s serial
            port, at the same time. When multiple hosts’ Redundant
            COM drivers open the serial port at the same time,
            the COM driver only provides a pure data tunnel
            without control ability. The serial port parameter
            will use the firmware settings instead of getting
            the settings from your application program (AP)."
        ::= { redundantComEntry 1 }

    redundantComIgnoreJammedIp OBJECT-TYPE
        SYNTAX INTEGER { no(0), yes(1) }
        MAX-ACCESS read-write
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { redundantComEntry 2 }

    redundantComAllowDriverControl OBJECT-TYPE
        SYNTAX INTEGER { no(0), yes(1) }
        MAX-ACCESS read-write
        STATUS current
        DESCRIPTION
            "If Max connection is greater than 1, CN2600 will
            ignore driver control commands from all connected
            hosts. However, if you set Allow driver control to
            YES, control commands will be accepted. Note that
            since the Terminal Server CN2600 series may get
            configuration changes from multiple hosts, the most
            recent command received will take precedence."
        ::= { redundantComEntry 3 }

	redundantComConnectionDownRTS OBJECT-TYPE
        SYNTAX INTEGER { always-low(1), always-high(0) }
        MAX-ACCESS read-write
        STATUS current
        DESCRIPTION
            "For some applications, serial devices must obtain
            the Ethernet link status by reading the RTS signal from the
            Terminal Server CN2600 series device server. If this setting is
            set to 'always low,' RTS will change its state to
            low if the Ethernet link is off."
        ::= { redundantComEntry 4 }

    redundantComConnectionDownDTR OBJECT-TYPE
        SYNTAX INTEGER { always-low(1), always-high(0) }
        MAX-ACCESS read-write
        STATUS current
        DESCRIPTION
            "For some applications, serial devices must obtain
            the Ethernet link status by reading the DTR signal from the
            Terminal Server CN2600 series device server. If this setting is
            set to 'goes low,' DTR will change its state to
            low if the Ethernet link is off."
        ::= { redundantComEntry 5 }

-- --------------------------------------------------------------------------------------
-- Serial port settings -> Operation Modes settings -> drdas
-- --------------------------------------------------------------------------------------

	drdas OBJECT IDENTIFIER ::= { application 4 }

	drdasTable OBJECT-TYPE
        SYNTAX SEQUENCE OF DrdasEntry
        MAX-ACCESS not-accessible
        STATUS current
        DESCRIPTION
            "The DRDAS table."
        ::= { drdas 1 }

    drdasEntry OBJECT-TYPE
        SYNTAX DrdasEntry
        MAX-ACCESS not-accessible
        STATUS current
        DESCRIPTION
            "The DRDAS entry."
        INDEX { portIndex }
        ::= { drdasTable 1 }

    DrdasEntry ::=
        SEQUENCE {
         	drdasTcpAliveCheck
            	INTEGER,
            drdasInactivityTime
            	INTEGER,
            drdasIgnoreJammedIp
            	INTEGER,
            drdasPrimaryIpAddress
            	IpAddress,
            drdasBackup1IpAddress
            	IpAddress,
            drdasBackup2IpAddress
            	IpAddress,
            drdasBackup3IpAddress
            	IpAddress,
            drdasTcpPort
            	INTEGER,
            drdasCmdPort
            	INTEGER,
            drdasConnectionDownRTS
            	INTEGER,
            drdasConnectionDownDTR
            	INTEGER
        }

	drdasTcpAliveCheck OBJECT-TYPE
        SYNTAX INTEGER
        MAX-ACCESS read-write
        STATUS current
        DESCRIPTION
            "The TCP alive check time.
            0 min: TCP connection will not be closed when the
            TCP connection is idle.
            1 to 99 min: The Terminal Server CN2600 series device server
            automatically closes the TCP connection if there is
            no TCP activity for the given time. After the
            connection is closed, the Terminal Server CN2600 series device
            server starts listening for another Real COM driver
            Connection."
        ::= { drdasEntry 1 }

    drdasInactivityTime OBJECT-TYPE
        SYNTAX INTEGER
        MAX-ACCESS read-write
        STATUS current
        DESCRIPTION
            "0 ms: TCP connection is not closed when the
            serial line is idle.
            1-65535 ms: The Terminal Server CN2600 series device server
            automatically closes the TCP connection if there is
            no serial data activity for the given time. After
            the connection is closed, the Terminal Server CN2600 series
            starts listening for another
            TCP connection."
        ::= { drdasEntry 2 }

    drdasIgnoreJammedIp OBJECT-TYPE
        SYNTAX INTEGER { no(0), yes(1) }
        MAX-ACCESS read-write
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { drdasEntry 3 }

	drdasPrimaryIpAddress OBJECT-TYPE
		SYNTAX IpAddress
		MAX-ACCESS read-write
		STATUS current
		DESCRIPTION
			"DRDAS Primary IP Address."
		::= { drdasEntry 4 }

	drdasBackup1IpAddress OBJECT-TYPE
		SYNTAX IpAddress
		MAX-ACCESS read-write
		STATUS current
		DESCRIPTION
			"DRDAS Backup 1 IP Address."
		::= { drdasEntry 5 }

	drdasBackup2IpAddress OBJECT-TYPE
		SYNTAX IpAddress
		MAX-ACCESS read-write
		STATUS current
		DESCRIPTION
			"DRDAS Backup 2 IP Address."
		::= { drdasEntry 6 }

	drdasBackup3IpAddress OBJECT-TYPE
		SYNTAX IpAddress
		MAX-ACCESS read-write
		STATUS current
		DESCRIPTION
			"DRDAS Backup 3 IP Address."
		::= { drdasEntry 7 }

    drdasTcpPort OBJECT-TYPE
        SYNTAX INTEGER
        MAX-ACCESS read-write
        STATUS current
        DESCRIPTION
            "The 'TCP port' is the TCP port that the
            Terminal Server CN2600 series uses to listen to
            connections, and that other devices must use to
            contact the Terminal Server CN2600 series device server."
        ::= { drdasEntry 8 }

    drdasCmdPort OBJECT-TYPE
        SYNTAX INTEGER
        MAX-ACCESS read-write
        STATUS current
        DESCRIPTION
            "The 'Command port' is a TCP port used to listen for
            IP-Serial Lib commands from the host. In order to
            prevent a TCP port conflict with other applications,
            the user can set the Command port to another port
            if needed. IP-Serial Lib will automatically check
            the Command Port on the Terminal Server CN2600 series device
            server to avoid the need for the user to configure
            the program."
        ::= { drdasEntry 9 }

	drdasConnectionDownRTS OBJECT-TYPE
        SYNTAX INTEGER { always-low(1), always-high(0) }
        MAX-ACCESS read-write
        STATUS current
        DESCRIPTION
            "For some applications, serial devices must obtain
            the Ethernet link status by reading the RTS signal from the
            Terminal Server CN2600 series device server. If this setting is
            set to 'always low,' RTS will change its state to
            low if the Ethernet link is off."
        ::= { drdasEntry 10 }

    drdasConnectionDownDTR OBJECT-TYPE
        SYNTAX INTEGER { always-low(1), always-high(0) }
        MAX-ACCESS read-write
        STATUS current
        DESCRIPTION
            "For some applications, serial devices must obtain
            the Ethernet link status by reading the DTR signal from the
            Terminal Server CN2600 series device server. If this setting is
            set to 'goes low,' DTR will change its state to
            low if the Ethernet link is off."
        ::= { drdasEntry 11 }

-- --------------------------------------------------------------------------------------
-- Serial port settings -> Operation Modes settings -> Application -> Terminal
-- --------------------------------------------------------------------------------------

	terminal OBJECT IDENTIFIER ::= { application 5 }

	terminalTable OBJECT-TYPE
        SYNTAX SEQUENCE OF TerminalEntry
        MAX-ACCESS not-accessible
        STATUS current
        DESCRIPTION
            "The Terminal Application table."
        ::= { terminal 1 }

    terminalEntry OBJECT-TYPE
        SYNTAX TerminalEntry
        MAX-ACCESS not-accessible
        STATUS current
        DESCRIPTION
            "The Terminal Application entry."
        INDEX { portIndex }
        ::= { terminalTable 1 }

    TerminalEntry ::=
        SEQUENCE {
        	terminalTcpAliveCheck
        		INTEGER,
        	terminalInactivityTime
        		INTEGER,
        	terminalAutoLinkProtocol
            	INTEGER,
            terminalPrimaryHostAddress
            	DisplayString,
            terminalSecondHostAddress
            	DisplayString,
            terminalTelnetTcpPort
            	INTEGER,
            terminalType
                DisplayString,
            terminalMaxSessions
            	INTEGER,
            terminalChangeSession
            	DisplayString,
            terminalQuit
            	DisplayString,
            terminalBreak
            	DisplayString,
            terminalInterrupt
            	DisplayString,
            terminalAuthenticationType
            	INTEGER,
            terminalAutoLoginPrompt
            	DisplayString,
            terminalPasswordPrompt
            	DisplayString,
            terminalLoginUserName
            	DisplayString,
            terminalLoginPassword
            	DisplayString
        }

	terminalTcpAliveCheck OBJECT-TYPE
        SYNTAX INTEGER
        MAX-ACCESS read-write
        STATUS current
        DESCRIPTION
            "The TCP alive check time.
            0 min: TCP connection will not be closed if the
            TCP connection becomes idle.
            1 to 99 min: The Terminal Server CN2600 series device server
            automatically closes the TCP connection if there is
            no TCP activity for the given time. After the
            connection is closed, the Terminal Server CN2600 series device
            server starts listening for another
            connection from another host."
        ::= { terminalEntry 1 }

	terminalInactivityTime OBJECT-TYPE
        SYNTAX INTEGER
        MAX-ACCESS read-write
        STATUS current
        DESCRIPTION
            "0 min: TCP connection will not be closed if the
            serial line becomes idle.
            0-99 min: The Terminal Server CN2600 series device server
            automatically closes the TCP connection if there is
            no serial data activity for the given time. After
            the connection is closed, the Terminal Server CN2600 series
            starts listening for another host's
            TCP connection."
        ::= { terminalEntry 2 }

    terminalAutoLinkProtocol OBJECT-TYPE
		SYNTAX INTEGER {none(0), telnet(1), rlogin(2)}
		MAX-ACCESS read-write
		STATUS current
		DESCRIPTION
			"If Auto-Link protocol is set to 'None,' the
			Terminal Server CN2600 series will not connect to the
			host automatically. If Auto-Link protocol is set to
			'Telnet,' the Terminal Server CN2600 series will
			connect to the host automatically using Telnet. If
			Auto-Link protocol is set to 'Rlogin,' the
			Terminal Server CN2600 series will connect to the host
			automatically using rlogin."
		::= { terminalEntry 3 }

	terminalPrimaryHostAddress OBJECT-TYPE
		SYNTAX DisplayString (SIZE(0..40))
		MAX-ACCESS read-write
		STATUS current
		DESCRIPTION
			"If specified, designates a 'permanent' host to
			which the terminal will always be connected."
		::= { terminalEntry 4 }

	terminalSecondHostAddress OBJECT-TYPE
		SYNTAX DisplayString (SIZE(0..40))
		MAX-ACCESS read-write
		STATUS current
		DESCRIPTION
			"If specified, designates a 'permanent' host to
			which the terminal will always be connected."
		::= { terminalEntry 5 }

	terminalTelnetTcpPort OBJECT-TYPE
		SYNTAX INTEGER
		MAX-ACCESS read-write
		STATUS current
		DESCRIPTION
			"By default, the Telnet TCP port number is set to
			23, which is the default TCP port number for Telnet.
			If you need to telnet to this Terminal Server CN2600 series
			device server's serial port, set the Telnet TCP port
			to a different number."
		::= { terminalEntry 6 }

	terminalType OBJECT-TYPE
		SYNTAX DisplayString (SIZE(0..8))
		MAX-ACCESS read-write
		STATUS current
		DESCRIPTION
			"Defines the terminal type for outgoing connections."
		::= { terminalEntry 7 }

	terminalMaxSessions OBJECT-TYPE
        SYNTAX INTEGER
        MAX-ACCESS read-write
        STATUS current
        DESCRIPTION
            "Configure the max. number of sessions."
        ::= { terminalEntry 8 }

    terminalChangeSession OBJECT-TYPE
		SYNTAX DisplayString (SIZE(0..2))
		MAX-ACCESS read-write
		STATUS current
		DESCRIPTION
			"Defines the control character used to change the terminal
			session."
		::= { terminalEntry 9 }

	terminalQuit OBJECT-TYPE
		SYNTAX DisplayString (SIZE(0..2))
		MAX-ACCESS read-write
		STATUS current
		DESCRIPTION
			"Defines the control character used to quit a terminal
			session."
		::= { terminalEntry 10 }

	terminalBreak OBJECT-TYPE
		SYNTAX DisplayString (SIZE(0..2))
		MAX-ACCESS read-write
		STATUS current
		DESCRIPTION
			"Defines the control character used to send a Telnet
			BREAK message."
		::= { terminalEntry 11 }

	terminalInterrupt OBJECT-TYPE
		SYNTAX DisplayString (SIZE(0..2))
		MAX-ACCESS read-write
		STATUS current
		DESCRIPTION
			"Defines the control character used to send a Telnet
			INTERRUPT message."
		::= { terminalEntry 12 }

	terminalAuthenticationType OBJECT-TYPE
        SYNTAX INTEGER  { none(0), local(1), radius(2) }
        MAX-ACCESS read-write
        STATUS current
        DESCRIPTION
            "The terminal authentication type."
        ::= { terminalEntry 13 }

    terminalAutoLoginPrompt OBJECT-TYPE
		SYNTAX DisplayString (SIZE(0..16))
		MAX-ACCESS read-write
		STATUS current
		DESCRIPTION
			"The prompt string for the automatic login ID. When the
			Terminal Server CN2600 series receives this string
			from a remote telnet/rlogin server, it will
			automatically reply with the user ID."
		::= { terminalEntry 14 }

	terminalPasswordPrompt OBJECT-TYPE
		SYNTAX DisplayString (SIZE(0..16))
		MAX-ACCESS read-write
		STATUS current
		DESCRIPTION
			"The prompt string for the automatic login password.
			When the Terminal Server CN2600 series receives this
			string from a remote telnet/rlogin server, it will
			automatically reply with the user password."
		::= { terminalEntry 15 }

	terminalLoginUserName OBJECT-TYPE
		SYNTAX DisplayString (SIZE(0..16))
		MAX-ACCESS read-write
		STATUS current
		DESCRIPTION
			"Terminal login ID for automatic login."
		::= { terminalEntry 16 }

	terminalLoginPassword OBJECT-TYPE
		SYNTAX DisplayString (SIZE(0..16))
		MAX-ACCESS read-write
		STATUS current
		DESCRIPTION
			"Terminal login password for automatic login."
		::= { terminalEntry 17 }

-- --------------------------------------------------------------------------------------
-- Serial port settings -> Operation Modes settings -> Application -> Reverse Terminal
-- --------------------------------------------------------------------------------------

	reverseTerminal OBJECT IDENTIFIER ::= { application 6 }

	reverseTerminalTable OBJECT-TYPE
        SYNTAX SEQUENCE OF ReverseTerminalEntry
        MAX-ACCESS not-accessible
        STATUS current
        DESCRIPTION
            "The Reverse Terminal Application table."
        ::= { reverseTerminal 1 }

    reverseTerminalEntry OBJECT-TYPE
        SYNTAX ReverseTerminalEntry
        MAX-ACCESS not-accessible
        STATUS current
        DESCRIPTION
            "The Reverse Terminal Application entry."
        INDEX { portIndex }
        ::= { reverseTerminalTable 1 }

    ReverseTerminalEntry ::=
        SEQUENCE {
        	reverseTerminalTcpAliveCheck
        		INTEGER,
        	reverseTerminalInactivityTime
        		INTEGER,
            reverseTerminalTcpPort
            	INTEGER,
            reverseTerminalAuthenticationType
            	INTEGER,
            reverseTerminalMapKeys
            	INTEGER
        }

	reverseTerminalTcpAliveCheck OBJECT-TYPE
        SYNTAX INTEGER
        MAX-ACCESS read-write
        STATUS current
        DESCRIPTION
            "The TCP alive check time.
            0 min: TCP connection will not be closed when the
            TCP connection becomes idle.
            1 to 99 min: The Terminal Server CN2600 series device server
            automatically closes the TCP connection if there is
            no TCP activity for the given time. After the
            connection is closed, the Terminal Server CN2600 series device
            server starts listening for another connection."
        ::= { reverseTerminalEntry 1 }

	reverseTerminalInactivityTime OBJECT-TYPE
        SYNTAX INTEGER
        MAX-ACCESS read-write
        STATUS current
        DESCRIPTION
            "0 min: TCP connection will not be closed if the
            serial line becomes idle.
            0-99 min: The Terminal Server CN2600 series device server
            automatically closes the TCP connection if there is
            no serial data activity for the given time. After
            the connection is closed, the Terminal Server CN2600 series
            starts listening for another
            TCP connection."
        ::= { reverseTerminalEntry 2 }

	reverseTerminalTcpPort OBJECT-TYPE
		SYNTAX INTEGER
		MAX-ACCESS read-write
		STATUS current
		DESCRIPTION
			"Each of the Terminal Server CN2600 series device server's serial
			ports are mapped to a TCP port."
		::= { reverseTerminalEntry 3 }

	reverseTerminalAuthenticationType OBJECT-TYPE
		SYNTAX INTEGER  { none(0), local(1), radius(2) }
		MAX-ACCESS read-write
		STATUS current
		DESCRIPTION
			"The reverse terminal authentication type."
		::= { reverseTerminalEntry 4 }

	reverseTerminalMapKeys OBJECT-TYPE
		SYNTAX INTEGER  { cr-lf(0), cr(1), lf(2) }
		MAX-ACCESS read-write
		STATUS current
		DESCRIPTION
			"If data received through Terminal Server CN2600 series device
			server's Ethernet port is sent using the 'enter'
			command, the data will be transmitted out through
			the serial port with an added
			1. 'carriage return + line feed' if you select the
			'cr-lf' option (i.e., the cursor will jump to the
			next line, and return to the first character of the
			line)
			2. 'carriage return' if you select the 'cr' option
			(i.e., the cursor will return to the first character
			of the line
			3. 'line feed' if you select the 'lf' option. (i.e.,
			the cursor will jump to the next line, but not move
			horizontally)"
		::= { reverseTerminalEntry 5 }

-- --------------------------------------------------------------------------------------
-- Serial port settings -> Operation Modes settings -> Application -> Dial In/Out
-- --------------------------------------------------------------------------------------

	dial OBJECT IDENTIFIER ::= { application 7 }

	dialTable OBJECT-TYPE
        SYNTAX SEQUENCE OF DialEntry
        MAX-ACCESS not-accessible
        STATUS current
        DESCRIPTION
            "The Dial In/Out table."
        ::= { dial 1 }

    dialEntry OBJECT-TYPE
        SYNTAX DialEntry
        MAX-ACCESS not-accessible
        STATUS current
        DESCRIPTION
            "The Dial In/Out entry."
        INDEX { portIndex }
        ::= { dialTable 1 }

    DialEntry ::=
        SEQUENCE {
			dialTERMBINMode
            	INTEGER,
            dialPPPDMode
            	INTEGER,
            dialSLIPDMode
            	INTEGER,
            dialAuthType
            	INTEGER,
            dialDisconnectBy
            	INTEGER,
            dialDestinationIpAddress
            	IpAddress,
            dialSourceIpAddress
            	IpAddress,
            dialIpNetmask
            	IpAddress,
            dialTcpIpCompression
            	INTEGER,
            dialInactivityTime
            	INTEGER,
            dialLinkQualityReport
            	INTEGER,
            dialOutgoingPAPID
            	DisplayString,
            dialPAPPassword
            	DisplayString,
            dialIncomingPAPCheck
            	INTEGER
        }

	dialTERMBINMode OBJECT-TYPE
        SYNTAX INTEGER  { no(0), yes(1) }
        MAX-ACCESS read-write
        STATUS current
        DESCRIPTION
            "Select Yes to enable a Binary Terminal connection."
        ::= { dialEntry 1 }

    dialPPPDMode OBJECT-TYPE
        SYNTAX INTEGER  { no(0), yes(1) }
        MAX-ACCESS read-write
        STATUS current
        DESCRIPTION
            "Select Yes to enable a PPPD connection."
        ::= { dialEntry 2 }

    dialSLIPDMode OBJECT-TYPE
        SYNTAX INTEGER  { no(0), yes(1) }
        MAX-ACCESS read-write
        STATUS current
        DESCRIPTION
            "Select Yes to enable a SLIPD Terminal connection."
        ::= { dialEntry 3 }

    dialAuthType OBJECT-TYPE
        SYNTAX INTEGER  { none(0), local(1), radius(2) }
        MAX-ACCESS read-write
        STATUS current
        DESCRIPTION
            "The dial in/out authentication type."
        ::= { dialEntry 4 }

    dialDisconnectBy OBJECT-TYPE
        SYNTAX INTEGER  { none(0), dcd-off(2), dsr-off(4) }
        MAX-ACCESS read-write
        STATUS current
        DESCRIPTION
            "If this field is set to 'dcd-off,' the connection
            will be disconnected when the DCD signal is off.
            If this field is set to 'dsr-off,' the connection
            will be disconnected when the DSR signal is off."
        ::= { dialEntry 5 }

	dialDestinationIpAddress OBJECT-TYPE
		SYNTAX IpAddress
		MAX-ACCESS read-write
		STATUS current
		DESCRIPTION
			"Destination IP address is the IP address of the
			remote dial-in/dial-out server."
		::= { dialEntry 6 }

	dialSourceIpAddress OBJECT-TYPE
		SYNTAX IpAddress
		MAX-ACCESS read-write
		STATUS current
		DESCRIPTION
			"Source IP address is IP address of this serial
			port. The Terminal Server CN2600 series will
			automatically assign an IP address for the port.
			We recommend leaving this field blank."
		::= { dialEntry 7 }

	dialIpNetmask OBJECT-TYPE
		SYNTAX IpAddress
		MAX-ACCESS read-write
		STATUS current
		DESCRIPTION
			"The IP netmask used for dial-in/dial-out networks
			(PPP or SLIP)."
		::= { dialEntry 8 }

	dialTcpIpCompression OBJECT-TYPE
		SYNTAX INTEGER { no(0), yes(1)}
		MAX-ACCESS read-write
		STATUS current
		DESCRIPTION
			"Depends on whether the remote user's application
			requests compression."
		::= { dialEntry 9 }

	dialInactivityTime OBJECT-TYPE
        SYNTAX INTEGER
        MAX-ACCESS read-write
        STATUS current
        DESCRIPTION
            "0 ms: TCP connection will not be closed if the
            serial line becomes idle.
            1-65535 ms: The Terminal Server CN2600 series device server
            automatically closes the TCP connection if there is
            no serial data activity for the given time. After
            the connection is closed, the Terminal Server CN2600 series
            starts listening for another
            TCP connection."
        ::= { dialEntry 10 }

	dialLinkQualityReport OBJECT-TYPE
		SYNTAX INTEGER { no(0), yes(1)}
		MAX-ACCESS read-write
		STATUS current
		DESCRIPTION
			"Choose YES if you are using software to collect Link quality
			information."
		::= { dialEntry 11 }

	dialOutgoingPAPID OBJECT-TYPE
		SYNTAX DisplayString
		MAX-ACCESS read-write
		STATUS current
		DESCRIPTION
			"Dial-out user ID account."
		::= { dialEntry 12 }

	dialPAPPassword OBJECT-TYPE
		SYNTAX DisplayString
		MAX-ACCESS read-write
		STATUS current
		DESCRIPTION
			"Dial-out user password."
		::= { dialEntry 13 }

	dialIncomingPAPCheck OBJECT-TYPE
        SYNTAX INTEGER  { none(0), local(1), radius(2) }
        MAX-ACCESS read-write
        STATUS current
        DESCRIPTION
            "The Dial in/out incoming PAP check type."
        ::= { dialEntry 14 }

-- --------------------------------------------------------------------------------------
-- Serial port settings -> Operation Modes settings -> Data Packing
-- --------------------------------------------------------------------------------------

	dataPacking OBJECT IDENTIFIER ::= { opModeSetting 3 }

	dataPackingPortTable OBJECT-TYPE
        SYNTAX SEQUENCE OF DataPackingPortEntry
        MAX-ACCESS not-accessible
        STATUS current
        DESCRIPTION
            "The Data Packing table."
        ::= { dataPacking 1 }

    dataPackingPortEntry OBJECT-TYPE
        SYNTAX DataPackingPortEntry
        MAX-ACCESS not-accessible
        STATUS current
        DESCRIPTION
            "The Data Packing entry."
        INDEX { portIndex }
        ::= { dataPackingPortTable 1 }

    DataPackingPortEntry ::=
        SEQUENCE {
            portPacketLength
                INTEGER,
            portDelimiter1Enable
                INTEGER,
            portDelimiter1
            	DisplayString,
            portDelimiter2Enable
                INTEGER,
            portDelimiter2
            	DisplayString,
            portDelimiterProcess
            	INTEGER,
            portForceTransmit
            	INTEGER
        }

	portPacketLength OBJECT-TYPE
        SYNTAX INTEGER
        MAX-ACCESS read-write
        STATUS current
        DESCRIPTION
            "If the value is 0, the Delimiter Process will be
            used, regardless of the length of the data
            packet. If the data length (in bytes) matches the
            configured value, the data will be forced out. The
            data length can be configured from 0 to 1024 bytes.
            Set to 0 if you do not need to limit the length."
        ::= { dataPackingPortEntry 1 }

    portDelimiter1Enable OBJECT-TYPE
		SYNTAX INTEGER {disable(0), enable(1)}
		MAX-ACCESS read-write
		STATUS current
		DESCRIPTION
			"Enable the first delimiter character."
		::= { dataPackingPortEntry 2 }

	portDelimiter1 OBJECT-TYPE
		SYNTAX DisplayString (SIZE(0..2))
		MAX-ACCESS read-write
		STATUS current
		DESCRIPTION
			"The first delimiter character, in hex decimal."
		::= { dataPackingPortEntry 3 }

	portDelimiter2Enable OBJECT-TYPE
		SYNTAX INTEGER {disable(0), enable(1)}
		MAX-ACCESS read-write
		STATUS current
		DESCRIPTION
			"Enable the second delimiter character."
		::= { dataPackingPortEntry 4 }

	portDelimiter2 OBJECT-TYPE
		SYNTAX DisplayString (SIZE(0..2))
		MAX-ACCESS read-write
		STATUS current
		DESCRIPTION
			"The second delimiter character, in hex decimal."
		::= { dataPackingPortEntry 5 }

	portDelimiterProcess OBJECT-TYPE
		SYNTAX INTEGER {
			doNothing(1),
			delimiterAddOne(2),
			delimiterAddTwo(4),
			stripDelimiter(8)
			}
		MAX-ACCESS read-write
		STATUS current
		DESCRIPTION
			"'delimiterAddOne' or 'delimiterAddTwo': The data
			will be transmitted when an additional byte (for
			'delimiterAddOne'), or an additional 2 bytes (for
			'delimiterAddTwo') of data is received after
			receiving the Delimiter.
			'stripDelimiter': When the delimiter is received,
			the Delimiter is deleted (i.e., stripped), and the
			remaining data is transmitted.
			'doNothing': The data will be transmitted when the
			delimiter is received."
		::= { dataPackingPortEntry 6 }

	portForceTransmit OBJECT-TYPE
		SYNTAX INTEGER
		MAX-ACCESS read-write
		STATUS current
		DESCRIPTION
			"0: Disable the force transmit timeout.
			1 to 65535: Forces the Terminal Server CN2600 series device
			server's TCP/IP protocol software to try to pack
			serial data received during the specified time into
			the same data frame."
		::= { dataPackingPortEntry 7 }

-- -------------------------------------------------------------
-- Serial port settings -> Communication Parameters settings
-- -------------------------------------------------------------

	comParamSetting OBJECT IDENTIFIER ::= { portSetting 2 }

    comParamPortTable OBJECT-TYPE
        SYNTAX SEQUENCE OF ComParamPortEntry
        MAX-ACCESS not-accessible
        STATUS current
        DESCRIPTION
            "The Communication Parameters table."
        ::= { comParamSetting 1 }

    comParamPortEntry OBJECT-TYPE
        SYNTAX ComParamPortEntry
        MAX-ACCESS not-accessible
        STATUS current
        DESCRIPTION
            "The Communication Parameters entry."
        INDEX { portIndex }
        ::= { comParamPortTable 1 }

    ComParamPortEntry ::=
        SEQUENCE {
            portAlias
                DisplayString,
            portInterface
            	INTEGER,
            portBaudRate
                INTEGER,
            portBaudRateManual
                INTEGER,
            portDataBits
                INTEGER,
            portStopBits
				INTEGER,
			portParity
				INTEGER,
			portFlowControl
				INTEGER,
			portFIFO
				INTEGER
        }

    portAlias OBJECT-TYPE
		SYNTAX DisplayString (SIZE(0..16))
		MAX-ACCESS read-write
		STATUS current
		DESCRIPTION
		"Port alias is included to allow easy identification of
		the serial devices that are connected to Terminal Server CN2600
		series device server's serial port."
		::= { comParamPortEntry 1 }

    portInterface OBJECT-TYPE
		SYNTAX INTEGER  {
			rs-232(0),
			rs-422(1),
			rs-485-2-wire(2),
			rs-485-4-wire(3)
		}
		MAX-ACCESS read-write
		STATUS current
		DESCRIPTION
			"The serial interface that the port works on."
		::= { comParamPortEntry 2 }

	portBaudRate OBJECT-TYPE
		SYNTAX INTEGER  {
			b50(0),
			b75(1),
			b110(2),
			b134(3),
			b150(4),
			b300(5),
			b600(6),
			b1200(7),
			b1800(8),
			b2400(9),
			b4800(10),
			b7200(11),
			b9600(12),
			b19200(13),
			b38400(14),
			b57600(15),
			b115200(16),
			b230400(17),
			b460800(18),
			b921600(19)
		}
		MAX-ACCESS read-write
		STATUS current
		DESCRIPTION
			"The port's speed in bits per second. You can choose
			a standard baud rate by indexing."
		::= { comParamPortEntry 3 }

	portBaudRateManual OBJECT-TYPE
        SYNTAX INTEGER
        MAX-ACCESS read-write
        STATUS current
        DESCRIPTION
            "The port's speed in bits per second. You can
            specify a baud rate manually."
        ::= { comParamPortEntry 4 }

    portDataBits OBJECT-TYPE
		SYNTAX INTEGER  {
			bits-5(0),
			bits-6(1),
			bits-7(2),
			bits-8(3)
		}
		MAX-ACCESS read-write
		STATUS current
		DESCRIPTION
			"The number of bits in a character for the port."
		::= { comParamPortEntry 5 }

	portStopBits OBJECT-TYPE
		SYNTAX INTEGER  {
			bits-1(0),
			bits-1dot5(1),
			bits-2(2)
		}
		MAX-ACCESS read-write
		STATUS current
		DESCRIPTION
			"The number of stop bits for the port."
		::= { comParamPortEntry 6 }

	portParity OBJECT-TYPE
		SYNTAX INTEGER  {
			none(0),
			odd(1),
			even(2),
			mark(3),
			space(4)
		}
		MAX-ACCESS read-write
		STATUS current
		DESCRIPTION
			"The parity bit for the port."
		::= { comParamPortEntry 7 }

	portFlowControl OBJECT-TYPE
		SYNTAX INTEGER  {
			none(0),
			rts-cts(1),
			xon-xoff(2),
			dtr-dsr(3)
		}
		MAX-ACCESS read-write
		STATUS current
		DESCRIPTION
			"The flow-control method for the port."
		::= { comParamPortEntry 8 }

	portFIFO OBJECT-TYPE
		SYNTAX INTEGER  {
			disable(0),
			enable(1)
		}
		MAX-ACCESS read-write
		STATUS current
		DESCRIPTION
			"Enable or disable the port's FIFO."
		::= { comParamPortEntry 9 }

-- --------------------------------------------------------------------------------------
-- Serial port settings -> Data Buffering/Log
-- --------------------------------------------------------------------------------------

	dataBuffering OBJECT IDENTIFIER ::= { portSetting 3 }

	dataBufferingPortTable OBJECT-TYPE
        SYNTAX SEQUENCE OF DataBufferingPortEntry
        MAX-ACCESS not-accessible
        STATUS current
        DESCRIPTION
            "The Data Buffering/Log table."
        ::= { dataBuffering 1 }

    dataBufferingPortEntry OBJECT-TYPE
        SYNTAX DataBufferingPortEntry
        MAX-ACCESS not-accessible
        STATUS current
        DESCRIPTION
            "The Data Buffering/Log entry."
        INDEX { portIndex }
        ::= { dataBufferingPortTable 1 }

    DataBufferingPortEntry ::=
        SEQUENCE {
            portBufferingEnable
                INTEGER,
            portSerialDataLoggingEnable
            	INTEGER
        }

	portBufferingEnable OBJECT-TYPE
		SYNTAX INTEGER {no(0), yes(1)}
		MAX-ACCESS read-write
		STATUS current
		DESCRIPTION
			"Enable off-line port buffering."
		::= { dataBufferingPortEntry 1 }

	portSerialDataLoggingEnable OBJECT-TYPE
		SYNTAX INTEGER {no(0), yes(1)}
		MAX-ACCESS read-write
		STATUS current
		DESCRIPTION
			"Enable or disable serial data logging for the port."
		::= { dataBufferingPortEntry 2 }

-- --------------------------------------------------------------------------------------
-- Serial port settings -> Modem Settings
-- --------------------------------------------------------------------------------------

	modemSettings OBJECT IDENTIFIER ::= { portSetting 4 }

	modemSettingsPortTable OBJECT-TYPE
        SYNTAX SEQUENCE OF ModemSettingsPortEntry
        MAX-ACCESS not-accessible
        STATUS current
        DESCRIPTION
            "The Modem Settings table."
        ::= { modemSettings 1 }

    modemSettingsPortEntry OBJECT-TYPE
        SYNTAX ModemSettingsPortEntry
        MAX-ACCESS not-accessible
        STATUS current
        DESCRIPTION
            "The Modem Settings entry."
        INDEX { portIndex }
        ::= { modemSettingsPortTable 1 }

    ModemSettingsPortEntry ::=
        SEQUENCE {
            portEnableModem
				INTEGER,
			portInitialString
				DisplayString,
			portDialUp
				DisplayString,
			portPhoneNumber
				DisplayString
        }

	portEnableModem OBJECT-TYPE
		SYNTAX INTEGER  { disable(0), enable(1) }
		MAX-ACCESS read-write
		STATUS current
		DESCRIPTION
			"Enable or disable modem for this port."
		::= { modemSettingsPortEntry 1 }

	portInitialString OBJECT-TYPE
		SYNTAX DisplayString (SIZE(0..24))
		MAX-ACCESS read-write
		STATUS current
		DESCRIPTION
		"Set the modem's initial string to establish the
		connection. E.g., 'AT&S0=1' for auto-answer."
		::= { modemSettingsPortEntry 2 }

	portDialUp OBJECT-TYPE
		SYNTAX DisplayString (SIZE(0..8))
		MAX-ACCESS read-write
		STATUS current
		DESCRIPTION
		"Set the modem's dial-up AT command string."
		::= { modemSettingsPortEntry 3 }

	portPhoneNumber OBJECT-TYPE
		SYNTAX DisplayString (SIZE(0..16))
		MAX-ACCESS read-write
		STATUS current
		DESCRIPTION
		"Set the number used to dial out."
		::= { modemSettingsPortEntry 4 }

-- --------------------------------------------------------------------------------------
-- Serial port settings -> Welcome Message
-- --------------------------------------------------------------------------------------

	welcomeMessage OBJECT IDENTIFIER ::= { portSetting 5 }

	portEnableWelcomeMessage OBJECT-TYPE
		SYNTAX INTEGER  { disable(0), enable(1) }
		MAX-ACCESS read-write
		STATUS current
		DESCRIPTION
			"Enable or disable the welcome message."
		::= { welcomeMessage 1 }

	portMessage OBJECT-TYPE
		SYNTAX DisplayString (SIZE(0..1280))
		MAX-ACCESS read-write
		STATUS current
		DESCRIPTION
		"Set up a welcome message to greet dial-in users."
		::= { welcomeMessage 2 }

-- -------------------------------------------------------------
-- System Management
-- -------------------------------------------------------------

	sysManagement OBJECT IDENTIFIER ::= { swMgmt 5 }

-- -------------------------------------------------------------
-- System Management -> Misc. Network Settings
-- -------------------------------------------------------------

	miscNetworkSettings OBJECT IDENTIFIER ::= { sysManagement 1 }

-- ----------------------------------------------------------------------------
-- System Management -> Misc. Network Settings -> Accessible IP List
-- ----------------------------------------------------------------------------

	accessibleIp OBJECT IDENTIFIER ::= { miscNetworkSettings 1 }

	enableAccessibleIpList  OBJECT-TYPE
        SYNTAX INTEGER { disable(0), enable(1)}
        MAX-ACCESS read-write
        STATUS current
        DESCRIPTION
            "Enable or disable the entire accessible IP list."
		::= { accessibleIp 1 }

	accessibleIpListTable OBJECT-TYPE
        SYNTAX SEQUENCE OF AccessibleIpListEntry
        MAX-ACCESS not-accessible
        STATUS current
        DESCRIPTION
            "Accessible IP List table."
        ::= { accessibleIp 2 }

    accessibleIpListEntry OBJECT-TYPE
        SYNTAX AccessibleIpListEntry
        MAX-ACCESS not-accessible
        STATUS current
        DESCRIPTION
            "Accessible IP List entry."
        INDEX { activeAccessibleIpList }
        ::= { accessibleIpListTable 1 }

    AccessibleIpListEntry ::=
        SEQUENCE {
        	accessibleIpListIndex
       			INTEGER,
            activeAccessibleIpList
            	INTEGER,
            accessibleIpListAddress
                IpAddress,
            accessibleIpListNetmask
                IpAddress
        }

	accessibleIpListIndex OBJECT-TYPE
        SYNTAX INTEGER
        MAX-ACCESS read-only
        STATUS current
        DESCRIPTION
            "Accessible IP List index."
        ::= { accessibleIpListEntry 1 }

	activeAccessibleIpList  OBJECT-TYPE
        SYNTAX INTEGER { disable(0), enable(1)}
        MAX-ACCESS read-write
        STATUS current
        DESCRIPTION
            "Enable or disable this accessible IP entry."
		::= { accessibleIpListEntry 2 }

	accessibleIpListAddress  OBJECT-TYPE
        SYNTAX IpAddress
        MAX-ACCESS read-write
        STATUS current
        DESCRIPTION
            "Accessible IP address. This value can be the IP address of a
	    single host if the netmask is set to '255.255.255.255,'
            or it can be a network address."
		::= { accessibleIpListEntry 3 }

	accessibleIpListNetmask  OBJECT-TYPE
        SYNTAX IpAddress
        MAX-ACCESS read-write
        STATUS current
        DESCRIPTION
            "Accessible IP address netmask. The IP address and
            netmask are used to specify a group of remote hosts."
		::= { accessibleIpListEntry 4 }

-- ----------------------------------------------------------------------------
-- System Management -> Misc. Network Settings -> SNMP Agent Settings
-- ----------------------------------------------------------------------------

	snmpAgentSettings OBJECT IDENTIFIER ::= { miscNetworkSettings 2 }

	snmpEnable  OBJECT-TYPE
        SYNTAX INTEGER { disable(0), enable(1)}
        MAX-ACCESS read-write
        STATUS current
        DESCRIPTION
            "Enable or disable SNMP agent."
		::= { snmpAgentSettings 1 }

	snmpContactName OBJECT-TYPE
        SYNTAX DisplayString (SIZE(0..40))
        MAX-ACCESS read-write
        STATUS current
        DESCRIPTION
            "The SNMP contact information usually includes an
            emergency contact name and telephone or pager
            number."
        ::= { snmpAgentSettings 2 }

    snmpLocation OBJECT-TYPE
        SYNTAX DisplayString (SIZE(0..40))
        MAX-ACCESS read-write
        STATUS current
        DESCRIPTION
            "Specify the location string for SNMP agents, such as
            the Terminal Server CN2600 series device server. This string is
            usually set to the street address where the
            Terminal Server CN2600 series is physically located."
        ::= { snmpAgentSettings 3 }

-- ----------------------------------------------------------------------------
-- System Management -> Misc. Network Settings -> DDNS Settings
-- ----------------------------------------------------------------------------

	dDNS OBJECT IDENTIFIER ::= { miscNetworkSettings 3 }

	dDNSEnable  OBJECT-TYPE
        SYNTAX INTEGER {disable(0), enable(1)}
        MAX-ACCESS read-write
        STATUS current
        DESCRIPTION
            "Enable or disable the DDNS function."
		::= { dDNS 1 }

	dDNSServerAddress  OBJECT-TYPE
        SYNTAX INTEGER { dynDns-org(0) }
        MAX-ACCESS read-write
        STATUS current
        DESCRIPTION
            "The DDNS server address. The DDNS is serviced by a
            3-party provider. To use the DDNS function, you may
            need to obtain a user account from the server."
		::= { dDNS 2 }

	dDNSHostName  OBJECT-TYPE
        SYNTAX DisplayString (SIZE(0..60))
        MAX-ACCESS read-write
        STATUS current
        DESCRIPTION
            "The host name of the machine to be registered to
            the DDNS server."
		::= { dDNS 3 }

	dDNSUserName  OBJECT-TYPE
        SYNTAX DisplayString (SIZE(0..60))
        MAX-ACCESS read-write
        STATUS current
        DESCRIPTION
            "The user account provided by the DDNS server."
		::= { dDNS 4 }

	dDNSPassword  OBJECT-TYPE
        SYNTAX DisplayString (SIZE(0..60))
        MAX-ACCESS read-write
        STATUS current
        DESCRIPTION
            "The user password provided by the DDNS server."
		::= { dDNS 5 }

-- ----------------------------------------------------------------------------
-- System Management -> Misc. Network Settings -> Host Table
-- ----------------------------------------------------------------------------

	hostTable OBJECT IDENTIFIER ::= { miscNetworkSettings 4 }

	hostTableTable OBJECT-TYPE
        SYNTAX SEQUENCE OF HostTableEntry
        MAX-ACCESS not-accessible
        STATUS current
        DESCRIPTION
            "Host Table."
        ::= { hostTable 1 }

    hostTableEntry OBJECT-TYPE
        SYNTAX HostTableEntry
        MAX-ACCESS not-accessible
        STATUS current
        DESCRIPTION
            "Host Table entry."
        INDEX { hostTableIndex }
        ::= { hostTableTable 1 }

    HostTableEntry ::=
        SEQUENCE {
        	hostTableIndex
        		INTEGER,
            hostName
                DisplayString,
            hostIpAddress
            	IpAddress
        }

	hostTableIndex OBJECT-TYPE
        SYNTAX INTEGER
        MAX-ACCESS read-only
        STATUS current
        DESCRIPTION
            "The Host Table index."
        ::= { hostTableEntry 1 }

	hostName  OBJECT-TYPE
        SYNTAX DisplayString (SIZE(0..16))
        MAX-ACCESS read-write
        STATUS current
        DESCRIPTION
            "The host name of the host table entry."
		::= { hostTableEntry 2 }

	hostIpAddress  OBJECT-TYPE
        SYNTAX IpAddress
        MAX-ACCESS read-write
        STATUS current
        DESCRIPTION
            "Related IP address of the host table entry."
		::= { hostTableEntry 3 }

-- ----------------------------------------------------------------------------
-- System Management -> Misc. Network Settings -> Route Table
-- ----------------------------------------------------------------------------

	routeTable OBJECT IDENTIFIER ::= { miscNetworkSettings 5 }

	routeTableTable OBJECT-TYPE
        SYNTAX SEQUENCE OF RouteTableEntry
        MAX-ACCESS not-accessible
        STATUS current
        DESCRIPTION
            "Route Table."
        ::= { routeTable 1 }

    routeTableEntry OBJECT-TYPE
        SYNTAX RouteTableEntry
        MAX-ACCESS not-accessible
        STATUS current
        DESCRIPTION
            "Route Table entry."
        INDEX { routeTableIndex }
        ::= { routeTableTable 1 }

    RouteTableEntry ::=
        SEQUENCE {
        	routeTableIndex
        		INTEGER,
            gatewayRouteTable
                IpAddress,
            destinationRouteTable
            	IpAddress,
            netmaskRouteTable
            	IpAddress,
            metricRouteTable
            	INTEGER,
            interfaceRouteTable
            	INTEGER
        }

	routeTableIndex OBJECT-TYPE
        SYNTAX INTEGER
        MAX-ACCESS read-only
        STATUS current
        DESCRIPTION
            "The Route Table index."
        ::= { routeTableEntry 1 }

	gatewayRouteTable  OBJECT-TYPE
        SYNTAX IpAddress
        MAX-ACCESS read-write
        STATUS current
        DESCRIPTION
            "The gateway property of the route table entry."
		::= { routeTableEntry 2 }

	destinationRouteTable  OBJECT-TYPE
        SYNTAX IpAddress
        MAX-ACCESS read-write
        STATUS current
        DESCRIPTION
            "The destination IP address of the route table entry.
            This value can be the IP address of a single host if
	    the netmask set to
            '255.255.255.255,' or it can be a network address."
		::= { routeTableEntry 3 }

	netmaskRouteTable  OBJECT-TYPE
        SYNTAX IpAddress
        MAX-ACCESS read-write
        STATUS current
        DESCRIPTION
            "The destination netmask of the route table entry."
		::= { routeTableEntry 4 }

	metricRouteTable  OBJECT-TYPE
        SYNTAX INTEGER
        MAX-ACCESS read-write
        STATUS current
        DESCRIPTION
            "The routing metric for this route. The semantics of
            this metric are determined by the routing-protocol.
            Normally, it represents the cost for the destination."
		::= { routeTableEntry 5 }

	interfaceRouteTable  OBJECT-TYPE
        SYNTAX INTEGER {
        	port1(0),
        	port2(1),
        	port3(2),
        	port4(3),
        	port5(4),
        	port6(5),
        	port7(6),
        	port8(7),
        	port9(8),
        	port10(9),
        	port11(10),
        	port12(11),
        	port13(12),
        	port14(13),
        	port15(14),
        	port16(15),
        	lan1(256),
        	lan2(257)
        }
        MAX-ACCESS read-write
        STATUS current
        DESCRIPTION
            "The value that identifies the local interface
            through which the next hop of this route should be
            reached."
		::= { routeTableEntry 6 }

-- ----------------------------------------------------------------------------
-- System Management -> Misc. Network Settings -> User Table
-- ----------------------------------------------------------------------------

	userTable OBJECT IDENTIFIER ::= { miscNetworkSettings 6 }

	userTableTable OBJECT-TYPE
        SYNTAX SEQUENCE OF UserTableEntry
        MAX-ACCESS not-accessible
        STATUS current
        DESCRIPTION
            "User Table."
        ::= { userTable 1 }

    userTableEntry OBJECT-TYPE
        SYNTAX UserTableEntry
        MAX-ACCESS not-accessible
        STATUS current
        DESCRIPTION
            "User Table entry."
        INDEX { userTableIndex }
        ::= { userTableTable 1 }

    UserTableEntry ::=
        SEQUENCE {
        	userTableIndex
        		INTEGER,
            userNameUserTable
                DisplayString,
            passwordUserTable
            	DisplayString,
            phoneNumberUserTable
            	DisplayString
        }

    userTableIndex OBJECT-TYPE
        SYNTAX INTEGER
        MAX-ACCESS read-only
        STATUS current
        DESCRIPTION
            "The User Table index."
        ::= { userTableEntry 1 }

	userNameUserTable  OBJECT-TYPE
        SYNTAX DisplayString (SIZE(0..16))
        MAX-ACCESS read-write
        STATUS current
        DESCRIPTION
            "The user name of this entry."
		::= { userTableEntry 2 }

	passwordUserTable  OBJECT-TYPE
        SYNTAX DisplayString (SIZE(0..16))
        MAX-ACCESS read-write
        STATUS current
        DESCRIPTION
            "The password of this user entry."
		::= { userTableEntry 3 }

	phoneNumberUserTable  OBJECT-TYPE
        SYNTAX DisplayString (SIZE(0..16))
        MAX-ACCESS read-write
        STATUS current
        DESCRIPTION
            "The phone number of this user entry."
		::= { userTableEntry 4 }

-- ----------------------------------------------------------------------------
-- System Management -> Misc. Network Settings -> Authentication Server
-- ----------------------------------------------------------------------------

	authenticationServer OBJECT IDENTIFIER ::= { miscNetworkSettings 7 }

	radiusServerIp  OBJECT-TYPE
        SYNTAX DisplayString
        MAX-ACCESS read-write
        STATUS current
        DESCRIPTION
            "The IP address or domain name of the RADIUS server."
		::= { authenticationServer 1 }

	radiusKey  OBJECT-TYPE
        SYNTAX DisplayString (SIZE(0..16))
        MAX-ACCESS read-write
        STATUS current
        DESCRIPTION
            "RADIUS password. Must be the same as in the RADIUS
            server."
		::= { authenticationServer 2 }

	udpPortAuthenticationServer  OBJECT-TYPE
        SYNTAX INTEGER { port1645(1645), port1812(1812)}
        MAX-ACCESS read-write
        STATUS current
        DESCRIPTION
            "The UDP port of the RADIUS server."
		::= { authenticationServer 3 }

	radiusAccounting  OBJECT-TYPE
        SYNTAX INTEGER { disable(0), enable(1)}
        MAX-ACCESS read-write
        STATUS current
        DESCRIPTION
            "Enable or disable RADIUS accounting."
		::= { authenticationServer 4 }

-- ----------------------------------------------------------------------------
-- System Management -> Misc. Network Settings -> System Log Settings
-- ----------------------------------------------------------------------------

	sysLogSettings OBJECT IDENTIFIER ::= { miscNetworkSettings 8 }

	sysLocalLog  OBJECT-TYPE
        SYNTAX INTEGER { disable(0), enable(1)}
        MAX-ACCESS read-write
        STATUS current
        DESCRIPTION
            "Log the following events to the system log: System Cold Start,
             System Warm Start, Power Down."
		::= { sysLogSettings 1 }

	networkLocalLog  OBJECT-TYPE
        SYNTAX INTEGER { disable(0), enable(1)}
        MAX-ACCESS read-write
        STATUS current
        DESCRIPTION
            "Log the following events to the system log:
            DHCP/BOOTP/PPPoE Get IP/Renew, NTP, Mail Fail, NTP
            Connect Fail, DHCP Fail, IP Conflict, Ethernet Link
            Down."
		::= { sysLogSettings 2 }

	configLocalLog  OBJECT-TYPE
        SYNTAX INTEGER { disable(0), enable(1)}
        MAX-ACCESS read-write
        STATUS current
        DESCRIPTION
            "Log the following events to the system log: Login Fail, IP
            Changed, Password Changed, Config Changed, Firmware
            Upgrade, SSL Key Import, Config Import, Config
            Export."
		::= { sysLogSettings 3 }

	opModeLocalLog  OBJECT-TYPE
        SYNTAX INTEGER { disable(0), enable(1)}
        MAX-ACCESS read-write
        STATUS current
        DESCRIPTION
            "Log the following op-mode events to the system log:
            Connect, Disconnect, Authentication Fail, Restart."
		::= { sysLogSettings 4 }


-- -------------------------------------------------------------
-- System Management -> Auto Warning Settings
-- -------------------------------------------------------------

	autoWarningSettings OBJECT IDENTIFIER ::= { sysManagement 2 }

-- -------------------------------------------------------------
-- System Management -> Auto Warning Settings -> Event Settings
-- -------------------------------------------------------------

	eventSettings OBJECT IDENTIFIER ::= { autoWarningSettings 1 }

	mailWarningColdStart OBJECT-TYPE
        SYNTAX INTEGER  { disable(0), enable(1) }
        MAX-ACCESS read-write
        STATUS current
        DESCRIPTION
            "Refers to starting the system from power off
            (contrast this with warm start). When performing a
            cold start, the Terminal Server CN2600 series will
            automatically issue an auto warning message by
            e-mail after booting up."
        ::= { eventSettings 1 }

    mailWarningWarmStart OBJECT-TYPE
        SYNTAX INTEGER  { disable(0), enable(1) }
        MAX-ACCESS read-write
        STATUS current
        DESCRIPTION
            "Refers to restarting the Terminal Server CN2600 without
            turning the power off. When performing a warm start,
            the Terminal Server CN2600 series will
            automatically send an e-mail after rebooting."
        ::= { eventSettings 2 }

    mailWarningPower1Down OBJECT-TYPE
        SYNTAX INTEGER  { disable(0), enable(1) }
        MAX-ACCESS read-write
        STATUS current
        DESCRIPTION
            "On dual power model, when power 1 is off,
            the Terminal Server CN2600 series will immediately send an e-mail."
        ::= { eventSettings 3 }

    mailWarningPower2Down OBJECT-TYPE
        SYNTAX INTEGER  { disable(0), enable(1) }
        MAX-ACCESS read-write
        STATUS current
        DESCRIPTION
            "On dual power model, when power 2 is off,
            the Terminal Server CN2600 series will immediately send an e-mail."
        ::= { eventSettings 4 }

    mailWarningEthernet1LinkDown OBJECT-TYPE
        SYNTAX INTEGER  { disable(0), enable(1) }
        MAX-ACCESS read-write
        STATUS current
        DESCRIPTION
            "When the built-in link1 port is off, the Terminal Server CN2600
            series will immediately send an e-mail."
        ::= { eventSettings 5 }

    mailWarningEthernet2LinkDown OBJECT-TYPE
        SYNTAX INTEGER  { disable(0), enable(1) }
        MAX-ACCESS read-write
        STATUS current
        DESCRIPTION
            "When the built-in link2 port is off, the Terminal Server CN2600
            series will immediately send an e-mail."
        ::= { eventSettings 6 }

    mailWarningAuthFailure OBJECT-TYPE
        SYNTAX INTEGER  { disable(0), enable(1) }
        MAX-ACCESS read-write
        STATUS current
        DESCRIPTION
            "The user inputs a wrong password from the Console
            or Administrator. When authentication failure
            occurs, the Terminal Server CN2600 series will
            immediately send an e-mail."
        ::= { eventSettings 7 }

    mailWarningIpChanged OBJECT-TYPE
        SYNTAX INTEGER  { disable(0), enable(1) }
        MAX-ACCESS read-write
        STATUS current
        DESCRIPTION
            "The user has changed the Terminal Server CN2600 series device
            server's IP address. When the IP address changes,
            the Terminal Server CN2600 series will send an
            e-mail with the new IP address before it reboots.
            If the Terminal Server CN2600 series is unable to
            send an e-mail message to the mail server within 15
            seconds, it will reboot anyway, and abort the e-mail
            auto warning."
        ::= { eventSettings 8 }

    mailWarningPasswordChanged OBJECT-TYPE
        SYNTAX INTEGER  { disable(0), enable(1) }
        MAX-ACCESS read-write
        STATUS current
        DESCRIPTION
            "The user has changed the Terminal Server CN2600 series device
            server's password. When the password changes, the
            Terminal Server CN2600 series will send an e-mail
            with the password changed notice before it reboots.
            If the Terminal Server CN2600 series is unable to
            send an e-mail message to the mail server within 15
            seconds, it will reboot anyway, and abort the e-mail
            auto warning."
        ::= { eventSettings 9 }

	trapServerColdStart OBJECT-TYPE
        SYNTAX INTEGER  { disable(0), enable(1) }
        MAX-ACCESS read-write
        STATUS current
        DESCRIPTION
            "Refers to starting the system from power off
            (contrast this with warm start). When performing a
            cold start, the Terminal Server CN2600 series will
            automatically issue an auto warning message by sending
            a SNMP trap after booting up."
        ::= { eventSettings 10 }

    trapServerWarmStart OBJECT-TYPE
        SYNTAX INTEGER  { disable(0), enable(1) }
        MAX-ACCESS read-write
        STATUS current
        DESCRIPTION
            "Refers to restarting the Terminal Server CN2600 without
            turning the power off. When performing a warm start,
            the Terminal Server CN2600 series will
            automatically send a SNMP trap after rebooting."
        ::= { eventSettings 11 }

    trapServerEthernet1LinkDown OBJECT-TYPE
        SYNTAX INTEGER  { disable(0), enable(1) }
        MAX-ACCESS read-write
        STATUS current
        DESCRIPTION
            "When the built-in link1 port is off, the Terminal Server CN2600
            series will immediately send a SNMP trap."
        ::= { eventSettings 12 }

    trapServerEthernet2LinkDown OBJECT-TYPE
        SYNTAX INTEGER  { disable(0), enable(1) }
        MAX-ACCESS read-write
        STATUS current
        DESCRIPTION
            "When the built-in link2 port is off, the Terminal Server CN2600
            series will immediately send a SNMP trap."
        ::= { eventSettings 13 }

    trapServerAuthFailure OBJECT-TYPE
        SYNTAX INTEGER  { disable(0), enable(1) }
        MAX-ACCESS read-write
        STATUS current
        DESCRIPTION
            "The user inputs a wrong password from the Console
            or Administrator. When authentication failure
            occurs, the Terminal Server CN2600 series will
            immediately send a SNMP trap."
        ::= { eventSettings 14 }

-- -------------------------------------------------------------
-- System Management -> Auto Warning Settings -> Serial Event Settings
-- -------------------------------------------------------------

	serialEventSettings OBJECT IDENTIFIER ::= { autoWarningSettings 2 }

	portEventSettingsTable OBJECT-TYPE
        SYNTAX SEQUENCE OF PortEventSettingsEntry
        MAX-ACCESS not-accessible
        STATUS current
        DESCRIPTION
            "Port Event Settings Table."
        ::= { serialEventSettings 1 }

    portEventSettingsEntry OBJECT-TYPE
        SYNTAX PortEventSettingsEntry
        MAX-ACCESS not-accessible
        STATUS current
        DESCRIPTION
            "Port Event Settings entry."
        INDEX { portIndex }
        ::= { portEventSettingsTable 1 }

    PortEventSettingsEntry ::=
        SEQUENCE {
        	mailDCDchange
        		INTEGER,
            trapDCDchange
                INTEGER,
            mailDSRchange
        		INTEGER,
            trapDSRchange
                INTEGER
        }

	mailDCDchange OBJECT-TYPE
        SYNTAX INTEGER { disable(0), enable(1)}
        MAX-ACCESS read-write
        STATUS current
        DESCRIPTION
            "A change in the DCD (Data Carrier Detect) signal
            indicates that the modem connection status has
            changed. For example, if the DCD signal changes to
            low, it indicates that the connection line is down.
            When the DCD signal changes to low, the Terminal Server CN2600
            series will immediately send an e-mail
            message."
        ::= { portEventSettingsEntry 1 }

	trapDCDchange OBJECT-TYPE
		SYNTAX INTEGER { disable(0), enable(1)}
		MAX-ACCESS read-write
		STATUS current
		DESCRIPTION
			"A change in the DCD (Data Carrier Detect) signal
            indicates that the modem connection status has
            changed. For example, if the DCD signal changes to
            low, it indicates that the connection line is down.
            When the DCD signal changes to low, the Terminal Server CN2600
            series will immediately send an SNMP
            trap."
		::= { portEventSettingsEntry 2 }

	mailDSRchange OBJECT-TYPE
        SYNTAX INTEGER { disable(0), enable(1)}
        MAX-ACCESS read-write
        STATUS current
        DESCRIPTION
            "A change in the DSR (Data Set Ready) signal
            indicates that the data communication equipment is
            powered off. For example, if the DSR signal changes
            to low, it indicates that the data communication
            equipment is powered down. When the DSR signal
            changes to low, the Terminal Server CN2600 series device server
            will immediately send an e-mail message."
        ::= { portEventSettingsEntry 3 }

	trapDSRchange OBJECT-TYPE
		SYNTAX INTEGER { disable(0), enable(1)}
		MAX-ACCESS read-write
		STATUS current
		DESCRIPTION
			"A change in the DSR (Data Set Ready) signal
            indicates that the data communication equipment is
            powered off. For example, if the DSR signal changes
            to low, it indicates that the data communication
            equipment is powered down. When the DSR signal
            changes to low, the Terminal Server CN2600 series device server
            will immediately send an SNMP trap."
		::= { portEventSettingsEntry 4 }

-- -------------------------------------------------------------
-- System Management -> Auto Warning Settings -> E-mail Alert
-- -------------------------------------------------------------

	emailAlert OBJECT IDENTIFIER ::= { autoWarningSettings 3 }

	emailWarningMailServer OBJECT-TYPE
        SYNTAX DisplayString
        MAX-ACCESS read-write
        STATUS current
        DESCRIPTION
            "The e-mail server's IP address or domain name of
            the e-mail warning function."
        ::= { emailAlert 1 }

    emailRequiresAuthentication  OBJECT-TYPE
        SYNTAX INTEGER { non-require(0), require(1)}
        MAX-ACCESS read-write
        STATUS current
        DESCRIPTION
            "Set if the mail server requires user login."
        ::= { emailAlert 2 }

    emailWarningUserName OBJECT-TYPE
        SYNTAX DisplayString
        MAX-ACCESS read-write
        STATUS current
        DESCRIPTION
            "The user name used to log into the mail server if
            authentication is required."
        ::= { emailAlert 3 }

    emailWarningPassword OBJECT-TYPE
        SYNTAX DisplayString
        MAX-ACCESS read-write
        STATUS current
        DESCRIPTION
            "The password used to log into the mail server if
            authentication is required."
        ::= { emailAlert 4 }

    emailWarningFromEmail OBJECT-TYPE
        SYNTAX DisplayString
        MAX-ACCESS read-write
        STATUS current
        DESCRIPTION
            "The e-mail address to be filled in the 'From' field of
            the auto-warning e-mail."
        ::= { emailAlert 5 }

    emailWarningFirstEmailAddr OBJECT-TYPE
        SYNTAX DisplayString
        MAX-ACCESS read-write
        STATUS current
        DESCRIPTION
            "The first email address to where the auto-warning
            e-mail is to be sent."
        ::= { emailAlert 6 }

    emailWarningSecondEmailAddr OBJECT-TYPE
        SYNTAX DisplayString
        MAX-ACCESS read-write
        STATUS current
        DESCRIPTION
            "The second email address to where the auto-warning
            e-mail is to be sent."
        ::= { emailAlert 7 }

    emailWarningThirdEmailAddr OBJECT-TYPE
        SYNTAX DisplayString
        MAX-ACCESS read-write
        STATUS current
        DESCRIPTION
            "The third email address to where the auto-warning
            e-mail is to be sent."
        ::= { emailAlert 8 }

    emailWarningFourthEmailAddr OBJECT-TYPE
        SYNTAX DisplayString
        MAX-ACCESS read-write
        STATUS current
        DESCRIPTION
            "The fourth email address to where the auto-warning
            e-mail is to be sent."
        ::= { emailAlert 9 }

-- -------------------------------------------------------------
-- System Management -> Auto Warning Settings -> SNMP Trap
-- -------------------------------------------------------------

	snmpTrap OBJECT IDENTIFIER ::= { autoWarningSettings 4 }

	snmpTrapReceiverIp  OBJECT-TYPE
        SYNTAX DisplayString
        MAX-ACCESS read-write
        STATUS current
        DESCRIPTION
            "SNMP trap server IP address or domain name."
		::= { snmpTrap 1 }

	trapVersion  OBJECT-TYPE
        SYNTAX INTEGER { v1(0), v2c(1)}
        MAX-ACCESS read-write
        STATUS current
        DESCRIPTION
            "SNMP trap version used for the auto-warning function."
		::= { snmpTrap 2 }

-- -------------------------------------------------------------
-- System Management -> Maintenance
-- -------------------------------------------------------------

	maintenance OBJECT IDENTIFIER ::= { sysManagement 3 }

-- ----------------------------------------------------------------------------
-- System Management -> Maintenance -> Console Settings
-- ----------------------------------------------------------------------------

	consoleSettings OBJECT IDENTIFIER ::= { maintenance 1 }

	httpConsole OBJECT-TYPE
        SYNTAX INTEGER { enable(0), disable(1)}
        MAX-ACCESS read-write
        STATUS current
        DESCRIPTION
            "Enable or disable HTTP console."
        ::= { consoleSettings 1 }

    httpsConsole OBJECT-TYPE
        SYNTAX INTEGER { enable(0), disable(1)}
        MAX-ACCESS read-write
        STATUS current
        DESCRIPTION
            "Enable or disable HTTPS console."
		::= { consoleSettings 2 }

	telnetConsole OBJECT-TYPE
        SYNTAX INTEGER { enable(0), disable(1)}
        MAX-ACCESS read-write
        STATUS current
        DESCRIPTION
            "Enable or disable Telnet console."
		::= { consoleSettings 3 }

	sshConsole OBJECT-TYPE
        SYNTAX INTEGER { enable(0), disable(1)}
        MAX-ACCESS read-write
        STATUS current
        DESCRIPTION
            "Enable or disable SSH console."
		::= { consoleSettings 4 }

	resetButtonFunction OBJECT-TYPE
        SYNTAX INTEGER { always-enable(0), disable-after-60-sec(1)}
        MAX-ACCESS read-write
        STATUS current
        DESCRIPTION
            "Enable or disable reset button protection. You can
            disable the hardware reset button after the Terminal Server CN2600
            series has been restarted for 60 seconds."
		::= { consoleSettings 5 }

	lcmReadOnlyProtect OBJECT-TYPE
        SYNTAX INTEGER { writable(0), readonly(1)}
        MAX-ACCESS read-write
        STATUS current
        DESCRIPTION
            "Enable or disable LCM read-only protection. If the LCM
            panel is under read-only protection, users can only
            view the configurations from the LCM panel. Otherwise,
            by default, users can modify the settings directly
            on the LCM panel."
		::= { consoleSettings 6 }

-- ----------------------------------------------------------------------------
-- System Management -> Maintenance -> Load Factory Default
-- ----------------------------------------------------------------------------

	loadFactoryDefault OBJECT IDENTIFIER ::= { maintenance 2 }

	loadFactoryDefaultSetting  OBJECT-TYPE
        SYNTAX INTEGER {
        	resetToFactoryDefault-ExcludingIpConfiguration (0),
        	resetToFactoryDefault (1)
        }
        MAX-ACCESS write-only
        STATUS current
        DESCRIPTION
            "This function will reset all of the Terminal Server CN2600 series
            device server's settings to the factory default
            values. Be aware that previous settings will be
            lost. Selecting Reset to factory default
            (excluding IP configuration) will reset all settings
            except the IP configuration to factory defaults.
            Selecting Reset to factory default will reset all
            settings including the IP configuration to factory
            defaults."
		::= { loadFactoryDefault 1 }

-- -------------------------------------------------------------
-- System Status
-- -------------------------------------------------------------

	sysStatus OBJECT IDENTIFIER ::= { swMgmt 6 }

-- -------------------------------------------------------------
-- System Status -> Serial to Network Connections
-- -------------------------------------------------------------

	s2eConnections OBJECT IDENTIFIER ::= { sysStatus 1 }

	monitorRemoteIpTable OBJECT-TYPE
        SYNTAX SEQUENCE OF MonitorRemoteIpEntry
        MAX-ACCESS not-accessible
        STATUS current
        DESCRIPTION
            "Serial to Network Connections Remote IP table."
        ::= { s2eConnections 1 }

    monitorRemoteIpEntry OBJECT-TYPE
        SYNTAX MonitorRemoteIpEntry
        MAX-ACCESS not-accessible
        STATUS current
        DESCRIPTION
            "Serial to Network Connections Remote IP entry."
        INDEX { portIndex, remoteIpIndex }
        ::= { monitorRemoteIpTable 1 }

    MonitorRemoteIpEntry ::=
        SEQUENCE {
        	remoteIpIndex
        		INTEGER,
            monitorRemoteIp
                IpAddress,
            monitorCipher
            	DisplayString
        }

    remoteIpIndex  OBJECT-TYPE
        SYNTAX INTEGER
        MAX-ACCESS read-only
        STATUS current
        DESCRIPTION
            "Serial to Network Connections Remote IP index."
		::= { monitorRemoteIpEntry 1 }

	monitorRemoteIp  OBJECT-TYPE
        SYNTAX IpAddress
        MAX-ACCESS read-only
        STATUS current
        DESCRIPTION
            "The remote IP currently connecting to this port."
		::= { monitorRemoteIpEntry 2 }

-- -------------------------------------------------------------
-- System Status -> Serial Port Status
-- -------------------------------------------------------------

	serialPortStatus OBJECT IDENTIFIER ::= { sysStatus 2 }

	monitorSerialPortStatusTable OBJECT-TYPE
        SYNTAX SEQUENCE OF MonitorSerialPortStatusEntry
        MAX-ACCESS not-accessible
        STATUS current
        DESCRIPTION
            "Serial Port Status table."
        ::= { serialPortStatus 1 }

    monitorSerialPortStatusEntry OBJECT-TYPE
        SYNTAX MonitorSerialPortStatusEntry
        MAX-ACCESS not-accessible
        STATUS current
        DESCRIPTION
            "Serial Port Status entry."
        INDEX { portIndex }
        ::= { monitorSerialPortStatusTable 1 }

    MonitorSerialPortStatusEntry ::=
        SEQUENCE {
            monitorTxCount
				INTEGER,
			monitorRxCount
				INTEGER,
			monitorTxTotalCount
				INTEGER,
			monitorRxTotalCount
				INTEGER,
			monitorDSR
				INTEGER,
			monitorDTR
				INTEGER,
			monitorRTS
				INTEGER,
			monitorCTS
				INTEGER,
			monitorDCD
				INTEGER
        }

	monitorTxCount  OBJECT-TYPE
        SYNTAX INTEGER
        MAX-ACCESS read-only
        STATUS current
        DESCRIPTION
            "View the number of bytes transmitted from the port
            since the last time the port was initialized."
		::= { monitorSerialPortStatusEntry 1 }

	monitorRxCount  OBJECT-TYPE
        SYNTAX INTEGER
        MAX-ACCESS read-only
        STATUS current
        DESCRIPTION
            "View the number of bytes received by the port since
            the last time the port was initialized."
		::= { monitorSerialPortStatusEntry 2 }

	monitorTxTotalCount  OBJECT-TYPE
        SYNTAX INTEGER
        MAX-ACCESS read-only
        STATUS current
        DESCRIPTION
            "View the number of bytes transmitted from the port
            since the last time the system was initialized."
		::= { monitorSerialPortStatusEntry 3 }

	monitorRxTotalCount  OBJECT-TYPE
        SYNTAX INTEGER
        MAX-ACCESS read-only
        STATUS current
        DESCRIPTION
            "View the number of bytes received by the port since
            the last time the system was initialized."
		::= { monitorSerialPortStatusEntry 4 }

	monitorDSR  OBJECT-TYPE
        SYNTAX INTEGER { off(0), on(1)}
        MAX-ACCESS read-only
        STATUS current
        DESCRIPTION
            "View the current DSR status of this port."
		::= { monitorSerialPortStatusEntry 5 }

	monitorDTR  OBJECT-TYPE
        SYNTAX INTEGER { off(0), on(1)}
        MAX-ACCESS read-only
        STATUS current
        DESCRIPTION
            "View the current DTR status of this port."
		::= { monitorSerialPortStatusEntry 6 }

	monitorRTS  OBJECT-TYPE
        SYNTAX INTEGER { off(0), on(1)}
        MAX-ACCESS read-only
        STATUS current
        DESCRIPTION
            "View the current RTS status of this port."
		::= { monitorSerialPortStatusEntry 7 }

	monitorCTS  OBJECT-TYPE
        SYNTAX INTEGER { off(0), on(1)}
        MAX-ACCESS read-only
        STATUS current
        DESCRIPTION
            "View the current CTS status of this port."
		::= { monitorSerialPortStatusEntry 8 }

	monitorDCD  OBJECT-TYPE
        SYNTAX INTEGER { off(0), on(1)}
        MAX-ACCESS read-only
        STATUS current
        DESCRIPTION
            "View the current DCD status of this port."
		::= { monitorSerialPortStatusEntry 9 }

-- -------------------------------------------------------------
-- System Status -> Serial Port Error Count
-- -------------------------------------------------------------

	serialPortErrorCount OBJECT IDENTIFIER ::= { sysStatus 3 }

	monitorSerialPortErrorCountTable OBJECT-TYPE
        SYNTAX SEQUENCE OF MonitorSerialPortErrorCountEntry
        MAX-ACCESS not-accessible
        STATUS current
        DESCRIPTION
            "Serial Port Error Count table."
        ::= { serialPortErrorCount 1 }

    monitorSerialPortErrorCountEntry OBJECT-TYPE
        SYNTAX MonitorSerialPortErrorCountEntry
        MAX-ACCESS not-accessible
        STATUS current
        DESCRIPTION
            "Serial Port Error Count entry."
        INDEX { portIndex }
        ::= { monitorSerialPortErrorCountTable 1 }

    MonitorSerialPortErrorCountEntry ::=
        SEQUENCE {
            monitorErrorCountFrame
				INTEGER,
			monitorErrorCountParity
				INTEGER,
			monitorErrorCountOverrun
				INTEGER,
			monitorErrorCountBreak
				INTEGER
        }

	monitorErrorCountFrame  OBJECT-TYPE
        SYNTAX INTEGER
        MAX-ACCESS read-only
        STATUS current
        DESCRIPTION
            "View the number of 'Frame' errors for this port."
		::= { monitorSerialPortErrorCountEntry 1 }

	monitorErrorCountParity  OBJECT-TYPE
        SYNTAX INTEGER
        MAX-ACCESS read-only
        STATUS current
        DESCRIPTION
            "View the number of 'Parity' errors for this port."
		::= { monitorSerialPortErrorCountEntry 2 }

	monitorErrorCountOverrun  OBJECT-TYPE
        SYNTAX INTEGER
        MAX-ACCESS read-only
        STATUS current
        DESCRIPTION
            "View the number of 'Overrun' errors for this port."
		::= { monitorSerialPortErrorCountEntry 3 }

	monitorErrorCountBreak  OBJECT-TYPE
        SYNTAX INTEGER
        MAX-ACCESS read-only
        STATUS current
        DESCRIPTION
            "View the number of 'Break' errors for this port."
		::= { monitorSerialPortErrorCountEntry 4 }

-- -------------------------------------------------------------
-- System Status -> Serial Port Settings
-- -------------------------------------------------------------

	serialPortSettings OBJECT IDENTIFIER ::= { sysStatus 4 }

	monitorSerialPortSettingsTable OBJECT-TYPE
        SYNTAX SEQUENCE OF MonitorSerialPortSettingsEntry
        MAX-ACCESS not-accessible
        STATUS current
        DESCRIPTION
            "Serial Port Settings table."
        ::= { serialPortSettings 1 }

    monitorSerialPortSettingsEntry OBJECT-TYPE
        SYNTAX MonitorSerialPortSettingsEntry
        MAX-ACCESS not-accessible
        STATUS current
        DESCRIPTION
            "Serial Port Settings entry."
        INDEX { portIndex }
        ::= { monitorSerialPortSettingsTable 1 }

    MonitorSerialPortSettingsEntry ::=
        SEQUENCE {
            monitorBaudRate
				INTEGER,
			monitorDataBits
				INTEGER,
			monitorStopBits
				DisplayString,
			monitorParity
				INTEGER,
			monitorRTSCTSFlowControl
				INTEGER,
			monitorXONXOFFFlowControl
				INTEGER,
			monitorDTRDSRFlowControl
				INTEGER,
			monitorFIFO
				INTEGER,
			monitorInterface
				INTEGER
        }

	monitorBaudRate  OBJECT-TYPE
        SYNTAX INTEGER
        MAX-ACCESS read-only
        STATUS current
        DESCRIPTION
            "View the current baudrate of the port."
		::= { monitorSerialPortSettingsEntry 1 }

	monitorDataBits  OBJECT-TYPE
		SYNTAX INTEGER  {
			bits-5(0),
			bits-6(1),
			bits-7(2),
			bits-8(3)
		}
        MAX-ACCESS read-only
        STATUS current
        DESCRIPTION
            "View the number of bits per byte for the port."
		::= { monitorSerialPortSettingsEntry 2 }

	monitorStopBits  OBJECT-TYPE
        SYNTAX DisplayString
        MAX-ACCESS read-only
        STATUS current
        DESCRIPTION
            "View the number of stop bits for the port."
		::= { monitorSerialPortSettingsEntry 3 }

	monitorParity  OBJECT-TYPE
        SYNTAX INTEGER {
        	none(0),
			odd(8),
			even(24),
			mark(40),
			space(56)
        }
        MAX-ACCESS read-only
        STATUS current
        DESCRIPTION
            "View the parity bit for the port."
		::= { monitorSerialPortSettingsEntry 4 }

	monitorRTSCTSFlowControl  OBJECT-TYPE
        SYNTAX INTEGER { off(0), on(1) }
        MAX-ACCESS read-only
        STATUS current
        DESCRIPTION
            "View if the port is using RTS/CTS flow control."
		::= { monitorSerialPortSettingsEntry 5 }

	monitorXONXOFFFlowControl  OBJECT-TYPE
        SYNTAX INTEGER { off(0), on(1) }
        MAX-ACCESS read-only
        STATUS current
        DESCRIPTION
            "View if the port is using XON/XOFF flow control."
		::= { monitorSerialPortSettingsEntry 6 }

	monitorDTRDSRFlowControl  OBJECT-TYPE
        SYNTAX INTEGER { off(0), on(1) }
        MAX-ACCESS read-only
        STATUS current
        DESCRIPTION
            "View if the port is using DTR/DSR flow control."
		::= { monitorSerialPortSettingsEntry 7 }

	monitorFIFO  OBJECT-TYPE
        SYNTAX INTEGER {
        	disable(0),
			enable(1)
        }
        MAX-ACCESS read-only
        STATUS current
        DESCRIPTION
            "View FIFO status of this port."
		::= { monitorSerialPortSettingsEntry 8 }

	monitorInterface  OBJECT-TYPE
        SYNTAX INTEGER {
        	rs-232(0),
			rs-422(1),
			rs-485-2-wire(2),
			rs-485-4-wire(3)
        }
        MAX-ACCESS read-only
        STATUS current
        DESCRIPTION
            "View the serial interface that the port is using."
		::= { monitorSerialPortSettingsEntry 9 }

-- -------------------------------------------------------------
-- System Status -> Buffering
-- -------------------------------------------------------------

	serialPortBuffering OBJECT IDENTIFIER ::= { sysStatus 5 }

	monitorSerialPortBufferingTable OBJECT-TYPE
        SYNTAX SEQUENCE OF MonitorSerialPortBufferingEntry
        MAX-ACCESS not-accessible
        STATUS current
        DESCRIPTION
            "Serial Port Buffering table."
        ::= { serialPortBuffering 1 }

    monitorSerialPortBufferingEntry OBJECT-TYPE
        SYNTAX MonitorSerialPortBufferingEntry
        MAX-ACCESS not-accessible
        STATUS current
        DESCRIPTION
            "Serial Port Settings entry."
        INDEX { portIndex }
        ::= { monitorSerialPortBufferingTable 1 }

    MonitorSerialPortBufferingEntry ::=
        SEQUENCE {
            monitorBuffering
				INTEGER
        }

	monitorBuffering  OBJECT-TYPE
        SYNTAX INTEGER
        MAX-ACCESS read-only
        STATUS current
        DESCRIPTION
            "View length of buffered data for the port. The length unit is byte."
		::= { monitorSerialPortBufferingEntry 1 }

-- -------------------------------------------------------------
-- Save Configuration
-- -------------------------------------------------------------

	saveConfiguration OBJECT IDENTIFIER ::= { swMgmt 7 }

	saveConfig  OBJECT-TYPE
        SYNTAX INTEGER {
        	save(1)
        }
        MAX-ACCESS write-only
        STATUS current
        DESCRIPTION
            "Save the applied configuration to the Terminal Server CN2600
            series device server."
		::= { saveConfiguration 1 }

-- -------------------------------------------------------------
-- Restart
-- -------------------------------------------------------------

	restart OBJECT IDENTIFIER ::= { swMgmt 8 }

	restartPorts  OBJECT-TYPE
        SYNTAX INTEGER {
        	port1(0),
        	port2(1),
        	port3(2),
        	port4(3),
        	port5(4),
        	port6(5),
        	port7(6),
        	port8(7),
        	port9(8),
        	port10(9),
        	port11(10),
        	port12(11),
        	port13(12),
        	port14(13),
        	port15(14),
        	port16(15)
        }
        MAX-ACCESS write-only
        STATUS current
        DESCRIPTION
            "Restart serial port. Restarting will cause port
            reseting."
		::= { restart 1 }

	restartSystem  OBJECT-TYPE
        SYNTAX INTEGER {
        	restart(1)
        }
        MAX-ACCESS write-only
        STATUS current
        DESCRIPTION
            "Restart the Terminal Server CN2600 series device server. Be sure
            to save all of your configuration changes before
            you restart the system. Otherwise, all of the changes will be
            lost."
		::= { restart 2 }

END
