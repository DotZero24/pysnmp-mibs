--  ***************************************************************************
--  ADVA-FSPR7-MIB.txt
--
--               ADVA AG Optical Networking MIB File
--
--  Copyright 2011 ADVA AG Optical Networking.
--
--  All rights reserved.
--  ***************************************************************************


--  MIB definitions required for entity management.

ADVA-FSPR7-MIB DEFINITIONS ::= BEGIN

IMPORTS
    RowStatus,
    RowPointer,
    DateAndTime,
    MacAddress,
    TruthValue
                                        FROM  SNMPv2-TC
    MODULE-COMPLIANCE,
    OBJECT-GROUP,
    NOTIFICATION-GROUP
                                        FROM  SNMPv2-CONF
    OBJECT-TYPE,
    MODULE-IDENTITY,
    NOTIFICATION-TYPE,
    Unsigned32,
    Integer32,
    TimeTicks,
    IpAddress
                                        FROM  SNMPv2-SMI
    SnmpAdminString
                                        FROM  SNMP-FRAMEWORK-MIB
    ApsHoldoffTime,
    ApsDirection,
    AssignmentState,
    EntityClass,
    EnableState,
    EthDuplexMode,
    fspR7,
    FspR7EquipmentType,
    FspR7EquipmentTypeCaps,
    LoopConfig,
    OhTerminationLevel,
    OtnPayloadType,
    OtnTcmLevel,
    ProtectionMech,
    ServiceAffecting,
    ServiceImpairment,
    SonetTimingSource,
    SonetTraceForm,
    SourceIpAddress,
    TrapAlarmSeverity,
    TimMode,
    VirtualContainerType
                                        FROM  ADVA-MIB
    ApsRevertMode,
    ApsType,
    ConnectionNotation,
    EntityClassName,
    EquipmentState,
    EntityType,
    FfpType,
    Grade,
    FspR7AdminState,
    FspR7AidType,
    FspR7AlarmListType,
    FspR7AlarmProfileList,
    FspR7AlsMode,
    FspR7AppType,
    FspR7ApsChannel,
    FspR7APSCommand,
    FspR7AseTabOpr,
    FspR7EquipmentAssignState,
    FspR7AutoThresReset,
    FspR7Baund,
    FspR7BERThreshold,
    FspR7BERThresholdSection,
    FspR7BidirectionalChannel,
    FspR7Bitrate,
    FspR7CapInventory,
    FspR7Category,
    FspR7CertApply,
    FspR7ChannelBandwidth,
    FspR7ChannelIdentifier,
    FspR7ChannelIdentifierCaps,
    FspR7ChannelNumber,
    FspR7ChannelNumberCaps,
    FspR7ChannelSpacing,
    FspR7CodeGain,
    FspR7ColumnMark,
    FspR7Conn,
    FspR7ConnectState,
    FspR7ConnectorType,
    FspR7CpAuthType,
    FspR7DCFiberType,
    FspR7DeploymentScenario,
    FspR7DisableEnable,
    FspR7DispersionCompensation,
    FspR7DispersionConfig,
    FspR7DispersionModes,
    FspR7EocProtAvailability,
    FspR7EdfaOutputPowerRating,
    FspR7EnableDisable,
    FspR7EncapsulationMethod,
    FspR7EntitySecondaryStates,
    FspR7EntityType,
    FspR7ErrorFwdMode,
    FspR7EqlzAdminState,
    FspR7FanMode,
    FspR7FanProfile,
    FspR7FDStatusCaps,
    FspR7FecType,
    FspR7FiberBrand,
    FspR7FiberDetect,
    FspR7FlowControlMode,
    FspR7ForceConfig,
    FspR7ForcedStatus,
    FspR7FrameFormat,
    FspR7FunctionCrs,
    FspR7Gain,
    FspR7GainRange,
    FspR7GropticsType,
    FspR7InitEqualization,
    FspR7InterfaceFunction,
    FspR7InterfaceType,
    FspR7InvertTelemetryInputLogic,
    FspR7IpType,
    FspR7Ipv6Address,
    FspR7IpMode,
    FspR7IPv6Type,
    FspR7KeyLength,
    FspR7LacpMode,
    FspR7LacpTimeout,
    FspR7LagFendState,
    FspR7LagIdFend,
    FspR7LagPorts,
    FspR7LagPortType,
    FspR7LagStandby,
    FspR7LagState,
    FspR7LagSysIdFend,
    FspR7LaneGroupInventory,
    FspR7LaserDelayTimer,
    FspR7LaserForcedOperation,
    FspR7LineCoding,
    FspR7LossAttenuation,
    FspR7MaxBitErrorRate,
    FspR7ManualAuto,
    FspR7Mapping,
    FspR7MonLevel,
    FspR7MuxMethod,
    FspR7NCTRouteType,
    FspR7NCTraceId,
    FspR7NdpCleanup,
    FspR7NewSshHostKey,
    FspR7NumberOfChannels,
    FspR7NumberOfChannelsProv,
    FspR7NtpAdminState,
    FspR7NtpSyncStatus,
    FspR7NtpTest,
    FspR7NtpTestStatus,
    FspR7NoYes,
    FspR7OdtuType,
    FspR7OperState,
    FspR7OpticalBand,
    FspR7OpticalFiberType,
    FspR7OpticalGroup,
    FspR7OpticalInterfaceReach,
    FspR7OpticalInterfaceReachCaps,
    FspR7OpticalLanes,
    FspR7OpticalMultiplexLevel,
    FspR7OpticalSubBand,
    FspR7OptUpdate,
    FspR7OpuPayloadType,
    FspR7OscChannel,
    FspR7OscUsage,
    FspR7OspfMode,
    FspR7OtdrPeriod,
    FspR7ParityBit,
    FspR7PathNode,
    FspR7PathProt,
    FspR7PlugDataRate,
    FspR7PlugDataRateCaps,
    FspR7PmReset,
    FspR7PmSnapshotStatus,
    FspR7PmSnapshotParameterTypes,
    FspR7PortBehaviour,
    FspR7PortMode,
    FspR7PortRole,
    FspR7PrbsPmReset,
    FspR7ProtectionRole,
    FspR7ProtectionType,
    FspR7Protocol,
    FspR7PsuOutputPower,
    FspR7RedLinedState,
    FspR7RlsMan,
    FspR7RenewMode,
    FspR7RoadmNumber,
    FspR7Scrambling,
    FspR7ScuRing,
    FspR7SignalDirection,
    FspR7SingleFiberLocation,
    FspR7SnmpHexString,
    FspR7SnmpLongString,
    FspR7SshHostKeyEncryptAlgorithm,
    FspR7SshHostKeyLength,
    FspR7Stages,
    FspR7StartPmSnapshot,
    FspR7StateConnection,
    FspR7Stuff,
    FspR7SupplyType,
    FspR7SwitchOverCause,
    FspR7TelemetryOutput,
    FspR7PRBSTest,
    FspR7TifOutputReset,
    FspR7TiltSet,
    FspR7Topology,
    FspR7TopologyType,
    FspR7TrafficDirection,
    FspR7TransmissionMode,
    FspR7TrapModeLegacy,
    FspR7TurnupConfig,
    FspR7TxOffOnTm,
    FspR7TypeConnection,
    FspR7TypeCrs,
    FspR7UntaggedFrames,
    FspR7ValidityPeriod,
    FspR7VoaMode,
    FspR7VSessChangeReason,
    FspR7VSessStatus,
    FspR7VSessWriteAccess,
    FspR7XfpDecisionThres,
    FspR7YcableType,
    FspR7FltrCableType,
    FspR7YesNo
                                        FROM  ADVA-FSPR7-TC-MIB;


advaFspR7 MODULE-IDENTITY

    LAST-UPDATED "201410150000Z"

    ORGANIZATION "ADVA Optical Networking"

    CONTACT-INFO "EMEA Support
                  Phone : +49 89 89 0665 848
                  Fax   : +49 89 89 0665 22848
                  Email : support@advaoptical.com

                  North American Support
                  Phone : 886 442 ADVA (2382) (toll-free within the US, Canada and Mexico)
                  Fax   : + 1 806 741 8529 (elsewhere)
                  Email : support-usa@advaoptical.com

                  Asia Pacific Support
                  Phone : + 1 866 442 2382 (other toll-free numbers available in some countries)
                  Email : support-asia@advaoptical.com"

    DESCRIPTION   "This is a MIB definition for ADVA AG Optical Networking entity management."

    REVISION      "201410150000Z"
    DESCRIPTION   "FSP3000 F7 Release 13.2.2 MIB."

    REVISION      "201409290000Z"
    DESCRIPTION   "FSP3000 F7 Release 13.2.1 MIB."

    REVISION      "201312040000Z"
    DESCRIPTION   "FSP3000 F7 Release 12.2.1 MIB."

    REVISION      "201308200000Z"
    DESCRIPTION   "FSP3000 F7 Release 12.1.1 MIB."

    REVISION      "201105220000Z"
    DESCRIPTION   "FSP3000 F7 Release 11.2 MIB."
    ::= { fspR7 7 }


containers
    OBJECT IDENTIFIER ::= { advaFspR7 1 }

entities
    OBJECT IDENTIFIER ::= { advaFspR7 2 }

management
    OBJECT IDENTIFIER ::= { advaFspR7 3 }

neMgmt
    OBJECT IDENTIFIER ::= { management 1 }

ipConf
    OBJECT IDENTIFIER ::= { neMgmt 100 }

specificMgmt
    OBJECT IDENTIFIER ::= { management 2 }

eqptMgmt
    OBJECT IDENTIFIER ::= { management 3 }

facilityMgmt
    OBJECT IDENTIFIER ::= { management 4 }

dcnMgmt
    OBJECT IDENTIFIER ::= { management 5 }

opticalMuxMgmt
    OBJECT IDENTIFIER ::= { management 6 }

shelfConnMgmt
    OBJECT IDENTIFIER ::= { management 7 }

envMgmt
    OBJECT IDENTIFIER ::= { management 8 }

containerMgmt
    OBJECT IDENTIFIER ::= { management 9 }

opticalLineMgmt
    OBJECT IDENTIFIER ::= { management 10 }

alarm
    OBJECT IDENTIFIER ::= { advaFspR7 4 }

alarmProfile
    OBJECT IDENTIFIER ::= { alarm 100 }

trap
    OBJECT IDENTIFIER ::= { advaFspR7 5 }

fspR7Trap
    OBJECT IDENTIFIER ::= { trap 0 }

performance
    OBJECT IDENTIFIER ::= { advaFspR7 6 }

performanceFacility
    OBJECT IDENTIFIER ::= { performance 4 }

performanceFacilityThreshold
    OBJECT IDENTIFIER ::= { performanceFacility 1 }

performanceFacilityMonitoring
    OBJECT IDENTIFIER ::= { performanceFacility 2 }

featureSpecific
    OBJECT IDENTIFIER ::= { advaFspR7 7 }

fiberMap
    OBJECT IDENTIFIER ::= { featureSpecific 1 }

pmSnapshot
    OBJECT IDENTIFIER ::= { featureSpecific 2 }

eci
    OBJECT IDENTIFIER ::= { featureSpecific 3 }

serviceDiagnostics
    OBJECT IDENTIFIER ::= { featureSpecific 4 }

changeService
    OBJECT IDENTIFIER ::= { featureSpecific 5 }

protection
    OBJECT IDENTIFIER ::= { featureSpecific 6 }

translation
    OBJECT IDENTIFIER ::= { featureSpecific 7 }

advaSecurity
    OBJECT IDENTIFIER ::= { featureSpecific 8 }

ipSettings
    OBJECT IDENTIFIER ::= { featureSpecific 9 }

dateAndTime
    OBJECT IDENTIFIER ::= { featureSpecific 10 }

relationship
    OBJECT IDENTIFIER ::= { advaFspR7 8 }

notAssignables
    OBJECT IDENTIFIER ::= { advaFspR7 9 }

inventory
    OBJECT IDENTIFIER ::= { advaFspR7 10 }

containerShelfTable OBJECT-TYPE
    SYNTAX      SEQUENCE OF ContainerShelfEntry
    MAX-ACCESS  not-accessible
    STATUS      current
    DESCRIPTION   "containerShelfTable"
    ::=  { containers 1 }

containerShelfEntry OBJECT-TYPE
    SYNTAX      ContainerShelfEntry
    MAX-ACCESS  not-accessible
    STATUS      current
    DESCRIPTION   "Entry of containerShelfTable"
    INDEX       {
                  containerShelfShelfNo,
                  containerShelfSlotNo,
                  containerShelfPortNo,
                  containerShelfExtNo,
                  containerShelfClassName
                }
    ::=  { containerShelfTable 1 }

ContainerShelfEntry ::=  SEQUENCE
  { containerShelfShelfNo Unsigned32,
    containerShelfSlotNo Unsigned32,
    containerShelfPortNo Unsigned32,
    containerShelfExtNo Unsigned32,
    containerShelfClassName EntityClassName,
    containerShelfAidString SnmpAdminString,
    containerShelfClass EntityClass,
    containerShelfTableId RowPointer,
    containerShelfEquipmentState EquipmentState,
    containerShelfParentId RowPointer }

containerShelfShelfNo OBJECT-TYPE
    SYNTAX      Unsigned32
    MAX-ACCESS  not-accessible
    STATUS      current
    DESCRIPTION   "Adress index."
    ::=  { containerShelfEntry 1 }

containerShelfSlotNo OBJECT-TYPE
    SYNTAX      Unsigned32
    MAX-ACCESS  not-accessible
    STATUS      current
    DESCRIPTION   "Adress index."
    ::=  { containerShelfEntry 2 }

containerShelfPortNo OBJECT-TYPE
    SYNTAX      Unsigned32
    MAX-ACCESS  not-accessible
    STATUS      current
    DESCRIPTION   "Adress index."
    ::=  { containerShelfEntry 3 }

containerShelfExtNo OBJECT-TYPE
    SYNTAX      Unsigned32
    MAX-ACCESS  not-accessible
    STATUS      current
    DESCRIPTION   "Adress index."
    ::=  { containerShelfEntry 4 }

containerShelfClassName OBJECT-TYPE
    SYNTAX      EntityClassName
    MAX-ACCESS  not-accessible
    STATUS      current
    DESCRIPTION
        "Entity Class Name"
    ::=  { containerShelfEntry 5 }

containerShelfAidString OBJECT-TYPE
    SYNTAX      SnmpAdminString
    MAX-ACCESS  read-only
    STATUS      current
    DESCRIPTION   "Aid string of entity."
    ::=  { containerShelfEntry 6 }

containerShelfClass OBJECT-TYPE
    SYNTAX      EntityClass
    MAX-ACCESS  read-only
    STATUS      current
    DESCRIPTION
        "Entity Class"
    ::=  { containerShelfEntry 7 }

containerShelfTableId OBJECT-TYPE
    SYNTAX      RowPointer
    MAX-ACCESS  read-only
    STATUS      current
    DESCRIPTION   "RowPointer to managment table"
    ::=  { containerShelfEntry 8 }

containerShelfEquipmentState OBJECT-TYPE
    SYNTAX      EquipmentState
    MAX-ACCESS  read-only
    STATUS      current
    DESCRIPTION   "See EquipmentState."
    ::=  { containerShelfEntry 9 }

containerShelfParentId OBJECT-TYPE
    SYNTAX      RowPointer
    MAX-ACCESS  read-only
    STATUS      current
    DESCRIPTION   "RowPointer to parent entity reported in corresponding entity table."
    ::=  { containerShelfEntry 10 }

containerFanTable OBJECT-TYPE
    SYNTAX      SEQUENCE OF ContainerFanEntry
    MAX-ACCESS  not-accessible
    STATUS      current
    DESCRIPTION   "containerFanTable"
    ::=  { containers 2 }

containerFanEntry OBJECT-TYPE
    SYNTAX      ContainerFanEntry
    MAX-ACCESS  not-accessible
    STATUS      current
    DESCRIPTION   "Entry of containerFanTable"
    INDEX       {
                  containerFanShelfNo,
                  containerFanSlotNo,
                  containerFanPortNo,
                  containerFanExtNo,
                  containerFanClassName
                }
    ::=  { containerFanTable 1 }

ContainerFanEntry ::=  SEQUENCE
  { containerFanShelfNo Unsigned32,
    containerFanSlotNo Unsigned32,
    containerFanPortNo Unsigned32,
    containerFanExtNo Unsigned32,
    containerFanClassName EntityClassName,
    containerFanAidString SnmpAdminString,
    containerFanClass EntityClass,
    containerFanTableId RowPointer,
    containerFanEquipmentState EquipmentState,
    containerFanParentId RowPointer }

containerFanShelfNo OBJECT-TYPE
    SYNTAX      Unsigned32
    MAX-ACCESS  not-accessible
    STATUS      current
    DESCRIPTION   "Adress index."
    ::=  { containerFanEntry 1 }

containerFanSlotNo OBJECT-TYPE
    SYNTAX      Unsigned32
    MAX-ACCESS  not-accessible
    STATUS      current
    DESCRIPTION   "Adress index."
    ::=  { containerFanEntry 2 }

containerFanPortNo OBJECT-TYPE
    SYNTAX      Unsigned32
    MAX-ACCESS  not-accessible
    STATUS      current
    DESCRIPTION   "Adress index."
    ::=  { containerFanEntry 3 }

containerFanExtNo OBJECT-TYPE
    SYNTAX      Unsigned32
    MAX-ACCESS  not-accessible
    STATUS      current
    DESCRIPTION   "Adress index."
    ::=  { containerFanEntry 4 }

containerFanClassName OBJECT-TYPE
    SYNTAX      EntityClassName
    MAX-ACCESS  not-accessible
    STATUS      current
    DESCRIPTION
        "Entity Class Name"
    ::=  { containerFanEntry 5 }

containerFanAidString OBJECT-TYPE
    SYNTAX      SnmpAdminString
    MAX-ACCESS  read-only
    STATUS      current
    DESCRIPTION   "Aid string of entity."
    ::=  { containerFanEntry 6 }

containerFanClass OBJECT-TYPE
    SYNTAX      EntityClass
    MAX-ACCESS  read-only
    STATUS      current
    DESCRIPTION
        "Entity Class"
    ::=  { containerFanEntry 7 }

containerFanTableId OBJECT-TYPE
    SYNTAX      RowPointer
    MAX-ACCESS  read-only
    STATUS      current
    DESCRIPTION   "RowPointer to managment table"
    ::=  { containerFanEntry 8 }

containerFanEquipmentState OBJECT-TYPE
    SYNTAX      EquipmentState
    MAX-ACCESS  read-only
    STATUS      current
    DESCRIPTION   "See EquipmentState."
    ::=  { containerFanEntry 9 }

containerFanParentId OBJECT-TYPE
    SYNTAX      RowPointer
    MAX-ACCESS  read-only
    STATUS      current
    DESCRIPTION   "RowPointer to parent entity reported in corresponding entity table."
    ::=  { containerFanEntry 10 }

containerPlugTable OBJECT-TYPE
    SYNTAX      SEQUENCE OF ContainerPlugEntry
    MAX-ACCESS  not-accessible
    STATUS      current
    DESCRIPTION   "containerPlugTable"
    ::=  { containers 3 }

containerPlugEntry OBJECT-TYPE
    SYNTAX      ContainerPlugEntry
    MAX-ACCESS  not-accessible
    STATUS      current
    DESCRIPTION   "Entry of containerPlugTable"
    INDEX       {
                  containerPlugShelfNo,
                  containerPlugSlotNo,
                  containerPlugPortNo,
                  containerPlugExtNo,
                  containerPlugClassName
                }
    ::=  { containerPlugTable 1 }

ContainerPlugEntry ::=  SEQUENCE
  { containerPlugShelfNo Unsigned32,
    containerPlugSlotNo Unsigned32,
    containerPlugPortNo Unsigned32,
    containerPlugExtNo Unsigned32,
    containerPlugClassName EntityClassName,
    containerPlugAidString SnmpAdminString,
    containerPlugClass EntityClass,
    containerPlugTableId RowPointer,
    containerPlugEquipmentState EquipmentState,
    containerPlugParentId RowPointer }

containerPlugShelfNo OBJECT-TYPE
    SYNTAX      Unsigned32
    MAX-ACCESS  not-accessible
    STATUS      current
    DESCRIPTION   "Adress index."
    ::=  { containerPlugEntry 1 }

containerPlugSlotNo OBJECT-TYPE
    SYNTAX      Unsigned32
    MAX-ACCESS  not-accessible
    STATUS      current
    DESCRIPTION   "Adress index."
    ::=  { containerPlugEntry 2 }

containerPlugPortNo OBJECT-TYPE
    SYNTAX      Unsigned32
    MAX-ACCESS  not-accessible
    STATUS      current
    DESCRIPTION   "Adress index."
    ::=  { containerPlugEntry 3 }

containerPlugExtNo OBJECT-TYPE
    SYNTAX      Unsigned32
    MAX-ACCESS  not-accessible
    STATUS      current
    DESCRIPTION   "Adress index."
    ::=  { containerPlugEntry 4 }

containerPlugClassName OBJECT-TYPE
    SYNTAX      EntityClassName
    MAX-ACCESS  not-accessible
    STATUS      current
    DESCRIPTION
        "Entity Class Name"
    ::=  { containerPlugEntry 5 }

containerPlugAidString OBJECT-TYPE
    SYNTAX      SnmpAdminString
    MAX-ACCESS  read-only
    STATUS      current
    DESCRIPTION   "Aid string of entity."
    ::=  { containerPlugEntry 6 }

containerPlugClass OBJECT-TYPE
    SYNTAX      EntityClass
    MAX-ACCESS  read-only
    STATUS      current
    DESCRIPTION
        "Entity Class"
    ::=  { containerPlugEntry 7 }

containerPlugTableId OBJECT-TYPE
    SYNTAX      RowPointer
    MAX-ACCESS  read-only
    STATUS      current
    DESCRIPTION   "RowPointer to managment table"
    ::=  { containerPlugEntry 8 }

containerPlugEquipmentState OBJECT-TYPE
    SYNTAX      EquipmentState
    MAX-ACCESS  read-only
    STATUS      current
    DESCRIPTION   "See EquipmentState."
    ::=  { containerPlugEntry 9 }

containerPlugParentId OBJECT-TYPE
    SYNTAX      RowPointer
    MAX-ACCESS  read-only
    STATUS      current
    DESCRIPTION   "RowPointer to parent entity reported in corresponding entity table."
    ::=  { containerPlugEntry 10 }

containerModTable OBJECT-TYPE
    SYNTAX      SEQUENCE OF ContainerModEntry
    MAX-ACCESS  not-accessible
    STATUS      current
    DESCRIPTION   "containerModTable"
    ::=  { containers 4 }

containerModEntry OBJECT-TYPE
    SYNTAX      ContainerModEntry
    MAX-ACCESS  not-accessible
    STATUS      current
    DESCRIPTION   "Entry of containerModTable"
    INDEX       {
                  containerModShelfNo,
                  containerModSlotNo,
                  containerModPortNo,
                  containerModExtNo,
                  containerModClassName
                }
    ::=  { containerModTable 1 }

ContainerModEntry ::=  SEQUENCE
  { containerModShelfNo Unsigned32,
    containerModSlotNo Unsigned32,
    containerModPortNo Unsigned32,
    containerModExtNo Unsigned32,
    containerModClassName EntityClassName,
    containerModAidString SnmpAdminString,
    containerModClass EntityClass,
    containerModTableId RowPointer,
    containerModEquipmentState EquipmentState,
    containerModParentId RowPointer }

containerModShelfNo OBJECT-TYPE
    SYNTAX      Unsigned32
    MAX-ACCESS  not-accessible
    STATUS      current
    DESCRIPTION   "Adress index."
    ::=  { containerModEntry 1 }

containerModSlotNo OBJECT-TYPE
    SYNTAX      Unsigned32
    MAX-ACCESS  not-accessible
    STATUS      current
    DESCRIPTION   "Adress index."
    ::=  { containerModEntry 2 }

containerModPortNo OBJECT-TYPE
    SYNTAX      Unsigned32
    MAX-ACCESS  not-accessible
    STATUS      current
    DESCRIPTION   "Adress index."
    ::=  { containerModEntry 3 }

containerModExtNo OBJECT-TYPE
    SYNTAX      Unsigned32
    MAX-ACCESS  not-accessible
    STATUS      current
    DESCRIPTION   "Adress index."
    ::=  { containerModEntry 4 }

containerModClassName OBJECT-TYPE
    SYNTAX      EntityClassName
    MAX-ACCESS  not-accessible
    STATUS      current
    DESCRIPTION
        "Entity Class Name"
    ::=  { containerModEntry 5 }

containerModAidString OBJECT-TYPE
    SYNTAX      SnmpAdminString
    MAX-ACCESS  read-only
    STATUS      current
    DESCRIPTION   "Aid string of entity."
    ::=  { containerModEntry 6 }

containerModClass OBJECT-TYPE
    SYNTAX      EntityClass
    MAX-ACCESS  read-only
    STATUS      current
    DESCRIPTION
        "Entity Class"
    ::=  { containerModEntry 7 }

containerModTableId OBJECT-TYPE
    SYNTAX      RowPointer
    MAX-ACCESS  read-only
    STATUS      current
    DESCRIPTION   "RowPointer to managment table"
    ::=  { containerModEntry 8 }

containerModEquipmentState OBJECT-TYPE
    SYNTAX      EquipmentState
    MAX-ACCESS  read-only
    STATUS      current
    DESCRIPTION   "See EquipmentState."
    ::=  { containerModEntry 9 }

containerModParentId OBJECT-TYPE
    SYNTAX      RowPointer
    MAX-ACCESS  read-only
    STATUS      current
    DESCRIPTION   "RowPointer to parent entity reported in corresponding entity table."
    ::=  { containerModEntry 10 }

containerVchTable OBJECT-TYPE
    SYNTAX      SEQUENCE OF ContainerVchEntry
    MAX-ACCESS  not-accessible
    STATUS      current
    DESCRIPTION   "containerVchTable"
    ::=  { containers 7 }

containerVchEntry OBJECT-TYPE
    SYNTAX      ContainerVchEntry
    MAX-ACCESS  not-accessible
    STATUS      current
    DESCRIPTION   "Entry of containerVchTable"
    INDEX       {
                  containerVchShelfNo,
                  containerVchSlotNo,
                  containerVchPortNo,
                  containerVchExtNo,
                  containerVchClassName
                }
    ::=  { containerVchTable 1 }

ContainerVchEntry ::=  SEQUENCE
  { containerVchShelfNo Unsigned32,
    containerVchSlotNo Unsigned32,
    containerVchPortNo Unsigned32,
    containerVchExtNo Unsigned32,
    containerVchClassName EntityClassName,
    containerVchAidString SnmpAdminString,
    containerVchClass EntityClass,
    containerVchTableId RowPointer,
    containerVchParentId RowPointer }

containerVchShelfNo OBJECT-TYPE
    SYNTAX      Unsigned32
    MAX-ACCESS  not-accessible
    STATUS      current
    DESCRIPTION   "Adress index."
    ::=  { containerVchEntry 1 }

containerVchSlotNo OBJECT-TYPE
    SYNTAX      Unsigned32
    MAX-ACCESS  not-accessible
    STATUS      current
    DESCRIPTION   "Adress index."
    ::=  { containerVchEntry 2 }

containerVchPortNo OBJECT-TYPE
    SYNTAX      Unsigned32
    MAX-ACCESS  not-accessible
    STATUS      current
    DESCRIPTION   "Adress index."
    ::=  { containerVchEntry 3 }

containerVchExtNo OBJECT-TYPE
    SYNTAX      Unsigned32
    MAX-ACCESS  not-accessible
    STATUS      current
    DESCRIPTION   "Adress index."
    ::=  { containerVchEntry 4 }

containerVchClassName OBJECT-TYPE
    SYNTAX      EntityClassName
    MAX-ACCESS  not-accessible
    STATUS      current
    DESCRIPTION
        "Entity Class Name"
    ::=  { containerVchEntry 5 }

containerVchAidString OBJECT-TYPE
    SYNTAX      SnmpAdminString
    MAX-ACCESS  read-only
    STATUS      current
    DESCRIPTION   "Aid string of entity."
    ::=  { containerVchEntry 6 }

containerVchClass OBJECT-TYPE
    SYNTAX      EntityClass
    MAX-ACCESS  read-only
    STATUS      current
    DESCRIPTION
        "Entity Class"
    ::=  { containerVchEntry 7 }

containerVchTableId OBJECT-TYPE
    SYNTAX      RowPointer
    MAX-ACCESS  read-only
    STATUS      current
    DESCRIPTION   "RowPointer to managment table"
    ::=  { containerVchEntry 8 }

containerVchParentId OBJECT-TYPE
    SYNTAX      RowPointer
    MAX-ACCESS  read-only
    STATUS      current
    DESCRIPTION   "RowPointer to parent entity reported in corresponding entity table."
    ::=  { containerVchEntry 9 }

containerCrossConnTable OBJECT-TYPE
    SYNTAX      SEQUENCE OF ContainerCrossConnEntry
    MAX-ACCESS  not-accessible
    STATUS      current
    DESCRIPTION   "containerCrossConnection"
    ::=  { containers 8 }

containerCrossConnEntry OBJECT-TYPE
    SYNTAX      ContainerCrossConnEntry
    MAX-ACCESS  not-accessible
    STATUS      current
    DESCRIPTION   "Entry of containerCrossConnectionTable"
    INDEX       {
                  containerCrossConnFromShelfNo,
                  containerCrossConnFromSlotNo,
                  containerCrossConnFromPortNo,
                  containerCrossConnFromExtNo,
                  containerCrossConnFromClassName,
                  containerCrossConnToShelfNo,
                  containerCrossConnToSlotNo,
                  containerCrossConnToPortNo,
                  containerCrossConnToExtNo,
                  containerCrossConnToClassName,
                  containerCrossConnClassName
                }
    ::=  { containerCrossConnTable 1 }

ContainerCrossConnEntry ::=  SEQUENCE
  { containerCrossConnFromShelfNo Unsigned32,
    containerCrossConnFromSlotNo Unsigned32,
    containerCrossConnFromPortNo Unsigned32,
    containerCrossConnFromExtNo Unsigned32,
    containerCrossConnFromClassName EntityClassName,
    containerCrossConnToShelfNo Unsigned32,
    containerCrossConnToSlotNo Unsigned32,
    containerCrossConnToPortNo Unsigned32,
    containerCrossConnToExtNo Unsigned32,
    containerCrossConnToClassName EntityClassName,
    containerCrossConnClassName EntityClassName,
    containerCrossConnAidString SnmpAdminString,
    containerCrossConnFromId RowPointer,
    containerCrossConnToId RowPointer,
    containerCrossConnClass EntityClass,
    containerCrossConnTableId RowPointer,
    containerCrossConnParentId RowPointer }

containerCrossConnFromShelfNo OBJECT-TYPE
    SYNTAX      Unsigned32
    MAX-ACCESS  not-accessible
    STATUS      current
    DESCRIPTION   "Adress index."
    ::=  { containerCrossConnEntry 1 }

containerCrossConnFromSlotNo OBJECT-TYPE
    SYNTAX      Unsigned32
    MAX-ACCESS  not-accessible
    STATUS      current
    DESCRIPTION   "Adress index."
    ::=  { containerCrossConnEntry 2 }

containerCrossConnFromPortNo OBJECT-TYPE
    SYNTAX      Unsigned32
    MAX-ACCESS  not-accessible
    STATUS      current
    DESCRIPTION   "Adress index."
    ::=  { containerCrossConnEntry 3 }

containerCrossConnFromExtNo OBJECT-TYPE
    SYNTAX      Unsigned32
    MAX-ACCESS  not-accessible
    STATUS      current
    DESCRIPTION   "Adress index."
    ::=  { containerCrossConnEntry 4 }

containerCrossConnFromClassName OBJECT-TYPE
    SYNTAX      EntityClassName
    MAX-ACCESS  not-accessible
    STATUS      current
    DESCRIPTION
        "Entity Class Name"
    ::=  { containerCrossConnEntry 5 }

containerCrossConnToShelfNo OBJECT-TYPE
    SYNTAX      Unsigned32
    MAX-ACCESS  not-accessible
    STATUS      current
    DESCRIPTION   "Adress index."
    ::=  { containerCrossConnEntry 6 }

containerCrossConnToSlotNo OBJECT-TYPE
    SYNTAX      Unsigned32
    MAX-ACCESS  not-accessible
    STATUS      current
    DESCRIPTION   "Adress index."
    ::=  { containerCrossConnEntry 7 }

containerCrossConnToPortNo OBJECT-TYPE
    SYNTAX      Unsigned32
    MAX-ACCESS  not-accessible
    STATUS      current
    DESCRIPTION   "Adress index."
    ::=  { containerCrossConnEntry 8 }

containerCrossConnToExtNo OBJECT-TYPE
    SYNTAX      Unsigned32
    MAX-ACCESS  not-accessible
    STATUS      current
    DESCRIPTION   "Adress index."
    ::=  { containerCrossConnEntry 9 }

containerCrossConnToClassName OBJECT-TYPE
    SYNTAX      EntityClassName
    MAX-ACCESS  not-accessible
    STATUS      current
    DESCRIPTION
        "Entity Class Name"
    ::=  { containerCrossConnEntry 10 }

containerCrossConnClassName OBJECT-TYPE
    SYNTAX      EntityClassName
    MAX-ACCESS  not-accessible
    STATUS      current
    DESCRIPTION
        "Entity Class Name"
    ::=  { containerCrossConnEntry 11 }

containerCrossConnAidString OBJECT-TYPE
    SYNTAX      SnmpAdminString
    MAX-ACCESS  read-only
    STATUS      current
    DESCRIPTION   "Aid string of entity."
    ::=  { containerCrossConnEntry 12 }

containerCrossConnFromId OBJECT-TYPE
    SYNTAX      RowPointer
    MAX-ACCESS  read-only
    STATUS      current
    DESCRIPTION   "RowPointer to FROM point entity."
    ::=  { containerCrossConnEntry 13 }

containerCrossConnToId OBJECT-TYPE
    SYNTAX      RowPointer
    MAX-ACCESS  read-only
    STATUS      current
    DESCRIPTION   "RowPointer to TO point entity."
    ::=  { containerCrossConnEntry 14 }

containerCrossConnClass OBJECT-TYPE
    SYNTAX      EntityClass
    MAX-ACCESS  read-only
    STATUS      current
    DESCRIPTION   "EntityClass"
    ::=  { containerCrossConnEntry 15 }

containerCrossConnTableId OBJECT-TYPE
    SYNTAX      RowPointer
    MAX-ACCESS  read-only
    STATUS      current
    DESCRIPTION   "RowPointer to managment table"
    ::=  { containerCrossConnEntry 16 }

containerCrossConnParentId OBJECT-TYPE
    SYNTAX      RowPointer
    MAX-ACCESS  read-only
    STATUS      current
    DESCRIPTION   "RowPointer to parent entity reported in corresponding entity table."
    ::=  { containerCrossConnEntry 17 }

containerCrossConnFromPointTable OBJECT-TYPE
    SYNTAX      SEQUENCE OF ContainerCrossConnFromPointEntry
    MAX-ACCESS  not-accessible
    STATUS      current
    DESCRIPTION   "containerCrossConnFromTable"
    ::=  { containers 9 }

containerCrossConnFromPointEntry OBJECT-TYPE
    SYNTAX      ContainerCrossConnFromPointEntry
    MAX-ACCESS  not-accessible
    STATUS      current
    DESCRIPTION   "Entry for containerCrossConnFromTable"
    INDEX       {
                  containerCrossConnFromPointShelfNo,
                  containerCrossConnFromPointSlotNo,
                  containerCrossConnFromPointPortNo,
                  containerCrossConnFromPointExtNo,
                  containerCrossConnFromPointClassName
                }
    ::=  { containerCrossConnFromPointTable 1 }

ContainerCrossConnFromPointEntry ::=  SEQUENCE
  { containerCrossConnFromPointShelfNo Unsigned32,
    containerCrossConnFromPointSlotNo Unsigned32,
    containerCrossConnFromPointPortNo Unsigned32,
    containerCrossConnFromPointExtNo Unsigned32,
    containerCrossConnFromPointClassName EntityClassName,
    containerCrossConnFromPointAidString SnmpAdminString,
    containerCrossConnFromPointFromId RowPointer,
    containerCrossConnFromPointClass EntityClass,
    containerCrossConnFromPointTableId RowPointer,
    containerCrossConnFromPointParentId RowPointer }

containerCrossConnFromPointShelfNo OBJECT-TYPE
    SYNTAX      Unsigned32
    MAX-ACCESS  not-accessible
    STATUS      current
    DESCRIPTION   "Adress index."
    ::=  { containerCrossConnFromPointEntry 1 }

containerCrossConnFromPointSlotNo OBJECT-TYPE
    SYNTAX      Unsigned32
    MAX-ACCESS  not-accessible
    STATUS      current
    DESCRIPTION   "Adress index."
    ::=  { containerCrossConnFromPointEntry 2 }

containerCrossConnFromPointPortNo OBJECT-TYPE
    SYNTAX      Unsigned32
    MAX-ACCESS  not-accessible
    STATUS      current
    DESCRIPTION   "Adress index."
    ::=  { containerCrossConnFromPointEntry 3 }

containerCrossConnFromPointExtNo OBJECT-TYPE
    SYNTAX      Unsigned32
    MAX-ACCESS  not-accessible
    STATUS      current
    DESCRIPTION   "Adress index."
    ::=  { containerCrossConnFromPointEntry 4 }

containerCrossConnFromPointClassName OBJECT-TYPE
    SYNTAX      EntityClassName
    MAX-ACCESS  not-accessible
    STATUS      current
    DESCRIPTION
        "Entity Class Name"
    ::=  { containerCrossConnFromPointEntry 5 }

containerCrossConnFromPointAidString OBJECT-TYPE
    SYNTAX      SnmpAdminString
    MAX-ACCESS  read-only
    STATUS      current
    DESCRIPTION   "Aid string of entity."
    ::=  { containerCrossConnFromPointEntry 6 }

containerCrossConnFromPointFromId OBJECT-TYPE
    SYNTAX      RowPointer
    MAX-ACCESS  read-only
    STATUS      current
    DESCRIPTION   "RowPointer to FROM point entity."
    ::=  { containerCrossConnFromPointEntry 7 }

containerCrossConnFromPointClass OBJECT-TYPE
    SYNTAX      EntityClass
    MAX-ACCESS  read-only
    STATUS      current
    DESCRIPTION   "EntityClass"
    ::=  { containerCrossConnFromPointEntry 8 }

containerCrossConnFromPointTableId OBJECT-TYPE
    SYNTAX      RowPointer
    MAX-ACCESS  read-only
    STATUS      current
    DESCRIPTION   "RowPointer to managment table"
    ::=  { containerCrossConnFromPointEntry 9 }

containerCrossConnFromPointParentId OBJECT-TYPE
    SYNTAX      RowPointer
    MAX-ACCESS  read-only
    STATUS      current
    DESCRIPTION   "RowPointer to parent entity reported in corresponding entity table."
    ::=  { containerCrossConnFromPointEntry 10 }

containerTerminPointTable OBJECT-TYPE
    SYNTAX      SEQUENCE OF ContainerTerminPointEntry
    MAX-ACCESS  not-accessible
    STATUS      current
    DESCRIPTION   "containerTerminPointTable"
    ::=  { containers 10 }

containerTerminPointEntry OBJECT-TYPE
    SYNTAX      ContainerTerminPointEntry
    MAX-ACCESS  not-accessible
    STATUS      current
    DESCRIPTION   "Entry for containerTerminPointTable"
    INDEX       {
                  containerTerminPointIndexNo1,
                  containerTerminPointIndexNo2,
                  containerTerminPointIndexNo3,
                  containerTerminPointIndexNo4,
                  containerTerminPointClassName
                }
    ::=  { containerTerminPointTable 1 }

ContainerTerminPointEntry ::=  SEQUENCE
  { containerTerminPointIndexNo1 Unsigned32,
    containerTerminPointIndexNo2 Unsigned32,
    containerTerminPointIndexNo3 Unsigned32,
    containerTerminPointIndexNo4 Unsigned32,
    containerTerminPointClassName EntityClassName,
    containerTerminPointAidString SnmpAdminString,
    containerTerminPointClass EntityClass,
    containerTerminPointTableId RowPointer,
    containerTerminPointParentId RowPointer }

containerTerminPointIndexNo1 OBJECT-TYPE
    SYNTAX      Unsigned32
    MAX-ACCESS  not-accessible
    STATUS      current
    DESCRIPTION   "Adress index."
    ::=  { containerTerminPointEntry 1 }

containerTerminPointIndexNo2 OBJECT-TYPE
    SYNTAX      Unsigned32
    MAX-ACCESS  not-accessible
    STATUS      current
    DESCRIPTION   "Adress index."
    ::=  { containerTerminPointEntry 2 }

containerTerminPointIndexNo3 OBJECT-TYPE
    SYNTAX      Unsigned32
    MAX-ACCESS  not-accessible
    STATUS      current
    DESCRIPTION   "Adress index."
    ::=  { containerTerminPointEntry 3 }

containerTerminPointIndexNo4 OBJECT-TYPE
    SYNTAX      Unsigned32
    MAX-ACCESS  not-accessible
    STATUS      current
    DESCRIPTION   "Adress index."
    ::=  { containerTerminPointEntry 4 }

containerTerminPointClassName OBJECT-TYPE
    SYNTAX      EntityClassName
    MAX-ACCESS  not-accessible
    STATUS      current
    DESCRIPTION
        "Entity Class Name"
    ::=  { containerTerminPointEntry 5 }

containerTerminPointAidString OBJECT-TYPE
    SYNTAX      SnmpAdminString
    MAX-ACCESS  read-only
    STATUS      current
    DESCRIPTION   "Aid string of entity."
    ::=  { containerTerminPointEntry 6 }

containerTerminPointClass OBJECT-TYPE
    SYNTAX      EntityClass
    MAX-ACCESS  read-only
    STATUS      current
    DESCRIPTION   "EntityClass"
    ::=  { containerTerminPointEntry 7 }

containerTerminPointTableId OBJECT-TYPE
    SYNTAX      RowPointer
    MAX-ACCESS  read-only
    STATUS      current
    DESCRIPTION   "RowPointer to managment table"
    ::=  { containerTerminPointEntry 8 }

containerTerminPointParentId OBJECT-TYPE
    SYNTAX      RowPointer
    MAX-ACCESS  read-only
    STATUS      current
    DESCRIPTION   "RowPointer to parent entity reported in corresponding entity table."
    ::=  { containerTerminPointEntry 9 }

containerConnectStdTable OBJECT-TYPE
    SYNTAX      SEQUENCE OF ContainerConnectStdEntry
    MAX-ACCESS  not-accessible
    STATUS      current
    DESCRIPTION   "containerConnectStdTable"
    ::=  { containers 11 }

containerConnectStdEntry OBJECT-TYPE
    SYNTAX      ContainerConnectStdEntry
    MAX-ACCESS  not-accessible
    STATUS      current
    DESCRIPTION   "Entry for containerConnectStdTable"
    INDEX       {
                  containerConnectStdNotation,
                  containerConnectStdFromIndexNo1,
                  containerConnectStdFromIndexNo2,
                  containerConnectStdFromIndexNo3,
                  containerConnectStdFromIndexNo4,
                  containerConnectStdFromClassName,
                  containerConnectStdToIndexNo1,
                  containerConnectStdToIndexNo2,
                  containerConnectStdToIndexNo3,
                  containerConnectStdToIndexNo4,
                  containerConnectStdToClassName,
                  containerConnectStdClassName
                }
    ::=  { containerConnectStdTable 1 }

ContainerConnectStdEntry ::=  SEQUENCE
  { containerConnectStdNotation ConnectionNotation,
    containerConnectStdFromIndexNo1 Unsigned32,
    containerConnectStdFromIndexNo2 Unsigned32,
    containerConnectStdFromIndexNo3 Unsigned32,
    containerConnectStdFromIndexNo4 Unsigned32,
    containerConnectStdFromClassName EntityClassName,
    containerConnectStdToIndexNo1 Unsigned32,
    containerConnectStdToIndexNo2 Unsigned32,
    containerConnectStdToIndexNo3 Unsigned32,
    containerConnectStdToIndexNo4 Unsigned32,
    containerConnectStdToClassName EntityClassName,
    containerConnectStdClassName EntityClassName,
    containerConnectStdAidString SnmpAdminString,
    containerConnectStdFromId RowPointer,
    containerConnectStdToId RowPointer,
    containerConnectStdClass EntityClass,
    containerConnectStdTableId RowPointer,
    containerConnectStdParentId RowPointer }

containerConnectStdNotation OBJECT-TYPE
    SYNTAX      ConnectionNotation
    MAX-ACCESS  not-accessible
    STATUS      current
    DESCRIPTION   "Notation indicates how to interpret the following indexes (keys) of
         the table. It has two values:
         fromToNotation(1) - first five idnexes represent FROM enity while next five indexes represent TO enity,
         toFromNotation(2) - first five idnexes represent TO enity while next five indexes represent FROM enity
        "
    ::=  { containerConnectStdEntry 1 }

containerConnectStdFromIndexNo1 OBJECT-TYPE
    SYNTAX      Unsigned32
    MAX-ACCESS  not-accessible
    STATUS      current
    DESCRIPTION   "Adress index."
    ::=  { containerConnectStdEntry 2 }

containerConnectStdFromIndexNo2 OBJECT-TYPE
    SYNTAX      Unsigned32
    MAX-ACCESS  not-accessible
    STATUS      current
    DESCRIPTION   "Adress index."
    ::=  { containerConnectStdEntry 3 }

containerConnectStdFromIndexNo3 OBJECT-TYPE
    SYNTAX      Unsigned32
    MAX-ACCESS  not-accessible
    STATUS      current
    DESCRIPTION   "Adress index."
    ::=  { containerConnectStdEntry 4 }

containerConnectStdFromIndexNo4 OBJECT-TYPE
    SYNTAX      Unsigned32
    MAX-ACCESS  not-accessible
    STATUS      current
    DESCRIPTION   "Adress index."
    ::=  { containerConnectStdEntry 5 }

containerConnectStdFromClassName OBJECT-TYPE
    SYNTAX      EntityClassName
    MAX-ACCESS  not-accessible
    STATUS      current
    DESCRIPTION
        "Entity Class Name"
    ::=  { containerConnectStdEntry 6 }

containerConnectStdToIndexNo1 OBJECT-TYPE
    SYNTAX      Unsigned32
    MAX-ACCESS  not-accessible
    STATUS      current
    DESCRIPTION   "Adress index."
    ::=  { containerConnectStdEntry 7 }

containerConnectStdToIndexNo2 OBJECT-TYPE
    SYNTAX      Unsigned32
    MAX-ACCESS  not-accessible
    STATUS      current
    DESCRIPTION   "Adress index."
    ::=  { containerConnectStdEntry 8 }

containerConnectStdToIndexNo3 OBJECT-TYPE
    SYNTAX      Unsigned32
    MAX-ACCESS  not-accessible
    STATUS      current
    DESCRIPTION   "Adress index."
    ::=  { containerConnectStdEntry 9 }

containerConnectStdToIndexNo4 OBJECT-TYPE
    SYNTAX      Unsigned32
    MAX-ACCESS  not-accessible
    STATUS      current
    DESCRIPTION   "Adress index."
    ::=  { containerConnectStdEntry 10 }

containerConnectStdToClassName OBJECT-TYPE
    SYNTAX      EntityClassName
    MAX-ACCESS  not-accessible
    STATUS      current
    DESCRIPTION
        "Entity Class Name"
    ::=  { containerConnectStdEntry 11 }

containerConnectStdClassName OBJECT-TYPE
    SYNTAX      EntityClassName
    MAX-ACCESS  not-accessible
    STATUS      current
    DESCRIPTION
        "Entity Class Name"
    ::=  { containerConnectStdEntry 12 }

containerConnectStdAidString OBJECT-TYPE
    SYNTAX      SnmpAdminString
    MAX-ACCESS  read-only
    STATUS      current
    DESCRIPTION   "Aid string of entity."
    ::=  { containerConnectStdEntry 13 }

containerConnectStdFromId OBJECT-TYPE
    SYNTAX      RowPointer
    MAX-ACCESS  read-only
    STATUS      current
    DESCRIPTION   "RowPointer to FROM point entity."
    ::=  { containerConnectStdEntry 14 }

containerConnectStdToId OBJECT-TYPE
    SYNTAX      RowPointer
    MAX-ACCESS  read-only
    STATUS      current
    DESCRIPTION   "RowPointer to TO point entity."
    ::=  { containerConnectStdEntry 15 }

containerConnectStdClass OBJECT-TYPE
    SYNTAX      EntityClass
    MAX-ACCESS  read-only
    STATUS      current
    DESCRIPTION   "EntityClass"
    ::=  { containerConnectStdEntry 16 }

containerConnectStdTableId OBJECT-TYPE
    SYNTAX      RowPointer
    MAX-ACCESS  read-only
    STATUS      current
    DESCRIPTION   "RowPointer to managment table"
    ::=  { containerConnectStdEntry 17 }

containerConnectStdParentId OBJECT-TYPE
    SYNTAX      RowPointer
    MAX-ACCESS  read-only
    STATUS      current
    DESCRIPTION   "RowPointer to parent entity reported in corresponding entity table."
    ::=  { containerConnectStdEntry 18 }

containerConnectNonStdTable OBJECT-TYPE
    SYNTAX      SEQUENCE OF ContainerConnectNonStdEntry
    MAX-ACCESS  not-accessible
    STATUS      current
    DESCRIPTION   "containerConnectNonStdTable"
    ::=  { containers 12 }

containerConnectNonStdEntry OBJECT-TYPE
    SYNTAX      ContainerConnectNonStdEntry
    MAX-ACCESS  not-accessible
    STATUS      current
    DESCRIPTION   "Entry for containerConnectNonStdTable"
    INDEX       {
                  containerConnectNonStdNotation,
                  containerConnectNonStdFromIndexNo1,
                  containerConnectNonStdFromIndexNo2,
                  containerConnectNonStdFromIndexNo3,
                  containerConnectNonStdFromIndexNo4,
                  containerConnectNonStdFromClassName,
                  containerConnectNonStdToIndexNo1,
                  containerConnectNonStdToIndexNo2,
                  containerConnectNonStdToIndexNo3,
                  containerConnectNonStdToIndexNo4,
                  containerConnectNonStdToClassName,
                  containerConnectNonStdClassName
                }
    ::=  { containerConnectNonStdTable 1 }

ContainerConnectNonStdEntry ::=  SEQUENCE
  { containerConnectNonStdNotation ConnectionNotation,
    containerConnectNonStdFromIndexNo1 Unsigned32,
    containerConnectNonStdFromIndexNo2 Unsigned32,
    containerConnectNonStdFromIndexNo3 Unsigned32,
    containerConnectNonStdFromIndexNo4 Unsigned32,
    containerConnectNonStdFromClassName EntityClassName,
    containerConnectNonStdToIndexNo1 Unsigned32,
    containerConnectNonStdToIndexNo2 Unsigned32,
    containerConnectNonStdToIndexNo3 Unsigned32,
    containerConnectNonStdToIndexNo4 Unsigned32,
    containerConnectNonStdToClassName EntityClassName,
    containerConnectNonStdClassName EntityClassName,
    containerConnectNonStdAidString SnmpAdminString,
    containerConnectNonStdFromId RowPointer,
    containerConnectNonStdToId RowPointer,
    containerConnectNonStdClass EntityClass,
    containerConnectNonStdTableId RowPointer,
    containerConnectNonStdParentId RowPointer }

containerConnectNonStdNotation OBJECT-TYPE
    SYNTAX      ConnectionNotation
    MAX-ACCESS  not-accessible
    STATUS      current
    DESCRIPTION   "Notation indicates how to interpret the following indexes (keys) of
         the table. It has two values:
         fromToNotation(1) - first five idnexes represent FROM enity while next five indexes represent TO enity,
         toFromNotation(2) - first five idnexes represent TO enity while next five indexes represent FROM enity
        "
    ::=  { containerConnectNonStdEntry 1 }

containerConnectNonStdFromIndexNo1 OBJECT-TYPE
    SYNTAX      Unsigned32
    MAX-ACCESS  not-accessible
    STATUS      current
    DESCRIPTION   "Adress index."
    ::=  { containerConnectNonStdEntry 2 }

containerConnectNonStdFromIndexNo2 OBJECT-TYPE
    SYNTAX      Unsigned32
    MAX-ACCESS  not-accessible
    STATUS      current
    DESCRIPTION   "Adress index."
    ::=  { containerConnectNonStdEntry 3 }

containerConnectNonStdFromIndexNo3 OBJECT-TYPE
    SYNTAX      Unsigned32
    MAX-ACCESS  not-accessible
    STATUS      current
    DESCRIPTION   "Adress index."
    ::=  { containerConnectNonStdEntry 4 }

containerConnectNonStdFromIndexNo4 OBJECT-TYPE
    SYNTAX      Unsigned32
    MAX-ACCESS  not-accessible
    STATUS      current
    DESCRIPTION   "Adress index."
    ::=  { containerConnectNonStdEntry 5 }

containerConnectNonStdFromClassName OBJECT-TYPE
    SYNTAX      EntityClassName
    MAX-ACCESS  not-accessible
    STATUS      current
    DESCRIPTION
        "Entity Class Name"
    ::=  { containerConnectNonStdEntry 6 }

containerConnectNonStdToIndexNo1 OBJECT-TYPE
    SYNTAX      Unsigned32
    MAX-ACCESS  not-accessible
    STATUS      current
    DESCRIPTION   "Adress index."
    ::=  { containerConnectNonStdEntry 7 }

containerConnectNonStdToIndexNo2 OBJECT-TYPE
    SYNTAX      Unsigned32
    MAX-ACCESS  not-accessible
    STATUS      current
    DESCRIPTION   "Adress index."
    ::=  { containerConnectNonStdEntry 8 }

containerConnectNonStdToIndexNo3 OBJECT-TYPE
    SYNTAX      Unsigned32
    MAX-ACCESS  not-accessible
    STATUS      current
    DESCRIPTION   "Adress index."
    ::=  { containerConnectNonStdEntry 9 }

containerConnectNonStdToIndexNo4 OBJECT-TYPE
    SYNTAX      Unsigned32
    MAX-ACCESS  not-accessible
    STATUS      current
    DESCRIPTION   "Adress index."
    ::=  { containerConnectNonStdEntry 10 }

containerConnectNonStdToClassName OBJECT-TYPE
    SYNTAX      EntityClassName
    MAX-ACCESS  not-accessible
    STATUS      current
    DESCRIPTION
        "Entity Class Name"
    ::=  { containerConnectNonStdEntry 11 }

containerConnectNonStdClassName OBJECT-TYPE
    SYNTAX      EntityClassName
    MAX-ACCESS  not-accessible
    STATUS      current
    DESCRIPTION
        "Entity Class Name"
    ::=  { containerConnectNonStdEntry 12 }

containerConnectNonStdAidString OBJECT-TYPE
    SYNTAX      SnmpAdminString
    MAX-ACCESS  read-only
    STATUS      current
    DESCRIPTION   "Aid string of entity."
    ::=  { containerConnectNonStdEntry 13 }

containerConnectNonStdFromId OBJECT-TYPE
    SYNTAX      RowPointer
    MAX-ACCESS  read-only
    STATUS      current
    DESCRIPTION   "RowPointer to FROM point entity."
    ::=  { containerConnectNonStdEntry 14 }

containerConnectNonStdToId OBJECT-TYPE
    SYNTAX      RowPointer
    MAX-ACCESS  read-only
    STATUS      current
    DESCRIPTION   "RowPointer to TO point entity."
    ::=  { containerConnectNonStdEntry 15 }

containerConnectNonStdClass OBJECT-TYPE
    SYNTAX      EntityClass
    MAX-ACCESS  read-only
    STATUS      current
    DESCRIPTION   "EntityClass"
    ::=  { containerConnectNonStdEntry 16 }

containerConnectNonStdTableId OBJECT-TYPE
    SYNTAX      RowPointer
    MAX-ACCESS  read-only
    STATUS      current
    DESCRIPTION   "RowPointer to managment table"
    ::=  { containerConnectNonStdEntry 17 }

containerConnectNonStdParentId OBJECT-TYPE
    SYNTAX      RowPointer
    MAX-ACCESS  read-only
    STATUS      current
    DESCRIPTION   "RowPointer to parent entity reported in corresponding entity table."
    ::=  { containerConnectNonStdEntry 18 }

containerExternalPortTable OBJECT-TYPE
    SYNTAX      SEQUENCE OF ContainerExternalPortEntry
    MAX-ACCESS  not-accessible
    STATUS      current
    DESCRIPTION   "containerExternalPort"
    ::=  { containers 13 }

containerExternalPortEntry OBJECT-TYPE
    SYNTAX      ContainerExternalPortEntry
    MAX-ACCESS  not-accessible
    STATUS      current
    DESCRIPTION   "Entry of containerExternalPort"
    INDEX       {
                  containerExternalPortShelfNo,
                  containerExternalPortSlotNo,
                  containerExternalPortPortNo,
                  containerExternalPortExtNo,
                  containerExternalPortClassName
                }
    ::=  { containerExternalPortTable 1 }

ContainerExternalPortEntry ::=  SEQUENCE
  { containerExternalPortShelfNo Unsigned32,
    containerExternalPortSlotNo Unsigned32,
    containerExternalPortPortNo Unsigned32,
    containerExternalPortExtNo Unsigned32,
    containerExternalPortClassName EntityClassName,
    containerExternalPortAidString SnmpAdminString,
    containerExternalPortClass EntityClass,
    containerExternalPortTableId RowPointer,
    containerExternalPortParentId RowPointer }

containerExternalPortShelfNo OBJECT-TYPE
    SYNTAX      Unsigned32
    MAX-ACCESS  not-accessible
    STATUS      current
    DESCRIPTION   "Adress index."
    ::=  { containerExternalPortEntry 1 }

containerExternalPortSlotNo OBJECT-TYPE
    SYNTAX      Unsigned32
    MAX-ACCESS  not-accessible
    STATUS      current
    DESCRIPTION   "Adress index."
    ::=  { containerExternalPortEntry 2 }

containerExternalPortPortNo OBJECT-TYPE
    SYNTAX      Unsigned32
    MAX-ACCESS  not-accessible
    STATUS      current
    DESCRIPTION   "Adress index."
    ::=  { containerExternalPortEntry 3 }

containerExternalPortExtNo OBJECT-TYPE
    SYNTAX      Unsigned32
    MAX-ACCESS  not-accessible
    STATUS      current
    DESCRIPTION   "Adress index."
    ::=  { containerExternalPortEntry 4 }

containerExternalPortClassName OBJECT-TYPE
    SYNTAX      EntityClassName
    MAX-ACCESS  not-accessible
    STATUS      current
    DESCRIPTION
        "Entity Class Name"
    ::=  { containerExternalPortEntry 5 }

containerExternalPortAidString OBJECT-TYPE
    SYNTAX      SnmpAdminString
    MAX-ACCESS  read-only
    STATUS      current
    DESCRIPTION   "Aid string of entity."
    ::=  { containerExternalPortEntry 6 }

containerExternalPortClass OBJECT-TYPE
    SYNTAX      EntityClass
    MAX-ACCESS  read-only
    STATUS      current
    DESCRIPTION   "EntityClass"
    ::=  { containerExternalPortEntry 7 }

containerExternalPortTableId OBJECT-TYPE
    SYNTAX      RowPointer
    MAX-ACCESS  read-only
    STATUS      current
    DESCRIPTION   "RowPointer to managment table"
    ::=  { containerExternalPortEntry 8 }

containerExternalPortParentId OBJECT-TYPE
    SYNTAX      RowPointer
    MAX-ACCESS  read-only
    STATUS      current
    DESCRIPTION   "RowPointer to parent entity reported in corresponding entity table."
    ::=  { containerExternalPortEntry 9 }

containerCrsOptLineTable OBJECT-TYPE
    SYNTAX      SEQUENCE OF ContainerCrsOptLineEntry
    MAX-ACCESS  not-accessible
    STATUS      current
    DESCRIPTION   "containerCrsOptLineTable"
    ::=  { containers 14 }

containerCrsOptLineEntry OBJECT-TYPE
    SYNTAX      ContainerCrsOptLineEntry
    MAX-ACCESS  not-accessible
    STATUS      current
    DESCRIPTION   "Entry of containerCrsOptLineTable"
    INDEX       {
                  containerCrsOptLineFromIndexNo1,
                  containerCrsOptLineFromIndexNo2,
                  containerCrsOptLineFromIndexNo3,
                  containerCrsOptLineFromIndexNo4,
                  containerCrsOptLineFromClassName,
                  containerCrsOptLineToIndexNo1,
                  containerCrsOptLineToIndexNo2,
                  containerCrsOptLineToIndexNo3,
                  containerCrsOptLineToIndexNo4,
                  containerCrsOptLineToClassName,
                  containerCrsOptLineClassName
                }
    ::=  { containerCrsOptLineTable 1 }

ContainerCrsOptLineEntry ::=  SEQUENCE
  { containerCrsOptLineFromIndexNo1 Unsigned32,
    containerCrsOptLineFromIndexNo2 Unsigned32,
    containerCrsOptLineFromIndexNo3 Unsigned32,
    containerCrsOptLineFromIndexNo4 Unsigned32,
    containerCrsOptLineFromClassName EntityClassName,
    containerCrsOptLineToIndexNo1 Unsigned32,
    containerCrsOptLineToIndexNo2 Unsigned32,
    containerCrsOptLineToIndexNo3 Unsigned32,
    containerCrsOptLineToIndexNo4 Unsigned32,
    containerCrsOptLineToClassName EntityClassName,
    containerCrsOptLineClassName EntityClassName,
    containerCrsOptLineAidString SnmpAdminString,
    containerCrsOptLineFromId RowPointer,
    containerCrsOptLineToId RowPointer,
    containerCrsOptLineClass EntityClass,
    containerCrsOptLineTableId RowPointer,
    containerCrsOptLineParentId RowPointer }

containerCrsOptLineFromIndexNo1 OBJECT-TYPE
    SYNTAX      Unsigned32
    MAX-ACCESS  not-accessible
    STATUS      current
    DESCRIPTION   "Adress index."
    ::=  { containerCrsOptLineEntry 1 }

containerCrsOptLineFromIndexNo2 OBJECT-TYPE
    SYNTAX      Unsigned32
    MAX-ACCESS  not-accessible
    STATUS      current
    DESCRIPTION   "Adress index."
    ::=  { containerCrsOptLineEntry 2 }

containerCrsOptLineFromIndexNo3 OBJECT-TYPE
    SYNTAX      Unsigned32
    MAX-ACCESS  not-accessible
    STATUS      current
    DESCRIPTION   "Adress index."
    ::=  { containerCrsOptLineEntry 3 }

containerCrsOptLineFromIndexNo4 OBJECT-TYPE
    SYNTAX      Unsigned32
    MAX-ACCESS  not-accessible
    STATUS      current
    DESCRIPTION   "Adress index."
    ::=  { containerCrsOptLineEntry 4 }

containerCrsOptLineFromClassName OBJECT-TYPE
    SYNTAX      EntityClassName
    MAX-ACCESS  not-accessible
    STATUS      current
    DESCRIPTION
        "Entity Class Name"
    ::=  { containerCrsOptLineEntry 5 }

containerCrsOptLineToIndexNo1 OBJECT-TYPE
    SYNTAX      Unsigned32
    MAX-ACCESS  not-accessible
    STATUS      current
    DESCRIPTION   "Adress index."
    ::=  { containerCrsOptLineEntry 6 }

containerCrsOptLineToIndexNo2 OBJECT-TYPE
    SYNTAX      Unsigned32
    MAX-ACCESS  not-accessible
    STATUS      current
    DESCRIPTION   "Adress index."
    ::=  { containerCrsOptLineEntry 7 }

containerCrsOptLineToIndexNo3 OBJECT-TYPE
    SYNTAX      Unsigned32
    MAX-ACCESS  not-accessible
    STATUS      current
    DESCRIPTION   "Adress index."
    ::=  { containerCrsOptLineEntry 8 }

containerCrsOptLineToIndexNo4 OBJECT-TYPE
    SYNTAX      Unsigned32
    MAX-ACCESS  not-accessible
    STATUS      current
    DESCRIPTION   "Adress index."
    ::=  { containerCrsOptLineEntry 9 }

containerCrsOptLineToClassName OBJECT-TYPE
    SYNTAX      EntityClassName
    MAX-ACCESS  not-accessible
    STATUS      current
    DESCRIPTION
        "Entity Class Name"
    ::=  { containerCrsOptLineEntry 10 }

containerCrsOptLineClassName OBJECT-TYPE
    SYNTAX      EntityClassName
    MAX-ACCESS  not-accessible
    STATUS      current
    DESCRIPTION
        "Entity Class Name"
    ::=  { containerCrsOptLineEntry 11 }

containerCrsOptLineAidString OBJECT-TYPE
    SYNTAX      SnmpAdminString
    MAX-ACCESS  read-only
    STATUS      current
    DESCRIPTION   "Aid string of entity."
    ::=  { containerCrsOptLineEntry 12 }

containerCrsOptLineFromId OBJECT-TYPE
    SYNTAX      RowPointer
    MAX-ACCESS  read-only
    STATUS      current
    DESCRIPTION   "RowPointer to FROM point entity."
    ::=  { containerCrsOptLineEntry 13 }

containerCrsOptLineToId OBJECT-TYPE
    SYNTAX      RowPointer
    MAX-ACCESS  read-only
    STATUS      current
    DESCRIPTION   "RowPointer to TO point entity."
    ::=  { containerCrsOptLineEntry 14 }

containerCrsOptLineClass OBJECT-TYPE
    SYNTAX      EntityClass
    MAX-ACCESS  read-only
    STATUS      current
    DESCRIPTION   "EntityClass"
    ::=  { containerCrsOptLineEntry 15 }

containerCrsOptLineTableId OBJECT-TYPE
    SYNTAX      RowPointer
    MAX-ACCESS  read-only
    STATUS      current
    DESCRIPTION   "RowPointer to managment table"
    ::=  { containerCrsOptLineEntry 16 }

containerCrsOptLineParentId OBJECT-TYPE
    SYNTAX      RowPointer
    MAX-ACCESS  read-only
    STATUS      current
    DESCRIPTION   "RowPointer to parent entity reported in corresponding entity table."
    ::=  { containerCrsOptLineEntry 17 }

containerCrsOptLineFromPointTable OBJECT-TYPE
    SYNTAX      SEQUENCE OF ContainerCrsOptLineFromPointEntry
    MAX-ACCESS  not-accessible
    STATUS      current
    DESCRIPTION   "containerCrsOptLineFromTable"
    ::=  { containers 15 }

containerCrsOptLineFromPointEntry OBJECT-TYPE
    SYNTAX      ContainerCrsOptLineFromPointEntry
    MAX-ACCESS  not-accessible
    STATUS      current
    DESCRIPTION   "Entry for containerCrsOptLineFromTable"
    INDEX       {
                  containerCrsOptLineFromPointIndexNo1,
                  containerCrsOptLineFromPointIndexNo2,
                  containerCrsOptLineFromPointIndexNo3,
                  containerCrsOptLineFromPointIndexNo4,
                  containerCrsOptLineFromPointClassName
                }
    ::=  { containerCrsOptLineFromPointTable 1 }

ContainerCrsOptLineFromPointEntry ::=  SEQUENCE
  { containerCrsOptLineFromPointIndexNo1 Unsigned32,
    containerCrsOptLineFromPointIndexNo2 Unsigned32,
    containerCrsOptLineFromPointIndexNo3 Unsigned32,
    containerCrsOptLineFromPointIndexNo4 Unsigned32,
    containerCrsOptLineFromPointClassName EntityClassName,
    containerCrsOptLineFromPointAidString SnmpAdminString,
    containerCrsOptLineFromPointFromId RowPointer,
    containerCrsOptLineFromPointClass EntityClass,
    containerCrsOptLineFromPointTableId RowPointer,
    containerCrsOptLineFromPointParentId RowPointer }

containerCrsOptLineFromPointIndexNo1 OBJECT-TYPE
    SYNTAX      Unsigned32
    MAX-ACCESS  not-accessible
    STATUS      current
    DESCRIPTION   "Adress index."
    ::=  { containerCrsOptLineFromPointEntry 1 }

containerCrsOptLineFromPointIndexNo2 OBJECT-TYPE
    SYNTAX      Unsigned32
    MAX-ACCESS  not-accessible
    STATUS      current
    DESCRIPTION   "Adress index."
    ::=  { containerCrsOptLineFromPointEntry 2 }

containerCrsOptLineFromPointIndexNo3 OBJECT-TYPE
    SYNTAX      Unsigned32
    MAX-ACCESS  not-accessible
    STATUS      current
    DESCRIPTION   "Adress index."
    ::=  { containerCrsOptLineFromPointEntry 3 }

containerCrsOptLineFromPointIndexNo4 OBJECT-TYPE
    SYNTAX      Unsigned32
    MAX-ACCESS  not-accessible
    STATUS      current
    DESCRIPTION   "Adress index."
    ::=  { containerCrsOptLineFromPointEntry 4 }

containerCrsOptLineFromPointClassName OBJECT-TYPE
    SYNTAX      EntityClassName
    MAX-ACCESS  not-accessible
    STATUS      current
    DESCRIPTION
        "Entity Class Name"
    ::=  { containerCrsOptLineFromPointEntry 5 }

containerCrsOptLineFromPointAidString OBJECT-TYPE
    SYNTAX      SnmpAdminString
    MAX-ACCESS  read-only
    STATUS      current
    DESCRIPTION   "Aid string of entity."
    ::=  { containerCrsOptLineFromPointEntry 6 }

containerCrsOptLineFromPointFromId OBJECT-TYPE
    SYNTAX      RowPointer
    MAX-ACCESS  read-only
    STATUS      current
    DESCRIPTION   "RowPointer to FROM point entity."
    ::=  { containerCrsOptLineFromPointEntry 7 }

containerCrsOptLineFromPointClass OBJECT-TYPE
    SYNTAX      EntityClass
    MAX-ACCESS  read-only
    STATUS      current
    DESCRIPTION   "EntityClass"
    ::=  { containerCrsOptLineFromPointEntry 8 }

containerCrsOptLineFromPointTableId OBJECT-TYPE
    SYNTAX      RowPointer
    MAX-ACCESS  read-only
    STATUS      current
    DESCRIPTION   "RowPointer to managment table"
    ::=  { containerCrsOptLineFromPointEntry 9 }

containerCrsOptLineFromPointParentId OBJECT-TYPE
    SYNTAX      RowPointer
    MAX-ACCESS  read-only
    STATUS      current
    DESCRIPTION   "RowPointer to parent entity reported in corresponding entity table."
    ::=  { containerCrsOptLineFromPointEntry 10 }

containerChTable OBJECT-TYPE
    SYNTAX      SEQUENCE OF ContainerChEntry
    MAX-ACCESS  not-accessible
    STATUS      current
    DESCRIPTION   "containerChTable"
    ::=  { containers 20 }

containerChEntry OBJECT-TYPE
    SYNTAX      ContainerChEntry
    MAX-ACCESS  not-accessible
    STATUS      current
    DESCRIPTION   "Entry of containerChTable"
    INDEX       {
                  containerChShelfNo,
                  containerChSlotNo,
                  containerChPortNo,
                  containerChExtNo,
                  containerChClassName
                }
    ::=  { containerChTable 1 }

ContainerChEntry ::=  SEQUENCE
  { containerChShelfNo Unsigned32,
    containerChSlotNo Unsigned32,
    containerChPortNo Unsigned32,
    containerChExtNo Unsigned32,
    containerChClassName EntityClassName,
    containerChAidString SnmpAdminString,
    containerChClass EntityClass,
    containerChTableId RowPointer,
    containerChParentId RowPointer }

containerChShelfNo OBJECT-TYPE
    SYNTAX      Unsigned32
    MAX-ACCESS  not-accessible
    STATUS      current
    DESCRIPTION   "Adress index."
    ::=  { containerChEntry 1 }

containerChSlotNo OBJECT-TYPE
    SYNTAX      Unsigned32
    MAX-ACCESS  not-accessible
    STATUS      current
    DESCRIPTION   "Adress index."
    ::=  { containerChEntry 2 }

containerChPortNo OBJECT-TYPE
    SYNTAX      Unsigned32
    MAX-ACCESS  not-accessible
    STATUS      current
    DESCRIPTION   "Adress index."
    ::=  { containerChEntry 3 }

containerChExtNo OBJECT-TYPE
    SYNTAX      Unsigned32
    MAX-ACCESS  not-accessible
    STATUS      current
    DESCRIPTION   "Adress index."
    ::=  { containerChEntry 4 }

containerChClassName OBJECT-TYPE
    SYNTAX      EntityClassName
    MAX-ACCESS  not-accessible
    STATUS      current
    DESCRIPTION
        "Entity Class Name"
    ::=  { containerChEntry 5 }

containerChAidString OBJECT-TYPE
    SYNTAX      SnmpAdminString
    MAX-ACCESS  read-only
    STATUS      current
    DESCRIPTION   "Aid string of entity."
    ::=  { containerChEntry 6 }

containerChClass OBJECT-TYPE
    SYNTAX      EntityClass
    MAX-ACCESS  read-only
    STATUS      current
    DESCRIPTION
        "Entity Class"
    ::=  { containerChEntry 7 }

containerChTableId OBJECT-TYPE
    SYNTAX      RowPointer
    MAX-ACCESS  read-only
    STATUS      current
    DESCRIPTION   "RowPointer to managment table"
    ::=  { containerChEntry 8 }

containerChParentId OBJECT-TYPE
    SYNTAX      RowPointer
    MAX-ACCESS  read-only
    STATUS      current
    DESCRIPTION   "RowPointer to parent entity reported in corresponding entity table."
    ::=  { containerChEntry 9 }

containerEthTable OBJECT-TYPE
    SYNTAX      SEQUENCE OF ContainerEthEntry
    MAX-ACCESS  not-accessible
    STATUS      current
    DESCRIPTION   "containerEthTable"
    ::=  { containers 21 }

containerEthEntry OBJECT-TYPE
    SYNTAX      ContainerEthEntry
    MAX-ACCESS  not-accessible
    STATUS      current
    DESCRIPTION   "Entry of containerEthTable"
    INDEX       {
                  containerEthShelfNo,
                  containerEthSlotNo,
                  containerEthPortNo,
                  containerEthExtNo,
                  containerEthClassName
                }
    ::=  { containerEthTable 1 }

ContainerEthEntry ::=  SEQUENCE
  { containerEthShelfNo Unsigned32,
    containerEthSlotNo Unsigned32,
    containerEthPortNo Unsigned32,
    containerEthExtNo Unsigned32,
    containerEthClassName EntityClassName,
    containerEthAidString SnmpAdminString,
    containerEthClass EntityClass,
    containerEthTableId RowPointer,
    containerEthParentId RowPointer }

containerEthShelfNo OBJECT-TYPE
    SYNTAX      Unsigned32
    MAX-ACCESS  not-accessible
    STATUS      current
    DESCRIPTION   "Adress index."
    ::=  { containerEthEntry 1 }

containerEthSlotNo OBJECT-TYPE
    SYNTAX      Unsigned32
    MAX-ACCESS  not-accessible
    STATUS      current
    DESCRIPTION   "Adress index."
    ::=  { containerEthEntry 2 }

containerEthPortNo OBJECT-TYPE
    SYNTAX      Unsigned32
    MAX-ACCESS  not-accessible
    STATUS      current
    DESCRIPTION   "Adress index."
    ::=  { containerEthEntry 3 }

containerEthExtNo OBJECT-TYPE
    SYNTAX      Unsigned32
    MAX-ACCESS  not-accessible
    STATUS      current
    DESCRIPTION   "Adress index."
    ::=  { containerEthEntry 4 }

containerEthClassName OBJECT-TYPE
    SYNTAX      EntityClassName
    MAX-ACCESS  not-accessible
    STATUS      current
    DESCRIPTION
        "Entity Class Name"
    ::=  { containerEthEntry 5 }

containerEthAidString OBJECT-TYPE
    SYNTAX      SnmpAdminString
    MAX-ACCESS  read-only
    STATUS      current
    DESCRIPTION   "Aid string of entity."
    ::=  { containerEthEntry 6 }

containerEthClass OBJECT-TYPE
    SYNTAX      EntityClass
    MAX-ACCESS  read-only
    STATUS      current
    DESCRIPTION
        "Entity Class"
    ::=  { containerEthEntry 7 }

containerEthTableId OBJECT-TYPE
    SYNTAX      RowPointer
    MAX-ACCESS  read-only
    STATUS      current
    DESCRIPTION   "RowPointer to managment table"
    ::=  { containerEthEntry 8 }

containerEthParentId OBJECT-TYPE
    SYNTAX      RowPointer
    MAX-ACCESS  read-only
    STATUS      current
    DESCRIPTION   "RowPointer to parent entity reported in corresponding entity table."
    ::=  { containerEthEntry 9 }

containerVethTable OBJECT-TYPE
    SYNTAX      SEQUENCE OF ContainerVethEntry
    MAX-ACCESS  not-accessible
    STATUS      current
    DESCRIPTION   "containerVethTable"
    ::=  { containers 22 }

containerVethEntry OBJECT-TYPE
    SYNTAX      ContainerVethEntry
    MAX-ACCESS  not-accessible
    STATUS      current
    DESCRIPTION   "Entry of containerVethTable"
    INDEX       {
                  containerVethShelfNo,
                  containerVethSlotNo,
                  containerVethPortNo,
                  containerVethExtNo,
                  containerVethClassName
                }
    ::=  { containerVethTable 1 }

ContainerVethEntry ::=  SEQUENCE
  { containerVethShelfNo Unsigned32,
    containerVethSlotNo Unsigned32,
    containerVethPortNo Unsigned32,
    containerVethExtNo Unsigned32,
    containerVethClassName EntityClassName,
    containerVethAidString SnmpAdminString,
    containerVethClass EntityClass,
    containerVethTableId RowPointer,
    containerVethParentId RowPointer }

containerVethShelfNo OBJECT-TYPE
    SYNTAX      Unsigned32
    MAX-ACCESS  not-accessible
    STATUS      current
    DESCRIPTION   "Adress index."
    ::=  { containerVethEntry 1 }

containerVethSlotNo OBJECT-TYPE
    SYNTAX      Unsigned32
    MAX-ACCESS  not-accessible
    STATUS      current
    DESCRIPTION   "Adress index."
    ::=  { containerVethEntry 2 }

containerVethPortNo OBJECT-TYPE
    SYNTAX      Unsigned32
    MAX-ACCESS  not-accessible
    STATUS      current
    DESCRIPTION   "Adress index."
    ::=  { containerVethEntry 3 }

containerVethExtNo OBJECT-TYPE
    SYNTAX      Unsigned32
    MAX-ACCESS  not-accessible
    STATUS      current
    DESCRIPTION   "Adress index."
    ::=  { containerVethEntry 4 }

containerVethClassName OBJECT-TYPE
    SYNTAX      EntityClassName
    MAX-ACCESS  not-accessible
    STATUS      current
    DESCRIPTION
        "Entity Class Name"
    ::=  { containerVethEntry 5 }

containerVethAidString OBJECT-TYPE
    SYNTAX      SnmpAdminString
    MAX-ACCESS  read-only
    STATUS      current
    DESCRIPTION   "Aid string of entity."
    ::=  { containerVethEntry 6 }

containerVethClass OBJECT-TYPE
    SYNTAX      EntityClass
    MAX-ACCESS  read-only
    STATUS      current
    DESCRIPTION
        "Entity Class"
    ::=  { containerVethEntry 7 }

containerVethTableId OBJECT-TYPE
    SYNTAX      RowPointer
    MAX-ACCESS  read-only
    STATUS      current
    DESCRIPTION   "RowPointer to managment table"
    ::=  { containerVethEntry 8 }

containerVethParentId OBJECT-TYPE
    SYNTAX      RowPointer
    MAX-ACCESS  read-only
    STATUS      current
    DESCRIPTION   "RowPointer to parent entity reported in corresponding entity table."
    ::=  { containerVethEntry 9 }

containerOtlgTable OBJECT-TYPE
    SYNTAX      SEQUENCE OF ContainerOtlgEntry
    MAX-ACCESS  not-accessible
    STATUS      current
    DESCRIPTION   "containerOtlgTable"
    ::=  { containers 23 }

containerOtlgEntry OBJECT-TYPE
    SYNTAX      ContainerOtlgEntry
    MAX-ACCESS  not-accessible
    STATUS      current
    DESCRIPTION   "Entry of containerOtlgTable"
    INDEX       {
                  containerOtlgShelfNo,
                  containerOtlgSlotNo,
                  containerOtlgPortNo,
                  containerOtlgExtNo,
                  containerOtlgClassName
                }
    ::=  { containerOtlgTable 1 }

ContainerOtlgEntry ::=  SEQUENCE
  { containerOtlgShelfNo Unsigned32,
    containerOtlgSlotNo Unsigned32,
    containerOtlgPortNo Unsigned32,
    containerOtlgExtNo Unsigned32,
    containerOtlgClassName EntityClassName,
    containerOtlgAidString SnmpAdminString,
    containerOtlgClass EntityClass,
    containerOtlgTableId RowPointer,
    containerOtlgParentId RowPointer }

containerOtlgShelfNo OBJECT-TYPE
    SYNTAX      Unsigned32
    MAX-ACCESS  not-accessible
    STATUS      current
    DESCRIPTION   "Adress index."
    ::=  { containerOtlgEntry 1 }

containerOtlgSlotNo OBJECT-TYPE
    SYNTAX      Unsigned32
    MAX-ACCESS  not-accessible
    STATUS      current
    DESCRIPTION   "Adress index."
    ::=  { containerOtlgEntry 2 }

containerOtlgPortNo OBJECT-TYPE
    SYNTAX      Unsigned32
    MAX-ACCESS  not-accessible
    STATUS      current
    DESCRIPTION   "Adress index."
    ::=  { containerOtlgEntry 3 }

containerOtlgExtNo OBJECT-TYPE
    SYNTAX      Unsigned32
    MAX-ACCESS  not-accessible
    STATUS      current
    DESCRIPTION   "Adress index."
    ::=  { containerOtlgEntry 4 }

containerOtlgClassName OBJECT-TYPE
    SYNTAX      EntityClassName
    MAX-ACCESS  not-accessible
    STATUS      current
    DESCRIPTION
        "Entity Class Name"
    ::=  { containerOtlgEntry 5 }

containerOtlgAidString OBJECT-TYPE
    SYNTAX      SnmpAdminString
    MAX-ACCESS  read-only
    STATUS      current
    DESCRIPTION   "Aid string of entity."
    ::=  { containerOtlgEntry 6 }

containerOtlgClass OBJECT-TYPE
    SYNTAX      EntityClass
    MAX-ACCESS  read-only
    STATUS      current
    DESCRIPTION
        "Entity Class"
    ::=  { containerOtlgEntry 7 }

containerOtlgTableId OBJECT-TYPE
    SYNTAX      RowPointer
    MAX-ACCESS  read-only
    STATUS      current
    DESCRIPTION   "RowPointer to managment table"
    ::=  { containerOtlgEntry 8 }

containerOtlgParentId OBJECT-TYPE
    SYNTAX      RowPointer
    MAX-ACCESS  read-only
    STATUS      current
    DESCRIPTION   "RowPointer to parent entity reported in corresponding entity table."
    ::=  { containerOtlgEntry 9 }

containerPchTable OBJECT-TYPE
    SYNTAX      SEQUENCE OF ContainerPchEntry
    MAX-ACCESS  not-accessible
    STATUS      current
    DESCRIPTION   "containerPchTable"
    ::=  { containers 24 }

containerPchEntry OBJECT-TYPE
    SYNTAX      ContainerPchEntry
    MAX-ACCESS  not-accessible
    STATUS      current
    DESCRIPTION   "Entry of containerPchTable"
    INDEX       {
                  containerPchShelfNo,
                  containerPchSlotNo,
                  containerPchPortNo,
                  containerPchExtNo,
                  containerPchClassName
                }
    ::=  { containerPchTable 1 }

ContainerPchEntry ::=  SEQUENCE
  { containerPchShelfNo Unsigned32,
    containerPchSlotNo Unsigned32,
    containerPchPortNo Unsigned32,
    containerPchExtNo Unsigned32,
    containerPchClassName EntityClassName,
    containerPchAidString SnmpAdminString,
    containerPchClass EntityClass,
    containerPchTableId RowPointer,
    containerPchParentId RowPointer }

containerPchShelfNo OBJECT-TYPE
    SYNTAX      Unsigned32
    MAX-ACCESS  not-accessible
    STATUS      current
    DESCRIPTION   "Adress index."
    ::=  { containerPchEntry 1 }

containerPchSlotNo OBJECT-TYPE
    SYNTAX      Unsigned32
    MAX-ACCESS  not-accessible
    STATUS      current
    DESCRIPTION   "Adress index."
    ::=  { containerPchEntry 2 }

containerPchPortNo OBJECT-TYPE
    SYNTAX      Unsigned32
    MAX-ACCESS  not-accessible
    STATUS      current
    DESCRIPTION   "Adress index."
    ::=  { containerPchEntry 3 }

containerPchExtNo OBJECT-TYPE
    SYNTAX      Unsigned32
    MAX-ACCESS  not-accessible
    STATUS      current
    DESCRIPTION   "Adress index."
    ::=  { containerPchEntry 4 }

containerPchClassName OBJECT-TYPE
    SYNTAX      EntityClassName
    MAX-ACCESS  not-accessible
    STATUS      current
    DESCRIPTION
        "Entity Class Name"
    ::=  { containerPchEntry 5 }

containerPchAidString OBJECT-TYPE
    SYNTAX      SnmpAdminString
    MAX-ACCESS  read-only
    STATUS      current
    DESCRIPTION   "Aid string of entity."
    ::=  { containerPchEntry 6 }

containerPchClass OBJECT-TYPE
    SYNTAX      EntityClass
    MAX-ACCESS  read-only
    STATUS      current
    DESCRIPTION
        "Entity Class"
    ::=  { containerPchEntry 7 }

containerPchTableId OBJECT-TYPE
    SYNTAX      RowPointer
    MAX-ACCESS  read-only
    STATUS      current
    DESCRIPTION   "RowPointer to managment table"
    ::=  { containerPchEntry 8 }

containerPchParentId OBJECT-TYPE
    SYNTAX      RowPointer
    MAX-ACCESS  read-only
    STATUS      current
    DESCRIPTION   "RowPointer to parent entity reported in corresponding entity table."
    ::=  { containerPchEntry 9 }

containerVschTable OBJECT-TYPE
    SYNTAX      SEQUENCE OF ContainerVschEntry
    MAX-ACCESS  not-accessible
    STATUS      current
    DESCRIPTION   "containerVschTable"
    ::=  { containers 25 }

containerVschEntry OBJECT-TYPE
    SYNTAX      ContainerVschEntry
    MAX-ACCESS  not-accessible
    STATUS      current
    DESCRIPTION   "Entry of containerVschTable"
    INDEX       {
                  containerVschShelfNo,
                  containerVschSlotNo,
                  containerVschPortNo,
                  containerVschExtNo,
                  containerVschClassName
                }
    ::=  { containerVschTable 1 }

ContainerVschEntry ::=  SEQUENCE
  { containerVschShelfNo Unsigned32,
    containerVschSlotNo Unsigned32,
    containerVschPortNo Unsigned32,
    containerVschExtNo Unsigned32,
    containerVschClassName EntityClassName,
    containerVschAidString SnmpAdminString,
    containerVschClass EntityClass,
    containerVschTableId RowPointer,
    containerVschParentId RowPointer }

containerVschShelfNo OBJECT-TYPE
    SYNTAX      Unsigned32
    MAX-ACCESS  not-accessible
    STATUS      current
    DESCRIPTION   "Adress index."
    ::=  { containerVschEntry 1 }

containerVschSlotNo OBJECT-TYPE
    SYNTAX      Unsigned32
    MAX-ACCESS  not-accessible
    STATUS      current
    DESCRIPTION   "Adress index."
    ::=  { containerVschEntry 2 }

containerVschPortNo OBJECT-TYPE
    SYNTAX      Unsigned32
    MAX-ACCESS  not-accessible
    STATUS      current
    DESCRIPTION   "Adress index."
    ::=  { containerVschEntry 3 }

containerVschExtNo OBJECT-TYPE
    SYNTAX      Unsigned32
    MAX-ACCESS  not-accessible
    STATUS      current
    DESCRIPTION   "Adress index."
    ::=  { containerVschEntry 4 }

containerVschClassName OBJECT-TYPE
    SYNTAX      EntityClassName
    MAX-ACCESS  not-accessible
    STATUS      current
    DESCRIPTION
        "Entity Class Name"
    ::=  { containerVschEntry 5 }

containerVschAidString OBJECT-TYPE
    SYNTAX      SnmpAdminString
    MAX-ACCESS  read-only
    STATUS      current
    DESCRIPTION   "Aid string of entity."
    ::=  { containerVschEntry 6 }

containerVschClass OBJECT-TYPE
    SYNTAX      EntityClass
    MAX-ACCESS  read-only
    STATUS      current
    DESCRIPTION
        "Entity Class"
    ::=  { containerVschEntry 7 }

containerVschTableId OBJECT-TYPE
    SYNTAX      RowPointer
    MAX-ACCESS  read-only
    STATUS      current
    DESCRIPTION   "RowPointer to managment table"
    ::=  { containerVschEntry 8 }

containerVschParentId OBJECT-TYPE
    SYNTAX      RowPointer
    MAX-ACCESS  read-only
    STATUS      current
    DESCRIPTION   "RowPointer to parent entity reported in corresponding entity table."
    ::=  { containerVschEntry 9 }

containerVch1Table OBJECT-TYPE
    SYNTAX      SEQUENCE OF ContainerVch1Entry
    MAX-ACCESS  not-accessible
    STATUS      current
    DESCRIPTION   "containerVch1Table"
    ::=  { containers 26 }

containerVch1Entry OBJECT-TYPE
    SYNTAX      ContainerVch1Entry
    MAX-ACCESS  not-accessible
    STATUS      current
    DESCRIPTION   "Entry of containerVch1Table"
    INDEX       {
                  containerVch1ShelfNo,
                  containerVch1SlotNo,
                  containerVch1PortNo,
                  containerVch1ExtNo,
                  containerVch1ClassName
                }
    ::=  { containerVch1Table 1 }

ContainerVch1Entry ::=  SEQUENCE
  { containerVch1ShelfNo Unsigned32,
    containerVch1SlotNo Unsigned32,
    containerVch1PortNo Unsigned32,
    containerVch1ExtNo Unsigned32,
    containerVch1ClassName EntityClassName,
    containerVch1AidString SnmpAdminString,
    containerVch1Class EntityClass,
    containerVch1TableId RowPointer,
    containerVch1ParentId RowPointer }

containerVch1ShelfNo OBJECT-TYPE
    SYNTAX      Unsigned32
    MAX-ACCESS  not-accessible
    STATUS      current
    DESCRIPTION   "Adress index."
    ::=  { containerVch1Entry 1 }

containerVch1SlotNo OBJECT-TYPE
    SYNTAX      Unsigned32
    MAX-ACCESS  not-accessible
    STATUS      current
    DESCRIPTION   "Adress index."
    ::=  { containerVch1Entry 2 }

containerVch1PortNo OBJECT-TYPE
    SYNTAX      Unsigned32
    MAX-ACCESS  not-accessible
    STATUS      current
    DESCRIPTION   "Adress index."
    ::=  { containerVch1Entry 3 }

containerVch1ExtNo OBJECT-TYPE
    SYNTAX      Unsigned32
    MAX-ACCESS  not-accessible
    STATUS      current
    DESCRIPTION   "Adress index."
    ::=  { containerVch1Entry 4 }

containerVch1ClassName OBJECT-TYPE
    SYNTAX      EntityClassName
    MAX-ACCESS  not-accessible
    STATUS      current
    DESCRIPTION
        "Entity Class Name"
    ::=  { containerVch1Entry 5 }

containerVch1AidString OBJECT-TYPE
    SYNTAX      SnmpAdminString
    MAX-ACCESS  read-only
    STATUS      current
    DESCRIPTION   "Aid string of entity."
    ::=  { containerVch1Entry 6 }

containerVch1Class OBJECT-TYPE
    SYNTAX      EntityClass
    MAX-ACCESS  read-only
    STATUS      current
    DESCRIPTION
        "Entity Class"
    ::=  { containerVch1Entry 7 }

containerVch1TableId OBJECT-TYPE
    SYNTAX      RowPointer
    MAX-ACCESS  read-only
    STATUS      current
    DESCRIPTION   "RowPointer to managment table"
    ::=  { containerVch1Entry 8 }

containerVch1ParentId OBJECT-TYPE
    SYNTAX      RowPointer
    MAX-ACCESS  read-only
    STATUS      current
    DESCRIPTION   "RowPointer to parent entity reported in corresponding entity table."
    ::=  { containerVch1Entry 9 }

containerOmTable OBJECT-TYPE
    SYNTAX      SEQUENCE OF ContainerOmEntry
    MAX-ACCESS  not-accessible
    STATUS      current
    DESCRIPTION   "containerOmTable"
    ::=  { containers 40 }

containerOmEntry OBJECT-TYPE
    SYNTAX      ContainerOmEntry
    MAX-ACCESS  not-accessible
    STATUS      current
    DESCRIPTION   "Entry of containerOmTable"
    INDEX       {
                  containerOmShelfNo,
                  containerOmSlotNo,
                  containerOmPortNo,
                  containerOmExtNo,
                  containerOmClassName
                }
    ::=  { containerOmTable 1 }

ContainerOmEntry ::=  SEQUENCE
  { containerOmShelfNo Unsigned32,
    containerOmSlotNo Unsigned32,
    containerOmPortNo Unsigned32,
    containerOmExtNo Unsigned32,
    containerOmClassName EntityClassName,
    containerOmAidString SnmpAdminString,
    containerOmClass EntityClass,
    containerOmTableId RowPointer,
    containerOmParentId RowPointer }

containerOmShelfNo OBJECT-TYPE
    SYNTAX      Unsigned32
    MAX-ACCESS  not-accessible
    STATUS      current
    DESCRIPTION   "Adress index."
    ::=  { containerOmEntry 1 }

containerOmSlotNo OBJECT-TYPE
    SYNTAX      Unsigned32
    MAX-ACCESS  not-accessible
    STATUS      current
    DESCRIPTION   "Adress index."
    ::=  { containerOmEntry 2 }

containerOmPortNo OBJECT-TYPE
    SYNTAX      Unsigned32
    MAX-ACCESS  not-accessible
    STATUS      current
    DESCRIPTION   "Adress index."
    ::=  { containerOmEntry 3 }

containerOmExtNo OBJECT-TYPE
    SYNTAX      Unsigned32
    MAX-ACCESS  not-accessible
    STATUS      current
    DESCRIPTION   "Adress index."
    ::=  { containerOmEntry 4 }

containerOmClassName OBJECT-TYPE
    SYNTAX      EntityClassName
    MAX-ACCESS  not-accessible
    STATUS      current
    DESCRIPTION
        "Entity Class Name"
    ::=  { containerOmEntry 5 }

containerOmAidString OBJECT-TYPE
    SYNTAX      SnmpAdminString
    MAX-ACCESS  read-only
    STATUS      current
    DESCRIPTION   "Aid string of entity."
    ::=  { containerOmEntry 6 }

containerOmClass OBJECT-TYPE
    SYNTAX      EntityClass
    MAX-ACCESS  read-only
    STATUS      current
    DESCRIPTION
        "Entity Class"
    ::=  { containerOmEntry 7 }

containerOmTableId OBJECT-TYPE
    SYNTAX      RowPointer
    MAX-ACCESS  read-only
    STATUS      current
    DESCRIPTION   "RowPointer to managment table"
    ::=  { containerOmEntry 8 }

containerOmParentId OBJECT-TYPE
    SYNTAX      RowPointer
    MAX-ACCESS  read-only
    STATUS      current
    DESCRIPTION   "RowPointer to parent entity reported in corresponding entity table."
    ::=  { containerOmEntry 9 }

containerVomTable OBJECT-TYPE
    SYNTAX      SEQUENCE OF ContainerVomEntry
    MAX-ACCESS  not-accessible
    STATUS      current
    DESCRIPTION   "containerVomTable"
    ::=  { containers 41 }

containerVomEntry OBJECT-TYPE
    SYNTAX      ContainerVomEntry
    MAX-ACCESS  not-accessible
    STATUS      current
    DESCRIPTION   "Entry of containerVomTable"
    INDEX       {
                  containerVomShelfNo,
                  containerVomSlotNo,
                  containerVomPortNo,
                  containerVomExtNo,
                  containerVomClassName
                }
    ::=  { containerVomTable 1 }

ContainerVomEntry ::=  SEQUENCE
  { containerVomShelfNo Unsigned32,
    containerVomSlotNo Unsigned32,
    containerVomPortNo Unsigned32,
    containerVomExtNo Unsigned32,
    containerVomClassName EntityClassName,
    containerVomAidString SnmpAdminString,
    containerVomClass EntityClass,
    containerVomTableId RowPointer,
    containerVomParentId RowPointer }

containerVomShelfNo OBJECT-TYPE
    SYNTAX      Unsigned32
    MAX-ACCESS  not-accessible
    STATUS      current
    DESCRIPTION   "Adress index."
    ::=  { containerVomEntry 1 }

containerVomSlotNo OBJECT-TYPE
    SYNTAX      Unsigned32
    MAX-ACCESS  not-accessible
    STATUS      current
    DESCRIPTION   "Adress index."
    ::=  { containerVomEntry 2 }

containerVomPortNo OBJECT-TYPE
    SYNTAX      Unsigned32
    MAX-ACCESS  not-accessible
    STATUS      current
    DESCRIPTION   "Adress index."
    ::=  { containerVomEntry 3 }

containerVomExtNo OBJECT-TYPE
    SYNTAX      Unsigned32
    MAX-ACCESS  not-accessible
    STATUS      current
    DESCRIPTION   "Adress index."
    ::=  { containerVomEntry 4 }

containerVomClassName OBJECT-TYPE
    SYNTAX      EntityClassName
    MAX-ACCESS  not-accessible
    STATUS      current
    DESCRIPTION
        "Entity Class Name"
    ::=  { containerVomEntry 5 }

containerVomAidString OBJECT-TYPE
    SYNTAX      SnmpAdminString
    MAX-ACCESS  read-only
    STATUS      current
    DESCRIPTION   "Aid string of entity."
    ::=  { containerVomEntry 6 }

containerVomClass OBJECT-TYPE
    SYNTAX      EntityClass
    MAX-ACCESS  read-only
    STATUS      current
    DESCRIPTION
        "Entity Class"
    ::=  { containerVomEntry 7 }

containerVomTableId OBJECT-TYPE
    SYNTAX      RowPointer
    MAX-ACCESS  read-only
    STATUS      current
    DESCRIPTION   "RowPointer to managment table"
    ::=  { containerVomEntry 8 }

containerVomParentId OBJECT-TYPE
    SYNTAX      RowPointer
    MAX-ACCESS  read-only
    STATUS      current
    DESCRIPTION   "RowPointer to parent entity reported in corresponding entity table."
    ::=  { containerVomEntry 9 }

containerShelfConnTable OBJECT-TYPE
    SYNTAX      SEQUENCE OF ContainerShelfConnEntry
    MAX-ACCESS  not-accessible
    STATUS      current
    DESCRIPTION   "containerShelfConnTable"
    ::=  { containers 50 }

containerShelfConnEntry OBJECT-TYPE
    SYNTAX      ContainerShelfConnEntry
    MAX-ACCESS  not-accessible
    STATUS      current
    DESCRIPTION   "Entry of containerShelfConnTable"
    INDEX       {
                  containerShelfConnShelfNo,
                  containerShelfConnSlotNo,
                  containerShelfConnPortNo,
                  containerShelfConnExtNo,
                  containerShelfConnClassName
                }
    ::=  { containerShelfConnTable 1 }

ContainerShelfConnEntry ::=  SEQUENCE
  { containerShelfConnShelfNo Unsigned32,
    containerShelfConnSlotNo Unsigned32,
    containerShelfConnPortNo Unsigned32,
    containerShelfConnExtNo Unsigned32,
    containerShelfConnClassName EntityClassName,
    containerShelfConnAidString SnmpAdminString,
    containerShelfConnClass EntityClass,
    containerShelfConnTableId RowPointer,
    containerShelfConnParentId RowPointer }

containerShelfConnShelfNo OBJECT-TYPE
    SYNTAX      Unsigned32
    MAX-ACCESS  not-accessible
    STATUS      current
    DESCRIPTION   "Adress index."
    ::=  { containerShelfConnEntry 1 }

containerShelfConnSlotNo OBJECT-TYPE
    SYNTAX      Unsigned32
    MAX-ACCESS  not-accessible
    STATUS      current
    DESCRIPTION   "Adress index."
    ::=  { containerShelfConnEntry 2 }

containerShelfConnPortNo OBJECT-TYPE
    SYNTAX      Unsigned32
    MAX-ACCESS  not-accessible
    STATUS      current
    DESCRIPTION   "Adress index."
    ::=  { containerShelfConnEntry 3 }

containerShelfConnExtNo OBJECT-TYPE
    SYNTAX      Unsigned32
    MAX-ACCESS  not-accessible
    STATUS      current
    DESCRIPTION   "Adress index."
    ::=  { containerShelfConnEntry 4 }

containerShelfConnClassName OBJECT-TYPE
    SYNTAX      EntityClassName
    MAX-ACCESS  not-accessible
    STATUS      current
    DESCRIPTION
        "Entity Class Name"
    ::=  { containerShelfConnEntry 5 }

containerShelfConnAidString OBJECT-TYPE
    SYNTAX      SnmpAdminString
    MAX-ACCESS  read-only
    STATUS      current
    DESCRIPTION   "Aid string of entity."
    ::=  { containerShelfConnEntry 6 }

containerShelfConnClass OBJECT-TYPE
    SYNTAX      EntityClass
    MAX-ACCESS  read-only
    STATUS      current
    DESCRIPTION   "EntityClass"
    ::=  { containerShelfConnEntry 7 }

containerShelfConnTableId OBJECT-TYPE
    SYNTAX      RowPointer
    MAX-ACCESS  read-only
    STATUS      current
    DESCRIPTION   "RowPointer to managment table"
    ::=  { containerShelfConnEntry 8 }

containerShelfConnParentId OBJECT-TYPE
    SYNTAX      RowPointer
    MAX-ACCESS  read-only
    STATUS      current
    DESCRIPTION   "RowPointer to parent entity reported in corresponding entity table."
    ::=  { containerShelfConnEntry 9 }

containerFfpTable OBJECT-TYPE
    SYNTAX      SEQUENCE OF ContainerFfpEntry
    MAX-ACCESS  not-accessible
    STATUS      current
    DESCRIPTION   "containerFfpTable"
    ::=  { containers 60 }

containerFfpEntry OBJECT-TYPE
    SYNTAX      ContainerFfpEntry
    MAX-ACCESS  not-accessible
    STATUS      current
    DESCRIPTION   "Entry of containerFfpTable"
    INDEX       {
                  containerFfpShelfNo,
                  containerFfpSlotNo,
                  containerFfpPortNo,
                  containerFfpExtNo,
                  containerFfpClassName
                }
    ::=  { containerFfpTable 1 }

ContainerFfpEntry ::=  SEQUENCE
  { containerFfpShelfNo Unsigned32,
    containerFfpSlotNo Unsigned32,
    containerFfpPortNo Unsigned32,
    containerFfpExtNo Unsigned32,
    containerFfpClassName EntityClassName,
    containerFfpAidString SnmpAdminString,
    containerFfpClass EntityClass,
    containerFfpTableId RowPointer,
    containerFfpParentId RowPointer }

containerFfpShelfNo OBJECT-TYPE
    SYNTAX      Unsigned32
    MAX-ACCESS  not-accessible
    STATUS      current
    DESCRIPTION   "Adress index."
    ::=  { containerFfpEntry 1 }

containerFfpSlotNo OBJECT-TYPE
    SYNTAX      Unsigned32
    MAX-ACCESS  not-accessible
    STATUS      current
    DESCRIPTION   "Adress index."
    ::=  { containerFfpEntry 2 }

containerFfpPortNo OBJECT-TYPE
    SYNTAX      Unsigned32
    MAX-ACCESS  not-accessible
    STATUS      current
    DESCRIPTION   "Adress index."
    ::=  { containerFfpEntry 3 }

containerFfpExtNo OBJECT-TYPE
    SYNTAX      Unsigned32
    MAX-ACCESS  not-accessible
    STATUS      current
    DESCRIPTION   "Adress index."
    ::=  { containerFfpEntry 4 }

containerFfpClassName OBJECT-TYPE
    SYNTAX      EntityClassName
    MAX-ACCESS  not-accessible
    STATUS      current
    DESCRIPTION
        "Entity Class Name"
    ::=  { containerFfpEntry 5 }

containerFfpAidString OBJECT-TYPE
    SYNTAX      SnmpAdminString
    MAX-ACCESS  read-only
    STATUS      current
    DESCRIPTION   "Aid string of entity."
    ::=  { containerFfpEntry 6 }

containerFfpClass OBJECT-TYPE
    SYNTAX      EntityClass
    MAX-ACCESS  read-only
    STATUS      current
    DESCRIPTION   "EntityClass"
    ::=  { containerFfpEntry 7 }

containerFfpTableId OBJECT-TYPE
    SYNTAX      RowPointer
    MAX-ACCESS  read-only
    STATUS      current
    DESCRIPTION   "RowPointer to managment table"
    ::=  { containerFfpEntry 8 }

containerFfpParentId OBJECT-TYPE
    SYNTAX      RowPointer
    MAX-ACCESS  read-only
    STATUS      current
    DESCRIPTION   "RowPointer to parent entity reported in corresponding entity table."
    ::=  { containerFfpEntry 9 }

containerEccTable OBJECT-TYPE
    SYNTAX      SEQUENCE OF ContainerEccEntry
    MAX-ACCESS  not-accessible
    STATUS      current
    DESCRIPTION   "containerEccTable"
    ::=  { containers 70 }

containerEccEntry OBJECT-TYPE
    SYNTAX      ContainerEccEntry
    MAX-ACCESS  not-accessible
    STATUS      current
    DESCRIPTION   "Entry of containerEccTable"
    INDEX       {
                  containerEccShelfNo,
                  containerEccSlotNo,
                  containerEccPortNo,
                  containerEccExtNo,
                  containerEccClassName
                }
    ::=  { containerEccTable 1 }

ContainerEccEntry ::=  SEQUENCE
  { containerEccShelfNo Unsigned32,
    containerEccSlotNo Unsigned32,
    containerEccPortNo Unsigned32,
    containerEccExtNo Unsigned32,
    containerEccClassName EntityClassName,
    containerEccAidString SnmpAdminString,
    containerEccClass EntityClass,
    containerEccTableId RowPointer,
    containerEccParentId RowPointer }

containerEccShelfNo OBJECT-TYPE
    SYNTAX      Unsigned32
    MAX-ACCESS  not-accessible
    STATUS      current
    DESCRIPTION   "Adress index."
    ::=  { containerEccEntry 1 }

containerEccSlotNo OBJECT-TYPE
    SYNTAX      Unsigned32
    MAX-ACCESS  not-accessible
    STATUS      current
    DESCRIPTION   "Adress index."
    ::=  { containerEccEntry 2 }

containerEccPortNo OBJECT-TYPE
    SYNTAX      Unsigned32
    MAX-ACCESS  not-accessible
    STATUS      current
    DESCRIPTION   "Adress index."
    ::=  { containerEccEntry 3 }

containerEccExtNo OBJECT-TYPE
    SYNTAX      Unsigned32
    MAX-ACCESS  not-accessible
    STATUS      current
    DESCRIPTION   "Adress index."
    ::=  { containerEccEntry 4 }

containerEccClassName OBJECT-TYPE
    SYNTAX      EntityClassName
    MAX-ACCESS  not-accessible
    STATUS      current
    DESCRIPTION
        "Entity Class Name"
    ::=  { containerEccEntry 5 }

containerEccAidString OBJECT-TYPE
    SYNTAX      SnmpAdminString
    MAX-ACCESS  read-only
    STATUS      current
    DESCRIPTION   "Aid string of entity."
    ::=  { containerEccEntry 6 }

containerEccClass OBJECT-TYPE
    SYNTAX      EntityClass
    MAX-ACCESS  read-only
    STATUS      current
    DESCRIPTION
        "Entity Class"
    ::=  { containerEccEntry 7 }

containerEccTableId OBJECT-TYPE
    SYNTAX      RowPointer
    MAX-ACCESS  read-only
    STATUS      current
    DESCRIPTION   "RowPointer to managment table"
    ::=  { containerEccEntry 8 }

containerEccParentId OBJECT-TYPE
    SYNTAX      RowPointer
    MAX-ACCESS  read-only
    STATUS      current
    DESCRIPTION   "RowPointer to parent entity reported in corresponding entity table."
    ::=  { containerEccEntry 9 }

containerLinkTable OBJECT-TYPE
    SYNTAX      SEQUENCE OF ContainerLinkEntry
    MAX-ACCESS  not-accessible
    STATUS      current
    DESCRIPTION   "containerLinkTable"
    ::=  { containers 71 }

containerLinkEntry OBJECT-TYPE
    SYNTAX      ContainerLinkEntry
    MAX-ACCESS  not-accessible
    STATUS      current
    DESCRIPTION   "Entry of containerLinkTable"
    INDEX       {
                  containerLinkShelfNo,
                  containerLinkSlotNo,
                  containerLinkPortNo,
                  containerLinkExtNo,
                  containerLinkClassName
                }
    ::=  { containerLinkTable 1 }

ContainerLinkEntry ::=  SEQUENCE
  { containerLinkShelfNo Unsigned32,
    containerLinkSlotNo Unsigned32,
    containerLinkPortNo Unsigned32,
    containerLinkExtNo Unsigned32,
    containerLinkClassName EntityClassName,
    containerLinkAidString SnmpAdminString,
    containerLinkClass EntityClass,
    containerLinkTableId RowPointer,
    containerLinkParentId RowPointer }

containerLinkShelfNo OBJECT-TYPE
    SYNTAX      Unsigned32
    MAX-ACCESS  not-accessible
    STATUS      current
    DESCRIPTION   "Adress index."
    ::=  { containerLinkEntry 1 }

containerLinkSlotNo OBJECT-TYPE
    SYNTAX      Unsigned32
    MAX-ACCESS  not-accessible
    STATUS      current
    DESCRIPTION   "Adress index."
    ::=  { containerLinkEntry 2 }

containerLinkPortNo OBJECT-TYPE
    SYNTAX      Unsigned32
    MAX-ACCESS  not-accessible
    STATUS      current
    DESCRIPTION   "Adress index."
    ::=  { containerLinkEntry 3 }

containerLinkExtNo OBJECT-TYPE
    SYNTAX      Unsigned32
    MAX-ACCESS  not-accessible
    STATUS      current
    DESCRIPTION   "Adress index."
    ::=  { containerLinkEntry 4 }

containerLinkClassName OBJECT-TYPE
    SYNTAX      EntityClassName
    MAX-ACCESS  not-accessible
    STATUS      current
    DESCRIPTION
        "Entity Class Name"
    ::=  { containerLinkEntry 5 }

containerLinkAidString OBJECT-TYPE
    SYNTAX      SnmpAdminString
    MAX-ACCESS  read-only
    STATUS      current
    DESCRIPTION   "Aid string of entity."
    ::=  { containerLinkEntry 6 }

containerLinkClass OBJECT-TYPE
    SYNTAX      EntityClass
    MAX-ACCESS  read-only
    STATUS      current
    DESCRIPTION
        "Entity Class"
    ::=  { containerLinkEntry 7 }

containerLinkTableId OBJECT-TYPE
    SYNTAX      RowPointer
    MAX-ACCESS  read-only
    STATUS      current
    DESCRIPTION   "RowPointer to managment table"
    ::=  { containerLinkEntry 8 }

containerLinkParentId OBJECT-TYPE
    SYNTAX      RowPointer
    MAX-ACCESS  read-only
    STATUS      current
    DESCRIPTION   "RowPointer to parent entity reported in corresponding entity table."
    ::=  { containerLinkEntry 9 }

containerScTable OBJECT-TYPE
    SYNTAX      SEQUENCE OF ContainerScEntry
    MAX-ACCESS  not-accessible
    STATUS      current
    DESCRIPTION   "containerScTable"
    ::=  { containers 72 }

containerScEntry OBJECT-TYPE
    SYNTAX      ContainerScEntry
    MAX-ACCESS  not-accessible
    STATUS      current
    DESCRIPTION   "Entry of containerScTable"
    INDEX       {
                  containerScShelfNo,
                  containerScSlotNo,
                  containerScPortNo,
                  containerScExtNo,
                  containerScClassName
                }
    ::=  { containerScTable 1 }

ContainerScEntry ::=  SEQUENCE
  { containerScShelfNo Unsigned32,
    containerScSlotNo Unsigned32,
    containerScPortNo Unsigned32,
    containerScExtNo Unsigned32,
    containerScClassName EntityClassName,
    containerScAidString SnmpAdminString,
    containerScClass EntityClass,
    containerScTableId RowPointer,
    containerScParentId RowPointer }

containerScShelfNo OBJECT-TYPE
    SYNTAX      Unsigned32
    MAX-ACCESS  not-accessible
    STATUS      current
    DESCRIPTION   "Adress index."
    ::=  { containerScEntry 1 }

containerScSlotNo OBJECT-TYPE
    SYNTAX      Unsigned32
    MAX-ACCESS  not-accessible
    STATUS      current
    DESCRIPTION   "Adress index."
    ::=  { containerScEntry 2 }

containerScPortNo OBJECT-TYPE
    SYNTAX      Unsigned32
    MAX-ACCESS  not-accessible
    STATUS      current
    DESCRIPTION   "Adress index."
    ::=  { containerScEntry 3 }

containerScExtNo OBJECT-TYPE
    SYNTAX      Unsigned32
    MAX-ACCESS  not-accessible
    STATUS      current
    DESCRIPTION   "Adress index."
    ::=  { containerScEntry 4 }

containerScClassName OBJECT-TYPE
    SYNTAX      EntityClassName
    MAX-ACCESS  not-accessible
    STATUS      current
    DESCRIPTION
        "Entity Class Name"
    ::=  { containerScEntry 5 }

containerScAidString OBJECT-TYPE
    SYNTAX      SnmpAdminString
    MAX-ACCESS  read-only
    STATUS      current
    DESCRIPTION   "Aid string of entity."
    ::=  { containerScEntry 6 }

containerScClass OBJECT-TYPE
    SYNTAX      EntityClass
    MAX-ACCESS  read-only
    STATUS      current
    DESCRIPTION
        "Entity Class"
    ::=  { containerScEntry 7 }

containerScTableId OBJECT-TYPE
    SYNTAX      RowPointer
    MAX-ACCESS  read-only
    STATUS      current
    DESCRIPTION   "RowPointer to managment table"
    ::=  { containerScEntry 8 }

containerScParentId OBJECT-TYPE
    SYNTAX      RowPointer
    MAX-ACCESS  read-only
    STATUS      current
    DESCRIPTION   "RowPointer to parent entity reported in corresponding entity table."
    ::=  { containerScEntry 9 }

containerLanTable OBJECT-TYPE
    SYNTAX      SEQUENCE OF ContainerLanEntry
    MAX-ACCESS  not-accessible
    STATUS      current
    DESCRIPTION   "containerLanTable"
    ::=  { containers 73 }

containerLanEntry OBJECT-TYPE
    SYNTAX      ContainerLanEntry
    MAX-ACCESS  not-accessible
    STATUS      current
    DESCRIPTION   "Entry of containerLanTable"
    INDEX       {
                  containerLanShelfNo,
                  containerLanSlotNo,
                  containerLanPortNo,
                  containerLanExtNo,
                  containerLanClassName
                }
    ::=  { containerLanTable 1 }

ContainerLanEntry ::=  SEQUENCE
  { containerLanShelfNo Unsigned32,
    containerLanSlotNo Unsigned32,
    containerLanPortNo Unsigned32,
    containerLanExtNo Unsigned32,
    containerLanClassName EntityClassName,
    containerLanAidString SnmpAdminString,
    containerLanClass EntityClass,
    containerLanTableId RowPointer,
    containerLanParentId RowPointer }

containerLanShelfNo OBJECT-TYPE
    SYNTAX      Unsigned32
    MAX-ACCESS  not-accessible
    STATUS      current
    DESCRIPTION   "Adress index."
    ::=  { containerLanEntry 1 }

containerLanSlotNo OBJECT-TYPE
    SYNTAX      Unsigned32
    MAX-ACCESS  not-accessible
    STATUS      current
    DESCRIPTION   "Adress index."
    ::=  { containerLanEntry 2 }

containerLanPortNo OBJECT-TYPE
    SYNTAX      Unsigned32
    MAX-ACCESS  not-accessible
    STATUS      current
    DESCRIPTION   "Adress index."
    ::=  { containerLanEntry 3 }

containerLanExtNo OBJECT-TYPE
    SYNTAX      Unsigned32
    MAX-ACCESS  not-accessible
    STATUS      current
    DESCRIPTION   "Adress index."
    ::=  { containerLanEntry 4 }

containerLanClassName OBJECT-TYPE
    SYNTAX      EntityClassName
    MAX-ACCESS  not-accessible
    STATUS      current
    DESCRIPTION
        "Entity Class Name"
    ::=  { containerLanEntry 5 }

containerLanAidString OBJECT-TYPE
    SYNTAX      SnmpAdminString
    MAX-ACCESS  read-only
    STATUS      current
    DESCRIPTION   "Aid string of entity."
    ::=  { containerLanEntry 6 }

containerLanClass OBJECT-TYPE
    SYNTAX      EntityClass
    MAX-ACCESS  read-only
    STATUS      current
    DESCRIPTION
        "Entity Class"
    ::=  { containerLanEntry 7 }

containerLanTableId OBJECT-TYPE
    SYNTAX      RowPointer
    MAX-ACCESS  read-only
    STATUS      current
    DESCRIPTION   "RowPointer to managment table"
    ::=  { containerLanEntry 8 }

containerLanParentId OBJECT-TYPE
    SYNTAX      RowPointer
    MAX-ACCESS  read-only
    STATUS      current
    DESCRIPTION   "RowPointer to parent entity reported in corresponding entity table."
    ::=  { containerLanEntry 9 }

containerEnvTable OBJECT-TYPE
    SYNTAX      SEQUENCE OF ContainerEnvEntry
    MAX-ACCESS  not-accessible
    STATUS      current
    DESCRIPTION   "containerEnvTable"
    ::=  { containers 80 }

containerEnvEntry OBJECT-TYPE
    SYNTAX      ContainerEnvEntry
    MAX-ACCESS  not-accessible
    STATUS      current
    DESCRIPTION   "Entry of containerEnvTable"
    INDEX       {
                  containerEnvShelfNo,
                  containerEnvSlotNo,
                  containerEnvPortNo,
                  containerEnvExtNo,
                  containerEnvClassName
                }
    ::=  { containerEnvTable 1 }

ContainerEnvEntry ::=  SEQUENCE
  { containerEnvShelfNo Unsigned32,
    containerEnvSlotNo Unsigned32,
    containerEnvPortNo Unsigned32,
    containerEnvExtNo Unsigned32,
    containerEnvClassName EntityClassName,
    containerEnvAidString SnmpAdminString,
    containerEnvClass EntityClass,
    containerEnvTableId RowPointer,
    containerEnvParentId RowPointer }

containerEnvShelfNo OBJECT-TYPE
    SYNTAX      Unsigned32
    MAX-ACCESS  not-accessible
    STATUS      current
    DESCRIPTION   "Adress index."
    ::=  { containerEnvEntry 1 }

containerEnvSlotNo OBJECT-TYPE
    SYNTAX      Unsigned32
    MAX-ACCESS  not-accessible
    STATUS      current
    DESCRIPTION   "Adress index."
    ::=  { containerEnvEntry 2 }

containerEnvPortNo OBJECT-TYPE
    SYNTAX      Unsigned32
    MAX-ACCESS  not-accessible
    STATUS      current
    DESCRIPTION   "Adress index."
    ::=  { containerEnvEntry 3 }

containerEnvExtNo OBJECT-TYPE
    SYNTAX      Unsigned32
    MAX-ACCESS  not-accessible
    STATUS      current
    DESCRIPTION   "Adress index."
    ::=  { containerEnvEntry 4 }

containerEnvClassName OBJECT-TYPE
    SYNTAX      EntityClassName
    MAX-ACCESS  not-accessible
    STATUS      current
    DESCRIPTION
        "Entity Class Name"
    ::=  { containerEnvEntry 5 }

containerEnvAidString OBJECT-TYPE
    SYNTAX      SnmpAdminString
    MAX-ACCESS  read-only
    STATUS      current
    DESCRIPTION   "Aid string of entity."
    ::=  { containerEnvEntry 6 }

containerEnvClass OBJECT-TYPE
    SYNTAX      EntityClass
    MAX-ACCESS  read-only
    STATUS      current
    DESCRIPTION   "EntityClass"
    ::=  { containerEnvEntry 7 }

containerEnvTableId OBJECT-TYPE
    SYNTAX      RowPointer
    MAX-ACCESS  read-only
    STATUS      current
    DESCRIPTION   "RowPointer to managment table"
    ::=  { containerEnvEntry 8 }

containerEnvParentId OBJECT-TYPE
    SYNTAX      RowPointer
    MAX-ACCESS  read-only
    STATUS      current
    DESCRIPTION   "RowPointer to parent entity reported in corresponding entity table."
    ::=  { containerEnvEntry 9 }

containerWchTable OBJECT-TYPE
    SYNTAX      SEQUENCE OF ContainerWchEntry
    MAX-ACCESS  not-accessible
    STATUS      current
    DESCRIPTION   "containerWchTable"
    ::=  { containers 90 }

containerWchEntry OBJECT-TYPE
    SYNTAX      ContainerWchEntry
    MAX-ACCESS  not-accessible
    STATUS      current
    DESCRIPTION   "Entry of containerWchTable"
    INDEX       {
                  containerWchIndexNo1,
                  containerWchIndexNo2,
                  containerWchIndexNo3,
                  containerWchIndexNo4,
                  containerWchClassName
                }
    ::=  { containerWchTable 1 }

ContainerWchEntry ::=  SEQUENCE
  { containerWchIndexNo1 Unsigned32,
    containerWchIndexNo2 Unsigned32,
    containerWchIndexNo3 Unsigned32,
    containerWchIndexNo4 Unsigned32,
    containerWchClassName EntityClassName,
    containerWchAidString SnmpAdminString,
    containerWchClass EntityClass,
    containerWchTableId RowPointer,
    containerWchParentId RowPointer }

containerWchIndexNo1 OBJECT-TYPE
    SYNTAX      Unsigned32
    MAX-ACCESS  not-accessible
    STATUS      current
    DESCRIPTION   "Adress index."
    ::=  { containerWchEntry 1 }

containerWchIndexNo2 OBJECT-TYPE
    SYNTAX      Unsigned32
    MAX-ACCESS  not-accessible
    STATUS      current
    DESCRIPTION   "Adress index."
    ::=  { containerWchEntry 2 }

containerWchIndexNo3 OBJECT-TYPE
    SYNTAX      Unsigned32
    MAX-ACCESS  not-accessible
    STATUS      current
    DESCRIPTION   "Adress index."
    ::=  { containerWchEntry 3 }

containerWchIndexNo4 OBJECT-TYPE
    SYNTAX      Unsigned32
    MAX-ACCESS  not-accessible
    STATUS      current
    DESCRIPTION   "Adress index."
    ::=  { containerWchEntry 4 }

containerWchClassName OBJECT-TYPE
    SYNTAX      EntityClassName
    MAX-ACCESS  not-accessible
    STATUS      current
    DESCRIPTION
        "Entity Class Name"
    ::=  { containerWchEntry 5 }

containerWchAidString OBJECT-TYPE
    SYNTAX      SnmpAdminString
    MAX-ACCESS  read-only
    STATUS      current
    DESCRIPTION   "Aid string of entity."
    ::=  { containerWchEntry 6 }

containerWchClass OBJECT-TYPE
    SYNTAX      EntityClass
    MAX-ACCESS  read-only
    STATUS      current
    DESCRIPTION
        "Entity Class"
    ::=  { containerWchEntry 7 }

containerWchTableId OBJECT-TYPE
    SYNTAX      RowPointer
    MAX-ACCESS  read-only
    STATUS      current
    DESCRIPTION   "RowPointer to managment table"
    ::=  { containerWchEntry 8 }

containerWchParentId OBJECT-TYPE
    SYNTAX      RowPointer
    MAX-ACCESS  read-only
    STATUS      current
    DESCRIPTION   "RowPointer to parent entity reported in corresponding entity table."
    ::=  { containerWchEntry 9 }

containerOlTable OBJECT-TYPE
    SYNTAX      SEQUENCE OF ContainerOlEntry
    MAX-ACCESS  not-accessible
    STATUS      current
    DESCRIPTION   "containerOlTable"
    ::=  { containers 91 }

containerOlEntry OBJECT-TYPE
    SYNTAX      ContainerOlEntry
    MAX-ACCESS  not-accessible
    STATUS      current
    DESCRIPTION   "Entry of containerOlTable"
    INDEX       {
                  containerOlIndexNo1,
                  containerOlIndexNo2,
                  containerOlIndexNo3,
                  containerOlIndexNo4,
                  containerOlClassName
                }
    ::=  { containerOlTable 1 }

ContainerOlEntry ::=  SEQUENCE
  { containerOlIndexNo1 Unsigned32,
    containerOlIndexNo2 Unsigned32,
    containerOlIndexNo3 Unsigned32,
    containerOlIndexNo4 Unsigned32,
    containerOlClassName EntityClassName,
    containerOlAidString SnmpAdminString,
    containerOlClass EntityClass,
    containerOlTableId RowPointer,
    containerOlParentId RowPointer }

containerOlIndexNo1 OBJECT-TYPE
    SYNTAX      Unsigned32
    MAX-ACCESS  not-accessible
    STATUS      current
    DESCRIPTION   "Adress index."
    ::=  { containerOlEntry 1 }

containerOlIndexNo2 OBJECT-TYPE
    SYNTAX      Unsigned32
    MAX-ACCESS  not-accessible
    STATUS      current
    DESCRIPTION   "Adress index."
    ::=  { containerOlEntry 2 }

containerOlIndexNo3 OBJECT-TYPE
    SYNTAX      Unsigned32
    MAX-ACCESS  not-accessible
    STATUS      current
    DESCRIPTION   "Adress index."
    ::=  { containerOlEntry 3 }

containerOlIndexNo4 OBJECT-TYPE
    SYNTAX      Unsigned32
    MAX-ACCESS  not-accessible
    STATUS      current
    DESCRIPTION   "Adress index."
    ::=  { containerOlEntry 4 }

containerOlClassName OBJECT-TYPE
    SYNTAX      EntityClassName
    MAX-ACCESS  not-accessible
    STATUS      current
    DESCRIPTION
        "Entity Class Name"
    ::=  { containerOlEntry 5 }

containerOlAidString OBJECT-TYPE
    SYNTAX      SnmpAdminString
    MAX-ACCESS  read-only
    STATUS      current
    DESCRIPTION   "Aid string of entity."
    ::=  { containerOlEntry 6 }

containerOlClass OBJECT-TYPE
    SYNTAX      EntityClass
    MAX-ACCESS  read-only
    STATUS      current
    DESCRIPTION
        "Entity Class"
    ::=  { containerOlEntry 7 }

containerOlTableId OBJECT-TYPE
    SYNTAX      RowPointer
    MAX-ACCESS  read-only
    STATUS      current
    DESCRIPTION   "RowPointer to managment table"
    ::=  { containerOlEntry 8 }

containerOlParentId OBJECT-TYPE
    SYNTAX      RowPointer
    MAX-ACCESS  read-only
    STATUS      current
    DESCRIPTION   "RowPointer to parent entity reported in corresponding entity table."
    ::=  { containerOlEntry 9 }

containerOwlgTable OBJECT-TYPE
    SYNTAX      SEQUENCE OF ContainerOwlgEntry
    MAX-ACCESS  not-accessible
    STATUS      current
    DESCRIPTION   "containerOwlgTable"
    ::=  { containers 92 }

containerOwlgEntry OBJECT-TYPE
    SYNTAX      ContainerOwlgEntry
    MAX-ACCESS  not-accessible
    STATUS      current
    DESCRIPTION   "Entry of containerOwlgTable"
    INDEX       {
                  containerOwlgIndexNo1,
                  containerOwlgIndexNo2,
                  containerOwlgIndexNo3,
                  containerOwlgIndexNo4,
                  containerOwlgClassName
                }
    ::=  { containerOwlgTable 1 }

ContainerOwlgEntry ::=  SEQUENCE
  { containerOwlgIndexNo1 Unsigned32,
    containerOwlgIndexNo2 Unsigned32,
    containerOwlgIndexNo3 Unsigned32,
    containerOwlgIndexNo4 Unsigned32,
    containerOwlgClassName EntityClassName,
    containerOwlgAidString SnmpAdminString,
    containerOwlgClass EntityClass,
    containerOwlgTableId RowPointer,
    containerOwlgParentId RowPointer }

containerOwlgIndexNo1 OBJECT-TYPE
    SYNTAX      Unsigned32
    MAX-ACCESS  not-accessible
    STATUS      current
    DESCRIPTION   "Adress index."
    ::=  { containerOwlgEntry 1 }

containerOwlgIndexNo2 OBJECT-TYPE
    SYNTAX      Unsigned32
    MAX-ACCESS  not-accessible
    STATUS      current
    DESCRIPTION   "Adress index."
    ::=  { containerOwlgEntry 2 }

containerOwlgIndexNo3 OBJECT-TYPE
    SYNTAX      Unsigned32
    MAX-ACCESS  not-accessible
    STATUS      current
    DESCRIPTION   "Adress index."
    ::=  { containerOwlgEntry 3 }

containerOwlgIndexNo4 OBJECT-TYPE
    SYNTAX      Unsigned32
    MAX-ACCESS  not-accessible
    STATUS      current
    DESCRIPTION   "Adress index."
    ::=  { containerOwlgEntry 4 }

containerOwlgClassName OBJECT-TYPE
    SYNTAX      EntityClassName
    MAX-ACCESS  not-accessible
    STATUS      current
    DESCRIPTION
        "Entity Class Name"
    ::=  { containerOwlgEntry 5 }

containerOwlgAidString OBJECT-TYPE
    SYNTAX      SnmpAdminString
    MAX-ACCESS  read-only
    STATUS      current
    DESCRIPTION   "Aid string of entity."
    ::=  { containerOwlgEntry 6 }

containerOwlgClass OBJECT-TYPE
    SYNTAX      EntityClass
    MAX-ACCESS  read-only
    STATUS      current
    DESCRIPTION
        "Entity Class"
    ::=  { containerOwlgEntry 7 }

containerOwlgTableId OBJECT-TYPE
    SYNTAX      RowPointer
    MAX-ACCESS  read-only
    STATUS      current
    DESCRIPTION   "RowPointer to managment table"
    ::=  { containerOwlgEntry 8 }

containerOwlgParentId OBJECT-TYPE
    SYNTAX      RowPointer
    MAX-ACCESS  read-only
    STATUS      current
    DESCRIPTION   "RowPointer to parent entity reported in corresponding entity table."
    ::=  { containerOwlgEntry 9 }

containerCrossDcnTable OBJECT-TYPE
    SYNTAX      SEQUENCE OF ContainerCrossDcnEntry
    MAX-ACCESS  not-accessible
    STATUS      current
    DESCRIPTION   "containerCrossDcnTable"
    ::=  { containers 93 }

containerCrossDcnEntry OBJECT-TYPE
    SYNTAX      ContainerCrossDcnEntry
    MAX-ACCESS  not-accessible
    STATUS      current
    DESCRIPTION   "Entry of containerCrossDcnTable"
    INDEX       {
                  containerCrossDcnShelfNo,
                  containerCrossDcnSlotNo,
                  containerCrossDcnPortNo,
                  containerCrossDcnExtNo,
                  containerCrossDcnClassName
                }
    ::=  { containerCrossDcnTable 1 }

ContainerCrossDcnEntry ::=  SEQUENCE
  { containerCrossDcnShelfNo Unsigned32,
    containerCrossDcnSlotNo Unsigned32,
    containerCrossDcnPortNo Unsigned32,
    containerCrossDcnExtNo Unsigned32,
    containerCrossDcnClassName EntityClassName,
    containerCrossDcnAidString SnmpAdminString,
    containerCrossDcnClass EntityClass,
    containerCrossDcnTableId RowPointer,
    containerCrossDcnParentId RowPointer }

containerCrossDcnShelfNo OBJECT-TYPE
    SYNTAX      Unsigned32
    MAX-ACCESS  not-accessible
    STATUS      current
    DESCRIPTION   "Adress index."
    ::=  { containerCrossDcnEntry 1 }

containerCrossDcnSlotNo OBJECT-TYPE
    SYNTAX      Unsigned32
    MAX-ACCESS  not-accessible
    STATUS      current
    DESCRIPTION   "Adress index."
    ::=  { containerCrossDcnEntry 2 }

containerCrossDcnPortNo OBJECT-TYPE
    SYNTAX      Unsigned32
    MAX-ACCESS  not-accessible
    STATUS      current
    DESCRIPTION   "Adress index."
    ::=  { containerCrossDcnEntry 3 }

containerCrossDcnExtNo OBJECT-TYPE
    SYNTAX      Unsigned32
    MAX-ACCESS  not-accessible
    STATUS      current
    DESCRIPTION   "Adress index."
    ::=  { containerCrossDcnEntry 4 }

containerCrossDcnClassName OBJECT-TYPE
    SYNTAX      EntityClassName
    MAX-ACCESS  not-accessible
    STATUS      current
    DESCRIPTION
        "Entity Class Name"
    ::=  { containerCrossDcnEntry 5 }

containerCrossDcnAidString OBJECT-TYPE
    SYNTAX      SnmpAdminString
    MAX-ACCESS  read-only
    STATUS      current
    DESCRIPTION   "Aid string of entity."
    ::=  { containerCrossDcnEntry 6 }

containerCrossDcnClass OBJECT-TYPE
    SYNTAX      EntityClass
    MAX-ACCESS  read-only
    STATUS      current
    DESCRIPTION
        "Entity Class"
    ::=  { containerCrossDcnEntry 7 }

containerCrossDcnTableId OBJECT-TYPE
    SYNTAX      RowPointer
    MAX-ACCESS  read-only
    STATUS      current
    DESCRIPTION   "RowPointer to managment table"
    ::=  { containerCrossDcnEntry 8 }

containerCrossDcnParentId OBJECT-TYPE
    SYNTAX      RowPointer
    MAX-ACCESS  read-only
    STATUS      current
    DESCRIPTION   "RowPointer to parent entity reported in corresponding entity table."
    ::=  { containerCrossDcnEntry 9 }

nextUnusedPc OBJECT-TYPE
    SYNTAX      SnmpAdminString
    MAX-ACCESS  read-only
    STATUS      current
    DESCRIPTION
        "First not assigned PC entity in the system"
    ::=  { containers 94 }

nextUnusedFc OBJECT-TYPE
    SYNTAX      SnmpAdminString
    MAX-ACCESS  read-only
    STATUS      current
    DESCRIPTION
        "First not assigned FC entity in the system"
    ::=  { containers 95 }

endOfContainers OBJECT-TYPE
    SYNTAX      Integer32
    MAX-ACCESS  read-only
    STATUS      current
    DESCRIPTION
        ""
    ::=  { containers 10000 }

entitySysTable OBJECT-TYPE
    SYNTAX      SEQUENCE OF EntitySysEntry
    MAX-ACCESS  not-accessible
    STATUS      current
    DESCRIPTION   "entitySysTable"
    ::=  { entities 1 }

entitySysEntry OBJECT-TYPE
    SYNTAX      EntitySysEntry
    MAX-ACCESS  not-accessible
    STATUS      current
    DESCRIPTION   "Entry of entitySysTable"
    INDEX       {
                  entitySysShelfNo,
                  entitySysSlotNo,
                  entitySysPortNo,
                  entitySysExtNo,
                  entitySysClassName
                }
    ::=  { entitySysTable 1 }

EntitySysEntry ::=  SEQUENCE
  { entitySysShelfNo Unsigned32,
    entitySysSlotNo Unsigned32,
    entitySysPortNo Unsigned32,
    entitySysExtNo Unsigned32,
    entitySysClassName EntityClassName,
    entitySysAidString SnmpAdminString,
    entitySysType FspR7EntityType,
    entitySysTableId RowPointer,
    entitySysParentId RowPointer,
    entitySysClass EntityClass,
    entitySysOneIndex Unsigned32,
    entitySysEquipmentState EquipmentState }

entitySysShelfNo OBJECT-TYPE
    SYNTAX      Unsigned32
    MAX-ACCESS  not-accessible
    STATUS      current
    DESCRIPTION   "Adress index."
    ::=  { entitySysEntry 1 }

entitySysSlotNo OBJECT-TYPE
    SYNTAX      Unsigned32
    MAX-ACCESS  not-accessible
    STATUS      current
    DESCRIPTION   "Adress index."
    ::=  { entitySysEntry 2 }

entitySysPortNo OBJECT-TYPE
    SYNTAX      Unsigned32
    MAX-ACCESS  not-accessible
    STATUS      current
    DESCRIPTION   "Adress index."
    ::=  { entitySysEntry 3 }

entitySysExtNo OBJECT-TYPE
    SYNTAX      Unsigned32
    MAX-ACCESS  not-accessible
    STATUS      current
    DESCRIPTION   "Adress index."
    ::=  { entitySysEntry 4 }

entitySysClassName OBJECT-TYPE
    SYNTAX      EntityClassName
    MAX-ACCESS  not-accessible
    STATUS      current
    DESCRIPTION
        "Entity Class Name"
    ::=  { entitySysEntry 5 }

entitySysAidString OBJECT-TYPE
    SYNTAX      SnmpAdminString
    MAX-ACCESS  read-only
    STATUS      current
    DESCRIPTION   "Aid string of entity."
    ::=  { entitySysEntry 6 }

entitySysType OBJECT-TYPE
    SYNTAX      FspR7EntityType
    MAX-ACCESS  read-only
    STATUS      current
    DESCRIPTION   "The type of entity."
    ::=  { entitySysEntry 7 }

entitySysTableId OBJECT-TYPE
    SYNTAX      RowPointer
    MAX-ACCESS  read-only
    STATUS      current
    DESCRIPTION   "RowPointer to managment table of entity."
    ::=  { entitySysEntry 8 }

entitySysParentId OBJECT-TYPE
    SYNTAX      RowPointer
    MAX-ACCESS  read-only
    STATUS      current
    DESCRIPTION   "RowPointer to parent entity reported in corresponding entity table."
    ::=  { entitySysEntry 9 }

entitySysClass OBJECT-TYPE
    SYNTAX      EntityClass
    MAX-ACCESS  read-only
    STATUS      current
    DESCRIPTION   "EntityClass"
    ::=  { entitySysEntry 10 }

entitySysOneIndex OBJECT-TYPE
    SYNTAX      Unsigned32
    MAX-ACCESS  read-only
    STATUS      current
    DESCRIPTION
        "One Index Aid representation"
    ::=  { entitySysEntry 11 }

entitySysEquipmentState OBJECT-TYPE
    SYNTAX      EquipmentState
    MAX-ACCESS  read-only
    STATUS      current
    DESCRIPTION   "See EquipmentState."
    ::=  { entitySysEntry 12 }

entityEqptTable OBJECT-TYPE
    SYNTAX      SEQUENCE OF EntityEqptEntry
    MAX-ACCESS  not-accessible
    STATUS      current
    DESCRIPTION   "entityEqptTable"
    ::=  { entities 2 }

entityEqptEntry OBJECT-TYPE
    SYNTAX      EntityEqptEntry
    MAX-ACCESS  not-accessible
    STATUS      current
    DESCRIPTION   "Entry of entityEqptTable"
    INDEX       {
                  entityEqptShelfNo,
                  entityEqptSlotNo,
                  entityEqptPortNo,
                  entityEqptExtNo,
                  entityEqptClassName
                }
    ::=  { entityEqptTable 1 }

EntityEqptEntry ::=  SEQUENCE
  { entityEqptShelfNo Unsigned32,
    entityEqptSlotNo Unsigned32,
    entityEqptPortNo Unsigned32,
    entityEqptExtNo Unsigned32,
    entityEqptClassName EntityClassName,
    entityEqptAidString SnmpAdminString,
    entityEqptType FspR7EntityType,
    entityEqptTableId RowPointer,
    entityEqptParentId RowPointer,
    entityEqptClass EntityClass,
    entityEqptOneIndex Unsigned32,
    entityEqptEquipmentState EquipmentState,
    entityEqptMtosiParentId RowPointer }

entityEqptShelfNo OBJECT-TYPE
    SYNTAX      Unsigned32
    MAX-ACCESS  not-accessible
    STATUS      current
    DESCRIPTION   "Adress index."
    ::=  { entityEqptEntry 1 }

entityEqptSlotNo OBJECT-TYPE
    SYNTAX      Unsigned32
    MAX-ACCESS  not-accessible
    STATUS      current
    DESCRIPTION   "Adress index."
    ::=  { entityEqptEntry 2 }

entityEqptPortNo OBJECT-TYPE
    SYNTAX      Unsigned32
    MAX-ACCESS  not-accessible
    STATUS      current
    DESCRIPTION   "Adress index."
    ::=  { entityEqptEntry 3 }

entityEqptExtNo OBJECT-TYPE
    SYNTAX      Unsigned32
    MAX-ACCESS  not-accessible
    STATUS      current
    DESCRIPTION   "Adress index."
    ::=  { entityEqptEntry 4 }

entityEqptClassName OBJECT-TYPE
    SYNTAX      EntityClassName
    MAX-ACCESS  not-accessible
    STATUS      current
    DESCRIPTION   "Entity Class Name."
    ::=  { entityEqptEntry 5 }

entityEqptAidString OBJECT-TYPE
    SYNTAX      SnmpAdminString
    MAX-ACCESS  read-only
    STATUS      current
    DESCRIPTION   "Aid string of entity."
    ::=  { entityEqptEntry 6 }

entityEqptType OBJECT-TYPE
    SYNTAX      FspR7EntityType
    MAX-ACCESS  read-only
    STATUS      current
    DESCRIPTION   "The type of entity."
    ::=  { entityEqptEntry 7 }

entityEqptTableId OBJECT-TYPE
    SYNTAX      RowPointer
    MAX-ACCESS  read-only
    STATUS      current
    DESCRIPTION   "RowPointer to managment table of entity."
    ::=  { entityEqptEntry 8 }

entityEqptParentId OBJECT-TYPE
    SYNTAX      RowPointer
    MAX-ACCESS  read-only
    STATUS      current
    DESCRIPTION   "RowPointer to parent entity reported in corresponding entity table."
    ::=  { entityEqptEntry 9 }

entityEqptClass OBJECT-TYPE
    SYNTAX      EntityClass
    MAX-ACCESS  read-only
    STATUS      current
    DESCRIPTION   "EntityClass"
    ::=  { entityEqptEntry 10 }

entityEqptOneIndex OBJECT-TYPE
    SYNTAX      Unsigned32
    MAX-ACCESS  read-only
    STATUS      current
    DESCRIPTION
        "One Index Aid representation"
    ::=  { entityEqptEntry 11 }

entityEqptEquipmentState OBJECT-TYPE
    SYNTAX      EquipmentState
    MAX-ACCESS  read-only
    STATUS      current
    DESCRIPTION   "See EquipmentState."
    ::=  { entityEqptEntry 12 }

entityEqptMtosiParentId OBJECT-TYPE
    SYNTAX      RowPointer
    MAX-ACCESS  read-only
    STATUS      current
    DESCRIPTION
        ""
    ::=  { entityEqptEntry 13 }

entityDcnTable OBJECT-TYPE
    SYNTAX      SEQUENCE OF EntityDcnEntry
    MAX-ACCESS  not-accessible
    STATUS      current
    DESCRIPTION   "entityDcnTable"
    ::=  { entities 3 }

entityDcnEntry OBJECT-TYPE
    SYNTAX      EntityDcnEntry
    MAX-ACCESS  not-accessible
    STATUS      current
    DESCRIPTION   "Entry of entityDcnTable"
    INDEX       {
                  entityDcnShelfNo,
                  entityDcnSlotNo,
                  entityDcnPortNo,
                  entityDcnExtNo,
                  entityDcnClassName
                }
    ::=  { entityDcnTable 1 }

EntityDcnEntry ::=  SEQUENCE
  { entityDcnShelfNo Unsigned32,
    entityDcnSlotNo Unsigned32,
    entityDcnPortNo Unsigned32,
    entityDcnExtNo Unsigned32,
    entityDcnClassName EntityClassName,
    entityDcnAidString SnmpAdminString,
    entityDcnType FspR7EntityType,
    entityDcnTableId RowPointer,
    entityDcnParentId RowPointer,
    entityDcnClass EntityClass,
    entityDcnOneIndex Unsigned32 }

entityDcnShelfNo OBJECT-TYPE
    SYNTAX      Unsigned32
    MAX-ACCESS  not-accessible
    STATUS      current
    DESCRIPTION   "Adress index."
    ::=  { entityDcnEntry 1 }

entityDcnSlotNo OBJECT-TYPE
    SYNTAX      Unsigned32
    MAX-ACCESS  not-accessible
    STATUS      current
    DESCRIPTION   "Adress index."
    ::=  { entityDcnEntry 2 }

entityDcnPortNo OBJECT-TYPE
    SYNTAX      Unsigned32
    MAX-ACCESS  not-accessible
    STATUS      current
    DESCRIPTION   "Adress index."
    ::=  { entityDcnEntry 3 }

entityDcnExtNo OBJECT-TYPE
    SYNTAX      Unsigned32
    MAX-ACCESS  not-accessible
    STATUS      current
    DESCRIPTION   "Adress index."
    ::=  { entityDcnEntry 4 }

entityDcnClassName OBJECT-TYPE
    SYNTAX      EntityClassName
    MAX-ACCESS  not-accessible
    STATUS      current
    DESCRIPTION
        "Entity Class Name"
    ::=  { entityDcnEntry 5 }

entityDcnAidString OBJECT-TYPE
    SYNTAX      SnmpAdminString
    MAX-ACCESS  read-only
    STATUS      current
    DESCRIPTION   "Aid string of entity."
    ::=  { entityDcnEntry 6 }

entityDcnType OBJECT-TYPE
    SYNTAX      FspR7EntityType
    MAX-ACCESS  read-only
    STATUS      current
    DESCRIPTION   "The type of entity."
    ::=  { entityDcnEntry 7 }

entityDcnTableId OBJECT-TYPE
    SYNTAX      RowPointer
    MAX-ACCESS  read-only
    STATUS      current
    DESCRIPTION   "RowPointer to managment table of entity."
    ::=  { entityDcnEntry 8 }

entityDcnParentId OBJECT-TYPE
    SYNTAX      RowPointer
    MAX-ACCESS  read-only
    STATUS      current
    DESCRIPTION   "RowPointer to parent entity reported in corresponding entity table."
    ::=  { entityDcnEntry 9 }

entityDcnClass OBJECT-TYPE
    SYNTAX      EntityClass
    MAX-ACCESS  read-only
    STATUS      current
    DESCRIPTION   "EntityClass"
    ::=  { entityDcnEntry 10 }

entityDcnOneIndex OBJECT-TYPE
    SYNTAX      Unsigned32
    MAX-ACCESS  read-only
    STATUS      current
    DESCRIPTION
        "One Index Aid representation"
    ::=  { entityDcnEntry 11 }

entityOptLineTable OBJECT-TYPE
    SYNTAX      SEQUENCE OF EntityOptLineEntry
    MAX-ACCESS  not-accessible
    STATUS      current
    DESCRIPTION   "entityOptLineTable"
    ::=  { entities 4 }

entityOptLineEntry OBJECT-TYPE
    SYNTAX      EntityOptLineEntry
    MAX-ACCESS  not-accessible
    STATUS      current
    DESCRIPTION   "Entry of entityOptLineTable"
    INDEX       {
                  entityOptLineIndexNo1,
                  entityOptLineIndexNo2,
                  entityOptLineIndexNo3,
                  entityOptLineIndexNo4,
                  entityOptLineClassName
                }
    ::=  { entityOptLineTable 1 }

EntityOptLineEntry ::=  SEQUENCE
  { entityOptLineIndexNo1 Unsigned32,
    entityOptLineIndexNo2 Unsigned32,
    entityOptLineIndexNo3 Unsigned32,
    entityOptLineIndexNo4 Unsigned32,
    entityOptLineClassName EntityClassName,
    entityOptLineAidString SnmpAdminString,
    entityOptLineType FspR7EntityType,
    entityOptLineTableId RowPointer,
    entityOptLineParentId RowPointer,
    entityOptLineOneIndex Unsigned32,
    entityOptLineClass EntityClass }

entityOptLineIndexNo1 OBJECT-TYPE
    SYNTAX      Unsigned32
    MAX-ACCESS  not-accessible
    STATUS      current
    DESCRIPTION   "Adress index."
    ::=  { entityOptLineEntry 1 }

entityOptLineIndexNo2 OBJECT-TYPE
    SYNTAX      Unsigned32
    MAX-ACCESS  not-accessible
    STATUS      current
    DESCRIPTION   "Adress index."
    ::=  { entityOptLineEntry 2 }

entityOptLineIndexNo3 OBJECT-TYPE
    SYNTAX      Unsigned32
    MAX-ACCESS  not-accessible
    STATUS      current
    DESCRIPTION   "Adress index."
    ::=  { entityOptLineEntry 3 }

entityOptLineIndexNo4 OBJECT-TYPE
    SYNTAX      Unsigned32
    MAX-ACCESS  not-accessible
    STATUS      current
    DESCRIPTION   "Adress index."
    ::=  { entityOptLineEntry 4 }

entityOptLineClassName OBJECT-TYPE
    SYNTAX      EntityClassName
    MAX-ACCESS  not-accessible
    STATUS      current
    DESCRIPTION
        "Entity Class Name"
    ::=  { entityOptLineEntry 5 }

entityOptLineAidString OBJECT-TYPE
    SYNTAX      SnmpAdminString
    MAX-ACCESS  read-only
    STATUS      current
    DESCRIPTION   "Aid string of entity."
    ::=  { entityOptLineEntry 6 }

entityOptLineType OBJECT-TYPE
    SYNTAX      FspR7EntityType
    MAX-ACCESS  read-only
    STATUS      current
    DESCRIPTION   "The type of entity."
    ::=  { entityOptLineEntry 7 }

entityOptLineTableId OBJECT-TYPE
    SYNTAX      RowPointer
    MAX-ACCESS  read-only
    STATUS      current
    DESCRIPTION   "RowPointer to managment table of entity."
    ::=  { entityOptLineEntry 8 }

entityOptLineParentId OBJECT-TYPE
    SYNTAX      RowPointer
    MAX-ACCESS  read-only
    STATUS      current
    DESCRIPTION   "RowPointer to parent entity reported in corresponding entity table."
    ::=  { entityOptLineEntry 9 }

entityOptLineOneIndex OBJECT-TYPE
    SYNTAX      Unsigned32
    MAX-ACCESS  read-only
    STATUS      current
    DESCRIPTION
        "One Index Aid representation"
    ::=  { entityOptLineEntry 10 }

entityOptLineClass OBJECT-TYPE
    SYNTAX      EntityClass
    MAX-ACCESS  read-only
    STATUS      current
    DESCRIPTION   "EntityClass"
    ::=  { entityOptLineEntry 11 }

entityEnvTable OBJECT-TYPE
    SYNTAX      SEQUENCE OF EntityEnvEntry
    MAX-ACCESS  not-accessible
    STATUS      current
    DESCRIPTION   "entityEnvTable"
    ::=  { entities 5 }

entityEnvEntry OBJECT-TYPE
    SYNTAX      EntityEnvEntry
    MAX-ACCESS  not-accessible
    STATUS      current
    DESCRIPTION   "Entry of entityEnvTable"
    INDEX       {
                  entityEnvShelfNo,
                  entityEnvSlotNo,
                  entityEnvPortNo,
                  entityEnvExtNo,
                  entityEnvClassName
                }
    ::=  { entityEnvTable 1 }

EntityEnvEntry ::=  SEQUENCE
  { entityEnvShelfNo Unsigned32,
    entityEnvSlotNo Unsigned32,
    entityEnvPortNo Unsigned32,
    entityEnvExtNo Unsigned32,
    entityEnvClassName EntityClassName,
    entityEnvAidString SnmpAdminString,
    entityEnvType FspR7EntityType,
    entityEnvTableId RowPointer,
    entityEnvParentId RowPointer,
    entityEnvClass EntityClass,
    entityEnvOneIndex Unsigned32 }

entityEnvShelfNo OBJECT-TYPE
    SYNTAX      Unsigned32
    MAX-ACCESS  not-accessible
    STATUS      current
    DESCRIPTION   "Adress index."
    ::=  { entityEnvEntry 1 }

entityEnvSlotNo OBJECT-TYPE
    SYNTAX      Unsigned32
    MAX-ACCESS  not-accessible
    STATUS      current
    DESCRIPTION   "Adress index."
    ::=  { entityEnvEntry 2 }

entityEnvPortNo OBJECT-TYPE
    SYNTAX      Unsigned32
    MAX-ACCESS  not-accessible
    STATUS      current
    DESCRIPTION   "Adress index."
    ::=  { entityEnvEntry 3 }

entityEnvExtNo OBJECT-TYPE
    SYNTAX      Unsigned32
    MAX-ACCESS  not-accessible
    STATUS      current
    DESCRIPTION   "Adress index."
    ::=  { entityEnvEntry 4 }

entityEnvClassName OBJECT-TYPE
    SYNTAX      EntityClassName
    MAX-ACCESS  not-accessible
    STATUS      current
    DESCRIPTION
        "Entity Class Name"
    ::=  { entityEnvEntry 5 }

entityEnvAidString OBJECT-TYPE
    SYNTAX      SnmpAdminString
    MAX-ACCESS  read-only
    STATUS      current
    DESCRIPTION   "Aid string of entity."
    ::=  { entityEnvEntry 6 }

entityEnvType OBJECT-TYPE
    SYNTAX      FspR7EntityType
    MAX-ACCESS  read-only
    STATUS      current
    DESCRIPTION   "The type of entity."
    ::=  { entityEnvEntry 7 }

entityEnvTableId OBJECT-TYPE
    SYNTAX      RowPointer
    MAX-ACCESS  read-only
    STATUS      current
    DESCRIPTION   "RowPointer to managment table of entity."
    ::=  { entityEnvEntry 8 }

entityEnvParentId OBJECT-TYPE
    SYNTAX      RowPointer
    MAX-ACCESS  read-only
    STATUS      current
    DESCRIPTION   "RowPointer to parent entity reported in corresponding entity table."
    ::=  { entityEnvEntry 9 }

entityEnvClass OBJECT-TYPE
    SYNTAX      EntityClass
    MAX-ACCESS  read-only
    STATUS      current
    DESCRIPTION   "EntityClass"
    ::=  { entityEnvEntry 10 }

entityEnvOneIndex OBJECT-TYPE
    SYNTAX      Unsigned32
    MAX-ACCESS  read-only
    STATUS      current
    DESCRIPTION
        "One Index Aid representation"
    ::=  { entityEnvEntry 11 }

entityFacilityTable OBJECT-TYPE
    SYNTAX      SEQUENCE OF EntityFacilityEntry
    MAX-ACCESS  not-accessible
    STATUS      current
    DESCRIPTION   "entityFacilityTable"
    ::=  { entities 7 }

entityFacilityEntry OBJECT-TYPE
    SYNTAX      EntityFacilityEntry
    MAX-ACCESS  not-accessible
    STATUS      current
    DESCRIPTION   "Entry of entityFacilityTable"
    INDEX       {
                  entityFacilityShelfNo,
                  entityFacilitySlotNo,
                  entityFacilityPortNo,
                  entityFacilityExtNo,
                  entityFacilityClassName
                }
    ::=  { entityFacilityTable 1 }

EntityFacilityEntry ::=  SEQUENCE
  { entityFacilityShelfNo Unsigned32,
    entityFacilitySlotNo Unsigned32,
    entityFacilityPortNo Unsigned32,
    entityFacilityExtNo Unsigned32,
    entityFacilityClassName EntityClassName,
    entityFacilityAidString SnmpAdminString,
    entityFacilityType FspR7EntityType,
    entityFacilityTableId RowPointer,
    entityFacilityParentId RowPointer,
    entityFacilityClass EntityClass,
    entityFacilityOneIndex Unsigned32 }

entityFacilityShelfNo OBJECT-TYPE
    SYNTAX      Unsigned32
    MAX-ACCESS  not-accessible
    STATUS      current
    DESCRIPTION   "Adress index."
    ::=  { entityFacilityEntry 1 }

entityFacilitySlotNo OBJECT-TYPE
    SYNTAX      Unsigned32
    MAX-ACCESS  not-accessible
    STATUS      current
    DESCRIPTION   "Adress index."
    ::=  { entityFacilityEntry 2 }

entityFacilityPortNo OBJECT-TYPE
    SYNTAX      Unsigned32
    MAX-ACCESS  not-accessible
    STATUS      current
    DESCRIPTION   "Adress index."
    ::=  { entityFacilityEntry 3 }

entityFacilityExtNo OBJECT-TYPE
    SYNTAX      Unsigned32
    MAX-ACCESS  not-accessible
    STATUS      current
    DESCRIPTION   "Adress index."
    ::=  { entityFacilityEntry 4 }

entityFacilityClassName OBJECT-TYPE
    SYNTAX      EntityClassName
    MAX-ACCESS  not-accessible
    STATUS      current
    DESCRIPTION
        "Entity Class Name"
    ::=  { entityFacilityEntry 5 }

entityFacilityAidString OBJECT-TYPE
    SYNTAX      SnmpAdminString
    MAX-ACCESS  read-only
    STATUS      current
    DESCRIPTION   "Aid string of entity."
    ::=  { entityFacilityEntry 6 }

entityFacilityType OBJECT-TYPE
    SYNTAX      FspR7EntityType
    MAX-ACCESS  read-only
    STATUS      current
    DESCRIPTION   "The type of entity."
    ::=  { entityFacilityEntry 7 }

entityFacilityTableId OBJECT-TYPE
    SYNTAX      RowPointer
    MAX-ACCESS  read-only
    STATUS      current
    DESCRIPTION   "RowPointer to managment table of entity."
    ::=  { entityFacilityEntry 8 }

entityFacilityParentId OBJECT-TYPE
    SYNTAX      RowPointer
    MAX-ACCESS  read-only
    STATUS      current
    DESCRIPTION   "RowPointer to parent entity reported in corresponding entity table."
    ::=  { entityFacilityEntry 9 }

entityFacilityClass OBJECT-TYPE
    SYNTAX      EntityClass
    MAX-ACCESS  read-only
    STATUS      current
    DESCRIPTION   "EntityClass"
    ::=  { entityFacilityEntry 10 }

entityFacilityOneIndex OBJECT-TYPE
    SYNTAX      Unsigned32
    MAX-ACCESS  read-only
    STATUS      current
    DESCRIPTION
        "One Index Aid representation"
    ::=  { entityFacilityEntry 11 }

entityCrossConnTable OBJECT-TYPE
    SYNTAX      SEQUENCE OF EntityCrossConnEntry
    MAX-ACCESS  not-accessible
    STATUS      current
    DESCRIPTION   "entityCrossConnTable"
    ::=  { entities 8 }

entityCrossConnEntry OBJECT-TYPE
    SYNTAX      EntityCrossConnEntry
    MAX-ACCESS  not-accessible
    STATUS      current
    DESCRIPTION   "Entry of entityCrossConnTable"
    INDEX       {
                  entityCrossConnFromShelfNo,
                  entityCrossConnFromSlotNo,
                  entityCrossConnFromPortNo,
                  entityCrossConnFromExtNo,
                  entityCrossConnFromClassName,
                  entityCrossConnToShelfNo,
                  entityCrossConnToSlotNo,
                  entityCrossConnToPortNo,
                  entityCrossConnToExtNo,
                  entityCrossConnToClassName,
                  entityCrossConnClassName
                }
    ::=  { entityCrossConnTable 1 }

EntityCrossConnEntry ::=  SEQUENCE
  { entityCrossConnFromShelfNo Unsigned32,
    entityCrossConnFromSlotNo Unsigned32,
    entityCrossConnFromPortNo Unsigned32,
    entityCrossConnFromExtNo Unsigned32,
    entityCrossConnFromClassName EntityClassName,
    entityCrossConnToShelfNo Unsigned32,
    entityCrossConnToSlotNo Unsigned32,
    entityCrossConnToPortNo Unsigned32,
    entityCrossConnToExtNo Unsigned32,
    entityCrossConnToClassName EntityClassName,
    entityCrossConnClassName EntityClassName,
    entityCrossConnAidString SnmpAdminString,
    entityCrossConnType FspR7EntityType,
    entityCrossConnTableId RowPointer,
    entityCrossConnParentId RowPointer,
    entityCrossConnFromId RowPointer,
    entityCrossConnToId RowPointer,
    entityCrossConnClass EntityClass }

entityCrossConnFromShelfNo OBJECT-TYPE
    SYNTAX      Unsigned32
    MAX-ACCESS  not-accessible
    STATUS      current
    DESCRIPTION   "Adress index."
    ::=  { entityCrossConnEntry 1 }

entityCrossConnFromSlotNo OBJECT-TYPE
    SYNTAX      Unsigned32
    MAX-ACCESS  not-accessible
    STATUS      current
    DESCRIPTION   "Adress index."
    ::=  { entityCrossConnEntry 2 }

entityCrossConnFromPortNo OBJECT-TYPE
    SYNTAX      Unsigned32
    MAX-ACCESS  not-accessible
    STATUS      current
    DESCRIPTION   "Adress index."
    ::=  { entityCrossConnEntry 3 }

entityCrossConnFromExtNo OBJECT-TYPE
    SYNTAX      Unsigned32
    MAX-ACCESS  not-accessible
    STATUS      current
    DESCRIPTION   "Adress index."
    ::=  { entityCrossConnEntry 4 }

entityCrossConnFromClassName OBJECT-TYPE
    SYNTAX      EntityClassName
    MAX-ACCESS  not-accessible
    STATUS      current
    DESCRIPTION
        "Entity Class Name"
    ::=  { entityCrossConnEntry 5 }

entityCrossConnToShelfNo OBJECT-TYPE
    SYNTAX      Unsigned32
    MAX-ACCESS  not-accessible
    STATUS      current
    DESCRIPTION   "Adress index."
    ::=  { entityCrossConnEntry 6 }

entityCrossConnToSlotNo OBJECT-TYPE
    SYNTAX      Unsigned32
    MAX-ACCESS  not-accessible
    STATUS      current
    DESCRIPTION   "Adress index."
    ::=  { entityCrossConnEntry 7 }

entityCrossConnToPortNo OBJECT-TYPE
    SYNTAX      Unsigned32
    MAX-ACCESS  not-accessible
    STATUS      current
    DESCRIPTION   "Adress index."
    ::=  { entityCrossConnEntry 8 }

entityCrossConnToExtNo OBJECT-TYPE
    SYNTAX      Unsigned32
    MAX-ACCESS  not-accessible
    STATUS      current
    DESCRIPTION   "Adress index."
    ::=  { entityCrossConnEntry 9 }

entityCrossConnToClassName OBJECT-TYPE
    SYNTAX      EntityClassName
    MAX-ACCESS  not-accessible
    STATUS      current
    DESCRIPTION
        "Entity Class Name"
    ::=  { entityCrossConnEntry 10 }

entityCrossConnClassName OBJECT-TYPE
    SYNTAX      EntityClassName
    MAX-ACCESS  not-accessible
    STATUS      current
    DESCRIPTION
        "Entity Class Name"
    ::=  { entityCrossConnEntry 11 }

entityCrossConnAidString OBJECT-TYPE
    SYNTAX      SnmpAdminString
    MAX-ACCESS  read-only
    STATUS      current
    DESCRIPTION   "Aid string of entity."
    ::=  { entityCrossConnEntry 12 }

entityCrossConnType OBJECT-TYPE
    SYNTAX      FspR7EntityType
    MAX-ACCESS  read-only
    STATUS      current
    DESCRIPTION   "The type of entity."
    ::=  { entityCrossConnEntry 13 }

entityCrossConnTableId OBJECT-TYPE
    SYNTAX      RowPointer
    MAX-ACCESS  read-only
    STATUS      current
    DESCRIPTION   "RowPointer to managment table of entity."
    ::=  { entityCrossConnEntry 14 }

entityCrossConnParentId OBJECT-TYPE
    SYNTAX      RowPointer
    MAX-ACCESS  read-only
    STATUS      current
    DESCRIPTION   "RowPointer to parent entity reported in corresponding entity table."
    ::=  { entityCrossConnEntry 15 }

entityCrossConnFromId OBJECT-TYPE
    SYNTAX      RowPointer
    MAX-ACCESS  read-only
    STATUS      current
    DESCRIPTION   "RowPointer to FROM point entity."
    ::=  { entityCrossConnEntry 16 }

entityCrossConnToId OBJECT-TYPE
    SYNTAX      RowPointer
    MAX-ACCESS  read-only
    STATUS      current
    DESCRIPTION   "RowPointer to TO point entity."
    ::=  { entityCrossConnEntry 17 }

entityCrossConnClass OBJECT-TYPE
    SYNTAX      EntityClass
    MAX-ACCESS  read-only
    STATUS      current
    DESCRIPTION   "EntityClass"
    ::=  { entityCrossConnEntry 18 }

entityTerminPointTable OBJECT-TYPE
    SYNTAX      SEQUENCE OF EntityTerminPointEntry
    MAX-ACCESS  not-accessible
    STATUS      current
    DESCRIPTION   "entityTerminPointTable"
    ::=  { entities 10 }

entityTerminPointEntry OBJECT-TYPE
    SYNTAX      EntityTerminPointEntry
    MAX-ACCESS  not-accessible
    STATUS      current
    DESCRIPTION   "Entry of entityTerminPointTable"
    INDEX       {
                  entityTerminPointIndexNo1,
                  entityTerminPointIndexNo2,
                  entityTerminPointIndexNo3,
                  entityTerminPointIndexNo4,
                  entityTerminPointClassName
                }
    ::=  { entityTerminPointTable 1 }

EntityTerminPointEntry ::=  SEQUENCE
  { entityTerminPointIndexNo1 Unsigned32,
    entityTerminPointIndexNo2 Unsigned32,
    entityTerminPointIndexNo3 Unsigned32,
    entityTerminPointIndexNo4 Unsigned32,
    entityTerminPointClassName EntityClassName,
    entityTerminPointAidString SnmpAdminString,
    entityTerminPointType FspR7EntityType,
    entityTerminPointAssignState AssignmentState,
    entityTerminPointTableId RowPointer,
    entityTerminPointParentId RowPointer,
    entityTerminPointOneIndex Unsigned32,
    entityTerminPointReferencedTo RowPointer,
    entityTerminPointClass EntityClass,
    entityTerminPointPortClass EntityClass }

entityTerminPointIndexNo1 OBJECT-TYPE
    SYNTAX      Unsigned32
    MAX-ACCESS  not-accessible
    STATUS      current
    DESCRIPTION   "Adress index."
    ::=  { entityTerminPointEntry 1 }

entityTerminPointIndexNo2 OBJECT-TYPE
    SYNTAX      Unsigned32
    MAX-ACCESS  not-accessible
    STATUS      current
    DESCRIPTION   "Adress index."
    ::=  { entityTerminPointEntry 2 }

entityTerminPointIndexNo3 OBJECT-TYPE
    SYNTAX      Unsigned32
    MAX-ACCESS  not-accessible
    STATUS      current
    DESCRIPTION   "Adress index."
    ::=  { entityTerminPointEntry 3 }

entityTerminPointIndexNo4 OBJECT-TYPE
    SYNTAX      Unsigned32
    MAX-ACCESS  not-accessible
    STATUS      current
    DESCRIPTION   "Adress index."
    ::=  { entityTerminPointEntry 4 }

entityTerminPointClassName OBJECT-TYPE
    SYNTAX      EntityClassName
    MAX-ACCESS  not-accessible
    STATUS      current
    DESCRIPTION
        "Entity Class Name"
    ::=  { entityTerminPointEntry 5 }

entityTerminPointAidString OBJECT-TYPE
    SYNTAX      SnmpAdminString
    MAX-ACCESS  read-only
    STATUS      current
    DESCRIPTION   "Aid string of entity."
    ::=  { entityTerminPointEntry 6 }

entityTerminPointType OBJECT-TYPE
    SYNTAX      FspR7EntityType
    MAX-ACCESS  read-only
    STATUS      current
    DESCRIPTION   "The type of entity."
    ::=  { entityTerminPointEntry 7 }

entityTerminPointAssignState OBJECT-TYPE
    SYNTAX      AssignmentState
    MAX-ACCESS  read-only
    STATUS      current
    DESCRIPTION   "Assignment state of entity."
    ::=  { entityTerminPointEntry 8 }

entityTerminPointTableId OBJECT-TYPE
    SYNTAX      RowPointer
    MAX-ACCESS  read-only
    STATUS      current
    DESCRIPTION   "RowPointer to managment table of entity."
    ::=  { entityTerminPointEntry 9 }

entityTerminPointParentId OBJECT-TYPE
    SYNTAX      RowPointer
    MAX-ACCESS  read-only
    STATUS      current
    DESCRIPTION   "RowPointer to parent entity reported in corresponding entity table."
    ::=  { entityTerminPointEntry 10 }

entityTerminPointOneIndex OBJECT-TYPE
    SYNTAX      Unsigned32
    MAX-ACCESS  read-only
    STATUS      current
    DESCRIPTION
        "One Index Aid representation"
    ::=  { entityTerminPointEntry 11 }

entityTerminPointReferencedTo OBJECT-TYPE
    SYNTAX      RowPointer
    MAX-ACCESS  read-only
    STATUS      current
    DESCRIPTION   "RowPointer to refer object."
    ::=  { entityTerminPointEntry 12 }

entityTerminPointClass OBJECT-TYPE
    SYNTAX      EntityClass
    MAX-ACCESS  read-only
    STATUS      current
    DESCRIPTION   "EntityClass"
    ::=  { entityTerminPointEntry 13 }

entityTerminPointPortClass OBJECT-TYPE
    SYNTAX      EntityClass
    MAX-ACCESS  read-only
    STATUS      current
    DESCRIPTION
        "EntityClass of the corresponding Port."
    ::=  { entityTerminPointEntry 14 }

entityConnectionTable OBJECT-TYPE
    SYNTAX      SEQUENCE OF EntityConnectionEntry
    MAX-ACCESS  not-accessible
    STATUS      current
    DESCRIPTION   "entityConnectionTable"
    ::=  { entities 11 }

entityConnectionEntry OBJECT-TYPE
    SYNTAX      EntityConnectionEntry
    MAX-ACCESS  not-accessible
    STATUS      current
    DESCRIPTION   "Entry of entityConnectionTable"
    INDEX       {
                  entityTerminPointIndexNo1,
                  entityTerminPointIndexNo2,
                  entityTerminPointIndexNo3,
                  entityTerminPointIndexNo4,
                  entityTerminPointClassName,
                  entityTerminPointIndexNo1,
                  entityTerminPointIndexNo2,
                  entityTerminPointIndexNo3,
                  entityTerminPointIndexNo4,
                  entityTerminPointClassName,
                  entityConnectionClassName
                }
    ::=  { entityConnectionTable 1 }

EntityConnectionEntry ::=  SEQUENCE
  { entityConnectionClassName EntityClassName,
    entityConnectionAidString SnmpAdminString,
    entityConnectionType FspR7EntityType,
    entityConnectionTableId RowPointer,
    entityConnectionParentId RowPointer,
    entityConnectionFromId RowPointer,
    entityConnectionToId RowPointer,
    entityConnectionClass EntityClass }

entityConnectionClassName OBJECT-TYPE
    SYNTAX      EntityClassName
    MAX-ACCESS  not-accessible
    STATUS      current
    DESCRIPTION
        "Entity Class Name"
    ::=  { entityConnectionEntry 1 }

entityConnectionAidString OBJECT-TYPE
    SYNTAX      SnmpAdminString
    MAX-ACCESS  read-only
    STATUS      current
    DESCRIPTION   "Aid string of entity."
    ::=  { entityConnectionEntry 2 }

entityConnectionType OBJECT-TYPE
    SYNTAX      FspR7EntityType
    MAX-ACCESS  read-only
    STATUS      current
    DESCRIPTION   "The type of entity."
    ::=  { entityConnectionEntry 3 }

entityConnectionTableId OBJECT-TYPE
    SYNTAX      RowPointer
    MAX-ACCESS  read-only
    STATUS      current
    DESCRIPTION   "RowPointer to managment table of entity."
    ::=  { entityConnectionEntry 4 }

entityConnectionParentId OBJECT-TYPE
    SYNTAX      RowPointer
    MAX-ACCESS  read-only
    STATUS      current
    DESCRIPTION   "RowPointer to parent entity reported in corresponding entity table."
    ::=  { entityConnectionEntry 5 }

entityConnectionFromId OBJECT-TYPE
    SYNTAX      RowPointer
    MAX-ACCESS  read-only
    STATUS      current
    DESCRIPTION   "RowPointer to FROM point entity."
    ::=  { entityConnectionEntry 6 }

entityConnectionToId OBJECT-TYPE
    SYNTAX      RowPointer
    MAX-ACCESS  read-only
    STATUS      current
    DESCRIPTION   "RowPointer to TO point entity."
    ::=  { entityConnectionEntry 7 }

entityConnectionClass OBJECT-TYPE
    SYNTAX      EntityClass
    MAX-ACCESS  read-only
    STATUS      current
    DESCRIPTION   "EntityClass"
    ::=  { entityConnectionEntry 8 }

entityExternalPortTable OBJECT-TYPE
    SYNTAX      SEQUENCE OF EntityExternalPortEntry
    MAX-ACCESS  not-accessible
    STATUS      current
    DESCRIPTION   "entityExternalPortTable"
    ::=  { entities 12 }

entityExternalPortEntry OBJECT-TYPE
    SYNTAX      EntityExternalPortEntry
    MAX-ACCESS  not-accessible
    STATUS      current
    DESCRIPTION   "Entry of entityExternalPortTable"
    INDEX       {
                  entityExternalPortShelfNo,
                  entityExternalPortSlotNo,
                  entityExternalPortPortNo,
                  entityExternalPortExtNo,
                  entityExternalPortClassName
                }
    ::=  { entityExternalPortTable 1 }

EntityExternalPortEntry ::=  SEQUENCE
  { entityExternalPortShelfNo Unsigned32,
    entityExternalPortSlotNo Unsigned32,
    entityExternalPortPortNo Unsigned32,
    entityExternalPortExtNo Unsigned32,
    entityExternalPortClassName EntityClassName,
    entityExternalPortAidString SnmpAdminString,
    entityExternalPortType FspR7EntityType,
    entityExternalPortTableId RowPointer,
    entityExternalPortParentId RowPointer,
    entityExternalPortClass EntityClass,
    entityExternalPortOneIndex Unsigned32 }

entityExternalPortShelfNo OBJECT-TYPE
    SYNTAX      Unsigned32
    MAX-ACCESS  not-accessible
    STATUS      current
    DESCRIPTION   "Adress index."
    ::=  { entityExternalPortEntry 1 }

entityExternalPortSlotNo OBJECT-TYPE
    SYNTAX      Unsigned32
    MAX-ACCESS  not-accessible
    STATUS      current
    DESCRIPTION   "Adress index."
    ::=  { entityExternalPortEntry 2 }

entityExternalPortPortNo OBJECT-TYPE
    SYNTAX      Unsigned32
    MAX-ACCESS  not-accessible
    STATUS      current
    DESCRIPTION   "Adress index."
    ::=  { entityExternalPortEntry 3 }

entityExternalPortExtNo OBJECT-TYPE
    SYNTAX      Unsigned32
    MAX-ACCESS  not-accessible
    STATUS      current
    DESCRIPTION   "Adress index."
    ::=  { entityExternalPortEntry 4 }

entityExternalPortClassName OBJECT-TYPE
    SYNTAX      EntityClassName
    MAX-ACCESS  not-accessible
    STATUS      current
    DESCRIPTION
        "Entity Class Name"
    ::=  { entityExternalPortEntry 5 }

entityExternalPortAidString OBJECT-TYPE
    SYNTAX      SnmpAdminString
    MAX-ACCESS  read-only
    STATUS      current
    DESCRIPTION   "Aid string of entity."
    ::=  { entityExternalPortEntry 6 }

entityExternalPortType OBJECT-TYPE
    SYNTAX      FspR7EntityType
    MAX-ACCESS  read-only
    STATUS      current
    DESCRIPTION   "The type of entity."
    ::=  { entityExternalPortEntry 7 }

entityExternalPortTableId OBJECT-TYPE
    SYNTAX      RowPointer
    MAX-ACCESS  read-only
    STATUS      current
    DESCRIPTION   "RowPointer to managment table of entity."
    ::=  { entityExternalPortEntry 8 }

entityExternalPortParentId OBJECT-TYPE
    SYNTAX      RowPointer
    MAX-ACCESS  read-only
    STATUS      current
    DESCRIPTION   "RowPointer to parent entity reported in corresponding entity table."
    ::=  { entityExternalPortEntry 9 }

entityExternalPortClass OBJECT-TYPE
    SYNTAX      EntityClass
    MAX-ACCESS  read-only
    STATUS      current
    DESCRIPTION   "EntityClass"
    ::=  { entityExternalPortEntry 10 }

entityExternalPortOneIndex OBJECT-TYPE
    SYNTAX      Unsigned32
    MAX-ACCESS  read-only
    STATUS      current
    DESCRIPTION
        "One Index Aid representation"
    ::=  { entityExternalPortEntry 11 }

entityCrsOptLineTable OBJECT-TYPE
    SYNTAX      SEQUENCE OF EntityCrsOptLineEntry
    MAX-ACCESS  not-accessible
    STATUS      current
    DESCRIPTION   "entityCrsOptLineTable"
    ::=  { entities 13 }

entityCrsOptLineEntry OBJECT-TYPE
    SYNTAX      EntityCrsOptLineEntry
    MAX-ACCESS  not-accessible
    STATUS      current
    DESCRIPTION   "Entry of entityCrsOptLineTable"
    INDEX       {
                  entityCrsOptLineFromIndexNo1,
                  entityCrsOptLineFromIndexNo2,
                  entityCrsOptLineFromIndexNo3,
                  entityCrsOptLineFromIndexNo4,
                  entityCrsOptLineFromClassName,
                  entityCrsOptLineToIndexNo1,
                  entityCrsOptLineToIndexNo2,
                  entityCrsOptLineToIndexNo3,
                  entityCrsOptLineToIndexNo4,
                  entityCrsOptLineToClassName,
                  entityCrsOptLineClassName
                }
    ::=  { entityCrsOptLineTable 1 }

EntityCrsOptLineEntry ::=  SEQUENCE
  { entityCrsOptLineFromIndexNo1 Unsigned32,
    entityCrsOptLineFromIndexNo2 Unsigned32,
    entityCrsOptLineFromIndexNo3 Unsigned32,
    entityCrsOptLineFromIndexNo4 Unsigned32,
    entityCrsOptLineFromClassName EntityClassName,
    entityCrsOptLineToIndexNo1 Unsigned32,
    entityCrsOptLineToIndexNo2 Unsigned32,
    entityCrsOptLineToIndexNo3 Unsigned32,
    entityCrsOptLineToIndexNo4 Unsigned32,
    entityCrsOptLineToClassName EntityClassName,
    entityCrsOptLineClassName EntityClassName,
    entityCrsOptLineAidString SnmpAdminString,
    entityCrsOptLineType FspR7EntityType,
    entityCrsOptLineTableId RowPointer,
    entityCrsOptLineParentId RowPointer,
    entityCrsOptLineFromId RowPointer,
    entityCrsOptLineToId RowPointer,
    entityCrsOptLineClass EntityClass }

entityCrsOptLineFromIndexNo1 OBJECT-TYPE
    SYNTAX      Unsigned32
    MAX-ACCESS  not-accessible
    STATUS      current
    DESCRIPTION   "Adress index."
    ::=  { entityCrsOptLineEntry 1 }

entityCrsOptLineFromIndexNo2 OBJECT-TYPE
    SYNTAX      Unsigned32
    MAX-ACCESS  not-accessible
    STATUS      current
    DESCRIPTION   "Adress index."
    ::=  { entityCrsOptLineEntry 2 }

entityCrsOptLineFromIndexNo3 OBJECT-TYPE
    SYNTAX      Unsigned32
    MAX-ACCESS  not-accessible
    STATUS      current
    DESCRIPTION   "Adress index."
    ::=  { entityCrsOptLineEntry 3 }

entityCrsOptLineFromIndexNo4 OBJECT-TYPE
    SYNTAX      Unsigned32
    MAX-ACCESS  not-accessible
    STATUS      current
    DESCRIPTION   "Adress index."
    ::=  { entityCrsOptLineEntry 4 }

entityCrsOptLineFromClassName OBJECT-TYPE
    SYNTAX      EntityClassName
    MAX-ACCESS  not-accessible
    STATUS      current
    DESCRIPTION
        "Entity Class Name"
    ::=  { entityCrsOptLineEntry 5 }

entityCrsOptLineToIndexNo1 OBJECT-TYPE
    SYNTAX      Unsigned32
    MAX-ACCESS  not-accessible
    STATUS      current
    DESCRIPTION   "Adress index."
    ::=  { entityCrsOptLineEntry 6 }

entityCrsOptLineToIndexNo2 OBJECT-TYPE
    SYNTAX      Unsigned32
    MAX-ACCESS  not-accessible
    STATUS      current
    DESCRIPTION   "Adress index."
    ::=  { entityCrsOptLineEntry 7 }

entityCrsOptLineToIndexNo3 OBJECT-TYPE
    SYNTAX      Unsigned32
    MAX-ACCESS  not-accessible
    STATUS      current
    DESCRIPTION   "Adress index."
    ::=  { entityCrsOptLineEntry 8 }

entityCrsOptLineToIndexNo4 OBJECT-TYPE
    SYNTAX      Unsigned32
    MAX-ACCESS  not-accessible
    STATUS      current
    DESCRIPTION   "Adress index."
    ::=  { entityCrsOptLineEntry 9 }

entityCrsOptLineToClassName OBJECT-TYPE
    SYNTAX      EntityClassName
    MAX-ACCESS  not-accessible
    STATUS      current
    DESCRIPTION
        "Entity Class Name"
    ::=  { entityCrsOptLineEntry 10 }

entityCrsOptLineClassName OBJECT-TYPE
    SYNTAX      EntityClassName
    MAX-ACCESS  not-accessible
    STATUS      current
    DESCRIPTION
        "Entity Class Name"
    ::=  { entityCrsOptLineEntry 11 }

entityCrsOptLineAidString OBJECT-TYPE
    SYNTAX      SnmpAdminString
    MAX-ACCESS  read-only
    STATUS      current
    DESCRIPTION   "Aid string of entity."
    ::=  { entityCrsOptLineEntry 12 }

entityCrsOptLineType OBJECT-TYPE
    SYNTAX      FspR7EntityType
    MAX-ACCESS  read-only
    STATUS      current
    DESCRIPTION   "The type of entity."
    ::=  { entityCrsOptLineEntry 13 }

entityCrsOptLineTableId OBJECT-TYPE
    SYNTAX      RowPointer
    MAX-ACCESS  read-only
    STATUS      current
    DESCRIPTION   "RowPointer to managment table of entity."
    ::=  { entityCrsOptLineEntry 14 }

entityCrsOptLineParentId OBJECT-TYPE
    SYNTAX      RowPointer
    MAX-ACCESS  read-only
    STATUS      current
    DESCRIPTION   "RowPointer to parent entity reported in corresponding entity table."
    ::=  { entityCrsOptLineEntry 15 }

entityCrsOptLineFromId OBJECT-TYPE
    SYNTAX      RowPointer
    MAX-ACCESS  read-only
    STATUS      current
    DESCRIPTION   "RowPointer to FROM point entity."
    ::=  { entityCrsOptLineEntry 16 }

entityCrsOptLineToId OBJECT-TYPE
    SYNTAX      RowPointer
    MAX-ACCESS  read-only
    STATUS      current
    DESCRIPTION   "RowPointer to TO point entity."
    ::=  { entityCrsOptLineEntry 17 }

entityCrsOptLineClass OBJECT-TYPE
    SYNTAX      EntityClass
    MAX-ACCESS  read-only
    STATUS      current
    DESCRIPTION   "EntityClass"
    ::=  { entityCrsOptLineEntry 18 }

entityContainerTable OBJECT-TYPE
    SYNTAX      SEQUENCE OF EntityContainerEntry
    MAX-ACCESS  not-accessible
    STATUS      current
    DESCRIPTION   "entityContainerTable"
    ::=  { entities 16 }

entityContainerEntry OBJECT-TYPE
    SYNTAX      EntityContainerEntry
    MAX-ACCESS  not-accessible
    STATUS      current
    DESCRIPTION   "Entry of entityContainerTable"
    INDEX       {
                  entityContainerShelfNo,
                  entityContainerSlotNo,
                  entityContainerPortNo,
                  entityContainerExtNo,
                  entityContainerClassName
                }
    ::=  { entityContainerTable 1 }

EntityContainerEntry ::=  SEQUENCE
  { entityContainerShelfNo Unsigned32,
    entityContainerSlotNo Unsigned32,
    entityContainerPortNo Unsigned32,
    entityContainerExtNo Unsigned32,
    entityContainerClassName EntityClassName,
    entityContainerAidString SnmpAdminString,
    entityContainerType FspR7EntityType,
    entityContainerTableId RowPointer,
    entityContainerParentId RowPointer,
    entityContainerClass EntityClass,
    entityContainerOneIndex Unsigned32 }

entityContainerShelfNo OBJECT-TYPE
    SYNTAX      Unsigned32
    MAX-ACCESS  not-accessible
    STATUS      current
    DESCRIPTION   "Adress index."
    ::=  { entityContainerEntry 1 }

entityContainerSlotNo OBJECT-TYPE
    SYNTAX      Unsigned32
    MAX-ACCESS  not-accessible
    STATUS      current
    DESCRIPTION   "Adress index."
    ::=  { entityContainerEntry 2 }

entityContainerPortNo OBJECT-TYPE
    SYNTAX      Unsigned32
    MAX-ACCESS  not-accessible
    STATUS      current
    DESCRIPTION   "Adress index."
    ::=  { entityContainerEntry 3 }

entityContainerExtNo OBJECT-TYPE
    SYNTAX      Unsigned32
    MAX-ACCESS  not-accessible
    STATUS      current
    DESCRIPTION   "Adress index."
    ::=  { entityContainerEntry 4 }

entityContainerClassName OBJECT-TYPE
    SYNTAX      EntityClassName
    MAX-ACCESS  not-accessible
    STATUS      current
    DESCRIPTION
        "Entity Class Name"
    ::=  { entityContainerEntry 5 }

entityContainerAidString OBJECT-TYPE
    SYNTAX      SnmpAdminString
    MAX-ACCESS  read-only
    STATUS      current
    DESCRIPTION   "Aid string of entity."
    ::=  { entityContainerEntry 6 }

entityContainerType OBJECT-TYPE
    SYNTAX      FspR7EntityType
    MAX-ACCESS  read-only
    STATUS      current
    DESCRIPTION   "The type of entity."
    ::=  { entityContainerEntry 7 }

entityContainerTableId OBJECT-TYPE
    SYNTAX      RowPointer
    MAX-ACCESS  read-only
    STATUS      current
    DESCRIPTION   "RowPointer to managment table of entity."
    ::=  { entityContainerEntry 8 }

entityContainerParentId OBJECT-TYPE
    SYNTAX      RowPointer
    MAX-ACCESS  read-only
    STATUS      current
    DESCRIPTION   "RowPointer to parent entity reported in corresponding entity table."
    ::=  { entityContainerEntry 9 }

entityContainerClass OBJECT-TYPE
    SYNTAX      EntityClass
    MAX-ACCESS  read-only
    STATUS      current
    DESCRIPTION   "EntityClass"
    ::=  { entityContainerEntry 10 }

entityContainerOneIndex OBJECT-TYPE
    SYNTAX      Unsigned32
    MAX-ACCESS  read-only
    STATUS      current
    DESCRIPTION
        "One Index Aid representation"
    ::=  { entityContainerEntry 11 }

entityOpticalMuxTable OBJECT-TYPE
    SYNTAX      SEQUENCE OF EntityOpticalMuxEntry
    MAX-ACCESS  not-accessible
    STATUS      current
    DESCRIPTION   "entityOpticalTable"
    ::=  { entities 17 }

entityOpticalMuxEntry OBJECT-TYPE
    SYNTAX      EntityOpticalMuxEntry
    MAX-ACCESS  not-accessible
    STATUS      current
    DESCRIPTION   "Entry of entityOpticalTable"
    INDEX       {
                  entityOpticalMuxShelfNo,
                  entityOpticalMuxSlotNo,
                  entityOpticalMuxPortNo,
                  entityOpticalMuxExtNo,
                  entityOpticalMuxClassName
                }
    ::=  { entityOpticalMuxTable 1 }

EntityOpticalMuxEntry ::=  SEQUENCE
  { entityOpticalMuxShelfNo Unsigned32,
    entityOpticalMuxSlotNo Unsigned32,
    entityOpticalMuxPortNo Unsigned32,
    entityOpticalMuxExtNo Unsigned32,
    entityOpticalMuxClassName EntityClassName,
    entityOpticalMuxAidString SnmpAdminString,
    entityOpticalMuxType FspR7EntityType,
    entityOpticalMuxTableId RowPointer,
    entityOpticalMuxParentId RowPointer,
    entityOpticalMuxClass EntityClass,
    entityOpticalMuxOneIndex Unsigned32 }

entityOpticalMuxShelfNo OBJECT-TYPE
    SYNTAX      Unsigned32
    MAX-ACCESS  not-accessible
    STATUS      current
    DESCRIPTION   "Adress index."
    ::=  { entityOpticalMuxEntry 1 }

entityOpticalMuxSlotNo OBJECT-TYPE
    SYNTAX      Unsigned32
    MAX-ACCESS  not-accessible
    STATUS      current
    DESCRIPTION   "Adress index."
    ::=  { entityOpticalMuxEntry 2 }

entityOpticalMuxPortNo OBJECT-TYPE
    SYNTAX      Unsigned32
    MAX-ACCESS  not-accessible
    STATUS      current
    DESCRIPTION   "Adress index."
    ::=  { entityOpticalMuxEntry 3 }

entityOpticalMuxExtNo OBJECT-TYPE
    SYNTAX      Unsigned32
    MAX-ACCESS  not-accessible
    STATUS      current
    DESCRIPTION   "Adress index."
    ::=  { entityOpticalMuxEntry 4 }

entityOpticalMuxClassName OBJECT-TYPE
    SYNTAX      EntityClassName
    MAX-ACCESS  not-accessible
    STATUS      current
    DESCRIPTION
        "Entity Class Name"
    ::=  { entityOpticalMuxEntry 5 }

entityOpticalMuxAidString OBJECT-TYPE
    SYNTAX      SnmpAdminString
    MAX-ACCESS  read-only
    STATUS      current
    DESCRIPTION   "Aid string of entity."
    ::=  { entityOpticalMuxEntry 6 }

entityOpticalMuxType OBJECT-TYPE
    SYNTAX      FspR7EntityType
    MAX-ACCESS  read-only
    STATUS      current
    DESCRIPTION   "The type of entity."
    ::=  { entityOpticalMuxEntry 7 }

entityOpticalMuxTableId OBJECT-TYPE
    SYNTAX      RowPointer
    MAX-ACCESS  read-only
    STATUS      current
    DESCRIPTION   "RowPointer to managment table of entity."
    ::=  { entityOpticalMuxEntry 8 }

entityOpticalMuxParentId OBJECT-TYPE
    SYNTAX      RowPointer
    MAX-ACCESS  read-only
    STATUS      current
    DESCRIPTION   "RowPointer to parent entity reported in corresponding entity table."
    ::=  { entityOpticalMuxEntry 9 }

entityOpticalMuxClass OBJECT-TYPE
    SYNTAX      EntityClass
    MAX-ACCESS  read-only
    STATUS      current
    DESCRIPTION   "EntityClass"
    ::=  { entityOpticalMuxEntry 10 }

entityOpticalMuxOneIndex OBJECT-TYPE
    SYNTAX      Unsigned32
    MAX-ACCESS  read-only
    STATUS      current
    DESCRIPTION
        "One Index Aid representation"
    ::=  { entityOpticalMuxEntry 11 }

entityShelfConnTable OBJECT-TYPE
    SYNTAX      SEQUENCE OF EntityShelfConnEntry
    MAX-ACCESS  not-accessible
    STATUS      current
    DESCRIPTION   "entityShelfConnTable"
    ::=  { entities 18 }

entityShelfConnEntry OBJECT-TYPE
    SYNTAX      EntityShelfConnEntry
    MAX-ACCESS  not-accessible
    STATUS      current
    DESCRIPTION   "Entry of entityShelfConnTable"
    INDEX       {
                  entityShelfConnShelfNo,
                  entityShelfConnSlotNo,
                  entityShelfConnPortNo,
                  entityShelfConnExtNo,
                  entityShelfConnClassName
                }
    ::=  { entityShelfConnTable 1 }

EntityShelfConnEntry ::=  SEQUENCE
  { entityShelfConnShelfNo Unsigned32,
    entityShelfConnSlotNo Unsigned32,
    entityShelfConnPortNo Unsigned32,
    entityShelfConnExtNo Unsigned32,
    entityShelfConnClassName EntityClassName,
    entityShelfConnAidString SnmpAdminString,
    entityShelfConnType FspR7EntityType,
    entityShelfConnTableId RowPointer,
    entityShelfConnParentId RowPointer,
    entityShelfConnClass EntityClass,
    entityShelfConnOneIndex Unsigned32 }

entityShelfConnShelfNo OBJECT-TYPE
    SYNTAX      Unsigned32
    MAX-ACCESS  not-accessible
    STATUS      current
    DESCRIPTION   "Adress index."
    ::=  { entityShelfConnEntry 1 }

entityShelfConnSlotNo OBJECT-TYPE
    SYNTAX      Unsigned32
    MAX-ACCESS  not-accessible
    STATUS      current
    DESCRIPTION   "Adress index."
    ::=  { entityShelfConnEntry 2 }

entityShelfConnPortNo OBJECT-TYPE
    SYNTAX      Unsigned32
    MAX-ACCESS  not-accessible
    STATUS      current
    DESCRIPTION   "Adress index."
    ::=  { entityShelfConnEntry 3 }

entityShelfConnExtNo OBJECT-TYPE
    SYNTAX      Unsigned32
    MAX-ACCESS  not-accessible
    STATUS      current
    DESCRIPTION   "Adress index."
    ::=  { entityShelfConnEntry 4 }

entityShelfConnClassName OBJECT-TYPE
    SYNTAX      EntityClassName
    MAX-ACCESS  not-accessible
    STATUS      current
    DESCRIPTION
        "Entity Class Name"
    ::=  { entityShelfConnEntry 5 }

entityShelfConnAidString OBJECT-TYPE
    SYNTAX      SnmpAdminString
    MAX-ACCESS  read-only
    STATUS      current
    DESCRIPTION   "Aid string of entity."
    ::=  { entityShelfConnEntry 6 }

entityShelfConnType OBJECT-TYPE
    SYNTAX      FspR7EntityType
    MAX-ACCESS  read-only
    STATUS      current
    DESCRIPTION   "The type of entity."
    ::=  { entityShelfConnEntry 7 }

entityShelfConnTableId OBJECT-TYPE
    SYNTAX      RowPointer
    MAX-ACCESS  read-only
    STATUS      current
    DESCRIPTION   "RowPointer to managment table of entity."
    ::=  { entityShelfConnEntry 8 }

entityShelfConnParentId OBJECT-TYPE
    SYNTAX      RowPointer
    MAX-ACCESS  read-only
    STATUS      current
    DESCRIPTION   "RowPointer to parent entity reported in corresponding entity table."
    ::=  { entityShelfConnEntry 9 }

entityShelfConnClass OBJECT-TYPE
    SYNTAX      EntityClass
    MAX-ACCESS  read-only
    STATUS      current
    DESCRIPTION   "EntityClass"
    ::=  { entityShelfConnEntry 10 }

entityShelfConnOneIndex OBJECT-TYPE
    SYNTAX      Unsigned32
    MAX-ACCESS  read-only
    STATUS      current
    DESCRIPTION
        "One Index Aid representation"
    ::=  { entityShelfConnEntry 11 }

entityFfpTable OBJECT-TYPE
    SYNTAX      SEQUENCE OF EntityFfpEntry
    MAX-ACCESS  not-accessible
    STATUS      current
    DESCRIPTION   "entityFfpTable - conatains entities used by Protection"
    ::=  { entities 19 }

entityFfpEntry OBJECT-TYPE
    SYNTAX      EntityFfpEntry
    MAX-ACCESS  not-accessible
    STATUS      current
    DESCRIPTION   "Entry of entityFfpTable"
    INDEX       {
                  entityFfpShelfNo,
                  entityFfpSlotNo,
                  entityFfpPortNo,
                  entityFfpExtNo,
                  entityFfpClassName
                }
    ::=  { entityFfpTable 1 }

EntityFfpEntry ::=  SEQUENCE
  { entityFfpShelfNo Unsigned32,
    entityFfpSlotNo Unsigned32,
    entityFfpPortNo Unsigned32,
    entityFfpExtNo Unsigned32,
    entityFfpClassName EntityClassName,
    entityFfpAidString SnmpAdminString,
    entityFfpType FspR7EntityType,
    entityFfpTableId RowPointer,
    entityFfpParentId RowPointer,
    entityFfpClass EntityClass,
    entityFfpOneIndex Unsigned32 }

entityFfpShelfNo OBJECT-TYPE
    SYNTAX      Unsigned32
    MAX-ACCESS  not-accessible
    STATUS      current
    DESCRIPTION   "Adress index."
    ::=  { entityFfpEntry 1 }

entityFfpSlotNo OBJECT-TYPE
    SYNTAX      Unsigned32
    MAX-ACCESS  not-accessible
    STATUS      current
    DESCRIPTION   "Adress index."
    ::=  { entityFfpEntry 2 }

entityFfpPortNo OBJECT-TYPE
    SYNTAX      Unsigned32
    MAX-ACCESS  not-accessible
    STATUS      current
    DESCRIPTION   "Adress index."
    ::=  { entityFfpEntry 3 }

entityFfpExtNo OBJECT-TYPE
    SYNTAX      Unsigned32
    MAX-ACCESS  not-accessible
    STATUS      current
    DESCRIPTION   "Adress index."
    ::=  { entityFfpEntry 4 }

entityFfpClassName OBJECT-TYPE
    SYNTAX      EntityClassName
    MAX-ACCESS  not-accessible
    STATUS      current
    DESCRIPTION
        "Entity Class Name"
    ::=  { entityFfpEntry 5 }

entityFfpAidString OBJECT-TYPE
    SYNTAX      SnmpAdminString
    MAX-ACCESS  read-only
    STATUS      current
    DESCRIPTION   "Aid string of entity."
    ::=  { entityFfpEntry 6 }

entityFfpType OBJECT-TYPE
    SYNTAX      FspR7EntityType
    MAX-ACCESS  read-only
    STATUS      current
    DESCRIPTION   "The type of entity."
    ::=  { entityFfpEntry 7 }

entityFfpTableId OBJECT-TYPE
    SYNTAX      RowPointer
    MAX-ACCESS  read-only
    STATUS      current
    DESCRIPTION   "RowPointer to managment table of entity."
    ::=  { entityFfpEntry 8 }

entityFfpParentId OBJECT-TYPE
    SYNTAX      RowPointer
    MAX-ACCESS  read-only
    STATUS      current
    DESCRIPTION   "RowPointer to parent entity reported in corresponding entity table."
    ::=  { entityFfpEntry 9 }

entityFfpClass OBJECT-TYPE
    SYNTAX      EntityClass
    MAX-ACCESS  read-only
    STATUS      current
    DESCRIPTION   "EntityClass"
    ::=  { entityFfpEntry 10 }

entityFfpOneIndex OBJECT-TYPE
    SYNTAX      Unsigned32
    MAX-ACCESS  read-only
    STATUS      current
    DESCRIPTION
        "One Index Aid representation"
    ::=  { entityFfpEntry 11 }

entityCrossDcnTable OBJECT-TYPE
    SYNTAX      SEQUENCE OF EntityCrossDcnEntry
    MAX-ACCESS  not-accessible
    STATUS      current
    DESCRIPTION   "entityCrossDcnTable - conatains entities of Cross-Dcn"
    ::=  { entities 20 }

entityCrossDcnEntry OBJECT-TYPE
    SYNTAX      EntityCrossDcnEntry
    MAX-ACCESS  not-accessible
    STATUS      current
    DESCRIPTION   "Entry of entityCrossDcnTable"
    INDEX       {
                  entityCrossDcnShelfNo,
                  entityCrossDcnSlotNo,
                  entityCrossDcnPortNo,
                  entityCrossDcnExtNo,
                  entityCrossDcnClassName
                }
    ::=  { entityCrossDcnTable 1 }

EntityCrossDcnEntry ::=  SEQUENCE
  { entityCrossDcnShelfNo Unsigned32,
    entityCrossDcnSlotNo Unsigned32,
    entityCrossDcnPortNo Unsigned32,
    entityCrossDcnExtNo Unsigned32,
    entityCrossDcnClassName EntityClassName,
    entityCrossDcnAidString SnmpAdminString,
    entityCrossDcnType FspR7EntityType,
    entityCrossDcnTableId RowPointer,
    entityCrossDcnParentId RowPointer,
    entityCrossDcnClass EntityClass,
    entityCrossDcnOneIndex Unsigned32 }

entityCrossDcnShelfNo OBJECT-TYPE
    SYNTAX      Unsigned32
    MAX-ACCESS  not-accessible
    STATUS      current
    DESCRIPTION   "Adress index."
    ::=  { entityCrossDcnEntry 1 }

entityCrossDcnSlotNo OBJECT-TYPE
    SYNTAX      Unsigned32
    MAX-ACCESS  not-accessible
    STATUS      current
    DESCRIPTION   "Adress index."
    ::=  { entityCrossDcnEntry 2 }

entityCrossDcnPortNo OBJECT-TYPE
    SYNTAX      Unsigned32
    MAX-ACCESS  not-accessible
    STATUS      current
    DESCRIPTION   "Adress index."
    ::=  { entityCrossDcnEntry 3 }

entityCrossDcnExtNo OBJECT-TYPE
    SYNTAX      Unsigned32
    MAX-ACCESS  not-accessible
    STATUS      current
    DESCRIPTION   "Adress index."
    ::=  { entityCrossDcnEntry 4 }

entityCrossDcnClassName OBJECT-TYPE
    SYNTAX      EntityClassName
    MAX-ACCESS  not-accessible
    STATUS      current
    DESCRIPTION
        "Entity Class Name"
    ::=  { entityCrossDcnEntry 5 }

entityCrossDcnAidString OBJECT-TYPE
    SYNTAX      SnmpAdminString
    MAX-ACCESS  read-only
    STATUS      current
    DESCRIPTION   "Aid string of entity."
    ::=  { entityCrossDcnEntry 6 }

entityCrossDcnType OBJECT-TYPE
    SYNTAX      FspR7EntityType
    MAX-ACCESS  read-only
    STATUS      current
    DESCRIPTION   "The type of entity."
    ::=  { entityCrossDcnEntry 7 }

entityCrossDcnTableId OBJECT-TYPE
    SYNTAX      RowPointer
    MAX-ACCESS  read-only
    STATUS      current
    DESCRIPTION   "RowPointer to managment table of entity."
    ::=  { entityCrossDcnEntry 8 }

entityCrossDcnParentId OBJECT-TYPE
    SYNTAX      RowPointer
    MAX-ACCESS  read-only
    STATUS      current
    DESCRIPTION   "RowPointer to parent entity reported in corresponding entity table."
    ::=  { entityCrossDcnEntry 9 }

entityCrossDcnClass OBJECT-TYPE
    SYNTAX      EntityClass
    MAX-ACCESS  read-only
    STATUS      current
    DESCRIPTION   "EntityClass"
    ::=  { entityCrossDcnEntry 10 }

entityCrossDcnOneIndex OBJECT-TYPE
    SYNTAX      Unsigned32
    MAX-ACCESS  read-only
    STATUS      current
    DESCRIPTION
        "One Index Aid representation"
    ::=  { entityCrossDcnEntry 11 }

entityProtectionCableTable OBJECT-TYPE
    SYNTAX      SEQUENCE OF EntityProtectionCableEntry
    MAX-ACCESS  not-accessible
    STATUS      current
    DESCRIPTION   "entityProtectionCableTable"
    ::=  { entities 21 }

entityProtectionCableEntry OBJECT-TYPE
    SYNTAX      EntityProtectionCableEntry
    MAX-ACCESS  not-accessible
    STATUS      current
    DESCRIPTION   "Entry of entityProtectionCableTable"
    INDEX       {
                  entityProtectionCableIndex1,
                  entityProtectionCableIndex2,
                  entityProtectionCableIndex3,
                  entityProtectionCableIndex4,
                  entityProtectionCableClassName
                }
    ::=  { entityProtectionCableTable 1 }

EntityProtectionCableEntry ::=  SEQUENCE
  { entityProtectionCableIndex1 Unsigned32,
    entityProtectionCableIndex2 Unsigned32,
    entityProtectionCableIndex3 Unsigned32,
    entityProtectionCableIndex4 Unsigned32,
    entityProtectionCableClassName EntityClassName,
    entityProtectionCableAidString SnmpAdminString,
    entityProtectionCableType FspR7EntityType,
    entityProtectionCableTableId RowPointer,
    entityProtectionCableParentId RowPointer,
    entityProtectionCableClass EntityClass }

entityProtectionCableIndex1 OBJECT-TYPE
    SYNTAX      Unsigned32
    MAX-ACCESS  not-accessible
    STATUS      current
    DESCRIPTION   "Adress index."
    ::=  { entityProtectionCableEntry 1 }

entityProtectionCableIndex2 OBJECT-TYPE
    SYNTAX      Unsigned32
    MAX-ACCESS  not-accessible
    STATUS      current
    DESCRIPTION   "Adress index."
    ::=  { entityProtectionCableEntry 2 }

entityProtectionCableIndex3 OBJECT-TYPE
    SYNTAX      Unsigned32
    MAX-ACCESS  not-accessible
    STATUS      current
    DESCRIPTION   "Adress index."
    ::=  { entityProtectionCableEntry 3 }

entityProtectionCableIndex4 OBJECT-TYPE
    SYNTAX      Unsigned32
    MAX-ACCESS  not-accessible
    STATUS      current
    DESCRIPTION   "Adress index."
    ::=  { entityProtectionCableEntry 4 }

entityProtectionCableClassName OBJECT-TYPE
    SYNTAX      EntityClassName
    MAX-ACCESS  not-accessible
    STATUS      current
    DESCRIPTION   "Entity Class Name."
    ::=  { entityProtectionCableEntry 5 }

entityProtectionCableAidString OBJECT-TYPE
    SYNTAX      SnmpAdminString
    MAX-ACCESS  read-only
    STATUS      current
    DESCRIPTION   "Aid string of entity."
    ::=  { entityProtectionCableEntry 6 }

entityProtectionCableType OBJECT-TYPE
    SYNTAX      FspR7EntityType
    MAX-ACCESS  read-only
    STATUS      current
    DESCRIPTION   "The type of entity."
    ::=  { entityProtectionCableEntry 7 }

entityProtectionCableTableId OBJECT-TYPE
    SYNTAX      RowPointer
    MAX-ACCESS  read-only
    STATUS      current
    DESCRIPTION   "RowPointer to managment table of entity."
    ::=  { entityProtectionCableEntry 8 }

entityProtectionCableParentId OBJECT-TYPE
    SYNTAX      RowPointer
    MAX-ACCESS  read-only
    STATUS      current
    DESCRIPTION   "RowPointer to parent entity reported in corresponding entity table."
    ::=  { entityProtectionCableEntry 9 }

entityProtectionCableClass OBJECT-TYPE
    SYNTAX      EntityClass
    MAX-ACCESS  read-only
    STATUS      current
    DESCRIPTION   "EntityClass"
    ::=  { entityProtectionCableEntry 10 }

entityFilterCableTable OBJECT-TYPE
    SYNTAX      SEQUENCE OF EntityFilterCableEntry
    MAX-ACCESS  not-accessible
    STATUS      current
    DESCRIPTION   "entityFilterCableTable"
    ::=  { entities 22 }

entityFilterCableEntry OBJECT-TYPE
    SYNTAX      EntityFilterCableEntry
    MAX-ACCESS  not-accessible
    STATUS      current
    DESCRIPTION   "Entry of entityFilterCableTable"
    INDEX       {
                  entityFilterCableIndex1,
                  entityFilterCableIndex2,
                  entityFilterCableIndex3,
                  entityFilterCableIndex4,
                  entityFilterCableClassName
                }
    ::=  { entityFilterCableTable 1 }

EntityFilterCableEntry ::=  SEQUENCE
  { entityFilterCableIndex1 Unsigned32,
    entityFilterCableIndex2 Unsigned32,
    entityFilterCableIndex3 Unsigned32,
    entityFilterCableIndex4 Unsigned32,
    entityFilterCableClassName EntityClassName,
    entityFilterCableAidString SnmpAdminString,
    entityFilterCableType FspR7EntityType,
    entityFilterCableTableId RowPointer,
    entityFilterCableParentId RowPointer,
    entityFilterCableClass EntityClass }

entityFilterCableIndex1 OBJECT-TYPE
    SYNTAX      Unsigned32
    MAX-ACCESS  not-accessible
    STATUS      current
    DESCRIPTION   "Adress index."
    ::=  { entityFilterCableEntry 1 }

entityFilterCableIndex2 OBJECT-TYPE
    SYNTAX      Unsigned32
    MAX-ACCESS  not-accessible
    STATUS      current
    DESCRIPTION   "Adress index."
    ::=  { entityFilterCableEntry 2 }

entityFilterCableIndex3 OBJECT-TYPE
    SYNTAX      Unsigned32
    MAX-ACCESS  not-accessible
    STATUS      current
    DESCRIPTION   "Adress index."
    ::=  { entityFilterCableEntry 3 }

entityFilterCableIndex4 OBJECT-TYPE
    SYNTAX      Unsigned32
    MAX-ACCESS  not-accessible
    STATUS      current
    DESCRIPTION   "Adress index."
    ::=  { entityFilterCableEntry 4 }

entityFilterCableClassName OBJECT-TYPE
    SYNTAX      EntityClassName
    MAX-ACCESS  not-accessible
    STATUS      current
    DESCRIPTION   "Entity Class Name."
    ::=  { entityFilterCableEntry 5 }

entityFilterCableAidString OBJECT-TYPE
    SYNTAX      SnmpAdminString
    MAX-ACCESS  read-only
    STATUS      current
    DESCRIPTION   "Aid string of entity."
    ::=  { entityFilterCableEntry 6 }

entityFilterCableType OBJECT-TYPE
    SYNTAX      FspR7EntityType
    MAX-ACCESS  read-only
    STATUS      current
    DESCRIPTION   "The type of entity."
    ::=  { entityFilterCableEntry 7 }

entityFilterCableTableId OBJECT-TYPE
    SYNTAX      RowPointer
    MAX-ACCESS  read-only
    STATUS      current
    DESCRIPTION   "RowPointer to managment table of entity."
    ::=  { entityFilterCableEntry 8 }

entityFilterCableParentId OBJECT-TYPE
    SYNTAX      RowPointer
    MAX-ACCESS  read-only
    STATUS      current
    DESCRIPTION   "RowPointer to parent entity reported in corresponding entity table."
    ::=  { entityFilterCableEntry 9 }

entityFilterCableClass OBJECT-TYPE
    SYNTAX      EntityClass
    MAX-ACCESS  read-only
    STATUS      current
    DESCRIPTION   "EntityClass"
    ::=  { entityFilterCableEntry 10 }

entityMtosiSlotsTable OBJECT-TYPE
    SYNTAX      SEQUENCE OF EntityMtosiSlotsEntry
    MAX-ACCESS  not-accessible
    STATUS      current
    DESCRIPTION   "entityMtosiSlotsTable"
    ::=  { entities 100 }

entityMtosiSlotsEntry OBJECT-TYPE
    SYNTAX      EntityMtosiSlotsEntry
    MAX-ACCESS  not-accessible
    STATUS      current
    DESCRIPTION   "Entry of entityMtosiSlotsTable"
    INDEX       {
                  entityMtosiSlotsShelfNo,
                  entityMtosiSlotsSlotNo,
                  entityMtosiSlotsPortNo,
                  entityMtosiSlotsExtNo,
                  entityMtosiSlotsClassName
                }
    ::=  { entityMtosiSlotsTable 1 }

EntityMtosiSlotsEntry ::=  SEQUENCE
  { entityMtosiSlotsShelfNo Unsigned32,
    entityMtosiSlotsSlotNo Unsigned32,
    entityMtosiSlotsPortNo Unsigned32,
    entityMtosiSlotsExtNo Unsigned32,
    entityMtosiSlotsClassName EntityClassName,
    entityMtosiSlotsAidString SnmpAdminString,
    entityMtosiSlotsParentId RowPointer,
    entityMtosiSlotsClass EntityClass,
    entityMtosiSlotsChildId RowPointer }

entityMtosiSlotsShelfNo OBJECT-TYPE
    SYNTAX      Unsigned32
    MAX-ACCESS  not-accessible
    STATUS      current
    DESCRIPTION   "Adress index."
    ::=  { entityMtosiSlotsEntry 1 }

entityMtosiSlotsSlotNo OBJECT-TYPE
    SYNTAX      Unsigned32
    MAX-ACCESS  not-accessible
    STATUS      current
    DESCRIPTION   "Adress index."
    ::=  { entityMtosiSlotsEntry 2 }

entityMtosiSlotsPortNo OBJECT-TYPE
    SYNTAX      Unsigned32
    MAX-ACCESS  not-accessible
    STATUS      current
    DESCRIPTION   "Adress index."
    ::=  { entityMtosiSlotsEntry 3 }

entityMtosiSlotsExtNo OBJECT-TYPE
    SYNTAX      Unsigned32
    MAX-ACCESS  not-accessible
    STATUS      current
    DESCRIPTION   "Adress index."
    ::=  { entityMtosiSlotsEntry 4 }

entityMtosiSlotsClassName OBJECT-TYPE
    SYNTAX      EntityClassName
    MAX-ACCESS  not-accessible
    STATUS      current
    DESCRIPTION   "Entity Class Name."
    ::=  { entityMtosiSlotsEntry 5 }

entityMtosiSlotsAidString OBJECT-TYPE
    SYNTAX      SnmpAdminString
    MAX-ACCESS  read-only
    STATUS      current
    DESCRIPTION   "Aid string of entity."
    ::=  { entityMtosiSlotsEntry 6 }

entityMtosiSlotsParentId OBJECT-TYPE
    SYNTAX      RowPointer
    MAX-ACCESS  read-only
    STATUS      current
    DESCRIPTION   "RowPointer to parent entity reported in corresponding entity table."
    ::=  { entityMtosiSlotsEntry 7 }

entityMtosiSlotsClass OBJECT-TYPE
    SYNTAX      EntityClass
    MAX-ACCESS  read-only
    STATUS      current
    DESCRIPTION   "EntityClass"
    ::=  { entityMtosiSlotsEntry 8 }

entityMtosiSlotsChildId OBJECT-TYPE
    SYNTAX      RowPointer
    MAX-ACCESS  read-only
    STATUS      current
    DESCRIPTION
        ""
    ::=  { entityMtosiSlotsEntry 9 }

endOfEntities OBJECT-TYPE
    SYNTAX      Integer32
    MAX-ACCESS  read-only
    STATUS      current
    DESCRIPTION
        ""
    ::=  { entities 10000 }

trapModeLegacy OBJECT-TYPE
    SYNTAX      FspR7TrapModeLegacy
    MAX-ACCESS  read-write
    STATUS      current
    DESCRIPTION   "Scalar indicate MIB from which will be taken OID of entity to trap
         when entity is supported by more than one MIB."
    ::=  { neMgmt 1 }

artificialEntity OBJECT-TYPE
    SYNTAX      FspR7ColumnMark
    MAX-ACCESS  read-write
    STATUS      current
    DESCRIPTION
        "Enables Artificial Entities in chosen tables"
    ::=  { neMgmt 2 }

identifyTraps OBJECT-TYPE
    SYNTAX      FspR7EnableDisable
    MAX-ACCESS  read-write
    STATUS      current
    DESCRIPTION
        "Enable/disable extra data in traps (current user and application source)"
    ::=  { neMgmt 3 }

ipv6 OBJECT-TYPE
    SYNTAX      FspR7EnableDisable
    MAX-ACCESS  read-write
    STATUS      current
    DESCRIPTION
        "IPv6 Control"
    ::=  { ipConf 1 }

ipv6DefGateway OBJECT-TYPE
    SYNTAX      SnmpAdminString
    MAX-ACCESS  read-write
    STATUS      current
    DESCRIPTION
        "IPv6 Address of Default Gateway"
    ::=  { ipConf 2 }

endOfNeMgmt OBJECT-TYPE
    SYNTAX      Integer32
    MAX-ACCESS  read-only
    STATUS      current
    DESCRIPTION
        ""
    ::=  { neMgmt 10000 }

crossConnectionTable OBJECT-TYPE
    SYNTAX      SEQUENCE OF CrossConnectionEntry
    MAX-ACCESS  not-accessible
    STATUS      current
    DESCRIPTION   "crossConnectionTable"
    ::=  { specificMgmt 6 }

crossConnectionEntry OBJECT-TYPE
    SYNTAX      CrossConnectionEntry
    MAX-ACCESS  not-accessible
    STATUS      current
    DESCRIPTION   "Entry of crossConnectionTable"
    INDEX       {
                  entityCrossConnFromShelfNo,
                  entityCrossConnFromSlotNo,
                  entityCrossConnFromPortNo,
                  entityCrossConnFromExtNo,
                  entityCrossConnFromClassName,
                  entityCrossConnToShelfNo,
                  entityCrossConnToSlotNo,
                  entityCrossConnToPortNo,
                  entityCrossConnToExtNo,
                  entityCrossConnToClassName,
                  entityCrossConnClassName
                }
    ::=  { crossConnectionTable 1 }

CrossConnectionEntry ::=  SEQUENCE
  { crossConnectionRowStatus RowStatus,
    crossConnectionAdmin FspR7AdminState,
    crossConnectionRedLineState FspR7RedLinedState,
    crossConnectionCrsFunction FspR7FunctionCrs,
    crossConnectionConn FspR7Conn,
    crossConnectionCrsType FspR7TypeCrs,
    crossConnectionAlias SnmpAdminString,
    crossConnectionPathNode FspR7PathNode,
    crossConnectionTunnelAid SnmpAdminString,
    crossConnectionIngressTid SnmpAdminString,
    crossConnectionIngressNodeIp IpAddress,
    crossConnectionOperState FspR7OperState,
    crossConnectionSecondaryStates FspR7EntitySecondaryStates,
    crossConnectionType FspR7InterfaceType,
    crossConnectionPathProtection FspR7PathProt,
    crossConnectionCrsFromAidTwo FspR7SnmpLongString,
    crossConnectionCrsToAidTwo FspR7SnmpLongString,
    crossConnectionCrsMcAidList FspR7SnmpLongString,
    crossConnectionCrsContAidList FspR7SnmpLongString,
    crossConnectionCrsContAidListTwo FspR7SnmpLongString }

crossConnectionRowStatus OBJECT-TYPE
    SYNTAX      RowStatus
    MAX-ACCESS  read-create
    STATUS      current
    DESCRIPTION   "RowStatus object is used to create or delete a row in the table."
    ::=  { crossConnectionEntry 1 }

crossConnectionAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { crossConnectionEntry 2 }

crossConnectionRedLineState OBJECT-TYPE
    SYNTAX      FspR7RedLinedState
    MAX-ACCESS  read-create
    STATUS      current
    DESCRIPTION
        "will be set by higher level software to act as a barrier to deletion"
    ::=  { crossConnectionEntry 3 }

crossConnectionCrsFunction OBJECT-TYPE
    SYNTAX      FspR7FunctionCrs
    MAX-ACCESS  read-create
    STATUS      current
    DESCRIPTION
        "Describes the Cross Connect Functionality"
    ::=  { crossConnectionEntry 4 }

crossConnectionConn OBJECT-TYPE
    SYNTAX      FspR7Conn
    MAX-ACCESS  read-create
    STATUS      current
    DESCRIPTION
        "Bidirectional | Unidirectional"
    ::=  { crossConnectionEntry 5 }

crossConnectionCrsType OBJECT-TYPE
    SYNTAX      FspR7TypeCrs
    MAX-ACCESS  read-create
    STATUS      current
    DESCRIPTION
        "Type of Cross-Connect"
    ::=  { crossConnectionEntry 6 }

crossConnectionAlias OBJECT-TYPE
    SYNTAX      SnmpAdminString
    MAX-ACCESS  read-create
    STATUS      current
    DESCRIPTION
        "User Applied Descriptor"
    ::=  { crossConnectionEntry 7 }

crossConnectionPathNode OBJECT-TYPE
    SYNTAX      FspR7PathNode
    MAX-ACCESS  read-create
    STATUS      current
    DESCRIPTION
        "Node count along a signal path on a unidirectional basis from the client signal ingress to egress"
    ::=  { crossConnectionEntry 8 }

crossConnectionTunnelAid OBJECT-TYPE
    SYNTAX      SnmpAdminString
    MAX-ACCESS  read-create
    STATUS      current
    DESCRIPTION
        "Tunnel AID"
    ::=  { crossConnectionEntry 9 }

crossConnectionIngressTid OBJECT-TYPE
    SYNTAX      SnmpAdminString
    MAX-ACCESS  read-only
    STATUS      current
    DESCRIPTION
        "Ingress Target ID"
    ::=  { crossConnectionEntry 10 }

crossConnectionIngressNodeIp OBJECT-TYPE
    SYNTAX      IpAddress
    MAX-ACCESS  read-only
    STATUS      current
    DESCRIPTION
        "Ingress Node IP"
    ::=  { crossConnectionEntry 11 }

crossConnectionOperState OBJECT-TYPE
    SYNTAX      FspR7OperState
    MAX-ACCESS  read-only
    STATUS      current
    DESCRIPTION
        "The Operational State will be displayed on the
         GUI with full name values; it will be differently
         displayed in TL1 syntax according to TL1 display rules."
    ::=  { crossConnectionEntry 12 }

crossConnectionSecondaryStates OBJECT-TYPE
    SYNTAX      FspR7EntitySecondaryStates
    MAX-ACCESS  read-only
    STATUS      current
    DESCRIPTION
        "Secondary States"
    ::=  { crossConnectionEntry 13 }

crossConnectionType OBJECT-TYPE
    SYNTAX      FspR7InterfaceType
    MAX-ACCESS  read-create
    STATUS      current
    DESCRIPTION
        "The TYPE defines the transport service type as wrapper with wrapper layer termination OR else as payload"
    ::=  { crossConnectionEntry 14 }

crossConnectionPathProtection OBJECT-TYPE
    SYNTAX      FspR7PathProt
    MAX-ACCESS  read-only
    STATUS      current
    DESCRIPTION
        "Indicates the traffic path for path protection cases when the FFP does not exist. When the FFP exists, protected is indicated and the status is determined by the FFP."
    ::=  { crossConnectionEntry 15 }

crossConnectionCrsFromAidTwo OBJECT-TYPE
    SYNTAX      FspR7SnmpLongString
    MAX-ACCESS  read-create
    STATUS      current
    DESCRIPTION
        "AID of a CH-#, VCH or VCHn instance."
    ::=  { crossConnectionEntry 16 }

crossConnectionCrsToAidTwo OBJECT-TYPE
    SYNTAX      FspR7SnmpLongString
    MAX-ACCESS  read-create
    STATUS      current
    DESCRIPTION
        "Second AID of a CH-C#, VCH or a VCHn instance."
    ::=  { crossConnectionEntry 17 }

crossConnectionCrsMcAidList OBJECT-TYPE
    SYNTAX      FspR7SnmpLongString
    MAX-ACCESS  read-create
    STATUS      current
    DESCRIPTION
        "A list of AIDs used in multicast variants of CRS"
    ::=  { crossConnectionEntry 18 }

crossConnectionCrsContAidList OBJECT-TYPE
    SYNTAX      FspR7SnmpLongString
    MAX-ACCESS  read-create
    STATUS      current
    DESCRIPTION
        "List of AIDs for Continue Points of a CRS"
    ::=  { crossConnectionEntry 19 }

crossConnectionCrsContAidListTwo OBJECT-TYPE
    SYNTAX      FspR7SnmpLongString
    MAX-ACCESS  read-create
    STATUS      current
    DESCRIPTION
        "Second list of AIDs for Continue Points of a CRS"
    ::=  { crossConnectionEntry 20 }

crossOpticalLineTable OBJECT-TYPE
    SYNTAX      SEQUENCE OF CrossOpticalLineEntry
    MAX-ACCESS  not-accessible
    STATUS      current
    DESCRIPTION   "crossOpticalLineTable"
    ::=  { specificMgmt 7 }

crossOpticalLineEntry OBJECT-TYPE
    SYNTAX      CrossOpticalLineEntry
    MAX-ACCESS  not-accessible
    STATUS      current
    DESCRIPTION   "Entry of crossOpticalLineTable"
    INDEX       {
                  entityCrsOptLineFromIndexNo1,
                  entityCrsOptLineFromIndexNo2,
                  entityCrsOptLineFromIndexNo3,
                  entityCrsOptLineFromIndexNo4,
                  entityCrsOptLineFromClassName,
                  entityCrsOptLineToIndexNo1,
                  entityCrsOptLineToIndexNo2,
                  entityCrsOptLineToIndexNo3,
                  entityCrsOptLineToIndexNo4,
                  entityCrsOptLineToClassName,
                  entityCrsOptLineClassName
                }
    ::=  { crossOpticalLineTable 1 }

CrossOpticalLineEntry ::=  SEQUENCE
  { crossOpticalLineRowStatus RowStatus,
    crossOpticalLineRedLineState FspR7RedLinedState,
    crossOpticalLineCrsFunction FspR7FunctionCrs,
    crossOpticalLineConn FspR7Conn,
    crossOpticalLineCrsType FspR7TypeCrs,
    crossOpticalLineAlias SnmpAdminString,
    crossOpticalLineTunnelAid SnmpAdminString,
    crossOpticalLineIngressTid SnmpAdminString,
    crossOpticalLineIngressNodeIp IpAddress,
    crossOpticalLineSecondaryStates FspR7EntitySecondaryStates }

crossOpticalLineRowStatus OBJECT-TYPE
    SYNTAX      RowStatus
    MAX-ACCESS  read-create
    STATUS      current
    DESCRIPTION   "RowStatus object is used to create or delete a row in the table."
    ::=  { crossOpticalLineEntry 1 }

crossOpticalLineRedLineState OBJECT-TYPE
    SYNTAX      FspR7RedLinedState
    MAX-ACCESS  read-create
    STATUS      current
    DESCRIPTION
        "will be set by higher level software to act as a barrier to deletion"
    ::=  { crossOpticalLineEntry 2 }

crossOpticalLineCrsFunction OBJECT-TYPE
    SYNTAX      FspR7FunctionCrs
    MAX-ACCESS  read-only
    STATUS      current
    DESCRIPTION
        "Describes the Cross Connect Functionality"
    ::=  { crossOpticalLineEntry 3 }

crossOpticalLineConn OBJECT-TYPE
    SYNTAX      FspR7Conn
    MAX-ACCESS  read-create
    STATUS      current
    DESCRIPTION
        "Bidirectional | Unidirectional"
    ::=  { crossOpticalLineEntry 4 }

crossOpticalLineCrsType OBJECT-TYPE
    SYNTAX      FspR7TypeCrs
    MAX-ACCESS  read-create
    STATUS      current
    DESCRIPTION
        "Type of Cross-Connect"
    ::=  { crossOpticalLineEntry 5 }

crossOpticalLineAlias OBJECT-TYPE
    SYNTAX      SnmpAdminString
    MAX-ACCESS  read-create
    STATUS      current
    DESCRIPTION
        "User Applied Descriptor"
    ::=  { crossOpticalLineEntry 6 }

crossOpticalLineTunnelAid OBJECT-TYPE
    SYNTAX      SnmpAdminString
    MAX-ACCESS  read-create
    STATUS      current
    DESCRIPTION
        "Tunnel AID"
    ::=  { crossOpticalLineEntry 7 }

crossOpticalLineIngressTid OBJECT-TYPE
    SYNTAX      SnmpAdminString
    MAX-ACCESS  read-only
    STATUS      current
    DESCRIPTION
        "Ingress Target ID"
    ::=  { crossOpticalLineEntry 8 }

crossOpticalLineIngressNodeIp OBJECT-TYPE
    SYNTAX      IpAddress
    MAX-ACCESS  read-only
    STATUS      current
    DESCRIPTION
        "Ingress Node IP"
    ::=  { crossOpticalLineEntry 9 }

crossOpticalLineSecondaryStates OBJECT-TYPE
    SYNTAX      FspR7EntitySecondaryStates
    MAX-ACCESS  read-only
    STATUS      current
    DESCRIPTION
        "Secondary States"
    ::=  { crossOpticalLineEntry 10 }

endOfCrossOpticalLineTable OBJECT-TYPE
    SYNTAX      Integer32
    MAX-ACCESS  read-only
    STATUS      current
    DESCRIPTION
        ""
    ::=  { specificMgmt 8 }

crossDcnTable OBJECT-TYPE
    SYNTAX      SEQUENCE OF CrossDcnEntry
    MAX-ACCESS  not-accessible
    STATUS      current
    DESCRIPTION   "crossDcnTable"
    ::=  { specificMgmt 9 }

crossDcnEntry OBJECT-TYPE
    SYNTAX      CrossDcnEntry
    MAX-ACCESS  not-accessible
    STATUS      current
    DESCRIPTION   "Entry of crossDcnTable"
    INDEX       {
                  entityCrossDcnShelfNo,
                  entityCrossDcnSlotNo,
                  entityCrossDcnPortNo,
                  entityCrossDcnExtNo,
                  entityCrossDcnClassName
                }
    ::=  { crossDcnTable 1 }

CrossDcnEntry ::=  SEQUENCE
  { crossDcnRowStatus RowStatus,
    crossDcnType FspR7TypeConnection,
    crossDcnLink SnmpAdminString,
    crossDcnEcc SnmpAdminString }

crossDcnRowStatus OBJECT-TYPE
    SYNTAX      RowStatus
    MAX-ACCESS  read-create
    STATUS      current
    DESCRIPTION   "RowStatus object is used to create or delete a row in the table."
    ::=  { crossDcnEntry 1 }

crossDcnType OBJECT-TYPE
    SYNTAX      FspR7TypeConnection
    MAX-ACCESS  read-create
    STATUS      current
    DESCRIPTION
        "Type of Cross-Connect"
    ::=  { crossDcnEntry 2 }

crossDcnLink OBJECT-TYPE
    SYNTAX      SnmpAdminString
    MAX-ACCESS  read-create
    STATUS      current
    DESCRIPTION
        "Address Identifier of PPPIP LINK Entity."
    ::=  { crossDcnEntry 3 }

crossDcnEcc OBJECT-TYPE
    SYNTAX      SnmpAdminString
    MAX-ACCESS  read-create
    STATUS      current
    DESCRIPTION
        "Address Identifier of ECC Entity."
    ::=  { crossDcnEntry 4 }

endOfCrossDcnTable OBJECT-TYPE
    SYNTAX      Integer32
    MAX-ACCESS  read-only
    STATUS      current
    DESCRIPTION
        ""
    ::=  { specificMgmt 10 }

endOfSpecificMgmt OBJECT-TYPE
    SYNTAX      Integer32
    MAX-ACCESS  read-only
    STATUS      current
    DESCRIPTION
        ""
    ::=  { specificMgmt 10000 }

shelfTable OBJECT-TYPE
    SYNTAX      SEQUENCE OF ShelfEntry
    MAX-ACCESS  not-accessible
    STATUS      current
    DESCRIPTION   "shelfTable"
    ::=  { eqptMgmt 1 }

shelfEntry OBJECT-TYPE
    SYNTAX      ShelfEntry
    MAX-ACCESS  not-accessible
    STATUS      current
    DESCRIPTION   "Entry of shelfTable"
    INDEX       {
                  entityEqptShelfNo,
                  entityEqptSlotNo,
                  entityEqptPortNo,
                  entityEqptExtNo,
                  entityEqptClassName
                }
    ::=  { shelfTable 1 }

ShelfEntry ::=  SEQUENCE
  { shelfRowStatus RowStatus,
    shelfNetworkPorts Unsigned32,
    shelfInternalPlugs FspR7EquipmentTypeCaps,
    shelfConnectionType FspR7TypeConnection,
    shelfOscPorts Unsigned32,
    shelfShelfHeight Unsigned32,
    shelfChannel FspR7ChannelIdentifierCaps,
    shelfPsuOutputPower FspR7PsuOutputPower,
    shelfType FspR7EquipmentType,
    shelfChannelsNumber FspR7NumberOfChannels,
    shelfRack SnmpAdminString,
    shelfInternalPlugRates FspR7PlugDataRateCaps,
    shelfConnectorType FspR7ConnectorType,
    shelfSupply FspR7SupplyType,
    shelfClientPorts Unsigned32,
    shelfFiberBrand FspR7FiberBrand,
    shelfTransmitChannel FspR7ChannelIdentifier,
    shelfBandProvision FspR7OpticalBand,
    shelfUpgradePorts Unsigned32,
    shelfStandardSlotHeight Unsigned32,
    shelfStandardSlots Unsigned32,
    shelfChannelBandwith FspR7ChannelBandwidth,
    shelfAdmin FspR7AdminState,
    shelfInternalPorts Unsigned32,
    shelfRackNumber Unsigned32,
    shelfRackOrder Unsigned32,
    shelfOscChannel FspR7OscChannel,
    shelfMaxPowerConsumption Unsigned32,
    shelfAlias SnmpAdminString,
    shelfFiberType FspR7OpticalFiberType,
    shelfChannelSpacing FspR7ChannelSpacing,
    shelfSecondaryStates FspR7EntitySecondaryStates,
    shelfOperState FspR7OperState,
    shelfScuRing FspR7ScuRing,
    shelfShelfId Unsigned32,
    shelfFDports Unsigned32,
    shelfSlot Unsigned32 }

shelfRowStatus OBJECT-TYPE
    SYNTAX      RowStatus
    MAX-ACCESS  read-create
    STATUS      current
    DESCRIPTION   "RowStatus object is used to create or delete a row in the table."
    ::=  { shelfEntry 1 }

shelfNetworkPorts OBJECT-TYPE
    SYNTAX      Unsigned32
    MAX-ACCESS  read-only
    STATUS      current
    DESCRIPTION
        "Number of Network Ports"
    ::=  { shelfEntry 2 }

shelfInternalPlugs OBJECT-TYPE
    SYNTAX      FspR7EquipmentTypeCaps
    MAX-ACCESS  read-only
    STATUS      current
    DESCRIPTION
        "Internal Plugs Required"
    ::=  { shelfEntry 3 }

shelfConnectionType OBJECT-TYPE
    SYNTAX      FspR7TypeConnection
    MAX-ACCESS  read-only
    STATUS      current
    DESCRIPTION
        "Connectivity Parameters for Facilities"
    ::=  { shelfEntry 4 }

shelfOscPorts OBJECT-TYPE
    SYNTAX      Unsigned32 (0..10)
    MAX-ACCESS  read-only
    STATUS      current
    DESCRIPTION
        "Number of OSC Ports"
    ::=  { shelfEntry 5 }

shelfShelfHeight OBJECT-TYPE
    SYNTAX      Unsigned32
    UNITS       "HU"
    MAX-ACCESS  read-only
    STATUS      current
    DESCRIPTION
        "Height of Shelf in HU"
    ::=  { shelfEntry 6 }

shelfChannel OBJECT-TYPE
    SYNTAX      FspR7ChannelIdentifierCaps
    MAX-ACCESS  read-only
    STATUS      current
    DESCRIPTION
        "Possible internal channel"
    ::=  { shelfEntry 7 }

shelfPsuOutputPower OBJECT-TYPE
    SYNTAX      FspR7PsuOutputPower
    MAX-ACCESS  read-create
    STATUS      current
    DESCRIPTION
        "Maximum PSU Output Power"
    ::=  { shelfEntry 8 }

shelfType OBJECT-TYPE
    SYNTAX      FspR7EquipmentType
    MAX-ACCESS  read-create
    STATUS      current
    DESCRIPTION
        "The TYPE of Equipment and the MODE setting determine uniquely the number and allowed TYPE's of the provisionable dependent entities (plugs, interfaces, modules)"
    ::=  { shelfEntry 9 }

shelfChannelsNumber OBJECT-TYPE
    SYNTAX      FspR7NumberOfChannels
    MAX-ACCESS  read-only
    STATUS      current
    DESCRIPTION
        "Number of channels supported by an entity"
    ::=  { shelfEntry 10 }

shelfRack OBJECT-TYPE
    SYNTAX      SnmpAdminString
    MAX-ACCESS  read-create
    STATUS      current
    DESCRIPTION
        "Rack Containing Shelf"
    ::=  { shelfEntry 11 }

shelfInternalPlugRates OBJECT-TYPE
    SYNTAX      FspR7PlugDataRateCaps
    MAX-ACCESS  read-only
    STATUS      current
    DESCRIPTION
        "List of Provisionable Internal Plug Rates Supported"
    ::=  { shelfEntry 12 }

shelfConnectorType OBJECT-TYPE
    SYNTAX      FspR7ConnectorType
    MAX-ACCESS  read-only
    STATUS      current
    DESCRIPTION
        "Connector Type"
    ::=  { shelfEntry 13 }

shelfSupply OBJECT-TYPE
    SYNTAX      FspR7SupplyType
    MAX-ACCESS  read-create
    STATUS      current
    DESCRIPTION
        "The kind of power supply - provisioned value"
    ::=  { shelfEntry 14 }

shelfClientPorts OBJECT-TYPE
    SYNTAX      Unsigned32 (0..96)
    MAX-ACCESS  read-only
    STATUS      current
    DESCRIPTION
        "Number of Client Ports"
    ::=  { shelfEntry 15 }

shelfFiberBrand OBJECT-TYPE
    SYNTAX      FspR7FiberBrand
    MAX-ACCESS  read-only
    STATUS      current
    DESCRIPTION
        "Brand of fiber present in the fiber plant"
    ::=  { shelfEntry 16 }

shelfTransmitChannel OBJECT-TYPE
    SYNTAX      FspR7ChannelIdentifier
    MAX-ACCESS  read-only
    STATUS      current
    DESCRIPTION
        "Channel"
    ::=  { shelfEntry 17 }

shelfBandProvision OBJECT-TYPE
    SYNTAX      FspR7OpticalBand
    MAX-ACCESS  read-create
    STATUS      current
    DESCRIPTION
        "Band Provision. Reference to BAND__INVENTORY."
    ::=  { shelfEntry 18 }

shelfUpgradePorts OBJECT-TYPE
    SYNTAX      Unsigned32
    MAX-ACCESS  read-only
    STATUS      current
    DESCRIPTION
        "Number of Upgrade Ports"
    ::=  { shelfEntry 19 }

shelfStandardSlotHeight OBJECT-TYPE
    SYNTAX      Unsigned32
    UNITS       "HU"
    MAX-ACCESS  read-only
    STATUS      current
    DESCRIPTION
        "Height of Standard Slots in Shelf in HU"
    ::=  { shelfEntry 20 }

shelfStandardSlots OBJECT-TYPE
    SYNTAX      Unsigned32 (2..20)
    MAX-ACCESS  read-only
    STATUS      current
    DESCRIPTION
        "Number of Provisionable Standard Slots"
    ::=  { shelfEntry 21 }

shelfChannelBandwith OBJECT-TYPE
    SYNTAX      FspR7ChannelBandwidth
    MAX-ACCESS  read-only
    STATUS      current
    DESCRIPTION
        "Channel Bandwidth"
    ::=  { shelfEntry 22 }

shelfAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { shelfEntry 23 }

shelfInternalPorts OBJECT-TYPE
    SYNTAX      Unsigned32
    MAX-ACCESS  read-only
    STATUS      current
    DESCRIPTION
        "Number of Internal Ports"
    ::=  { shelfEntry 24 }

shelfRackNumber OBJECT-TYPE
    SYNTAX      Unsigned32 (0..16)
    MAX-ACCESS  read-create
    STATUS      current
    DESCRIPTION
        "Number of the Rack"
    ::=  { shelfEntry 25 }

shelfRackOrder OBJECT-TYPE
    SYNTAX      Unsigned32 (0..45)
    MAX-ACCESS  read-create
    STATUS      current
    DESCRIPTION
        "Number place where the Shelf is placed in the rack (buttom up counting)"
    ::=  { shelfEntry 26 }

shelfOscChannel OBJECT-TYPE
    SYNTAX      FspR7OscChannel
    MAX-ACCESS  read-only
    STATUS      current
    DESCRIPTION
        "OSC Channel"
    ::=  { shelfEntry 27 }

shelfMaxPowerConsumption OBJECT-TYPE
    SYNTAX      Unsigned32
    UNITS       "0.1 W"
    MAX-ACCESS  read-only
    STATUS      current
    DESCRIPTION
        "Maximum Power Consumption of the device"
    ::=  { shelfEntry 28 }

shelfAlias OBJECT-TYPE
    SYNTAX      SnmpAdminString
    MAX-ACCESS  read-create
    STATUS      current
    DESCRIPTION
        "User Applied Descriptor"
    ::=  { shelfEntry 29 }

shelfFiberType OBJECT-TYPE
    SYNTAX      FspR7OpticalFiberType
    MAX-ACCESS  read-only
    STATUS      current
    DESCRIPTION
        "Fiber of Optical Interface - Provision, Reference to FIBER__INVENTORY"
    ::=  { shelfEntry 30 }

shelfChannelSpacing OBJECT-TYPE
    SYNTAX      FspR7ChannelSpacing
    MAX-ACCESS  read-only
    STATUS      current
    DESCRIPTION
        "ITU Grid channel spacing"
    ::=  { shelfEntry 31 }

shelfSecondaryStates OBJECT-TYPE
    SYNTAX      FspR7EntitySecondaryStates
    MAX-ACCESS  read-only
    STATUS      current
    DESCRIPTION
        "Secondary States"
    ::=  { shelfEntry 32 }

shelfOperState OBJECT-TYPE
    SYNTAX      FspR7OperState
    MAX-ACCESS  read-only
    STATUS      current
    DESCRIPTION
        "The Operational State will be displayed on the
         GUI with full name values; it will be differently
         displayed in TL1 syntax according to TL1 display rules."
    ::=  { shelfEntry 33 }

shelfScuRing OBJECT-TYPE
    SYNTAX      FspR7ScuRing
    MAX-ACCESS  read-only
    STATUS      current
    DESCRIPTION
        "SCU Interconnection"
    ::=  { shelfEntry 34 }

shelfShelfId OBJECT-TYPE
    SYNTAX      Unsigned32
    MAX-ACCESS  read-only
    STATUS      current
    DESCRIPTION
        "Shelf ID"
    ::=  { shelfEntry 35 }

shelfFDports OBJECT-TYPE
    SYNTAX      Unsigned32
    MAX-ACCESS  read-only
    STATUS      current
    DESCRIPTION
        "Number of Fiber Detect Ports"
    ::=  { shelfEntry 36 }

shelfSlot OBJECT-TYPE
    SYNTAX      Unsigned32 (0..20)
    MAX-ACCESS  read-create
    STATUS      current
    DESCRIPTION
        "Slot Position"
    ::=  { shelfEntry 37 }

endOfShelfTable OBJECT-TYPE
    SYNTAX      Integer32
    MAX-ACCESS  read-only
    STATUS      current
    DESCRIPTION
        ""
    ::=  { eqptMgmt 2 }

fanTable OBJECT-TYPE
    SYNTAX      SEQUENCE OF FanEntry
    MAX-ACCESS  not-accessible
    STATUS      current
    DESCRIPTION   "fanTable"
    ::=  { eqptMgmt 3 }

fanEntry OBJECT-TYPE
    SYNTAX      FanEntry
    MAX-ACCESS  not-accessible
    STATUS      current
    DESCRIPTION   "Entry of fanTable"
    INDEX       {
                  entityEqptShelfNo,
                  entityEqptSlotNo,
                  entityEqptPortNo,
                  entityEqptExtNo,
                  entityEqptClassName
                }
    ::=  { fanTable 1 }

FanEntry ::=  SEQUENCE
  { fanRowStatus RowStatus,
    fanForceDestroy FspR7ForcedStatus,
    fanMaxPowerConsumption Unsigned32,
    fanAdmin FspR7AdminState,
    fanType FspR7EquipmentType,
    fanAlias SnmpAdminString,
    fanOutputReset FspR7TifOutputReset,
    fanFanPorts Unsigned32,
    fanSecondaryStates FspR7EntitySecondaryStates,
    fanOperState FspR7OperState,
    fanFanProfile FspR7FanProfile }

fanRowStatus OBJECT-TYPE
    SYNTAX      RowStatus
    MAX-ACCESS  read-create
    STATUS      current
    DESCRIPTION   "RowStatus object is used to create or delete a row in the table."
    ::=  { fanEntry 1 }

fanForceDestroy OBJECT-TYPE
    SYNTAX      FspR7ForcedStatus
    MAX-ACCESS  read-create
    STATUS      current
    DESCRIPTION
        "Forced Destroy"
    ::=  { fanEntry 2 }

fanMaxPowerConsumption OBJECT-TYPE
    SYNTAX      Unsigned32
    UNITS       "0.1 W"
    MAX-ACCESS  read-only
    STATUS      current
    DESCRIPTION
        "Maximum Power Consumption of the device"
    ::=  { fanEntry 3 }

fanAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { fanEntry 4 }

fanType OBJECT-TYPE
    SYNTAX      FspR7EquipmentType
    MAX-ACCESS  read-create
    STATUS      current
    DESCRIPTION
        "The TYPE of Equipment and the MODE setting determine uniquely the number and allowed TYPE's of the provisionable dependent entities (plugs, interfaces, modules)"
    ::=  { fanEntry 5 }

fanAlias OBJECT-TYPE
    SYNTAX      SnmpAdminString
    MAX-ACCESS  read-create
    STATUS      current
    DESCRIPTION
        "User Applied Descriptor"
    ::=  { fanEntry 6 }

fanOutputReset OBJECT-TYPE
    SYNTAX      FspR7TifOutputReset
    MAX-ACCESS  read-write
    STATUS      current
    DESCRIPTION
        "Has the same function as the HW switch at the UTM board"
    ::=  { fanEntry 7 }

fanFanPorts OBJECT-TYPE
    SYNTAX      Unsigned32 (0..3)
    MAX-ACCESS  read-only
    STATUS      current
    DESCRIPTION
        "Number of Fan Plug ins"
    ::=  { fanEntry 8 }

fanSecondaryStates OBJECT-TYPE
    SYNTAX      FspR7EntitySecondaryStates
    MAX-ACCESS  read-only
    STATUS      current
    DESCRIPTION
        "Secondary States"
    ::=  { fanEntry 9 }

fanOperState OBJECT-TYPE
    SYNTAX      FspR7OperState
    MAX-ACCESS  read-only
    STATUS      current
    DESCRIPTION
        "The Operational State will be displayed on the
         GUI with full name values; it will be differently
         displayed in TL1 syntax according to TL1 display rules."
    ::=  { fanEntry 10 }

fanFanProfile OBJECT-TYPE
    SYNTAX      FspR7FanProfile
    MAX-ACCESS  read-only
    STATUS      current
    DESCRIPTION
        "Fan mode Calculated over all modules in the shelf"
    ::=  { fanEntry 11 }

endOfFanTable OBJECT-TYPE
    SYNTAX      Integer32
    MAX-ACCESS  read-only
    STATUS      current
    DESCRIPTION
        ""
    ::=  { eqptMgmt 4 }

plugTable OBJECT-TYPE
    SYNTAX      SEQUENCE OF PlugEntry
    MAX-ACCESS  not-accessible
    STATUS      current
    DESCRIPTION   "plugTable"
    ::=  { eqptMgmt 5 }

plugEntry OBJECT-TYPE
    SYNTAX      PlugEntry
    MAX-ACCESS  not-accessible
    STATUS      current
    DESCRIPTION   "Entry of plugTable"
    INDEX       {
                  entityEqptShelfNo,
                  entityEqptSlotNo,
                  entityEqptPortNo,
                  entityEqptExtNo,
                  entityEqptClassName
                }
    ::=  { plugTable 1 }

PlugEntry ::=  SEQUENCE
  { plugRowStatus RowStatus,
    plugConnector FspR7ConnectorType,
    plugType FspR7EquipmentType,
    plugReach FspR7OpticalInterfaceReach,
    plugLoopbackAttenuation Unsigned32,
    plugGenericPorts Unsigned32,
    plugConnectorType FspR7ConnectorType,
    plugFiberType FspR7OpticalFiberType,
    plugTransmitChannel FspR7ChannelIdentifier,
    plugAlias SnmpAdminString,
    plugLaneGroup FspR7LaneGroupInventory,
    plugMaxDataRate FspR7PlugDataRate,
    plugThirdPartyUsage EnableState,
    plugAdmin FspR7AdminState,
    plugSecondaryStates FspR7EntitySecondaryStates,
    plugOperState FspR7OperState,
    plugBidirectionalChannel FspR7BidirectionalChannel,
    plugChannelSpacingProvision FspR7ChannelSpacing }

plugRowStatus OBJECT-TYPE
    SYNTAX      RowStatus
    MAX-ACCESS  read-create
    STATUS      current
    DESCRIPTION   "RowStatus object is used to create or delete a row in the table."
    ::=  { plugEntry 1 }

plugConnector OBJECT-TYPE
    SYNTAX      FspR7ConnectorType
    MAX-ACCESS  read-create
    STATUS      current
    DESCRIPTION
        "Connector"
    ::=  { plugEntry 2 }

plugType OBJECT-TYPE
    SYNTAX      FspR7EquipmentType
    MAX-ACCESS  read-create
    STATUS      current
    DESCRIPTION
        "The TYPE of Equipment and the MODE setting determine uniquely the number and allowed TYPE's of the provisionable dependent entities (plugs, interfaces, modules)"
    ::=  { plugEntry 3 }

plugReach OBJECT-TYPE
    SYNTAX      FspR7OpticalInterfaceReach
    MAX-ACCESS  read-create
    STATUS      current
    DESCRIPTION
        "Reach"
    ::=  { plugEntry 4 }

plugLoopbackAttenuation OBJECT-TYPE
    SYNTAX      Unsigned32 (10..300)
    UNITS       "0.1 dB"
    MAX-ACCESS  read-create
    STATUS      current
    DESCRIPTION
        "Loop back attenuation used for Optojack SE plugs"
    ::=  { plugEntry 5 }

plugGenericPorts OBJECT-TYPE
    SYNTAX      Unsigned32 (0..40)
    MAX-ACCESS  read-only
    STATUS      current
    DESCRIPTION
        "Number of Generic Ports"
    ::=  { plugEntry 6 }

plugConnectorType OBJECT-TYPE
    SYNTAX      FspR7ConnectorType
    MAX-ACCESS  read-only
    STATUS      current
    DESCRIPTION
        "Connector Type"
    ::=  { plugEntry 7 }

plugFiberType OBJECT-TYPE
    SYNTAX      FspR7OpticalFiberType
    MAX-ACCESS  read-only
    STATUS      current
    DESCRIPTION
        "Fiber of Optical Interface - Provision, Reference to FIBER__INVENTORY"
    ::=  { plugEntry 8 }

plugTransmitChannel OBJECT-TYPE
    SYNTAX      FspR7ChannelIdentifier
    MAX-ACCESS  read-create
    STATUS      current
    DESCRIPTION
        "Channel"
    ::=  { plugEntry 9 }

plugAlias OBJECT-TYPE
    SYNTAX      SnmpAdminString
    MAX-ACCESS  read-create
    STATUS      current
    DESCRIPTION
        "User Applied Descriptor"
    ::=  { plugEntry 10 }

plugLaneGroup OBJECT-TYPE
    SYNTAX      FspR7LaneGroupInventory
    MAX-ACCESS  read-create
    STATUS      current
    DESCRIPTION
        "Lane group to provision"
    ::=  { plugEntry 11 }

plugMaxDataRate OBJECT-TYPE
    SYNTAX      FspR7PlugDataRate
    MAX-ACCESS  read-create
    STATUS      current
    DESCRIPTION
        "Rate"
    ::=  { plugEntry 12 }

plugThirdPartyUsage OBJECT-TYPE
    SYNTAX      EnableState
    MAX-ACCESS  read-create
    STATUS      current
    DESCRIPTION
        "Usage of 3rd Party Plugs"
    ::=  { plugEntry 13 }

plugAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { plugEntry 14 }

plugSecondaryStates OBJECT-TYPE
    SYNTAX      FspR7EntitySecondaryStates
    MAX-ACCESS  read-only
    STATUS      current
    DESCRIPTION
        "Secondary States"
    ::=  { plugEntry 15 }

plugOperState OBJECT-TYPE
    SYNTAX      FspR7OperState
    MAX-ACCESS  read-only
    STATUS      current
    DESCRIPTION
        "The Operational State will be displayed on the
         GUI with full name values; it will be differently
         displayed in TL1 syntax according to TL1 display rules."
    ::=  { plugEntry 16 }

plugBidirectionalChannel OBJECT-TYPE
    SYNTAX      FspR7BidirectionalChannel
    MAX-ACCESS  read-create
    STATUS      current
    DESCRIPTION
        "Bidirectional Channel Rates from Provisioning"
    ::=  { plugEntry 17 }

plugChannelSpacingProvision OBJECT-TYPE
    SYNTAX      FspR7ChannelSpacing
    MAX-ACCESS  read-create
    STATUS      current
    DESCRIPTION
        "Channel Space Provision, reference to CHA-SPC__INVENTORY"
    ::=  { plugEntry 18 }

endOfPlugTable OBJECT-TYPE
    SYNTAX      Integer32
    MAX-ACCESS  read-only
    STATUS      current
    DESCRIPTION
        ""
    ::=  { eqptMgmt 6 }

moduleTable OBJECT-TYPE
    SYNTAX      SEQUENCE OF ModuleEntry
    MAX-ACCESS  not-accessible
    STATUS      current
    DESCRIPTION   "moduleTable"
    ::=  { eqptMgmt 7 }

moduleEntry OBJECT-TYPE
    SYNTAX      ModuleEntry
    MAX-ACCESS  not-accessible
    STATUS      current
    DESCRIPTION   "Entry of moduleTable"
    INDEX       {
                  entityEqptShelfNo,
                  entityEqptSlotNo,
                  entityEqptPortNo,
                  entityEqptExtNo,
                  entityEqptClassName
                }
    ::=  { moduleTable 1 }

ModuleEntry ::=  SEQUENCE
  { moduleRowStatus RowStatus,
    moduleForceDestroy FspR7ForcedStatus,
    moduleCategory FspR7Category,
    moduleNetworkPorts Unsigned32,
    moduleInternalPlugs FspR7EquipmentTypeCaps,
    modulePsuOutputPower FspR7PsuOutputPower,
    moduleWidth Unsigned32,
    modulePower FspR7EdfaOutputPowerRating,
    moduleReach FspR7OpticalInterfaceReach,
    moduleInitEqlz FspR7InitEqualization,
    moduleSuppClientPlugTypes FspR7EquipmentTypeCaps,
    moduleSuppNetworkPlugTypes FspR7EquipmentTypeCaps,
    moduleLanAid SnmpAdminString,
    moduleType FspR7EquipmentType,
    moduleMapping FspR7Mapping,
    moduleGainRange FspR7GainRange,
    moduleInternalPlugRates FspR7PlugDataRateCaps,
    moduleSfProvision FspR7SingleFiberLocation,
    moduleInternalPlugsReach FspR7OpticalInterfaceReachCaps,
    moduleCapabilityLevelProvision FspR7CapInventory,
    moduleConnector FspR7ConnectorType,
    moduleDCFiberType FspR7DCFiberType,
    moduleChannelsProvision FspR7NumberOfChannelsProv,
    moduleFiberDetect FspR7FiberDetect,
    moduleDescription SnmpAdminString,
    moduleSupply FspR7SupplyType,
    moduleSuppClientPlugRates FspR7PlugDataRateCaps,
    moduleClientPorts Unsigned32,
    moduleGroup FspR7OpticalGroup,
    moduleDeploy FspR7DeploymentScenario,
    moduleLagSysPrio Unsigned32,
    moduleMaxPowerConsumption Unsigned32,
    moduleTransmitChannel FspR7ChannelIdentifier,
    moduleBand FspR7OpticalBand,
    moduleUpgradePorts Unsigned32,
    moduleTrafficDirection FspR7TrafficDirection,
    moduleMidstagePorts Unsigned32,
    moduleStages FspR7Stages,
    moduleIpAddr IpAddress,
    moduleDispersionCompensation FspR7DispersionCompensation,
    moduleActivateDetect FspR7YesNo,
    moduleOscUsage FspR7OscUsage,
    moduleInternalPorts Unsigned32,
    moduleAdmin FspR7AdminState,
    moduleScrambling FspR7Scrambling,
    moduleTerminationType FspR7EquipmentType,
    moduleChannelsNumber FspR7NumberOfChannels,
    moduleLanPorts Unsigned32,
    moduleChannelSpacingProvision FspR7ChannelSpacing,
    moduleMode FspR7TransmissionMode,
    moduleEccPorts Unsigned32,
    moduleSubBandProvision FspR7OpticalSubBand,
    moduleSuppNetworkPlugRates FspR7PlugDataRateCaps,
    moduleHeight Unsigned32,
    moduleAlias SnmpAdminString,
    moduleFiberType FspR7OpticalFiberType,
    moduleChannelSpacing FspR7ChannelSpacing,
    moduleOutputReset FspR7TifOutputReset,
    moduleSerialPorts Unsigned32,
    moduleRoadmNumber FspR7RoadmNumber,
    moduleSecondaryStates FspR7EntitySecondaryStates,
    moduleOperState FspR7OperState,
    moduleAlsConf FspR7EnableDisable,
    moduleTopologyType FspR7TopologyType,
    moduleScuRing FspR7ScuRing,
    moduleNodeIpAddress SnmpAdminString,
    moduleInventoryDescription SnmpAdminString,
    moduleGenericPlugRates FspR7PlugDataRateCaps,
    moduleTopology FspR7Topology,
    moduleForceConfig FspR7ForceConfig,
    moduleRamUsage Unsigned32,
    moduleFanMode FspR7FanMode,
    moduleMuxMethod FspR7MuxMethod,
    moduleNdpCleanup FspR7NdpCleanup,
    moduleAvlndpGbeTxcrs Unsigned32,
    moduleAvlndpGbeRxcrs Unsigned32,
    moduleAvlndpF125Txcrs Unsigned32,
    moduleAvlndpF125Rxcrs Unsigned32,
    moduleAvlndpF270Txcrs Unsigned32,
    moduleAvlndpF270Rxcrs Unsigned32,
    moduleAvlndpF1483Txcrs Unsigned32,
    moduleAvlndpF1483Rxcrs Unsigned32,
    moduleAvlndpF1485Txcrs Unsigned32,
    moduleAvlndpF1485Rxcrs Unsigned32,
    moduleAvlndpF2967Txcrs Unsigned32,
    moduleAvlndpF2967Rxcrs Unsigned32,
    moduleAvlndpF2970Txcrs Unsigned32,
    moduleAvlndpF2970Rxcrs Unsigned32,
    moduleAvlmdp Unsigned32,
    moduleRstp FspR7EnableDisable,
    moduleRemoteReset FspR7RlsMan }

moduleRowStatus OBJECT-TYPE
    SYNTAX      RowStatus
    MAX-ACCESS  read-create
    STATUS      current
    DESCRIPTION   "RowStatus object is used to create or delete a row in the table."
    ::=  { moduleEntry 1 }

moduleForceDestroy OBJECT-TYPE
    SYNTAX      FspR7ForcedStatus
    MAX-ACCESS  read-create
    STATUS      current
    DESCRIPTION
        "Forced Destroy"
    ::=  { moduleEntry 2 }

moduleCategory OBJECT-TYPE
    SYNTAX      FspR7Category
    MAX-ACCESS  read-only
    STATUS      current
    DESCRIPTION
        "Used For Internal Purposes (and possibly for pre-selection in GUI)"
    ::=  { moduleEntry 3 }

moduleNetworkPorts OBJECT-TYPE
    SYNTAX      Unsigned32
    MAX-ACCESS  read-only
    STATUS      current
    DESCRIPTION
        "Number of Network Ports"
    ::=  { moduleEntry 4 }

moduleInternalPlugs OBJECT-TYPE
    SYNTAX      FspR7EquipmentTypeCaps
    MAX-ACCESS  read-only
    STATUS      current
    DESCRIPTION
        "Internal Plugs Required"
    ::=  { moduleEntry 5 }

modulePsuOutputPower OBJECT-TYPE
    SYNTAX      FspR7PsuOutputPower
    MAX-ACCESS  read-create
    STATUS      current
    DESCRIPTION
        "Maximum PSU Output Power"
    ::=  { moduleEntry 6 }

moduleWidth OBJECT-TYPE
    SYNTAX      Unsigned32
    UNITS       "0.1 HP"
    MAX-ACCESS  read-only
    STATUS      current
    DESCRIPTION
        "Module Width"
    ::=  { moduleEntry 7 }

modulePower OBJECT-TYPE
    SYNTAX      FspR7EdfaOutputPowerRating
    MAX-ACCESS  read-create
    STATUS      current
    DESCRIPTION
        "Optical Output Power Rating - Provision"
    ::=  { moduleEntry 8 }

moduleReach OBJECT-TYPE
    SYNTAX      FspR7OpticalInterfaceReach
    MAX-ACCESS  read-create
    STATUS      current
    DESCRIPTION
        "Reach"
    ::=  { moduleEntry 9 }

moduleInitEqlz OBJECT-TYPE
    SYNTAX      FspR7InitEqualization
    MAX-ACCESS  read-write
    STATUS      current
    DESCRIPTION
        "Initiate Equalization"
    ::=  { moduleEntry 10 }

moduleSuppClientPlugTypes OBJECT-TYPE
    SYNTAX      FspR7EquipmentTypeCaps
    MAX-ACCESS  read-only
    STATUS      current
    DESCRIPTION
        "List of Client Plugs Supported"
    ::=  { moduleEntry 11 }

moduleSuppNetworkPlugTypes OBJECT-TYPE
    SYNTAX      FspR7EquipmentTypeCaps
    MAX-ACCESS  read-only
    STATUS      current
    DESCRIPTION
        "Network Plugs Required"
    ::=  { moduleEntry 12 }

moduleLanAid OBJECT-TYPE
    SYNTAX      SnmpAdminString
    MAX-ACCESS  read-create
    STATUS      current
    DESCRIPTION
        "AID of LAN"
    ::=  { moduleEntry 13 }

moduleType OBJECT-TYPE
    SYNTAX      FspR7EquipmentType
    MAX-ACCESS  read-create
    STATUS      current
    DESCRIPTION
        "The TYPE of Equipment and the MODE setting determine uniquely the number and allowed TYPE's of the provisionable dependent entities (plugs, interfaces, modules)"
    ::=  { moduleEntry 14 }

moduleMapping OBJECT-TYPE
    SYNTAX      FspR7Mapping
    MAX-ACCESS  read-create
    STATUS      current
    DESCRIPTION
        "Type of mapping; transparent or framing"
    ::=  { moduleEntry 15 }

moduleGainRange OBJECT-TYPE
    SYNTAX      FspR7GainRange
    MAX-ACCESS  read-create
    STATUS      current
    DESCRIPTION
        "EDFA gain range to provision"
    ::=  { moduleEntry 16 }

moduleInternalPlugRates OBJECT-TYPE
    SYNTAX      FspR7PlugDataRateCaps
    MAX-ACCESS  read-only
    STATUS      current
    DESCRIPTION
        "List of Provisionable Internal Plug Rates Supported"
    ::=  { moduleEntry 17 }

moduleSfProvision OBJECT-TYPE
    SYNTAX      FspR7SingleFiberLocation
    MAX-ACCESS  read-create
    STATUS      current
    DESCRIPTION
        "determines the location (A or B) for Single Fiber applications"
    ::=  { moduleEntry 18 }

moduleInternalPlugsReach OBJECT-TYPE
    SYNTAX      FspR7OpticalInterfaceReachCaps
    MAX-ACCESS  read-only
    STATUS      current
    DESCRIPTION
        "Reach of Internal Plugs"
    ::=  { moduleEntry 19 }

moduleCapabilityLevelProvision OBJECT-TYPE
    SYNTAX      FspR7CapInventory
    MAX-ACCESS  read-create
    STATUS      current
    DESCRIPTION
        "Capability level provisioned"
    ::=  { moduleEntry 20 }

moduleConnector OBJECT-TYPE
    SYNTAX      FspR7ConnectorType
    MAX-ACCESS  read-only
    STATUS      current
    DESCRIPTION
        "Connector Type"
    ::=  { moduleEntry 21 }

moduleDCFiberType OBJECT-TYPE
    SYNTAX      FspR7DCFiberType
    MAX-ACCESS  read-create
    STATUS      current
    DESCRIPTION
        "Dispersion Compensation Fibertype"
    ::=  { moduleEntry 22 }

moduleChannelsProvision OBJECT-TYPE
    SYNTAX      FspR7NumberOfChannelsProv
    MAX-ACCESS  read-create
    STATUS      current
    DESCRIPTION
        "Number of channels supported by an entity"
    ::=  { moduleEntry 23 }

moduleFiberDetect OBJECT-TYPE
    SYNTAX      FspR7FiberDetect
    MAX-ACCESS  read-create
    STATUS      current
    DESCRIPTION
        "Fiber Detect"
    ::=  { moduleEntry 24 }

moduleDescription OBJECT-TYPE
    SYNTAX      SnmpAdminString
    MAX-ACCESS  read-only
    STATUS      current
    DESCRIPTION
        "Detailed description of capability level"
    ::=  { moduleEntry 25 }

moduleSupply OBJECT-TYPE
    SYNTAX      FspR7SupplyType
    MAX-ACCESS  read-create
    STATUS      current
    DESCRIPTION
        "The kind of power supply - provisioned value"
    ::=  { moduleEntry 26 }

moduleSuppClientPlugRates OBJECT-TYPE
    SYNTAX      FspR7PlugDataRateCaps
    MAX-ACCESS  read-only
    STATUS      current
    DESCRIPTION
        "List of Provisionable Client Plug Rates Supported"
    ::=  { moduleEntry 27 }

moduleClientPorts OBJECT-TYPE
    SYNTAX      Unsigned32 (0..96)
    MAX-ACCESS  read-only
    STATUS      current
    DESCRIPTION
        "Number of Client Ports"
    ::=  { moduleEntry 28 }

moduleGroup OBJECT-TYPE
    SYNTAX      FspR7OpticalGroup
    MAX-ACCESS  read-create
    STATUS      current
    DESCRIPTION
        "The Group of 4 DWDM channels or the Group of 4 CWDM channels"
    ::=  { moduleEntry 29 }

moduleDeploy OBJECT-TYPE
    SYNTAX      FspR7DeploymentScenario
    MAX-ACCESS  read-create
    STATUS      current
    DESCRIPTION
        "Describes how the card is applied related to a network scenario"
    ::=  { moduleEntry 30 }

moduleLagSysPrio OBJECT-TYPE
    SYNTAX      Unsigned32 (0..65535)
    MAX-ACCESS  read-create
    STATUS      current
    DESCRIPTION
        "Link Aggregation Group Actor System Priority Part of LAG ID"
    ::=  { moduleEntry 31 }

moduleMaxPowerConsumption OBJECT-TYPE
    SYNTAX      Unsigned32
    UNITS       "0.1 W"
    MAX-ACCESS  read-only
    STATUS      current
    DESCRIPTION
        "Maximum Power Consumption of the device"
    ::=  { moduleEntry 32 }

moduleTransmitChannel OBJECT-TYPE
    SYNTAX      FspR7ChannelIdentifier
    MAX-ACCESS  read-create
    STATUS      current
    DESCRIPTION
        "Channel"
    ::=  { moduleEntry 33 }

moduleBand OBJECT-TYPE
    SYNTAX      FspR7OpticalBand
    MAX-ACCESS  read-create
    STATUS      current
    DESCRIPTION   "The optical band of the module."
    ::=  { moduleEntry 34 }

moduleUpgradePorts OBJECT-TYPE
    SYNTAX      Unsigned32
    MAX-ACCESS  read-only
    STATUS      current
    DESCRIPTION
        "Number of Upgrade Ports"
    ::=  { moduleEntry 35 }

moduleTrafficDirection OBJECT-TYPE
    SYNTAX      FspR7TrafficDirection
    MAX-ACCESS  read-create
    STATUS      current
    DESCRIPTION
        "Traffic Direction"
    ::=  { moduleEntry 36 }

moduleMidstagePorts OBJECT-TYPE
    SYNTAX      Unsigned32
    MAX-ACCESS  read-only
    STATUS      current
    DESCRIPTION
        "Number of Midstage Ports"
    ::=  { moduleEntry 37 }

moduleStages OBJECT-TYPE
    SYNTAX      FspR7Stages
    MAX-ACCESS  read-only
    STATUS      current
    DESCRIPTION
        "Number of Stages"
    ::=  { moduleEntry 38 }

moduleIpAddr OBJECT-TYPE
    SYNTAX      IpAddress
    MAX-ACCESS  read-create
    STATUS      current
    DESCRIPTION
        "IP Address assigned to LAN IP Interface"
    ::=  { moduleEntry 39 }

moduleDispersionCompensation OBJECT-TYPE
    SYNTAX      FspR7DispersionCompensation
    MAX-ACCESS  read-create
    STATUS      current
    DESCRIPTION
        "Dispersion Compensation Value in km of SSMF fiber"
    ::=  { moduleEntry 40 }

moduleActivateDetect OBJECT-TYPE
    SYNTAX      FspR7YesNo
    MAX-ACCESS  read-write
    STATUS      current
    DESCRIPTION
        "Initialize Topology Detection"
    ::=  { moduleEntry 41 }

moduleOscUsage OBJECT-TYPE
    SYNTAX      FspR7OscUsage
    MAX-ACCESS  read-create
    STATUS      current
    DESCRIPTION
        "Select if and how the OSC is to be used on an amplifier"
    ::=  { moduleEntry 42 }

moduleInternalPorts OBJECT-TYPE
    SYNTAX      Unsigned32
    MAX-ACCESS  read-only
    STATUS      current
    DESCRIPTION
        "Number of Internal Ports"
    ::=  { moduleEntry 43 }

moduleAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { moduleEntry 44 }

moduleScrambling OBJECT-TYPE
    SYNTAX      FspR7Scrambling
    MAX-ACCESS  read-create
    STATUS      current
    DESCRIPTION
        "Configuration of scrambling functionality for Virtual Facilities"
    ::=  { moduleEntry 45 }

moduleTerminationType OBJECT-TYPE
    SYNTAX      FspR7EquipmentType
    MAX-ACCESS  read-only
    STATUS      current
    DESCRIPTION
        "Type of Physical Termination"
    ::=  { moduleEntry 46 }

moduleChannelsNumber OBJECT-TYPE
    SYNTAX      FspR7NumberOfChannels
    MAX-ACCESS  read-create
    STATUS      current
    DESCRIPTION
        "Number of channels supported by an entity"
    ::=  { moduleEntry 47 }

moduleLanPorts OBJECT-TYPE
    SYNTAX      Unsigned32 (0..20)
    MAX-ACCESS  read-only
    STATUS      current
    DESCRIPTION
        "Number of LAN Ports"
    ::=  { moduleEntry 48 }

moduleChannelSpacingProvision OBJECT-TYPE
    SYNTAX      FspR7ChannelSpacing
    MAX-ACCESS  read-create
    STATUS      current
    DESCRIPTION
        "Channel Space Provision, reference to CHA-SPC__INVENTORY"
    ::=  { moduleEntry 49 }

moduleMode OBJECT-TYPE
    SYNTAX      FspR7TransmissionMode
    MAX-ACCESS  read-create
    STATUS      current
    DESCRIPTION
        "Mode of the module, determine operation or functionality"
    ::=  { moduleEntry 50 }

moduleEccPorts OBJECT-TYPE
    SYNTAX      Unsigned32 (0..20)
    MAX-ACCESS  read-only
    STATUS      current
    DESCRIPTION
        "Number of PPP over ECC Ports"
    ::=  { moduleEntry 51 }

moduleSubBandProvision OBJECT-TYPE
    SYNTAX      FspR7OpticalSubBand
    MAX-ACCESS  read-create
    STATUS      current
    DESCRIPTION
        "Subband - Provision"
    ::=  { moduleEntry 52 }

moduleSuppNetworkPlugRates OBJECT-TYPE
    SYNTAX      FspR7PlugDataRateCaps
    MAX-ACCESS  read-only
    STATUS      current
    DESCRIPTION
        "List of Provisionable Network Plug Rates Supported"
    ::=  { moduleEntry 53 }

moduleHeight OBJECT-TYPE
    SYNTAX      Unsigned32
    UNITS       "0.1 HU"
    MAX-ACCESS  read-only
    STATUS      current
    DESCRIPTION
        "Module Height"
    ::=  { moduleEntry 54 }

moduleAlias OBJECT-TYPE
    SYNTAX      SnmpAdminString
    MAX-ACCESS  read-create
    STATUS      current
    DESCRIPTION
        "User Applied Descriptor"
    ::=  { moduleEntry 55 }

moduleFiberType OBJECT-TYPE
    SYNTAX      FspR7OpticalFiberType
    MAX-ACCESS  read-create
    STATUS      current
    DESCRIPTION
        "Fiber of Optical Interface - Provision, Reference to FIBER__INVENTORY"
    ::=  { moduleEntry 56 }

moduleChannelSpacing OBJECT-TYPE
    SYNTAX      FspR7ChannelSpacing
    MAX-ACCESS  read-create
    STATUS      current
    DESCRIPTION
        "ITU Grid channel spacing"
    ::=  { moduleEntry 57 }

moduleOutputReset OBJECT-TYPE
    SYNTAX      FspR7TifOutputReset
    MAX-ACCESS  read-write
    STATUS      current
    DESCRIPTION
        "Has the same function as the HW switch at the UTM board"
    ::=  { moduleEntry 58 }

moduleSerialPorts OBJECT-TYPE
    SYNTAX      Unsigned32 (0..2)
    MAX-ACCESS  read-only
    STATUS      current
    DESCRIPTION
        "Number of Serial Ports"
    ::=  { moduleEntry 59 }

moduleRoadmNumber OBJECT-TYPE
    SYNTAX      FspR7RoadmNumber
    MAX-ACCESS  read-create
    STATUS      current
    DESCRIPTION
        "Number for ROADM module typically associated with a Network Fiber or Degree"
    ::=  { moduleEntry 60 }

moduleSecondaryStates OBJECT-TYPE
    SYNTAX      FspR7EntitySecondaryStates
    MAX-ACCESS  read-only
    STATUS      current
    DESCRIPTION
        "Secondary States"
    ::=  { moduleEntry 61 }

moduleOperState OBJECT-TYPE
    SYNTAX      FspR7OperState
    MAX-ACCESS  read-only
    STATUS      current
    DESCRIPTION
        "The Operational State will be displayed on the
         GUI with full name values; it will be differently
         displayed in TL1 syntax according to TL1 display rules."
    ::=  { moduleEntry 62 }

moduleAlsConf OBJECT-TYPE
    SYNTAX      FspR7EnableDisable
    MAX-ACCESS  read-only
    STATUS      current
    DESCRIPTION   "Enables EDFA amplifiers to provision their LOS behavior as 'ALS enabled' or 'ALS disabled'."
    ::=  { moduleEntry 63 }

moduleTopologyType OBJECT-TYPE
    SYNTAX      FspR7TopologyType
    MAX-ACCESS  read-only
    STATUS      current
    DESCRIPTION
        "Monitored Topology Type"
    ::=  { moduleEntry 64 }

moduleScuRing OBJECT-TYPE
    SYNTAX      FspR7ScuRing
    MAX-ACCESS  read-only
    STATUS      current
    DESCRIPTION
        "SCU Interconnection"
    ::=  { moduleEntry 65 }

moduleNodeIpAddress OBJECT-TYPE
    SYNTAX      SnmpAdminString
    MAX-ACCESS  read-only
    STATUS      current
    DESCRIPTION
        "List of IP Addresses, Position of list is the internal NODE-ID in the ring"
    ::=  { moduleEntry 66 }

moduleInventoryDescription OBJECT-TYPE
    SYNTAX      SnmpAdminString
    MAX-ACCESS  read-only
    STATUS      current
    DESCRIPTION
        "Description string of capability level reported by hw"
    ::=  { moduleEntry 67 }

moduleGenericPlugRates OBJECT-TYPE
    SYNTAX      FspR7PlugDataRateCaps
    MAX-ACCESS  read-only
    STATUS      current
    DESCRIPTION
        "List of Provisionable Generic Plug Rates Supported"
    ::=  { moduleEntry 68 }

moduleTopology OBJECT-TYPE
    SYNTAX      FspR7Topology
    MAX-ACCESS  read-create
    STATUS      current
    DESCRIPTION
        "Shows the card topology in the NE"
    ::=  { moduleEntry 69 }

moduleForceConfig OBJECT-TYPE
    SYNTAX      FspR7ForceConfig
    MAX-ACCESS  read-write
    STATUS      current
    DESCRIPTION
        "Force cserver to send down configuration to module"
    ::=  { moduleEntry 70 }

moduleRamUsage OBJECT-TYPE
    SYNTAX      Unsigned32
    UNITS       "kByte"
    MAX-ACCESS  read-only
    STATUS      current
    DESCRIPTION
        "Device RAM Consumption"
    ::=  { moduleEntry 71 }

moduleFanMode OBJECT-TYPE
    SYNTAX      FspR7FanMode
    MAX-ACCESS  read-only
    STATUS      current
    DESCRIPTION
        "Required CEM fan speed"
    ::=  { moduleEntry 72 }

moduleMuxMethod OBJECT-TYPE
    SYNTAX      FspR7MuxMethod
    MAX-ACCESS  read-create
    STATUS      current
    DESCRIPTION
        "Selection of mux method"
    ::=  { moduleEntry 73 }

moduleNdpCleanup OBJECT-TYPE
    SYNTAX      FspR7NdpCleanup
    MAX-ACCESS  read-write
    STATUS      current
    DESCRIPTION
        "Cleanup Network Data Path allocation"
    ::=  { moduleEntry 74 }

moduleAvlndpGbeTxcrs OBJECT-TYPE
    SYNTAX      Unsigned32
    MAX-ACCESS  read-only
    STATUS      current
    DESCRIPTION
        "Availabel network data path for gigabit ethernet (GBE) services in TXRCS direction"
    ::=  { moduleEntry 75 }

moduleAvlndpGbeRxcrs OBJECT-TYPE
    SYNTAX      Unsigned32
    MAX-ACCESS  read-only
    STATUS      current
    DESCRIPTION
        "Availabel network data path for gigabit ethernet (GBE) services in RXRCS direction"
    ::=  { moduleEntry 76 }

moduleAvlndpF125Txcrs OBJECT-TYPE
    SYNTAX      Unsigned32
    MAX-ACCESS  read-only
    STATUS      current
    DESCRIPTION
        "Availabel network data path for F125 services in TXRCS direction"
    ::=  { moduleEntry 77 }

moduleAvlndpF125Rxcrs OBJECT-TYPE
    SYNTAX      Unsigned32
    MAX-ACCESS  read-only
    STATUS      current
    DESCRIPTION
        "Availabel network data path for F125 services in RXRCS direction"
    ::=  { moduleEntry 78 }

moduleAvlndpF270Txcrs OBJECT-TYPE
    SYNTAX      Unsigned32
    MAX-ACCESS  read-only
    STATUS      current
    DESCRIPTION
        "Availabel network data path for F270 services in TXRCS direction"
    ::=  { moduleEntry 79 }

moduleAvlndpF270Rxcrs OBJECT-TYPE
    SYNTAX      Unsigned32
    MAX-ACCESS  read-only
    STATUS      current
    DESCRIPTION
        "Availabel network data path for F270 services in RXRCS direction"
    ::=  { moduleEntry 80 }

moduleAvlndpF1483Txcrs OBJECT-TYPE
    SYNTAX      Unsigned32
    MAX-ACCESS  read-only
    STATUS      current
    DESCRIPTION
        "Availabel network data path for F1483 services in TXRCS direction"
    ::=  { moduleEntry 81 }

moduleAvlndpF1483Rxcrs OBJECT-TYPE
    SYNTAX      Unsigned32
    MAX-ACCESS  read-only
    STATUS      current
    DESCRIPTION
        "Availabel network data path for F1483 services in RXRCS direction"
    ::=  { moduleEntry 82 }

moduleAvlndpF1485Txcrs OBJECT-TYPE
    SYNTAX      Unsigned32
    MAX-ACCESS  read-only
    STATUS      current
    DESCRIPTION
        "Availabel network data path for F1485 services in TXRCS direction"
    ::=  { moduleEntry 83 }

moduleAvlndpF1485Rxcrs OBJECT-TYPE
    SYNTAX      Unsigned32
    MAX-ACCESS  read-only
    STATUS      current
    DESCRIPTION
        "Availabel network data path for F1485 services in RXRCS direction"
    ::=  { moduleEntry 84 }

moduleAvlndpF2967Txcrs OBJECT-TYPE
    SYNTAX      Unsigned32
    MAX-ACCESS  read-only
    STATUS      current
    DESCRIPTION
        "Availabel network data path for F2967 services in TXRCS direction"
    ::=  { moduleEntry 85 }

moduleAvlndpF2967Rxcrs OBJECT-TYPE
    SYNTAX      Unsigned32
    MAX-ACCESS  read-only
    STATUS      current
    DESCRIPTION
        "Availabel network data path for F2967 services in RXRCS direction"
    ::=  { moduleEntry 86 }

moduleAvlndpF2970Txcrs OBJECT-TYPE
    SYNTAX      Unsigned32
    MAX-ACCESS  read-only
    STATUS      current
    DESCRIPTION
        "Availabel network data path for F2970 services in TXRCS direction"
    ::=  { moduleEntry 87 }

moduleAvlndpF2970Rxcrs OBJECT-TYPE
    SYNTAX      Unsigned32
    MAX-ACCESS  read-only
    STATUS      current
    DESCRIPTION
        "Availabel network data path for F2970 services in RXRCS direction"
    ::=  { moduleEntry 88 }

moduleAvlmdp OBJECT-TYPE
    SYNTAX      Unsigned32
    MAX-ACCESS  read-only
    STATUS      current
    DESCRIPTION
        "There are up to 4 simultaneous monitor path"
    ::=  { moduleEntry 89 }

moduleRstp OBJECT-TYPE
    SYNTAX      FspR7EnableDisable
    MAX-ACCESS  read-create
    STATUS      current
    DESCRIPTION
        "Rapid spanning tree protocol"
    ::=  { moduleEntry 90 }

moduleRemoteReset OBJECT-TYPE
    SYNTAX      FspR7RlsMan
    MAX-ACCESS  read-write
    STATUS      current
    DESCRIPTION
        "Remote reset of module. This parameter will be available only on SH9HU and SH1HUPF shelves."
    ::=  { moduleEntry 91 }

endOfModuleTable OBJECT-TYPE
    SYNTAX      Integer32
    MAX-ACCESS  read-only
    STATUS      current
    DESCRIPTION
        ""
    ::=  { eqptMgmt 8 }

protectionCableTable OBJECT-TYPE
    SYNTAX      SEQUENCE OF ProtectionCableEntry
    MAX-ACCESS  not-accessible
    STATUS      current
    DESCRIPTION   "protectionCableTable"
    ::=  { eqptMgmt 9 }

protectionCableEntry OBJECT-TYPE
    SYNTAX      ProtectionCableEntry
    MAX-ACCESS  not-accessible
    STATUS      current
    DESCRIPTION   "Entry of protectionCableTable"
    INDEX       {
                  entityProtectionCableIndex1,
                  entityProtectionCableIndex2,
                  entityProtectionCableIndex3,
                  entityProtectionCableIndex4,
                  entityProtectionCableClassName
                }
    ::=  { protectionCableTable 1 }

ProtectionCableEntry ::=  SEQUENCE
  { protectionCableRowStatus RowStatus,
    protectionCableType FspR7YcableType }

protectionCableRowStatus OBJECT-TYPE
    SYNTAX      RowStatus
    MAX-ACCESS  read-create
    STATUS      current
    DESCRIPTION   "RowStatus object is used to create or delete a row in the table."
    ::=  { protectionCableEntry 1 }

protectionCableType OBJECT-TYPE
    SYNTAX      FspR7YcableType
    MAX-ACCESS  read-create
    STATUS      current
    DESCRIPTION
        "Type of Y-cable"
    ::=  { protectionCableEntry 2 }

endOfProtectionCableTable OBJECT-TYPE
    SYNTAX      Integer32
    MAX-ACCESS  read-only
    STATUS      current
    DESCRIPTION
        ""
    ::=  { eqptMgmt 10 }

filterCableTable OBJECT-TYPE
    SYNTAX      SEQUENCE OF FilterCableEntry
    MAX-ACCESS  not-accessible
    STATUS      current
    DESCRIPTION   "filterCableTable"
    ::=  { eqptMgmt 11 }

filterCableEntry OBJECT-TYPE
    SYNTAX      FilterCableEntry
    MAX-ACCESS  not-accessible
    STATUS      current
    DESCRIPTION   "Entry of filterCableTable"
    INDEX       {
                  entityFilterCableIndex1,
                  entityFilterCableIndex2,
                  entityFilterCableIndex3,
                  entityFilterCableIndex4,
                  entityFilterCableClassName
                }
    ::=  { filterCableTable 1 }

FilterCableEntry ::=  SEQUENCE
  { filterCableRowStatus RowStatus,
    filterCableType FspR7FltrCableType }

filterCableRowStatus OBJECT-TYPE
    SYNTAX      RowStatus
    MAX-ACCESS  read-create
    STATUS      current
    DESCRIPTION   "RowStatus object is used to create or delete a row in the table."
    ::=  { filterCableEntry 1 }

filterCableType OBJECT-TYPE
    SYNTAX      FspR7FltrCableType
    MAX-ACCESS  read-create
    STATUS      current
    DESCRIPTION
        "Filter Cable"
    ::=  { filterCableEntry 2 }

endOfFilterCableTable OBJECT-TYPE
    SYNTAX      Integer32
    MAX-ACCESS  read-only
    STATUS      current
    DESCRIPTION
        ""
    ::=  { eqptMgmt 12 }

endOfEqptMgmt OBJECT-TYPE
    SYNTAX      Integer32
    MAX-ACCESS  read-only
    STATUS      current
    DESCRIPTION
        ""
    ::=  { eqptMgmt 10000 }

physicalPortTable OBJECT-TYPE
    SYNTAX      SEQUENCE OF PhysicalPortEntry
    MAX-ACCESS  not-accessible
    STATUS      current
    DESCRIPTION   "physicalPortTable"
    ::=  { facilityMgmt 1 }

physicalPortEntry OBJECT-TYPE
    SYNTAX      PhysicalPortEntry
    MAX-ACCESS  not-accessible
    STATUS      current
    DESCRIPTION   "Entry of physicalPortTable"
    INDEX       {
                  entityFacilityShelfNo,
                  entityFacilitySlotNo,
                  entityFacilityPortNo,
                  entityFacilityExtNo,
                  entityFacilityClassName
                }
    ::=  { physicalPortTable 1 }

PhysicalPortEntry ::=  SEQUENCE
  { physicalPortRowStatus RowStatus,
    physicalPortType FspR7InterfaceType,
    physicalPortAdmin FspR7AdminState,
    physicalPortConnector FspR7ConnectorType,
    physicalPortFiber FspR7OpticalFiberType,
    physicalPortConnType FspR7TypeConnection,
    physicalPortOperState FspR7OperState,
    physicalPortLaneChannel FspR7ChannelIdentifier,
    physicalPortLaserBiasCurrLevel Unsigned32,
    physicalPortLaserTemp Integer32,
    physicalPortInputPower Integer32,
    physicalPortOutputPower Integer32,
    physicalPortSecondaryStates FspR7EntitySecondaryStates,
    physicalPortAlias SnmpAdminString,
    physicalPortAlsMode FspR7AlsMode,
    physicalPortAutoThresReset FspR7AutoThresReset,
    physicalPortAutonegotiation EnableState,
    physicalPortBand FspR7OpticalBand,
    physicalPortPhysIfBaseType FspR7InterfaceType,
    physicalPortConnState FspR7ConnectState,
    physicalPortBehaviour FspR7PortBehaviour,
    physicalPortRate Unsigned32,
    physicalPortBitrate FspR7Bitrate,
    physicalPortDispertionConfig FspR7DispersionConfig,
    physicalPortDispersionSetting Integer32,
    physicalPortDispersionMode FspR7DispersionModes,
    physicalPortChannelSpacing FspR7ChannelSpacing,
    physicalPortChannelProv FspR7ChannelIdentifier,
    physicalPortWdmRxChannel FspR7ChannelIdentifier,
    physicalPortCodeGain FspR7CodeGain,
    physicalPortXfpDecisionThres FspR7XfpDecisionThres,
    physicalPortDisparityCorrection EnableState,
    physicalPortDuplexMode EthDuplexMode,
    physicalPortEqlzAdmin FspR7EqlzAdminState,
    physicalPortErrorForwarding FspR7ErrorFwdMode,
    physicalPortFecType FspR7FecType,
    physicalPortFarEndCommunication FspR7YesNo,
    physicalPortFlowControl FspR7FlowControlMode,
    physicalPortForceLaserOn FspR7LaserForcedOperation,
    physicalPortFrequency Unsigned32,
    physicalPortReceiverFrequency Unsigned32,
    physicalPortInhibitSwitchToProt FspR7YesNo,
    physicalPortInhibitSwitchToWork FspR7YesNo,
    physicalPortTransmitWavelength Unsigned32,
    physicalPortReceiverWavelength Unsigned32,
    physicalPortLaneChannelSetting FspR7ChannelIdentifier,
    physicalPortLaneChannel1 FspR7ChannelIdentifier,
    physicalPortLaneChannel2 FspR7ChannelIdentifier,
    physicalPortLaneChannel3 FspR7ChannelIdentifier,
    physicalPortLaneChannel4 FspR7ChannelIdentifier,
    physicalPortLaneGroup FspR7LaneGroupInventory,
    physicalPortLoopConfig LoopConfig,
    physicalPortLaserDelayTimer FspR7LaserDelayTimer,
    physicalPortLaserOffTimer Unsigned32,
    physicalPortLaserOnTimer Unsigned32,
    physicalPortLaserOffDelayFunction EnableState,
    physicalPortMonLevel FspR7MonLevel,
    physicalPortSumTransmited Unsigned32,
    physicalPortAutoPTassignment FspR7ManualAuto,
    physicalPortTributarySlotMethod FspR7ManualAuto,
    physicalPortTributaryFreeSlotNo Unsigned32,
    physicalPortTributaryAssignedSlotNo Unsigned32,
    physicalPortInitiateEqualization FspR7InitEqualization,
    physicalPortLossAttenuation FspR7LossAttenuation,
    physicalPortOpticalSetPoint Integer32,
    physicalPortDataLayerPmReset FspR7PmReset,
    physicalPortPrbsPmReset FspR7PrbsPmReset,
    physicalPortTestPrbsRcvMode FspR7PRBSTest,
    physicalPortTestPrbsTrmtMode FspR7PRBSTest,
    physicalPortSwitchCommand FspR7APSCommand,
    physicalPortOpuPayloadType FspR7OpuPayloadType,
    physicalPortReach FspR7OpticalInterfaceReach,
    physicalPortSigDegThresSonetLine FspR7BERThreshold,
    physicalPortSigDegThresSdhMs Unsigned32,
    physicalPortSigDegThresOtu Integer32,
    physicalPortSigDegThresOdu Integer32,
    physicalPortSigDegThreshold Unsigned32,
    physicalPortSigDegPcslThreshold Unsigned32,
    physicalPortSigDegThresSonetSection FspR7BERThresholdSection,
    physicalPortSigDegThresSdhSection Unsigned32,
    physicalPortSigDegThresOduTcmA Integer32,
    physicalPortSigDegThresOduTcmB Integer32,
    physicalPortSigDegThresOduTcmC Integer32,
    physicalPortSignalDegradePeriod Unsigned32,
    physicalPortSigDegPeriodOdu Unsigned32,
    physicalPortSigDegPeriodOtu Unsigned32,
    physicalPortSigDegPeriodIntegration Unsigned32,
    physicalPortSigDegPeriodSdhSection Unsigned32,
    physicalPortSigDegPeriodOduTcmA Unsigned32,
    physicalPortSigDegPeriodOduTcmB Unsigned32,
    physicalPortSigDegPeriodOduTcmC Unsigned32,
    physicalPortOtnStuffing FspR7Stuff,
    physicalPortTcmALevel OtnTcmLevel,
    physicalPortTcmBLevel OtnTcmLevel,
    physicalPortTcmCLevel OtnTcmLevel,
    physicalPortTerminationLevel OhTerminationLevel,
    physicalPortTimingSource SonetTimingSource,
    physicalPortTimModeOdu TimMode,
    physicalPortTimModeOtu TimMode,
    physicalPortTimModeSonetSection TimMode,
    physicalPortTimModeOduTcmA TimMode,
    physicalPortTimModeOduTcmB TimMode,
    physicalPortTimModeOduTcmC TimMode,
    physicalPortTraceFormSonetSection SonetTraceForm,
    physicalPortTraceExpectedSonetSection OCTET STRING,
    physicalPortTraceTransmitSonetSection OCTET STRING,
    physicalPortTraceExpectedOtu OCTET STRING,
    physicalPortTraceTransmitSapiOtu OCTET STRING,
    physicalPortTraceTransmitDapiOtu OCTET STRING,
    physicalPortTraceTransmitOpspOtu OCTET STRING,
    physicalPortTraceExpectedOdu OCTET STRING,
    physicalPortTraceTransmitSapiOdu OCTET STRING,
    physicalPortTraceTransmitDapiOdu OCTET STRING,
    physicalPortTraceTransmitOpspOdu OCTET STRING,
    physicalPortTraceExpectedOduTcmA OCTET STRING,
    physicalPortTraceTransmitSapiOduTcmA OCTET STRING,
    physicalPortTraceTransmitDapiOduTcmA OCTET STRING,
    physicalPortTraceTransmitOpspOduTcmA OCTET STRING,
    physicalPortTraceExpectedOduTcmB OCTET STRING,
    physicalPortTraceTransmitSapiOduTcmB OCTET STRING,
    physicalPortTraceTransmitDapiOduTcmB OCTET STRING,
    physicalPortTraceTransmitOpspOduTcmB OCTET STRING,
    physicalPortTraceExpectedOduTcmC OCTET STRING,
    physicalPortTraceTransmitSapiOduTcmC OCTET STRING,
    physicalPortTraceTransmitDapiOduTcmC OCTET STRING,
    physicalPortTraceTransmitOpspOduTcmC OCTET STRING,
    physicalPortTraceRcvSapiOdu OCTET STRING,
    physicalPortTraceRcvDapiOdu OCTET STRING,
    physicalPortTraceRcvOpspOdu OCTET STRING,
    physicalPortTraceRcvSapiOtu OCTET STRING,
    physicalPortTraceRcvDapiOtu OCTET STRING,
    physicalPortTraceRcvOpspOtu OCTET STRING,
    physicalPortTraceRcvSapiTcma OCTET STRING,
    physicalPortTraceRcvDapiTcma OCTET STRING,
    physicalPortTraceRcvOpspTcma OCTET STRING,
    physicalPortTraceRcvSapiTcmb OCTET STRING,
    physicalPortTraceRcvDapiTcmb OCTET STRING,
    physicalPortTraceRcvOpspTcmb OCTET STRING,
    physicalPortTraceRcvSapiTcmc OCTET STRING,
    physicalPortTraceRcvDapiTcmc OCTET STRING,
    physicalPortTraceRcvOpspTcmc OCTET STRING,
    physicalPortTraceReceived OCTET STRING,
    physicalPortTurnupConfig FspR7TurnupConfig,
    physicalPortTxOffDelay FspR7EnableDisable,
    physicalPortVoaMode FspR7VoaMode,
    physicalPortVoaSetpoint Unsigned32,
    physicalPortCbsRcv Unsigned32,
    physicalPortCbsTrmt Unsigned32,
    physicalPortCirRcv Unsigned32,
    physicalPortCirTrmt Unsigned32,
    physicalPortLagPrio Unsigned32,
    physicalPortMacAddress MacAddress,
    physicalPortMaxFrameSize Unsigned32,
    physicalPortPayload OtnPayloadType,
    physicalPortPortMode FspR7PortMode,
    physicalPortPortRole FspR7PortRole,
    physicalPortPriority Unsigned32,
    physicalPortPvid Unsigned32,
    physicalPortStagType FspR7SnmpHexString,
    physicalPortUtag FspR7UntaggedFrames,
    physicalPortVethAid SnmpAdminString,
    physicalPortChannelBandwith FspR7ChannelBandwidth,
    physicalPortFacilities SnmpAdminString,
    physicalPortLanes FspR7OpticalLanes,
    physicalPortProtectionRole FspR7ProtectionRole,
    physicalPortMonitoredBitrate Unsigned32,
    physicalPortLagState FspR7LagState,
    physicalPortLagIdFend FspR7LagIdFend,
    physicalPortLagFendState FspR7LagFendState,
    physicalPortLagPortNo Unsigned32,
    physicalPortLagKey Unsigned32,
    physicalPortValidSigTimer Unsigned32,
    physicalPortLaserReleaseTimer Unsigned32,
    physicalPortBidirectionalChannel FspR7BidirectionalChannel,
    physicalPortTransmitterWavelength Unsigned32,
    physicalPortTransmitterFrequency Unsigned32,
    physicalPortRedLineState FspR7RedLinedState,
    physicalPortTunnelAid SnmpAdminString,
    physicalPortIngressTid SnmpAdminString,
    physicalPortIngressNodeIp IpAddress,
    physicalPortRateLimit FspR7DisableEnable,
    physicalPortPathProtection FspR7PathProt,
    physicalPortGropticsType FspR7GropticsType,
    physicalPortAvlntsTxcrs Unsigned32,
    physicalPortAvlntsRxcrs Unsigned32,
    physicalPortTxOffOnTm FspR7TxOffOnTm,
    physicalPortTxOffTimer Unsigned32,
    physicalPortTxOnTimer Unsigned32,
    physicalPortTrafficDirection FspR7TrafficDirection,
    physicalPortChannelSpacingProvision FspR7ChannelSpacing }

physicalPortRowStatus OBJECT-TYPE
    SYNTAX      RowStatus
    MAX-ACCESS  read-create
    STATUS      current
    DESCRIPTION   "RowStatus object is used to create or delete a row in the table."
    ::=  { physicalPortEntry 1 }

physicalPortType OBJECT-TYPE
    SYNTAX      FspR7InterfaceType
    MAX-ACCESS  read-create
    STATUS      current
    DESCRIPTION
        "The TYPE defines the transport service type as wrapper with wrapper layer termination OR else as payload"
    ::=  { physicalPortEntry 2 }

physicalPortAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { physicalPortEntry 3 }

physicalPortConnector OBJECT-TYPE
    SYNTAX      FspR7ConnectorType
    MAX-ACCESS  read-only
    STATUS      current
    DESCRIPTION
        "Connector Type"
    ::=  { physicalPortEntry 4 }

physicalPortFiber OBJECT-TYPE
    SYNTAX      FspR7OpticalFiberType
    MAX-ACCESS  read-only
    STATUS      current
    DESCRIPTION
        "Fiber of Optical Interface - Provision, Reference to FIBER__INVENTORY"
    ::=  { physicalPortEntry 5 }

physicalPortConnType OBJECT-TYPE
    SYNTAX      FspR7TypeConnection
    MAX-ACCESS  read-only
    STATUS      current
    DESCRIPTION
        "Connectivity Parameters for Facilities"
    ::=  { physicalPortEntry 6 }

physicalPortOperState OBJECT-TYPE
    SYNTAX      FspR7OperState
    MAX-ACCESS  read-only
    STATUS      current
    DESCRIPTION
        "The Operational State will be displayed on the
         GUI with full name values; it will be differently
         displayed in TL1 syntax according to TL1 display rules."
    ::=  { physicalPortEntry 7 }

physicalPortLaneChannel OBJECT-TYPE
    SYNTAX      FspR7ChannelIdentifier
    MAX-ACCESS  read-only
    STATUS      current
    DESCRIPTION
        "Lane Channel of OLT Entity on CFP plug"
    ::=  { physicalPortEntry 8 }

physicalPortLaserBiasCurrLevel OBJECT-TYPE
    SYNTAX      Unsigned32
    UNITS       "0.001 A"
    MAX-ACCESS  read-only
    STATUS      current
    DESCRIPTION
        "Laser Bias Current Level on demand"
    ::=  { physicalPortEntry 9 }

physicalPortLaserTemp OBJECT-TYPE
    SYNTAX      Integer32
    UNITS       "0.1 degree Celsius"
    MAX-ACCESS  read-only
    STATUS      current
    DESCRIPTION
        "Laser Temperature"
    ::=  { physicalPortEntry 10 }

physicalPortInputPower OBJECT-TYPE
    SYNTAX      Integer32
    UNITS       "0.1 dBm"
    MAX-ACCESS  read-only
    STATUS      deprecated
    DESCRIPTION
        "Total Optical Input Power Received"
    ::=  { physicalPortEntry 11 }

physicalPortOutputPower OBJECT-TYPE
    SYNTAX      Integer32
    UNITS       "0.1 dBm"
    MAX-ACCESS  read-only
    STATUS      deprecated
    DESCRIPTION
        "Instantaneous Optical Power Transmitted (Output)"
    ::=  { physicalPortEntry 12 }

physicalPortSecondaryStates OBJECT-TYPE
    SYNTAX      FspR7EntitySecondaryStates
    MAX-ACCESS  read-only
    STATUS      current
    DESCRIPTION
        "Secondary States"
    ::=  { physicalPortEntry 13 }

physicalPortAlias OBJECT-TYPE
    SYNTAX      SnmpAdminString
    MAX-ACCESS  read-create
    STATUS      current
    DESCRIPTION
        "User Applied Descriptor"
    ::=  { physicalPortEntry 14 }

physicalPortAlsMode OBJECT-TYPE
    SYNTAX      FspR7AlsMode
    MAX-ACCESS  read-create
    STATUS      current
    DESCRIPTION
        "Determines the reaction in backward direction in response to a LOS
         on the same Interface: on a Network Interface connected to the DWDM
         this is a matter of laser safety"
    ::=  { physicalPortEntry 15 }

physicalPortAutoThresReset OBJECT-TYPE
    SYNTAX      FspR7AutoThresReset
    MAX-ACCESS  read-write
    STATUS      current
    DESCRIPTION
        "Adaptive Threshold Control Reset"
    ::=  { physicalPortEntry 16 }

physicalPortAutonegotiation OBJECT-TYPE
    SYNTAX      EnableState
    MAX-ACCESS  read-create
    STATUS      current
    DESCRIPTION
        "Auto Negotiation for the data rate"
    ::=  { physicalPortEntry 17 }

physicalPortBand OBJECT-TYPE
    SYNTAX      FspR7OpticalBand
    MAX-ACCESS  read-only
    STATUS      current
    DESCRIPTION
        "Band Provision. Reference to BAND__INVENTORY."
    ::=  { physicalPortEntry 18 }

physicalPortPhysIfBaseType OBJECT-TYPE
    SYNTAX      FspR7InterfaceType
    MAX-ACCESS  read-only
    STATUS      current
    DESCRIPTION
        "The type of the physical interface. Will be nedded for LANIP interfaces to deliver information about the BASE facility type."
    ::=  { physicalPortEntry 19 }

physicalPortConnState OBJECT-TYPE
    SYNTAX      FspR7ConnectState
    MAX-ACCESS  read-only
    STATUS      current
    DESCRIPTION
        "Connection State"
    ::=  { physicalPortEntry 20 }

physicalPortBehaviour OBJECT-TYPE
    SYNTAX      FspR7PortBehaviour
    MAX-ACCESS  read-create
    STATUS      current
    DESCRIPTION
        "Behavior or Port usage based on configuration/usage in the system regardless of faceplate designation"
    ::=  { physicalPortEntry 21 }

physicalPortRate OBJECT-TYPE
    SYNTAX      Unsigned32
    UNITS       "Mbps"
    MAX-ACCESS  read-only
    STATUS      current
    DESCRIPTION
        "Derived from TYPE and possibly PAYLOAD"
    ::=  { physicalPortEntry 22 }

physicalPortBitrate OBJECT-TYPE
    SYNTAX      FspR7Bitrate
    MAX-ACCESS  read-only
    STATUS      current
    DESCRIPTION
        "Provisioned data rate"
    ::=  { physicalPortEntry 23 }

physicalPortDispertionConfig OBJECT-TYPE
    SYNTAX      FspR7DispersionConfig
    MAX-ACCESS  read-write
    STATUS      current
    DESCRIPTION
        "Chromatic Dispersion Compensation"
    ::=  { physicalPortEntry 24 }

physicalPortDispersionSetting OBJECT-TYPE
    SYNTAX      Integer32 (-50000..50000)
    UNITS       "ps/nm"
    MAX-ACCESS  read-create
    STATUS      current
    DESCRIPTION
        "Chromatic Dispersion Compensation setting on module"
    ::=  { physicalPortEntry 25 }

physicalPortDispersionMode OBJECT-TYPE
    SYNTAX      FspR7DispersionModes
    MAX-ACCESS  read-create
    STATUS      current
    DESCRIPTION
        "Chromatic Dispersion Compensation Mode"
    ::=  { physicalPortEntry 26 }

physicalPortChannelSpacing OBJECT-TYPE
    SYNTAX      FspR7ChannelSpacing
    MAX-ACCESS  read-only
    STATUS      current
    DESCRIPTION
        "ITU Grid channel spacing"
    ::=  { physicalPortEntry 27 }

physicalPortChannelProv OBJECT-TYPE
    SYNTAX      FspR7ChannelIdentifier
    MAX-ACCESS  read-create
    STATUS      current
    DESCRIPTION
        "Channel"
    ::=  { physicalPortEntry 28 }

physicalPortWdmRxChannel OBJECT-TYPE
    SYNTAX      FspR7ChannelIdentifier
    MAX-ACCESS  read-create
    STATUS      current
    DESCRIPTION
        "Configuration of Rx optical channel"
    ::=  { physicalPortEntry 29 }

physicalPortCodeGain OBJECT-TYPE
    SYNTAX      FspR7CodeGain
    MAX-ACCESS  read-create
    STATUS      current
    DESCRIPTION
        "Forward Error Correction Coding gain"
    ::=  { physicalPortEntry 30 }

physicalPortXfpDecisionThres OBJECT-TYPE
    SYNTAX      FspR7XfpDecisionThres
    MAX-ACCESS  read-create
    STATUS      current
    DESCRIPTION
        "XFP Decision threshold setting"
    ::=  { physicalPortEntry 31 }

physicalPortDisparityCorrection OBJECT-TYPE
    SYNTAX      EnableState
    MAX-ACCESS  read-create
    STATUS      current
    DESCRIPTION
        "Disparity correction"
    ::=  { physicalPortEntry 32 }

physicalPortDuplexMode OBJECT-TYPE
    SYNTAX      EthDuplexMode
    MAX-ACCESS  read-only
    STATUS      current
    DESCRIPTION
        "Duplex Mode Provision."
    ::=  { physicalPortEntry 33 }

physicalPortEqlzAdmin OBJECT-TYPE
    SYNTAX      FspR7EqlzAdminState
    MAX-ACCESS  read-create
    STATUS      current
    DESCRIPTION
        "Scheduled Equalization Administration"
    ::=  { physicalPortEntry 34 }

physicalPortErrorForwarding OBJECT-TYPE
    SYNTAX      FspR7ErrorFwdMode
    MAX-ACCESS  read-create
    STATUS      current
    DESCRIPTION
        "Determines the reaction in forward direction in response to a LOS on
         the interface on the opposite side of the module: may override
         this behaviour in the interests of laser safety."
    ::=  { physicalPortEntry 35 }

physicalPortFecType OBJECT-TYPE
    SYNTAX      FspR7FecType
    MAX-ACCESS  read-create
    STATUS      current
    DESCRIPTION
        "Forward Error Correction (Only relevant where TYPE = OTU#)"
    ::=  { physicalPortEntry 36 }

physicalPortFarEndCommunication OBJECT-TYPE
    SYNTAX      FspR7YesNo
    MAX-ACCESS  read-create
    STATUS      current
    DESCRIPTION
        "Used for Optojack plugs; Communication to Far End Plug is observed"
    ::=  { physicalPortEntry 37 }

physicalPortFlowControl OBJECT-TYPE
    SYNTAX      FspR7FlowControlMode
    MAX-ACCESS  read-create
    STATUS      current
    DESCRIPTION
        "Flow Control mechanism"
    ::=  { physicalPortEntry 38 }

physicalPortForceLaserOn OBJECT-TYPE
    SYNTAX      FspR7LaserForcedOperation
    MAX-ACCESS  read-write
    STATUS      current
    DESCRIPTION
        "Laser Forced On"
    ::=  { physicalPortEntry 39 }

physicalPortFrequency OBJECT-TYPE
    SYNTAX      Unsigned32
    UNITS       "0.01 THz"
    MAX-ACCESS  read-only
    STATUS      current
    DESCRIPTION
        "Frequency of Optical Interface (unit: nm)"
    ::=  { physicalPortEntry 40 }

physicalPortReceiverFrequency OBJECT-TYPE
    SYNTAX      Unsigned32
    UNITS       "0.01 THz"
    MAX-ACCESS  read-only
    STATUS      current
    DESCRIPTION
        "Receiver Frequency of Optical Interface (unit: nm)"
    ::=  { physicalPortEntry 41 }

physicalPortInhibitSwitchToProt OBJECT-TYPE
    SYNTAX      FspR7YesNo
    MAX-ACCESS  read-write
    STATUS      current
    DESCRIPTION   "Inhibit Switch to protection facility. Inhibition blocks an automatic switch
         to the protection facility. Valid only for the working facility."
    ::=  { physicalPortEntry 42 }

physicalPortInhibitSwitchToWork OBJECT-TYPE
    SYNTAX      FspR7YesNo
    MAX-ACCESS  read-write
    STATUS      current
    DESCRIPTION   "Inhibit Switch to working facility. Inhibition blocks an automatic switch to the
         working facility. Valid only for the protection facility."
    ::=  { physicalPortEntry 43 }

physicalPortTransmitWavelength OBJECT-TYPE
    SYNTAX      Unsigned32
    UNITS       "0.01 nm"
    MAX-ACCESS  read-only
    STATUS      current
    DESCRIPTION
        "Wavelength of Optical Interface (unit: nm)"
    ::=  { physicalPortEntry 44 }

physicalPortReceiverWavelength OBJECT-TYPE
    SYNTAX      Unsigned32
    UNITS       "0.01 nm"
    MAX-ACCESS  read-only
    STATUS      current
    DESCRIPTION
        "Receiver Wavelength of Optical Interface (unit: nm)"
    ::=  { physicalPortEntry 45 }

physicalPortLaneChannelSetting OBJECT-TYPE
    SYNTAX      FspR7ChannelIdentifier
    MAX-ACCESS  read-create
    STATUS      current
    DESCRIPTION
        "Lane Channel Setting"
    ::=  { physicalPortEntry 46 }

physicalPortLaneChannel1 OBJECT-TYPE
    SYNTAX      FspR7ChannelIdentifier
    MAX-ACCESS  read-only
    STATUS      current
    DESCRIPTION
        "Lane Channel"
    ::=  { physicalPortEntry 47 }

physicalPortLaneChannel2 OBJECT-TYPE
    SYNTAX      FspR7ChannelIdentifier
    MAX-ACCESS  read-only
    STATUS      current
    DESCRIPTION
        "Lane Channel"
    ::=  { physicalPortEntry 48 }

physicalPortLaneChannel3 OBJECT-TYPE
    SYNTAX      FspR7ChannelIdentifier
    MAX-ACCESS  read-only
    STATUS      current
    DESCRIPTION
        "Lane Channel"
    ::=  { physicalPortEntry 49 }

physicalPortLaneChannel4 OBJECT-TYPE
    SYNTAX      FspR7ChannelIdentifier
    MAX-ACCESS  read-only
    STATUS      current
    DESCRIPTION
        "Lane Channel"
    ::=  { physicalPortEntry 50 }

physicalPortLaneGroup OBJECT-TYPE
    SYNTAX      FspR7LaneGroupInventory
    MAX-ACCESS  read-only
    STATUS      current
    DESCRIPTION
        "Lane group to provision"
    ::=  { physicalPortEntry 51 }

physicalPortLoopConfig OBJECT-TYPE
    SYNTAX      LoopConfig
    MAX-ACCESS  read-write
    STATUS      current
    DESCRIPTION   "The configuration of the loopback function.
         - noLoop: no loop configuration on the interface.
         - lineLoop: the incoming signal is looped to the outgoing
         line on the interface. The incoming signal is sent in the
         downstream direction and processed as normal.
         - inwardLoop: the output signal is looped to the incoming line
         on the interface. The looped signal is transmitted unchanged on
         the optical output."
    ::=  { physicalPortEntry 52 }

physicalPortLaserDelayTimer OBJECT-TYPE
    SYNTAX      FspR7LaserDelayTimer
    MAX-ACCESS  read-create
    STATUS      current
    DESCRIPTION
        "Relevant only when ERRFWD=LSROFF. Enables/disables the
         possibility to delay turning off and on the laser.
         This applies to the case when turning off the laser
         is done as an error forwarding mechanism."
    ::=  { physicalPortEntry 53 }

physicalPortLaserOffTimer OBJECT-TYPE
    SYNTAX      Unsigned32 (1..1000)
    UNITS       "ms"
    MAX-ACCESS  read-create
    STATUS      current
    DESCRIPTION
        "Delay before laser is swiched off"
    ::=  { physicalPortEntry 54 }

physicalPortLaserOnTimer OBJECT-TYPE
    SYNTAX      Unsigned32 (1..1000)
    UNITS       "ms"
    MAX-ACCESS  read-create
    STATUS      current
    DESCRIPTION
        "Delay before laser is switched on"
    ::=  { physicalPortEntry 55 }

physicalPortLaserOffDelayFunction OBJECT-TYPE
    SYNTAX      EnableState
    MAX-ACCESS  read-create
    STATUS      current
    DESCRIPTION   "A configuration request for the Laser Off Delay function. This function
         delays turning off the laser as a consequent action to a defect."
    ::=  { physicalPortEntry 56 }

physicalPortMonLevel OBJECT-TYPE
    SYNTAX      FspR7MonLevel
    MAX-ACCESS  read-only
    STATUS      current
    DESCRIPTION
        "Indicates the highest level of intrusive/non-intrusive performance monitoring performed."
    ::=  { physicalPortEntry 57 }

physicalPortSumTransmited OBJECT-TYPE
    SYNTAX      Unsigned32 (0..96)
    MAX-ACCESS  read-only
    STATUS      current
    DESCRIPTION
        "Sum of Transmitted Optical Channels Provisioned"
    ::=  { physicalPortEntry 58 }

physicalPortAutoPTassignment OBJECT-TYPE
    SYNTAX      FspR7ManualAuto
    MAX-ACCESS  read-create
    STATUS      current
    DESCRIPTION
        "Auto assignment of ODU PT"
    ::=  { physicalPortEntry 59 }

physicalPortTributarySlotMethod OBJECT-TYPE
    SYNTAX      FspR7ManualAuto
    MAX-ACCESS  read-create
    STATUS      current
    DESCRIPTION
        "Tributary Slot assignment method"
    ::=  { physicalPortEntry 60 }

physicalPortTributaryFreeSlotNo OBJECT-TYPE
    SYNTAX      Unsigned32 (0..512)
    MAX-ACCESS  read-only
    STATUS      current
    DESCRIPTION
        "Number of Tributary Slots which are available for assignment."
    ::=  { physicalPortEntry 61 }

physicalPortTributaryAssignedSlotNo OBJECT-TYPE
    SYNTAX      Unsigned32 (0..512)
    MAX-ACCESS  read-only
    STATUS      current
    DESCRIPTION
        "Number of Tributary Slots which have been assigned."
    ::=  { physicalPortEntry 62 }

physicalPortInitiateEqualization OBJECT-TYPE
    SYNTAX      FspR7InitEqualization
    MAX-ACCESS  read-write
    STATUS      current
    DESCRIPTION
        "Initiate Equalization"
    ::=  { physicalPortEntry 63 }

physicalPortLossAttenuation OBJECT-TYPE
    SYNTAX      FspR7LossAttenuation
    MAX-ACCESS  read-write
    STATUS      current
    DESCRIPTION
        "LOS Attenuation Finding in progress"
    ::=  { physicalPortEntry 64 }

physicalPortOpticalSetPoint OBJECT-TYPE
    SYNTAX      Integer32 (-250..50)
    UNITS       "0.1 dBm"
    MAX-ACCESS  read-create
    STATUS      current
    DESCRIPTION
        "Sets the optical power for power equalization in ROADM or for channel power control in OPCM"
    ::=  { physicalPortEntry 65 }

physicalPortDataLayerPmReset OBJECT-TYPE
    SYNTAX      FspR7PmReset
    MAX-ACCESS  read-write
    STATUS      current
    DESCRIPTION
        "Reset data-layer Performance registers"
    ::=  { physicalPortEntry 66 }

physicalPortPrbsPmReset OBJECT-TYPE
    SYNTAX      FspR7PrbsPmReset
    MAX-ACCESS  read-write
    STATUS      current
    DESCRIPTION
        "Reset PRBS PM counters"
    ::=  { physicalPortEntry 67 }

physicalPortTestPrbsRcvMode OBJECT-TYPE
    SYNTAX      FspR7PRBSTest
    MAX-ACCESS  read-write
    STATUS      current
    DESCRIPTION
        "PRBS test pattern received"
    ::=  { physicalPortEntry 68 }

physicalPortTestPrbsTrmtMode OBJECT-TYPE
    SYNTAX      FspR7PRBSTest
    MAX-ACCESS  read-write
    STATUS      current
    DESCRIPTION
        "PRBS test pattern transmitted"
    ::=  { physicalPortEntry 69 }

physicalPortSwitchCommand OBJECT-TYPE
    SYNTAX      FspR7APSCommand
    MAX-ACCESS  read-write
    STATUS      current
    DESCRIPTION   "The switch command action for this facility. A command resulting
         in a switch event will also cause a change of the facility secondary state
         and a corresponding condition. Addressed by this command is the active port,
         the port to switch away from. Since this is a manual switch command, it will
         not switch if other port suffers from a signalfailure or a signal degrade."
    ::=  { physicalPortEntry 70 }

physicalPortOpuPayloadType OBJECT-TYPE
    SYNTAX      FspR7OpuPayloadType
    MAX-ACCESS  read-create
    STATUS      current
    DESCRIPTION
        "OPU Payload Type Indicator"
    ::=  { physicalPortEntry 71 }

physicalPortReach OBJECT-TYPE
    SYNTAX      FspR7OpticalInterfaceReach
    MAX-ACCESS  read-only
    STATUS      current
    DESCRIPTION
        "Reach"
    ::=  { physicalPortEntry 72 }

physicalPortSigDegThresSonetLine OBJECT-TYPE
    SYNTAX      FspR7BERThreshold
    MAX-ACCESS  read-create
    STATUS      current
    DESCRIPTION
        "Bit-Error-Based Degradation Definition for SONET (standard integration period)"
    ::=  { physicalPortEntry 73 }

physicalPortSigDegThresSdhMs OBJECT-TYPE
    SYNTAX      Unsigned32 (1..100)
    UNITS       "%"
    MAX-ACCESS  read-create
    STATUS      current
    DESCRIPTION
        "Block-Error-Based Degradation Definition for SDH (standard integration period).
         Defined as percentage Background Block Errors (30% default) evaluated
         over a defined period (SDPER-RS)."
    ::=  { physicalPortEntry 74 }

physicalPortSigDegThresOtu OBJECT-TYPE
    SYNTAX      Integer32 (1..100)
    UNITS       "%"
    MAX-ACCESS  read-create
    STATUS      current
    DESCRIPTION
        "Background-Block-Error-Based Signal Degradation Definition for OTU"
    ::=  { physicalPortEntry 75 }

physicalPortSigDegThresOdu OBJECT-TYPE
    SYNTAX      Integer32 (1..100)
    UNITS       "%"
    MAX-ACCESS  read-create
    STATUS      current
    DESCRIPTION
        "Background-Block-Error-Based Signal Degradation Definition for ODU"
    ::=  { physicalPortEntry 76 }

physicalPortSigDegThreshold OBJECT-TYPE
    SYNTAX      Unsigned32 (1..10000)
    MAX-ACCESS  read-create
    STATUS      current
    DESCRIPTION
        "Threshold for number of errors (CV or CV+DE) in one second"
    ::=  { physicalPortEntry 77 }

physicalPortSigDegPcslThreshold OBJECT-TYPE
    SYNTAX      Unsigned32 (1..100)
    UNITS       "%"
    MAX-ACCESS  read-create
    STATUS      current
    DESCRIPTION
        "Block-Error-Based Degradation Definition for Physical Coding Sublayer"
    ::=  { physicalPortEntry 78 }

physicalPortSigDegThresSonetSection OBJECT-TYPE
    SYNTAX      FspR7BERThresholdSection
    MAX-ACCESS  read-create
    STATUS      current
    DESCRIPTION
        "Bit-Error-Based Degradation Definition for SONET (standard integration period)"
    ::=  { physicalPortEntry 79 }

physicalPortSigDegThresSdhSection OBJECT-TYPE
    SYNTAX      Unsigned32 (1..100)
    UNITS       "%"
    MAX-ACCESS  read-create
    STATUS      current
    DESCRIPTION
        "Block-Error-Based Degradation Definition for SDH (standard integration period).
         Defined as percentage Background Block Errors (30% default) evaluated
         over a defined period (SDPER-RS)."
    ::=  { physicalPortEntry 80 }

physicalPortSigDegThresOduTcmA OBJECT-TYPE
    SYNTAX      Integer32 (1..100)
    UNITS       "%"
    MAX-ACCESS  read-create
    STATUS      current
    DESCRIPTION
        "Background-Block-Error-Based Signal Degradation Definition for TCM-A"
    ::=  { physicalPortEntry 81 }

physicalPortSigDegThresOduTcmB OBJECT-TYPE
    SYNTAX      Integer32 (1..100)
    UNITS       "%"
    MAX-ACCESS  read-create
    STATUS      current
    DESCRIPTION
        "Background-Block-Error-Based Signal Degradation Definition for TCM-B"
    ::=  { physicalPortEntry 82 }

physicalPortSigDegThresOduTcmC OBJECT-TYPE
    SYNTAX      Integer32 (1..100)
    UNITS       "%"
    MAX-ACCESS  read-create
    STATUS      current
    DESCRIPTION
        "Background-Block-Error-Based Signal Degradation Definition for TCM-C"
    ::=  { physicalPortEntry 83 }

physicalPortSignalDegradePeriod OBJECT-TYPE
    SYNTAX      Unsigned32 (2..10)
    UNITS       "s"
    MAX-ACCESS  read-create
    STATUS      current
    DESCRIPTION   "The measurement period in seconds used together with
         the deployProvIfSigDegThresSdhRegSect based on the block error counting method.
         The valid range is 2..10,
         The default being 7."
    ::=  { physicalPortEntry 84 }

physicalPortSigDegPeriodOdu OBJECT-TYPE
    SYNTAX      Unsigned32 (2..10)
    UNITS       "s"
    MAX-ACCESS  read-create
    STATUS      current
    DESCRIPTION
        "Integration Period for Signal degrade"
    ::=  { physicalPortEntry 85 }

physicalPortSigDegPeriodOtu OBJECT-TYPE
    SYNTAX      Unsigned32 (2..10)
    UNITS       "s"
    MAX-ACCESS  read-create
    STATUS      current
    DESCRIPTION
        "Integration Period for Signal degrade"
    ::=  { physicalPortEntry 86 }

physicalPortSigDegPeriodIntegration OBJECT-TYPE
    SYNTAX      Unsigned32 (1..10)
    UNITS       "s"
    MAX-ACCESS  read-create
    STATUS      current
    DESCRIPTION
        "Integration Period for Signal degrade"
    ::=  { physicalPortEntry 87 }

physicalPortSigDegPeriodSdhSection OBJECT-TYPE
    SYNTAX      Unsigned32 (2..10)
    UNITS       "s"
    MAX-ACCESS  read-create
    STATUS      current
    DESCRIPTION
        "Provisionable Signal Degrade Integration Period for SDH"
    ::=  { physicalPortEntry 88 }

physicalPortSigDegPeriodOduTcmA OBJECT-TYPE
    SYNTAX      Unsigned32 (2..10)
    UNITS       "s"
    MAX-ACCESS  read-create
    STATUS      current
    DESCRIPTION
        "Integration Period for Signal degrade"
    ::=  { physicalPortEntry 89 }

physicalPortSigDegPeriodOduTcmB OBJECT-TYPE
    SYNTAX      Unsigned32 (2..10)
    UNITS       "s"
    MAX-ACCESS  read-create
    STATUS      current
    DESCRIPTION
        "Integration Period of TCMB Signal Segrade"
    ::=  { physicalPortEntry 90 }

physicalPortSigDegPeriodOduTcmC OBJECT-TYPE
    SYNTAX      Unsigned32 (2..10)
    UNITS       "s"
    MAX-ACCESS  read-create
    STATUS      current
    DESCRIPTION
        "Integration Period of TCMC Signal Segrade"
    ::=  { physicalPortEntry 91 }

physicalPortOtnStuffing OBJECT-TYPE
    SYNTAX      FspR7Stuff
    MAX-ACCESS  read-create
    STATUS      current
    DESCRIPTION
        "Indicates if bit/byte stuffing is used in the transport signal."
    ::=  { physicalPortEntry 92 }

physicalPortTcmALevel OBJECT-TYPE
    SYNTAX      OtnTcmLevel
    MAX-ACCESS  read-create
    STATUS      current
    DESCRIPTION
        "Activation of Tandem Connection Monitoring Instance A"
    ::=  { physicalPortEntry 93 }

physicalPortTcmBLevel OBJECT-TYPE
    SYNTAX      OtnTcmLevel
    MAX-ACCESS  read-create
    STATUS      current
    DESCRIPTION
        "Activation of Tandem Connection Monitoring Instance B"
    ::=  { physicalPortEntry 94 }

physicalPortTcmCLevel OBJECT-TYPE
    SYNTAX      OtnTcmLevel
    MAX-ACCESS  read-create
    STATUS      current
    DESCRIPTION
        "Activation of Tandem Connection Monitoring Instance C"
    ::=  { physicalPortEntry 95 }

physicalPortTerminationLevel OBJECT-TYPE
    SYNTAX      OhTerminationLevel
    MAX-ACCESS  read-create
    STATUS      current
    DESCRIPTION
        "The entity is Addressable by Management [because its supporting entity is defined in the database and therefore its address existsSignal Tremination Level of Intrusive Access to Header Information.
         Not used in 7.0, monitoring is one layer higher than TERM level,
         if applicable. All conditions detected on monitoring layer will not
         be reported (severity degradated to NR)."
    ::=  { physicalPortEntry 96 }

physicalPortTimingSource OBJECT-TYPE
    SYNTAX      SonetTimingSource
    MAX-ACCESS  read-create
    STATUS      current
    DESCRIPTION   "The timing source for this interface.
         - internal: used in stand-alone, point-to-point topologies stand-alone (dedicated fiber operation).
         - loopTiming: e.g. used in point-to-point via SONET network and feeder topologies. The default is
         internal(1)."
    ::=  { physicalPortEntry 97 }

physicalPortTimModeOdu OBJECT-TYPE
    SYNTAX      TimMode
    MAX-ACCESS  read-create
    STATUS      current
    DESCRIPTION
        "Detection of TIM-ODU Condition can be configured"
    ::=  { physicalPortEntry 98 }

physicalPortTimModeOtu OBJECT-TYPE
    SYNTAX      TimMode
    MAX-ACCESS  read-create
    STATUS      current
    DESCRIPTION
        "Detection of TIM-OTU Condition can be configured"
    ::=  { physicalPortEntry 99 }

physicalPortTimModeSonetSection OBJECT-TYPE
    SYNTAX      TimMode
    MAX-ACCESS  read-create
    STATUS      current
    DESCRIPTION
        "Detection of TIM Sonet Section Condition can be configured"
    ::=  { physicalPortEntry 100 }

physicalPortTimModeOduTcmA OBJECT-TYPE
    SYNTAX      TimMode
    MAX-ACCESS  read-create
    STATUS      current
    DESCRIPTION
        "Detection of TIM-TCMA Condition can be configured"
    ::=  { physicalPortEntry 101 }

physicalPortTimModeOduTcmB OBJECT-TYPE
    SYNTAX      TimMode
    MAX-ACCESS  read-create
    STATUS      current
    DESCRIPTION
        "Detection of TIM-TCMB Condition can be configured"
    ::=  { physicalPortEntry 102 }

physicalPortTimModeOduTcmC OBJECT-TYPE
    SYNTAX      TimMode
    MAX-ACCESS  read-create
    STATUS      current
    DESCRIPTION
        "Detection of TIM-TCMC Condition can be configured"
    ::=  { physicalPortEntry 103 }

physicalPortTraceFormSonetSection OBJECT-TYPE
    SYNTAX      SonetTraceForm
    MAX-ACCESS  read-create
    STATUS      current
    DESCRIPTION
        "Byte-Length of Trace Compared to Expected"
    ::=  { physicalPortEntry 104 }

physicalPortTraceExpectedSonetSection OBJECT-TYPE
    SYNTAX      OCTET STRING (SIZE(0..62))
    MAX-ACCESS  read-create
    STATUS      current
    DESCRIPTION
        "Expected Sec/RS trace. NULL TRACE implies that no trace comparison is made."
    ::=  { physicalPortEntry 105 }

physicalPortTraceTransmitSonetSection OBJECT-TYPE
    SYNTAX      OCTET STRING (SIZE(0..62))
    MAX-ACCESS  read-create
    STATUS      current
    DESCRIPTION
        "Sec/RS Trace to be Transmitted"
    ::=  { physicalPortEntry 106 }

physicalPortTraceExpectedOtu OBJECT-TYPE
    SYNTAX      OCTET STRING (SIZE(0..15))
    MAX-ACCESS  read-create
    STATUS      current
    DESCRIPTION
        "Expected SAPI part of the OTU trace (15 character). NULL TRACE implies that no trace comparison is made."
    ::=  { physicalPortEntry 107 }

physicalPortTraceTransmitSapiOtu OBJECT-TYPE
    SYNTAX      OCTET STRING (SIZE(0..15))
    MAX-ACCESS  read-create
    STATUS      current
    DESCRIPTION
        "The transmitted SAPI part of the OTU trace (15 character)"
    ::=  { physicalPortEntry 108 }

physicalPortTraceTransmitDapiOtu OBJECT-TYPE
    SYNTAX      OCTET STRING (SIZE(0..15))
    MAX-ACCESS  read-create
    STATUS      current
    DESCRIPTION
        "The transmitted DAPI part of the OTU trace (15 character)"
    ::=  { physicalPortEntry 109 }

physicalPortTraceTransmitOpspOtu OBJECT-TYPE
    SYNTAX      OCTET STRING (SIZE(0..32))
    MAX-ACCESS  read-create
    STATUS      current
    DESCRIPTION
        "The transmitted Operator Specific part of the OTU trace (32 character)"
    ::=  { physicalPortEntry 110 }

physicalPortTraceExpectedOdu OBJECT-TYPE
    SYNTAX      OCTET STRING (SIZE(0..15))
    MAX-ACCESS  read-create
    STATUS      current
    DESCRIPTION
        "Expected SAPI part of the ODU trace (15 character). NULL TRACE implies that no trace comparison is made."
    ::=  { physicalPortEntry 111 }

physicalPortTraceTransmitSapiOdu OBJECT-TYPE
    SYNTAX      OCTET STRING (SIZE(0..15))
    MAX-ACCESS  read-create
    STATUS      current
    DESCRIPTION
        "The transmitted SAPI part of the ODU trace (15 character)"
    ::=  { physicalPortEntry 112 }

physicalPortTraceTransmitDapiOdu OBJECT-TYPE
    SYNTAX      OCTET STRING (SIZE(0..15))
    MAX-ACCESS  read-create
    STATUS      current
    DESCRIPTION
        "The transmitted DAPI part of the ODU trace (15 character)"
    ::=  { physicalPortEntry 113 }

physicalPortTraceTransmitOpspOdu OBJECT-TYPE
    SYNTAX      OCTET STRING (SIZE(0..32))
    MAX-ACCESS  read-create
    STATUS      current
    DESCRIPTION
        "The transmitted Operator Specific part of the ODU trace (32 character)"
    ::=  { physicalPortEntry 114 }

physicalPortTraceExpectedOduTcmA OBJECT-TYPE
    SYNTAX      OCTET STRING (SIZE(0..15))
    MAX-ACCESS  read-create
    STATUS      current
    DESCRIPTION
        "Expected SAPI part of the TCMA trace (15 character). NULL TRACE-TCM implies that no trace comparison is made."
    ::=  { physicalPortEntry 115 }

physicalPortTraceTransmitSapiOduTcmA OBJECT-TYPE
    SYNTAX      OCTET STRING (SIZE(0..15))
    MAX-ACCESS  read-create
    STATUS      current
    DESCRIPTION
        "The transmitted SAPI part of the TCMA trace (15 character)"
    ::=  { physicalPortEntry 116 }

physicalPortTraceTransmitDapiOduTcmA OBJECT-TYPE
    SYNTAX      OCTET STRING (SIZE(0..15))
    MAX-ACCESS  read-create
    STATUS      current
    DESCRIPTION
        "The transmitted DAPI part of the TCMA trace (15 character)"
    ::=  { physicalPortEntry 117 }

physicalPortTraceTransmitOpspOduTcmA OBJECT-TYPE
    SYNTAX      OCTET STRING (SIZE(0..32))
    MAX-ACCESS  read-create
    STATUS      current
    DESCRIPTION
        "The transmitted Operator Specific part of the TCMA trace (32 character)"
    ::=  { physicalPortEntry 118 }

physicalPortTraceExpectedOduTcmB OBJECT-TYPE
    SYNTAX      OCTET STRING (SIZE(0..15))
    MAX-ACCESS  read-create
    STATUS      current
    DESCRIPTION
        "Expected SAPI part of the TCMB trace (15 character). NULL TRACE-TCM implies that no trace comparison is made."
    ::=  { physicalPortEntry 119 }

physicalPortTraceTransmitSapiOduTcmB OBJECT-TYPE
    SYNTAX      OCTET STRING (SIZE(0..15))
    MAX-ACCESS  read-create
    STATUS      current
    DESCRIPTION
        "The transmitted SAPI part of the TCMB trace (15 character)"
    ::=  { physicalPortEntry 120 }

physicalPortTraceTransmitDapiOduTcmB OBJECT-TYPE
    SYNTAX      OCTET STRING (SIZE(0..15))
    MAX-ACCESS  read-create
    STATUS      current
    DESCRIPTION
        "The transmitted DAPI part of the TCMB trace (15 character)"
    ::=  { physicalPortEntry 121 }

physicalPortTraceTransmitOpspOduTcmB OBJECT-TYPE
    SYNTAX      OCTET STRING (SIZE(0..32))
    MAX-ACCESS  read-create
    STATUS      current
    DESCRIPTION
        "The transmitted Operator Specific part of the TCMB trace (32 character)"
    ::=  { physicalPortEntry 122 }

physicalPortTraceExpectedOduTcmC OBJECT-TYPE
    SYNTAX      OCTET STRING (SIZE(0..15))
    MAX-ACCESS  read-create
    STATUS      current
    DESCRIPTION
        "Expected SAPI part of the TCMC trace (15 character). NULL TRACE-TCM implies that no trace comparison is made."
    ::=  { physicalPortEntry 123 }

physicalPortTraceTransmitSapiOduTcmC OBJECT-TYPE
    SYNTAX      OCTET STRING (SIZE(0..15))
    MAX-ACCESS  read-create
    STATUS      current
    DESCRIPTION
        "The transmitted SAPI part of the TCMC trace (15 character)"
    ::=  { physicalPortEntry 124 }

physicalPortTraceTransmitDapiOduTcmC OBJECT-TYPE
    SYNTAX      OCTET STRING (SIZE(0..15))
    MAX-ACCESS  read-create
    STATUS      current
    DESCRIPTION
        "The transmitted DAPI part of the TCMC trace (15 character)"
    ::=  { physicalPortEntry 125 }

physicalPortTraceTransmitOpspOduTcmC OBJECT-TYPE
    SYNTAX      OCTET STRING (SIZE(0..32))
    MAX-ACCESS  read-create
    STATUS      current
    DESCRIPTION
        "The transmitted Operator Specific part of the TCMC trace (32 character)"
    ::=  { physicalPortEntry 126 }

physicalPortTraceRcvSapiOdu OBJECT-TYPE
    SYNTAX      OCTET STRING (SIZE(0..15))
    MAX-ACCESS  read-only
    STATUS      current
    DESCRIPTION
        "The received SAPI part of the ODU trace (15 character)"
    ::=  { physicalPortEntry 127 }

physicalPortTraceRcvDapiOdu OBJECT-TYPE
    SYNTAX      OCTET STRING (SIZE(0..15))
    MAX-ACCESS  read-only
    STATUS      current
    DESCRIPTION
        "The received DAPI part of the ODU trace (15 character)"
    ::=  { physicalPortEntry 128 }

physicalPortTraceRcvOpspOdu OBJECT-TYPE
    SYNTAX      OCTET STRING (SIZE(0..32))
    MAX-ACCESS  read-only
    STATUS      current
    DESCRIPTION
        "The received Operator Specific part of the ODU trace (32 character)"
    ::=  { physicalPortEntry 129 }

physicalPortTraceRcvSapiOtu OBJECT-TYPE
    SYNTAX      OCTET STRING (SIZE(0..15))
    MAX-ACCESS  read-only
    STATUS      current
    DESCRIPTION
        "The received SAPI part of the OTU trace (15 character)"
    ::=  { physicalPortEntry 130 }

physicalPortTraceRcvDapiOtu OBJECT-TYPE
    SYNTAX      OCTET STRING (SIZE(0..15))
    MAX-ACCESS  read-only
    STATUS      current
    DESCRIPTION
        "The received DAPI part of the OTU trace (15 character)"
    ::=  { physicalPortEntry 131 }

physicalPortTraceRcvOpspOtu OBJECT-TYPE
    SYNTAX      OCTET STRING (SIZE(0..32))
    MAX-ACCESS  read-only
    STATUS      current
    DESCRIPTION
        "The received Operator Specific part of the OTU trace (32 character)"
    ::=  { physicalPortEntry 132 }

physicalPortTraceRcvSapiTcma OBJECT-TYPE
    SYNTAX      OCTET STRING (SIZE(0..15))
    MAX-ACCESS  read-only
    STATUS      current
    DESCRIPTION
        "The received SAPI part of the TCMA trace (15 character)"
    ::=  { physicalPortEntry 133 }

physicalPortTraceRcvDapiTcma OBJECT-TYPE
    SYNTAX      OCTET STRING (SIZE(0..15))
    MAX-ACCESS  read-only
    STATUS      current
    DESCRIPTION
        "The received DAPI part of the TCMA trace (15 character)"
    ::=  { physicalPortEntry 134 }

physicalPortTraceRcvOpspTcma OBJECT-TYPE
    SYNTAX      OCTET STRING (SIZE(0..32))
    MAX-ACCESS  read-only
    STATUS      current
    DESCRIPTION
        "The received Operator Specific part of the TCMA trace (32 character)"
    ::=  { physicalPortEntry 135 }

physicalPortTraceRcvSapiTcmb OBJECT-TYPE
    SYNTAX      OCTET STRING (SIZE(0..15))
    MAX-ACCESS  read-only
    STATUS      current
    DESCRIPTION
        "The received SAPI part of the TCMB trace (15 character)"
    ::=  { physicalPortEntry 136 }

physicalPortTraceRcvDapiTcmb OBJECT-TYPE
    SYNTAX      OCTET STRING (SIZE(0..15))
    MAX-ACCESS  read-only
    STATUS      current
    DESCRIPTION
        "The received DAPI part of the TCMB trace (15 character)"
    ::=  { physicalPortEntry 137 }

physicalPortTraceRcvOpspTcmb OBJECT-TYPE
    SYNTAX      OCTET STRING (SIZE(0..32))
    MAX-ACCESS  read-only
    STATUS      current
    DESCRIPTION
        "The received Operator Specific part of the TCMB trace (32 character)"
    ::=  { physicalPortEntry 138 }

physicalPortTraceRcvSapiTcmc OBJECT-TYPE
    SYNTAX      OCTET STRING (SIZE(0..15))
    MAX-ACCESS  read-only
    STATUS      current
    DESCRIPTION
        "The received SAPI part of the TCMC trace (15 character)"
    ::=  { physicalPortEntry 139 }

physicalPortTraceRcvDapiTcmc OBJECT-TYPE
    SYNTAX      OCTET STRING (SIZE(0..15))
    MAX-ACCESS  read-only
    STATUS      current
    DESCRIPTION
        "The received DAPI part of the TCMC trace (15 character)"
    ::=  { physicalPortEntry 140 }

physicalPortTraceRcvOpspTcmc OBJECT-TYPE
    SYNTAX      OCTET STRING (SIZE(0..32))
    MAX-ACCESS  read-only
    STATUS      current
    DESCRIPTION
        "The received Operator Specific part of the TCMC trace (32 character)"
    ::=  { physicalPortEntry 141 }

physicalPortTraceReceived OBJECT-TYPE
    SYNTAX      OCTET STRING (SIZE(0..62))
    MAX-ACCESS  read-only
    STATUS      current
    DESCRIPTION
        "The received Sec/RS Trace"
    ::=  { physicalPortEntry 142 }

physicalPortTurnupConfig OBJECT-TYPE
    SYNTAX      FspR7TurnupConfig
    MAX-ACCESS  read-write
    STATUS      current
    DESCRIPTION
        "Turnup Operation"
    ::=  { physicalPortEntry 143 }

physicalPortTxOffDelay OBJECT-TYPE
    SYNTAX      FspR7EnableDisable
    MAX-ACCESS  read-create
    STATUS      current
    DESCRIPTION
        "Enable or disable TXOFFHOLD Period for Error Forwarding and LKDO-OFF Consequent Action."
    ::=  { physicalPortEntry 144 }

physicalPortVoaMode OBJECT-TYPE
    SYNTAX      FspR7VoaMode
    MAX-ACCESS  read-create
    STATUS      current
    DESCRIPTION
        "VOA operating mode"
    ::=  { physicalPortEntry 145 }

physicalPortVoaSetpoint OBJECT-TYPE
    SYNTAX      Unsigned32 (0..300)
    UNITS       "0.1 dB"
    MAX-ACCESS  read-create
    STATUS      current
    DESCRIPTION
        "Sets the optical attenuation of VOA"
    ::=  { physicalPortEntry 146 }

physicalPortCbsRcv OBJECT-TYPE
    SYNTAX      Unsigned32 (0..26214400)
    UNITS       "Byte"
    MAX-ACCESS  read-only
    STATUS      current
    DESCRIPTION
        "Committed Burst Size"
    ::=  { physicalPortEntry 147 }

physicalPortCbsTrmt OBJECT-TYPE
    SYNTAX      Unsigned32 (0..25600)
    UNITS       "kByte"
    MAX-ACCESS  read-only
    STATUS      current
    DESCRIPTION
        "Committed Burst Size"
    ::=  { physicalPortEntry 148 }

physicalPortCirRcv OBJECT-TYPE
    SYNTAX      Unsigned32
    UNITS       "Mbps"
    MAX-ACCESS  read-only
    STATUS      current
    DESCRIPTION
        "CIR (Committed Information Rate ) is used on Ethernet Interfaces with a policing function"
    ::=  { physicalPortEntry 149 }

physicalPortCirTrmt OBJECT-TYPE
    SYNTAX      Unsigned32
    UNITS       "Mbps"
    MAX-ACCESS  read-only
    STATUS      current
    DESCRIPTION
        "CIR (Committed Information Rate ) is used on Ethernet Interfaces with a policing function"
    ::=  { physicalPortEntry 150 }

physicalPortLagPrio OBJECT-TYPE
    SYNTAX      Unsigned32 (0..65535)
    MAX-ACCESS  read-create
    STATUS      current
    DESCRIPTION
        "Part of ID. Port pri that defines standby."
    ::=  { physicalPortEntry 151 }

physicalPortMacAddress OBJECT-TYPE
    SYNTAX      MacAddress
    MAX-ACCESS  read-only
    STATUS      current
    DESCRIPTION
        "Ethernet MAC address"
    ::=  { physicalPortEntry 152 }

physicalPortMaxFrameSize OBJECT-TYPE
    SYNTAX      Unsigned32 (1518..9600)
    MAX-ACCESS  read-create
    STATUS      current
    DESCRIPTION
        "Max Frame Size"
    ::=  { physicalPortEntry 153 }

physicalPortPayload OBJECT-TYPE
    SYNTAX      OtnPayloadType
    MAX-ACCESS  read-create
    STATUS      current
    DESCRIPTION
        "The PAYLOAD defines the transport service type of the payload"
    ::=  { physicalPortEntry 154 }

physicalPortPortMode OBJECT-TYPE
    SYNTAX      FspR7PortMode
    MAX-ACCESS  read-create
    STATUS      current
    DESCRIPTION
        "Port Mode"
    ::=  { physicalPortEntry 155 }

physicalPortPortRole OBJECT-TYPE
    SYNTAX      FspR7PortRole
    MAX-ACCESS  read-create
    STATUS      current
    DESCRIPTION
        "ADVA cloud Port Roles"
    ::=  { physicalPortEntry 156 }

physicalPortPriority OBJECT-TYPE
    SYNTAX      Unsigned32 (0..7)
    MAX-ACCESS  read-create
    STATUS      current
    DESCRIPTION
        "Default PCP in case UTAG is Enabled. The Prio may be remapped in the EVC."
    ::=  { physicalPortEntry 157 }

physicalPortPvid OBJECT-TYPE
    SYNTAX      Unsigned32 (1..4095)
    MAX-ACCESS  read-create
    STATUS      current
    DESCRIPTION
        "Default VLAN ID (both STAG/CTAG mode) in case UTAG is enabled"
    ::=  { physicalPortEntry 158 }

physicalPortStagType OBJECT-TYPE
    SYNTAX      FspR7SnmpHexString
    MAX-ACCESS  read-create
    STATUS      current
    DESCRIPTION
        "TAG type field"
    ::=  { physicalPortEntry 159 }

physicalPortUtag OBJECT-TYPE
    SYNTAX      FspR7UntaggedFrames
    MAX-ACCESS  read-create
    STATUS      current
    DESCRIPTION
        "If untagged frames shall be enabled on this port or not."
    ::=  { physicalPortEntry 160 }

physicalPortVethAid OBJECT-TYPE
    SYNTAX      SnmpAdminString
    MAX-ACCESS  read-create
    STATUS      current
    DESCRIPTION
        "Shows if PORT is a member in the LAG with the VETH AID"
    ::=  { physicalPortEntry 161 }

physicalPortChannelBandwith OBJECT-TYPE
    SYNTAX      FspR7ChannelBandwidth
    MAX-ACCESS  read-only
    STATUS      current
    DESCRIPTION
        "Channel Bandwidth"
    ::=  { physicalPortEntry 162 }

physicalPortFacilities OBJECT-TYPE
    SYNTAX      SnmpAdminString
    MAX-ACCESS  read-only
    STATUS      current
    DESCRIPTION
        "AID of a WCH, VCH or CH instance"
    ::=  { physicalPortEntry 163 }

physicalPortLanes OBJECT-TYPE
    SYNTAX      FspR7OpticalLanes
    MAX-ACCESS  read-only
    STATUS      current
    DESCRIPTION
        "Number of Optical Transport Lanes in OTLG"
    ::=  { physicalPortEntry 164 }

physicalPortProtectionRole OBJECT-TYPE
    SYNTAX      FspR7ProtectionRole
    MAX-ACCESS  read-only
    STATUS      current
    DESCRIPTION
        "Path label Working or Protect"
    ::=  { physicalPortEntry 165 }

physicalPortMonitoredBitrate OBJECT-TYPE
    SYNTAX      Unsigned32
    UNITS       "Mbps"
    MAX-ACCESS  read-only
    STATUS      current
    DESCRIPTION
        "Bit Rate read from card, - relevant to- auto clock"
    ::=  { physicalPortEntry 166 }

physicalPortLagState OBJECT-TYPE
    SYNTAX      FspR7LagState
    MAX-ACCESS  read-only
    STATUS      current
    DESCRIPTION
        "State of the LACP on this port"
    ::=  { physicalPortEntry 167 }

physicalPortLagIdFend OBJECT-TYPE
    SYNTAX      FspR7LagIdFend
    MAX-ACCESS  read-only
    STATUS      current
    DESCRIPTION
        "Part of Partner PORT ID. Operational Key, Pri and No. uses 4+2+4 HEX values. Coded as 10 HEXV2 in DD."
    ::=  { physicalPortEntry 168 }

physicalPortLagFendState OBJECT-TYPE
    SYNTAX      FspR7LagFendState
    MAX-ACCESS  read-only
    STATUS      current
    DESCRIPTION
        "State of the LACP on partner port"
    ::=  { physicalPortEntry 169 }

physicalPortLagPortNo OBJECT-TYPE
    SYNTAX      Unsigned32
    MAX-ACCESS  read-only
    STATUS      current
    DESCRIPTION
        "Part of ID. Hardcoded to physical port no."
    ::=  { physicalPortEntry 170 }

physicalPortLagKey OBJECT-TYPE
    SYNTAX      Unsigned32
    MAX-ACCESS  read-only
    STATUS      current
    DESCRIPTION
        "Part of ID. Operational KEY"
    ::=  { physicalPortEntry 171 }

physicalPortValidSigTimer OBJECT-TYPE
    SYNTAX      Unsigned32 (0..5760)
    UNITS       "min"
    MAX-ACCESS  read-only
    STATUS      current
    DESCRIPTION
        "AINS state signal quality soak time remaining until transition to IS."
    ::=  { physicalPortEntry 172 }

physicalPortLaserReleaseTimer OBJECT-TYPE
    SYNTAX      Unsigned32 (0..1440)
    UNITS       "min"
    MAX-ACCESS  read-only
    STATUS      current
    DESCRIPTION
        "Fall-back timer for forced laser operation."
    ::=  { physicalPortEntry 173 }

physicalPortBidirectionalChannel OBJECT-TYPE
    SYNTAX      FspR7BidirectionalChannel
    MAX-ACCESS  read-only
    STATUS      current
    DESCRIPTION
        "Bidirectional Channel Rates from Provisioning"
    ::=  { physicalPortEntry 174 }

physicalPortTransmitterWavelength OBJECT-TYPE
    SYNTAX      Unsigned32
    UNITS       "0.01 nm"
    MAX-ACCESS  read-only
    STATUS      current
    DESCRIPTION
        "Transmitter Wavelength of Optical Interface (unit: nm)"
    ::=  { physicalPortEntry 175 }

physicalPortTransmitterFrequency OBJECT-TYPE
    SYNTAX      Unsigned32
    UNITS       "0.01 THz"
    MAX-ACCESS  read-only
    STATUS      current
    DESCRIPTION
        "Transmitter Frequency of Optical Interface (unit: nm)"
    ::=  { physicalPortEntry 176 }

physicalPortRedLineState OBJECT-TYPE
    SYNTAX      FspR7RedLinedState
    MAX-ACCESS  read-create
    STATUS      current
    DESCRIPTION
        "will be set by higher level software to act as a barrier to deletion"
    ::=  { physicalPortEntry 177 }

physicalPortTunnelAid OBJECT-TYPE
    SYNTAX      SnmpAdminString
    MAX-ACCESS  read-create
    STATUS      current
    DESCRIPTION
        "Tunnel AID"
    ::=  { physicalPortEntry 178 }

physicalPortIngressTid OBJECT-TYPE
    SYNTAX      SnmpAdminString
    MAX-ACCESS  read-only
    STATUS      current
    DESCRIPTION
        "Ingress Target ID"
    ::=  { physicalPortEntry 179 }

physicalPortIngressNodeIp OBJECT-TYPE
    SYNTAX      IpAddress
    MAX-ACCESS  read-only
    STATUS      current
    DESCRIPTION
        "Ingress Node IP"
    ::=  { physicalPortEntry 180 }

physicalPortRateLimit OBJECT-TYPE
    SYNTAX      FspR7DisableEnable
    MAX-ACCESS  read-create
    STATUS      current
    DESCRIPTION
        "Selection to apply rate limit feature or not."
    ::=  { physicalPortEntry 181 }

physicalPortPathProtection OBJECT-TYPE
    SYNTAX      FspR7PathProt
    MAX-ACCESS  read-only
    STATUS      current
    DESCRIPTION
        "Indicates the traffic path for path protection cases when the FFP does not exist. When the FFP exists, protected is indicated and the status is determined by the FFP."
    ::=  { physicalPortEntry 182 }

physicalPortGropticsType OBJECT-TYPE
    SYNTAX      FspR7GropticsType
    MAX-ACCESS  read-only
    STATUS      current
    DESCRIPTION
        "Identification of the desired group optics inorder to verify the plug types are as expected"
    ::=  { physicalPortEntry 183 }

physicalPortAvlntsTxcrs OBJECT-TYPE
    SYNTAX      Unsigned32 (0..1000)
    MAX-ACCESS  read-only
    STATUS      current
    DESCRIPTION
        "Available Time slots in CRS transmit direction (from CRS to N-port)"
    ::=  { physicalPortEntry 184 }

physicalPortAvlntsRxcrs OBJECT-TYPE
    SYNTAX      Unsigned32 (0..1000)
    MAX-ACCESS  read-only
    STATUS      current
    DESCRIPTION
        "Available network time slots in CRS receive direction (from N-port to CRS)"
    ::=  { physicalPortEntry 185 }

physicalPortTxOffOnTm OBJECT-TYPE
    SYNTAX      FspR7TxOffOnTm
    MAX-ACCESS  read-create
    STATUS      current
    DESCRIPTION
        "Relevant only when ERRFWD=TXOFF. Enables/disables the
         possibility to delay turning off and on the the transmitter.
         This applies to the case when turning off the transmitter
         is done as an error forwarding mechanism."
    ::=  { physicalPortEntry 186 }

physicalPortTxOffTimer OBJECT-TYPE
    SYNTAX      Unsigned32 (1..1000)
    UNITS       "ms"
    MAX-ACCESS  read-create
    STATUS      current
    DESCRIPTION
        "Delay before transmitter is swiched off"
    ::=  { physicalPortEntry 187 }

physicalPortTxOnTimer OBJECT-TYPE
    SYNTAX      Unsigned32 (1..1000)
    UNITS       "ms"
    MAX-ACCESS  read-create
    STATUS      current
    DESCRIPTION
        "Delay before transmitter is switched on"
    ::=  { physicalPortEntry 188 }

physicalPortTrafficDirection OBJECT-TYPE
    SYNTAX      FspR7TrafficDirection
    MAX-ACCESS  read-only
    STATUS      current
    DESCRIPTION
        "Traffic Direction"
    ::=  { physicalPortEntry 189 }

physicalPortChannelSpacingProvision OBJECT-TYPE
    SYNTAX      FspR7ChannelSpacing
    MAX-ACCESS  read-only
    STATUS      current
    DESCRIPTION
        "Channel Space Provision, reference to CHA-SPC__INVENTORY"
    ::=  { physicalPortEntry 190 }

virtualPortTable OBJECT-TYPE
    SYNTAX      SEQUENCE OF VirtualPortEntry
    MAX-ACCESS  not-accessible
    STATUS      current
    DESCRIPTION   "virtualPortTable"
    ::=  { facilityMgmt 2 }

virtualPortEntry OBJECT-TYPE
    SYNTAX      VirtualPortEntry
    MAX-ACCESS  not-accessible
    STATUS      current
    DESCRIPTION   "Entry of virtualPortTable"
    INDEX       {
                  entityFacilityShelfNo,
                  entityFacilitySlotNo,
                  entityFacilityPortNo,
                  entityFacilityExtNo,
                  entityFacilityClassName
                }
    ::=  { virtualPortTable 1 }

VirtualPortEntry ::=  SEQUENCE
  { virtualPortRowStatus RowStatus,
    virtualPortChannelBand FspR7ChannelBandwidth,
    virtualPortType FspR7InterfaceType,
    virtualPortAlias SnmpAdminString,
    virtualPortFunction FspR7InterfaceFunction,
    virtualPortChannelProv FspR7ChannelIdentifier,
    virtualPortLambda Unsigned32,
    virtualPortFrequency Unsigned32,
    virtualPortAdmin FspR7AdminState,
    virtualPortOperState FspR7OperState,
    virtualPortConnState FspR7ConnectState,
    virtualPortEqlzAdmin FspR7EqlzAdminState,
    virtualPortInitEqlz FspR7InitEqualization,
    virtualPortInputPower Integer32,
    virtualPortOutputPower Integer32,
    virtualPortSecondaryStates FspR7EntitySecondaryStates,
    virtualPortRate Unsigned32,
    virtualPortCirRcv Unsigned32,
    virtualPortCbsRcv Unsigned32,
    virtualPortCirTrmt Unsigned32,
    virtualPortCbsTrmt Unsigned32,
    virtualPortLagPorts FspR7LagPorts,
    virtualPortLagPortType FspR7LagPortType,
    virtualPortLagStandby FspR7LagStandby,
    virtualPortLacpMode FspR7LacpMode,
    virtualPortLacpTimeout FspR7LacpTimeout,
    virtualPortLagActivePorts Unsigned32,
    virtualPortMacAddress MacAddress,
    virtualPortMaxFrameSize Unsigned32,
    virtualPortPortMode FspR7PortMode,
    virtualPortDataLayerPmReset FspR7PmReset,
    virtualPortPortRole FspR7PortRole,
    virtualPortPriority Unsigned32,
    virtualPortPvid Unsigned32,
    virtualPortRevertiveMode ApsRevertMode,
    virtualPortStagType FspR7SnmpHexString,
    virtualPortUtag FspR7UntaggedFrames,
    virtualPortBundle FspR7SnmpLongString,
    virtualPortSwitchCommand FspR7APSCommand,
    virtualPortInhibitSwitchToWork FspR7YesNo,
    virtualPortInhibitSwitchToProt FspR7YesNo,
    virtualPortMonLevel FspR7MonLevel,
    virtualPortOduTribPortNo SnmpAdminString,
    virtualPortOduTribTimeSlottNo SnmpAdminString,
    virtualPortSigDegThresOdu Integer32,
    virtualPortSigDegPeriodOdu Unsigned32,
    virtualPortTraceExpectedOdu OCTET STRING,
    virtualPortTraceTransmitSapiOdu OCTET STRING,
    virtualPortTraceTransmitDapiOdu OCTET STRING,
    virtualPortTraceTransmitOpspOdu OCTET STRING,
    virtualPortTimModeOdu TimMode,
    virtualPortSigDegThresOduTcmA Integer32,
    virtualPortSigDegPeriodOduTcmA Unsigned32,
    virtualPortSigDegThresOduTcmB Integer32,
    virtualPortSigDegPeriodOduTcmB Unsigned32,
    virtualPortSigDegThresOduTcmC Integer32,
    virtualPortSigDegPeriodOduTcmC Unsigned32,
    virtualPortTcmALevel OtnTcmLevel,
    virtualPortTcmBLevel OtnTcmLevel,
    virtualPortTcmCLevel OtnTcmLevel,
    virtualPortTraceTransmitSapiOduTcmA OCTET STRING,
    virtualPortTraceTransmitDapiOduTcmA OCTET STRING,
    virtualPortTraceTransmitOpspOduTcmA OCTET STRING,
    virtualPortTraceExpectedOduTcmA OCTET STRING,
    virtualPortTimModeOduTcmA TimMode,
    virtualPortTraceExpectedOduTcmB OCTET STRING,
    virtualPortTraceTransmitSapiOduTcmB OCTET STRING,
    virtualPortTraceTransmitDapiOduTcmB OCTET STRING,
    virtualPortTraceTransmitOpspOduTcmB OCTET STRING,
    virtualPortTimModeOduTcmB TimMode,
    virtualPortTraceExpectedOduTcmC OCTET STRING,
    virtualPortTraceTransmitSapiOduTcmC OCTET STRING,
    virtualPortTraceTransmitDapiOduTcmC OCTET STRING,
    virtualPortTraceTransmitOpspOduTcmC OCTET STRING,
    virtualPortTimModeOduTcmC TimMode,
    virtualPortTraceRcvSapiOdu OCTET STRING,
    virtualPortTraceRcvDapiOdu OCTET STRING,
    virtualPortTraceRcvOpspOdu OCTET STRING,
    virtualPortTraceRcvSapiTcma OCTET STRING,
    virtualPortTraceRcvDapiTcma OCTET STRING,
    virtualPortTraceRcvOpspTcma OCTET STRING,
    virtualPortTraceRcvSapiTcmb OCTET STRING,
    virtualPortTraceRcvDapiTcmb OCTET STRING,
    virtualPortTraceRcvOpspTcmb OCTET STRING,
    virtualPortTraceRcvSapiTcmc OCTET STRING,
    virtualPortTraceRcvDapiTcmc OCTET STRING,
    virtualPortTraceRcvOpspTcmc OCTET STRING,
    virtualPortTerminationLevel OhTerminationLevel,
    virtualPortChannelSpacing FspR7ChannelSpacing,
    virtualPortCir Unsigned32,
    virtualPortLoopConfig LoopConfig,
    virtualPortOwnerAid SnmpAdminString,
    virtualPortPayload OtnPayloadType,
    virtualPortVcType VirtualContainerType,
    virtualPortOdtuType FspR7OdtuType,
    virtualPortProtectionRole FspR7ProtectionRole,
    virtualPortLagSysPrio Unsigned32,
    virtualPortOpuPayloadType FspR7OpuPayloadType,
    virtualPortLagSysMac MacAddress,
    virtualPortLagSysIdFend FspR7LagSysIdFend,
    virtualPortValidSigTimer Unsigned32,
    virtualPortOtnStuffing FspR7Stuff,
    virtualPortRedLineState FspR7RedLinedState,
    virtualPortTunnelAid SnmpAdminString,
    virtualPortIngressTid SnmpAdminString,
    virtualPortIngressNodeIp IpAddress,
    virtualPortEncapsulationMethod FspR7EncapsulationMethod,
    virtualPortPathProtection FspR7PathProt,
    virtualPortTimeslot Unsigned32,
    virtualPortOffsetHigh Integer32,
    virtualPortOffsetLow Integer32,
    virtualPortTrafficDirection FspR7TrafficDirection,
    virtualPortChannelId Unsigned32 }

virtualPortRowStatus OBJECT-TYPE
    SYNTAX      RowStatus
    MAX-ACCESS  read-create
    STATUS      current
    DESCRIPTION   "RowStatus object is used to create or delete a row in the table."
    ::=  { virtualPortEntry 1 }

virtualPortChannelBand OBJECT-TYPE
    SYNTAX      FspR7ChannelBandwidth
    MAX-ACCESS  read-create
    STATUS      current
    DESCRIPTION
        "Channel Bandwidth"
    ::=  { virtualPortEntry 2 }

virtualPortType OBJECT-TYPE
    SYNTAX      FspR7InterfaceType
    MAX-ACCESS  read-create
    STATUS      current
    DESCRIPTION
        "The TYPE defines the transport service type as wrapper with wrapper layer termination OR else as payload"
    ::=  { virtualPortEntry 3 }

virtualPortAlias OBJECT-TYPE
    SYNTAX      SnmpAdminString
    MAX-ACCESS  read-create
    STATUS      current
    DESCRIPTION
        "User Applied Descriptor"
    ::=  { virtualPortEntry 4 }

virtualPortFunction OBJECT-TYPE
    SYNTAX      FspR7InterfaceFunction
    MAX-ACCESS  read-only
    STATUS      current
    DESCRIPTION
        "Interface Function"
    ::=  { virtualPortEntry 5 }

virtualPortChannelProv OBJECT-TYPE
    SYNTAX      FspR7ChannelIdentifier
    MAX-ACCESS  read-only
    STATUS      current
    DESCRIPTION
        "Channel"
    ::=  { virtualPortEntry 6 }

virtualPortLambda OBJECT-TYPE
    SYNTAX      Unsigned32
    UNITS       "0.01 nm"
    MAX-ACCESS  read-only
    STATUS      current
    DESCRIPTION
        "Wavelength of Optical Interface (unit: nm)"
    ::=  { virtualPortEntry 7 }

virtualPortFrequency OBJECT-TYPE
    SYNTAX      Unsigned32
    UNITS       "0.01 THz"
    MAX-ACCESS  read-only
    STATUS      current
    DESCRIPTION
        "Frequency of Optical Interface (unit: nm)"
    ::=  { virtualPortEntry 8 }

virtualPortAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { virtualPortEntry 9 }

virtualPortOperState OBJECT-TYPE
    SYNTAX      FspR7OperState
    MAX-ACCESS  read-only
    STATUS      current
    DESCRIPTION
        "The Operational State will be displayed on the
         GUI with full name values; it will be differently
         displayed in TL1 syntax according to TL1 display rules."
    ::=  { virtualPortEntry 10 }

virtualPortConnState OBJECT-TYPE
    SYNTAX      FspR7ConnectState
    MAX-ACCESS  read-only
    STATUS      current
    DESCRIPTION
        "Connection State"
    ::=  { virtualPortEntry 11 }

virtualPortEqlzAdmin OBJECT-TYPE
    SYNTAX      FspR7EqlzAdminState
    MAX-ACCESS  read-create
    STATUS      current
    DESCRIPTION
        "Scheduled Equalization Administration"
    ::=  { virtualPortEntry 12 }

virtualPortInitEqlz OBJECT-TYPE
    SYNTAX      FspR7InitEqualization
    MAX-ACCESS  read-write
    STATUS      current
    DESCRIPTION
        "Initiate Equalization"
    ::=  { virtualPortEntry 13 }

virtualPortInputPower OBJECT-TYPE
    SYNTAX      Integer32
    UNITS       "0.1 dBm"
    MAX-ACCESS  read-only
    STATUS      deprecated
    DESCRIPTION
        "Total Optical Input Power Received"
    ::=  { virtualPortEntry 14 }

virtualPortOutputPower OBJECT-TYPE
    SYNTAX      Integer32
    UNITS       "0.1 dBm"
    MAX-ACCESS  read-only
    STATUS      deprecated
    DESCRIPTION
        "Instantaneous Optical Power Transmitted (Output)"
    ::=  { virtualPortEntry 15 }

virtualPortSecondaryStates OBJECT-TYPE
    SYNTAX      FspR7EntitySecondaryStates
    MAX-ACCESS  read-only
    STATUS      current
    DESCRIPTION
        "Secondary States"
    ::=  { virtualPortEntry 16 }

virtualPortRate OBJECT-TYPE
    SYNTAX      Unsigned32
    UNITS       "Mbps"
    MAX-ACCESS  read-only
    STATUS      current
    DESCRIPTION
        "Derived from TYPE and possibly PAYLOAD"
    ::=  { virtualPortEntry 17 }

virtualPortCirRcv OBJECT-TYPE
    SYNTAX      Unsigned32
    UNITS       "Mbps"
    MAX-ACCESS  read-only
    STATUS      current
    DESCRIPTION
        "CIR (Committed Information Rate ) is used on Ethernet Interfaces with a policing function"
    ::=  { virtualPortEntry 18 }

virtualPortCbsRcv OBJECT-TYPE
    SYNTAX      Unsigned32 (0..26214400)
    UNITS       "Byte"
    MAX-ACCESS  read-only
    STATUS      current
    DESCRIPTION
        "Committed Burst Size"
    ::=  { virtualPortEntry 19 }

virtualPortCirTrmt OBJECT-TYPE
    SYNTAX      Unsigned32
    UNITS       "Mbps"
    MAX-ACCESS  read-only
    STATUS      current
    DESCRIPTION
        "CIR (Committed Information Rate ) is used on Ethernet Interfaces with a policing function"
    ::=  { virtualPortEntry 20 }

virtualPortCbsTrmt OBJECT-TYPE
    SYNTAX      Unsigned32 (0..25600)
    UNITS       "kByte"
    MAX-ACCESS  read-only
    STATUS      current
    DESCRIPTION
        "Committed Burst Size"
    ::=  { virtualPortEntry 21 }

virtualPortLagPorts OBJECT-TYPE
    SYNTAX      FspR7LagPorts
    MAX-ACCESS  read-only
    STATUS      current
    DESCRIPTION
        "A list of ports(AIDs) in the LAG."
    ::=  { virtualPortEntry 22 }

virtualPortLagPortType OBJECT-TYPE
    SYNTAX      FspR7LagPortType
    MAX-ACCESS  read-create
    STATUS      current
    DESCRIPTION
        "Type/Speed of connected ports in the Link Aggregation Group"
    ::=  { virtualPortEntry 23 }

virtualPortLagStandby OBJECT-TYPE
    SYNTAX      FspR7LagStandby
    MAX-ACCESS  read-only
    STATUS      current
    DESCRIPTION
        "Port is in standby in the Link Aggregation Group"
    ::=  { virtualPortEntry 24 }

virtualPortLacpMode OBJECT-TYPE
    SYNTAX      FspR7LacpMode
    MAX-ACCESS  read-create
    STATUS      current
    DESCRIPTION
        "Enable of LACP state machine"
    ::=  { virtualPortEntry 25 }

virtualPortLacpTimeout OBJECT-TYPE
    SYNTAX      FspR7LacpTimeout
    MAX-ACCESS  read-create
    STATUS      current
    DESCRIPTION
        "Timeout of the LACP"
    ::=  { virtualPortEntry 26 }

virtualPortLagActivePorts OBJECT-TYPE
    SYNTAX      Unsigned32 (1..12)
    MAX-ACCESS  read-create
    STATUS      current
    DESCRIPTION
        "Number of active ports in the Link Aggregation Group"
    ::=  { virtualPortEntry 27 }

virtualPortMacAddress OBJECT-TYPE
    SYNTAX      MacAddress
    MAX-ACCESS  read-only
    STATUS      current
    DESCRIPTION
        "Ethernet MAC address"
    ::=  { virtualPortEntry 28 }

virtualPortMaxFrameSize OBJECT-TYPE
    SYNTAX      Unsigned32 (1518..9600)
    MAX-ACCESS  read-create
    STATUS      current
    DESCRIPTION
        "Max Frame Size"
    ::=  { virtualPortEntry 29 }

virtualPortPortMode OBJECT-TYPE
    SYNTAX      FspR7PortMode
    MAX-ACCESS  read-create
    STATUS      current
    DESCRIPTION
        "Port Mode"
    ::=  { virtualPortEntry 30 }

virtualPortDataLayerPmReset OBJECT-TYPE
    SYNTAX      FspR7PmReset
    MAX-ACCESS  read-write
    STATUS      current
    DESCRIPTION
        "Reset data-layer Performance registers"
    ::=  { virtualPortEntry 31 }

virtualPortPortRole OBJECT-TYPE
    SYNTAX      FspR7PortRole
    MAX-ACCESS  read-create
    STATUS      current
    DESCRIPTION
        "ADVA cloud Port Roles"
    ::=  { virtualPortEntry 32 }

virtualPortPriority OBJECT-TYPE
    SYNTAX      Unsigned32 (0..7)
    MAX-ACCESS  read-create
    STATUS      current
    DESCRIPTION
        "Default PCP in case UTAG is Enabled. The Prio may be remapped in the EVC."
    ::=  { virtualPortEntry 33 }

virtualPortPvid OBJECT-TYPE
    SYNTAX      Unsigned32 (1..4095)
    MAX-ACCESS  read-create
    STATUS      current
    DESCRIPTION
        "Default VLAN ID (both STAG/CTAG mode) in case UTAG is enabled"
    ::=  { virtualPortEntry 34 }

virtualPortRevertiveMode OBJECT-TYPE
    SYNTAX      ApsRevertMode
    MAX-ACCESS  read-create
    STATUS      current
    DESCRIPTION
        "Revertive Protection Switching"
    ::=  { virtualPortEntry 35 }

virtualPortStagType OBJECT-TYPE
    SYNTAX      FspR7SnmpHexString
    MAX-ACCESS  read-create
    STATUS      current
    DESCRIPTION
        "TAG type field"
    ::=  { virtualPortEntry 36 }

virtualPortUtag OBJECT-TYPE
    SYNTAX      FspR7UntaggedFrames
    MAX-ACCESS  read-create
    STATUS      current
    DESCRIPTION
        "If untagged frames shall be enabled on this port or not."
    ::=  { virtualPortEntry 37 }

virtualPortBundle OBJECT-TYPE
    SYNTAX      FspR7SnmpLongString
    MAX-ACCESS  read-create
    STATUS      current
    DESCRIPTION
        "List of VC4/VC3/STS1/STS3c/STS24c/STS48c containers used in the BUNDLE"
    ::=  { virtualPortEntry 38 }

virtualPortSwitchCommand OBJECT-TYPE
    SYNTAX      FspR7APSCommand
    MAX-ACCESS  read-write
    STATUS      current
    DESCRIPTION   "The switch command action for this facility. A command resulting
         in a switch event will also cause a change of the facility secondary state
         and a corresponding condition. Addressed by this command is the active port,
         the port to switch away from. Since this is a manual switch command, it will
         not switch if other port suffers from a signalfailure or a signal degrade."
    ::=  { virtualPortEntry 39 }

virtualPortInhibitSwitchToWork OBJECT-TYPE
    SYNTAX      FspR7YesNo
    MAX-ACCESS  read-write
    STATUS      current
    DESCRIPTION   "Inhibit Switch to working facility. Inhibition blocks an automatic switch to the
         working facility. Valid only for the protection facility."
    ::=  { virtualPortEntry 40 }

virtualPortInhibitSwitchToProt OBJECT-TYPE
    SYNTAX      FspR7YesNo
    MAX-ACCESS  read-write
    STATUS      current
    DESCRIPTION   "Inhibit Switch to protection facility. Inhibition blocks an automatic switch
         to the protection facility. Valid only for the working facility."
    ::=  { virtualPortEntry 41 }

virtualPortMonLevel OBJECT-TYPE
    SYNTAX      FspR7MonLevel
    MAX-ACCESS  read-only
    STATUS      current
    DESCRIPTION
        "Indicates the highest level of intrusive/non-intrusive performance monitoring performed."
    ::=  { virtualPortEntry 42 }

virtualPortOduTribPortNo OBJECT-TYPE
    SYNTAX      SnmpAdminString
    MAX-ACCESS  read-create
    STATUS      current
    DESCRIPTION
        "ODU Tributary Port Number"
    ::=  { virtualPortEntry 43 }

virtualPortOduTribTimeSlottNo OBJECT-TYPE
    SYNTAX      SnmpAdminString
    MAX-ACCESS  read-create
    STATUS      current
    DESCRIPTION   "ODU Tributary slot number. Multiple values can be entered as a string, separated by commas or given as a range.
         For capabilities objects possible number of slots and valid range are displayed in a form:
         [1,2,3,8][count: 1-1]
         In first brackets valid slots are shown and in the second possible number of slots."
    ::=  { virtualPortEntry 44 }

virtualPortSigDegThresOdu OBJECT-TYPE
    SYNTAX      Integer32 (1..100)
    UNITS       "%"
    MAX-ACCESS  read-create
    STATUS      current
    DESCRIPTION
        "Background-Block-Error-Based Signal Degradation Definition for ODU"
    ::=  { virtualPortEntry 45 }

virtualPortSigDegPeriodOdu OBJECT-TYPE
    SYNTAX      Unsigned32 (2..10)
    UNITS       "s"
    MAX-ACCESS  read-create
    STATUS      current
    DESCRIPTION
        "Integration Period for Signal degrade"
    ::=  { virtualPortEntry 46 }

virtualPortTraceExpectedOdu OBJECT-TYPE
    SYNTAX      OCTET STRING (SIZE(0..15))
    MAX-ACCESS  read-create
    STATUS      current
    DESCRIPTION
        "Expected SAPI part of the ODU trace (15 character). NULL TRACE implies that no trace comparison is made."
    ::=  { virtualPortEntry 47 }

virtualPortTraceTransmitSapiOdu OBJECT-TYPE
    SYNTAX      OCTET STRING (SIZE(0..15))
    MAX-ACCESS  read-create
    STATUS      current
    DESCRIPTION
        "The transmitted SAPI part of the ODU trace (15 character)"
    ::=  { virtualPortEntry 48 }

virtualPortTraceTransmitDapiOdu OBJECT-TYPE
    SYNTAX      OCTET STRING (SIZE(0..15))
    MAX-ACCESS  read-create
    STATUS      current
    DESCRIPTION
        "The transmitted DAPI part of the ODU trace (15 character)"
    ::=  { virtualPortEntry 49 }

virtualPortTraceTransmitOpspOdu OBJECT-TYPE
    SYNTAX      OCTET STRING (SIZE(0..32))
    MAX-ACCESS  read-create
    STATUS      current
    DESCRIPTION
        "The transmitted Operator Specific part of the ODU trace (32 character)"
    ::=  { virtualPortEntry 50 }

virtualPortTimModeOdu OBJECT-TYPE
    SYNTAX      TimMode
    MAX-ACCESS  read-create
    STATUS      current
    DESCRIPTION
        "Detection of TIM-ODU Condition can be configured"
    ::=  { virtualPortEntry 51 }

virtualPortSigDegThresOduTcmA OBJECT-TYPE
    SYNTAX      Integer32 (1..100)
    UNITS       "%"
    MAX-ACCESS  read-create
    STATUS      current
    DESCRIPTION
        "Background-Block-Error-Based Signal Degradation Definition for TCM-A"
    ::=  { virtualPortEntry 52 }

virtualPortSigDegPeriodOduTcmA OBJECT-TYPE
    SYNTAX      Unsigned32 (2..10)
    UNITS       "s"
    MAX-ACCESS  read-create
    STATUS      current
    DESCRIPTION
        "Integration Period for Signal degrade"
    ::=  { virtualPortEntry 53 }

virtualPortSigDegThresOduTcmB OBJECT-TYPE
    SYNTAX      Integer32 (1..100)
    UNITS       "%"
    MAX-ACCESS  read-create
    STATUS      current
    DESCRIPTION
        "Background-Block-Error-Based Signal Degradation Definition for TCM-B"
    ::=  { virtualPortEntry 54 }

virtualPortSigDegPeriodOduTcmB OBJECT-TYPE
    SYNTAX      Unsigned32 (2..10)
    UNITS       "s"
    MAX-ACCESS  read-create
    STATUS      current
    DESCRIPTION
        "Integration Period of TCMB Signal Segrade"
    ::=  { virtualPortEntry 55 }

virtualPortSigDegThresOduTcmC OBJECT-TYPE
    SYNTAX      Integer32 (1..100)
    UNITS       "%"
    MAX-ACCESS  read-create
    STATUS      current
    DESCRIPTION
        "Background-Block-Error-Based Signal Degradation Definition for TCM-C"
    ::=  { virtualPortEntry 56 }

virtualPortSigDegPeriodOduTcmC OBJECT-TYPE
    SYNTAX      Unsigned32 (2..10)
    UNITS       "s"
    MAX-ACCESS  read-create
    STATUS      current
    DESCRIPTION
        "Integration Period of TCMC Signal Segrade"
    ::=  { virtualPortEntry 57 }

virtualPortTcmALevel OBJECT-TYPE
    SYNTAX      OtnTcmLevel
    MAX-ACCESS  read-create
    STATUS      current
    DESCRIPTION
        "Activation of Tandem Connection Monitoring Instance A"
    ::=  { virtualPortEntry 58 }

virtualPortTcmBLevel OBJECT-TYPE
    SYNTAX      OtnTcmLevel
    MAX-ACCESS  read-create
    STATUS      current
    DESCRIPTION
        "Activation of Tandem Connection Monitoring Instance B"
    ::=  { virtualPortEntry 59 }

virtualPortTcmCLevel OBJECT-TYPE
    SYNTAX      OtnTcmLevel
    MAX-ACCESS  read-create
    STATUS      current
    DESCRIPTION
        "Activation of Tandem Connection Monitoring Instance C"
    ::=  { virtualPortEntry 60 }

virtualPortTraceTransmitSapiOduTcmA OBJECT-TYPE
    SYNTAX      OCTET STRING (SIZE(0..15))
    MAX-ACCESS  read-create
    STATUS      current
    DESCRIPTION
        "The transmitted SAPI part of the TCMA trace (15 character)"
    ::=  { virtualPortEntry 61 }

virtualPortTraceTransmitDapiOduTcmA OBJECT-TYPE
    SYNTAX      OCTET STRING (SIZE(0..15))
    MAX-ACCESS  read-create
    STATUS      current
    DESCRIPTION
        "The transmitted DAPI part of the TCMA trace (15 character)"
    ::=  { virtualPortEntry 62 }

virtualPortTraceTransmitOpspOduTcmA OBJECT-TYPE
    SYNTAX      OCTET STRING (SIZE(0..32))
    MAX-ACCESS  read-create
    STATUS      current
    DESCRIPTION
        "The transmitted Operator Specific part of the TCMA trace (32 character)"
    ::=  { virtualPortEntry 63 }

virtualPortTraceExpectedOduTcmA OBJECT-TYPE
    SYNTAX      OCTET STRING (SIZE(0..15))
    MAX-ACCESS  read-create
    STATUS      current
    DESCRIPTION
        "Expected SAPI part of the TCMA trace (15 character). NULL TRACE-TCM implies that no trace comparison is made."
    ::=  { virtualPortEntry 64 }

virtualPortTimModeOduTcmA OBJECT-TYPE
    SYNTAX      TimMode
    MAX-ACCESS  read-create
    STATUS      current
    DESCRIPTION
        "Detection of TIM-TCMA Condition can be configured"
    ::=  { virtualPortEntry 65 }

virtualPortTraceExpectedOduTcmB OBJECT-TYPE
    SYNTAX      OCTET STRING (SIZE(0..15))
    MAX-ACCESS  read-create
    STATUS      current
    DESCRIPTION
        "Expected SAPI part of the TCMB trace (15 character). NULL TRACE-TCM implies that no trace comparison is made."
    ::=  { virtualPortEntry 66 }

virtualPortTraceTransmitSapiOduTcmB OBJECT-TYPE
    SYNTAX      OCTET STRING (SIZE(0..15))
    MAX-ACCESS  read-create
    STATUS      current
    DESCRIPTION
        "The transmitted SAPI part of the TCMB trace (15 character)"
    ::=  { virtualPortEntry 67 }

virtualPortTraceTransmitDapiOduTcmB OBJECT-TYPE
    SYNTAX      OCTET STRING (SIZE(0..15))
    MAX-ACCESS  read-create
    STATUS      current
    DESCRIPTION
        "The transmitted DAPI part of the TCMB trace (15 character)"
    ::=  { virtualPortEntry 68 }

virtualPortTraceTransmitOpspOduTcmB OBJECT-TYPE
    SYNTAX      OCTET STRING (SIZE(0..32))
    MAX-ACCESS  read-create
    STATUS      current
    DESCRIPTION
        "The transmitted Operator Specific part of the TCMB trace (32 character)"
    ::=  { virtualPortEntry 69 }

virtualPortTimModeOduTcmB OBJECT-TYPE
    SYNTAX      TimMode
    MAX-ACCESS  read-create
    STATUS      current
    DESCRIPTION
        "Detection of TIM-TCMB Condition can be configured"
    ::=  { virtualPortEntry 70 }

virtualPortTraceExpectedOduTcmC OBJECT-TYPE
    SYNTAX      OCTET STRING (SIZE(0..15))
    MAX-ACCESS  read-create
    STATUS      current
    DESCRIPTION
        "Expected SAPI part of the TCMC trace (15 character). NULL TRACE-TCM implies that no trace comparison is made."
    ::=  { virtualPortEntry 71 }

virtualPortTraceTransmitSapiOduTcmC OBJECT-TYPE
    SYNTAX      OCTET STRING (SIZE(0..15))
    MAX-ACCESS  read-create
    STATUS      current
    DESCRIPTION
        "The transmitted SAPI part of the TCMC trace (15 character)"
    ::=  { virtualPortEntry 72 }

virtualPortTraceTransmitDapiOduTcmC OBJECT-TYPE
    SYNTAX      OCTET STRING (SIZE(0..15))
    MAX-ACCESS  read-create
    STATUS      current
    DESCRIPTION
        "The transmitted DAPI part of the TCMC trace (15 character)"
    ::=  { virtualPortEntry 73 }

virtualPortTraceTransmitOpspOduTcmC OBJECT-TYPE
    SYNTAX      OCTET STRING (SIZE(0..32))
    MAX-ACCESS  read-create
    STATUS      current
    DESCRIPTION
        "The transmitted Operator Specific part of the TCMC trace (32 character)"
    ::=  { virtualPortEntry 74 }

virtualPortTimModeOduTcmC OBJECT-TYPE
    SYNTAX      TimMode
    MAX-ACCESS  read-create
    STATUS      current
    DESCRIPTION
        "Detection of TIM-TCMC Condition can be configured"
    ::=  { virtualPortEntry 75 }

virtualPortTraceRcvSapiOdu OBJECT-TYPE
    SYNTAX      OCTET STRING (SIZE(0..15))
    MAX-ACCESS  read-only
    STATUS      current
    DESCRIPTION
        "The received SAPI part of the ODU trace (15 character)"
    ::=  { virtualPortEntry 76 }

virtualPortTraceRcvDapiOdu OBJECT-TYPE
    SYNTAX      OCTET STRING (SIZE(0..15))
    MAX-ACCESS  read-only
    STATUS      current
    DESCRIPTION
        "The received DAPI part of the ODU trace (15 character)"
    ::=  { virtualPortEntry 77 }

virtualPortTraceRcvOpspOdu OBJECT-TYPE
    SYNTAX      OCTET STRING (SIZE(0..32))
    MAX-ACCESS  read-only
    STATUS      current
    DESCRIPTION
        "The received Operator Specific part of the ODU trace (32 character)"
    ::=  { virtualPortEntry 78 }

virtualPortTraceRcvSapiTcma OBJECT-TYPE
    SYNTAX      OCTET STRING (SIZE(0..15))
    MAX-ACCESS  read-only
    STATUS      current
    DESCRIPTION
        "The received SAPI part of the TCMA trace (15 character)"
    ::=  { virtualPortEntry 79 }

virtualPortTraceRcvDapiTcma OBJECT-TYPE
    SYNTAX      OCTET STRING (SIZE(0..15))
    MAX-ACCESS  read-only
    STATUS      current
    DESCRIPTION
        "The received DAPI part of the TCMA trace (15 character)"
    ::=  { virtualPortEntry 80 }

virtualPortTraceRcvOpspTcma OBJECT-TYPE
    SYNTAX      OCTET STRING (SIZE(0..32))
    MAX-ACCESS  read-only
    STATUS      current
    DESCRIPTION
        "The received Operator Specific part of the TCMA trace (32 character)"
    ::=  { virtualPortEntry 81 }

virtualPortTraceRcvSapiTcmb OBJECT-TYPE
    SYNTAX      OCTET STRING (SIZE(0..15))
    MAX-ACCESS  read-only
    STATUS      current
    DESCRIPTION
        "The received SAPI part of the TCMB trace (15 character)"
    ::=  { virtualPortEntry 82 }

virtualPortTraceRcvDapiTcmb OBJECT-TYPE
    SYNTAX      OCTET STRING (SIZE(0..15))
    MAX-ACCESS  read-only
    STATUS      current
    DESCRIPTION
        "The received DAPI part of the TCMB trace (15 character)"
    ::=  { virtualPortEntry 83 }

virtualPortTraceRcvOpspTcmb OBJECT-TYPE
    SYNTAX      OCTET STRING (SIZE(0..32))
    MAX-ACCESS  read-only
    STATUS      current
    DESCRIPTION
        "The received Operator Specific part of the TCMB trace (32 character)"
    ::=  { virtualPortEntry 84 }

virtualPortTraceRcvSapiTcmc OBJECT-TYPE
    SYNTAX      OCTET STRING (SIZE(0..15))
    MAX-ACCESS  read-only
    STATUS      current
    DESCRIPTION
        "The received SAPI part of the TCMC trace (15 character)"
    ::=  { virtualPortEntry 85 }

virtualPortTraceRcvDapiTcmc OBJECT-TYPE
    SYNTAX      OCTET STRING (SIZE(0..15))
    MAX-ACCESS  read-only
    STATUS      current
    DESCRIPTION
        "The received DAPI part of the TCMC trace (15 character)"
    ::=  { virtualPortEntry 86 }

virtualPortTraceRcvOpspTcmc OBJECT-TYPE
    SYNTAX      OCTET STRING (SIZE(0..32))
    MAX-ACCESS  read-only
    STATUS      current
    DESCRIPTION
        "The received Operator Specific part of the TCMC trace (32 character)"
    ::=  { virtualPortEntry 87 }

virtualPortTerminationLevel OBJECT-TYPE
    SYNTAX      OhTerminationLevel
    MAX-ACCESS  read-create
    STATUS      current
    DESCRIPTION
        "The entity is Addressable by Management [because its supporting entity is defined in the database and therefore its address existsSignal Tremination Level of Intrusive Access to Header Information.
         Not used in 7.0, monitoring is one layer higher than TERM level,
         if applicable. All conditions detected on monitoring layer will not
         be reported (severity degradated to NR)."
    ::=  { virtualPortEntry 88 }

virtualPortChannelSpacing OBJECT-TYPE
    SYNTAX      FspR7ChannelSpacing
    MAX-ACCESS  read-only
    STATUS      current
    DESCRIPTION
        "ITU Grid channel spacing"
    ::=  { virtualPortEntry 89 }

virtualPortCir OBJECT-TYPE
    SYNTAX      Unsigned32
    UNITS       "Mbps"
    MAX-ACCESS  read-create
    STATUS      current
    DESCRIPTION
        "CIR (Committed Information Rate ) is used on Ethernet Interfaces with a policing function"
    ::=  { virtualPortEntry 90 }

virtualPortLoopConfig OBJECT-TYPE
    SYNTAX      LoopConfig
    MAX-ACCESS  read-write
    STATUS      current
    DESCRIPTION
        "External or Facility Loopback"
    ::=  { virtualPortEntry 91 }

virtualPortOwnerAid OBJECT-TYPE
    SYNTAX      SnmpAdminString
    MAX-ACCESS  read-only
    STATUS      current
    DESCRIPTION
        "Owner AID"
    ::=  { virtualPortEntry 92 }

virtualPortPayload OBJECT-TYPE
    SYNTAX      OtnPayloadType
    MAX-ACCESS  read-only
    STATUS      current
    DESCRIPTION
        "The PAYLOAD defines the transport service type of the payload"
    ::=  { virtualPortEntry 93 }

virtualPortVcType OBJECT-TYPE
    SYNTAX      VirtualContainerType
    MAX-ACCESS  read-create
    STATUS      current
    DESCRIPTION
        "Virtual Container Group Type"
    ::=  { virtualPortEntry 94 }

virtualPortOdtuType OBJECT-TYPE
    SYNTAX      FspR7OdtuType
    MAX-ACCESS  read-only
    STATUS      current
    DESCRIPTION
        "ODTU Transport Unit"
    ::=  { virtualPortEntry 95 }

virtualPortProtectionRole OBJECT-TYPE
    SYNTAX      FspR7ProtectionRole
    MAX-ACCESS  read-only
    STATUS      current
    DESCRIPTION
        "Path label Working or Protect"
    ::=  { virtualPortEntry 96 }

virtualPortLagSysPrio OBJECT-TYPE
    SYNTAX      Unsigned32 (0..65535)
    MAX-ACCESS  read-only
    STATUS      current
    DESCRIPTION
        "Link Aggregation Group Actor System Priority Part of LAG ID"
    ::=  { virtualPortEntry 97 }

virtualPortOpuPayloadType OBJECT-TYPE
    SYNTAX      FspR7OpuPayloadType
    MAX-ACCESS  read-create
    STATUS      current
    DESCRIPTION
        "OPU Payload Type Indicator"
    ::=  { virtualPortEntry 98 }

virtualPortLagSysMac OBJECT-TYPE
    SYNTAX      MacAddress
    MAX-ACCESS  read-only
    STATUS      current
    DESCRIPTION
        "System MAC set to first member port"
    ::=  { virtualPortEntry 99 }

virtualPortLagSysIdFend OBJECT-TYPE
    SYNTAX      FspR7LagSysIdFend
    MAX-ACCESS  read-only
    STATUS      current
    DESCRIPTION
        "System ID (Pri&MAC) received from the Partner of the Link Aggregation Group."
    ::=  { virtualPortEntry 100 }

virtualPortValidSigTimer OBJECT-TYPE
    SYNTAX      Unsigned32 (0..5760)
    UNITS       "min"
    MAX-ACCESS  read-only
    STATUS      current
    DESCRIPTION
        "AINS state signal quality soak time remaining until transition to IS."
    ::=  { virtualPortEntry 101 }

virtualPortOtnStuffing OBJECT-TYPE
    SYNTAX      FspR7Stuff
    MAX-ACCESS  read-create
    STATUS      current
    DESCRIPTION
        "Indicates if bit/byte stuffing is used in the transport signal."
    ::=  { virtualPortEntry 102 }

virtualPortRedLineState OBJECT-TYPE
    SYNTAX      FspR7RedLinedState
    MAX-ACCESS  read-create
    STATUS      current
    DESCRIPTION
        "will be set by higher level software to act as a barrier to deletion"
    ::=  { virtualPortEntry 103 }

virtualPortTunnelAid OBJECT-TYPE
    SYNTAX      SnmpAdminString
    MAX-ACCESS  read-create
    STATUS      current
    DESCRIPTION
        "Tunnel AID"
    ::=  { virtualPortEntry 104 }

virtualPortIngressTid OBJECT-TYPE
    SYNTAX      SnmpAdminString
    MAX-ACCESS  read-only
    STATUS      current
    DESCRIPTION
        "Ingress Target ID"
    ::=  { virtualPortEntry 105 }

virtualPortIngressNodeIp OBJECT-TYPE
    SYNTAX      IpAddress
    MAX-ACCESS  read-only
    STATUS      current
    DESCRIPTION
        "Ingress Node IP"
    ::=  { virtualPortEntry 106 }

virtualPortEncapsulationMethod OBJECT-TYPE
    SYNTAX      FspR7EncapsulationMethod
    MAX-ACCESS  read-only
    STATUS      current
    DESCRIPTION
        "Indicates the encapsulation method being used."
    ::=  { virtualPortEntry 107 }

virtualPortPathProtection OBJECT-TYPE
    SYNTAX      FspR7PathProt
    MAX-ACCESS  read-only
    STATUS      current
    DESCRIPTION
        "Indicates the traffic path for path protection cases when the FFP does not exist. When the FFP exists, protected is indicated and the status is determined by the FFP."
    ::=  { virtualPortEntry 108 }

virtualPortTimeslot OBJECT-TYPE
    SYNTAX      Unsigned32 (0..1000)
    MAX-ACCESS  read-only
    STATUS      current
    DESCRIPTION
        "Time slots used"
    ::=  { virtualPortEntry 109 }

virtualPortOffsetHigh OBJECT-TYPE
    SYNTAX      Integer32 (-250..210)
    UNITS       "0.1 dBm"
    MAX-ACCESS  read-only
    STATUS      current
    DESCRIPTION
        "Sets the high level offset for power equalization in CCM"
    ::=  { virtualPortEntry 110 }

virtualPortOffsetLow OBJECT-TYPE
    SYNTAX      Integer32 (-250..210)
    UNITS       "0.1 dBm"
    MAX-ACCESS  read-only
    STATUS      current
    DESCRIPTION
        "Sets the low level offset for power equalization in CCM"
    ::=  { virtualPortEntry 111 }

virtualPortTrafficDirection OBJECT-TYPE
    SYNTAX      FspR7TrafficDirection
    MAX-ACCESS  read-create
    STATUS      current
    DESCRIPTION
        "Traffic Direction"
    ::=  { virtualPortEntry 112 }

virtualPortChannelId OBJECT-TYPE
    SYNTAX      Unsigned32 (1..256)
    MAX-ACCESS  read-create
    STATUS      current
    DESCRIPTION
        "Channel ID [1 ..256]"
    ::=  { virtualPortEntry 113 }

endOfFacilityMgmt OBJECT-TYPE
    SYNTAX      Integer32
    MAX-ACCESS  read-only
    STATUS      current
    DESCRIPTION
        ""
    ::=  { facilityMgmt 10000 }

linkTable OBJECT-TYPE
    SYNTAX      SEQUENCE OF LinkEntry
    MAX-ACCESS  not-accessible
    STATUS      current
    DESCRIPTION   "linkTable"
    ::=  { dcnMgmt 1 }

linkEntry OBJECT-TYPE
    SYNTAX      LinkEntry
    MAX-ACCESS  not-accessible
    STATUS      current
    DESCRIPTION   "Entry of linkTable"
    INDEX       {
                  entityDcnShelfNo,
                  entityDcnSlotNo,
                  entityDcnPortNo,
                  entityDcnExtNo,
                  entityDcnClassName
                }
    ::=  { linkTable 1 }

LinkEntry ::=  SEQUENCE
  { linkRowStatus RowStatus,
    linkType FspR7InterfaceType,
    linkAdmin FspR7AdminState,
    linkAlias SnmpAdminString,
    linkAuthString SnmpAdminString,
    linkConnector FspR7ConnectorType,
    linkProxyArp FspR7NoYes,
    linkOspf FspR7OspfMode,
    linkBaud FspR7Baund,
    linkAuthType FspR7CpAuthType,
    linkIpType FspR7IpType,
    linkMetric Unsigned32,
    linkAreaAid SnmpAdminString,
    linkEccAid SnmpAdminString,
    linkNearEndIp IpAddress,
    linkFarEndIp IpAddress,
    linkBitrate Unsigned32,
    linkParityBit FspR7ParityBit,
    linkSecondaryStates FspR7EntitySecondaryStates,
    linkOperState FspR7OperState,
    linkNendIpMonitor IpAddress,
    linkValidSigTimer Unsigned32,
    linkIPv6Type FspR7IPv6Type,
    linkNendIPv6 SnmpAdminString,
    linkFendIPv6 SnmpAdminString }

linkRowStatus OBJECT-TYPE
    SYNTAX      RowStatus
    MAX-ACCESS  read-create
    STATUS      current
    DESCRIPTION   "RowStatus object is used to create or delete a row in the table."
    ::=  { linkEntry 1 }

linkType OBJECT-TYPE
    SYNTAX      FspR7InterfaceType
    MAX-ACCESS  read-create
    STATUS      current
    DESCRIPTION
        "The TYPE defines the transport service type as wrapper with wrapper layer termination OR else as payload"
    ::=  { linkEntry 2 }

linkAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { linkEntry 3 }

linkAlias OBJECT-TYPE
    SYNTAX      SnmpAdminString
    MAX-ACCESS  read-create
    STATUS      current
    DESCRIPTION
        "User Applied Descriptor"
    ::=  { linkEntry 4 }

linkAuthString OBJECT-TYPE
    SYNTAX      SnmpAdminString
    MAX-ACCESS  read-create
    STATUS      current
    DESCRIPTION
        "OSPF Authentication Key/String depending on Authentication Type"
    ::=  { linkEntry 5 }

linkConnector OBJECT-TYPE
    SYNTAX      FspR7ConnectorType
    MAX-ACCESS  read-only
    STATUS      current
    DESCRIPTION
        "Connector Type"
    ::=  { linkEntry 6 }

linkProxyArp OBJECT-TYPE
    SYNTAX      FspR7NoYes
    MAX-ACCESS  read-create
    STATUS      current
    DESCRIPTION
        "If enabled then ARP requests for FENDIP (coming in on another interface in the same subnet as FENDIP) will be replied too."
    ::=  { linkEntry 7 }

linkOspf OBJECT-TYPE
    SYNTAX      FspR7OspfMode
    MAX-ACCESS  read-create
    STATUS      current
    DESCRIPTION
        "OSPF Routing (Dynamic)"
    ::=  { linkEntry 8 }

linkBaud OBJECT-TYPE
    SYNTAX      FspR7Baund
    MAX-ACCESS  read-create
    STATUS      current
    DESCRIPTION
        "Baud rate of the serial interface"
    ::=  { linkEntry 9 }

linkAuthType OBJECT-TYPE
    SYNTAX      FspR7CpAuthType
    MAX-ACCESS  read-create
    STATUS      current
    DESCRIPTION
        "OSPF Authentication Type"
    ::=  { linkEntry 10 }

linkIpType OBJECT-TYPE
    SYNTAX      FspR7IpType
    MAX-ACCESS  read-create
    STATUS      current
    DESCRIPTION
        "Type of IP configuration"
    ::=  { linkEntry 11 }

linkMetric OBJECT-TYPE
    SYNTAX      Unsigned32 (0..65535)
    MAX-ACCESS  read-create
    STATUS      current
    DESCRIPTION
        "Routing Metric"
    ::=  { linkEntry 12 }

linkAreaAid OBJECT-TYPE
    SYNTAX      SnmpAdminString
    MAX-ACCESS  read-create
    STATUS      current
    DESCRIPTION
        "OSPF Area AID"
    ::=  { linkEntry 13 }

linkEccAid OBJECT-TYPE
    SYNTAX      SnmpAdminString
    MAX-ACCESS  read-only
    STATUS      current
    DESCRIPTION
        "Address Identifier of ECC Entity."
    ::=  { linkEntry 14 }

linkNearEndIp OBJECT-TYPE
    SYNTAX      IpAddress
    MAX-ACCESS  read-create
    STATUS      current
    DESCRIPTION
        "IP Address assigned to PPP Termination Point on Near-End NE. Defaults to System IP address"
    ::=  { linkEntry 15 }

linkFarEndIp OBJECT-TYPE
    SYNTAX      IpAddress
    MAX-ACCESS  read-only
    STATUS      current
    DESCRIPTION
        "IP Address assigned to PPP Termination Point on Far-End NE. Default is set by NE System on LINK establishment if FENDIPACPT = Y"
    ::=  { linkEntry 16 }

linkBitrate OBJECT-TYPE
    SYNTAX      Unsigned32 (1..13702)
    UNITS       "kbps"
    MAX-ACCESS  read-create
    STATUS      current
    DESCRIPTION
        "Maximum provisioned bit rate for PPP/IP Link of transmitter for an ECC"
    ::=  { linkEntry 17 }

linkParityBit OBJECT-TYPE
    SYNTAX      FspR7ParityBit
    MAX-ACCESS  read-only
    STATUS      current
    DESCRIPTION
        "Parity Bit Settings"
    ::=  { linkEntry 18 }

linkSecondaryStates OBJECT-TYPE
    SYNTAX      FspR7EntitySecondaryStates
    MAX-ACCESS  read-only
    STATUS      current
    DESCRIPTION
        "Secondary States"
    ::=  { linkEntry 19 }

linkOperState OBJECT-TYPE
    SYNTAX      FspR7OperState
    MAX-ACCESS  read-only
    STATUS      current
    DESCRIPTION
        "The Operational State will be displayed on the
         GUI with full name values; it will be differently
         displayed in TL1 syntax according to TL1 display rules."
    ::=  { linkEntry 20 }

linkNendIpMonitor OBJECT-TYPE
    SYNTAX      IpAddress
    MAX-ACCESS  read-only
    STATUS      current
    DESCRIPTION
        "IP address assigned to Near-End NE"
    ::=  { linkEntry 21 }

linkValidSigTimer OBJECT-TYPE
    SYNTAX      Unsigned32 (0..5760)
    UNITS       "min"
    MAX-ACCESS  read-only
    STATUS      current
    DESCRIPTION
        "AINS state signal quality soak time remaining until transition to IS."
    ::=  { linkEntry 22 }

linkIPv6Type OBJECT-TYPE
    SYNTAX      FspR7IPv6Type
    MAX-ACCESS  read-create
    STATUS      current
    DESCRIPTION
        "Type of IPv6 configuration"
    ::=  { linkEntry 23 }

linkNendIPv6 OBJECT-TYPE
    SYNTAX      SnmpAdminString
    MAX-ACCESS  read-create
    STATUS      current
    DESCRIPTION
        "IPv6 Address assigned to PPP Termination Point on Near-End NE."
    ::=  { linkEntry 24 }

linkFendIPv6 OBJECT-TYPE
    SYNTAX      SnmpAdminString
    MAX-ACCESS  read-only
    STATUS      current
    DESCRIPTION
        "IPv6 Address assigned to PPP Termination Point on Far-End NE."
    ::=  { linkEntry 25 }

endOfLinkTable OBJECT-TYPE
    SYNTAX      Integer32
    MAX-ACCESS  read-only
    STATUS      current
    DESCRIPTION
        ""
    ::=  { dcnMgmt 2 }

scTable OBJECT-TYPE
    SYNTAX      SEQUENCE OF ScEntry
    MAX-ACCESS  not-accessible
    STATUS      current
    DESCRIPTION   "scTable"
    ::=  { dcnMgmt 3 }

scEntry OBJECT-TYPE
    SYNTAX      ScEntry
    MAX-ACCESS  not-accessible
    STATUS      current
    DESCRIPTION   "Entry of scTable"
    INDEX       {
                  entityDcnShelfNo,
                  entityDcnSlotNo,
                  entityDcnPortNo,
                  entityDcnExtNo,
                  entityDcnClassName
                }
    ::=  { scTable 1 }

ScEntry ::=  SEQUENCE
  { scRowStatus RowStatus,
    scType FspR7InterfaceType,
    scAdmin FspR7AdminState,
    scAlias SnmpAdminString,
    scAuthString SnmpAdminString,
    scConnector FspR7ConnectorType,
    scOspf FspR7OspfMode,
    scAuthType FspR7CpAuthType,
    scIpType FspR7IpType,
    scMetric Unsigned32,
    scAreaAid SnmpAdminString,
    scAlsMode FspR7AlsMode,
    scSigDegThresReceiver Unsigned32,
    scAutonegotiation EnableState,
    scPhysIfBaseType FspR7InterfaceType,
    scBitrate FspR7Bitrate,
    scConnectionType FspR7TypeConnection,
    scChannel FspR7ChannelIdentifier,
    scDuplex EthDuplexMode,
    scFarEndTid SnmpAdminString,
    scFiberType FspR7OpticalFiberType,
    scTrmtFrequency Unsigned32,
    scAttGradientTh Unsigned32,
    scIpAddr IpAddress,
    scTrmtWavelength Unsigned32,
    scLanAid SnmpAdminString,
    scIpMask IpAddress,
    scDataLayerPmReset FspR7PmReset,
    scPriority Unsigned32,
    scReach FspR7OpticalInterfaceReach,
    scSecondaryStates FspR7EntitySecondaryStates,
    scOperState FspR7OperState,
    scIpAddrMonitor IpAddress,
    scMonitoredDuplexMode EthDuplexMode,
    scMonitoredBitrate Unsigned32,
    scIpMaskMonitor IpAddress,
    scFarEndPort SnmpAdminString,
    scFendTransportTermPoint SnmpAdminString,
    scFarEndIp IpAddress,
    scFarEndSigDegThres Unsigned32,
    scValidSigTimer Unsigned32,
    scIPv6 SnmpAdminString,
    scIPv6PrefixLen Unsigned32,
    scIPv6LinkLocal SnmpAdminString,
    scIpMode FspR7IpMode,
    scGatewayProxyArp FspR7EnableDisable }

scRowStatus OBJECT-TYPE
    SYNTAX      RowStatus
    MAX-ACCESS  read-create
    STATUS      current
    DESCRIPTION   "RowStatus object is used to create or delete a row in the table."
    ::=  { scEntry 1 }

scType OBJECT-TYPE
    SYNTAX      FspR7InterfaceType
    MAX-ACCESS  read-create
    STATUS      current
    DESCRIPTION
        "The TYPE defines the transport service type as wrapper with wrapper layer termination OR else as payload"
    ::=  { scEntry 2 }

scAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { scEntry 3 }

scAlias OBJECT-TYPE
    SYNTAX      SnmpAdminString
    MAX-ACCESS  read-create
    STATUS      current
    DESCRIPTION
        "User Applied Descriptor"
    ::=  { scEntry 4 }

scAuthString OBJECT-TYPE
    SYNTAX      SnmpAdminString
    MAX-ACCESS  read-create
    STATUS      current
    DESCRIPTION
        "OSPF Authentication Key/String depending on Authentication Type"
    ::=  { scEntry 5 }

scConnector OBJECT-TYPE
    SYNTAX      FspR7ConnectorType
    MAX-ACCESS  read-only
    STATUS      current
    DESCRIPTION
        "Connector Type"
    ::=  { scEntry 6 }

scOspf OBJECT-TYPE
    SYNTAX      FspR7OspfMode
    MAX-ACCESS  read-create
    STATUS      current
    DESCRIPTION
        "OSPF Routing (Dynamic)"
    ::=  { scEntry 7 }

scAuthType OBJECT-TYPE
    SYNTAX      FspR7CpAuthType
    MAX-ACCESS  read-create
    STATUS      current
    DESCRIPTION
        "OSPF Authentication Type"
    ::=  { scEntry 8 }

scIpType OBJECT-TYPE
    SYNTAX      FspR7IpType
    MAX-ACCESS  read-create
    STATUS      current
    DESCRIPTION
        "Type of IP configuration"
    ::=  { scEntry 9 }

scMetric OBJECT-TYPE
    SYNTAX      Unsigned32 (0..65535)
    MAX-ACCESS  read-create
    STATUS      current
    DESCRIPTION
        "Routing Metric"
    ::=  { scEntry 10 }

scAreaAid OBJECT-TYPE
    SYNTAX      SnmpAdminString
    MAX-ACCESS  read-create
    STATUS      current
    DESCRIPTION
        "OSPF Area AID"
    ::=  { scEntry 11 }

scAlsMode OBJECT-TYPE
    SYNTAX      FspR7AlsMode
    MAX-ACCESS  read-create
    STATUS      current
    DESCRIPTION
        "Determines the reaction in backward direction in response to a LOS
         on the same Interface: on a Network Interface connected to the DWDM
         this is a matter of laser safety"
    ::=  { scEntry 12 }

scSigDegThresReceiver OBJECT-TYPE
    SYNTAX      Unsigned32
    UNITS       "0.1 dB"
    MAX-ACCESS  read-create
    STATUS      current
    DESCRIPTION
        "Signal Degrade Threshold on Receiver. Reported as ATTRMT-SDHT to far end."
    ::=  { scEntry 13 }

scAutonegotiation OBJECT-TYPE
    SYNTAX      EnableState
    MAX-ACCESS  read-create
    STATUS      current
    DESCRIPTION
        "Auto Negotiation for the data rate"
    ::=  { scEntry 14 }

scPhysIfBaseType OBJECT-TYPE
    SYNTAX      FspR7InterfaceType
    MAX-ACCESS  read-only
    STATUS      current
    DESCRIPTION
        "The type of the physical interface. Will be nedded for LANIP interfaces to deliver information about the BASE facility type."
    ::=  { scEntry 15 }

scBitrate OBJECT-TYPE
    SYNTAX      FspR7Bitrate
    MAX-ACCESS  read-create
    STATUS      current
    DESCRIPTION
        "Provisioned data rate"
    ::=  { scEntry 16 }

scConnectionType OBJECT-TYPE
    SYNTAX      FspR7TypeConnection
    MAX-ACCESS  read-only
    STATUS      current
    DESCRIPTION
        "Connectivity Parameters for Facilities"
    ::=  { scEntry 17 }

scChannel OBJECT-TYPE
    SYNTAX      FspR7ChannelIdentifier
    MAX-ACCESS  read-only
    STATUS      current
    DESCRIPTION
        "Channel"
    ::=  { scEntry 18 }

scDuplex OBJECT-TYPE
    SYNTAX      EthDuplexMode
    MAX-ACCESS  read-create
    STATUS      current
    DESCRIPTION
        "Duplex Mode Provision."
    ::=  { scEntry 19 }

scFarEndTid OBJECT-TYPE
    SYNTAX      SnmpAdminString
    MAX-ACCESS  read-only
    STATUS      current
    DESCRIPTION
        "Far End Target ID"
    ::=  { scEntry 20 }

scFiberType OBJECT-TYPE
    SYNTAX      FspR7OpticalFiberType
    MAX-ACCESS  read-only
    STATUS      current
    DESCRIPTION
        "Fiber of Optical Interface - Provision, Reference to FIBER__INVENTORY"
    ::=  { scEntry 21 }

scTrmtFrequency OBJECT-TYPE
    SYNTAX      Unsigned32
    UNITS       "0.01 THz"
    MAX-ACCESS  read-only
    STATUS      current
    DESCRIPTION
        "Frequency of Optical Interface (unit: nm)"
    ::=  { scEntry 22 }

scAttGradientTh OBJECT-TYPE
    SYNTAX      Unsigned32 (5..30)
    UNITS       "0.1 dB/min"
    MAX-ACCESS  read-create
    STATUS      current
    DESCRIPTION   "Attenuation Gradient Threshold on Receive Fiber. Applies to both
         TRMT and RCV directions; but threshold violation is reported for
         each direction separately by the 'tapping' alarms: INTRUDE-RCV
         and INTRUDE-TRMT."
    ::=  { scEntry 23 }

scIpAddr OBJECT-TYPE
    SYNTAX      IpAddress
    MAX-ACCESS  read-create
    STATUS      current
    DESCRIPTION
        "IP Address assigned to LAN IP Interface"
    ::=  { scEntry 24 }

scTrmtWavelength OBJECT-TYPE
    SYNTAX      Unsigned32
    UNITS       "0.01 nm"
    MAX-ACCESS  read-only
    STATUS      current
    DESCRIPTION
        "Wavelength of Optical Interface (unit: nm)"
    ::=  { scEntry 25 }

scLanAid OBJECT-TYPE
    SYNTAX      SnmpAdminString
    MAX-ACCESS  read-create
    STATUS      current
    DESCRIPTION
        "AID of LAN"
    ::=  { scEntry 26 }

scIpMask OBJECT-TYPE
    SYNTAX      IpAddress
    MAX-ACCESS  read-create
    STATUS      current
    DESCRIPTION
        "IP MASK assigned to LAN IP Interface"
    ::=  { scEntry 27 }

scDataLayerPmReset OBJECT-TYPE
    SYNTAX      FspR7PmReset
    MAX-ACCESS  read-write
    STATUS      current
    DESCRIPTION
        "Reset data-layer Performance registers"
    ::=  { scEntry 28 }

scPriority OBJECT-TYPE
    SYNTAX      Unsigned32 (0..255)
    MAX-ACCESS  read-create
    STATUS      current
    DESCRIPTION
        "Priority"
    ::=  { scEntry 29 }

scReach OBJECT-TYPE
    SYNTAX      FspR7OpticalInterfaceReach
    MAX-ACCESS  read-only
    STATUS      current
    DESCRIPTION
        "Reach"
    ::=  { scEntry 30 }

scSecondaryStates OBJECT-TYPE
    SYNTAX      FspR7EntitySecondaryStates
    MAX-ACCESS  read-only
    STATUS      current
    DESCRIPTION
        "Secondary States"
    ::=  { scEntry 31 }

scOperState OBJECT-TYPE
    SYNTAX      FspR7OperState
    MAX-ACCESS  read-only
    STATUS      current
    DESCRIPTION
        "The Operational State will be displayed on the
         GUI with full name values; it will be differently
         displayed in TL1 syntax according to TL1 display rules."
    ::=  { scEntry 32 }

scIpAddrMonitor OBJECT-TYPE
    SYNTAX      IpAddress
    MAX-ACCESS  read-only
    STATUS      current
    DESCRIPTION
        "IP address assigned to LAN IP Interface"
    ::=  { scEntry 33 }

scMonitoredDuplexMode OBJECT-TYPE
    SYNTAX      EthDuplexMode
    MAX-ACCESS  read-only
    STATUS      current
    DESCRIPTION
        "Monitored Duplex Mode. Available if AUTONEG=ENABLE"
    ::=  { scEntry 34 }

scMonitoredBitrate OBJECT-TYPE
    SYNTAX      Unsigned32
    UNITS       "Mbps"
    MAX-ACCESS  read-only
    STATUS      current
    DESCRIPTION
        "Bit Rate read from card, - relevant to- auto clock"
    ::=  { scEntry 35 }

scIpMaskMonitor OBJECT-TYPE
    SYNTAX      IpAddress
    MAX-ACCESS  read-only
    STATUS      current
    DESCRIPTION
        "IP mask assigned to LAN IP Interface"
    ::=  { scEntry 36 }

scFarEndPort OBJECT-TYPE
    SYNTAX      SnmpAdminString
    MAX-ACCESS  read-only
    STATUS      current
    DESCRIPTION
        "Far End DCN Port (SC-*)"
    ::=  { scEntry 37 }

scFendTransportTermPoint OBJECT-TYPE
    SYNTAX      SnmpAdminString
    MAX-ACCESS  read-only
    STATUS      current
    DESCRIPTION
        "Far End Transport Layer Termination Point (OL-* for WDM)"
    ::=  { scEntry 38 }

scFarEndIp OBJECT-TYPE
    SYNTAX      IpAddress
    MAX-ACCESS  read-only
    STATUS      current
    DESCRIPTION
        "Far End IP Address as seen by the neighbor discovery protocol"
    ::=  { scEntry 39 }

scFarEndSigDegThres OBJECT-TYPE
    SYNTAX      Unsigned32
    UNITS       "0.1 dB"
    MAX-ACCESS  read-only
    STATUS      current
    DESCRIPTION
        "Far End Signal Degrade Threshold"
    ::=  { scEntry 40 }

scValidSigTimer OBJECT-TYPE
    SYNTAX      Unsigned32 (0..5760)
    UNITS       "min"
    MAX-ACCESS  read-only
    STATUS      current
    DESCRIPTION
        "AINS state signal quality soak time remaining until transition to IS."
    ::=  { scEntry 41 }

scIPv6 OBJECT-TYPE
    SYNTAX      SnmpAdminString
    MAX-ACCESS  read-create
    STATUS      current
    DESCRIPTION
        "IPv6 Address"
    ::=  { scEntry 42 }

scIPv6PrefixLen OBJECT-TYPE
    SYNTAX      Unsigned32 (0..128)
    MAX-ACCESS  read-create
    STATUS      current
    DESCRIPTION
        "IPv6 Subnet Prefix Length"
    ::=  { scEntry 43 }

scIPv6LinkLocal OBJECT-TYPE
    SYNTAX      SnmpAdminString
    MAX-ACCESS  read-only
    STATUS      current
    DESCRIPTION
        "IPv6 Link Local Address. This address is derived from MAC"
    ::=  { scEntry 44 }

scIpMode OBJECT-TYPE
    SYNTAX      FspR7IpMode
    MAX-ACCESS  read-create
    STATUS      current
    DESCRIPTION
        "IP Mode of Operation either IPv4 only or IPv4 and IPv6. When operation supports IPv6, it is used for addresses external to the network."
    ::=  { scEntry 45 }

scGatewayProxyArp OBJECT-TYPE
    SYNTAX      FspR7EnableDisable
    MAX-ACCESS  read-create
    STATUS      current
    DESCRIPTION
        "Gateway works as an ARP proxy"
    ::=  { scEntry 46 }

endOfScTable OBJECT-TYPE
    SYNTAX      Integer32
    MAX-ACCESS  read-only
    STATUS      current
    DESCRIPTION
        ""
    ::=  { dcnMgmt 4 }

lanTable OBJECT-TYPE
    SYNTAX      SEQUENCE OF LanEntry
    MAX-ACCESS  not-accessible
    STATUS      current
    DESCRIPTION   "lanTable"
    ::=  { dcnMgmt 5 }

lanEntry OBJECT-TYPE
    SYNTAX      LanEntry
    MAX-ACCESS  not-accessible
    STATUS      current
    DESCRIPTION   "Entry of lanTable"
    INDEX       {
                  entityDcnShelfNo,
                  entityDcnSlotNo,
                  entityDcnPortNo,
                  entityDcnExtNo,
                  entityDcnClassName
                }
    ::=  { lanTable 1 }

LanEntry ::=  SEQUENCE
  { lanRowStatus RowStatus,
    lanType FspR7InterfaceType,
    lanAdmin FspR7AdminState,
    lanAlias SnmpAdminString,
    lanAuthString SnmpAdminString,
    lanOspf FspR7OspfMode,
    lanAuthType FspR7CpAuthType,
    lanIpType FspR7IpType,
    lanMetric Unsigned32,
    lanAreaAid SnmpAdminString,
    lanIpAddr IpAddress,
    lanIpMask IpAddress,
    lanPriority Unsigned32,
    lanLanMembers SnmpAdminString,
    lanSecondaryStates FspR7EntitySecondaryStates,
    lanOperState FspR7OperState,
    lanIpAddrMonitor IpAddress,
    lanIpMaskMonitor IpAddress,
    lanValidSigTimer Unsigned32,
    lanIPv6 SnmpAdminString,
    lanIPv6PrefixLen Unsigned32,
    lanIPv6LinkLocal SnmpAdminString,
    lanIpMode FspR7IpMode }

lanRowStatus OBJECT-TYPE
    SYNTAX      RowStatus
    MAX-ACCESS  read-create
    STATUS      current
    DESCRIPTION   "RowStatus object is used to create or delete a row in the table."
    ::=  { lanEntry 1 }

lanType OBJECT-TYPE
    SYNTAX      FspR7InterfaceType
    MAX-ACCESS  read-create
    STATUS      current
    DESCRIPTION
        "The TYPE defines the transport service type as wrapper with wrapper layer termination OR else as payload"
    ::=  { lanEntry 2 }

lanAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { lanEntry 3 }

lanAlias OBJECT-TYPE
    SYNTAX      SnmpAdminString
    MAX-ACCESS  read-create
    STATUS      current
    DESCRIPTION
        "User Applied Descriptor"
    ::=  { lanEntry 4 }

lanAuthString OBJECT-TYPE
    SYNTAX      SnmpAdminString
    MAX-ACCESS  read-create
    STATUS      current
    DESCRIPTION
        "OSPF Authentication Key/String depending on Authentication Type"
    ::=  { lanEntry 5 }

lanOspf OBJECT-TYPE
    SYNTAX      FspR7OspfMode
    MAX-ACCESS  read-create
    STATUS      current
    DESCRIPTION
        "OSPF Routing (Dynamic)"
    ::=  { lanEntry 6 }

lanAuthType OBJECT-TYPE
    SYNTAX      FspR7CpAuthType
    MAX-ACCESS  read-create
    STATUS      current
    DESCRIPTION
        "OSPF Authentication Type"
    ::=  { lanEntry 7 }

lanIpType OBJECT-TYPE
    SYNTAX      FspR7IpType
    MAX-ACCESS  read-create
    STATUS      current
    DESCRIPTION
        "Type of IP configuration"
    ::=  { lanEntry 8 }

lanMetric OBJECT-TYPE
    SYNTAX      Unsigned32 (0..65535)
    MAX-ACCESS  read-create
    STATUS      current
    DESCRIPTION
        "Routing Metric"
    ::=  { lanEntry 9 }

lanAreaAid OBJECT-TYPE
    SYNTAX      SnmpAdminString
    MAX-ACCESS  read-create
    STATUS      current
    DESCRIPTION
        "OSPF Area AID"
    ::=  { lanEntry 10 }

lanIpAddr OBJECT-TYPE
    SYNTAX      IpAddress
    MAX-ACCESS  read-create
    STATUS      current
    DESCRIPTION
        "IP Address assigned to LAN IP Interface"
    ::=  { lanEntry 11 }

lanIpMask OBJECT-TYPE
    SYNTAX      IpAddress
    MAX-ACCESS  read-create
    STATUS      current
    DESCRIPTION
        "IP MASK assigned to LAN IP Interface"
    ::=  { lanEntry 12 }

lanPriority OBJECT-TYPE
    SYNTAX      Unsigned32 (0..255)
    MAX-ACCESS  read-create
    STATUS      current
    DESCRIPTION
        "Priority"
    ::=  { lanEntry 13 }

lanLanMembers OBJECT-TYPE
    SYNTAX      SnmpAdminString
    MAX-ACCESS  read-only
    STATUS      current
    DESCRIPTION
        "List of Entity AID's (modules, ports) belonging to this LAN"
    ::=  { lanEntry 14 }

lanSecondaryStates OBJECT-TYPE
    SYNTAX      FspR7EntitySecondaryStates
    MAX-ACCESS  read-only
    STATUS      current
    DESCRIPTION
        "Secondary States"
    ::=  { lanEntry 15 }

lanOperState OBJECT-TYPE
    SYNTAX      FspR7OperState
    MAX-ACCESS  read-only
    STATUS      current
    DESCRIPTION
        "The Operational State will be displayed on the
         GUI with full name values; it will be differently
         displayed in TL1 syntax according to TL1 display rules."
    ::=  { lanEntry 16 }

lanIpAddrMonitor OBJECT-TYPE
    SYNTAX      IpAddress
    MAX-ACCESS  read-only
    STATUS      current
    DESCRIPTION
        "IP address assigned to LAN IP Interface"
    ::=  { lanEntry 17 }

lanIpMaskMonitor OBJECT-TYPE
    SYNTAX      IpAddress
    MAX-ACCESS  read-only
    STATUS      current
    DESCRIPTION
        "IP mask assigned to LAN IP Interface"
    ::=  { lanEntry 18 }

lanValidSigTimer OBJECT-TYPE
    SYNTAX      Unsigned32 (0..5760)
    UNITS       "min"
    MAX-ACCESS  read-only
    STATUS      current
    DESCRIPTION
        "AINS state signal quality soak time remaining until transition to IS."
    ::=  { lanEntry 19 }

lanIPv6 OBJECT-TYPE
    SYNTAX      SnmpAdminString
    MAX-ACCESS  read-create
    STATUS      current
    DESCRIPTION
        "IPv6 Address"
    ::=  { lanEntry 20 }

lanIPv6PrefixLen OBJECT-TYPE
    SYNTAX      Unsigned32 (0..128)
    MAX-ACCESS  read-create
    STATUS      current
    DESCRIPTION
        "IPv6 Subnet Prefix Length"
    ::=  { lanEntry 21 }

lanIPv6LinkLocal OBJECT-TYPE
    SYNTAX      SnmpAdminString
    MAX-ACCESS  read-only
    STATUS      current
    DESCRIPTION
        "IPv6 Link Local Address. This address is derived from MAC"
    ::=  { lanEntry 22 }

lanIpMode OBJECT-TYPE
    SYNTAX      FspR7IpMode
    MAX-ACCESS  read-create
    STATUS      current
    DESCRIPTION
        "IP Mode of Operation either IPv4 only or IPv4 and IPv6. When operation supports IPv6, it is used for addresses external to the network."
    ::=  { lanEntry 23 }

endOfLanTable OBJECT-TYPE
    SYNTAX      Integer32
    MAX-ACCESS  read-only
    STATUS      current
    DESCRIPTION
        ""
    ::=  { dcnMgmt 6 }

eccTable OBJECT-TYPE
    SYNTAX      SEQUENCE OF EccEntry
    MAX-ACCESS  not-accessible
    STATUS      current
    DESCRIPTION   "eccTable (Embedded Communication Channel)"
    ::=  { dcnMgmt 7 }

eccEntry OBJECT-TYPE
    SYNTAX      EccEntry
    MAX-ACCESS  not-accessible
    STATUS      current
    DESCRIPTION   "Entry of eccTable"
    INDEX       {
                  entityDcnShelfNo,
                  entityDcnSlotNo,
                  entityDcnPortNo,
                  entityDcnExtNo,
                  entityDcnClassName
                }
    ::=  { eccTable 1 }

EccEntry ::=  SEQUENCE
  { eccRowStatus RowStatus,
    eccType FspR7InterfaceType,
    eccAdmin FspR7AdminState,
    eccAlias SnmpAdminString,
    eccConnectionType FspR7TypeConnection,
    eccLanAid SnmpAdminString,
    eccExternalVid Unsigned32,
    eccpppIpLinkAid SnmpAdminString,
    eccMaxDataRate Unsigned32,
    eccProtAvailability FspR7EocProtAvailability,
    eccSecondaryStates FspR7EntitySecondaryStates,
    eccConnState FspR7ConnectState,
    eccOperState FspR7OperState,
    eccValidSigTimer Unsigned32 }

eccRowStatus OBJECT-TYPE
    SYNTAX      RowStatus
    MAX-ACCESS  read-create
    STATUS      current
    DESCRIPTION   "RowStatus object is used to create or delete a row in the table."
    ::=  { eccEntry 1 }

eccType OBJECT-TYPE
    SYNTAX      FspR7InterfaceType
    MAX-ACCESS  read-create
    STATUS      current
    DESCRIPTION
        "The TYPE defines the transport service type as wrapper with wrapper layer termination OR else as payload"
    ::=  { eccEntry 2 }

eccAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { eccEntry 3 }

eccAlias OBJECT-TYPE
    SYNTAX      SnmpAdminString
    MAX-ACCESS  read-create
    STATUS      current
    DESCRIPTION
        "User Applied Descriptor"
    ::=  { eccEntry 4 }

eccConnectionType OBJECT-TYPE
    SYNTAX      FspR7TypeConnection
    MAX-ACCESS  read-only
    STATUS      current
    DESCRIPTION
        "Connectivity Parameters for Facilities"
    ::=  { eccEntry 5 }

eccLanAid OBJECT-TYPE
    SYNTAX      SnmpAdminString
    MAX-ACCESS  read-create
    STATUS      current
    DESCRIPTION
        "AID of LAN"
    ::=  { eccEntry 6 }

eccExternalVid OBJECT-TYPE
    SYNTAX      Unsigned32 (1..4095)
    MAX-ACCESS  read-create
    STATUS      current
    DESCRIPTION
        "External VID"
    ::=  { eccEntry 7 }

eccpppIpLinkAid OBJECT-TYPE
    SYNTAX      SnmpAdminString
    MAX-ACCESS  read-only
    STATUS      current
    DESCRIPTION
        "Address Identifier of PPPIP LINK Entity."
    ::=  { eccEntry 8 }

eccMaxDataRate OBJECT-TYPE
    SYNTAX      Unsigned32
    UNITS       "kbps"
    MAX-ACCESS  read-only
    STATUS      current
    DESCRIPTION
        "Maximum Embedded Communication Channel Bitrate"
    ::=  { eccEntry 9 }

eccProtAvailability OBJECT-TYPE
    SYNTAX      FspR7EocProtAvailability
    MAX-ACCESS  read-only
    STATUS      current
    DESCRIPTION
        "ECC Protection Availability"
    ::=  { eccEntry 10 }

eccSecondaryStates OBJECT-TYPE
    SYNTAX      FspR7EntitySecondaryStates
    MAX-ACCESS  read-only
    STATUS      current
    DESCRIPTION
        "Secondary States"
    ::=  { eccEntry 11 }

eccConnState OBJECT-TYPE
    SYNTAX      FspR7ConnectState
    MAX-ACCESS  read-only
    STATUS      current
    DESCRIPTION
        "Connection State"
    ::=  { eccEntry 12 }

eccOperState OBJECT-TYPE
    SYNTAX      FspR7OperState
    MAX-ACCESS  read-only
    STATUS      current
    DESCRIPTION
        "The Operational State will be displayed on the
         GUI with full name values; it will be differently
         displayed in TL1 syntax according to TL1 display rules."
    ::=  { eccEntry 13 }

eccValidSigTimer OBJECT-TYPE
    SYNTAX      Unsigned32 (0..5760)
    UNITS       "min"
    MAX-ACCESS  read-only
    STATUS      current
    DESCRIPTION
        "AINS state signal quality soak time remaining until transition to IS."
    ::=  { eccEntry 14 }

endOfEccTable OBJECT-TYPE
    SYNTAX      Integer32
    MAX-ACCESS  read-only
    STATUS      current
    DESCRIPTION
        ""
    ::=  { dcnMgmt 8 }

endOfDcnMgmt OBJECT-TYPE
    SYNTAX      Integer32
    MAX-ACCESS  read-only
    STATUS      current
    DESCRIPTION
        ""
    ::=  { dcnMgmt 10000 }

opticalMuxTable OBJECT-TYPE
    SYNTAX      SEQUENCE OF OpticalMuxEntry
    MAX-ACCESS  not-accessible
    STATUS      current
    DESCRIPTION   "opticalTable"
    ::=  { opticalMuxMgmt 1 }

opticalMuxEntry OBJECT-TYPE
    SYNTAX      OpticalMuxEntry
    MAX-ACCESS  not-accessible
    STATUS      current
    DESCRIPTION   "Entry of opticalTable"
    INDEX       {
                  entityOpticalMuxShelfNo,
                  entityOpticalMuxSlotNo,
                  entityOpticalMuxPortNo,
                  entityOpticalMuxExtNo,
                  entityOpticalMuxClassName
                }
    ::=  { opticalMuxTable 1 }

OpticalMuxEntry ::=  SEQUENCE
  { opticalMuxRowStatus RowStatus,
    opticalMuxConnectionType FspR7TypeConnection,
    opticalMuxChannelsNumber FspR7NumberOfChannels,
    opticalMuxPumpPower Integer32,
    opticalMuxInhibitSwitchToWork FspR7YesNo,
    opticalMuxForceLaserOn FspR7LaserForcedOperation,
    opticalMuxAseTabCreation FspR7AseTabOpr,
    opticalMuxTransmitFrequency Unsigned32,
    opticalMuxMultiplexLevel FspR7OpticalMultiplexLevel,
    opticalMuxOpticalSetPoint Integer32,
    opticalMuxInitiateEqualization FspR7InitEqualization,
    opticalMuxConnectorType FspR7ConnectorType,
    opticalMuxFiberType FspR7OpticalFiberType,
    opticalMuxTilt Integer32,
    opticalMuxOscOpticalSetpoint Integer32,
    opticalMuxOffset Integer32,
    opticalMuxSwitchCommand FspR7APSCommand,
    opticalMuxTransmitChannel FspR7ChannelIdentifier,
    opticalMuxBandProvision FspR7OpticalBand,
    opticalMuxAlsMode FspR7AlsMode,
    opticalMuxType FspR7InterfaceType,
    opticalMuxAttenuationGradient Unsigned32,
    opticalMuxTransmitWavelength Unsigned32,
    opticalMuxInhibitSwitchToProt FspR7YesNo,
    opticalMuxTrmtChannel FspR7ChannelIdentifier,
    opticalMuxVariableGain Unsigned32,
    opticalMuxSumTransmited Unsigned32,
    opticalMuxRcvChannel FspR7ChannelIdentifier,
    opticalMuxAdmin FspR7AdminState,
    opticalMuxTimePeriod FspR7OtdrPeriod,
    opticalMuxSigDegThresReceiver Unsigned32,
    opticalMuxChannelsProvision FspR7NumberOfChannels,
    opticalMuxAlias SnmpAdminString,
    opticalMuxChannelSpacing FspR7ChannelSpacing,
    opticalMuxDataLayerPmReset FspR7PmReset,
    opticalMuxGain FspR7Gain,
    opticalMuxSignalDirection FspR7SignalDirection,
    opticalMuxEdfaPwrOut FspR7EdfaOutputPowerRating,
    opticalMuxVoaSetpoint Unsigned32,
    opticalMuxFiberBrand FspR7FiberBrand,
    opticalMuxStages FspR7Stages,
    opticalMuxTiltSet FspR7TiltSet,
    opticalMuxForceFwdAsePilotOn FspR7LaserForcedOperation,
    opticalMuxSecondaryStates FspR7EntitySecondaryStates,
    opticalMuxConnState FspR7ConnectState,
    opticalMuxOperState FspR7OperState,
    opticalMuxProtectionRole FspR7ProtectionRole,
    opticalMuxFarEndSigDegThres Unsigned32,
    opticalMuxMaxRamanGainMon Unsigned32,
    opticalMuxValidSigTimer Unsigned32,
    opticalMuxGainRange FspR7GainRange,
    opticalMuxPpc Integer32,
    opticalMuxOffsetHigh Integer32,
    opticalMuxOffsetLow Integer32,
    opticalMuxOptUpdate FspR7OptUpdate }

opticalMuxRowStatus OBJECT-TYPE
    SYNTAX      RowStatus
    MAX-ACCESS  read-create
    STATUS      current
    DESCRIPTION   "RowStatus object is used to create or delete a row in the table."
    ::=  { opticalMuxEntry 1 }

opticalMuxConnectionType OBJECT-TYPE
    SYNTAX      FspR7TypeConnection
    MAX-ACCESS  read-only
    STATUS      current
    DESCRIPTION
        "Connectivity Parameters for Facilities"
    ::=  { opticalMuxEntry 2 }

opticalMuxChannelsNumber OBJECT-TYPE
    SYNTAX      FspR7NumberOfChannels
    MAX-ACCESS  read-only
    STATUS      current
    DESCRIPTION
        "Number of channels supported by an entity"
    ::=  { opticalMuxEntry 3 }

opticalMuxPumpPower OBJECT-TYPE
    SYNTAX      Integer32 (115..138)
    UNITS       "0.2 dBm"
    MAX-ACCESS  read-create
    STATUS      current
    DESCRIPTION
        "Total raman pump power"
    ::=  { opticalMuxEntry 4 }

opticalMuxInhibitSwitchToWork OBJECT-TYPE
    SYNTAX      FspR7YesNo
    MAX-ACCESS  read-write
    STATUS      current
    DESCRIPTION
        "Inhibit Switch to Working. Inhibition blocks a switchInhibit Switch to Protection facility. Inhibition blocksInhibit Switch to Working. Inhibition blocks a switch
         switch to the Protection facility (protection path).Inhibit Switch to Protection facility. Inhibition blocks
         switch to the Protection facility (protection path).
         to the Working facility (working path).
         to the Working facility (working path).
         Applicable only for the Working facility in ACT state.
         Applicable only for the Working facility in ACT state.
         Applicable for the Protection facility in ACT state.
         Applicable for the Protection facility in ACT state."
    ::=  { opticalMuxEntry 5 }

opticalMuxForceLaserOn OBJECT-TYPE
    SYNTAX      FspR7LaserForcedOperation
    MAX-ACCESS  read-write
    STATUS      current
    DESCRIPTION
        "Laser Forced On"
    ::=  { opticalMuxEntry 6 }

opticalMuxAseTabCreation OBJECT-TYPE
    SYNTAX      FspR7AseTabOpr
    MAX-ACCESS  read-write
    STATUS      current
    DESCRIPTION
        "ASE Table creation in process"
    ::=  { opticalMuxEntry 7 }

opticalMuxTransmitFrequency OBJECT-TYPE
    SYNTAX      Unsigned32
    UNITS       "0.01 THz"
    MAX-ACCESS  read-only
    STATUS      current
    DESCRIPTION
        "Frequency of Optical Interface (unit: nm)"
    ::=  { opticalMuxEntry 8 }

opticalMuxMultiplexLevel OBJECT-TYPE
    SYNTAX      FspR7OpticalMultiplexLevel
    MAX-ACCESS  read-only
    STATUS      current
    DESCRIPTION
        "Optical Multiplex Level"
    ::=  { opticalMuxEntry 9 }

opticalMuxOpticalSetPoint OBJECT-TYPE
    SYNTAX      Integer32 (-250..50)
    UNITS       "0.1 dBm"
    MAX-ACCESS  read-create
    STATUS      current
    DESCRIPTION
        "Sets the optical power for power equalization in ROADM or for channel power control in OPCM"
    ::=  { opticalMuxEntry 10 }

opticalMuxInitiateEqualization OBJECT-TYPE
    SYNTAX      FspR7InitEqualization
    MAX-ACCESS  read-write
    STATUS      current
    DESCRIPTION
        "Initiate Equalization"
    ::=  { opticalMuxEntry 11 }

opticalMuxConnectorType OBJECT-TYPE
    SYNTAX      FspR7ConnectorType
    MAX-ACCESS  read-only
    STATUS      current
    DESCRIPTION
        "Connector Type"
    ::=  { opticalMuxEntry 12 }

opticalMuxFiberType OBJECT-TYPE
    SYNTAX      FspR7OpticalFiberType
    MAX-ACCESS  read-only
    STATUS      current
    DESCRIPTION
        "Fiber of Optical Interface - Provision, Reference to FIBER__INVENTORY"
    ::=  { opticalMuxEntry 13 }

opticalMuxTilt OBJECT-TYPE
    SYNTAX      Integer32 (-50..0)
    UNITS       "0.1 dB"
    MAX-ACCESS  read-create
    STATUS      current
    DESCRIPTION
        "Change of optical channel power in dB over the complete transmission band"
    ::=  { opticalMuxEntry 14 }

opticalMuxOscOpticalSetpoint OBJECT-TYPE
    SYNTAX      Integer32 (-250..50)
    UNITS       "0.1 dBm"
    MAX-ACCESS  read-create
    STATUS      current
    DESCRIPTION
        "Sets the OSC optical power"
    ::=  { opticalMuxEntry 15 }

opticalMuxOffset OBJECT-TYPE
    SYNTAX      Integer32 (10..30)
    UNITS       "0.1 dB"
    MAX-ACCESS  read-create
    STATUS      current
    DESCRIPTION
        "Sets the offset for the mean optical power for power equalization in ROADM"
    ::=  { opticalMuxEntry 16 }

opticalMuxSwitchCommand OBJECT-TYPE
    SYNTAX      FspR7APSCommand
    MAX-ACCESS  read-write
    STATUS      current
    DESCRIPTION   "The switch command action for this facility. A command resulting
         in a switch event will also cause a change of the facility secondary state
         and a corresponding condition. Addressed by this command is the active port,
         the port to switch away from. Since this is a manual switch command, it will
         not switch if other port suffers from a signalfailure or a signal degrade."
    ::=  { opticalMuxEntry 17 }

opticalMuxTransmitChannel OBJECT-TYPE
    SYNTAX      FspR7ChannelIdentifier
    MAX-ACCESS  read-only
    STATUS      current
    DESCRIPTION
        "Channel"
    ::=  { opticalMuxEntry 18 }

opticalMuxBandProvision OBJECT-TYPE
    SYNTAX      FspR7OpticalBand
    MAX-ACCESS  read-create
    STATUS      current
    DESCRIPTION
        "Band Provision. Reference to BAND__INVENTORY."
    ::=  { opticalMuxEntry 19 }

opticalMuxAlsMode OBJECT-TYPE
    SYNTAX      FspR7AlsMode
    MAX-ACCESS  read-create
    STATUS      current
    DESCRIPTION
        "Determines the reaction in backward direction in response to a LOS
         on the same Interface: on a Network Interface connected to the DWDM
         this is a matter of laser safety"
    ::=  { opticalMuxEntry 20 }

opticalMuxType OBJECT-TYPE
    SYNTAX      FspR7InterfaceType
    MAX-ACCESS  read-create
    STATUS      current
    DESCRIPTION
        "The TYPE defines the transport service type as wrapper with wrapper layer termination OR else as payload"
    ::=  { opticalMuxEntry 21 }

opticalMuxAttenuationGradient OBJECT-TYPE
    SYNTAX      Unsigned32 (5..30)
    UNITS       "0.1 dB/min"
    MAX-ACCESS  read-create
    STATUS      current
    DESCRIPTION
        "Attenuation Gradient Threshold on Receive Fiber. Applies to both TRMT and RCV directions; but threshold violation is reported for each direction separately by the 'tapping' alarms: INTRUDE-RCV and INTRUDE-TRMT."
    ::=  { opticalMuxEntry 22 }

opticalMuxTransmitWavelength OBJECT-TYPE
    SYNTAX      Unsigned32
    UNITS       "0.01 nm"
    MAX-ACCESS  read-only
    STATUS      current
    DESCRIPTION
        "Wavelength of Optical Interface (unit: nm)"
    ::=  { opticalMuxEntry 23 }

opticalMuxInhibitSwitchToProt OBJECT-TYPE
    SYNTAX      FspR7YesNo
    MAX-ACCESS  read-write
    STATUS      current
    DESCRIPTION
        "Inhibit Switch to Working. Inhibition blocks a switchInhibit Switch to Protection facility. Inhibition blocksInhibit Switch to Working. Inhibition blocks a switch"
    ::=  { opticalMuxEntry 24 }

opticalMuxTrmtChannel OBJECT-TYPE
    SYNTAX      FspR7ChannelIdentifier
    MAX-ACCESS  read-only
    STATUS      current
    DESCRIPTION
        "Derived Transmit optical channel"
    ::=  { opticalMuxEntry 25 }

opticalMuxVariableGain OBJECT-TYPE
    SYNTAX      Unsigned32 (0..350)
    UNITS       "0.1 dB"
    MAX-ACCESS  read-create
    STATUS      current
    DESCRIPTION
        "Variable Gain of EDFA"
    ::=  { opticalMuxEntry 26 }

opticalMuxSumTransmited OBJECT-TYPE
    SYNTAX      Unsigned32 (0..96)
    MAX-ACCESS  read-only
    STATUS      current
    DESCRIPTION
        "Sum of Transmitted Optical Channels Provisioned"
    ::=  { opticalMuxEntry 27 }

opticalMuxRcvChannel OBJECT-TYPE
    SYNTAX      FspR7ChannelIdentifier
    MAX-ACCESS  read-only
    STATUS      current
    DESCRIPTION
        "Derived Rcv optical channel"
    ::=  { opticalMuxEntry 28 }

opticalMuxAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { opticalMuxEntry 29 }

opticalMuxTimePeriod OBJECT-TYPE
    SYNTAX      FspR7OtdrPeriod
    MAX-ACCESS  read-write
    STATUS      current
    DESCRIPTION
        "NONE - OTDR measurement disabled otherwise the OTDR duration in minutes."
    ::=  { opticalMuxEntry 30 }

opticalMuxSigDegThresReceiver OBJECT-TYPE
    SYNTAX      Unsigned32
    UNITS       "0.1 dB"
    MAX-ACCESS  read-create
    STATUS      current
    DESCRIPTION
        "Signal Degrade Threshold on Receiver. Reported as ATTRMT-SDHT to far end."
    ::=  { opticalMuxEntry 31 }

opticalMuxChannelsProvision OBJECT-TYPE
    SYNTAX      FspR7NumberOfChannels
    MAX-ACCESS  read-only
    STATUS      current
    DESCRIPTION
        "Number of channels supported by an entity"
    ::=  { opticalMuxEntry 32 }

opticalMuxAlias OBJECT-TYPE
    SYNTAX      SnmpAdminString
    MAX-ACCESS  read-create
    STATUS      current
    DESCRIPTION
        "User Applied Descriptor"
    ::=  { opticalMuxEntry 33 }

opticalMuxChannelSpacing OBJECT-TYPE
    SYNTAX      FspR7ChannelSpacing
    MAX-ACCESS  read-only
    STATUS      current
    DESCRIPTION
        "ITU Grid channel spacing"
    ::=  { opticalMuxEntry 34 }

opticalMuxDataLayerPmReset OBJECT-TYPE
    SYNTAX      FspR7PmReset
    MAX-ACCESS  read-write
    STATUS      current
    DESCRIPTION
        "Reset data-layer Performance registers"
    ::=  { opticalMuxEntry 35 }

opticalMuxGain OBJECT-TYPE
    SYNTAX      FspR7Gain
    MAX-ACCESS  read-create
    STATUS      current
    DESCRIPTION
        "Gain"
    ::=  { opticalMuxEntry 36 }

opticalMuxSignalDirection OBJECT-TYPE
    SYNTAX      FspR7SignalDirection
    MAX-ACCESS  read-only
    STATUS      current
    DESCRIPTION
        "Signal Direction"
    ::=  { opticalMuxEntry 37 }

opticalMuxEdfaPwrOut OBJECT-TYPE
    SYNTAX      FspR7EdfaOutputPowerRating
    MAX-ACCESS  read-create
    STATUS      current
    DESCRIPTION
        "Optical Output Power Rating - Provision"
    ::=  { opticalMuxEntry 38 }

opticalMuxVoaSetpoint OBJECT-TYPE
    SYNTAX      Unsigned32 (0..300)
    UNITS       "0.1 dB"
    MAX-ACCESS  read-create
    STATUS      current
    DESCRIPTION
        "Sets the optical attenuation of VOA"
    ::=  { opticalMuxEntry 39 }

opticalMuxFiberBrand OBJECT-TYPE
    SYNTAX      FspR7FiberBrand
    MAX-ACCESS  read-create
    STATUS      current
    DESCRIPTION
        "Brand of fiber present in the fiber plant"
    ::=  { opticalMuxEntry 40 }

opticalMuxStages OBJECT-TYPE
    SYNTAX      FspR7Stages
    MAX-ACCESS  read-only
    STATUS      current
    DESCRIPTION
        "Number of Stages"
    ::=  { opticalMuxEntry 41 }

opticalMuxTiltSet OBJECT-TYPE
    SYNTAX      FspR7TiltSet
    MAX-ACCESS  read-create
    STATUS      current
    DESCRIPTION
        "Tilt setting as discrete values versus a range"
    ::=  { opticalMuxEntry 42 }

opticalMuxForceFwdAsePilotOn OBJECT-TYPE
    SYNTAX      FspR7LaserForcedOperation
    MAX-ACCESS  read-write
    STATUS      current
    DESCRIPTION
        "Force the BWD Raman pilot on to allow building of FWD Raman ASE Table"
    ::=  { opticalMuxEntry 43 }

opticalMuxSecondaryStates OBJECT-TYPE
    SYNTAX      FspR7EntitySecondaryStates
    MAX-ACCESS  read-only
    STATUS      current
    DESCRIPTION
        "Secondary States"
    ::=  { opticalMuxEntry 44 }

opticalMuxConnState OBJECT-TYPE
    SYNTAX      FspR7ConnectState
    MAX-ACCESS  read-only
    STATUS      current
    DESCRIPTION
        "Connection State"
    ::=  { opticalMuxEntry 45 }

opticalMuxOperState OBJECT-TYPE
    SYNTAX      FspR7OperState
    MAX-ACCESS  read-only
    STATUS      current
    DESCRIPTION
        "The Operational State will be displayed on the
         GUI with full name values; it will be differently
         displayed in TL1 syntax according to TL1 display rules."
    ::=  { opticalMuxEntry 46 }

opticalMuxProtectionRole OBJECT-TYPE
    SYNTAX      FspR7ProtectionRole
    MAX-ACCESS  read-only
    STATUS      current
    DESCRIPTION
        "Path label Working or Protect"
    ::=  { opticalMuxEntry 47 }

opticalMuxFarEndSigDegThres OBJECT-TYPE
    SYNTAX      Unsigned32
    UNITS       "0.1 dB"
    MAX-ACCESS  read-only
    STATUS      current
    DESCRIPTION
        "Far End Signal Degrade Threshold"
    ::=  { opticalMuxEntry 48 }

opticalMuxMaxRamanGainMon OBJECT-TYPE
    SYNTAX      Unsigned32
    UNITS       "0.1 dB"
    MAX-ACCESS  read-only
    STATUS      current
    DESCRIPTION
        "Maximum Raman gain monitored from Raman ASE table build data"
    ::=  { opticalMuxEntry 49 }

opticalMuxValidSigTimer OBJECT-TYPE
    SYNTAX      Unsigned32 (0..5760)
    UNITS       "min"
    MAX-ACCESS  read-only
    STATUS      current
    DESCRIPTION
        "AINS state signal quality soak time remaining until transition to IS."
    ::=  { opticalMuxEntry 50 }

opticalMuxGainRange OBJECT-TYPE
    SYNTAX      FspR7GainRange
    MAX-ACCESS  read-only
    STATUS      current
    DESCRIPTION
        "EDFA gain range to provision"
    ::=  { opticalMuxEntry 51 }

opticalMuxPpc OBJECT-TYPE
    SYNTAX      Integer32 (-220..80)
    UNITS       "0.1 dBm"
    MAX-ACCESS  read-only
    STATUS      current
    DESCRIPTION
        "Target output optical power for each channel."
    ::=  { opticalMuxEntry 52 }

opticalMuxOffsetHigh OBJECT-TYPE
    SYNTAX      Integer32 (-250..210)
    UNITS       "0.1 dBm"
    MAX-ACCESS  read-create
    STATUS      current
    DESCRIPTION
        "Sets the high level offset for power equalization in CCM"
    ::=  { opticalMuxEntry 53 }

opticalMuxOffsetLow OBJECT-TYPE
    SYNTAX      Integer32 (-250..210)
    UNITS       "0.1 dBm"
    MAX-ACCESS  read-create
    STATUS      current
    DESCRIPTION
        "Sets the low level offset for power equalization in CCM"
    ::=  { opticalMuxEntry 54 }

opticalMuxOptUpdate OBJECT-TYPE
    SYNTAX      FspR7OptUpdate
    MAX-ACCESS  read-write
    STATUS      current
    DESCRIPTION
        "This parameter is used to operate/trigger OPT PM update; it triggers the entity to update its current OPT PM value, which can be retrieved via GET function."
    ::=  { opticalMuxEntry 55 }

endOfOpticalMuxTable OBJECT-TYPE
    SYNTAX      Integer32
    MAX-ACCESS  read-only
    STATUS      current
    DESCRIPTION
        ""
    ::=  { opticalMuxMgmt 2 }

endOfOpticalMuxMgmt OBJECT-TYPE
    SYNTAX      Integer32
    MAX-ACCESS  read-only
    STATUS      current
    DESCRIPTION
        ""
    ::=  { opticalMuxMgmt 10000 }

shelfConnTable OBJECT-TYPE
    SYNTAX      SEQUENCE OF ShelfConnEntry
    MAX-ACCESS  not-accessible
    STATUS      current
    DESCRIPTION   "shelfConnTable"
    ::=  { shelfConnMgmt 1 }

shelfConnEntry OBJECT-TYPE
    SYNTAX      ShelfConnEntry
    MAX-ACCESS  not-accessible
    STATUS      current
    DESCRIPTION   "Entry of shelfConnTable"
    INDEX       {
                  entityShelfConnShelfNo,
                  entityShelfConnSlotNo,
                  entityShelfConnPortNo,
                  entityShelfConnExtNo,
                  entityShelfConnClassName
                }
    ::=  { shelfConnTable 1 }

ShelfConnEntry ::=  SEQUENCE
  { shelfConnRowStatus RowStatus,
    shelfConnConnectionType FspR7TypeConnection,
    shelfConnConnector FspR7ConnectorType,
    shelfConnFiber FspR7OpticalFiberType,
    shelfConnReach FspR7OpticalInterfaceReach,
    shelfConnRate Unsigned32,
    shelfConnAdmin FspR7AdminState,
    shelfConnAlias SnmpAdminString,
    shelfConnTransmitChannel FspR7ChannelIdentifier,
    shelfConnFacilityType FspR7InterfaceType,
    shelfConnSecondaryStates FspR7EntitySecondaryStates,
    shelfConnOperState FspR7OperState,
    shelfConnValidSigTimer Unsigned32 }

shelfConnRowStatus OBJECT-TYPE
    SYNTAX      RowStatus
    MAX-ACCESS  read-create
    STATUS      current
    DESCRIPTION   "RowStatus object is used to create or delete a row in the table."
    ::=  { shelfConnEntry 1 }

shelfConnConnectionType OBJECT-TYPE
    SYNTAX      FspR7TypeConnection
    MAX-ACCESS  read-only
    STATUS      current
    DESCRIPTION
        "Connectivity Parameters for Facilities"
    ::=  { shelfConnEntry 2 }

shelfConnConnector OBJECT-TYPE
    SYNTAX      FspR7ConnectorType
    MAX-ACCESS  read-only
    STATUS      current
    DESCRIPTION
        "Connector Type"
    ::=  { shelfConnEntry 3 }

shelfConnFiber OBJECT-TYPE
    SYNTAX      FspR7OpticalFiberType
    MAX-ACCESS  read-only
    STATUS      current
    DESCRIPTION
        "Fiber of Optical Interface - Provision, Reference to FIBER__INVENTORY"
    ::=  { shelfConnEntry 4 }

shelfConnReach OBJECT-TYPE
    SYNTAX      FspR7OpticalInterfaceReach
    MAX-ACCESS  read-only
    STATUS      current
    DESCRIPTION
        "Reach"
    ::=  { shelfConnEntry 5 }

shelfConnRate OBJECT-TYPE
    SYNTAX      Unsigned32
    UNITS       "Mbps"
    MAX-ACCESS  read-only
    STATUS      current
    DESCRIPTION
        "Derived from TYPE and possibly PAYLOAD"
    ::=  { shelfConnEntry 6 }

shelfConnAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { shelfConnEntry 7 }

shelfConnAlias OBJECT-TYPE
    SYNTAX      SnmpAdminString
    MAX-ACCESS  read-create
    STATUS      current
    DESCRIPTION
        "User Applied Descriptor"
    ::=  { shelfConnEntry 8 }

shelfConnTransmitChannel OBJECT-TYPE
    SYNTAX      FspR7ChannelIdentifier
    MAX-ACCESS  read-only
    STATUS      current
    DESCRIPTION
        "Channel"
    ::=  { shelfConnEntry 9 }

shelfConnFacilityType OBJECT-TYPE
    SYNTAX      FspR7InterfaceType
    MAX-ACCESS  read-create
    STATUS      current
    DESCRIPTION
        "The TYPE defines the transport service type as wrapper with wrapper layer termination OR else as payload"
    ::=  { shelfConnEntry 10 }

shelfConnSecondaryStates OBJECT-TYPE
    SYNTAX      FspR7EntitySecondaryStates
    MAX-ACCESS  read-only
    STATUS      current
    DESCRIPTION
        "Secondary States"
    ::=  { shelfConnEntry 11 }

shelfConnOperState OBJECT-TYPE
    SYNTAX      FspR7OperState
    MAX-ACCESS  read-only
    STATUS      current
    DESCRIPTION
        "The Operational State will be displayed on the
         GUI with full name values; it will be differently
         displayed in TL1 syntax according to TL1 display rules."
    ::=  { shelfConnEntry 12 }

shelfConnValidSigTimer OBJECT-TYPE
    SYNTAX      Unsigned32 (0..5760)
    UNITS       "min"
    MAX-ACCESS  read-only
    STATUS      current
    DESCRIPTION
        "AINS state signal quality soak time remaining until transition to IS."
    ::=  { shelfConnEntry 13 }

endOfShelfConnTable OBJECT-TYPE
    SYNTAX      Integer32
    MAX-ACCESS  read-only
    STATUS      current
    DESCRIPTION
        ""
    ::=  { shelfConnMgmt 2 }

endOfShelfConnMgmt OBJECT-TYPE
    SYNTAX      Integer32
    MAX-ACCESS  read-only
    STATUS      current
    DESCRIPTION
        ""
    ::=  { shelfConnMgmt 10000 }

envPortTable OBJECT-TYPE
    SYNTAX      SEQUENCE OF EnvPortEntry
    MAX-ACCESS  not-accessible
    STATUS      current
    DESCRIPTION   "telemetryPortTable"
    ::=  { envMgmt 1 }

envPortEntry OBJECT-TYPE
    SYNTAX      EnvPortEntry
    MAX-ACCESS  not-accessible
    STATUS      current
    DESCRIPTION   "Entry of telemetryPortTable"
    INDEX       {
                  entityEqptShelfNo,
                  entityEqptSlotNo,
                  entityEqptPortNo,
                  entityEqptExtNo,
                  entityEqptClassName
                }
    ::=  { envPortTable 1 }

EnvPortEntry ::=  SEQUENCE
  { envPortRowStatus RowStatus,
    envPortConnectorType FspR7ConnectorType,
    envPortTelemetry FspR7TelemetryOutput,
    envPortFacilityType FspR7InterfaceType,
    envPortTifAlarmType SnmpAdminString,
    envPortTifAlarmMessage SnmpAdminString,
    envPortInvertTifInputLogic FspR7InvertTelemetryInputLogic }

envPortRowStatus OBJECT-TYPE
    SYNTAX      RowStatus
    MAX-ACCESS  read-create
    STATUS      current
    DESCRIPTION   "RowStatus object is used to create or delete a row in the table."
    ::=  { envPortEntry 1 }

envPortConnectorType OBJECT-TYPE
    SYNTAX      FspR7ConnectorType
    MAX-ACCESS  read-only
    STATUS      current
    DESCRIPTION
        "Connector Type"
    ::=  { envPortEntry 2 }

envPortTelemetry OBJECT-TYPE
    SYNTAX      FspR7TelemetryOutput
    MAX-ACCESS  read-create
    STATUS      current
    DESCRIPTION
        "Telemetry interface output provision"
    ::=  { envPortEntry 3 }

envPortFacilityType OBJECT-TYPE
    SYNTAX      FspR7InterfaceType
    MAX-ACCESS  read-create
    STATUS      current
    DESCRIPTION
        "The TYPE defines the transport service type as wrapper with wrapper layer termination OR else as payload"
    ::=  { envPortEntry 4 }

envPortTifAlarmType OBJECT-TYPE
    SYNTAX      SnmpAdminString
    MAX-ACCESS  read-create
    STATUS      current
    DESCRIPTION
        "Telemetry interface alarm type"
    ::=  { envPortEntry 5 }

envPortTifAlarmMessage OBJECT-TYPE
    SYNTAX      SnmpAdminString
    MAX-ACCESS  read-create
    STATUS      current
    DESCRIPTION
        "Telemetry interface alarm message"
    ::=  { envPortEntry 6 }

envPortInvertTifInputLogic OBJECT-TYPE
    SYNTAX      FspR7InvertTelemetryInputLogic
    MAX-ACCESS  read-create
    STATUS      current
    DESCRIPTION
        "Invert telemetry interface input logic"
    ::=  { envPortEntry 7 }

endOfEnvPortTable OBJECT-TYPE
    SYNTAX      Integer32
    MAX-ACCESS  read-only
    STATUS      current
    DESCRIPTION
        ""
    ::=  { envMgmt 2 }

endOfEnvMgmt OBJECT-TYPE
    SYNTAX      Integer32
    MAX-ACCESS  read-only
    STATUS      current
    DESCRIPTION
        ""
    ::=  { envMgmt 10000 }

containerTable OBJECT-TYPE
    SYNTAX      SEQUENCE OF ContainerEntry
    MAX-ACCESS  not-accessible
    STATUS      current
    DESCRIPTION   "containerTable"
    ::=  { containerMgmt 1 }

containerEntry OBJECT-TYPE
    SYNTAX      ContainerEntry
    MAX-ACCESS  not-accessible
    STATUS      current
    DESCRIPTION   "Entry of containerTable"
    INDEX       {
                  entityContainerShelfNo,
                  entityContainerSlotNo,
                  entityContainerPortNo,
                  entityContainerExtNo,
                  entityContainerClassName
                }
    ::=  { containerTable 1 }

ContainerEntry ::=  SEQUENCE
  { containerRowStatus RowStatus,
    containerAdmin FspR7AdminState,
    containerSequenceNumber Unsigned32,
    containerFacilityType FspR7InterfaceType,
    containerContainer SnmpAdminString,
    containerVSContainer SnmpAdminString,
    containerSecondaryStates FspR7EntitySecondaryStates,
    containerOperState FspR7OperState }

containerRowStatus OBJECT-TYPE
    SYNTAX      RowStatus
    MAX-ACCESS  read-create
    STATUS      current
    DESCRIPTION   "RowStatus object is used to create or delete a row in the table."
    ::=  { containerEntry 1 }

containerAdmin OBJECT-TYPE
    SYNTAX      FspR7AdminState
    MAX-ACCESS  read-only
    STATUS      current
    DESCRIPTION
        "The Administrative State will be displayed in the GUI with full
         name values; it will be differently displayed in TL1 syntax according
         to TL1 display rules. The transaction into the UAS state requires
         a special destroy/delete function"
    ::=  { containerEntry 2 }

containerSequenceNumber OBJECT-TYPE
    SYNTAX      Unsigned32
    MAX-ACCESS  read-only
    STATUS      current
    DESCRIPTION
        "Sequence number of an individual container within a Virtual Concatenated Group"
    ::=  { containerEntry 3 }

containerFacilityType OBJECT-TYPE
    SYNTAX      FspR7InterfaceType
    MAX-ACCESS  read-create
    STATUS      current
    DESCRIPTION
        "The TYPE defines the transport service type as wrapper with wrapper layer termination OR else as payload"
    ::=  { containerEntry 4 }

containerContainer OBJECT-TYPE
    SYNTAX      SnmpAdminString
    MAX-ACCESS  read-only
    STATUS      current
    DESCRIPTION
        "AID of a logically linked Virtual Channel."
    ::=  { containerEntry 5 }

containerVSContainer OBJECT-TYPE
    SYNTAX      SnmpAdminString
    MAX-ACCESS  read-only
    STATUS      current
    DESCRIPTION
        "AID of a logically linked Virtual SubChannel."
    ::=  { containerEntry 6 }

containerSecondaryStates OBJECT-TYPE
    SYNTAX      FspR7EntitySecondaryStates
    MAX-ACCESS  read-only
    STATUS      current
    DESCRIPTION
        "Secondary States"
    ::=  { containerEntry 7 }

containerOperState OBJECT-TYPE
    SYNTAX      FspR7OperState
    MAX-ACCESS  read-only
    STATUS      current
    DESCRIPTION
        "The Operational State will be displayed on the
         GUI with full name values; it will be differently
         displayed in TL1 syntax according to TL1 display rules."
    ::=  { containerEntry 8 }

endOfContainerTable OBJECT-TYPE
    SYNTAX      Integer32
    MAX-ACCESS  read-only
    STATUS      current
    DESCRIPTION
        ""
    ::=  { containerMgmt 2 }

endOfContainerMgmt OBJECT-TYPE
    SYNTAX      Integer32
    MAX-ACCESS  read-only
    STATUS      current
    DESCRIPTION
        ""
    ::=  { containerMgmt 10000 }

opticalLineTable OBJECT-TYPE
    SYNTAX      SEQUENCE OF OpticalLineEntry
    MAX-ACCESS  not-accessible
    STATUS      current
    DESCRIPTION   "opticalLineTable"
    ::=  { opticalLineMgmt 1 }

opticalLineEntry OBJECT-TYPE
    SYNTAX      OpticalLineEntry
    MAX-ACCESS  not-accessible
    STATUS      current
    DESCRIPTION   "Entry of opticalLineTable"
    INDEX       {
                  entityOptLineIndexNo1,
                  entityOptLineIndexNo1,
                  entityOptLineIndexNo1,
                  entityOptLineIndexNo1,
                  entityOptLineClassName
                }
    ::=  { opticalLineTable 1 }

OpticalLineEntry ::=  SEQUENCE
  { opticalLineRowStatus RowStatus,
    opticalLineTxLineAttenuation Integer32,
    opticalLineRxLineAttenuation Integer32,
    opticalLineAlias SnmpAdminString,
    opticalLineFarEndLocation SnmpAdminString,
    opticalLineLaneChannel1 FspR7ChannelIdentifier,
    opticalLineLaneChannel2 FspR7ChannelIdentifier,
    opticalLineLaneChannel3 FspR7ChannelIdentifier,
    opticalLineLaneChannel4 FspR7ChannelIdentifier,
    opticalLineLanes FspR7OpticalLanes,
    opticalLineChannelBandwith FspR7ChannelBandwidth,
    opticalLineChannelSpacing FspR7ChannelSpacing,
    opticalLineFacilities SnmpAdminString,
    opticalLineSecondaryStates FspR7EntitySecondaryStates,
    opticalLineConnState FspR7ConnectState,
    opticalLineLogicalInterfaceAid SnmpAdminString,
    opticalLineOwnerAid SnmpAdminString,
    opticalLineTransmitWavelength Unsigned32,
    opticalLineTransmitFrequency Unsigned32,
    opticalLineTransmitChannel FspR7ChannelIdentifier }

opticalLineRowStatus OBJECT-TYPE
    SYNTAX      RowStatus
    MAX-ACCESS  read-create
    STATUS      current
    DESCRIPTION   "RowStatus object is used to create or delete a row in the table."
    ::=  { opticalLineEntry 1 }

opticalLineTxLineAttenuation OBJECT-TYPE
    SYNTAX      Integer32
    UNITS       "0.1 dB"
    MAX-ACCESS  read-create
    STATUS      current
    DESCRIPTION   "The Attenuation (in 0.1 dB) on line connected to
         transmitter of this interface. If there is loss of signal
         then line attenuation is -65535. The value -255 will be
         returned if the value isn't available."
    ::=  { opticalLineEntry 2 }

opticalLineRxLineAttenuation OBJECT-TYPE
    SYNTAX      Integer32
    UNITS       "0.1 dB"
    MAX-ACCESS  read-create
    STATUS      current
    DESCRIPTION   "The Attenuation (in 0.1 dB) on line connected to receiver
         of this interface. If there is loss of signal then ine
         attenuation is -65535. The value -255 will be returned if
         the value isn't available."
    ::=  { opticalLineEntry 3 }

opticalLineAlias OBJECT-TYPE
    SYNTAX      SnmpAdminString
    MAX-ACCESS  read-create
    STATUS      current
    DESCRIPTION
        "User Applied Descriptor"
    ::=  { opticalLineEntry 4 }

opticalLineFarEndLocation OBJECT-TYPE
    SYNTAX      SnmpAdminString
    MAX-ACCESS  read-create
    STATUS      current
    DESCRIPTION
        "FEND Location"
    ::=  { opticalLineEntry 5 }

opticalLineLaneChannel1 OBJECT-TYPE
    SYNTAX      FspR7ChannelIdentifier
    MAX-ACCESS  read-only
    STATUS      current
    DESCRIPTION
        "Lane Channel"
    ::=  { opticalLineEntry 6 }

opticalLineLaneChannel2 OBJECT-TYPE
    SYNTAX      FspR7ChannelIdentifier
    MAX-ACCESS  read-only
    STATUS      current
    DESCRIPTION
        "Lane Channel"
    ::=  { opticalLineEntry 7 }

opticalLineLaneChannel3 OBJECT-TYPE
    SYNTAX      FspR7ChannelIdentifier
    MAX-ACCESS  read-only
    STATUS      current
    DESCRIPTION
        "Lane Channel"
    ::=  { opticalLineEntry 8 }

opticalLineLaneChannel4 OBJECT-TYPE
    SYNTAX      FspR7ChannelIdentifier
    MAX-ACCESS  read-only
    STATUS      current
    DESCRIPTION
        "Lane Channel"
    ::=  { opticalLineEntry 9 }

opticalLineLanes OBJECT-TYPE
    SYNTAX      FspR7OpticalLanes
    MAX-ACCESS  read-only
    STATUS      current
    DESCRIPTION
        "Number of Optical Transport Lanes in OTLG"
    ::=  { opticalLineEntry 10 }

opticalLineChannelBandwith OBJECT-TYPE
    SYNTAX      FspR7ChannelBandwidth
    MAX-ACCESS  read-only
    STATUS      current
    DESCRIPTION
        "Channel Bandwidth"
    ::=  { opticalLineEntry 11 }

opticalLineChannelSpacing OBJECT-TYPE
    SYNTAX      FspR7ChannelSpacing
    MAX-ACCESS  read-only
    STATUS      current
    DESCRIPTION
        "ITU Grid channel spacing"
    ::=  { opticalLineEntry 12 }

opticalLineFacilities OBJECT-TYPE
    SYNTAX      SnmpAdminString
    MAX-ACCESS  read-only
    STATUS      current
    DESCRIPTION
        "AID of a WCH, VCH or CH instance"
    ::=  { opticalLineEntry 13 }

opticalLineSecondaryStates OBJECT-TYPE
    SYNTAX      FspR7EntitySecondaryStates
    MAX-ACCESS  read-only
    STATUS      current
    DESCRIPTION
        "Secondary States"
    ::=  { opticalLineEntry 14 }

opticalLineConnState OBJECT-TYPE
    SYNTAX      FspR7ConnectState
    MAX-ACCESS  read-only
    STATUS      current
    DESCRIPTION
        "Connection State"
    ::=  { opticalLineEntry 15 }

opticalLineLogicalInterfaceAid OBJECT-TYPE
    SYNTAX      SnmpAdminString
    MAX-ACCESS  read-only
    STATUS      current
    DESCRIPTION
        "Logical Interface AID"
    ::=  { opticalLineEntry 16 }

opticalLineOwnerAid OBJECT-TYPE
    SYNTAX      SnmpAdminString
    MAX-ACCESS  read-only
    STATUS      current
    DESCRIPTION
        "Owner AID"
    ::=  { opticalLineEntry 17 }

opticalLineTransmitWavelength OBJECT-TYPE
    SYNTAX      Unsigned32
    UNITS       "0.01 nm"
    MAX-ACCESS  read-only
    STATUS      current
    DESCRIPTION
        "Wavelength of Optical Interface (unit: nm)"
    ::=  { opticalLineEntry 18 }

opticalLineTransmitFrequency OBJECT-TYPE
    SYNTAX      Unsigned32
    UNITS       "0.01 THz"
    MAX-ACCESS  read-only
    STATUS      current
    DESCRIPTION
        "Frequency of Optical Interface (unit: nm)"
    ::=  { opticalLineEntry 19 }

opticalLineTransmitChannel OBJECT-TYPE
    SYNTAX      FspR7ChannelIdentifier
    MAX-ACCESS  read-only
    STATUS      current
    DESCRIPTION
        "Channel"
    ::=  { opticalLineEntry 20 }

endOfOpticalLineTable OBJECT-TYPE
    SYNTAX      Integer32
    MAX-ACCESS  read-only
    STATUS      current
    DESCRIPTION
        ""
    ::=  { opticalLineMgmt 2 }

endOfOpticalLineMgmt OBJECT-TYPE
    SYNTAX      Integer32
    MAX-ACCESS  read-only
    STATUS      current
    DESCRIPTION
        ""
    ::=  { opticalLineMgmt 10000 }

serviceAffecting OBJECT-TYPE
    SYNTAX      ServiceAffecting
    MAX-ACCESS  accessible-for-notify
    STATUS      current
    DESCRIPTION   "Re-init of modules is SA or NSA. This object is send within a trap."
    ::=  { alarm 1000 }

alarmSysTable OBJECT-TYPE
    SYNTAX      SEQUENCE OF AlarmSysEntry
    MAX-ACCESS  not-accessible
    STATUS      current
    DESCRIPTION   "alarmSysTable"
    ::=  { alarm 1 }

alarmSysEntry OBJECT-TYPE
    SYNTAX      AlarmSysEntry
    MAX-ACCESS  not-accessible
    STATUS      current
    DESCRIPTION   "Entry of alarmSysTable"
    INDEX       {
                  entitySysShelfNo,
                  entitySysSlotNo,
                  entitySysPortNo,
                  entitySysExtNo,
                  entitySysClassName,
                  alarmSysType
                }
    ::=  { alarmSysTable 1 }

AlarmSysEntry ::=  SEQUENCE
  { alarmSysType FspR7AlarmListType,
    alarmSysSeverity TrapAlarmSeverity,
    alarmSysAffect ServiceImpairment,
    alarmSysTimeStamp DateAndTime }

alarmSysType OBJECT-TYPE
    SYNTAX      FspR7AlarmListType
    MAX-ACCESS  not-accessible
    STATUS      current
    DESCRIPTION   "List of all interface conditions."
    ::=  { alarmSysEntry 1 }

alarmSysSeverity OBJECT-TYPE
    SYNTAX      TrapAlarmSeverity
    MAX-ACCESS  read-only
    STATUS      current
    DESCRIPTION   "Object identifies the current severity of alarm."
    ::=  { alarmSysEntry 2 }

alarmSysAffect OBJECT-TYPE
    SYNTAX      ServiceImpairment
    MAX-ACCESS  read-only
    STATUS      current
    DESCRIPTION   "Object indicates the service impairment affect of the alarm."
    ::=  { alarmSysEntry 3 }

alarmSysTimeStamp OBJECT-TYPE
    SYNTAX      DateAndTime
    MAX-ACCESS  read-only
    STATUS      current
    DESCRIPTION   "Timestamp."
    ::=  { alarmSysEntry 4 }

endOfAlarmSysTable OBJECT-TYPE
    SYNTAX      Integer32
    MAX-ACCESS  read-only
    STATUS      current
    DESCRIPTION
        ""
    ::=  { alarm 2 }

alarmSeveritySysTable OBJECT-TYPE
    SYNTAX      SEQUENCE OF AlarmSeveritySysEntry
    MAX-ACCESS  not-accessible
    STATUS      current
    DESCRIPTION   "alarmSeveritySysTable"
    ::=  { alarm 3 }

alarmSeveritySysEntry OBJECT-TYPE
    SYNTAX      AlarmSeveritySysEntry
    MAX-ACCESS  not-accessible
    STATUS      current
    DESCRIPTION   "Entry of alarmSeveritySysTable"
    INDEX       {
                  entitySysShelfNo,
                  entitySysSlotNo,
                  entitySysPortNo,
                  entitySysExtNo,
                  entitySysClassName,
                  alarmSeveritySysType
                }
    ::=  { alarmSeveritySysTable 1 }

AlarmSeveritySysEntry ::=  SEQUENCE
  { alarmSeveritySysType FspR7AlarmListType,
    alarmSeveritySysValue TrapAlarmSeverity }

alarmSeveritySysType OBJECT-TYPE
    SYNTAX      FspR7AlarmListType
    MAX-ACCESS  not-accessible
    STATUS      current
    DESCRIPTION   "Type of severity."
    ::=  { alarmSeveritySysEntry 1 }

alarmSeveritySysValue OBJECT-TYPE
    SYNTAX      TrapAlarmSeverity
    MAX-ACCESS  read-write
    STATUS      current
    DESCRIPTION   "Value of severity."
    ::=  { alarmSeveritySysEntry 2 }

endOfAlarmSeveritySysTable OBJECT-TYPE
    SYNTAX      Integer32
    MAX-ACCESS  read-only
    STATUS      current
    DESCRIPTION
        ""
    ::=  { alarm 4 }

alarmEqptTable OBJECT-TYPE
    SYNTAX      SEQUENCE OF AlarmEqptEntry
    MAX-ACCESS  not-accessible
    STATUS      current
    DESCRIPTION   "alarmEqptTable"
    ::=  { alarm 5 }

alarmEqptEntry OBJECT-TYPE
    SYNTAX      AlarmEqptEntry
    MAX-ACCESS  not-accessible
    STATUS      current
    DESCRIPTION   "Entry of alarmEqptTable"
    INDEX       {
                  entityEqptShelfNo,
                  entityEqptSlotNo,
                  entityEqptPortNo,
                  entityEqptExtNo,
                  entityEqptClassName,
                  alarmEqptType
                }
    ::=  { alarmEqptTable 1 }

AlarmEqptEntry ::=  SEQUENCE
  { alarmEqptType FspR7AlarmListType,
    alarmEqptSeverity TrapAlarmSeverity,
    alarmEqptAffect ServiceImpairment,
    alarmEqptTimeStamp DateAndTime }

alarmEqptType OBJECT-TYPE
    SYNTAX      FspR7AlarmListType
    MAX-ACCESS  not-accessible
    STATUS      current
    DESCRIPTION   "List of all interface conditions."
    ::=  { alarmEqptEntry 1 }

alarmEqptSeverity OBJECT-TYPE
    SYNTAX      TrapAlarmSeverity
    MAX-ACCESS  read-only
    STATUS      current
    DESCRIPTION   "Object identifies the current severity of alarm."
    ::=  { alarmEqptEntry 2 }

alarmEqptAffect OBJECT-TYPE
    SYNTAX      ServiceImpairment
    MAX-ACCESS  read-only
    STATUS      current
    DESCRIPTION   "Object indicates the service impairment affect of the alarm."
    ::=  { alarmEqptEntry 3 }

alarmEqptTimeStamp OBJECT-TYPE
    SYNTAX      DateAndTime
    MAX-ACCESS  read-only
    STATUS      current
    DESCRIPTION   "Timestamp."
    ::=  { alarmEqptEntry 4 }

endOfAlarmEqptTable OBJECT-TYPE
    SYNTAX      Integer32
    MAX-ACCESS  read-only
    STATUS      current
    DESCRIPTION
        ""
    ::=  { alarm 6 }

alarmFacilityTable OBJECT-TYPE
    SYNTAX      SEQUENCE OF AlarmFacilityEntry
    MAX-ACCESS  not-accessible
    STATUS      current
    DESCRIPTION   "alarmFacilityTable"
    ::=  { alarm 7 }

alarmFacilityEntry OBJECT-TYPE
    SYNTAX      AlarmFacilityEntry
    MAX-ACCESS  not-accessible
    STATUS      current
    DESCRIPTION   "Entry of alarmFacilityTable"
    INDEX       {
                  entityFacilityShelfNo,
                  entityFacilitySlotNo,
                  entityFacilityPortNo,
                  entityFacilityExtNo,
                  entityFacilityClassName,
                  alarmFacilityType
                }
    ::=  { alarmFacilityTable 1 }

AlarmFacilityEntry ::=  SEQUENCE
  { alarmFacilityType FspR7AlarmListType,
    alarmFacilitySeverity TrapAlarmSeverity,
    alarmFacilityAffect ServiceImpairment,
    alarmFacilityTimeStamp DateAndTime }

alarmFacilityType OBJECT-TYPE
    SYNTAX      FspR7AlarmListType
    MAX-ACCESS  not-accessible
    STATUS      current
    DESCRIPTION   "List of all interface conditions."
    ::=  { alarmFacilityEntry 1 }

alarmFacilitySeverity OBJECT-TYPE
    SYNTAX      TrapAlarmSeverity
    MAX-ACCESS  read-only
    STATUS      current
    DESCRIPTION   "Object identifies the current severity of alarm."
    ::=  { alarmFacilityEntry 2 }

alarmFacilityAffect OBJECT-TYPE
    SYNTAX      ServiceImpairment
    MAX-ACCESS  read-only
    STATUS      current
    DESCRIPTION   "Object indicates the service impairment affect of the alarm."
    ::=  { alarmFacilityEntry 3 }

alarmFacilityTimeStamp OBJECT-TYPE
    SYNTAX      DateAndTime
    MAX-ACCESS  read-only
    STATUS      current
    DESCRIPTION   "Timestamp."
    ::=  { alarmFacilityEntry 4 }

alarmSeverityFacilityTable OBJECT-TYPE
    SYNTAX      SEQUENCE OF AlarmSeverityFacilityEntry
    MAX-ACCESS  not-accessible
    STATUS      current
    DESCRIPTION   "alarmSeverityFacilityTable"
    ::=  { alarm 8 }

alarmSeverityFacilityEntry OBJECT-TYPE
    SYNTAX      AlarmSeverityFacilityEntry
    MAX-ACCESS  not-accessible
    STATUS      current
    DESCRIPTION   "Entry of alarmSeverityFacilityTable"
    INDEX       {
                  entityFacilityShelfNo,
                  entityFacilitySlotNo,
                  entityFacilityPortNo,
                  entityFacilityExtNo,
                  entityFacilityClassName,
                  alarmSeverityFacilityType
                }
    ::=  { alarmSeverityFacilityTable 1 }

AlarmSeverityFacilityEntry ::=  SEQUENCE
  { alarmSeverityFacilityType FspR7AlarmListType,
    alarmSeverityFacilityValue TrapAlarmSeverity }

alarmSeverityFacilityType OBJECT-TYPE
    SYNTAX      FspR7AlarmListType
    MAX-ACCESS  not-accessible
    STATUS      current
    DESCRIPTION   "Type of severity."
    ::=  { alarmSeverityFacilityEntry 1 }

alarmSeverityFacilityValue OBJECT-TYPE
    SYNTAX      TrapAlarmSeverity
    MAX-ACCESS  read-write
    STATUS      current
    DESCRIPTION   "Value of severity."
    ::=  { alarmSeverityFacilityEntry 2 }

alarmTerminPointTable OBJECT-TYPE
    SYNTAX      SEQUENCE OF AlarmTerminPointEntry
    MAX-ACCESS  not-accessible
    STATUS      current
    DESCRIPTION   "alarmTerminPointTable"
    ::=  { alarm 9 }

alarmTerminPointEntry OBJECT-TYPE
    SYNTAX      AlarmTerminPointEntry
    MAX-ACCESS  not-accessible
    STATUS      current
    DESCRIPTION   "Entry of alarmTerminPointTable"
    INDEX       {
                  entityTerminPointIndexNo1,
                  entityTerminPointIndexNo2,
                  entityTerminPointIndexNo3,
                  entityTerminPointIndexNo4,
                  entityTerminPointClassName,
                  alarmTerminPointType
                }
    ::=  { alarmTerminPointTable 1 }

AlarmTerminPointEntry ::=  SEQUENCE
  { alarmTerminPointType FspR7AlarmListType,
    alarmTerminPointSeverity TrapAlarmSeverity,
    alarmTerminPointAffect ServiceImpairment,
    alarmTerminPointTimeStamp DateAndTime }

alarmTerminPointType OBJECT-TYPE
    SYNTAX      FspR7AlarmListType
    MAX-ACCESS  not-accessible
    STATUS      current
    DESCRIPTION   "List of all interface conditions."
    ::=  { alarmTerminPointEntry 1 }

alarmTerminPointSeverity OBJECT-TYPE
    SYNTAX      TrapAlarmSeverity
    MAX-ACCESS  read-only
    STATUS      current
    DESCRIPTION   "Object identifies the current severity of alarm."
    ::=  { alarmTerminPointEntry 2 }

alarmTerminPointAffect OBJECT-TYPE
    SYNTAX      ServiceImpairment
    MAX-ACCESS  read-only
    STATUS      current
    DESCRIPTION   "Object indicates the service impairment affect of the alarm."
    ::=  { alarmTerminPointEntry 3 }

alarmTerminPointTimeStamp OBJECT-TYPE
    SYNTAX      DateAndTime
    MAX-ACCESS  read-only
    STATUS      current
    DESCRIPTION   "Timestamp."
    ::=  { alarmTerminPointEntry 4 }

alarmSeverityTerminPointTable OBJECT-TYPE
    SYNTAX      SEQUENCE OF AlarmSeverityTerminPointEntry
    MAX-ACCESS  not-accessible
    STATUS      current
    DESCRIPTION   "alarmSeverityTerminPointTable"
    ::=  { alarm 10 }

alarmSeverityTerminPointEntry OBJECT-TYPE
    SYNTAX      AlarmSeverityTerminPointEntry
    MAX-ACCESS  not-accessible
    STATUS      current
    DESCRIPTION   "Entry of alarmSeverityTerminPointTable"
    INDEX       {
                  entityTerminPointIndexNo1,
                  entityTerminPointIndexNo2,
                  entityTerminPointIndexNo3,
                  entityTerminPointIndexNo4,
                  entityTerminPointClassName,
                  alarmSeverityTerminPointType
                }
    ::=  { alarmSeverityTerminPointTable 1 }

AlarmSeverityTerminPointEntry ::=  SEQUENCE
  { alarmSeverityTerminPointType FspR7AlarmListType,
    alarmSeverityTerminPointValue TrapAlarmSeverity }

alarmSeverityTerminPointType OBJECT-TYPE
    SYNTAX      FspR7AlarmListType
    MAX-ACCESS  not-accessible
    STATUS      current
    DESCRIPTION   "Type of severity."
    ::=  { alarmSeverityTerminPointEntry 1 }

alarmSeverityTerminPointValue OBJECT-TYPE
    SYNTAX      TrapAlarmSeverity
    MAX-ACCESS  read-write
    STATUS      current
    DESCRIPTION   "Value of severity."
    ::=  { alarmSeverityTerminPointEntry 2 }

alarmExternalPortTable OBJECT-TYPE
    SYNTAX      SEQUENCE OF AlarmExternalPortEntry
    MAX-ACCESS  not-accessible
    STATUS      current
    DESCRIPTION   "alarmExternalPort"
    ::=  { alarm 11 }

alarmExternalPortEntry OBJECT-TYPE
    SYNTAX      AlarmExternalPortEntry
    MAX-ACCESS  not-accessible
    STATUS      current
    DESCRIPTION   "Entry of alarmExternalPort"
    INDEX       {
                  entityExternalPortShelfNo,
                  entityExternalPortSlotNo,
                  entityExternalPortPortNo,
                  entityExternalPortExtNo,
                  entityExternalPortClassName,
                  alarmExternalPortType
                }
    ::=  { alarmExternalPortTable 1 }

AlarmExternalPortEntry ::=  SEQUENCE
  { alarmExternalPortType FspR7AlarmListType,
    alarmExternalPortSeverity TrapAlarmSeverity,
    alarmExternalPortAffect ServiceImpairment,
    alarmExternalPortTimeStamp DateAndTime }

alarmExternalPortType OBJECT-TYPE
    SYNTAX      FspR7AlarmListType
    MAX-ACCESS  not-accessible
    STATUS      current
    DESCRIPTION   "List of all interface conditions."
    ::=  { alarmExternalPortEntry 1 }

alarmExternalPortSeverity OBJECT-TYPE
    SYNTAX      TrapAlarmSeverity
    MAX-ACCESS  read-only
    STATUS      current
    DESCRIPTION   "Object identifies the current severity of alarm."
    ::=  { alarmExternalPortEntry 2 }

alarmExternalPortAffect OBJECT-TYPE
    SYNTAX      ServiceImpairment
    MAX-ACCESS  read-only
    STATUS      current
    DESCRIPTION   "Object indicates the service impairment affect of the alarm."
    ::=  { alarmExternalPortEntry 3 }

alarmExternalPortTimeStamp OBJECT-TYPE
    SYNTAX      DateAndTime
    MAX-ACCESS  read-only
    STATUS      current
    DESCRIPTION   "Timestamp."
    ::=  { alarmExternalPortEntry 4 }

alarmSeverityExternalPortTable OBJECT-TYPE
    SYNTAX      SEQUENCE OF AlarmSeverityExternalPortEntry
    MAX-ACCESS  not-accessible
    STATUS      current
    DESCRIPTION   "alarmSeverityExternalPort"
    ::=  { alarm 12 }

alarmSeverityExternalPortEntry OBJECT-TYPE
    SYNTAX      AlarmSeverityExternalPortEntry
    MAX-ACCESS  not-accessible
    STATUS      current
    DESCRIPTION   "Entry of alarmSeverityExternalPort"
    INDEX       {
                  entityExternalPortShelfNo,
                  entityExternalPortSlotNo,
                  entityExternalPortPortNo,
                  entityExternalPortExtNo,
                  entityExternalPortClassName,
                  alarmSeverityExternalPortType
                }
    ::=  { alarmSeverityExternalPortTable 1 }

AlarmSeverityExternalPortEntry ::=  SEQUENCE
  { alarmSeverityExternalPortType FspR7AlarmListType,
    alarmSeverityExternalPortValue TrapAlarmSeverity }

alarmSeverityExternalPortType OBJECT-TYPE
    SYNTAX      FspR7AlarmListType
    MAX-ACCESS  not-accessible
    STATUS      current
    DESCRIPTION   "Type of severity."
    ::=  { alarmSeverityExternalPortEntry 1 }

alarmSeverityExternalPortValue OBJECT-TYPE
    SYNTAX      TrapAlarmSeverity
    MAX-ACCESS  read-write
    STATUS      current
    DESCRIPTION   "Value of severity."
    ::=  { alarmSeverityExternalPortEntry 2 }

endOfAlarmSeverityExternalPortTable OBJECT-TYPE
    SYNTAX      Integer32
    MAX-ACCESS  read-only
    STATUS      current
    DESCRIPTION
        ""
    ::=  { alarm 13 }

alarmSeverityEqptTable OBJECT-TYPE
    SYNTAX      SEQUENCE OF AlarmSeverityEqptEntry
    MAX-ACCESS  not-accessible
    STATUS      current
    DESCRIPTION   "alarmSeverityEqptTable"
    ::=  { alarm 14 }

alarmSeverityEqptEntry OBJECT-TYPE
    SYNTAX      AlarmSeverityEqptEntry
    MAX-ACCESS  not-accessible
    STATUS      current
    DESCRIPTION   "Entry of alarmSeverityEqptTable"
    INDEX       {
                  entityEqptShelfNo,
                  entityEqptSlotNo,
                  entityEqptPortNo,
                  entityEqptExtNo,
                  entityEqptClassName,
                  alarmSeverityEqptType
                }
    ::=  { alarmSeverityEqptTable 1 }

AlarmSeverityEqptEntry ::=  SEQUENCE
  { alarmSeverityEqptType FspR7AlarmListType,
    alarmSeverityEqptValue TrapAlarmSeverity }

alarmSeverityEqptType OBJECT-TYPE
    SYNTAX      FspR7AlarmListType
    MAX-ACCESS  not-accessible
    STATUS      current
    DESCRIPTION   "Type of severity."
    ::=  { alarmSeverityEqptEntry 1 }

alarmSeverityEqptValue OBJECT-TYPE
    SYNTAX      TrapAlarmSeverity
    MAX-ACCESS  read-write
    STATUS      current
    DESCRIPTION   "Value of severity."
    ::=  { alarmSeverityEqptEntry 2 }

endOfAlarmSeverityEqptTable OBJECT-TYPE
    SYNTAX      Integer32
    MAX-ACCESS  read-only
    STATUS      current
    DESCRIPTION
        ""
    ::=  { alarm 15 }

alarmDcnTable OBJECT-TYPE
    SYNTAX      SEQUENCE OF AlarmDcnEntry
    MAX-ACCESS  not-accessible
    STATUS      current
    DESCRIPTION   "alarmDcnTable"
    ::=  { alarm 16 }

alarmDcnEntry OBJECT-TYPE
    SYNTAX      AlarmDcnEntry
    MAX-ACCESS  not-accessible
    STATUS      current
    DESCRIPTION   "Entry of alarmDcnTable"
    INDEX       {
                  entityDcnShelfNo,
                  entityDcnSlotNo,
                  entityDcnPortNo,
                  entityDcnExtNo,
                  entityDcnClassName,
                  alarmDcnType
                }
    ::=  { alarmDcnTable 1 }

AlarmDcnEntry ::=  SEQUENCE
  { alarmDcnType FspR7AlarmListType,
    alarmDcnSeverity TrapAlarmSeverity,
    alarmDcnAffect ServiceImpairment,
    alarmDcnTimeStamp DateAndTime }

alarmDcnType OBJECT-TYPE
    SYNTAX      FspR7AlarmListType
    MAX-ACCESS  not-accessible
    STATUS      current
    DESCRIPTION   "List of all interface conditions."
    ::=  { alarmDcnEntry 1 }

alarmDcnSeverity OBJECT-TYPE
    SYNTAX      TrapAlarmSeverity
    MAX-ACCESS  read-only
    STATUS      current
    DESCRIPTION   "Object identifies the current severity of alarm."
    ::=  { alarmDcnEntry 2 }

alarmDcnAffect OBJECT-TYPE
    SYNTAX      ServiceImpairment
    MAX-ACCESS  read-only
    STATUS      current
    DESCRIPTION   "Object indicates the service impairment affect of the alarm."
    ::=  { alarmDcnEntry 3 }

alarmDcnTimeStamp OBJECT-TYPE
    SYNTAX      DateAndTime
    MAX-ACCESS  read-only
    STATUS      current
    DESCRIPTION   "Timestamp."
    ::=  { alarmDcnEntry 4 }

endOfAlarmDcnTable OBJECT-TYPE
    SYNTAX      Integer32
    MAX-ACCESS  read-only
    STATUS      current
    DESCRIPTION
        ""
    ::=  { alarm 17 }

alarmSeverityDcnTable OBJECT-TYPE
    SYNTAX      SEQUENCE OF AlarmSeverityDcnEntry
    MAX-ACCESS  not-accessible
    STATUS      current
    DESCRIPTION   "alarmSeverityDcnTable"
    ::=  { alarm 18 }

alarmSeverityDcnEntry OBJECT-TYPE
    SYNTAX      AlarmSeverityDcnEntry
    MAX-ACCESS  not-accessible
    STATUS      current
    DESCRIPTION   "Entry of alarmSeverityDcnTable"
    INDEX       {
                  entityDcnShelfNo,
                  entityDcnSlotNo,
                  entityDcnPortNo,
                  entityDcnExtNo,
                  entityDcnClassName,
                  alarmSeverityDcnType
                }
    ::=  { alarmSeverityDcnTable 1 }

AlarmSeverityDcnEntry ::=  SEQUENCE
  { alarmSeverityDcnType FspR7AlarmListType,
    alarmSeverityDcnValue TrapAlarmSeverity }

alarmSeverityDcnType OBJECT-TYPE
    SYNTAX      FspR7AlarmListType
    MAX-ACCESS  not-accessible
    STATUS      current
    DESCRIPTION   "Type of severity."
    ::=  { alarmSeverityDcnEntry 1 }

alarmSeverityDcnValue OBJECT-TYPE
    SYNTAX      TrapAlarmSeverity
    MAX-ACCESS  read-write
    STATUS      current
    DESCRIPTION   "Value of severity."
    ::=  { alarmSeverityDcnEntry 2 }

endOfAlarmSeverityDcnTable OBJECT-TYPE
    SYNTAX      Integer32
    MAX-ACCESS  read-only
    STATUS      current
    DESCRIPTION
        ""
    ::=  { alarm 19 }

alarmEnvTable OBJECT-TYPE
    SYNTAX      SEQUENCE OF AlarmEnvEntry
    MAX-ACCESS  not-accessible
    STATUS      current
    DESCRIPTION   "alarmEnvTable"
    ::=  { alarm 20 }

alarmEnvEntry OBJECT-TYPE
    SYNTAX      AlarmEnvEntry
    MAX-ACCESS  not-accessible
    STATUS      current
    DESCRIPTION   "Entry of alarmEnvTable"
    INDEX       {
                  entityEnvShelfNo,
                  entityEnvSlotNo,
                  entityEnvPortNo,
                  entityEnvExtNo,
                  entityEnvClassName,
                  alarmEnvType
                }
    ::=  { alarmEnvTable 1 }

AlarmEnvEntry ::=  SEQUENCE
  { alarmEnvType FspR7AlarmListType,
    alarmEnvSeverity TrapAlarmSeverity,
    alarmEnvAffect ServiceImpairment,
    alarmEnvTimeStamp DateAndTime }

alarmEnvType OBJECT-TYPE
    SYNTAX      FspR7AlarmListType
    MAX-ACCESS  not-accessible
    STATUS      current
    DESCRIPTION   "List of all interface conditions."
    ::=  { alarmEnvEntry 1 }

alarmEnvSeverity OBJECT-TYPE
    SYNTAX      TrapAlarmSeverity
    MAX-ACCESS  read-only
    STATUS      current
    DESCRIPTION   "Object identifies the current severity of alarm."
    ::=  { alarmEnvEntry 2 }

alarmEnvAffect OBJECT-TYPE
    SYNTAX      ServiceImpairment
    MAX-ACCESS  read-only
    STATUS      current
    DESCRIPTION   "Object indicates the service impairment affect of the alarm."
    ::=  { alarmEnvEntry 3 }

alarmEnvTimeStamp OBJECT-TYPE
    SYNTAX      DateAndTime
    MAX-ACCESS  read-only
    STATUS      current
    DESCRIPTION   "Timestamp."
    ::=  { alarmEnvEntry 4 }

endOfAlarmEnvTable OBJECT-TYPE
    SYNTAX      Integer32
    MAX-ACCESS  read-only
    STATUS      current
    DESCRIPTION
        ""
    ::=  { alarm 21 }

alarmSeverityEnvTable OBJECT-TYPE
    SYNTAX      SEQUENCE OF AlarmSeverityEnvEntry
    MAX-ACCESS  not-accessible
    STATUS      current
    DESCRIPTION   "alarmSeverityEnvTable"
    ::=  { alarm 22 }

alarmSeverityEnvEntry OBJECT-TYPE
    SYNTAX      AlarmSeverityEnvEntry
    MAX-ACCESS  not-accessible
    STATUS      current
    DESCRIPTION   "Entry of alarmSeverityEnvTable"
    INDEX       {
                  entityEnvShelfNo,
                  entityEnvSlotNo,
                  entityEnvPortNo,
                  entityEnvExtNo,
                  entityEnvClassName,
                  alarmSeverityEnvType
                }
    ::=  { alarmSeverityEnvTable 1 }

AlarmSeverityEnvEntry ::=  SEQUENCE
  { alarmSeverityEnvType FspR7AlarmListType,
    alarmSeverityEnvValue TrapAlarmSeverity }

alarmSeverityEnvType OBJECT-TYPE
    SYNTAX      FspR7AlarmListType
    MAX-ACCESS  not-accessible
    STATUS      current
    DESCRIPTION   "Type of severity."
    ::=  { alarmSeverityEnvEntry 1 }

alarmSeverityEnvValue OBJECT-TYPE
    SYNTAX      TrapAlarmSeverity
    MAX-ACCESS  read-write
    STATUS      current
    DESCRIPTION   "Value of severity."
    ::=  { alarmSeverityEnvEntry 2 }

endOfAlarmSeverityEnvTable OBJECT-TYPE
    SYNTAX      Integer32
    MAX-ACCESS  read-only
    STATUS      current
    DESCRIPTION
        ""
    ::=  { alarm 23 }

alarmContainerTable OBJECT-TYPE
    SYNTAX      SEQUENCE OF AlarmContainerEntry
    MAX-ACCESS  not-accessible
    STATUS      current
    DESCRIPTION   "alarmContainerTable"
    ::=  { alarm 24 }

alarmContainerEntry OBJECT-TYPE
    SYNTAX      AlarmContainerEntry
    MAX-ACCESS  not-accessible
    STATUS      current
    DESCRIPTION   "Entry of alarmContainerTable"
    INDEX       {
                  entityContainerShelfNo,
                  entityContainerSlotNo,
                  entityContainerPortNo,
                  entityContainerExtNo,
                  entityContainerClassName,
                  alarmContainerType
                }
    ::=  { alarmContainerTable 1 }

AlarmContainerEntry ::=  SEQUENCE
  { alarmContainerType FspR7AlarmListType,
    alarmContainerSeverity TrapAlarmSeverity,
    alarmContainerAffect ServiceImpairment,
    alarmContainerTimeStamp DateAndTime }

alarmContainerType OBJECT-TYPE
    SYNTAX      FspR7AlarmListType
    MAX-ACCESS  not-accessible
    STATUS      current
    DESCRIPTION   "List of all interface conditions."
    ::=  { alarmContainerEntry 1 }

alarmContainerSeverity OBJECT-TYPE
    SYNTAX      TrapAlarmSeverity
    MAX-ACCESS  read-only
    STATUS      current
    DESCRIPTION   "Object identifies the current severity of alarm."
    ::=  { alarmContainerEntry 2 }

alarmContainerAffect OBJECT-TYPE
    SYNTAX      ServiceImpairment
    MAX-ACCESS  read-only
    STATUS      current
    DESCRIPTION   "Object indicates the service impairment affect of the alarm."
    ::=  { alarmContainerEntry 3 }

alarmContainerTimeStamp OBJECT-TYPE
    SYNTAX      DateAndTime
    MAX-ACCESS  read-only
    STATUS      current
    DESCRIPTION   "Timestamp."
    ::=  { alarmContainerEntry 4 }

endOfAlarmContainerTable OBJECT-TYPE
    SYNTAX      Integer32
    MAX-ACCESS  read-only
    STATUS      current
    DESCRIPTION
        ""
    ::=  { alarm 25 }

alarmSeverityContainerTable OBJECT-TYPE
    SYNTAX      SEQUENCE OF AlarmSeverityContainerEntry
    MAX-ACCESS  not-accessible
    STATUS      current
    DESCRIPTION   "alarmSeverityContainerTable"
    ::=  { alarm 26 }

alarmSeverityContainerEntry OBJECT-TYPE
    SYNTAX      AlarmSeverityContainerEntry
    MAX-ACCESS  not-accessible
    STATUS      current
    DESCRIPTION   "Entry of alarmSeverityContainerTable"
    INDEX       {
                  entityContainerShelfNo,
                  entityContainerSlotNo,
                  entityContainerPortNo,
                  entityContainerExtNo,
                  entityContainerClassName,
                  alarmSeverityContainerType
                }
    ::=  { alarmSeverityContainerTable 1 }

AlarmSeverityContainerEntry ::=  SEQUENCE
  { alarmSeverityContainerType FspR7AlarmListType,
    alarmSeverityContainerValue TrapAlarmSeverity }

alarmSeverityContainerType OBJECT-TYPE
    SYNTAX      FspR7AlarmListType
    MAX-ACCESS  not-accessible
    STATUS      current
    DESCRIPTION   "Type of severity."
    ::=  { alarmSeverityContainerEntry 1 }

alarmSeverityContainerValue OBJECT-TYPE
    SYNTAX      TrapAlarmSeverity
    MAX-ACCESS  read-write
    STATUS      current
    DESCRIPTION   "Value of severity."
    ::=  { alarmSeverityContainerEntry 2 }

endOfAlarmSeverityContainerTable OBJECT-TYPE
    SYNTAX      Integer32
    MAX-ACCESS  read-only
    STATUS      current
    DESCRIPTION
        ""
    ::=  { alarm 27 }

alarmOpticalMuxTable OBJECT-TYPE
    SYNTAX      SEQUENCE OF AlarmOpticalMuxEntry
    MAX-ACCESS  not-accessible
    STATUS      current
    DESCRIPTION   "alarmOpticalMuxTable"
    ::=  { alarm 28 }

alarmOpticalMuxEntry OBJECT-TYPE
    SYNTAX      AlarmOpticalMuxEntry
    MAX-ACCESS  not-accessible
    STATUS      current
    DESCRIPTION   "Entry of alarmOpticalMuxTable"
    INDEX       {
                  entityOpticalMuxShelfNo,
                  entityOpticalMuxSlotNo,
                  entityOpticalMuxPortNo,
                  entityOpticalMuxExtNo,
                  entityOpticalMuxClassName,
                  alarmOpticalMuxType
                }
    ::=  { alarmOpticalMuxTable 1 }

AlarmOpticalMuxEntry ::=  SEQUENCE
  { alarmOpticalMuxType FspR7AlarmListType,
    alarmOpticalMuxSeverity TrapAlarmSeverity,
    alarmOpticalMuxAffect ServiceImpairment,
    alarmOpticalMuxTimeStamp DateAndTime }

alarmOpticalMuxType OBJECT-TYPE
    SYNTAX      FspR7AlarmListType
    MAX-ACCESS  not-accessible
    STATUS      current
    DESCRIPTION   "List of all interface conditions."
    ::=  { alarmOpticalMuxEntry 1 }

alarmOpticalMuxSeverity OBJECT-TYPE
    SYNTAX      TrapAlarmSeverity
    MAX-ACCESS  read-only
    STATUS      current
    DESCRIPTION   "Object identifies the current severity of alarm."
    ::=  { alarmOpticalMuxEntry 2 }

alarmOpticalMuxAffect OBJECT-TYPE
    SYNTAX      ServiceImpairment
    MAX-ACCESS  read-only
    STATUS      current
    DESCRIPTION   "Object indicates the service impairment affect of the alarm."
    ::=  { alarmOpticalMuxEntry 3 }

alarmOpticalMuxTimeStamp OBJECT-TYPE
    SYNTAX      DateAndTime
    MAX-ACCESS  read-only
    STATUS      current
    DESCRIPTION   "Timestamp."
    ::=  { alarmOpticalMuxEntry 4 }

endOfAlarmOpticalMuxTable OBJECT-TYPE
    SYNTAX      Integer32
    MAX-ACCESS  read-only
    STATUS      current
    DESCRIPTION
        ""
    ::=  { alarm 29 }

alarmSeverityOpticalMuxTable OBJECT-TYPE
    SYNTAX      SEQUENCE OF AlarmSeverityOpticalMuxEntry
    MAX-ACCESS  not-accessible
    STATUS      current
    DESCRIPTION   "alarmSeverityOpticalMuxTable"
    ::=  { alarm 30 }

alarmSeverityOpticalMuxEntry OBJECT-TYPE
    SYNTAX      AlarmSeverityOpticalMuxEntry
    MAX-ACCESS  not-accessible
    STATUS      current
    DESCRIPTION   "Entry of alarmSeverityOpticalMuxTable"
    INDEX       {
                  entityOpticalMuxShelfNo,
                  entityOpticalMuxSlotNo,
                  entityOpticalMuxPortNo,
                  entityOpticalMuxExtNo,
                  entityOpticalMuxClassName,
                  alarmSeverityOpticalMuxType
                }
    ::=  { alarmSeverityOpticalMuxTable 1 }

AlarmSeverityOpticalMuxEntry ::=  SEQUENCE
  { alarmSeverityOpticalMuxType FspR7AlarmListType,
    alarmSeverityOpticalMuxValue TrapAlarmSeverity }

alarmSeverityOpticalMuxType OBJECT-TYPE
    SYNTAX      FspR7AlarmListType
    MAX-ACCESS  not-accessible
    STATUS      current
    DESCRIPTION   "Type of severity."
    ::=  { alarmSeverityOpticalMuxEntry 1 }

alarmSeverityOpticalMuxValue OBJECT-TYPE
    SYNTAX      TrapAlarmSeverity
    MAX-ACCESS  read-write
    STATUS      current
    DESCRIPTION   "Value of severity."
    ::=  { alarmSeverityOpticalMuxEntry 2 }

endOfAlarmSeverityOpticalMuxTable OBJECT-TYPE
    SYNTAX      Integer32
    MAX-ACCESS  read-only
    STATUS      current
    DESCRIPTION
        ""
    ::=  { alarm 31 }

alarmShelfConnTable OBJECT-TYPE
    SYNTAX      SEQUENCE OF AlarmShelfConnEntry
    MAX-ACCESS  not-accessible
    STATUS      current
    DESCRIPTION   "alarmShelfConnTable"
    ::=  { alarm 32 }

alarmShelfConnEntry OBJECT-TYPE
    SYNTAX      AlarmShelfConnEntry
    MAX-ACCESS  not-accessible
    STATUS      current
    DESCRIPTION   "Entry of alarmShelfConnTable"
    INDEX       {
                  entityShelfConnShelfNo,
                  entityShelfConnSlotNo,
                  entityShelfConnPortNo,
                  entityShelfConnExtNo,
                  entityShelfConnClassName,
                  alarmShelfConnType
                }
    ::=  { alarmShelfConnTable 1 }

AlarmShelfConnEntry ::=  SEQUENCE
  { alarmShelfConnType FspR7AlarmListType,
    alarmShelfConnSeverity TrapAlarmSeverity,
    alarmShelfConnAffect ServiceImpairment,
    alarmShelfConnTimeStamp DateAndTime }

alarmShelfConnType OBJECT-TYPE
    SYNTAX      FspR7AlarmListType
    MAX-ACCESS  not-accessible
    STATUS      current
    DESCRIPTION   "List of all interface conditions."
    ::=  { alarmShelfConnEntry 1 }

alarmShelfConnSeverity OBJECT-TYPE
    SYNTAX      TrapAlarmSeverity
    MAX-ACCESS  read-only
    STATUS      current
    DESCRIPTION   "Object identifies the current severity of alarm."
    ::=  { alarmShelfConnEntry 2 }

alarmShelfConnAffect OBJECT-TYPE
    SYNTAX      ServiceImpairment
    MAX-ACCESS  read-only
    STATUS      current
    DESCRIPTION   "Object indicates the service impairment affect of the alarm."
    ::=  { alarmShelfConnEntry 3 }

alarmShelfConnTimeStamp OBJECT-TYPE
    SYNTAX      DateAndTime
    MAX-ACCESS  read-only
    STATUS      current
    DESCRIPTION   "Timestamp."
    ::=  { alarmShelfConnEntry 4 }

endOfAlarmShelfConnTable OBJECT-TYPE
    SYNTAX      Integer32
    MAX-ACCESS  read-only
    STATUS      current
    DESCRIPTION
        ""
    ::=  { alarm 33 }

alarmSeverityShelfConnTable OBJECT-TYPE
    SYNTAX      SEQUENCE OF AlarmSeverityShelfConnEntry
    MAX-ACCESS  not-accessible
    STATUS      current
    DESCRIPTION   "alarmSeverityShelfConnTable"
    ::=  { alarm 34 }

alarmSeverityShelfConnEntry OBJECT-TYPE
    SYNTAX      AlarmSeverityShelfConnEntry
    MAX-ACCESS  not-accessible
    STATUS      current
    DESCRIPTION   "Entry of alarmSeverityShelfConnTable"
    INDEX       {
                  entityShelfConnShelfNo,
                  entityShelfConnSlotNo,
                  entityShelfConnPortNo,
                  entityShelfConnExtNo,
                  entityShelfConnClassName,
                  alarmSeverityShelfConnType
                }
    ::=  { alarmSeverityShelfConnTable 1 }

AlarmSeverityShelfConnEntry ::=  SEQUENCE
  { alarmSeverityShelfConnType FspR7AlarmListType,
    alarmSeverityShelfConnValue TrapAlarmSeverity }

alarmSeverityShelfConnType OBJECT-TYPE
    SYNTAX      FspR7AlarmListType
    MAX-ACCESS  not-accessible
    STATUS      current
    DESCRIPTION   "Type of severity."
    ::=  { alarmSeverityShelfConnEntry 1 }

alarmSeverityShelfConnValue OBJECT-TYPE
    SYNTAX      TrapAlarmSeverity
    MAX-ACCESS  read-write
    STATUS      current
    DESCRIPTION   "Value of severity."
    ::=  { alarmSeverityShelfConnEntry 2 }

endOfAlarmSeverityShelfConnTable OBJECT-TYPE
    SYNTAX      Integer32
    MAX-ACCESS  read-only
    STATUS      current
    DESCRIPTION
        ""
    ::=  { alarm 35 }

alarmProfileSeverityTable OBJECT-TYPE
    SYNTAX      SEQUENCE OF AlarmProfileSeverityEntry
    MAX-ACCESS  not-accessible
    STATUS      current
    DESCRIPTION   ""
    ::=  { alarmProfile 1 }

alarmProfileSeverityEntry OBJECT-TYPE
    SYNTAX      AlarmProfileSeverityEntry
    MAX-ACCESS  not-accessible
    STATUS      current
    DESCRIPTION   ""
    INDEX       {
                  alarmProfileSeverityAidType,
                  alarmProfileSeverityType
                }
    ::=  { alarmProfileSeverityTable 1 }

AlarmProfileSeverityEntry ::=  SEQUENCE
  { alarmProfileSeverityAidType FspR7AidType,
    alarmProfileSeverityType FspR7AlarmProfileList,
    alarmProfileSeverityValue TrapAlarmSeverity,
    alarmProfileSeverityDefaultValue TrapAlarmSeverity }

alarmProfileSeverityAidType OBJECT-TYPE
    SYNTAX      FspR7AidType
    MAX-ACCESS  not-accessible
    STATUS      current
    DESCRIPTION   ""
    ::=  { alarmProfileSeverityEntry 1 }

alarmProfileSeverityType OBJECT-TYPE
    SYNTAX      FspR7AlarmProfileList
    MAX-ACCESS  not-accessible
    STATUS      current
    DESCRIPTION   ""
    ::=  { alarmProfileSeverityEntry 2 }

alarmProfileSeverityValue OBJECT-TYPE
    SYNTAX      TrapAlarmSeverity
    MAX-ACCESS  read-write
    STATUS      current
    DESCRIPTION   "This object identifies the severity assigned to this alarm."
    ::=  { alarmProfileSeverityEntry 3 }

alarmProfileSeverityDefaultValue OBJECT-TYPE
    SYNTAX      TrapAlarmSeverity
    MAX-ACCESS  read-only
    STATUS      current
    DESCRIPTION   "This object identifies the default severity of this alarm."
    ::=  { alarmProfileSeverityEntry 4 }

endOfAlarmProfileSeverityTable OBJECT-TYPE
    SYNTAX      Integer32
    MAX-ACCESS  read-only
    STATUS      current
    DESCRIPTION
        ""
    ::=  { alarmProfile 2 }

endOfAlarmProfile OBJECT-TYPE
    SYNTAX      Integer32
    MAX-ACCESS  read-only
    STATUS      current
    DESCRIPTION
        ""
    ::=  { alarmProfile 10000 }

endOfAlarm OBJECT-TYPE
    SYNTAX      Integer32
    MAX-ACCESS  read-only
    STATUS      current
    DESCRIPTION
        ""
    ::=  { alarm 10000 }


fspR7CreationTrap NOTIFICATION-TYPE
    STATUS      current
    DESCRIPTION   "This trap is sent every time an entity is created."
    ::=  { fspR7Trap 1 }

fspR7DeletionTrap NOTIFICATION-TYPE
    STATUS      current
    DESCRIPTION   "This trap is sent every time an entity is destroyed."
    ::=  { fspR7Trap 2 }

fspR7StateChangeTrap NOTIFICATION-TYPE
    STATUS      current
    DESCRIPTION   "This trap is sent when an entity state is changed."
    ::=  { fspR7Trap 3 }

fspR7ObjectChangeTrap NOTIFICATION-TYPE
    STATUS      current
    DESCRIPTION   "This trap is sent when an object is changed."
    ::=  { fspR7Trap 4 }

alarmTerminalLoopback NOTIFICATION-TYPE
    STATUS      current
    DESCRIPTION   "Inward Loopback on Interface"
    ::=  { fspR7Trap 5 }


alarmOosDisabled NOTIFICATION-TYPE
    STATUS      current
    DESCRIPTION   "Non-Specific Disablement of Management Access"
    ::=  { fspR7Trap 6 }


alarmOosManagement NOTIFICATION-TYPE
    STATUS      current
    DESCRIPTION   "Alarms are logged but not notified, service affecting changes are permitted"
    ::=  { fspR7Trap 7 }


alarmOosMaintenance NOTIFICATION-TYPE
    STATUS      current
    DESCRIPTION   "Alarms are logged but not notified, service affecting changes and operations are permitted"
    ::=  { fspR7Trap 8 }


alarmOosAins NOTIFICATION-TYPE
    STATUS      current
    DESCRIPTION   "Automatic In Service"
    ::=  { fspR7Trap 9 }


alarmRemoved NOTIFICATION-TYPE
    STATUS      current
    DESCRIPTION   "The equipment has been removed / unplugged / disconnected.
         This condition has been determined to be more probable than that below,
         which is also supersedes."
    ::=  { fspR7Trap 10 }


alarmLossOfSignal NOTIFICATION-TYPE
    STATUS      current
    DESCRIPTION   "Loss of Signal"
    ::=  { fspR7Trap 11 }


alarmOptInputPwrReceivedTooLow NOTIFICATION-TYPE
    STATUS      current
    DESCRIPTION   "Optical Power Rx too Low"
    ::=  { fspR7Trap 12 }


alarmOptInputPwrReceivedTooHigh NOTIFICATION-TYPE
    STATUS      current
    DESCRIPTION   "Optical Power Rx too High"
    ::=  { fspR7Trap 13 }


alarmLaserTemperatureTooHigh NOTIFICATION-TYPE
    STATUS      current
    DESCRIPTION   "TCA - Fixed high threshold of Laser Temperature has been crossed."
    ::=  { fspR7Trap 14 }


alarmLaserTemperatureTooLow NOTIFICATION-TYPE
    STATUS      current
    DESCRIPTION   "TCA - Fixed low threshold of Laser Temperature has been crossed."
    ::=  { fspR7Trap 15 }


alarmOptOutputPowerTransTooLow NOTIFICATION-TYPE
    STATUS      current
    DESCRIPTION   "TCA - Optical Power Transmitted (output) too low"
    ::=  { fspR7Trap 16 }


alarmOptOutputPowerTransTooHigh NOTIFICATION-TYPE
    STATUS      current
    DESCRIPTION   "TCA - Optical Power Transmitted (output) too high"
    ::=  { fspR7Trap 17 }


alarmAutoShutdownToHighTemp NOTIFICATION-TYPE
    STATUS      current
    DESCRIPTION   "Facility autonomously shut down with Transmitter off due to temperature."
    ::=  { fspR7Trap 18 }


alarmAutoShutdownToHighTxPwr NOTIFICATION-TYPE
    STATUS      current
    DESCRIPTION   "Facility Autonomously Shut Down with Transmitter OFF because of excessiv optical Power Transmitted."
    ::=  { fspR7Trap 19 }


alarmLaserEndOfLife NOTIFICATION-TYPE
    STATUS      current
    DESCRIPTION   "End Of Life [laser degrade]."
    ::=  { fspR7Trap 20 }


alarmServerSignalFailureVf NOTIFICATION-TYPE
    STATUS      current
    DESCRIPTION   "Aggregate level failure"
    ::=  { fspR7Trap 21 }


alarmEqualizationProgress NOTIFICATION-TYPE
    STATUS      current
    DESCRIPTION   "Equalization and countdown in progress"
    ::=  { fspR7Trap 22 }


alarmUPortFailure NOTIFICATION-TYPE
    STATUS      current
    DESCRIPTION   "Internal U Port Failure"
    ::=  { fspR7Trap 23 }


alarmAutoShutdownBlock NOTIFICATION-TYPE
    STATUS      current
    DESCRIPTION   "Auto Shutdown Block"
    ::=  { fspR7Trap 24 }


alarmAutoPowerShutdown NOTIFICATION-TYPE
    STATUS      current
    DESCRIPTION   "Automatic Power Shutdown"
    ::=  { fspR7Trap 25 }


alarmConfOutPowerTransTooHigh NOTIFICATION-TYPE
    STATUS      current
    DESCRIPTION   "TCA - Optical Power Transmitted (output) too high"
    ::=  { fspR7Trap 26 }


alarmConfOutPowerTransTooLow NOTIFICATION-TYPE
    STATUS      current
    DESCRIPTION   "TCA - Optical Power Transmitted (output) too low"
    ::=  { fspR7Trap 27 }


alarmOptSignalFailure NOTIFICATION-TYPE
    STATUS      current
    DESCRIPTION   "Optical Power Transmit Signal Failure"
    ::=  { fspR7Trap 28 }


alarmDsbdChannelPowerTooHigh NOTIFICATION-TYPE
    STATUS      current
    DESCRIPTION   "Optical power is not blocked when service is disabled (OPT > -25 dBm)."
    ::=  { fspR7Trap 29 }


alarmLossOfSignalCPort NOTIFICATION-TYPE
    STATUS      current
    DESCRIPTION   "Loss of signal on C Port that corresponds to the network VCH via CRS"
    ::=  { fspR7Trap 30 }


alarmLossOfSignalNPort NOTIFICATION-TYPE
    STATUS      current
    DESCRIPTION   "Internal N Port Failure"
    ::=  { fspR7Trap 31 }


alarmOutputPowerFault NOTIFICATION-TYPE
    STATUS      current
    DESCRIPTION   "There is no channel output power while the input power for the channel is above the LOS TH and the channel attenuation is set to a valid value."
    ::=  { fspR7Trap 32 }


alarmEqlzAdjust NOTIFICATION-TYPE
    STATUS      current
    DESCRIPTION   "Channel power adjustment is in progress"
    ::=  { fspR7Trap 33 }


alarmAmpFailure NOTIFICATION-TYPE
    STATUS      current
    DESCRIPTION   "SGEO-AMP is raised at a dependent entity due to an AMP auto shutdown condition at the associated supporting entity."
    ::=  { fspR7Trap 34 }


alarmEqptProvMismatch NOTIFICATION-TYPE
    STATUS      current
    DESCRIPTION   "Provisioning incompatible with configuration"
    ::=  { fspR7Trap 35 }


alarmBackreflectionTooHigh NOTIFICATION-TYPE
    STATUS      current
    DESCRIPTION   "Backreflection Power too High, at Tx port"
    ::=  { fspR7Trap 36 }


transientEqlzStart NOTIFICATION-TYPE
    STATUS      current
    DESCRIPTION   "Start of Connection Equalization"
    ::=  { fspR7Trap 37 }


transientEqlzFailed NOTIFICATION-TYPE
    STATUS      current
    DESCRIPTION   "Failure of Connection Equalization"
    ::=  { fspR7Trap 38 }


transientEqlzCompleted NOTIFICATION-TYPE
    STATUS      current
    DESCRIPTION   "Completion of Connection Equalization"
    ::=  { fspR7Trap 39 }


transientEqlzRequestDenied NOTIFICATION-TYPE
    STATUS      current
    DESCRIPTION   "Equalization request denied (could not be performed) by enity"
    ::=  { fspR7Trap 40 }


transientEqlzNotRequired NOTIFICATION-TYPE
    STATUS      current
    DESCRIPTION   "Equalization Null - Not Required - channel(s) are currently equalized"
    ::=  { fspR7Trap 41 }


transientEqlzProcessPassed NOTIFICATION-TYPE
    STATUS      current
    DESCRIPTION   "Equalization Operation completed sucessfully"
    ::=  { fspR7Trap 42 }


transientEqlzProcessWait NOTIFICATION-TYPE
    STATUS      current
    DESCRIPTION   "Eqalization is in progress, User must wait then request equalization"
    ::=  { fspR7Trap 43 }


transientPmSnapshotStarted NOTIFICATION-TYPE
    STATUS      current
    DESCRIPTION   "Reference value save start"
    ::=  { fspR7Trap 44 }


transientEqlzAuto NOTIFICATION-TYPE
    STATUS      current
    DESCRIPTION   "Scheduled Equalization resulted in adjustment of VCH"
    ::=  { fspR7Trap 45 }


transientEqlzRamanAdjust NOTIFICATION-TYPE
    STATUS      current
    DESCRIPTION   "Auto equalization for RAMAN adjustment on existing in-service cross-connected VCHs"
    ::=  { fspR7Trap 46 }


alarmFiberConnLos NOTIFICATION-TYPE
    STATUS      current
    DESCRIPTION   "Fiber Connection Loss of Signal"
    ::=  { fspR7Trap 48 }


alarmFiberConnOptFault NOTIFICATION-TYPE
    STATUS      current
    DESCRIPTION   "Fiber connection transmit optical power failure."
    ::=  { fspR7Trap 49 }


alarmFiberConnInvalid NOTIFICATION-TYPE
    STATUS      current
    DESCRIPTION   "The fiber connection is in violation of the fiber connection rules."
    ::=  { fspR7Trap 50 }


alarmFiberConnMismatch NOTIFICATION-TYPE
    STATUS      current
    DESCRIPTION   "The fiber connection does not match the existing fiber-map in database."
    ::=  { fspR7Trap 51 }


alarmFiberConnCommError NOTIFICATION-TYPE
    STATUS      current
    DESCRIPTION   "Fiber Connection Communications Fault"
    ::=  { fspR7Trap 52 }


alarmFiberConnProtocolFailure NOTIFICATION-TYPE
    STATUS      current
    DESCRIPTION   "Fiber Connection Protocol Fault"
    ::=  { fspR7Trap 53 }


alarmFiberConnDataFailure NOTIFICATION-TYPE
    STATUS      current
    DESCRIPTION   "Fiber Connection Data Fault"
    ::=  { fspR7Trap 54 }


alarmFiberAttenuationHigh NOTIFICATION-TYPE
    STATUS      current
    DESCRIPTION   "Fiber Connection Attenuation High"
    ::=  { fspR7Trap 55 }


transientFiberConnStatChange NOTIFICATION-TYPE
    STATUS      current
    DESCRIPTION   "Fiber Connection Status Change"
    ::=  { fspR7Trap 56 }


alarmLaserBiasCurrAbnormal NOTIFICATION-TYPE
    STATUS      current
    DESCRIPTION   "Abnormally High Laser Bias Current Level under the current operating conditions."
    ::=  { fspR7Trap 57 }


alarmFiberConnInvalidTx NOTIFICATION-TYPE
    STATUS      current
    DESCRIPTION   "The fiber connection is in violation of the fiber connection rules."
    ::=  { fspR7Trap 58 }


alarmFiberConnMismatchTx NOTIFICATION-TYPE
    STATUS      current
    DESCRIPTION   "The fiber connection does not match the existing fiber-map in database."
    ::=  { fspR7Trap 59 }


alarmFiberAttenuationHighTx NOTIFICATION-TYPE
    STATUS      current
    DESCRIPTION   "Fiber Connection Attenuation High Tx"
    ::=  { fspR7Trap 60 }


alarmLaserFailure NOTIFICATION-TYPE
    STATUS      current
    DESCRIPTION   "Optical Power Transmitted Failure: Laser Failure"
    ::=  { fspR7Trap 61 }


alarmLossOfReceiverClockRecovery NOTIFICATION-TYPE
    STATUS      current
    DESCRIPTION   "Rx Clock Sync Failure"
    ::=  { fspR7Trap 62 }


alarmFiberAttenuationCond NOTIFICATION-TYPE
    STATUS      current
    DESCRIPTION   "Fiber Connection High Fiber Attenuation Condition"
    ::=  { fspR7Trap 63 }


alarmChannelMismatch NOTIFICATION-TYPE
    STATUS      current
    DESCRIPTION   "Channel provisioning incompatible with associated port configuration"
    ::=  { fspR7Trap 64 }


alarmAlarmIndicationSignalLine NOTIFICATION-TYPE
    STATUS      current
    DESCRIPTION   "Alarm Indication Signal Line / Multiplex Section"
    ::=  { fspR7Trap 65 }


alarmAlarmIndicationSignalLowerOrderPath NOTIFICATION-TYPE
    STATUS      current
    DESCRIPTION   "Alarm Indication Signal Lower Order Path"
    ::=  { fspR7Trap 66 }


alarmAlarmIndicationSignalOdu NOTIFICATION-TYPE
    STATUS      current
    DESCRIPTION   "Alarm Indication Signal ODU Path Monitoring"
    ::=  { fspR7Trap 67 }


alarmAlarmIndicationSignalOpu NOTIFICATION-TYPE
    STATUS      current
    DESCRIPTION   "Alarm Indication Signal OPU Path Monitoring"
    ::=  { fspR7Trap 68 }


alarmAlarmIndicationSignalOtu NOTIFICATION-TYPE
    STATUS      current
    DESCRIPTION   "Alarm Indication Signal OTU Section Monitoring"
    ::=  { fspR7Trap 69 }


alarmAlarmIndicationSignalHigherOrderPath NOTIFICATION-TYPE
    STATUS      current
    DESCRIPTION   "Alarm Indication Signal Path"
    ::=  { fspR7Trap 70 }


alarmAlarmIndicationSignalOduTcmA NOTIFICATION-TYPE
    STATUS      current
    DESCRIPTION   "Alarm Indication Signal ODU Tandem Connection Monitoring Instance A"
    ::=  { fspR7Trap 71 }


alarmAlarmIndicationSignalOduTcmB NOTIFICATION-TYPE
    STATUS      current
    DESCRIPTION   "Alarm Indication Signal ODU Tandem Connection Monitoring Instance B"
    ::=  { fspR7Trap 72 }


alarmAlarmIndicationSignalOduTcmC NOTIFICATION-TYPE
    STATUS      current
    DESCRIPTION   "Alarm Indication Signal ODU Tandem Connection Monitoring Instance C"
    ::=  { fspR7Trap 73 }


alarmVirtualChannelAis NOTIFICATION-TYPE
    STATUS      current
    DESCRIPTION   "Client Failure Far-end"
    ::=  { fspR7Trap 74 }


alarmAmplifierAbnormal NOTIFICATION-TYPE
    STATUS      current
    DESCRIPTION   "Output of amplifier is abnormal"
    ::=  { fspR7Trap 75 }


alarmAutomaticPowerReduction NOTIFICATION-TYPE
    STATUS      current
    DESCRIPTION   "The signal power exceeds the limit"
    ::=  { fspR7Trap 76 }


alarmAutomaticPowerReductionForEyeSafety NOTIFICATION-TYPE
    STATUS      current
    DESCRIPTION   "Output power is automatically reduced to eye safety limit"
    ::=  { fspR7Trap 77 }


transientAlpSettingFinished NOTIFICATION-TYPE
    STATUS      current
    DESCRIPTION   "Setting of alarm severities to Alarm Profile values completed"
    ::=  { fspR7Trap 78 }


transientAlpSettingStarted NOTIFICATION-TYPE
    STATUS      current
    DESCRIPTION   "Setting of alarm severities to Alarm Profile values started"
    ::=  { fspR7Trap 79 }


alarmApsConfigMismatch NOTIFICATION-TYPE
    STATUS      current
    DESCRIPTION   "Configuration Mismatch between NEND and FEND. Reported by working facility (PATHID==WKG) or protection facility (PATHID==PROTN)"
    ::=  { fspR7Trap 80 }


alarmApsProtocolFailure NOTIFICATION-TYPE
    STATUS      current
    DESCRIPTION   "Protocol Failure between NEND and FEND. Reported by protecting facility (PATHID==PROTN)."
    ::=  { fspR7Trap 81 }


alarmAseLow NOTIFICATION-TYPE
    STATUS      current
    DESCRIPTION   "Pump laser is not switched on because of too low ASE power"
    ::=  { fspR7Trap 82 }


alarmAseTableGenFailLow NOTIFICATION-TYPE
    STATUS      current
    DESCRIPTION   "ASE table generation failed because of too low ASE level"
    ::=  { fspR7Trap 83 }


alarmAseTableGenFailHighBackreflection NOTIFICATION-TYPE
    STATUS      current
    DESCRIPTION   "ASE table generation failed because of too high backreflection"
    ::=  { fspR7Trap 84 }


alarmAseTableGenFailOscMissing NOTIFICATION-TYPE
    STATUS      current
    DESCRIPTION   "ASE table generation failed because OSC is missing"
    ::=  { fspR7Trap 85 }


alarmAseTableGenFailPilot NOTIFICATION-TYPE
    STATUS      current
    DESCRIPTION   "ASE table generation failed because PILOT is missing"
    ::=  { fspR7Trap 86 }


alarmAseTableGenFailSignalinput NOTIFICATION-TYPE
    STATUS      current
    DESCRIPTION   "ASE table generation failed because of detected input signal"
    ::=  { fspR7Trap 87 }


alarmAseTableNotAvailable NOTIFICATION-TYPE
    STATUS      current
    DESCRIPTION   "ASE table not available or invalid"
    ::=  { fspR7Trap 88 }


alarmAseTableGenProgress NOTIFICATION-TYPE
    STATUS      current
    DESCRIPTION   "ASE table is in the build process"
    ::=  { fspR7Trap 89 }


alarmEncryptionPortAuthPasswdMissing NOTIFICATION-TYPE
    STATUS      current
    DESCRIPTION   "Authentication password missing"
    ::=  { fspR7Trap 90 }


transientCryptoAuthPasswdChanged NOTIFICATION-TYPE
    STATUS      current
    DESCRIPTION   "Change of Authentication Password"
    ::=  { fspR7Trap 91 }


alarmBackwardDefectIndicationOdu NOTIFICATION-TYPE
    STATUS      current
    DESCRIPTION   "ODU Backward Defect Indication"
    ::=  { fspR7Trap 92 }


alarmBackwardDefectIndicationOtu NOTIFICATION-TYPE
    STATUS      current
    DESCRIPTION   "OTU Backward Defect Indication"
    ::=  { fspR7Trap 93 }


alarmBackwardDefectIndicationOduTcmA NOTIFICATION-TYPE
    STATUS      current
    DESCRIPTION   "ODU Tandem Connection Monitoring A Backward Defect Indication"
    ::=  { fspR7Trap 94 }


alarmBackwardDefectIndicationOduTcmB NOTIFICATION-TYPE
    STATUS      current
    DESCRIPTION   "ODU Tandem Connection Monitoring B Backward Defect Indication"
    ::=  { fspR7Trap 95 }


alarmBackwardDefectIndicationOduTcmC NOTIFICATION-TYPE
    STATUS      current
    DESCRIPTION   "ODU Tandem Connection Monitoring C Backward Defect Indication"
    ::=  { fspR7Trap 96 }


alarmTopologyDataCalculationInProgress NOTIFICATION-TYPE
    STATUS      current
    DESCRIPTION   "Calculation of topology in progress"
    ::=  { fspR7Trap 97 }


transientDispersionCompFailed NOTIFICATION-TYPE
    STATUS      current
    DESCRIPTION   "Optimization of Chromatic Dispersion Compensation Fail"
    ::=  { fspR7Trap 98 }


alarmDispertionTunningCondition NOTIFICATION-TYPE
    STATUS      current
    DESCRIPTION   "Chromatic Dispersion Compensation In Progress"
    ::=  { fspR7Trap 99 }


alarmLossOfCharSync NOTIFICATION-TYPE
    STATUS      current
    DESCRIPTION   "Unable to syncronise on the characters in the incoming datastream"
    ::=  { fspR7Trap 100 }


alarmLossOfCharSyncFromFarEnd NOTIFICATION-TYPE
    STATUS      current
    DESCRIPTION   "Loss of Character Synchronization from FEND"
    ::=  { fspR7Trap 101 }


transientCryptoAuthPasswdInvalid NOTIFICATION-TYPE
    STATUS      current
    DESCRIPTION   "A wrong Authentication password was sent with the command"
    ::=  { fspR7Trap 102 }


alarmEncryptionPortEncryptionSwitchOffEnabled NOTIFICATION-TYPE
    STATUS      current
    DESCRIPTION   "User enabled switching encryption off"
    ::=  { fspR7Trap 103 }


alarmEncryptionModuleCryPasswdMissing NOTIFICATION-TYPE
    STATUS      current
    DESCRIPTION   "Crypto Officer password missing"
    ::=  { fspR7Trap 104 }


transientCryptoPasswdChanged NOTIFICATION-TYPE
    STATUS      current
    DESCRIPTION   "Crypto Officer Password Changed"
    ::=  { fspR7Trap 105 }


transientCryptoRtf NOTIFICATION-TYPE
    STATUS      current
    DESCRIPTION   "Encryption settings reset to factory defaults"
    ::=  { fspR7Trap 106 }


alarmEncryptionModuleSelfTestStarted NOTIFICATION-TYPE
    STATUS      current
    DESCRIPTION   "Encryption selftest running"
    ::=  { fspR7Trap 107 }


alarmEncryptionPortEncryptionSwitchedOff NOTIFICATION-TYPE
    STATUS      current
    DESCRIPTION   "Encryption switched off"
    ::=  { fspR7Trap 108 }


alarmOpuClientSignalFail NOTIFICATION-TYPE
    STATUS      current
    DESCRIPTION   "OPU Client Signal Fail"
    ::=  { fspR7Trap 109 }


alarmDatabaseMismatch NOTIFICATION-TYPE
    STATUS      current
    DESCRIPTION   "compare DBACT__FAIL x.y.z in UBR note DBTYPE is retrievable immediately with RTRV-SYS, we do not currently supported a RTRV-COND-SYS"
    ::=  { fspR7Trap 110 }


alarmDatabaseFailure NOTIFICATION-TYPE
    STATUS      current
    DESCRIPTION   "Database Failure detect by Database Check Routine"
    ::=  { fspR7Trap 111 }


alarmDatabaseNcuMismatch NOTIFICATION-TYPE
    STATUS      current
    DESCRIPTION   "This parameter indicates a change of NCU Type (NCU<->NCU2E)"
    ::=  { fspR7Trap 112 }


alarmDbReplicationIncompleted NOTIFICATION-TYPE
    STATUS      current
    DESCRIPTION   "DB Replication Incomplete"
    ::=  { fspR7Trap 113 }


alarmDatabaseVersionMismatch NOTIFICATION-TYPE
    STATUS      current
    DESCRIPTION   "The current DB is newer than required, or not updateable"
    ::=  { fspR7Trap 114 }


alarmXfpDecisionThresSetFailed NOTIFICATION-TYPE
    STATUS      current
    DESCRIPTION   "Decision threshold setting failed"
    ::=  { fspR7Trap 115 }


alarmDuplexLinkFailure NOTIFICATION-TYPE
    STATUS      current
    DESCRIPTION   "Controller Protection Link Failure"
    ::=  { fspR7Trap 116 }


transientFarEndDyingGasp NOTIFICATION-TYPE
    STATUS      current
    DESCRIPTION   "signal received from far end upon far end power loss"
    ::=  { fspR7Trap 117 }


alarmSingleFanFailure NOTIFICATION-TYPE
    STATUS      current
    DESCRIPTION   "Fan operation is degraded and needs attention (cleaning, filter replacement or possible fan replacement)."
    ::=  { fspR7Trap 118 }


alarmMultipleFanFailure NOTIFICATION-TYPE
    STATUS      current
    DESCRIPTION   "Fan is failing or failed and needs replacement."
    ::=  { fspR7Trap 119 }


alarmLossOfSignalTransmitter NOTIFICATION-TYPE
    STATUS      current
    DESCRIPTION   "A Loss of signal has been detected on the FAR-END facility."
    ::=  { fspR7Trap 120 }


transientFarEndChanged NOTIFICATION-TYPE
    STATUS      current
    DESCRIPTION   "Neighbor Discovery Dectected a Far End Change"
    ::=  { fspR7Trap 121 }


alarmFarEndIpAddressUnknown NOTIFICATION-TYPE
    STATUS      current
    DESCRIPTION   "Send by active facility. If an FEND IP Address is changed the corresponding NODE-IP cannot be determined by the OSCM"
    ::=  { fspR7Trap 122 }


alarmFarEndCommFailure NOTIFICATION-TYPE
    STATUS      current
    DESCRIPTION   "The connection to the Far End Optojack plug is dysfunctional"
    ::=  { fspR7Trap 123 }


transientTopologyDataInvalid NOTIFICATION-TYPE
    STATUS      current
    DESCRIPTION   "Topology Detection Data invalid"
    ::=  { fspR7Trap 124 }


alarmBackupForcedToHalt NOTIFICATION-TYPE
    STATUS      current
    DESCRIPTION   "Forced Halt"
    ::=  { fspR7Trap 125 }


transientForcedReboot NOTIFICATION-TYPE
    STATUS      current
    DESCRIPTION   "Forced Reboot"
    ::=  { fspR7Trap 126 }


alarmFacilityForcedOn NOTIFICATION-TYPE
    STATUS      current
    DESCRIPTION   "Laser or Switch forced ON"
    ::=  { fspR7Trap 127 }


alarmFwdAseTableFailPilot NOTIFICATION-TYPE
    STATUS      current
    DESCRIPTION   "Force of BWD Raman pilot for FWD ASE Table Build Failed"
    ::=  { fspR7Trap 128 }


alarmFwdAseTableOnPilot NOTIFICATION-TYPE
    STATUS      current
    DESCRIPTION   "Force the BWD Raman Pilot on to allow building of FWD Raman ASE Table"
    ::=  { fspR7Trap 129 }


transientCryptoFwpUpdate NOTIFICATION-TYPE
    STATUS      current
    DESCRIPTION   "A new FWP is installed"
    ::=  { fspR7Trap 130 }


alarmEncryptionModuleFwpUpdateEnabled NOTIFICATION-TYPE
    STATUS      current
    DESCRIPTION   "FWP upgrade is allowed"
    ::=  { fspR7Trap 131 }


alarmFwpMismatchDownloadNotServiceAffecting NOTIFICATION-TYPE
    STATUS      current
    DESCRIPTION   "Firmware Package Mismatch; download will be NOT Service Affecting"
    ::=  { fspR7Trap 132 }


alarmFwpMismatchDownloadServiceAffecting NOTIFICATION-TYPE
    STATUS      current
    DESCRIPTION   "Firmware Package Mismatch; download will be Service Affecting"
    ::=  { fspR7Trap 133 }


transientCryptoFwpRevChanged NOTIFICATION-TYPE
    STATUS      current
    DESCRIPTION   "FWP upgrade revision number is changed"
    ::=  { fspR7Trap 134 }


alarmGainTiltNotSettable NOTIFICATION-TYPE
    STATUS      current
    DESCRIPTION   "The nominal tilt and gain values are not settable"
    ::=  { fspR7Trap 135 }


alarmHighBer NOTIFICATION-TYPE
    STATUS      current
    DESCRIPTION   "More than 16 invalid 64B/66B sync headers within the current 125us period"
    ::=  { fspR7Trap 136 }


alarmReceiverOverloadProtection NOTIFICATION-TYPE
    STATUS      current
    DESCRIPTION   "Safety condition, protecting the system against too high receive power."
    ::=  { fspR7Trap 137 }


alarmHwInitializing NOTIFICATION-TYPE
    STATUS      current
    DESCRIPTION   "Hardware is Initializing"
    ::=  { fspR7Trap 138 }


alarmHwOprReachedHT NOTIFICATION-TYPE
    STATUS      current
    DESCRIPTION   "HW OPR has reached a high thershold and could be damaged"
    ::=  { fspR7Trap 139 }


alarmHwDegrade NOTIFICATION-TYPE
    STATUS      current
    DESCRIPTION   "HW operation is degraded by a HW fault, but traffic is unaffected."
    ::=  { fspR7Trap 140 }


alarmHwFailure NOTIFICATION-TYPE
    STATUS      current
    DESCRIPTION   "General Hardware Failure"
    ::=  { fspR7Trap 141 }


alarmSwitchtoProtectionInhibited NOTIFICATION-TYPE
    STATUS      current
    DESCRIPTION   "Protection Switch Inhibited. Switch to PROTN facility Locked Out. Reported by WKG facility. Leads to PSI state."
    ::=  { fspR7Trap 142 }


alarmSwitchtoWorkingInhibited NOTIFICATION-TYPE
    STATUS      current
    DESCRIPTION   "Protection Release Inhibited. Switch back to WKG facility Locked Out. Reported by PROTN facility. Leads to PRI state."
    ::=  { fspR7Trap 143 }


transientIntrusionRx NOTIFICATION-TYPE
    STATUS      current
    DESCRIPTION   "Intrusion on the Receiver Fiber based on GRADHT-AT keyword."
    ::=  { fspR7Trap 144 }


transientIntrusionTx NOTIFICATION-TYPE
    STATUS      current
    DESCRIPTION   "Intrusion on the Receiver Fiber based on GRADHT-AT keyword."
    ::=  { fspR7Trap 145 }


transientEncryptionPortSingleKeyExchgFailed NOTIFICATION-TYPE
    STATUS      current
    DESCRIPTION   "At least one Key exchange failed"
    ::=  { fspR7Trap 146 }


transientCryptoKeyExchgFailCondClr NOTIFICATION-TYPE
    STATUS      current
    DESCRIPTION   "Key exchange fail counter reset"
    ::=  { fspR7Trap 147 }


alarmEncryptionPortKeyInitExchgMissed NOTIFICATION-TYPE
    STATUS      current
    DESCRIPTION   "The initial successful key exchange has not be completed"
    ::=  { fspR7Trap 148 }


alarmEncryptionPortMaxKeyExchgFailuresReachedIs NOTIFICATION-TYPE
    STATUS      current
    DESCRIPTION   "Maximum Key exchange failure count reached"
    ::=  { fspR7Trap 149 }


alarmEncryptionPortMaxKeyExchgFailuresReachedOos NOTIFICATION-TYPE
    STATUS      current
    DESCRIPTION   "Session Key missing"
    ::=  { fspR7Trap 150 }


alarmEncryptionPortKeyExchangedForced NOTIFICATION-TYPE
    STATUS      current
    DESCRIPTION   "Encryption Key exchanged forced"
    ::=  { fspR7Trap 151 }


alarmLaserOnDelay NOTIFICATION-TYPE
    STATUS      current
    DESCRIPTION   "Laser in process of turning on"
    ::=  { fspR7Trap 152 }


alarmLockedDefectOdu NOTIFICATION-TYPE
    STATUS      current
    DESCRIPTION   "ODU Locked"
    ::=  { fspR7Trap 153 }


alarmLockedDefectOduTcmA NOTIFICATION-TYPE
    STATUS      current
    DESCRIPTION   "Locked Defect ODU TCM Instance A"
    ::=  { fspR7Trap 154 }


alarmLockedDefectOduTcmB NOTIFICATION-TYPE
    STATUS      current
    DESCRIPTION   "Locked Defect ODU TCM Instance B"
    ::=  { fspR7Trap 155 }


alarmLockedDefectOduTcmC NOTIFICATION-TYPE
    STATUS      current
    DESCRIPTION   "Locked Defect ODU TCM Instance C"
    ::=  { fspR7Trap 156 }


alarmLinkControlProtocolFailure NOTIFICATION-TYPE
    STATUS      current
    DESCRIPTION   "Link Control Protocol setup error or timeout"
    ::=  { fspR7Trap 157 }


alarmLinkDown NOTIFICATION-TYPE
    STATUS      current
    DESCRIPTION   "Failure of External Linkage"
    ::=  { fspR7Trap 158 }


alarmAutoShutdownSendingAisLine NOTIFICATION-TYPE
    STATUS      current
    DESCRIPTION   "Auto Shutdown (L-AIS)"
    ::=  { fspR7Trap 159 }


alarmAutoShutdownSendingAisOdu NOTIFICATION-TYPE
    STATUS      current
    DESCRIPTION   "Auto Shutdown (ODU-AIS)"
    ::=  { fspR7Trap 160 }


alarmAutoShutdownSendingAisOpu NOTIFICATION-TYPE
    STATUS      current
    DESCRIPTION   "Auto Shutdown (OPU-AIS)"
    ::=  { fspR7Trap 161 }


alarmClientFailForwarding NOTIFICATION-TYPE
    STATUS      current
    DESCRIPTION   "Forwarding of Client Failure"
    ::=  { fspR7Trap 162 }


alarmAutoShutdownAls NOTIFICATION-TYPE
    STATUS      current
    DESCRIPTION   "Auto Shutdown (ALS)"
    ::=  { fspR7Trap 163 }


alarmAutoAmpShutdown NOTIFICATION-TYPE
    STATUS      current
    DESCRIPTION   "Amplifier Auto Shutdown"
    ::=  { fspR7Trap 164 }


alarmAutoShutdownAmpAps NOTIFICATION-TYPE
    STATUS      current
    DESCRIPTION   "Auto Shutdown on Network Tx fiber due to LOS on Network Rx fiber (AMP-APS enabled)"
    ::=  { fspR7Trap 165 }


alarmAseTableBuild NOTIFICATION-TYPE
    STATUS      current
    DESCRIPTION   "Auto shutdown due to missing ASE table"
    ::=  { fspR7Trap 166 }


alarmAutoShutdownOpuClientSignalFail NOTIFICATION-TYPE
    STATUS      current
    DESCRIPTION   "Automatic Shutdown - Client Signal Fail transmit (LKDO-CSF)"
    ::=  { fspR7Trap 167 }


alarmAutoShutdownSendingEPC NOTIFICATION-TYPE
    STATUS      current
    DESCRIPTION   "Auto Shutdown (EPC)"
    ::=  { fspR7Trap 168 }


alarmAutoShutdownSendingLckOdu NOTIFICATION-TYPE
    STATUS      current
    DESCRIPTION   "Auto Shutdown (ODU-LCK)"
    ::=  { fspR7Trap 169 }


alarmAutoShutdownSendingOciOdu NOTIFICATION-TYPE
    STATUS      current
    DESCRIPTION   "Auto Shutdown (ODU-OCI)"
    ::=  { fspR7Trap 170 }


alarmAutoShutdownLaserOffDueToErrFwd NOTIFICATION-TYPE
    STATUS      current
    DESCRIPTION   "Forward ALS"
    ::=  { fspR7Trap 171 }


alarmAutoShutdownTxRxLasersDueToHighTemp NOTIFICATION-TYPE
    STATUS      current
    DESCRIPTION   "Facility autonomously shut down with Transmitter and Receiver off due to temperature."
    ::=  { fspR7Trap 172 }


alarmLocalFault NOTIFICATION-TYPE
    STATUS      current
    DESCRIPTION   "Local Fault Sequence ordered_set received by the local PHY"
    ::=  { fspR7Trap 173 }


alarmLocalOscLevelAbnormal NOTIFICATION-TYPE
    STATUS      current
    DESCRIPTION   "Rx Laser Current Level Abnormal (used for Local Oscillator)"
    ::=  { fspR7Trap 174 }


alarmLossOfGfpFrame NOTIFICATION-TYPE
    STATUS      current
    DESCRIPTION   "GFP LOF"
    ::=  { fspR7Trap 175 }


alarmLossOfFrameMux NOTIFICATION-TYPE
    STATUS      current
    DESCRIPTION   "Multiplexer Loss of Frame"
    ::=  { fspR7Trap 176 }


alarmLossOfFrameOtu NOTIFICATION-TYPE
    STATUS      current
    DESCRIPTION   "OTU LOF"
    ::=  { fspR7Trap 177 }


alarmLossOfFrame NOTIFICATION-TYPE
    STATUS      current
    DESCRIPTION   "Section (SONET) / Regeneration Section (SDH) - Loss of Frame"
    ::=  { fspR7Trap 178 }


alarmLossOfFrameLossOfMultiFrameOdu NOTIFICATION-TYPE
    STATUS      current
    DESCRIPTION   "ODU LOF/LOM"
    ::=  { fspR7Trap 179 }


alarmLossOfLane NOTIFICATION-TYPE
    STATUS      current
    DESCRIPTION   "Loss of Lane Alignment"
    ::=  { fspR7Trap 180 }


alarmLossofMultiframeLowerOrderPath NOTIFICATION-TYPE
    STATUS      current
    DESCRIPTION   "LO-Path Loss Of Multiframe Condition"
    ::=  { fspR7Trap 181 }


alarmLossOfMultiFrameOtu NOTIFICATION-TYPE
    STATUS      current
    DESCRIPTION   "OTU LOM"
    ::=  { fspR7Trap 182 }


alarmLossofMultiframeHigherOrderPath NOTIFICATION-TYPE
    STATUS      current
    DESCRIPTION   "Path LOM"
    ::=  { fspR7Trap 183 }


alarmLossOfPointerLowerOrderPath NOTIFICATION-TYPE
    STATUS      current
    DESCRIPTION   "Is this the same as LOF-LP"
    ::=  { fspR7Trap 184 }


alarmLossOfPointerHigherOrderPath NOTIFICATION-TYPE
    STATUS      current
    DESCRIPTION   "Path LOP"
    ::=  { fspR7Trap 185 }


alarmLosAttProgress NOTIFICATION-TYPE
    STATUS      current
    DESCRIPTION   "Loss of Signal Attenuation finding in process"
    ::=  { fspR7Trap 186 }


alarmLossOsc NOTIFICATION-TYPE
    STATUS      current
    DESCRIPTION   "Loss Of OSC"
    ::=  { fspR7Trap 187 }


alarmGfpLossOfClientSig NOTIFICATION-TYPE
    STATUS      current
    DESCRIPTION   "GFP Loss Of Client Signal"
    ::=  { fspR7Trap 188 }


alarmLoopbackError NOTIFICATION-TYPE
    STATUS      current
    DESCRIPTION   "A loop in the PPP-IP path is detected"
    ::=  { fspR7Trap 189 }


alarmFacilityLoopback NOTIFICATION-TYPE
    STATUS      current
    DESCRIPTION   "External (Line) Loopback on Interface"
    ::=  { fspR7Trap 190 }


alarmLossofTandemConnectionOduTcmA NOTIFICATION-TYPE
    STATUS      current
    DESCRIPTION   "Loss of Tandem Connection ODU Tandem Connection Monitoring Instane A"
    ::=  { fspR7Trap 191 }


alarmLossofTandemConnectionOduTcmB NOTIFICATION-TYPE
    STATUS      current
    DESCRIPTION   "Loss of Tandem Connection ODU Tandem Connection Monitoring Instane B"
    ::=  { fspR7Trap 192 }


alarmLossofTandemConnectionOduTcmC NOTIFICATION-TYPE
    STATUS      current
    DESCRIPTION   "Loss of Tandem Connection ODU Tandem Connection Monitoring Instane C"
    ::=  { fspR7Trap 193 }


alarmMansw NOTIFICATION-TYPE
    STATUS      current
    DESCRIPTION   "This condition will only be shown on the working entity, meaning the MANSW has switched traffic from the working entity to the protection entity."
    ::=  { fspR7Trap 194 }


transientManualWorkingSwitchedBacktoWorking NOTIFICATION-TYPE
    STATUS      current
    DESCRIPTION   "Working Traffic (ACT) switched back to WKG facility from PROTN facility manually: sent by PROTN."
    ::=  { fspR7Trap 195 }


transientManualWorkingSwitchedtoProtection NOTIFICATION-TYPE
    STATUS      current
    DESCRIPTION   "Working Traffic (ACT) switched from Working facility to Protection facility manually: sent by WKG."
    ::=  { fspR7Trap 196 }


alarmEquipmentNotAccepted NOTIFICATION-TYPE
    STATUS      current
    DESCRIPTION   "The Plug cannot support any of the services provisionable on this card OR the Plug is unrecognizable"
    ::=  { fspR7Trap 197 }


alarmEquipmentNotApproved NOTIFICATION-TYPE
    STATUS      current
    DESCRIPTION   "The Plug is recognizable to the extent that service support can
         be determined, but is not approved: this is susperseded by SGEO-RATE"
    ::=  { fspR7Trap 198 }


alarmCapabilityLevelMismatch NOTIFICATION-TYPE
    STATUS      current
    DESCRIPTION   "Capability level mismatch"
    ::=  { fspR7Trap 199 }


alarmEquipmentMismatch NOTIFICATION-TYPE
    STATUS      current
    DESCRIPTION   "The Plug is approved but does not match the specific Plug provisioned: this is superseded by MEA-APPROVE"
    ::=  { fspR7Trap 200 }


alarmEquipmentNotSupportedByPhysicalLayer NOTIFICATION-TYPE
    STATUS      current
    DESCRIPTION   "Equipment not Support Configured Physical Layer"
    ::=  { fspR7Trap 201 }


alarmMeaSwRevision NOTIFICATION-TYPE
    STATUS      current
    DESCRIPTION   "Mismatch of SW Revision"
    ::=  { fspR7Trap 202 }


alarmMismatch NOTIFICATION-TYPE
    STATUS      current
    DESCRIPTION   "Non-Specific Mismatch. Equipment Not Match Provisioned Hardware"
    ::=  { fspR7Trap 203 }


alarmMidstageFault NOTIFICATION-TYPE
    STATUS      current
    DESCRIPTION   "Out of Service due to Midstage Fault."
    ::=  { fspR7Trap 204 }


alarmMultiplexStructureIdentifierMismatchOPU NOTIFICATION-TYPE
    STATUS      current
    DESCRIPTION   "Multiplex Structure Identifier Mismatch OPU"
    ::=  { fspR7Trap 205 }


alarmBackupNotResponding NOTIFICATION-TYPE
    STATUS      current
    DESCRIPTION   "Not Responding"
    ::=  { fspR7Trap 206 }


alarmOpenConnectionIndicationOdu NOTIFICATION-TYPE
    STATUS      current
    DESCRIPTION   "Open Connection Indication ODU"
    ::=  { fspR7Trap 207 }


alarmOpenConnectionIndicationOduTcmA NOTIFICATION-TYPE
    STATUS      current
    DESCRIPTION   "Open Connection Indication ODU Tandem Connection Monitoring A"
    ::=  { fspR7Trap 208 }


alarmOpenConnectionIndicationOduTcmB NOTIFICATION-TYPE
    STATUS      current
    DESCRIPTION   "Open Connection Indication ODU Tandem Connection Monitoring B"
    ::=  { fspR7Trap 209 }


alarmOpenConnectionIndicationOduTcmC NOTIFICATION-TYPE
    STATUS      current
    DESCRIPTION   "Open Connection Indication ODU Tandem Connection Monitoring C"
    ::=  { fspR7Trap 210 }


alarmOduTribMsiMismatch NOTIFICATION-TYPE
    STATUS      current
    DESCRIPTION   "Tributary Port no and ODTU type do not match in provisioned time slots"
    ::=  { fspR7Trap 211 }


alarmTransmitterDisabledOff NOTIFICATION-TYPE
    STATUS      current
    DESCRIPTION   "Disablement of Management Access with Transmitter OFF"
    ::=  { fspR7Trap 212 }


alarmReceiverDisabled NOTIFICATION-TYPE
    STATUS      current
    DESCRIPTION   "Disablement of Management Access with Receiver OFF"
    ::=  { fspR7Trap 213 }


alarmOpmAbnormalCondition NOTIFICATION-TYPE
    STATUS      current
    DESCRIPTION   "OPM condition is abnormal (degraded)"
    ::=  { fspR7Trap 214 }


alarmFaultOnOpm NOTIFICATION-TYPE
    STATUS      current
    DESCRIPTION   "Fault detected on OPM"
    ::=  { fspR7Trap 215 }


alarmThresOptPowerCtrlFailureHigh NOTIFICATION-TYPE
    STATUS      current
    DESCRIPTION   "Optical Power Control Failure High Threshold"
    ::=  { fspR7Trap 216 }


alarmThresOptPowerCtrlFailureLow NOTIFICATION-TYPE
    STATUS      current
    DESCRIPTION   "Optical Power Control Failure Low Threshold"
    ::=  { fspR7Trap 217 }


alarmTxPowerLimited NOTIFICATION-TYPE
    STATUS      current
    DESCRIPTION   "The optical output power reached limit"
    ::=  { fspR7Trap 218 }


alarmOscOpticalPowerControlFailHigh NOTIFICATION-TYPE
    STATUS      current
    DESCRIPTION   "OSC Optical Power Control Failure High Threshold"
    ::=  { fspR7Trap 219 }


alarmOscOpticalPowerControlFailLow NOTIFICATION-TYPE
    STATUS      current
    DESCRIPTION   "OSC Optical Power Control Failure Low Threshold"
    ::=  { fspR7Trap 220 }


alarmOTDRMeasuringinProgress NOTIFICATION-TYPE
    STATUS      current
    DESCRIPTION   ""
    ::=  { fspR7Trap 221 }


alarmEncryptionModuleCryPasswdError NOTIFICATION-TYPE
    STATUS      current
    DESCRIPTION   "3 invalid CRYPW entered; The Module refuses input of CRYPW for xxx sec."
    ::=  { fspR7Trap 222 }


alarmPeerLink NOTIFICATION-TYPE
    STATUS      current
    DESCRIPTION   "Failure of Internal Link or Link Protocol (could be protocol incompatibility) between Cards in Protection or Regeneration Pair"
    ::=  { fspR7Trap 223 }


alarmPilotReceiveLevelHigh NOTIFICATION-TYPE
    STATUS      current
    DESCRIPTION   "Pilot receive level is high"
    ::=  { fspR7Trap 224 }


alarmLossOfPilotSignal NOTIFICATION-TYPE
    STATUS      current
    DESCRIPTION   "Loss of Pilot Signal"
    ::=  { fspR7Trap 225 }


alarmPayloadMismatchGfp NOTIFICATION-TYPE
    STATUS      current
    DESCRIPTION   "GFP Payload Mismatch"
    ::=  { fspR7Trap 226 }


alarmPayloadMismatchLowerOrderPath NOTIFICATION-TYPE
    STATUS      current
    DESCRIPTION   "LO-Path Payload Mismatch"
    ::=  { fspR7Trap 227 }


alarmPayloadMismatchOPU NOTIFICATION-TYPE
    STATUS      current
    DESCRIPTION   "OPU Payload Mismatch"
    ::=  { fspR7Trap 228 }


alarmPayloadMismatchHigherOrderPath NOTIFICATION-TYPE
    STATUS      current
    DESCRIPTION   "SONET/SDH Path Payload Mismatch"
    ::=  { fspR7Trap 229 }


alarmProvPayloadMismatch NOTIFICATION-TYPE
    STATUS      current
    DESCRIPTION   "Provisioning payload mismatch alarm"
    ::=  { fspR7Trap 230 }


alarmPrbsLossOfSeqSynch NOTIFICATION-TYPE
    STATUS      current
    DESCRIPTION   "PRBS Loss of Sequence Synchronization"
    ::=  { fspR7Trap 231 }


alarmPrbsRcvActivated NOTIFICATION-TYPE
    STATUS      current
    DESCRIPTION   "PRBS Receive Activated"
    ::=  { fspR7Trap 232 }


alarmPrbsTrmtActivated NOTIFICATION-TYPE
    STATUS      current
    DESCRIPTION   "PRBS Transmit Activated"
    ::=  { fspR7Trap 233 }


alarmProtectionNotAvailable NOTIFICATION-TYPE
    STATUS      current
    DESCRIPTION   "(Protection Not Available)
         In the case of Channel Card Protection: due to unequipped or mismatched partner equipment - sent by active facility.
         In the case of HST Channel Protection: due to unequipped or mismatched partner plug - sent by active facility;
         on an OLM, the pilot laser has been switched off for a defined perion to allow an Optical Time Domain Reflectormeter to be deployed.
         In the case of Controller Protection: due to partner OOS-AU or OOS-MA, DSBLD (Protection Not Available)."
    ::=  { fspR7Trap 234 }


alarmPowerSupplyUnitFailure NOTIFICATION-TYPE
    STATUS      current
    DESCRIPTION   ""
    ::=  { fspR7Trap 235 }


alarmMaxPowerConsProvModulesToHigh NOTIFICATION-TYPE
    STATUS      current
    DESCRIPTION   "The maximum power consumption of all provisioned equipment exceeds the capability of a single PSU in the shelf."
    ::=  { fspR7Trap 236 }


alarmMaxPowerConsEquipModulesToHigh NOTIFICATION-TYPE
    STATUS      current
    DESCRIPTION   "The maximum power consumption of the installed equipment exceeds the capability of a single PSU in the shelf."
    ::=  { fspR7Trap 237 }


alarmPowerMissing NOTIFICATION-TYPE
    STATUS      current
    DESCRIPTION   "Power Unit Missing"
    ::=  { fspR7Trap 238 }


alarmRemoteDefectIndicationLine NOTIFICATION-TYPE
    STATUS      current
    DESCRIPTION   "Line / Multiplex Section RDI"
    ::=  { fspR7Trap 239 }


alarmRemoteDefectIndicationLowerOrderPath NOTIFICATION-TYPE
    STATUS      current
    DESCRIPTION   "LO-Path Remote Defect Indication"
    ::=  { fspR7Trap 240 }


alarmRemoteDefectIndicationHigherOrderPath NOTIFICATION-TYPE
    STATUS      current
    DESCRIPTION   "Path RDI"
    ::=  { fspR7Trap 241 }


transientPmSnapshotEnded NOTIFICATION-TYPE
    STATUS      current
    DESCRIPTION   "Reference value save end"
    ::=  { fspR7Trap 242 }


alarmDcnCommunicationFail NOTIFICATION-TYPE
    STATUS      current
    DESCRIPTION   "The connection to the shelf is dysfunctional or the connection to the module within the shelf is dysfunctional"
    ::=  { fspR7Trap 243 }


alarmNtpForSchedEqlzRequired NOTIFICATION-TYPE
    STATUS      current
    DESCRIPTION   "Scheduled Equalization requires NTP to be enabled"
    ::=  { fspR7Trap 244 }


alarmSignalDegradeOlm NOTIFICATION-TYPE
    STATUS      current
    DESCRIPTION   "Signal Degrade"
    ::=  { fspR7Trap 245 }


alarmSignalDegradeLine NOTIFICATION-TYPE
    STATUS      current
    DESCRIPTION   "Line/Mux Section SD alarm; related to a configurable threshold"
    ::=  { fspR7Trap 246 }


alarmSignalDegradationonLinkVector NOTIFICATION-TYPE
    STATUS      current
    DESCRIPTION   "Signal Degradation on Link Vector. Superseeded by SF-LINK."
    ::=  { fspR7Trap 247 }


alarmSignalDegradeOdu NOTIFICATION-TYPE
    STATUS      current
    DESCRIPTION   "ODU Signal Degrade alarm; Related to a configurable threshold"
    ::=  { fspR7Trap 248 }


alarmSignalDegradeOtu NOTIFICATION-TYPE
    STATUS      current
    DESCRIPTION   "OTU Signal Degrade alarm; related to a configurable threshold"
    ::=  { fspR7Trap 249 }


alarmPcsSignalDegrade NOTIFICATION-TYPE
    STATUS      current
    DESCRIPTION   "Pysical Coding Sublayer Signal Degrade alarm; related to a configurable threshold"
    ::=  { fspR7Trap 250 }


alarmSignalDegradeScn NOTIFICATION-TYPE
    STATUS      current
    DESCRIPTION   "Sec/RS signal degrade alarm; related to a configurable threshold"
    ::=  { fspR7Trap 251 }


alarmSignalDegradeOduTcmA NOTIFICATION-TYPE
    STATUS      current
    DESCRIPTION   "Signal Degrade ODU Tandem Connection Monitoring Instance A. Related to a configurable threshold"
    ::=  { fspR7Trap 252 }


alarmSignalDegradeOduTcmB NOTIFICATION-TYPE
    STATUS      current
    DESCRIPTION   "Signal Degrade ODU Tandem Connection Monitoring Instance B. Related to a configurable threshold"
    ::=  { fspR7Trap 253 }


alarmSignalDegradeOduTcmC NOTIFICATION-TYPE
    STATUS      current
    DESCRIPTION   "Signal Degrade ODU Tandem Connection Monitoring Instance C. Related to a configurable threshold"
    ::=  { fspR7Trap 254 }


alarmEncryptionModuleSelfTestFail NOTIFICATION-TYPE
    STATUS      current
    DESCRIPTION   "Noncritical selftest failed"
    ::=  { fspR7Trap 255 }


alarmEncryptionModuleSelfTestFailCritical NOTIFICATION-TYPE
    STATUS      current
    DESCRIPTION   "Critical selftest failed"
    ::=  { fspR7Trap 256 }


alarmSignalFailureOnLink NOTIFICATION-TYPE
    STATUS      current
    DESCRIPTION   "Signal Failure on Link"
    ::=  { fspR7Trap 257 }


alarmSignalFailureonLinkVector NOTIFICATION-TYPE
    STATUS      current
    DESCRIPTION   "Signal Fail Link Vector"
    ::=  { fspR7Trap 258 }


alarmSignalFailureOPU NOTIFICATION-TYPE
    STATUS      current
    DESCRIPTION   "This is a very severe signal degradation or loss"
    ::=  { fspR7Trap 259 }


alarmServerSignalFailTx NOTIFICATION-TYPE
    STATUS      current
    DESCRIPTION   "Aggregate level failure"
    ::=  { fspR7Trap 260 }


alarmFacilityDataRateNotSupported NOTIFICATION-TYPE
    STATUS      current
    DESCRIPTION   "The Plug inserted cannot support the actual service provisioned on this card: this is superseded by the above"
    ::=  { fspR7Trap 261 }


transientCryptoSessKeyLifetimeChanged NOTIFICATION-TYPE
    STATUS      current
    DESCRIPTION   "Change of session key lifetime"
    ::=  { fspR7Trap 262 }


alarmLossofSequenceLowerOrderPath NOTIFICATION-TYPE
    STATUS      current
    DESCRIPTION   "LO-Path Loss Of Sequence"
    ::=  { fspR7Trap 263 }


alarmLossofSequenceHigherOrderPath NOTIFICATION-TYPE
    STATUS      current
    DESCRIPTION   "Path Loss Of Sequence"
    ::=  { fspR7Trap 264 }


alarmServerSignalFail NOTIFICATION-TYPE
    STATUS      current
    DESCRIPTION   "All member ports signals have failed"
    ::=  { fspR7Trap 265 }


alarmServerSignalFailureGfp NOTIFICATION-TYPE
    STATUS      current
    DESCRIPTION   "GFP Server Signal Failure"
    ::=  { fspR7Trap 266 }


alarmServerSignalFailureODU NOTIFICATION-TYPE
    STATUS      current
    DESCRIPTION   "ODU Server Signal Failure"
    ::=  { fspR7Trap 267 }


alarmServerSignalFailurePath NOTIFICATION-TYPE
    STATUS      current
    DESCRIPTION   "SONET/SDH Path Server Signal Failure"
    ::=  { fspR7Trap 268 }


alarmServerSignalFailureSectionRS NOTIFICATION-TYPE
    STATUS      current
    DESCRIPTION   "Section (SONET) / Regeneration Section (SDH) - Server Signal Failure"
    ::=  { fspR7Trap 269 }


transientProtSwToDuplexCompl NOTIFICATION-TYPE
    STATUS      current
    DESCRIPTION   "Switch to Partner Controller complete"
    ::=  { fspR7Trap 270 }


transientProtSwToDuplexFail NOTIFICATION-TYPE
    STATUS      current
    DESCRIPTION   "Switch to Partner Controller failed"
    ::=  { fspR7Trap 271 }


alarmSwitchToDuplexInhibited NOTIFICATION-TYPE
    STATUS      current
    DESCRIPTION   "Switch-Over to Partner Controller inhibited"
    ::=  { fspR7Trap 272 }


transientProtSwToDuplexStart NOTIFICATION-TYPE
    STATUS      current
    DESCRIPTION   "Switch to Partner Controller started"
    ::=  { fspR7Trap 273 }


alarmSwitchFailed NOTIFICATION-TYPE
    STATUS      current
    DESCRIPTION   "Failure to Respond to Switch/Bridge Request within 50 ms"
    ::=  { fspR7Trap 274 }


transientSwResetReload NOTIFICATION-TYPE
    STATUS      current
    DESCRIPTION   "System Restart-RELOAD"
    ::=  { fspR7Trap 275 }


alarmCurrentTooHigh NOTIFICATION-TYPE
    STATUS      current
    DESCRIPTION   "Current Too High"
    ::=  { fspR7Trap 276 }


alarmAttOnReceiverFiberHigherThanMonitor NOTIFICATION-TYPE
    STATUS      current
    DESCRIPTION   "Attenuation Rx Too High"
    ::=  { fspR7Trap 277 }


alarmAttOnReceiverFiberLowerThanMonitor NOTIFICATION-TYPE
    STATUS      current
    DESCRIPTION   "Attenuation Rx Too Low"
    ::=  { fspR7Trap 278 }


alarmAttOnTransmitterFiberHigherThanMonitor NOTIFICATION-TYPE
    STATUS      current
    DESCRIPTION   "Attenuation Tx Too High"
    ::=  { fspR7Trap 279 }


alarmAttOnTransmitterFiberLowerThanMonitor NOTIFICATION-TYPE
    STATUS      current
    DESCRIPTION   "Attenuation Tx Too Low"
    ::=  { fspR7Trap 280 }


alarmThres15MinExceededOduBbe NOTIFICATION-TYPE
    STATUS      current
    DESCRIPTION   "Background Block Errors ODU Section Monitoring"
    ::=  { fspR7Trap 281 }


transientThres1DayExceededOduBbe NOTIFICATION-TYPE
    STATUS      current
    DESCRIPTION   "Background Block Errors ODU Section Monitoring"
    ::=  { fspR7Trap 282 }


alarmThres15MinExceededOtuBbe NOTIFICATION-TYPE
    STATUS      current
    DESCRIPTION   "Background Block Errors OTU Section Monitoring"
    ::=  { fspR7Trap 283 }


transientThres1DayExceededOtuBbe NOTIFICATION-TYPE
    STATUS      current
    DESCRIPTION   "Background Block Errors OTU Section Monitoring"
    ::=  { fspR7Trap 284 }


alarmThres15MinExceededOduTcmABbe NOTIFICATION-TYPE
    STATUS      current
    DESCRIPTION   "Background Block Errors ODU Tandem Connection Monitoring"
    ::=  { fspR7Trap 285 }


transientThres1DayExceededOduTcmABbe NOTIFICATION-TYPE
    STATUS      current
    DESCRIPTION   "Background Block Errors ODU Tandem Connection Monitoring"
    ::=  { fspR7Trap 286 }


alarmThres15MinExceededOduTcmBBbe NOTIFICATION-TYPE
    STATUS      current
    DESCRIPTION   "Background Block Errors ODU Tandem Connection Monitoring"
    ::=  { fspR7Trap 287 }


transientThres1DayExceededOduTcmBBbe NOTIFICATION-TYPE
    STATUS      current
    DESCRIPTION   "Background Block Errors ODU Tandem Connection Monitoring"
    ::=  { fspR7Trap 288 }


alarmThres15MinExceededOduTcmCBbe NOTIFICATION-TYPE
    STATUS      current
    DESCRIPTION   "Background Block Errors ODU Tandem Connection Monitoring"
    ::=  { fspR7Trap 289 }


transientThres1DayExceededOduTcmCBbe NOTIFICATION-TYPE
    STATUS      current
    DESCRIPTION   "Background Block Errors ODU Tandem Connection Monitoring"
    ::=  { fspR7Trap 290 }


alarmThres15MinExceededFecBERCE NOTIFICATION-TYPE
    STATUS      current
    DESCRIPTION   "Bit error rate before FEC 15 minutes high threshold crossed"
    ::=  { fspR7Trap 291 }


transientThres1DayExceededFecBERCE NOTIFICATION-TYPE
    STATUS      current
    DESCRIPTION   "Bit error rate before FEC 1day high threshold crossed"
    ::=  { fspR7Trap 292 }


alarmBrPwrRxTooHigh NOTIFICATION-TYPE
    STATUS      current
    DESCRIPTION   "Backreflection Rx too High"
    ::=  { fspR7Trap 293 }


alarmChromaticDispersionTooHigh NOTIFICATION-TYPE
    STATUS      current
    DESCRIPTION   "Chromatic Dispersion too High"
    ::=  { fspR7Trap 294 }


alarmChromaticDispersionTooLow NOTIFICATION-TYPE
    STATUS      current
    DESCRIPTION   "Chromatic Dispersion too Low"
    ::=  { fspR7Trap 295 }


alarmDispersionCompensationTooHigh NOTIFICATION-TYPE
    STATUS      current
    DESCRIPTION   "Chromatic Dispersion Compensation too High"
    ::=  { fspR7Trap 296 }


alarmDispersionCompensationTooLow NOTIFICATION-TYPE
    STATUS      current
    DESCRIPTION   "Chromatic Dispersion Compensation too Low"
    ::=  { fspR7Trap 297 }


alarmThres15MinExceededFecCE NOTIFICATION-TYPE
    STATUS      current
    DESCRIPTION   "FEC Corrected Errors Exceeded 15 Minute Threshold"
    ::=  { fspR7Trap 298 }


transientThres1DayExceededFecCE NOTIFICATION-TYPE
    STATUS      current
    DESCRIPTION   "FEC Corrected Errors Exceeded Day Threshold"
    ::=  { fspR7Trap 299 }


alarmCarrierFreqOffsetTooHigh NOTIFICATION-TYPE
    STATUS      current
    DESCRIPTION   "Carrier Frequency Offset too High"
    ::=  { fspR7Trap 300 }


alarmCarrierFreqOffsetTooLow NOTIFICATION-TYPE
    STATUS      current
    DESCRIPTION   "Carrier Frequency Offset too Low"
    ::=  { fspR7Trap 301 }


alarmThres15MinExceededSonetLineCV NOTIFICATION-TYPE
    STATUS      current
    DESCRIPTION   "Coding Violations Line"
    ::=  { fspR7Trap 302 }


transientThres1DayExceededSonetLineCV NOTIFICATION-TYPE
    STATUS      current
    DESCRIPTION   "Coding Violations Line"
    ::=  { fspR7Trap 303 }


alarmThres15MinExceededPhysConvCV NOTIFICATION-TYPE
    STATUS      current
    DESCRIPTION   "Coding Violations Physical Coding Layer"
    ::=  { fspR7Trap 304 }


transientThres1DayExceededPhysConvCV NOTIFICATION-TYPE
    STATUS      current
    DESCRIPTION   "Coding Violations Physical Coding Layer"
    ::=  { fspR7Trap 305 }


alarmThres15MinExceededSonetSectCV NOTIFICATION-TYPE
    STATUS      current
    DESCRIPTION   "Coding Violations Section"
    ::=  { fspR7Trap 306 }


transientThres1DayExceededSonetSectCV NOTIFICATION-TYPE
    STATUS      current
    DESCRIPTION   "Coding Violations Section"
    ::=  { fspR7Trap 307 }


alarmThres15MinExceededPhysConvDE NOTIFICATION-TYPE
    STATUS      current
    DESCRIPTION   "Disparity Errors Physical Coding Layer"
    ::=  { fspR7Trap 308 }


transientThres1DayExceededPhysConvDE NOTIFICATION-TYPE
    STATUS      current
    DESCRIPTION   "Disparity Errors Physical Coding Layer"
    ::=  { fspR7Trap 309 }


alarmDifferentialGroupDelayTooHigh NOTIFICATION-TYPE
    STATUS      current
    DESCRIPTION   "Differential Group Delay too High"
    ::=  { fspR7Trap 310 }


alarmThres15MinExceededFecES NOTIFICATION-TYPE
    STATUS      current
    DESCRIPTION   "Errored Seconds FEC OTU Monitoring"
    ::=  { fspR7Trap 311 }


transientThres1DayExceededFecES NOTIFICATION-TYPE
    STATUS      current
    DESCRIPTION   "Errored Seconds FEC OTU Monitoring"
    ::=  { fspR7Trap 312 }


alarmThres15MinExceededSonetLineES NOTIFICATION-TYPE
    STATUS      current
    DESCRIPTION   "Errored Seconds Line"
    ::=  { fspR7Trap 313 }


transientThres1DayExceededSonetLineES NOTIFICATION-TYPE
    STATUS      current
    DESCRIPTION   "Errored Seconds Line"
    ::=  { fspR7Trap 314 }


alarmThres15MinExceededOduES NOTIFICATION-TYPE
    STATUS      current
    DESCRIPTION   "Errored Seconds ODU Path Monitoring"
    ::=  { fspR7Trap 315 }


transientThres1DayExceededOduES NOTIFICATION-TYPE
    STATUS      current
    DESCRIPTION   "Errored Seconds ODU Path Monitoring"
    ::=  { fspR7Trap 316 }


alarmThres15MinExceededOtuES NOTIFICATION-TYPE
    STATUS      current
    DESCRIPTION   "Errored Seconds OTU Section Monitoring"
    ::=  { fspR7Trap 317 }


transientThres1DayExceededOtuES NOTIFICATION-TYPE
    STATUS      current
    DESCRIPTION   "Errored Seconds OTU Section Monitoring"
    ::=  { fspR7Trap 318 }


alarmThres15MinExceededPhysConvES NOTIFICATION-TYPE
    STATUS      current
    DESCRIPTION   "Errored Seconds Physical Coding Layer"
    ::=  { fspR7Trap 319 }


transientThres1DayExceededPhysConvES NOTIFICATION-TYPE
    STATUS      current
    DESCRIPTION   "Errored Seconds Physical Coding Layer"
    ::=  { fspR7Trap 320 }


alarmThres15MinExceededSonetSectES NOTIFICATION-TYPE
    STATUS      current
    DESCRIPTION   "Errored Seconds Section"
    ::=  { fspR7Trap 321 }


transientThres1DayExceededSonetSectES NOTIFICATION-TYPE
    STATUS      current
    DESCRIPTION   "Errored Seconds Section"
    ::=  { fspR7Trap 322 }


alarmThres15MinExceededOduTcmAES NOTIFICATION-TYPE
    STATUS      current
    DESCRIPTION   "Errored Seconds ODU Tandem Connection Monitoring"
    ::=  { fspR7Trap 323 }


transientThres1DayExceededOduTcmAES NOTIFICATION-TYPE
    STATUS      current
    DESCRIPTION   "Errored Seconds ODU Tandem Connection Monitoring"
    ::=  { fspR7Trap 324 }


alarmThres15MinExceededOduTcmBES NOTIFICATION-TYPE
    STATUS      current
    DESCRIPTION   "Errored Seconds ODU Tandem Connection Monitoring"
    ::=  { fspR7Trap 325 }


transientThres1DayExceededOduTcmBES NOTIFICATION-TYPE
    STATUS      current
    DESCRIPTION   "Errored Seconds ODU Tandem Connection Monitoring"
    ::=  { fspR7Trap 326 }


alarmThres15MinExceededOduTcmCES NOTIFICATION-TYPE
    STATUS      current
    DESCRIPTION   "Errored Seconds ODU Tandem Connection Monitoring"
    ::=  { fspR7Trap 327 }


transientThres1DayExceededOduTcmCES NOTIFICATION-TYPE
    STATUS      current
    DESCRIPTION   "Errored Seconds ODU Tandem Connection Monitoring"
    ::=  { fspR7Trap 328 }


alarmLatencyTooHigh NOTIFICATION-TYPE
    STATUS      current
    DESCRIPTION   "TCA -Round Trip Delay Too High"
    ::=  { fspR7Trap 329 }


alarmLatencyTooLow NOTIFICATION-TYPE
    STATUS      current
    DESCRIPTION   "TCA -Round trip delay Too Low"
    ::=  { fspR7Trap 330 }


alarmLaserBiasCurrentNormalizedtooHigh NOTIFICATION-TYPE
    STATUS      current
    DESCRIPTION   "TCA - Laser Bias Current Level too High. Fixed threshold has been crossed."
    ::=  { fspR7Trap 331 }


alarmLocalOscTemperatureTooHigh NOTIFICATION-TYPE
    STATUS      current
    DESCRIPTION   "Rx Laser used for Local Oscillator Temperature High"
    ::=  { fspR7Trap 332 }


alarmLocalOscTemperatureTooLow NOTIFICATION-TYPE
    STATUS      current
    DESCRIPTION   "Rx Laser used for Local Oscillator Temperature Low"
    ::=  { fspR7Trap 333 }


alarmPumpLaser1TempTooHigh NOTIFICATION-TYPE
    STATUS      current
    DESCRIPTION   "TCA - Fixed high threshold of Laser 1 Temperature has been crossed."
    ::=  { fspR7Trap 334 }


alarmPumpLaser1TempTooLow NOTIFICATION-TYPE
    STATUS      current
    DESCRIPTION   "TCA - Fixed low threshold of Laser 1 Temperature has been crossed."
    ::=  { fspR7Trap 335 }


alarmPumpLaser2TempTooHigh NOTIFICATION-TYPE
    STATUS      current
    DESCRIPTION   "TCA - Fixed high threshold of Laser 2 Temperature has been crossed."
    ::=  { fspR7Trap 336 }


alarmPumpLaser2TempTooLow NOTIFICATION-TYPE
    STATUS      current
    DESCRIPTION   "TCA - Fixed low threshold of Laser 2 Temperature has been crossed."
    ::=  { fspR7Trap 337 }


alarmPumpLaser3TempTooHigh NOTIFICATION-TYPE
    STATUS      current
    DESCRIPTION   "TCA - Fixed high threshold of Laser 3 Temperature has been crossed."
    ::=  { fspR7Trap 338 }


alarmPumpLaser3TempTooLow NOTIFICATION-TYPE
    STATUS      current
    DESCRIPTION   "TCA - Fixed low threshold of Laser 3 Temperature has been crossed."
    ::=  { fspR7Trap 339 }


alarmPumpLaser4TempTooHigh NOTIFICATION-TYPE
    STATUS      current
    DESCRIPTION   "TCA - Fixed high threshold of Laser 4 Temperature has been crossed."
    ::=  { fspR7Trap 340 }


alarmPumpLaser4TempTooLow NOTIFICATION-TYPE
    STATUS      current
    DESCRIPTION   "TCA - Fixed low threshold of Laser 4 Temperature has been crossed."
    ::=  { fspR7Trap 341 }


alarmOscPwrTooHigh NOTIFICATION-TYPE
    STATUS      current
    DESCRIPTION   "Optical Supervisory Channel Input Power current high threshold crossed"
    ::=  { fspR7Trap 342 }


alarmOscPwrTooLow NOTIFICATION-TYPE
    STATUS      current
    DESCRIPTION   "Optical Supervisory Channel Input Power current low threshold crossed"
    ::=  { fspR7Trap 343 }


alarmRamanPumpPwrTooHigh NOTIFICATION-TYPE
    STATUS      current
    DESCRIPTION   "TCA - Fixed high threshold of Pump Laser has been crossed."
    ::=  { fspR7Trap 344 }


alarmRamanPumpPwrTooLow NOTIFICATION-TYPE
    STATUS      current
    DESCRIPTION   "TCA - Fixed low threshold of Pump Power has been crossed."
    ::=  { fspR7Trap 345 }


alarmRoundTripDelayTooHigh NOTIFICATION-TYPE
    STATUS      current
    DESCRIPTION   "TCA - Round trip delay too high"
    ::=  { fspR7Trap 346 }


alarmRoundTripDelayTooLow NOTIFICATION-TYPE
    STATUS      current
    DESCRIPTION   "TCA -Round trip delay Too Low"
    ::=  { fspR7Trap 347 }


alarmThres15MinExceededSonetSectSEFS NOTIFICATION-TYPE
    STATUS      current
    DESCRIPTION   "Severely Errored Framing Seconds Section"
    ::=  { fspR7Trap 348 }


transientThres1DayExceededSonetSectSEFS NOTIFICATION-TYPE
    STATUS      current
    DESCRIPTION   "Severely Errored Framing Seconds Section"
    ::=  { fspR7Trap 349 }


alarmThres15MinExceededFecSES NOTIFICATION-TYPE
    STATUS      current
    DESCRIPTION   "FEC-SES 15Min Exceeded"
    ::=  { fspR7Trap 350 }


transientThres1DayExceededFecSES NOTIFICATION-TYPE
    STATUS      current
    DESCRIPTION   "FEC-SES 1Day Exceeded"
    ::=  { fspR7Trap 351 }


alarmThres15MinExceededSonetLineSES NOTIFICATION-TYPE
    STATUS      current
    DESCRIPTION   "Severely Errored Seconds Line"
    ::=  { fspR7Trap 352 }


transientThres1DayExceededSonetLineSES NOTIFICATION-TYPE
    STATUS      current
    DESCRIPTION   "Severely Errored Seconds Line"
    ::=  { fspR7Trap 353 }


alarmThres15MinExceededOduSES NOTIFICATION-TYPE
    STATUS      current
    DESCRIPTION   "Severely Errored Seconds ODU Path Monitoring"
    ::=  { fspR7Trap 354 }


transientThres1DayExceededOduSES NOTIFICATION-TYPE
    STATUS      current
    DESCRIPTION   "Severely Errored Seconds ODU Path Monitoring"
    ::=  { fspR7Trap 355 }


alarmThres15MinExceededOtuSES NOTIFICATION-TYPE
    STATUS      current
    DESCRIPTION   "Severely Errored Seconds OTU Section Monitoring"
    ::=  { fspR7Trap 356 }


transientThres1DayExceededOtuSES NOTIFICATION-TYPE
    STATUS      current
    DESCRIPTION   "Severely Errored Seconds OTU Section Monitoring"
    ::=  { fspR7Trap 357 }


alarmThres15MinExceededSonetSectSES NOTIFICATION-TYPE
    STATUS      current
    DESCRIPTION   "Severely Errored Seconds Section"
    ::=  { fspR7Trap 358 }


transientThres1DayExceededSonetSectSES NOTIFICATION-TYPE
    STATUS      current
    DESCRIPTION   "Severely Errored Seconds Section"
    ::=  { fspR7Trap 359 }


alarmThres15MinExceededOduTcmASES NOTIFICATION-TYPE
    STATUS      current
    DESCRIPTION   "Severely Errored Seconds ODU Tandem Connection Monitoring"
    ::=  { fspR7Trap 360 }


transientThres1DayExceededOduTcmASES NOTIFICATION-TYPE
    STATUS      current
    DESCRIPTION   "Severely Errored Seconds ODU Tandem Connection Monitoring"
    ::=  { fspR7Trap 361 }


alarmThres15MinExceededOduTcmBSES NOTIFICATION-TYPE
    STATUS      current
    DESCRIPTION   "Severely Errored Seconds ODU Tandem Connection Monitoring"
    ::=  { fspR7Trap 362 }


transientThres1DayExceededOduTcmBSES NOTIFICATION-TYPE
    STATUS      current
    DESCRIPTION   "Severely Errored Seconds ODU Tandem Connection Monitoring"
    ::=  { fspR7Trap 363 }


alarmThres15MinExceededOduTcmCSES NOTIFICATION-TYPE
    STATUS      current
    DESCRIPTION   "Severely Errored Seconds ODU Tandem Connection Monitoring"
    ::=  { fspR7Trap 364 }


transientThres1DayExceededOduTcmCSES NOTIFICATION-TYPE
    STATUS      current
    DESCRIPTION   "Severely Errored Seconds ODU Tandem Connection Monitoring"
    ::=  { fspR7Trap 365 }


alarmLogicalLanesSkewTooHigh NOTIFICATION-TYPE
    STATUS      current
    DESCRIPTION   "Skew between logical lanes farthest apart high threshold condition"
    ::=  { fspR7Trap 366 }


alarmSignalToNoiseRatioTooLow NOTIFICATION-TYPE
    STATUS      current
    DESCRIPTION   "Signal-to-Noise Ratio too Low"
    ::=  { fspR7Trap 367 }


alarmSubModuleTempTooHigh NOTIFICATION-TYPE
    STATUS      current
    DESCRIPTION   "Relevant only when ERRFWD=LSROFF. Enables/disables theSubmodule Tempe
         possibility to delay turning off the laser.Relevant only when ERRFWD=LSROFF. Enables/disables theSubmodule Temperature too High
         possibility to delay turning off the laser.
         This applies to the case when turning off the laserrature too High
         is done as an error forwarding mechanism.
         This applies to the case when turning off the laser
         is done as an error forwarding mechanism."
    ::=  { fspR7Trap 368 }


alarmTemperatureTooHigh NOTIFICATION-TYPE
    STATUS      current
    DESCRIPTION   "Temperature Too High"
    ::=  { fspR7Trap 369 }


alarmTemperatureTooLow NOTIFICATION-TYPE
    STATUS      current
    DESCRIPTION   "Temperature Too Low"
    ::=  { fspR7Trap 370 }


alarmThres15MinExceededSonetLineUAS NOTIFICATION-TYPE
    STATUS      current
    DESCRIPTION   "Unavailable Seconds Line"
    ::=  { fspR7Trap 371 }


transientThres1DayExceededSonetLineUAS NOTIFICATION-TYPE
    STATUS      current
    DESCRIPTION   "Unavailable Seconds Line"
    ::=  { fspR7Trap 372 }


alarmThres15MinExceededOduUAS NOTIFICATION-TYPE
    STATUS      current
    DESCRIPTION   "Unavailable Seconds ODU Path Monitoring"
    ::=  { fspR7Trap 373 }


transientThres1DayExceededOduUAS NOTIFICATION-TYPE
    STATUS      current
    DESCRIPTION   "Unavailable Seconds ODU Path Monitoring"
    ::=  { fspR7Trap 374 }


alarmThres15MinExceededOtuUAS NOTIFICATION-TYPE
    STATUS      current
    DESCRIPTION   "Unavailable Seconds OTU Section Monitoring"
    ::=  { fspR7Trap 375 }


transientThres1DayExceededOtuUAS NOTIFICATION-TYPE
    STATUS      current
    DESCRIPTION   "Unavailable Seconds OTU Section Monitoring"
    ::=  { fspR7Trap 376 }


alarmThres15MinExceededOduTcmAUAS NOTIFICATION-TYPE
    STATUS      current
    DESCRIPTION   "Unavailable Seconds ODU Tandem Connection Monitoring"
    ::=  { fspR7Trap 377 }


transientThres1DayExceededOduTcmAUAS NOTIFICATION-TYPE
    STATUS      current
    DESCRIPTION   "Unavailable Seconds ODU Tandem Connection Monitoring"
    ::=  { fspR7Trap 378 }


alarmThres15MinExceededOduTcmBUAS NOTIFICATION-TYPE
    STATUS      current
    DESCRIPTION   "Unavailable Seconds ODU Tandem Connection Monitoring"
    ::=  { fspR7Trap 379 }


transientThres1DayExceededOduTcmBUAS NOTIFICATION-TYPE
    STATUS      current
    DESCRIPTION   "Unavailable Seconds ODU Tandem Connection Monitoring"
    ::=  { fspR7Trap 380 }


alarmThres15MinExceededOduTcmCUAS NOTIFICATION-TYPE
    STATUS      current
    DESCRIPTION   "Unavailable Seconds ODU Tandem Connection Monitoring"
    ::=  { fspR7Trap 381 }


transientThres1DayExceededOduTcmCUAS NOTIFICATION-TYPE
    STATUS      current
    DESCRIPTION   "Unavailable Seconds ODU Tandem Connection Monitoring"
    ::=  { fspR7Trap 382 }


alarmThres15MinExceededFecUBE NOTIFICATION-TYPE
    STATUS      current
    DESCRIPTION   "FEC Uncorrected Block Error 15 Minute Threshold Exceeded"
    ::=  { fspR7Trap 383 }


transientThres1DayExceededFecUBE NOTIFICATION-TYPE
    STATUS      current
    DESCRIPTION   "FEC Uncorrected Block Error Day Threshold Exceeded"
    ::=  { fspR7Trap 384 }


alarmEncryptionModuleTamperDetected NOTIFICATION-TYPE
    STATUS      current
    DESCRIPTION   "Tamper event on Encryption module"
    ::=  { fspR7Trap 385 }


alarmThermoElectricCoolerEndOfLife NOTIFICATION-TYPE
    STATUS      current
    DESCRIPTION   "TEC End of Life"
    ::=  { fspR7Trap 386 }

alarmInputTIF NOTIFICATION-TYPE
    STATUS      current
    DESCRIPTION   "Telemetry interface alarm."
    ::=  { fspR7Trap 387 }

transientHardwareResetInputTIF NOTIFICATION-TYPE
    STATUS      current
    DESCRIPTION   "Telemetry interface alarm reset by hardware switch"
    ::=  { fspR7Trap 388 }


alarmTraceIdentifierMismatchOdu NOTIFICATION-TYPE
    STATUS      current
    DESCRIPTION   "ODU-Trace Identifier Mismatch"
    ::=  { fspR7Trap 389 }


alarmTraceIdentifierMismatchOtu NOTIFICATION-TYPE
    STATUS      current
    DESCRIPTION   "OTU-TIM"
    ::=  { fspR7Trap 390 }


alarmSectionTraceMismatch NOTIFICATION-TYPE
    STATUS      current
    DESCRIPTION   "Section (SONET) / Regeneration Section (SDH) - Trace Identifier Mismatch"
    ::=  { fspR7Trap 391 }


alarmTraceIdentifierMismatchOduTcmA NOTIFICATION-TYPE
    STATUS      current
    DESCRIPTION   "Trace Identifier Mismatch of ODU Tandem Connection Monitoring Instance A"
    ::=  { fspR7Trap 392 }


alarmTraceIdentifierMismatchOduTcmB NOTIFICATION-TYPE
    STATUS      current
    DESCRIPTION   "Trace Identifier Mismatch of ODU Tandem Connection Monitoring Instance B"
    ::=  { fspR7Trap 393 }


alarmTraceIdentifierMismatchOduTcmC NOTIFICATION-TYPE
    STATUS      current
    DESCRIPTION   "Trace Identifier Mismatch of ODU Tandem Connection Monitoring Instance C"
    ::=  { fspR7Trap 394 }


alarmTurnupFailed NOTIFICATION-TYPE
    STATUS      current
    DESCRIPTION   "Turnup Operation failed"
    ::=  { fspR7Trap 395 }


alarmTurnupCondition NOTIFICATION-TYPE
    STATUS      current
    DESCRIPTION   "Turnup Operation in progress"
    ::=  { fspR7Trap 396 }


alarmUnequippedLowerOrderPath NOTIFICATION-TYPE
    STATUS      current
    DESCRIPTION   "LO-Path Unequipped"
    ::=  { fspR7Trap 397 }


alarmUnequippedHigherOrderPath NOTIFICATION-TYPE
    STATUS      current
    DESCRIPTION   "Path UNEQ"
    ::=  { fspR7Trap 398 }


alarmVoaControlFail NOTIFICATION-TYPE
    STATUS      current
    DESCRIPTION   "The power or attenuation control of OPCM failed"
    ::=  { fspR7Trap 399 }


alarmVoltageOutOfRange NOTIFICATION-TYPE
    STATUS      current
    DESCRIPTION   "Voltage Out of Range"
    ::=  { fspR7Trap 400 }


alarmInputVoltageFailure NOTIFICATION-TYPE
    STATUS      current
    DESCRIPTION   "Failure of Input Voltage"
    ::=  { fspR7Trap 401 }


alarmInputVoltageFailurePort1 NOTIFICATION-TYPE
    STATUS      current
    DESCRIPTION   "Failure of Input Voltage port 1"
    ::=  { fspR7Trap 402 }


alarmInputVoltageFailurePort2 NOTIFICATION-TYPE
    STATUS      current
    DESCRIPTION   "Failure of Input Voltage port 2"
    ::=  { fspR7Trap 403 }


transientWorkingSwitchedBacktoWorking NOTIFICATION-TYPE
    STATUS      current
    DESCRIPTION   "Working Traffic (ACT) switched back to Working facility from Protection facility automatically: sent by PROTN."
    ::=  { fspR7Trap 404 }


transientWorkingSwitchedtoProtection NOTIFICATION-TYPE
    STATUS      current
    DESCRIPTION   "Working Traffic (ACT) switched from WKG facility to PROTN facility automatically, sent by WKG."
    ::=  { fspR7Trap 405 }


alarmWtrTimerRunning NOTIFICATION-TYPE
    STATUS      current
    DESCRIPTION   "WTR timer is running"
    ::=  { fspR7Trap 406 }


alarmLossOfLaneOtu NOTIFICATION-TYPE
    STATUS      current
    DESCRIPTION   "OTU Loss of Lane Alignment"
    ::=  { fspR7Trap 407 }


alarmLossOfTestSeqSynchOpu NOTIFICATION-TYPE
    STATUS      current
    DESCRIPTION   "Loss of test Sequence Synchronization at OPU layer"
    ::=  { fspR7Trap 408 }


alarmLossOfMfiOpu NOTIFICATION-TYPE
    STATUS      current
    DESCRIPTION   "Loss of OPU Multiframe Indication for an OPU4 (LOOMFI per G.798)"
    ::=  { fspR7Trap 409 }


alarmOosDisabledLckOduTrmt NOTIFICATION-TYPE
    STATUS      current
    DESCRIPTION   "Disablement of Management Access with Transmitter Sending LCK"
    ::=  { fspR7Trap 410 }


alarmConfigurationMismatch NOTIFICATION-TYPE
    STATUS      current
    DESCRIPTION   "configuration mismatch"
    ::=  { fspR7Trap 411 }


alarmOduAutoShutdownRxAIS NOTIFICATION-TYPE
    STATUS      current
    DESCRIPTION   "Auto Shutdown (ODU-AIS-RCV)"
    ::=  { fspR7Trap 412 }


alarmOduAutoShutdownTxAIS NOTIFICATION-TYPE
    STATUS      current
    DESCRIPTION   "Auto Shutdown (ODU-AIS-TRMT)"
    ::=  { fspR7Trap 413 }


alarmOosDisabledLckOduRx NOTIFICATION-TYPE
    STATUS      current
    DESCRIPTION   "Disablement of Management Access with sending LCK-ODU in Rx"
    ::=  { fspR7Trap 414 }


transientBootUpFailed NOTIFICATION-TYPE
    STATUS      current
    DESCRIPTION   "Boot up failed"
    ::=  { fspR7Trap 415 }


transientBootUpCompleted NOTIFICATION-TYPE
    STATUS      current
    DESCRIPTION   "Boot up completed"
    ::=  { fspR7Trap 416 }


transientBootUpStarted NOTIFICATION-TYPE
    STATUS      current
    DESCRIPTION   "Boot up started"
    ::=  { fspR7Trap 417 }


transientInstallFwpCompleted NOTIFICATION-TYPE
    STATUS      current
    DESCRIPTION   "Installation of FWP completed"
    ::=  { fspR7Trap 418 }


transientBootUpRejected NOTIFICATION-TYPE
    STATUS      current
    DESCRIPTION   "Boot up rejected"
    ::=  { fspR7Trap 419 }


alarmThres15MinExceededBbePcs NOTIFICATION-TYPE
    STATUS      current
    DESCRIPTION   "Background Block Errors PCS Section Monitoring"
    ::=  { fspR7Trap 420 }


transientThres15DayExceededBbePcs NOTIFICATION-TYPE
    STATUS      current
    DESCRIPTION   "Background Block Errors PCS Monitoring"
    ::=  { fspR7Trap 421 }


alarmAutoShutdownGAis NOTIFICATION-TYPE
    STATUS      current
    DESCRIPTION   "Auto Shutdown (G-AIS)"
    ::=  { fspR7Trap 422 }


alarmEquipmentMismatchAllow NOTIFICATION-TYPE
    STATUS      current
    DESCRIPTION   "Equipment Mismatch Allow"
    ::=  { fspR7Trap 423 }


alarmWarmUp NOTIFICATION-TYPE
    STATUS      current
    DESCRIPTION   "Shelf is warming up"
    ::=  { fspR7Trap 424 }


transientFwpInstallStarted NOTIFICATION-TYPE
    STATUS      current
    DESCRIPTION   "Install started"
    ::=  { fspR7Trap 425 }


transientFwpInstallFailed NOTIFICATION-TYPE
    STATUS      current
    DESCRIPTION   "Install failed"
    ::=  { fspR7Trap 426 }


transientFwpInstallCompleted NOTIFICATION-TYPE
    STATUS      current
    DESCRIPTION   "Install completed"
    ::=  { fspR7Trap 427 }


transientFwpSwitchStarted NOTIFICATION-TYPE
    STATUS      current
    DESCRIPTION   "Switch started"
    ::=  { fspR7Trap 428 }


transientFwpSwitchFailed NOTIFICATION-TYPE
    STATUS      current
    DESCRIPTION   "Switch failed"
    ::=  { fspR7Trap 429 }


transientFwpSwitchCompleted NOTIFICATION-TYPE
    STATUS      current
    DESCRIPTION   "Switch completed"
    ::=  { fspR7Trap 430 }


transientFwpSwitchRejected NOTIFICATION-TYPE
    STATUS      current
    DESCRIPTION   "Switch rejected"
    ::=  { fspR7Trap 431 }


alarmNetworkPathRestricted NOTIFICATION-TYPE
    STATUS      current
    DESCRIPTION   "Available network data path are restricted"
    ::=  { fspR7Trap 432 }


transientPathCleanupComplete NOTIFICATION-TYPE
    STATUS      current
    DESCRIPTION   "Network data path cleanup completed"
    ::=  { fspR7Trap 433 }


alarmVfClientSignalFail NOTIFICATION-TYPE
    STATUS      current
    DESCRIPTION   "GFP Client Signal Fail on virtual Facility"
    ::=  { fspR7Trap 434 }


alarmAutoShutdownVfCSF NOTIFICATION-TYPE
    STATUS      current
    DESCRIPTION   "Automatic Shutdown - Client Signal Fail transmit (LKDO-CSF)"
    ::=  { fspR7Trap 435 }



fspR7EquipmentInsertedTrap NOTIFICATION-TYPE
    STATUS      current
    DESCRIPTION   "This trap is sent when an equipment is inserted."
    ::=  { fspR7Trap 10001 }

fspR7EquipmentRemovedTrap NOTIFICATION-TYPE
    STATUS      current
    DESCRIPTION   "This trap is sent when an equipment is inserted."
    ::=  { fspR7Trap 10002 }

fspR7WriteAccessRequest NOTIFICATION-TYPE
    STATUS      current
    DESCRIPTION   ""
    ::=  { fspR7Trap 10010 }

fspR7WriteAccessGranted NOTIFICATION-TYPE
    STATUS      current
    DESCRIPTION   ""
    ::=  { fspR7Trap 10011 }

fspR7WriteAccessRevoked NOTIFICATION-TYPE
    STATUS      current
    DESCRIPTION   ""
    ::=  { fspR7Trap 10012 }

fspR7WriteAccessDenied NOTIFICATION-TYPE
    STATUS      current
    DESCRIPTION   ""
    ::=  { fspR7Trap 10013 }

fspR7WriteAccessTimeout NOTIFICATION-TYPE
    STATUS      current
    DESCRIPTION   ""
    ::=  { fspR7Trap 10014 }

fspR7WriteAccessRequestTimeout NOTIFICATION-TYPE
    STATUS      current
    DESCRIPTION   ""
    ::=  { fspR7Trap 10015 }
optThresholdConfigTable OBJECT-TYPE
    SYNTAX      SEQUENCE OF OptThresholdConfigEntry
    MAX-ACCESS  not-accessible
    STATUS      deprecated
    DESCRIPTION   "optThresholdConfigTable"
    ::=  { performanceFacilityThreshold 1 }

optThresholdConfigEntry OBJECT-TYPE
    SYNTAX      OptThresholdConfigEntry
    MAX-ACCESS  not-accessible
    STATUS      deprecated
    DESCRIPTION   "Entry of optThresholdConfigTable"
    INDEX       {
                  entityFacilityShelfNo,
                  entityFacilitySlotNo,
                  entityFacilityPortNo,
                  entityFacilityExtNo,
                  entityFacilityClassName
                }
    ::=  { optThresholdConfigTable 1 }

OptThresholdConfigEntry ::=  SEQUENCE
  { optThresholdConfigLowFixed Integer32,
    optThresholdConfigHighFixed Integer32,
    optThresholdConfigLowConfig Integer32,
    optThresholdConfigHighConfig Integer32 }

optThresholdConfigLowFixed OBJECT-TYPE
    SYNTAX      Integer32
    UNITS       "0.1 dBm"
    MAX-ACCESS  read-only
    STATUS      deprecated
    DESCRIPTION
        "Low fixed threshold of the Optical Power Transmitted (output)"
    ::=  { optThresholdConfigEntry 1 }

optThresholdConfigHighFixed OBJECT-TYPE
    SYNTAX      Integer32
    UNITS       "0.1 dBm"
    MAX-ACCESS  read-only
    STATUS      deprecated
    DESCRIPTION
        "High fixed threshold of the Optical Power Transmitted (output)"
    ::=  { optThresholdConfigEntry 2 }

optThresholdConfigLowConfig OBJECT-TYPE
    SYNTAX      Integer32 (-500..300)
    UNITS       "0.1 dBm"
    MAX-ACCESS  read-write
    STATUS      deprecated
    DESCRIPTION
        "Configurable threshold of the Optical Power Transmitted (output)"
    ::=  { optThresholdConfigEntry 3 }

optThresholdConfigHighConfig OBJECT-TYPE
    SYNTAX      Integer32 (-500..300)
    UNITS       "0.1 dBm"
    MAX-ACCESS  read-write
    STATUS      deprecated
    DESCRIPTION
        "Configurable high threshold of the Optical Power Transmitted (output)"
    ::=  { optThresholdConfigEntry 4 }

oprThresholdConfigTable OBJECT-TYPE
    SYNTAX      SEQUENCE OF OprThresholdConfigEntry
    MAX-ACCESS  not-accessible
    STATUS      deprecated
    DESCRIPTION   "oprThresholdConfigTable"
    ::=  { performanceFacilityThreshold 2 }

oprThresholdConfigEntry OBJECT-TYPE
    SYNTAX      OprThresholdConfigEntry
    MAX-ACCESS  not-accessible
    STATUS      deprecated
    DESCRIPTION   "Entry of oprThresholdConfigTable"
    INDEX       {
                  entityFacilityShelfNo,
                  entityFacilitySlotNo,
                  entityFacilityPortNo,
                  entityFacilityExtNo,
                  entityFacilityClassName
                }
    ::=  { oprThresholdConfigTable 1 }

OprThresholdConfigEntry ::=  SEQUENCE
  { oprThresholdConfigLowConfig Integer32,
    oprThresholdConfigHighConfig Integer32 }

oprThresholdConfigLowConfig OBJECT-TYPE
    SYNTAX      Integer32 (-450..260)
    UNITS       "0.1 dBm"
    MAX-ACCESS  read-write
    STATUS      deprecated
    DESCRIPTION
        "Optical Input Power Received"
    ::=  { oprThresholdConfigEntry 1 }

oprThresholdConfigHighConfig OBJECT-TYPE
    SYNTAX      Integer32 (-450..260)
    UNITS       "0.1 dBm"
    MAX-ACCESS  read-write
    STATUS      deprecated
    DESCRIPTION
        "Optical Input Power Received"
    ::=  { oprThresholdConfigEntry 2 }

lsrtempThresholdConfigTable OBJECT-TYPE
    SYNTAX      SEQUENCE OF LsrtempThresholdConfigEntry
    MAX-ACCESS  not-accessible
    STATUS      deprecated
    DESCRIPTION   "lsrtempThresholdConfigTable"
    ::=  { performanceFacilityThreshold 3 }

lsrtempThresholdConfigEntry OBJECT-TYPE
    SYNTAX      LsrtempThresholdConfigEntry
    MAX-ACCESS  not-accessible
    STATUS      deprecated
    DESCRIPTION   "Entry of lsrtempThresholdConfigTable"
    INDEX       {
                  entityFacilityShelfNo,
                  entityFacilitySlotNo,
                  entityFacilityPortNo,
                  entityFacilityExtNo,
                  entityFacilityClassName
                }
    ::=  { lsrtempThresholdConfigTable 1 }

LsrtempThresholdConfigEntry ::=  SEQUENCE
  { lsrtempThresholdConfigLowFixed Integer32,
    lsrtempThresholdConfigHighFixed Integer32 }

lsrtempThresholdConfigLowFixed OBJECT-TYPE
    SYNTAX      Integer32
    UNITS       "0.1 degree Celsius"
    MAX-ACCESS  read-only
    STATUS      deprecated
    DESCRIPTION
        "Laser temperature fixed low threshold."
    ::=  { lsrtempThresholdConfigEntry 1 }

lsrtempThresholdConfigHighFixed OBJECT-TYPE
    SYNTAX      Integer32
    UNITS       "0.1 degree Celsius"
    MAX-ACCESS  read-only
    STATUS      deprecated
    DESCRIPTION
        "Laser temperature fixed high threshold."
    ::=  { lsrtempThresholdConfigEntry 2 }

optIntervalPm15minTable OBJECT-TYPE
    SYNTAX      SEQUENCE OF OptIntervalPm15minEntry
    MAX-ACCESS  not-accessible
    STATUS      deprecated
    DESCRIPTION   "optIntervalPm15minTable"
    ::=  { performanceFacilityMonitoring 1 }

optIntervalPm15minEntry OBJECT-TYPE
    SYNTAX      OptIntervalPm15minEntry
    MAX-ACCESS  not-accessible
    STATUS      deprecated
    DESCRIPTION   "Entry of optIntervalPm15minTable"
    INDEX       {
                  entityFacilityShelfNo,
                  entityFacilitySlotNo,
                  entityFacilityPortNo,
                  entityFacilityExtNo,
                  entityFacilityClassName,
                  optIntervalPm15minNumber
                }
    ::=  { optIntervalPm15minTable 1 }

OptIntervalPm15minEntry ::=  SEQUENCE
  { optIntervalPm15minNumber Integer32,
    optIntervalPm15minLow Integer32,
    optIntervalPm15minMean Integer32,
    optIntervalPm15minHigh Integer32,
    optIntervalPm15minValidFlag TruthValue,
    optIntervalPm15minTimeStamp DateAndTime }

optIntervalPm15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1."
    ::=  { optIntervalPm15minEntry 1 }

optIntervalPm15minLow OBJECT-TYPE
    SYNTAX      Integer32
    UNITS       "0.1 dBm"
    MAX-ACCESS  read-only
    STATUS      deprecated
    DESCRIPTION
        "Optical Output Power Transmitted"
    ::=  { optIntervalPm15minEntry 2 }

optIntervalPm15minMean OBJECT-TYPE
    SYNTAX      Integer32
    UNITS       "0.1 dBm"
    MAX-ACCESS  read-only
    STATUS      deprecated
    DESCRIPTION
        "Optical Output Power Transmitted"
    ::=  { optIntervalPm15minEntry 3 }

optIntervalPm15minHigh OBJECT-TYPE
    SYNTAX      Integer32
    UNITS       "0.1 dBm"
    MAX-ACCESS  read-only
    STATUS      deprecated
    DESCRIPTION
        "Optical Output Power Transmitted"
    ::=  { optIntervalPm15minEntry 4 }

optIntervalPm15minValidFlag OBJECT-TYPE
    SYNTAX      TruthValue
    MAX-ACCESS  read-only
    STATUS      deprecated
    DESCRIPTION
        "Valid Flag"
    ::=  { optIntervalPm15minEntry 5 }

optIntervalPm15minTimeStamp OBJECT-TYPE
    SYNTAX      DateAndTime
    MAX-ACCESS  read-only
    STATUS      deprecated
    DESCRIPTION
        "Timestamp"
    ::=  { optIntervalPm15minEntry 6 }

optIntervalPm1dayTable OBJECT-TYPE
    SYNTAX      SEQUENCE OF OptIntervalPm1dayEntry
    MAX-ACCESS  not-accessible
    STATUS      deprecated
    DESCRIPTION   "optIntervalPm1dayTable"
    ::=  { performanceFacilityMonitoring 2 }

optIntervalPm1dayEntry OBJECT-TYPE
    SYNTAX      OptIntervalPm1dayEntry
    MAX-ACCESS  not-accessible
    STATUS      deprecated
    DESCRIPTION   "Entry of optIntervalPm1dayTable"
    INDEX       {
                  entityFacilityShelfNo,
                  entityFacilitySlotNo,
                  entityFacilityPortNo,
                  entityFacilityExtNo,
                  entityFacilityClassName,
                  optIntervalPm1dayNumber
                }
    ::=  { optIntervalPm1dayTable 1 }

OptIntervalPm1dayEntry ::=  SEQUENCE
  { optIntervalPm1dayNumber Integer32,
    optIntervalPm1dayLow Integer32,
    optIntervalPm1dayMean Integer32,
    optIntervalPm1dayHigh Integer32,
    optIntervalPm1dayValidFlag TruthValue,
    optIntervalPm1dayTimeStamp DateAndTime }

optIntervalPm1dayNumber OBJECT-TYPE
    SYNTAX      Integer32 (1..31)
    MAX-ACCESS  not-accessible
    STATUS      current
    DESCRIPTION
        "A number, which identifies the interval for
         which the set of statistics is available. The interval
         identified by 1 is the most recently completed 1 day
         interval."
    ::=  { optIntervalPm1dayEntry 1 }

optIntervalPm1dayLow OBJECT-TYPE
    SYNTAX      Integer32
    UNITS       "0.1 dBm"
    MAX-ACCESS  read-only
    STATUS      deprecated
    DESCRIPTION
        "Optical Output Power Transmitted"
    ::=  { optIntervalPm1dayEntry 2 }

optIntervalPm1dayMean OBJECT-TYPE
    SYNTAX      Integer32
    UNITS       "0.1 dBm"
    MAX-ACCESS  read-only
    STATUS      deprecated
    DESCRIPTION
        "Optical Output Power Transmitted"
    ::=  { optIntervalPm1dayEntry 3 }

optIntervalPm1dayHigh OBJECT-TYPE
    SYNTAX      Integer32
    UNITS       "0.1 dBm"
    MAX-ACCESS  read-only
    STATUS      deprecated
    DESCRIPTION
        "Optical Output Power Transmitted"
    ::=  { optIntervalPm1dayEntry 4 }

optIntervalPm1dayValidFlag OBJECT-TYPE
    SYNTAX      TruthValue
    MAX-ACCESS  read-only
    STATUS      deprecated
    DESCRIPTION
        "Valid Flag"
    ::=  { optIntervalPm1dayEntry 5 }

optIntervalPm1dayTimeStamp OBJECT-TYPE
    SYNTAX      DateAndTime
    MAX-ACCESS  read-only
    STATUS      deprecated
    DESCRIPTION
        "Timestamp"
    ::=  { optIntervalPm1dayEntry 6 }

optIntervalPm1weekTable OBJECT-TYPE
    SYNTAX      SEQUENCE OF OptIntervalPm1weekEntry
    MAX-ACCESS  not-accessible
    STATUS      deprecated
    DESCRIPTION   "optIntervalPm1weekTable"
    ::=  { performanceFacilityMonitoring 3 }

optIntervalPm1weekEntry OBJECT-TYPE
    SYNTAX      OptIntervalPm1weekEntry
    MAX-ACCESS  not-accessible
    STATUS      deprecated
    DESCRIPTION   "Entry of optIntervalPm1weekTable"
    INDEX       {
                  entityFacilityShelfNo,
                  entityFacilitySlotNo,
                  entityFacilityPortNo,
                  entityFacilityExtNo,
                  entityFacilityClassName,
                  optIntervalPm1weekNumber
                }
    ::=  { optIntervalPm1weekTable 1 }

OptIntervalPm1weekEntry ::=  SEQUENCE
  { optIntervalPm1weekNumber Integer32,
    optIntervalPm1weekLow Integer32,
    optIntervalPm1weekMean Integer32,
    optIntervalPm1weekHigh Integer32,
    optIntervalPm1weekValidFlag TruthValue,
    optIntervalPm1weekTimeStamp DateAndTime }

optIntervalPm1weekNumber OBJECT-TYPE
    SYNTAX      Integer32 (1..52)
    MAX-ACCESS  not-accessible
    STATUS      current
    DESCRIPTION
        "Number 1week"
    ::=  { optIntervalPm1weekEntry 1 }

optIntervalPm1weekLow OBJECT-TYPE
    SYNTAX      Integer32
    UNITS       "0.1 dBm"
    MAX-ACCESS  read-only
    STATUS      deprecated
    DESCRIPTION
        "Optical Output Power Transmitted"
    ::=  { optIntervalPm1weekEntry 2 }

optIntervalPm1weekMean OBJECT-TYPE
    SYNTAX      Integer32
    UNITS       "0.1 dBm"
    MAX-ACCESS  read-only
    STATUS      deprecated
    DESCRIPTION
        "Optical Output Power Transmitted"
    ::=  { optIntervalPm1weekEntry 3 }

optIntervalPm1weekHigh OBJECT-TYPE
    SYNTAX      Integer32
    UNITS       "0.1 dBm"
    MAX-ACCESS  read-only
    STATUS      deprecated
    DESCRIPTION
        "Optical Output Power Transmitted"
    ::=  { optIntervalPm1weekEntry 4 }

optIntervalPm1weekValidFlag OBJECT-TYPE
    SYNTAX      TruthValue
    MAX-ACCESS  read-only
    STATUS      deprecated
    DESCRIPTION
        "Valid Flag"
    ::=  { optIntervalPm1weekEntry 5 }

optIntervalPm1weekTimeStamp OBJECT-TYPE
    SYNTAX      DateAndTime
    MAX-ACCESS  read-only
    STATUS      deprecated
    DESCRIPTION
        "Timestamp"
    ::=  { optIntervalPm1weekEntry 6 }

oprIntervalPm15minTable OBJECT-TYPE
    SYNTAX      SEQUENCE OF OprIntervalPm15minEntry
    MAX-ACCESS  not-accessible
    STATUS      deprecated
    DESCRIPTION   "oprIntervalPm15minTable"
    ::=  { performanceFacilityMonitoring 4 }

oprIntervalPm15minEntry OBJECT-TYPE
    SYNTAX      OprIntervalPm15minEntry
    MAX-ACCESS  not-accessible
    STATUS      deprecated
    DESCRIPTION   "Entry of oprIntervalPm15minTable"
    INDEX       {
                  entityFacilityShelfNo,
                  entityFacilitySlotNo,
                  entityFacilityPortNo,
                  entityFacilityExtNo,
                  entityFacilityClassName,
                  oprIntervalPm15minNumber
                }
    ::=  { oprIntervalPm15minTable 1 }

OprIntervalPm15minEntry ::=  SEQUENCE
  { oprIntervalPm15minNumber Integer32,
    oprIntervalPm15minLow Integer32,
    oprIntervalPm15minMean Integer32,
    oprIntervalPm15minHigh Integer32,
    oprIntervalPm15minValidFlag TruthValue,
    oprIntervalPm15minTimeStamp DateAndTime }

oprIntervalPm15minNumber OBJECT-TYPE
    SYNTAX      Integer32 (1..96)
    MAX-ACCESS  not-accessible
    STATUS      current
    DESCRIPTION
        "A number between 1 and 96, which identifies the interval for
         which the set of statistics is available. The interval
         identified by 1 is the most recently completed 15 minute
         interval, and the interval identified by N is the interval
         immediately preceding the one identified by N-1."
    ::=  { oprIntervalPm15minEntry 1 }

oprIntervalPm15minLow OBJECT-TYPE
    SYNTAX      Integer32
    UNITS       "0.1 dBm"
    MAX-ACCESS  read-only
    STATUS      deprecated
    DESCRIPTION
        "Optical Input Power Received"
    ::=  { oprIntervalPm15minEntry 2 }

oprIntervalPm15minMean OBJECT-TYPE
    SYNTAX      Integer32
    UNITS       "0.1 dBm"
    MAX-ACCESS  read-only
    STATUS      deprecated
    DESCRIPTION
        "Optical Input Power Received"
    ::=  { oprIntervalPm15minEntry 3 }

oprIntervalPm15minHigh OBJECT-TYPE
    SYNTAX      Integer32
    UNITS       "0.1 dBm"
    MAX-ACCESS  read-only
    STATUS      deprecated
    DESCRIPTION
        "Optical Input Power Received"
    ::=  { oprIntervalPm15minEntry 4 }

oprIntervalPm15minValidFlag OBJECT-TYPE
    SYNTAX      TruthValue
    MAX-ACCESS  read-only
    STATUS      deprecated
    DESCRIPTION
        "Valid Flag"
    ::=  { oprIntervalPm15minEntry 5 }

oprIntervalPm15minTimeStamp OBJECT-TYPE
    SYNTAX      DateAndTime
    MAX-ACCESS  read-only
    STATUS      deprecated
    DESCRIPTION
        "Timestamp"
    ::=  { oprIntervalPm15minEntry 6 }

oprIntervalPm1dayTable OBJECT-TYPE
    SYNTAX      SEQUENCE OF OprIntervalPm1dayEntry
    MAX-ACCESS  not-accessible
    STATUS      deprecated
    DESCRIPTION   "oprIntervalPm1dayTable"
    ::=  { performanceFacilityMonitoring 5 }

oprIntervalPm1dayEntry OBJECT-TYPE
    SYNTAX      OprIntervalPm1dayEntry
    MAX-ACCESS  not-accessible
    STATUS      deprecated
    DESCRIPTION   "Entry of oprIntervalPm1dayTable"
    INDEX       {
                  entityFacilityShelfNo,
                  entityFacilitySlotNo,
                  entityFacilityPortNo,
                  entityFacilityExtNo,
                  entityFacilityClassName,
                  oprIntervalPm1dayNumber
                }
    ::=  { oprIntervalPm1dayTable 1 }

OprIntervalPm1dayEntry ::=  SEQUENCE
  { oprIntervalPm1dayNumber Integer32,
    oprIntervalPm1dayLow Integer32,
    oprIntervalPm1dayMean Integer32,
    oprIntervalPm1dayHigh Integer32,
    oprIntervalPm1dayValidFlag TruthValue,
    oprIntervalPm1dayTimeStamp DateAndTime }

oprIntervalPm1dayNumber OBJECT-TYPE
    SYNTAX      Integer32 (1..31)
    MAX-ACCESS  not-accessible
    STATUS      current
    DESCRIPTION
        "A number, which identifies the interval for
         which the set of statistics is available. The interval
         identified by 1 is the most recently completed 1 day
         interval."
    ::=  { oprIntervalPm1dayEntry 1 }

oprIntervalPm1dayLow OBJECT-TYPE
    SYNTAX      Integer32
    UNITS       "0.1 dBm"
    MAX-ACCESS  read-only
    STATUS      deprecated
    DESCRIPTION
        "Optical Input Power Received"
    ::=  { oprIntervalPm1dayEntry 2 }

oprIntervalPm1dayMean OBJECT-TYPE
    SYNTAX      Integer32
    UNITS       "0.1 dBm"
    MAX-ACCESS  read-only
    STATUS      deprecated
    DESCRIPTION
        "Optical Input Power Received"
    ::=  { oprIntervalPm1dayEntry 3 }

oprIntervalPm1dayHigh OBJECT-TYPE
    SYNTAX      Integer32
    UNITS       "0.1 dBm"
    MAX-ACCESS  read-only
    STATUS      deprecated
    DESCRIPTION
        "Optical Input Power Received"
    ::=  { oprIntervalPm1dayEntry 4 }

oprIntervalPm1dayValidFlag OBJECT-TYPE
    SYNTAX      TruthValue
    MAX-ACCESS  read-only
    STATUS      deprecated
    DESCRIPTION
        "Valid Flag"
    ::=  { oprIntervalPm1dayEntry 5 }

oprIntervalPm1dayTimeStamp OBJECT-TYPE
    SYNTAX      DateAndTime
    MAX-ACCESS  read-only
    STATUS      deprecated
    DESCRIPTION
        "Timestamp"
    ::=  { oprIntervalPm1dayEntry 6 }

oprIntervalPm1weekTable OBJECT-TYPE
    SYNTAX      SEQUENCE OF OprIntervalPm1weekEntry
    MAX-ACCESS  not-accessible
    STATUS      deprecated
    DESCRIPTION   "oprIntervalPm1weekTable"
    ::=  { performanceFacilityMonitoring 6 }

oprIntervalPm1weekEntry OBJECT-TYPE
    SYNTAX      OprIntervalPm1weekEntry
    MAX-ACCESS  not-accessible
    STATUS      deprecated
    DESCRIPTION   "Entry of oprIntervalPm1weekTable"
    INDEX       {
                  entityFacilityShelfNo,
                  entityFacilitySlotNo,
                  entityFacilityPortNo,
                  entityFacilityExtNo,
                  entityFacilityClassName,
                  oprIntervalPm1weekNumber
                }
    ::=  { oprIntervalPm1weekTable 1 }

OprIntervalPm1weekEntry ::=  SEQUENCE
  { oprIntervalPm1weekNumber Integer32,
    oprIntervalPm1weekLow Integer32,
    oprIntervalPm1weekMean Integer32,
    oprIntervalPm1weekHigh Integer32,
    oprIntervalPm1weekValidFlag TruthValue,
    oprIntervalPm1weekTimeStamp DateAndTime }

oprIntervalPm1weekNumber OBJECT-TYPE
    SYNTAX      Integer32 (1..52)
    MAX-ACCESS  not-accessible
    STATUS      current
    DESCRIPTION
        "Number 1week"
    ::=  { oprIntervalPm1weekEntry 1 }

oprIntervalPm1weekLow OBJECT-TYPE
    SYNTAX      Integer32
    UNITS       "0.1 dBm"
    MAX-ACCESS  read-only
    STATUS      deprecated
    DESCRIPTION
        "Optical Input Power Received"
    ::=  { oprIntervalPm1weekEntry 2 }

oprIntervalPm1weekMean OBJECT-TYPE
    SYNTAX      Integer32
    UNITS       "0.1 dBm"
    MAX-ACCESS  read-only
    STATUS      deprecated
    DESCRIPTION
        "Optical Input Power Received"
    ::=  { oprIntervalPm1weekEntry 3 }

oprIntervalPm1weekHigh OBJECT-TYPE
    SYNTAX      Integer32
    UNITS       "0.1 dBm"
    MAX-ACCESS  read-only
    STATUS      deprecated
    DESCRIPTION
        "Optical Input Power Received"
    ::=  { oprIntervalPm1weekEntry 4 }

oprIntervalPm1weekValidFlag OBJECT-TYPE
    SYNTAX      TruthValue
    MAX-ACCESS  read-only
    STATUS      deprecated
    DESCRIPTION
        "Valid Flag"
    ::=  { oprIntervalPm1weekEntry 5 }

oprIntervalPm1weekTimeStamp OBJECT-TYPE
    SYNTAX      DateAndTime
    MAX-ACCESS  read-only
    STATUS      deprecated
    DESCRIPTION
        "Timestamp"
    ::=  { oprIntervalPm1weekEntry 6 }

endOfPerformance OBJECT-TYPE
    SYNTAX      Integer32
    MAX-ACCESS  read-only
    STATUS      current
    DESCRIPTION
        ""
    ::=  { performance 10000 }

terminationPointTable OBJECT-TYPE
    SYNTAX      SEQUENCE OF TerminationPointEntry
    MAX-ACCESS  not-accessible
    STATUS      current
    DESCRIPTION   "terminationPoint"
    ::=  { fiberMap 1 }

terminationPointEntry OBJECT-TYPE
    SYNTAX      TerminationPointEntry
    MAX-ACCESS  not-accessible
    STATUS      current
    DESCRIPTION   "Entry of terminationPoint"
    INDEX       {
                  entityTerminPointIndexNo1,
                  entityTerminPointIndexNo2,
                  entityTerminPointIndexNo3,
                  entityTerminPointIndexNo4,
                  entityTerminPointClassName
                }
    ::=  { terminationPointTable 1 }

TerminationPointEntry ::=  SEQUENCE
  { terminationPointRowStatus RowStatus,
    terminationPointPartnerAid RowPointer,
    terminationPointAdmin FspR7AdminState,
    terminationPointFiberDetect FspR7FiberDetect,
    terminationPointFiberDetectStatus FspR7FDStatusCaps,
    terminationPointFunction FspR7InterfaceFunction,
    terminationPointAlias SnmpAdminString,
    terminationPointValidSigTimer Unsigned32,
    terminationPointConnector FspR7ConnectorType,
    terminationPointFiber FspR7OpticalFiberType,
    terminationPointConnType FspR7TypeConnection,
    terminationPointOper FspR7OperState,
    terminationPointOutputPower Integer32,
    terminationPointInputPower Integer32,
    terminationPointFiberConnAtten Integer32,
    terminationPointConnEqptState FspR7ConnectState,
    terminationPointTermType FspR7EquipmentType,
    terminationPointChannel FspR7ChannelIdentifier,
    terminationPointLambda Unsigned32,
    terminationPointFrequency Unsigned32,
    terminationPointReach FspR7OpticalInterfaceReach,
    terminationPointBand FspR7OpticalBand,
    terminationPointSubBand FspR7OpticalSubBand,
    terminationPointGroup FspR7OpticalGroup,
    terminationPointSfProvision FspR7SingleFiberLocation,
    terminationPointDirection ApsDirection,
    terminationPointLevel FspR7OpticalMultiplexLevel,
    terminationPointSecondaryStates FspR7EntitySecondaryStates }

terminationPointRowStatus OBJECT-TYPE
    SYNTAX      RowStatus
    MAX-ACCESS  read-create
    STATUS      current
    DESCRIPTION   "Termination Point RowStatus. Object is used to
         create or delete a row in the table."
    ::=  { terminationPointEntry 1 }

terminationPointPartnerAid OBJECT-TYPE
    SYNTAX      RowPointer
    MAX-ACCESS  read-only
    STATUS      current
    DESCRIPTION   "Termination Point Partner AID."
    ::=  { terminationPointEntry 2 }

terminationPointAdmin OBJECT-TYPE
    SYNTAX      FspR7AdminState
    MAX-ACCESS  read-create
    STATUS      current
    DESCRIPTION   "Termination Point Adminstrative State."
    ::=  { terminationPointEntry 3 }

terminationPointFiberDetect OBJECT-TYPE
    SYNTAX      FspR7FiberDetect
    MAX-ACCESS  read-create
    STATUS      current
    DESCRIPTION   "Termination Point Fiber Detect."
    ::=  { terminationPointEntry 4 }

terminationPointFiberDetectStatus OBJECT-TYPE
    SYNTAX      FspR7FDStatusCaps
    MAX-ACCESS  read-only
    STATUS      current
    DESCRIPTION   "Termination Point Fiber Detect Status."
    ::=  { terminationPointEntry 5 }

terminationPointFunction OBJECT-TYPE
    SYNTAX      FspR7InterfaceFunction
    MAX-ACCESS  read-only
    STATUS      current
    DESCRIPTION   "Termination Point Interface Function."
    ::=  { terminationPointEntry 6 }

terminationPointAlias OBJECT-TYPE
    SYNTAX      SnmpAdminString
    MAX-ACCESS  read-write
    STATUS      current
    DESCRIPTION   "Termination Point Alias."
    ::=  { terminationPointEntry 7 }

terminationPointValidSigTimer OBJECT-TYPE
    SYNTAX      Unsigned32 (0..5760)
    UNITS       "min"
    MAX-ACCESS  read-only
    STATUS      current
    DESCRIPTION   "Termination Point Valid Signal Timer."
    ::=  { terminationPointEntry 8 }

terminationPointConnector OBJECT-TYPE
    SYNTAX      FspR7ConnectorType
    MAX-ACCESS  read-only
    STATUS      current
    DESCRIPTION   "Termination Point Connector Type."
    ::=  { terminationPointEntry 9 }

terminationPointFiber OBJECT-TYPE
    SYNTAX      FspR7OpticalFiberType
    MAX-ACCESS  read-only
    STATUS      current
    DESCRIPTION   "Termination Point Fiber Type."
    ::=  { terminationPointEntry 10 }

terminationPointConnType OBJECT-TYPE
    SYNTAX      FspR7TypeConnection
    MAX-ACCESS  read-only
    STATUS      current
    DESCRIPTION   "Termination Point Connectivity Type."
    ::=  { terminationPointEntry 11 }

terminationPointOper OBJECT-TYPE
    SYNTAX      FspR7OperState
    MAX-ACCESS  read-only
    STATUS      current
    DESCRIPTION   "Termination Point Operational State."
    ::=  { terminationPointEntry 12 }

terminationPointOutputPower OBJECT-TYPE
    SYNTAX      Integer32
    UNITS       "0.1 dBm"
    MAX-ACCESS  read-only
    STATUS      current
    DESCRIPTION   "Termination Point Optical Power Tx."
    ::=  { terminationPointEntry 13 }

terminationPointInputPower OBJECT-TYPE
    SYNTAX      Integer32
    UNITS       "0.1 dBm"
    MAX-ACCESS  read-only
    STATUS      current
    DESCRIPTION   "Termination Point Optical Power Rx."
    ::=  { terminationPointEntry 14 }

terminationPointFiberConnAtten OBJECT-TYPE
    SYNTAX      Integer32
    UNITS       "0.1 dB"
    MAX-ACCESS  read-only
    STATUS      current
    DESCRIPTION   "Termination Point Fiber Connection Attenuation."
    ::=  { terminationPointEntry 15 }

terminationPointConnEqptState OBJECT-TYPE
    SYNTAX      FspR7ConnectState
    MAX-ACCESS  read-only
    STATUS      current
    DESCRIPTION   "Termination Point Fiber Connection Eqpt State."
    ::=  { terminationPointEntry 16 }

terminationPointTermType OBJECT-TYPE
    SYNTAX      FspR7EquipmentType
    MAX-ACCESS  read-only
    STATUS      current
    DESCRIPTION   "Termination Point Termination Type."
    ::=  { terminationPointEntry 17 }

terminationPointChannel OBJECT-TYPE
    SYNTAX      FspR7ChannelIdentifier
    MAX-ACCESS  read-only
    STATUS      current
    DESCRIPTION   "Termination Point Channel Provision."
    ::=  { terminationPointEntry 18 }

terminationPointLambda OBJECT-TYPE
    SYNTAX      Unsigned32
    UNITS       "0.01 nm"
    MAX-ACCESS  read-only
    STATUS      current
    DESCRIPTION   "Termination Point Lambda."
    ::=  { terminationPointEntry 19 }

terminationPointFrequency OBJECT-TYPE
    SYNTAX      Unsigned32
    UNITS       "0.01 THz"
    MAX-ACCESS  read-only
    STATUS      current
    DESCRIPTION   "Termination Point Frequency."
    ::=  { terminationPointEntry 20 }

terminationPointReach OBJECT-TYPE
    SYNTAX      FspR7OpticalInterfaceReach
    MAX-ACCESS  read-only
    STATUS      current
    DESCRIPTION   "Termination Point Reach Provision."
    ::=  { terminationPointEntry 21 }

terminationPointBand OBJECT-TYPE
    SYNTAX      FspR7OpticalBand
    MAX-ACCESS  read-only
    STATUS      current
    DESCRIPTION   "Termination Point Band Provision."
    ::=  { terminationPointEntry 22 }

terminationPointSubBand OBJECT-TYPE
    SYNTAX      FspR7OpticalSubBand
    MAX-ACCESS  read-only
    STATUS      current
    DESCRIPTION   "Termination Point SubBand Provision."
    ::=  { terminationPointEntry 23 }

terminationPointGroup OBJECT-TYPE
    SYNTAX      FspR7OpticalGroup
    MAX-ACCESS  read-only
    STATUS      current
    DESCRIPTION   "Termination Point Group Provision."
    ::=  { terminationPointEntry 24 }

terminationPointSfProvision OBJECT-TYPE
    SYNTAX      FspR7SingleFiberLocation
    MAX-ACCESS  read-only
    STATUS      current
    DESCRIPTION   "Termination Point Sf Provision."
    ::=  { terminationPointEntry 25 }

terminationPointDirection OBJECT-TYPE
    SYNTAX      ApsDirection
    MAX-ACCESS  read-only
    STATUS      current
    DESCRIPTION   "Termination Point Direction."
    ::=  { terminationPointEntry 26 }

terminationPointLevel OBJECT-TYPE
    SYNTAX      FspR7OpticalMultiplexLevel
    MAX-ACCESS  read-only
    STATUS      current
    DESCRIPTION   "Termination Point Level."
    ::=  { terminationPointEntry 27 }

terminationPointSecondaryStates OBJECT-TYPE
    SYNTAX      FspR7EntitySecondaryStates
    MAX-ACCESS  read-only
    STATUS      current
    DESCRIPTION   "Termination Secondary States."
    ::=  { terminationPointEntry 28 }

connectionTable OBJECT-TYPE
    SYNTAX      SEQUENCE OF ConnectionEntry
    MAX-ACCESS  not-accessible
    STATUS      current
    DESCRIPTION   "connectionTable"
    ::=  { fiberMap 2 }

connectionEntry OBJECT-TYPE
    SYNTAX      ConnectionEntry
    MAX-ACCESS  not-accessible
    STATUS      current
    DESCRIPTION   "Entry of connectionTable"
    INDEX       {
                  entityTerminPointIndexNo1,
                  entityTerminPointIndexNo2,
                  entityTerminPointIndexNo3,
                  entityTerminPointIndexNo4,
                  entityTerminPointClassName,
                  entityTerminPointIndexNo1,
                  entityTerminPointIndexNo2,
                  entityTerminPointIndexNo3,
                  entityTerminPointIndexNo4,
                  entityTerminPointClassName,
                  entityConnectionClassName
                }
    ::=  { connectionTable 1 }

ConnectionEntry ::=  SEQUENCE
  { connectionRowStatus RowStatus,
    connectionType FspR7TypeConnection,
    connectionState FspR7StateConnection,
    connectionCreationMethod FfpType }

connectionRowStatus OBJECT-TYPE
    SYNTAX      RowStatus
    MAX-ACCESS  read-create
    STATUS      current
    DESCRIPTION   "Physical Connection RowStatus. Object is used to create
         or delete a row in the table."
    ::=  { connectionEntry 1 }

connectionType OBJECT-TYPE
    SYNTAX      FspR7TypeConnection
    MAX-ACCESS  read-create
    STATUS      current
    DESCRIPTION   "Physical Connection Type."
    ::=  { connectionEntry 2 }

connectionState OBJECT-TYPE
    SYNTAX      FspR7StateConnection
    MAX-ACCESS  read-only
    STATUS      current
    DESCRIPTION   "Physical Connection State."
    ::=  { connectionEntry 3 }

connectionCreationMethod OBJECT-TYPE
    SYNTAX      FfpType
    MAX-ACCESS  read-create
    STATUS      current
    DESCRIPTION   "Type of protection (normal/forced)"
    ::=  { connectionEntry 4 }

facilityReferByTable OBJECT-TYPE
    SYNTAX      SEQUENCE OF FacilityReferByEntry
    MAX-ACCESS  not-accessible
    STATUS      current
    DESCRIPTION   "facilityReferByTable"
    ::=  { fiberMap 3 }

facilityReferByEntry OBJECT-TYPE
    SYNTAX      FacilityReferByEntry
    MAX-ACCESS  not-accessible
    STATUS      current
    DESCRIPTION   "Entry of facilityReferByTable"
    INDEX       {
                  entityFacilityShelfNo,
                  entityFacilitySlotNo,
                  entityFacilityPortNo,
                  entityFacilityExtNo,
                  entityFacilityClassName
                }
    ::=  { facilityReferByTable 1 }

FacilityReferByEntry ::=  SEQUENCE
  { facilityReferByTerminPoint RowPointer }

facilityReferByTerminPoint OBJECT-TYPE
    SYNTAX      RowPointer
    MAX-ACCESS  read-only
    STATUS      current
    DESCRIPTION   "RowPointer to object which refer to."
    ::=  { facilityReferByEntry 1 }

externalPortReferByTable OBJECT-TYPE
    SYNTAX      SEQUENCE OF ExternalPortReferByEntry
    MAX-ACCESS  not-accessible
    STATUS      current
    DESCRIPTION   "externalPortReferByTable"
    ::=  { fiberMap 4 }

externalPortReferByEntry OBJECT-TYPE
    SYNTAX      ExternalPortReferByEntry
    MAX-ACCESS  not-accessible
    STATUS      current
    DESCRIPTION   "Entry of externalPortReferByTable"
    INDEX       {
                  entityExternalPortShelfNo,
                  entityExternalPortSlotNo,
                  entityExternalPortPortNo,
                  entityExternalPortExtNo,
                  entityExternalPortClassName
                }
    ::=  { externalPortReferByTable 1 }

ExternalPortReferByEntry ::=  SEQUENCE
  { externalPortReferByTerminPoint RowPointer }

externalPortReferByTerminPoint OBJECT-TYPE
    SYNTAX      RowPointer
    MAX-ACCESS  read-only
    STATUS      current
    DESCRIPTION   "RowPointer to object which refer to."
    ::=  { externalPortReferByEntry 1 }

endOfExternalPortReferByTabke OBJECT-TYPE
    SYNTAX      Integer32
    MAX-ACCESS  read-only
    STATUS      current
    DESCRIPTION
        ""
    ::=  { fiberMap 5 }

dcnReferByTable OBJECT-TYPE
    SYNTAX      SEQUENCE OF DcnReferByEntry
    MAX-ACCESS  not-accessible
    STATUS      current
    DESCRIPTION   "dcnReferByTable"
    ::=  { fiberMap 6 }

dcnReferByEntry OBJECT-TYPE
    SYNTAX      DcnReferByEntry
    MAX-ACCESS  not-accessible
    STATUS      current
    DESCRIPTION   "Entry of dcnReferByTable"
    INDEX       {
                  entityDcnShelfNo,
                  entityDcnSlotNo,
                  entityDcnPortNo,
                  entityDcnExtNo,
                  entityDcnClassName
                }
    ::=  { dcnReferByTable 1 }

DcnReferByEntry ::=  SEQUENCE
  { dcnReferByTerminPoint RowPointer }

dcnReferByTerminPoint OBJECT-TYPE
    SYNTAX      RowPointer
    MAX-ACCESS  read-only
    STATUS      current
    DESCRIPTION   "RowPointer to object which refer to."
    ::=  { dcnReferByEntry 1 }

endOfDcnReferByTable OBJECT-TYPE
    SYNTAX      Integer32
    MAX-ACCESS  read-only
    STATUS      current
    DESCRIPTION
        ""
    ::=  { fiberMap 7 }

opticalMuxReferByTable OBJECT-TYPE
    SYNTAX      SEQUENCE OF OpticalMuxReferByEntry
    MAX-ACCESS  not-accessible
    STATUS      current
    DESCRIPTION   "opticalMuxReferByTable"
    ::=  { fiberMap 8 }

opticalMuxReferByEntry OBJECT-TYPE
    SYNTAX      OpticalMuxReferByEntry
    MAX-ACCESS  not-accessible
    STATUS      current
    DESCRIPTION   "Entry of opticalMuxReferByTable"
    INDEX       {
                  entityOpticalMuxShelfNo,
                  entityOpticalMuxSlotNo,
                  entityOpticalMuxPortNo,
                  entityOpticalMuxExtNo,
                  entityOpticalMuxClassName
                }
    ::=  { opticalMuxReferByTable 1 }

OpticalMuxReferByEntry ::=  SEQUENCE
  { opticalMuxReferByTerminPoint RowPointer }

opticalMuxReferByTerminPoint OBJECT-TYPE
    SYNTAX      RowPointer
    MAX-ACCESS  read-only
    STATUS      current
    DESCRIPTION   "RowPointer to object which refer to."
    ::=  { opticalMuxReferByEntry 1 }

endOfOpticalMuxReferByTable OBJECT-TYPE
    SYNTAX      Integer32
    MAX-ACCESS  read-only
    STATUS      current
    DESCRIPTION
        ""
    ::=  { fiberMap 9 }

endOfFiberMap OBJECT-TYPE
    SYNTAX      Integer32
    MAX-ACCESS  read-only
    STATUS      current
    DESCRIPTION
        ""
    ::=  { fiberMap 10000 }

startPmSnapshot OBJECT-TYPE
    SYNTAX      FspR7StartPmSnapshot
    MAX-ACCESS  read-write
    STATUS      current
    DESCRIPTION   "Apply PM reference values"
    ::=  { pmSnapshot 1 }

pmSnapshotStatus OBJECT-TYPE
    SYNTAX      FspR7PmSnapshotStatus
    MAX-ACCESS  read-only
    STATUS      current
    DESCRIPTION   "PM Reference value Status"
    ::=  { pmSnapshot 2 }

pmSnapshotCurrentTable OBJECT-TYPE
    SYNTAX      SEQUENCE OF PmSnapshotCurrentEntry
    MAX-ACCESS  not-accessible
    STATUS      current
    DESCRIPTION   "pmSnapshotCurrentFacilityTable"
    ::=  { pmSnapshot 3 }

pmSnapshotCurrentEntry OBJECT-TYPE
    SYNTAX      PmSnapshotCurrentEntry
    MAX-ACCESS  not-accessible
    STATUS      current
    DESCRIPTION   "Entry of pmSnapshotCurrentFacilityTable"
    INDEX       {
                  entityFacilityShelfNo,
                  entityFacilitySlotNo,
                  entityFacilityPortNo,
                  entityFacilityExtNo,
                  entityFacilityClassName
                }
    ::=  { pmSnapshotCurrentTable 1 }

PmSnapshotCurrentEntry ::=  SEQUENCE
  { pmSnapshotCurrentOutputPower Integer32,
    pmSnapshotCurrentInputPower Integer32,
    pmSnapshotCurrentAttenuation Integer32,
    pmSnapshotCurrentAttenOfVoa Unsigned32,
    pmSnapshotCurrentOscGain Unsigned32,
    pmSnapshotCurrentBckreflecPwrRx Integer32,
    pmSnapshotCurrentRamanPumpPower Integer32,
    pmSnapshotCurrentOscPwrReceived Integer32,
    pmSnapshotCurrentVariableGain Unsigned32,
    pmSnapshotCurrentTxLineAtten Integer32,
    pmSnapshotCurrentRxLineAtten Integer32 }

pmSnapshotCurrentOutputPower OBJECT-TYPE
    SYNTAX      Integer32
    UNITS       "0.1 dBm"
    MAX-ACCESS  read-only
    STATUS      current
    DESCRIPTION   "Instantaneous Optical Power Transmitted (Output)."
    ::=  { pmSnapshotCurrentEntry 1 }

pmSnapshotCurrentInputPower OBJECT-TYPE
    SYNTAX      Integer32
    UNITS       "0.1 dBm"
    MAX-ACCESS  read-only
    STATUS      current
    DESCRIPTION   "Total Optical Input Power Received."
    ::=  { pmSnapshotCurrentEntry 2 }

pmSnapshotCurrentAttenuation OBJECT-TYPE
    SYNTAX      Integer32
    UNITS       "0.1 dB"
    MAX-ACCESS  read-only
    STATUS      current
    DESCRIPTION   "The attenuation in dB from the TRMT of the 1st stage to the RCV of the 2nd stage.'"
    ::=  { pmSnapshotCurrentEntry 3 }

pmSnapshotCurrentAttenOfVoa OBJECT-TYPE
    SYNTAX      Unsigned32
    UNITS       "0.1 dB"
    MAX-ACCESS  read-only
    STATUS      current
    DESCRIPTION   "The attenuation of VOA in dB."
    ::=  { pmSnapshotCurrentEntry 4 }

pmSnapshotCurrentOscGain OBJECT-TYPE
    SYNTAX      Unsigned32
    UNITS       "0.1 dB"
    MAX-ACCESS  read-only
    STATUS      current
    DESCRIPTION   "Current Raman OSC gain."
    ::=  { pmSnapshotCurrentEntry 5 }

pmSnapshotCurrentBckreflecPwrRx OBJECT-TYPE
    SYNTAX      Integer32
    UNITS       "0.1 dB"
    MAX-ACCESS  read-only
    STATUS      current
    DESCRIPTION   "Backreflection Received Current."
    ::=  { pmSnapshotCurrentEntry 6 }

pmSnapshotCurrentRamanPumpPower OBJECT-TYPE
    SYNTAX      Integer32
    UNITS       "0.1 dBm"
    MAX-ACCESS  read-only
    STATUS      current
    DESCRIPTION   "Total raman pump power."
    ::=  { pmSnapshotCurrentEntry 7 }

pmSnapshotCurrentOscPwrReceived OBJECT-TYPE
    SYNTAX      Integer32
    UNITS       "0.1 dBm"
    MAX-ACCESS  read-only
    STATUS      current
    DESCRIPTION   "Optical Supervisory Channel Input Power Received Current."
    ::=  { pmSnapshotCurrentEntry 8 }

pmSnapshotCurrentVariableGain OBJECT-TYPE
    SYNTAX      Unsigned32
    UNITS       "0.1 dB"
    MAX-ACCESS  read-only
    STATUS      current
    DESCRIPTION   "Variable Gain of EDFA."
    ::=  { pmSnapshotCurrentEntry 9 }

pmSnapshotCurrentTxLineAtten OBJECT-TYPE
    SYNTAX      Integer32
    UNITS       "0.1 dB"
    MAX-ACCESS  read-only
    STATUS      current
    DESCRIPTION   "Attenuation on Transmit Fiber."
    ::=  { pmSnapshotCurrentEntry 10 }

pmSnapshotCurrentRxLineAtten OBJECT-TYPE
    SYNTAX      Integer32
    UNITS       "0.1 dB"
    MAX-ACCESS  read-only
    STATUS      current
    DESCRIPTION   "Instantaneous Attenuation on Receive Fiber."
    ::=  { pmSnapshotCurrentEntry 11 }

pmSnapshotHistoricalTable OBJECT-TYPE
    SYNTAX      SEQUENCE OF PmSnapshotHistoricalEntry
    MAX-ACCESS  not-accessible
    STATUS      current
    DESCRIPTION   "pmSnapshotHistoricalFacilityTable"
    ::=  { pmSnapshot 4 }

pmSnapshotHistoricalEntry OBJECT-TYPE
    SYNTAX      PmSnapshotHistoricalEntry
    MAX-ACCESS  not-accessible
    STATUS      current
    DESCRIPTION   "Entry of pmSnapshotHistoricalFacilityTable"
    INDEX       {
                  pmSnapshotHistoricalParameter,
                  entityFacilityShelfNo,
                  entityFacilitySlotNo,
                  entityFacilityPortNo,
                  entityFacilityExtNo,
                  entityFacilityClassName,
                  pmSnapshotHistoricalNumber
                }
    ::=  { pmSnapshotHistoricalTable 1 }

PmSnapshotHistoricalEntry ::=  SEQUENCE
  { pmSnapshotHistoricalParameter FspR7PmSnapshotParameterTypes,
    pmSnapshotHistoricalNumber Unsigned32,
    pmSnapshotHistoricalValue Integer32,
    pmSnapshotHistoricalValidFlag TruthValue,
    pmSnapshotHistoricalTimeStamp DateAndTime }

pmSnapshotHistoricalParameter OBJECT-TYPE
    SYNTAX      FspR7PmSnapshotParameterTypes
    MAX-ACCESS  not-accessible
    STATUS      current
    DESCRIPTION   "Index representing the PM parameter"
    ::=  { pmSnapshotHistoricalEntry 1 }

pmSnapshotHistoricalNumber OBJECT-TYPE
    SYNTAX      Unsigned32 (1..10)
    MAX-ACCESS  not-accessible
    STATUS      current
    DESCRIPTION   "Record number of optical power reference level."
    ::=  { pmSnapshotHistoricalEntry 2 }

pmSnapshotHistoricalValue OBJECT-TYPE
    SYNTAX      Integer32
    UNITS       "0.1"
    MAX-ACCESS  read-only
    STATUS      current
    DESCRIPTION   "Different units are used for specific parameters (intervalPmSnapshotParameter - the first index of the table):
         'dBm' for OutputPower, InputPower, RamanPumpPower, OscPowerReceived;
         'dB' for Attenuation, AttenuationOfVoa, OscGain, BackreflectionPowerReceived, TxLineAttenuation, RxLineAttenuation;
         'no unit' for VariableGain."
    ::=  { pmSnapshotHistoricalEntry 3 }

pmSnapshotHistoricalValidFlag OBJECT-TYPE
    SYNTAX      TruthValue
    MAX-ACCESS  read-only
    STATUS      current
    DESCRIPTION   "Valid Flag."
    ::=  { pmSnapshotHistoricalEntry 4 }

pmSnapshotHistoricalTimeStamp OBJECT-TYPE
    SYNTAX      DateAndTime
    MAX-ACCESS  read-only
    STATUS      current
    DESCRIPTION   "Timestamp."
    ::=  { pmSnapshotHistoricalEntry 5 }

pmSnapshotCurrentTerminPointTable OBJECT-TYPE
    SYNTAX      SEQUENCE OF PmSnapshotCurrentTerminPointEntry
    MAX-ACCESS  not-accessible
    STATUS      deprecated
    DESCRIPTION   "pmSnapshotCurrentTerminPointTable"
    ::=  { pmSnapshot 5 }

pmSnapshotCurrentTerminPointEntry OBJECT-TYPE
    SYNTAX      PmSnapshotCurrentTerminPointEntry
    MAX-ACCESS  not-accessible
    STATUS      deprecated
    DESCRIPTION   "Entry of pmSnapshotCurrentTerminPointTable"
    INDEX       {
                  entityTerminPointIndexNo1,
                  entityTerminPointIndexNo2,
                  entityTerminPointIndexNo3,
                  entityTerminPointIndexNo4,
                  entityTerminPointClassName
                }
    ::=  { pmSnapshotCurrentTerminPointTable 1 }

PmSnapshotCurrentTerminPointEntry ::=  SEQUENCE
  { pmSnapshotCurrentTerminPointOutputPower Integer32,
    pmSnapshotCurrentTerminPointInputPower Integer32,
    pmSnapshotCurrentTerminPointFiberConnAtten Integer32 }

pmSnapshotCurrentTerminPointOutputPower OBJECT-TYPE
    SYNTAX      Integer32
    UNITS       "0.1 dBm"
    MAX-ACCESS  read-only
    STATUS      deprecated
    DESCRIPTION   "Instantaneous Optical Power Transmitted (Output)."
    ::=  { pmSnapshotCurrentTerminPointEntry 1 }

pmSnapshotCurrentTerminPointInputPower OBJECT-TYPE
    SYNTAX      Integer32
    UNITS       "0.1 dBm"
    MAX-ACCESS  read-only
    STATUS      deprecated
    DESCRIPTION   "Total Optical Input Power Received."
    ::=  { pmSnapshotCurrentTerminPointEntry 2 }

pmSnapshotCurrentTerminPointFiberConnAtten OBJECT-TYPE
    SYNTAX      Integer32
    UNITS       "0.1 dB"
    MAX-ACCESS  read-only
    STATUS      deprecated
    DESCRIPTION   "Fiber Connection Attenuation."
    ::=  { pmSnapshotCurrentTerminPointEntry 3 }

pmSnapshotHistoricalTerminPointTable OBJECT-TYPE
    SYNTAX      SEQUENCE OF PmSnapshotHistoricalTerminPointEntry
    MAX-ACCESS  not-accessible
    STATUS      deprecated
    DESCRIPTION   "pmSnapshotHistoricalTerminPointTable"
    ::=  { pmSnapshot 6 }

pmSnapshotHistoricalTerminPointEntry OBJECT-TYPE
    SYNTAX      PmSnapshotHistoricalTerminPointEntry
    MAX-ACCESS  not-accessible
    STATUS      deprecated
    DESCRIPTION   "Entry of pmSnapshotHistoricalTerminPointTable"
    INDEX       {
                  pmSnapshotHistoricalTerminPointParameter,
                  entityTerminPointIndexNo1,
                  entityTerminPointIndexNo2,
                  entityTerminPointIndexNo3,
                  entityTerminPointIndexNo4,
                  entityTerminPointClassName,
                  pmSnapshotHistoricalTerminPointNumber
                }
    ::=  { pmSnapshotHistoricalTerminPointTable 1 }

PmSnapshotHistoricalTerminPointEntry ::=  SEQUENCE
  { pmSnapshotHistoricalTerminPointParameter FspR7PmSnapshotParameterTypes,
    pmSnapshotHistoricalTerminPointNumber Unsigned32,
    pmSnapshotHistoricalTerminPointValue Integer32,
    pmSnapshotHistoricalTerminPointValidFlag TruthValue,
    pmSnapshotHistoricalTerminPointTimeStamp DateAndTime }

pmSnapshotHistoricalTerminPointParameter OBJECT-TYPE
    SYNTAX      FspR7PmSnapshotParameterTypes
    MAX-ACCESS  not-accessible
    STATUS      deprecated
    DESCRIPTION   "Index representing the PM parameter"
    ::=  { pmSnapshotHistoricalTerminPointEntry 1 }

pmSnapshotHistoricalTerminPointNumber OBJECT-TYPE
    SYNTAX      Unsigned32 (1..10)
    MAX-ACCESS  not-accessible
    STATUS      deprecated
    DESCRIPTION   "Record number of optical power reference level."
    ::=  { pmSnapshotHistoricalTerminPointEntry 2 }

pmSnapshotHistoricalTerminPointValue OBJECT-TYPE
    SYNTAX      Integer32
    UNITS       "0.1"
    MAX-ACCESS  read-only
    STATUS      deprecated
    DESCRIPTION   "Different units are used for specific parameters (intervalPmSnapshotParameter - the first index of the table):
         'dBm' for OutputPower, InputPower, RamanPumpPower, OscPowerReceived;
         'dB' for Attenuation, AttenuationOfVoa, OscGain, BackreflectionPowerReceived, TxLineAttenuation, RxLineAttenuation;
         'no unit' for VariableGain."
    ::=  { pmSnapshotHistoricalTerminPointEntry 3 }

pmSnapshotHistoricalTerminPointValidFlag OBJECT-TYPE
    SYNTAX      TruthValue
    MAX-ACCESS  read-only
    STATUS      deprecated
    DESCRIPTION   "Valid Flag."
    ::=  { pmSnapshotHistoricalTerminPointEntry 4 }

pmSnapshotHistoricalTerminPointTimeStamp OBJECT-TYPE
    SYNTAX      DateAndTime
    MAX-ACCESS  read-only
    STATUS      deprecated
    DESCRIPTION   "Timestamp."
    ::=  { pmSnapshotHistoricalTerminPointEntry 5 }

endOfPmSnampshot OBJECT-TYPE
    SYNTAX      Integer32
    MAX-ACCESS  read-only
    STATUS      current
    DESCRIPTION
        ""
    ::=  { pmSnapshot 10000 }

externalPortTable OBJECT-TYPE
    SYNTAX      SEQUENCE OF ExternalPortEntry
    MAX-ACCESS  not-accessible
    STATUS      current
    DESCRIPTION   "externalPort"
    ::=  { eci 1 }

externalPortEntry OBJECT-TYPE
    SYNTAX      ExternalPortEntry
    MAX-ACCESS  not-accessible
    STATUS      current
    DESCRIPTION   "Entry of externalPort"
    INDEX       {
                  entityExternalPortShelfNo,
                  entityExternalPortSlotNo,
                  entityExternalPortPortNo,
                  entityExternalPortExtNo,
                  entityExternalPortClassName
                }
    ::=  { externalPortTable 1 }

ExternalPortEntry ::=  SEQUENCE
  { externalPortRowStatus RowStatus,
    externalPortConnectionState FspR7ConnectState,
    externalPortType FspR7InterfaceType,
    externalPortTransmitChannel FspR7ChannelIdentifier,
    externalPortChannelBandwith FspR7ChannelBandwidth,
    externalPortAlias SnmpAdminString,
    externalPortFarEndLocation SnmpAdminString,
    externalPortBitrate Unsigned32,
    externalPortFecType FspR7FecType,
    externalPortLineCoding FspR7LineCoding,
    externalPortFrameFormat FspR7FrameFormat,
    externalPortOpticalPowerTx Integer32,
    externalPortOsnrTransmit Unsigned32,
    externalPortPmdTransmit Unsigned32,
    externalPortChromDisperTx Integer32,
    externalPortMinOsnrRcv Unsigned32,
    externalPortMinOptPowerRcv Integer32,
    externalPortMaxOptPowerRcv Integer32,
    externalPortMaxPmdRcv Unsigned32,
    externalPortMinChromDisperRcv Integer32,
    externalPortMaxChromDisperRcv Integer32,
    externalPortMaxBitErrorRate FspR7MaxBitErrorRate,
    externalPortSourceProfile SnmpAdminString,
    externalPortSecondaryStates FspR7EntitySecondaryStates }

externalPortRowStatus OBJECT-TYPE
    SYNTAX      RowStatus
    MAX-ACCESS  read-create
    STATUS      current
    DESCRIPTION   "RowStatus object is used to create or delete a row in the table."
    ::=  { externalPortEntry 1 }

externalPortConnectionState OBJECT-TYPE
    SYNTAX      FspR7ConnectState
    MAX-ACCESS  read-only
    STATUS      current
    DESCRIPTION
        "Connection State"
    ::=  { externalPortEntry 2 }

externalPortType OBJECT-TYPE
    SYNTAX      FspR7InterfaceType
    MAX-ACCESS  read-create
    STATUS      current
    DESCRIPTION
        "The TYPE defines the transport service type as wrapper with wrapper layer termination OR else as payload"
    ::=  { externalPortEntry 3 }

externalPortTransmitChannel OBJECT-TYPE
    SYNTAX      FspR7ChannelIdentifier
    MAX-ACCESS  read-create
    STATUS      current
    DESCRIPTION
        "Channel"
    ::=  { externalPortEntry 4 }

externalPortChannelBandwith OBJECT-TYPE
    SYNTAX      FspR7ChannelBandwidth
    MAX-ACCESS  read-create
    STATUS      current
    DESCRIPTION
        "Channel Bandwidth"
    ::=  { externalPortEntry 5 }

externalPortAlias OBJECT-TYPE
    SYNTAX      SnmpAdminString
    MAX-ACCESS  read-create
    STATUS      current
    DESCRIPTION
        "User Applied Descriptor"
    ::=  { externalPortEntry 6 }

externalPortFarEndLocation OBJECT-TYPE
    SYNTAX      SnmpAdminString
    MAX-ACCESS  read-create
    STATUS      current
    DESCRIPTION
        "FEND Location"
    ::=  { externalPortEntry 7 }

externalPortBitrate OBJECT-TYPE
    SYNTAX      Unsigned32
    UNITS       "Mbps"
    MAX-ACCESS  read-create
    STATUS      current
    DESCRIPTION
        "Derived from TYPE"
    ::=  { externalPortEntry 8 }

externalPortFecType OBJECT-TYPE
    SYNTAX      FspR7FecType
    MAX-ACCESS  read-create
    STATUS      current
    DESCRIPTION
        "Forward Error Correction (Only relevant where TYPE = OTU#)"
    ::=  { externalPortEntry 9 }

externalPortLineCoding OBJECT-TYPE
    SYNTAX      FspR7LineCoding
    MAX-ACCESS  read-create
    STATUS      current
    DESCRIPTION
        "Line Coding"
    ::=  { externalPortEntry 10 }

externalPortFrameFormat OBJECT-TYPE
    SYNTAX      FspR7FrameFormat
    MAX-ACCESS  read-create
    STATUS      current
    DESCRIPTION
        "Frame Format"
    ::=  { externalPortEntry 11 }

externalPortOpticalPowerTx OBJECT-TYPE
    SYNTAX      Integer32 (-9900..600)
    UNITS       "0.1 dBm"
    MAX-ACCESS  read-create
    STATUS      current
    DESCRIPTION
        "Optical Power Transmit"
    ::=  { externalPortEntry 12 }

externalPortOsnrTransmit OBJECT-TYPE
    SYNTAX      Unsigned32 (0..58)
    UNITS       "dB"
    MAX-ACCESS  read-create
    STATUS      current
    DESCRIPTION
        "Optical Signal to Noise Ratio Transmit"
    ::=  { externalPortEntry 13 }

externalPortPmdTransmit OBJECT-TYPE
    SYNTAX      Unsigned32 (0..30)
    UNITS       "ps"
    MAX-ACCESS  read-create
    STATUS      current
    DESCRIPTION
        "Polarization Mode Dispersion Transmit"
    ::=  { externalPortEntry 14 }

externalPortChromDisperTx OBJECT-TYPE
    SYNTAX      Integer32 (-60000..60000)
    UNITS       "ps/nm"
    MAX-ACCESS  read-create
    STATUS      current
    DESCRIPTION
        "Chromatic Dispersion Transmit"
    ::=  { externalPortEntry 15 }

externalPortMinOsnrRcv OBJECT-TYPE
    SYNTAX      Unsigned32 (10..58)
    UNITS       "dB"
    MAX-ACCESS  read-create
    STATUS      current
    DESCRIPTION
        "Minimum Optical Signal to Noise Ratio, Rcv"
    ::=  { externalPortEntry 16 }

externalPortMinOptPowerRcv OBJECT-TYPE
    SYNTAX      Integer32 (-2500..0)
    UNITS       "0.1 dBm"
    MAX-ACCESS  read-create
    STATUS      current
    DESCRIPTION
        "Minimum Optical Pwr Rcv"
    ::=  { externalPortEntry 17 }

externalPortMaxOptPowerRcv OBJECT-TYPE
    SYNTAX      Integer32 (-1000..1000)
    UNITS       "0.1 dBm"
    MAX-ACCESS  read-create
    STATUS      current
    DESCRIPTION
        "Maximum Optical Pwr Rcv"
    ::=  { externalPortEntry 18 }

externalPortMaxPmdRcv OBJECT-TYPE
    SYNTAX      Unsigned32 (0..30)
    UNITS       "ps"
    MAX-ACCESS  read-create
    STATUS      current
    DESCRIPTION
        "Maximum Polarization Mode Dispersion Rcv"
    ::=  { externalPortEntry 19 }

externalPortMinChromDisperRcv OBJECT-TYPE
    SYNTAX      Integer32 (-60000..60000)
    UNITS       "ps/nm"
    MAX-ACCESS  read-create
    STATUS      current
    DESCRIPTION
        "Minimum Chromatic Dispersion Rcv"
    ::=  { externalPortEntry 20 }

externalPortMaxChromDisperRcv OBJECT-TYPE
    SYNTAX      Integer32 (-60000..60000)
    UNITS       "ps/nm"
    MAX-ACCESS  read-create
    STATUS      current
    DESCRIPTION
        "Maximum Chromatic Dispersion Rcv"
    ::=  { externalPortEntry 21 }

externalPortMaxBitErrorRate OBJECT-TYPE
    SYNTAX      FspR7MaxBitErrorRate
    MAX-ACCESS  read-create
    STATUS      current
    DESCRIPTION
        "Maximum Bit Error Rate"
    ::=  { externalPortEntry 22 }

externalPortSourceProfile OBJECT-TYPE
    SYNTAX      SnmpAdminString
    MAX-ACCESS  read-create
    STATUS      current
    DESCRIPTION
        "File Name"
    ::=  { externalPortEntry 23 }

externalPortSecondaryStates OBJECT-TYPE
    SYNTAX      FspR7EntitySecondaryStates
    MAX-ACCESS  read-only
    STATUS      current
    DESCRIPTION
        "Secondary States"
    ::=  { externalPortEntry 24 }

endOfEci OBJECT-TYPE
    SYNTAX      Integer32
    MAX-ACCESS  read-only
    STATUS      current
    DESCRIPTION
        ""
    ::=  { eci 10000 }

channelTracesTable OBJECT-TYPE
    SYNTAX      SEQUENCE OF ChannelTracesEntry
    MAX-ACCESS  not-accessible
    STATUS      current
    DESCRIPTION   "newNodeChannelTrace"
    ::=  { serviceDiagnostics 1 }

channelTracesEntry OBJECT-TYPE
    SYNTAX      ChannelTracesEntry
    MAX-ACCESS  not-accessible
    STATUS      current
    DESCRIPTION   "Entry of newNodeChannelTrace"
    INDEX       {
                  channelTracesIndexNo1,
                  channelTracesIndexNo2,
                  channelTracesIndexNo3,
                  channelTracesIndexNo4,
                  channelTracesClassName,
                  channelTracesChannelNumber,
                  channelTracesRouteId,
                  channelTracesElementId
                }
    ::=  { channelTracesTable 1 }

ChannelTracesEntry ::=  SEQUENCE
  { channelTracesIndexNo1 Unsigned32,
    channelTracesIndexNo2 Unsigned32,
    channelTracesIndexNo3 Unsigned32,
    channelTracesIndexNo4 Unsigned32,
    channelTracesClassName EntityClassName,
    channelTracesChannelNumber FspR7ChannelNumber,
    channelTracesRouteId FspR7NCTraceId,
    channelTracesElementId Unsigned32,
    channelTracesFromAid SnmpAdminString,
    channelTracesToAid SnmpAdminString,
    channelTracesRouteType FspR7NCTRouteType,
    channelTracesChannelRx FspR7ChannelNumber,
    channelTracesChannelTx FspR7ChannelNumber }

channelTracesIndexNo1 OBJECT-TYPE
    SYNTAX      Unsigned32
    MAX-ACCESS  not-accessible
    STATUS      current
    DESCRIPTION   "Adress index."
    ::=  { channelTracesEntry 1 }

channelTracesIndexNo2 OBJECT-TYPE
    SYNTAX      Unsigned32
    MAX-ACCESS  not-accessible
    STATUS      current
    DESCRIPTION   "Adress index."
    ::=  { channelTracesEntry 2 }

channelTracesIndexNo3 OBJECT-TYPE
    SYNTAX      Unsigned32
    MAX-ACCESS  not-accessible
    STATUS      current
    DESCRIPTION   "Adress index."
    ::=  { channelTracesEntry 3 }

channelTracesIndexNo4 OBJECT-TYPE
    SYNTAX      Unsigned32
    MAX-ACCESS  not-accessible
    STATUS      current
    DESCRIPTION   "Adress index."
    ::=  { channelTracesEntry 4 }

channelTracesClassName OBJECT-TYPE
    SYNTAX      EntityClassName
    MAX-ACCESS  not-accessible
    STATUS      current
    DESCRIPTION   "Entity Class Name."
    ::=  { channelTracesEntry 5 }

channelTracesChannelNumber OBJECT-TYPE
    SYNTAX      FspR7ChannelNumber
    MAX-ACCESS  not-accessible
    STATUS      current
    DESCRIPTION   "Channel Number"
    ::=  { channelTracesEntry 6 }

channelTracesRouteId OBJECT-TYPE
    SYNTAX      FspR7NCTraceId
    MAX-ACCESS  not-accessible
    STATUS      current
    DESCRIPTION   "Route ID"
    ::=  { channelTracesEntry 7 }

channelTracesElementId OBJECT-TYPE
    SYNTAX      Unsigned32
    MAX-ACCESS  not-accessible
    STATUS      current
    DESCRIPTION   "Route element ID"
    ::=  { channelTracesEntry 8 }

channelTracesFromAid OBJECT-TYPE
    SYNTAX      SnmpAdminString
    MAX-ACCESS  read-only
    STATUS      current
    DESCRIPTION
        "AID FROM represented as string"
    ::=  { channelTracesEntry 9 }

channelTracesToAid OBJECT-TYPE
    SYNTAX      SnmpAdminString
    MAX-ACCESS  read-only
    STATUS      current
    DESCRIPTION
        "AID TO represented as string"
    ::=  { channelTracesEntry 10 }

channelTracesRouteType OBJECT-TYPE
    SYNTAX      FspR7NCTRouteType
    MAX-ACCESS  read-only
    STATUS      current
    DESCRIPTION   "FspR7NCTRouteType Textual-Convention indicates the connection type between two ports.
         If a connection between the two ports is within a module (i.e. Client to Network port),
         the Route-Type is either provisioned(6) of fixed ( equipment(5) ). If the connection
         is between two modules ports, then the Route-Type is fiber(2), cable(3) or backPlane(4).
        "
    ::=  { channelTracesEntry 11 }

channelTracesChannelRx OBJECT-TYPE
    SYNTAX      FspR7ChannelNumber
    MAX-ACCESS  read-only
    STATUS      current
    DESCRIPTION
        "Channel Number for the Receive Interface"
    ::=  { channelTracesEntry 12 }

channelTracesChannelTx OBJECT-TYPE
    SYNTAX      FspR7ChannelNumber
    MAX-ACCESS  read-only
    STATUS      current
    DESCRIPTION
        "Channel Number for the Transmit Interface"
    ::=  { channelTracesEntry 13 }

endOfchannelTracesTable OBJECT-TYPE
    SYNTAX      Integer32
    MAX-ACCESS  read-only
    STATUS      current
    DESCRIPTION
        ""
    ::=  { serviceDiagnostics 2 }

ratFrom OBJECT-TYPE
    SYNTAX      SnmpAdminString
    MAX-ACCESS  read-write
    STATUS      current
    DESCRIPTION
        "FROM-end of equipment connection (jumper). FROM direction is significant only for 1WAY connections."
    ::=  { serviceDiagnostics 3 }

ratTo OBJECT-TYPE
    SYNTAX      SnmpAdminString
    MAX-ACCESS  read-write
    STATUS      current
    DESCRIPTION
        "TO-end of equipment connection (jumper). TO direction is signaificant only for 1WAY"
    ::=  { serviceDiagnostics 4 }

ratChIngress OBJECT-TYPE
    SYNTAX      FspR7ChannelNumber
    MAX-ACCESS  read-write
    STATUS      current
    DESCRIPTION
        "Channel"
    ::=  { serviceDiagnostics 5 }

ratChEgress OBJECT-TYPE
    SYNTAX      FspR7ChannelNumber
    MAX-ACCESS  read-write
    STATUS      current
    DESCRIPTION
        "Channel"
    ::=  { serviceDiagnostics 6 }

ratSuperChannel OBJECT-TYPE
    SYNTAX      FspR7NoYes
    MAX-ACCESS  read-write
    STATUS      current
    DESCRIPTION
        "Super Channel Support"
    ::=  { serviceDiagnostics 7 }

ratSuperChannelFq OBJECT-TYPE
    SYNTAX      FspR7ChannelIdentifier
    MAX-ACCESS  read-write
    STATUS      current
    DESCRIPTION
        "Lane Channel Setting"
    ::=  { serviceDiagnostics 8 }

ratStartPointTable OBJECT-TYPE
    SYNTAX      SEQUENCE OF RatStartPointEntry
    MAX-ACCESS  not-accessible
    STATUS      current
    DESCRIPTION   "ratStartPoint"
    ::=  { serviceDiagnostics 10 }

ratStartPointEntry OBJECT-TYPE
    SYNTAX      RatStartPointEntry
    MAX-ACCESS  not-accessible
    STATUS      current
    DESCRIPTION   "Entry of ratStartPoint"
    INDEX       {
                  ratStartPointIndexNo1,
                  ratStartPointIndexNo2,
                  ratStartPointIndexNo3,
                  ratStartPointIndexNo4,
                  ratStartPointClassName
                }
    ::=  { ratStartPointTable 1 }

RatStartPointEntry ::=  SEQUENCE
  { ratStartPointIndexNo1 Unsigned32,
    ratStartPointIndexNo2 Unsigned32,
    ratStartPointIndexNo3 Unsigned32,
    ratStartPointIndexNo4 Unsigned32,
    ratStartPointClassName EntityClassName,
    ratStartPointAidString SnmpAdminString,
    ratStartPointTableId RowPointer,
    ratStartPointChannelNumber FspR7ChannelNumberCaps,
    ratStartPointChannelGroup FspR7ChannelIdentifierCaps,
    ratStartPointClass EntityClass }

ratStartPointIndexNo1 OBJECT-TYPE
    SYNTAX      Unsigned32
    MAX-ACCESS  not-accessible
    STATUS      current
    DESCRIPTION   "Adress index."
    ::=  { ratStartPointEntry 1 }

ratStartPointIndexNo2 OBJECT-TYPE
    SYNTAX      Unsigned32
    MAX-ACCESS  not-accessible
    STATUS      current
    DESCRIPTION   "Adress index."
    ::=  { ratStartPointEntry 2 }

ratStartPointIndexNo3 OBJECT-TYPE
    SYNTAX      Unsigned32
    MAX-ACCESS  not-accessible
    STATUS      current
    DESCRIPTION   "Adress index."
    ::=  { ratStartPointEntry 3 }

ratStartPointIndexNo4 OBJECT-TYPE
    SYNTAX      Unsigned32
    MAX-ACCESS  not-accessible
    STATUS      current
    DESCRIPTION   "Adress index."
    ::=  { ratStartPointEntry 4 }

ratStartPointClassName OBJECT-TYPE
    SYNTAX      EntityClassName
    MAX-ACCESS  not-accessible
    STATUS      current
    DESCRIPTION
        "Entity Class Name"
    ::=  { ratStartPointEntry 5 }

ratStartPointAidString OBJECT-TYPE
    SYNTAX      SnmpAdminString
    MAX-ACCESS  read-only
    STATUS      current
    DESCRIPTION   "Aid string of entity."
    ::=  { ratStartPointEntry 6 }

ratStartPointTableId OBJECT-TYPE
    SYNTAX      RowPointer
    MAX-ACCESS  read-only
    STATUS      current
    DESCRIPTION   "RowPointer to the dependent entity."
    ::=  { ratStartPointEntry 7 }

ratStartPointChannelNumber OBJECT-TYPE
    SYNTAX      FspR7ChannelNumberCaps
    MAX-ACCESS  read-only
    STATUS      current
    DESCRIPTION   "Channel Number"
    ::=  { ratStartPointEntry 8 }

ratStartPointChannelGroup OBJECT-TYPE
    SYNTAX      FspR7ChannelIdentifierCaps
    MAX-ACCESS  read-only
    STATUS      current
    DESCRIPTION   "Channel Group Number"
    ::=  { ratStartPointEntry 9 }

ratStartPointClass OBJECT-TYPE
    SYNTAX      EntityClass
    MAX-ACCESS  read-only
    STATUS      current
    DESCRIPTION   "EntityClass"
    ::=  { ratStartPointEntry 10 }

endOfRatStartPointTable OBJECT-TYPE
    SYNTAX      Integer32
    MAX-ACCESS  read-only
    STATUS      current
    DESCRIPTION
        ""
    ::=  { serviceDiagnostics 11 }

ratAnalyzerTable OBJECT-TYPE
    SYNTAX      SEQUENCE OF RatAnalyzerEntry
    MAX-ACCESS  not-accessible
    STATUS      current
    DESCRIPTION   "resourceAnalyzer"
    ::=  { serviceDiagnostics 12 }

ratAnalyzerEntry OBJECT-TYPE
    SYNTAX      RatAnalyzerEntry
    MAX-ACCESS  not-accessible
    STATUS      current
    DESCRIPTION   "Entry of resourceAnalyzer"
    INDEX       {
                  ratAnalyzerRouteId,
                  ratAnalyzerElementId
                }
    ::=  { ratAnalyzerTable 1 }

RatAnalyzerEntry ::=  SEQUENCE
  { ratAnalyzerRouteId Unsigned32,
    ratAnalyzerElementId Unsigned32,
    ratAnalyzerFromAid SnmpAdminString,
    ratAnalyzerToAid SnmpAdminString,
    ratAnalyzerChannelTx FspR7ChannelNumber,
    ratAnalyzerState FspR7StateConnection,
    ratAnalyzerRouteType FspR7NCTRouteType }

ratAnalyzerRouteId OBJECT-TYPE
    SYNTAX      Unsigned32
    MAX-ACCESS  not-accessible
    STATUS      current
    DESCRIPTION   "Route ID"
    ::=  { ratAnalyzerEntry 1 }

ratAnalyzerElementId OBJECT-TYPE
    SYNTAX      Unsigned32
    MAX-ACCESS  not-accessible
    STATUS      current
    DESCRIPTION   "Route element ID"
    ::=  { ratAnalyzerEntry 2 }

ratAnalyzerFromAid OBJECT-TYPE
    SYNTAX      SnmpAdminString
    MAX-ACCESS  read-only
    STATUS      current
    DESCRIPTION
        "FROM-end of equipment connection (jumper). FROM direction is significant only for 1WAY connections."
    ::=  { ratAnalyzerEntry 3 }

ratAnalyzerToAid OBJECT-TYPE
    SYNTAX      SnmpAdminString
    MAX-ACCESS  read-only
    STATUS      current
    DESCRIPTION
        "TO-end of equipment connection (jumper). TO direction is signaificant only for 1WAY"
    ::=  { ratAnalyzerEntry 4 }

ratAnalyzerChannelTx OBJECT-TYPE
    SYNTAX      FspR7ChannelNumber
    MAX-ACCESS  read-only
    STATUS      current
    DESCRIPTION
        "Channel Number for the Transmit Interface"
    ::=  { ratAnalyzerEntry 5 }

ratAnalyzerState OBJECT-TYPE
    SYNTAX      FspR7StateConnection
    MAX-ACCESS  read-only
    STATUS      current
    DESCRIPTION
        "State of the Physical Connection"
    ::=  { ratAnalyzerEntry 6 }

ratAnalyzerRouteType OBJECT-TYPE
    SYNTAX      FspR7NCTRouteType
    MAX-ACCESS  read-only
    STATUS      current
    DESCRIPTION   "FspR7NCTRouteType Textual-Convention indicates the connection type between two ports.
         If a connection between the two ports is within a module (i.e. Client to Network port),
         the Route-Type is either provisioned(6) of fixed ( equipment(5) ). If the connection
         is between two modules ports, then the Route-Type is fiber(2), cable(3) or backPlane(4).
        "
    ::=  { ratAnalyzerEntry 7 }

endOfRatAnalyzerTable OBJECT-TYPE
    SYNTAX      Integer32
    MAX-ACCESS  read-only
    STATUS      current
    DESCRIPTION
        ""
    ::=  { serviceDiagnostics 13 }

ratBlockingTable OBJECT-TYPE
    SYNTAX      SEQUENCE OF RatBlockingEntry
    MAX-ACCESS  not-accessible
    STATUS      current
    DESCRIPTION   "ratBlocking"
    ::=  { serviceDiagnostics 14 }

ratBlockingEntry OBJECT-TYPE
    SYNTAX      RatBlockingEntry
    MAX-ACCESS  not-accessible
    STATUS      current
    DESCRIPTION   "Entry of ratBlocking"
    INDEX       {
                  ratBlockingElementId
                }
    ::=  { ratBlockingTable 1 }

RatBlockingEntry ::=  SEQUENCE
  { ratBlockingElementId Unsigned32,
    ratBlockingType FspR7EquipmentType,
    ratBlockingConnState FspR7ConnectState,
    ratBlockingAid SnmpAdminString }

ratBlockingElementId OBJECT-TYPE
    SYNTAX      Unsigned32
    MAX-ACCESS  not-accessible
    STATUS      current
    DESCRIPTION   "Element ID"
    ::=  { ratBlockingEntry 1 }

ratBlockingType OBJECT-TYPE
    SYNTAX      FspR7EquipmentType
    MAX-ACCESS  read-only
    STATUS      current
    DESCRIPTION
        "The TYPE of Equipment and the MODE setting determine uniquely the number and allowed TYPE's of the provisionable dependent entities (plugs, interfaces, modules)"
    ::=  { ratBlockingEntry 2 }

ratBlockingConnState OBJECT-TYPE
    SYNTAX      FspR7ConnectState
    MAX-ACCESS  read-only
    STATUS      current
    DESCRIPTION
        "Connection State"
    ::=  { ratBlockingEntry 3 }

ratBlockingAid OBJECT-TYPE
    SYNTAX      SnmpAdminString
    MAX-ACCESS  read-only
    STATUS      current
    DESCRIPTION
        "TL1 Access Identifier"
    ::=  { ratBlockingEntry 4 }

endOfRatBlockingTable OBJECT-TYPE
    SYNTAX      Integer32
    MAX-ACCESS  read-only
    STATUS      current
    DESCRIPTION
        ""
    ::=  { serviceDiagnostics 15 }

endOfserviceDiagnostics OBJECT-TYPE
    SYNTAX      Integer32
    MAX-ACCESS  read-only
    STATUS      current
    DESCRIPTION
        ""
    ::=  { serviceDiagnostics 10000 }

changePhysicalPortServiceTable OBJECT-TYPE
    SYNTAX      SEQUENCE OF ChangePhysicalPortServiceEntry
    MAX-ACCESS  not-accessible
    STATUS      current
    DESCRIPTION   ""
    ::=  { changeService 1 }

changePhysicalPortServiceEntry OBJECT-TYPE
    SYNTAX      ChangePhysicalPortServiceEntry
    MAX-ACCESS  not-accessible
    STATUS      current
    DESCRIPTION   ""
    INDEX       {
                  entityFacilityShelfNo,
                  entityFacilitySlotNo,
                  entityFacilityPortNo,
                  entityFacilityExtNo,
                  entityFacilityClassName
                }
    ::=  { changePhysicalPortServiceTable 1 }

ChangePhysicalPortServiceEntry ::=  SEQUENCE
  { changePhysicalPortServiceRowStatus RowStatus,
    changePhysicalPortServiceType FspR7InterfaceType,
    changePhysicalPortServiceAdmin FspR7AdminState,
    changePhysicalPortServiceAlias SnmpAdminString,
    changePhysicalPortServiceAlsMode FspR7AlsMode,
    changePhysicalPortServiceBehaviour FspR7PortBehaviour,
    changePhysicalPortServiceDispersionSetting Integer32,
    changePhysicalPortServiceDispersionMode FspR7DispersionModes,
    changePhysicalPortServiceChannelProv FspR7ChannelIdentifier,
    changePhysicalPortServiceWdmRxChannel FspR7ChannelIdentifier,
    changePhysicalPortServiceCodeGain FspR7CodeGain,
    changePhysicalPortServiceXfpDecisionThres FspR7XfpDecisionThres,
    changePhysicalPortServiceDisparityCorrection EnableState,
    changePhysicalPortServiceEqlzAdmin FspR7EqlzAdminState,
    changePhysicalPortServiceErrorForwarding FspR7ErrorFwdMode,
    changePhysicalPortServiceFecType FspR7FecType,
    changePhysicalPortServiceFarEndCommunication FspR7YesNo,
    changePhysicalPortServiceFlowControl FspR7FlowControlMode,
    changePhysicalPortServiceLaneChannelSetting FspR7ChannelIdentifier,
    changePhysicalPortServiceLaserDelayTimer FspR7LaserDelayTimer,
    changePhysicalPortServiceLaserOffTimer Unsigned32,
    changePhysicalPortServiceLaserOnTimer Unsigned32,
    changePhysicalPortServiceLaserOffDelayFunction EnableState,
    changePhysicalPortServiceAutoPTassignment FspR7ManualAuto,
    changePhysicalPortServiceTributarySlotMethod FspR7ManualAuto,
    changePhysicalPortServiceOpticalSetPoint Integer32,
    changePhysicalPortServiceOpuPayloadType FspR7OpuPayloadType,
    changePhysicalPortServiceSigDegThresSonetLine FspR7BERThreshold,
    changePhysicalPortServiceSigDegThresSdhMs Unsigned32,
    changePhysicalPortServiceSigDegThresOtu Integer32,
    changePhysicalPortServiceSigDegThresOdu Integer32,
    changePhysicalPortServiceSigDegThreshold Unsigned32,
    changePhysicalPortServiceSigDegPcslThreshold Unsigned32,
    changePhysicalPortServiceSigDegThresSonetSection FspR7BERThresholdSection,
    changePhysicalPortServiceSigDegThresSdhSection Unsigned32,
    changePhysicalPortServiceSigDegThresOduTcmA Integer32,
    changePhysicalPortServiceSigDegThresOduTcmB Integer32,
    changePhysicalPortServiceSigDegThresOduTcmC Integer32,
    changePhysicalPortServiceSignalDegradePeriod Unsigned32,
    changePhysicalPortServiceSigDegPeriodOdu Unsigned32,
    changePhysicalPortServiceSigDegPeriodOtu Unsigned32,
    changePhysicalPortServiceSigDegPeriodIntegration Unsigned32,
    changePhysicalPortServiceSigDegPeriodSdhSection Unsigned32,
    changePhysicalPortServiceSigDegPeriodOduTcmA Unsigned32,
    changePhysicalPortServiceSigDegPeriodOduTcmB Unsigned32,
    changePhysicalPortServiceSigDegPeriodOduTcmC Unsigned32,
    changePhysicalPortServiceOtnStuffing FspR7Stuff,
    changePhysicalPortServiceTcmALevel OtnTcmLevel,
    changePhysicalPortServiceTcmBLevel OtnTcmLevel,
    changePhysicalPortServiceTcmCLevel OtnTcmLevel,
    changePhysicalPortServiceTerminationLevel OhTerminationLevel,
    changePhysicalPortServiceTimingSource SonetTimingSource,
    changePhysicalPortServiceTimModeOdu TimMode,
    changePhysicalPortServiceTimModeOtu TimMode,
    changePhysicalPortServiceTimModeSonetSection TimMode,
    changePhysicalPortServiceTimModeOduTcmA TimMode,
    changePhysicalPortServiceTimModeOduTcmB TimMode,
    changePhysicalPortServiceTimModeOduTcmC TimMode,
    changePhysicalPortServiceTraceFormSonetSection SonetTraceForm,
    changePhysicalPortServiceTraceExpectedSonetSection OCTET STRING,
    changePhysicalPortServiceTraceTransmitSonetSection OCTET STRING,
    changePhysicalPortServiceTraceExpectedOtu OCTET STRING,
    changePhysicalPortServiceTraceTransmitSapiOtu OCTET STRING,
    changePhysicalPortServiceTraceTransmitDapiOtu OCTET STRING,
    changePhysicalPortServiceTraceTransmitOpspOtu OCTET STRING,
    changePhysicalPortServiceTraceExpectedOdu OCTET STRING,
    changePhysicalPortServiceTraceTransmitSapiOdu OCTET STRING,
    changePhysicalPortServiceTraceTransmitDapiOdu OCTET STRING,
    changePhysicalPortServiceTraceTransmitOpspOdu OCTET STRING,
    changePhysicalPortServiceTraceExpectedOduTcmA OCTET STRING,
    changePhysicalPortServiceTraceTransmitSapiOduTcmA OCTET STRING,
    changePhysicalPortServiceTraceTransmitDapiOduTcmA OCTET STRING,
    changePhysicalPortServiceTraceTransmitOpspOduTcmA OCTET STRING,
    changePhysicalPortServiceTraceExpectedOduTcmB OCTET STRING,
    changePhysicalPortServiceTraceTransmitSapiOduTcmB OCTET STRING,
    changePhysicalPortServiceTraceTransmitDapiOduTcmB OCTET STRING,
    changePhysicalPortServiceTraceTransmitOpspOduTcmB OCTET STRING,
    changePhysicalPortServiceTraceExpectedOduTcmC OCTET STRING,
    changePhysicalPortServiceTraceTransmitSapiOduTcmC OCTET STRING,
    changePhysicalPortServiceTraceTransmitDapiOduTcmC OCTET STRING,
    changePhysicalPortServiceTraceTransmitOpspOduTcmC OCTET STRING,
    changePhysicalPortServiceTxOffDelay FspR7EnableDisable,
    changePhysicalPortServiceVoaMode FspR7VoaMode,
    changePhysicalPortServiceVoaSetpoint Unsigned32,
    changePhysicalPortServiceTxOffOnTm FspR7TxOffOnTm,
    changePhysicalPortServiceTxOffTimer Unsigned32,
    changePhysicalPortServiceTxOnTimer Unsigned32 }

changePhysicalPortServiceRowStatus OBJECT-TYPE
    SYNTAX      RowStatus
    MAX-ACCESS  read-create
    STATUS      current
    DESCRIPTION   "RowStatus object is used to create or delete a row in the table."
    ::=  { changePhysicalPortServiceEntry 1 }

changePhysicalPortServiceType OBJECT-TYPE
    SYNTAX      FspR7InterfaceType
    MAX-ACCESS  read-create
    STATUS      current
    DESCRIPTION
        "The TYPE defines the transport service type as wrapper with wrapper layer termination OR else as payload"
    ::=  { changePhysicalPortServiceEntry 2 }

changePhysicalPortServiceAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { changePhysicalPortServiceEntry 3 }

changePhysicalPortServiceAlias OBJECT-TYPE
    SYNTAX      SnmpAdminString
    MAX-ACCESS  read-create
    STATUS      current
    DESCRIPTION
        "User Applied Descriptor"
    ::=  { changePhysicalPortServiceEntry 4 }

changePhysicalPortServiceAlsMode OBJECT-TYPE
    SYNTAX      FspR7AlsMode
    MAX-ACCESS  read-create
    STATUS      current
    DESCRIPTION
        "Determines the reaction in backward direction in response to a LOS
         on the same Interface: on a Network Interface connected to the DWDM
         this is a matter of laser safety"
    ::=  { changePhysicalPortServiceEntry 5 }

changePhysicalPortServiceBehaviour OBJECT-TYPE
    SYNTAX      FspR7PortBehaviour
    MAX-ACCESS  read-create
    STATUS      current
    DESCRIPTION
        "Behavior or Port usage based on configuration/usage in the system regardless of faceplate designation"
    ::=  { changePhysicalPortServiceEntry 6 }

changePhysicalPortServiceDispersionSetting OBJECT-TYPE
    SYNTAX      Integer32 (-50000..50000)
    UNITS       "ps/nm"
    MAX-ACCESS  read-create
    STATUS      current
    DESCRIPTION
        "Chromatic Dispersion Compensation setting on module"
    ::=  { changePhysicalPortServiceEntry 7 }

changePhysicalPortServiceDispersionMode OBJECT-TYPE
    SYNTAX      FspR7DispersionModes
    MAX-ACCESS  read-create
    STATUS      current
    DESCRIPTION
        "Chromatic Dispersion Compensation Mode"
    ::=  { changePhysicalPortServiceEntry 8 }

changePhysicalPortServiceChannelProv OBJECT-TYPE
    SYNTAX      FspR7ChannelIdentifier
    MAX-ACCESS  read-create
    STATUS      current
    DESCRIPTION
        "Channel"
    ::=  { changePhysicalPortServiceEntry 9 }

changePhysicalPortServiceWdmRxChannel OBJECT-TYPE
    SYNTAX      FspR7ChannelIdentifier
    MAX-ACCESS  read-create
    STATUS      current
    DESCRIPTION
        "Configuration of Rx optical channel"
    ::=  { changePhysicalPortServiceEntry 10 }

changePhysicalPortServiceCodeGain OBJECT-TYPE
    SYNTAX      FspR7CodeGain
    MAX-ACCESS  read-create
    STATUS      current
    DESCRIPTION
        "Forward Error Correction Coding gain"
    ::=  { changePhysicalPortServiceEntry 11 }

changePhysicalPortServiceXfpDecisionThres OBJECT-TYPE
    SYNTAX      FspR7XfpDecisionThres
    MAX-ACCESS  read-create
    STATUS      current
    DESCRIPTION
        "XFP Decision threshold setting"
    ::=  { changePhysicalPortServiceEntry 12 }

changePhysicalPortServiceDisparityCorrection OBJECT-TYPE
    SYNTAX      EnableState
    MAX-ACCESS  read-create
    STATUS      current
    DESCRIPTION
        "Disparity correction"
    ::=  { changePhysicalPortServiceEntry 13 }

changePhysicalPortServiceEqlzAdmin OBJECT-TYPE
    SYNTAX      FspR7EqlzAdminState
    MAX-ACCESS  read-create
    STATUS      current
    DESCRIPTION
        "Scheduled Equalization Administration"
    ::=  { changePhysicalPortServiceEntry 14 }

changePhysicalPortServiceErrorForwarding OBJECT-TYPE
    SYNTAX      FspR7ErrorFwdMode
    MAX-ACCESS  read-create
    STATUS      current
    DESCRIPTION
        "Determines the reaction in forward direction in response to a LOS on
         the interface on the opposite side of the module: may override
         this behaviour in the interests of laser safety."
    ::=  { changePhysicalPortServiceEntry 15 }

changePhysicalPortServiceFecType OBJECT-TYPE
    SYNTAX      FspR7FecType
    MAX-ACCESS  read-create
    STATUS      current
    DESCRIPTION
        "Forward Error Correction (Only relevant where TYPE = OTU#)"
    ::=  { changePhysicalPortServiceEntry 16 }

changePhysicalPortServiceFarEndCommunication OBJECT-TYPE
    SYNTAX      FspR7YesNo
    MAX-ACCESS  read-create
    STATUS      current
    DESCRIPTION
        "Used for Optojack plugs; Communication to Far End Plug is observed"
    ::=  { changePhysicalPortServiceEntry 17 }

changePhysicalPortServiceFlowControl OBJECT-TYPE
    SYNTAX      FspR7FlowControlMode
    MAX-ACCESS  read-create
    STATUS      current
    DESCRIPTION
        "Flow Control mechanism"
    ::=  { changePhysicalPortServiceEntry 18 }

changePhysicalPortServiceLaneChannelSetting OBJECT-TYPE
    SYNTAX      FspR7ChannelIdentifier
    MAX-ACCESS  read-create
    STATUS      current
    DESCRIPTION
        "Lane Channel Setting"
    ::=  { changePhysicalPortServiceEntry 19 }

changePhysicalPortServiceLaserDelayTimer OBJECT-TYPE
    SYNTAX      FspR7LaserDelayTimer
    MAX-ACCESS  read-create
    STATUS      current
    DESCRIPTION
        "Relevant only when ERRFWD=LSROFF. Enables/disables the
         possibility to delay turning off and on the laser.
         This applies to the case when turning off the laser
         is done as an error forwarding mechanism."
    ::=  { changePhysicalPortServiceEntry 20 }

changePhysicalPortServiceLaserOffTimer OBJECT-TYPE
    SYNTAX      Unsigned32 (1..1000)
    UNITS       "ms"
    MAX-ACCESS  read-create
    STATUS      current
    DESCRIPTION
        "Delay before laser is swiched off"
    ::=  { changePhysicalPortServiceEntry 21 }

changePhysicalPortServiceLaserOnTimer OBJECT-TYPE
    SYNTAX      Unsigned32 (1..1000)
    UNITS       "ms"
    MAX-ACCESS  read-create
    STATUS      current
    DESCRIPTION
        "Delay before laser is switched on"
    ::=  { changePhysicalPortServiceEntry 22 }

changePhysicalPortServiceLaserOffDelayFunction OBJECT-TYPE
    SYNTAX      EnableState
    MAX-ACCESS  read-create
    STATUS      current
    DESCRIPTION   "A configuration request for the Laser Off Delay function. This function
         delays turning off the laser as a consequent action to a defect."
    ::=  { changePhysicalPortServiceEntry 23 }

changePhysicalPortServiceAutoPTassignment OBJECT-TYPE
    SYNTAX      FspR7ManualAuto
    MAX-ACCESS  read-create
    STATUS      current
    DESCRIPTION
        "Auto assignment of ODU PT"
    ::=  { changePhysicalPortServiceEntry 24 }

changePhysicalPortServiceTributarySlotMethod OBJECT-TYPE
    SYNTAX      FspR7ManualAuto
    MAX-ACCESS  read-create
    STATUS      current
    DESCRIPTION
        "Tributary Slot assignment method"
    ::=  { changePhysicalPortServiceEntry 25 }

changePhysicalPortServiceOpticalSetPoint OBJECT-TYPE
    SYNTAX      Integer32 (-250..50)
    UNITS       "0.1 dBm"
    MAX-ACCESS  read-create
    STATUS      current
    DESCRIPTION
        "Sets the optical power for power equalization in ROADM or for channel power control in OPCM"
    ::=  { changePhysicalPortServiceEntry 26 }

changePhysicalPortServiceOpuPayloadType OBJECT-TYPE
    SYNTAX      FspR7OpuPayloadType
    MAX-ACCESS  read-create
    STATUS      current
    DESCRIPTION
        "OPU Payload Type Indicator"
    ::=  { changePhysicalPortServiceEntry 27 }

changePhysicalPortServiceSigDegThresSonetLine OBJECT-TYPE
    SYNTAX      FspR7BERThreshold
    MAX-ACCESS  read-create
    STATUS      current
    DESCRIPTION
        "Bit-Error-Based Degradation Definition for SONET (standard integration period)"
    ::=  { changePhysicalPortServiceEntry 28 }

changePhysicalPortServiceSigDegThresSdhMs OBJECT-TYPE
    SYNTAX      Unsigned32 (1..100)
    UNITS       "%"
    MAX-ACCESS  read-create
    STATUS      current
    DESCRIPTION
        "Block-Error-Based Degradation Definition for SDH (standard integration period).
         Defined as percentage Background Block Errors (30% default) evaluated
         over a defined period (SDPER-RS)."
    ::=  { changePhysicalPortServiceEntry 29 }

changePhysicalPortServiceSigDegThresOtu OBJECT-TYPE
    SYNTAX      Integer32 (1..100)
    UNITS       "%"
    MAX-ACCESS  read-create
    STATUS      current
    DESCRIPTION
        "Background-Block-Error-Based Signal Degradation Definition for OTU"
    ::=  { changePhysicalPortServiceEntry 30 }

changePhysicalPortServiceSigDegThresOdu OBJECT-TYPE
    SYNTAX      Integer32 (1..100)
    UNITS       "%"
    MAX-ACCESS  read-create
    STATUS      current
    DESCRIPTION
        "Background-Block-Error-Based Signal Degradation Definition for ODU"
    ::=  { changePhysicalPortServiceEntry 31 }

changePhysicalPortServiceSigDegThreshold OBJECT-TYPE
    SYNTAX      Unsigned32 (1..10000)
    MAX-ACCESS  read-create
    STATUS      current
    DESCRIPTION
        "Threshold for number of errors (CV or CV+DE) in one second"
    ::=  { changePhysicalPortServiceEntry 32 }

changePhysicalPortServiceSigDegPcslThreshold OBJECT-TYPE
    SYNTAX      Unsigned32 (1..100)
    UNITS       "%"
    MAX-ACCESS  read-create
    STATUS      current
    DESCRIPTION
        "Block-Error-Based Degradation Definition for Physical Coding Sublayer"
    ::=  { changePhysicalPortServiceEntry 33 }

changePhysicalPortServiceSigDegThresSonetSection OBJECT-TYPE
    SYNTAX      FspR7BERThresholdSection
    MAX-ACCESS  read-create
    STATUS      current
    DESCRIPTION
        "Bit-Error-Based Degradation Definition for SONET (standard integration period)"
    ::=  { changePhysicalPortServiceEntry 34 }

changePhysicalPortServiceSigDegThresSdhSection OBJECT-TYPE
    SYNTAX      Unsigned32 (1..100)
    UNITS       "%"
    MAX-ACCESS  read-create
    STATUS      current
    DESCRIPTION
        "Block-Error-Based Degradation Definition for SDH (standard integration period).
         Defined as percentage Background Block Errors (30% default) evaluated
         over a defined period (SDPER-RS)."
    ::=  { changePhysicalPortServiceEntry 35 }

changePhysicalPortServiceSigDegThresOduTcmA OBJECT-TYPE
    SYNTAX      Integer32 (1..100)
    UNITS       "%"
    MAX-ACCESS  read-create
    STATUS      current
    DESCRIPTION
        "Background-Block-Error-Based Signal Degradation Definition for TCM-A"
    ::=  { changePhysicalPortServiceEntry 36 }

changePhysicalPortServiceSigDegThresOduTcmB OBJECT-TYPE
    SYNTAX      Integer32 (1..100)
    UNITS       "%"
    MAX-ACCESS  read-create
    STATUS      current
    DESCRIPTION
        "Background-Block-Error-Based Signal Degradation Definition for TCM-B"
    ::=  { changePhysicalPortServiceEntry 37 }

changePhysicalPortServiceSigDegThresOduTcmC OBJECT-TYPE
    SYNTAX      Integer32 (1..100)
    UNITS       "%"
    MAX-ACCESS  read-create
    STATUS      current
    DESCRIPTION
        "Background-Block-Error-Based Signal Degradation Definition for TCM-C"
    ::=  { changePhysicalPortServiceEntry 38 }

changePhysicalPortServiceSignalDegradePeriod OBJECT-TYPE
    SYNTAX      Unsigned32 (2..10)
    UNITS       "s"
    MAX-ACCESS  read-create
    STATUS      current
    DESCRIPTION   "The measurement period in seconds used together with
         the deployProvIfSigDegThresSdhRegSect based on the block error counting method.
         The valid range is 2..10,
         The default being 7."
    ::=  { changePhysicalPortServiceEntry 39 }

changePhysicalPortServiceSigDegPeriodOdu OBJECT-TYPE
    SYNTAX      Unsigned32 (2..10)
    UNITS       "s"
    MAX-ACCESS  read-create
    STATUS      current
    DESCRIPTION
        "Integration Period for Signal degrade"
    ::=  { changePhysicalPortServiceEntry 40 }

changePhysicalPortServiceSigDegPeriodOtu OBJECT-TYPE
    SYNTAX      Unsigned32 (2..10)
    UNITS       "s"
    MAX-ACCESS  read-create
    STATUS      current
    DESCRIPTION
        "Integration Period for Signal degrade"
    ::=  { changePhysicalPortServiceEntry 41 }

changePhysicalPortServiceSigDegPeriodIntegration OBJECT-TYPE
    SYNTAX      Unsigned32 (1..10)
    UNITS       "s"
    MAX-ACCESS  read-create
    STATUS      current
    DESCRIPTION
        "Integration Period for Signal degrade"
    ::=  { changePhysicalPortServiceEntry 42 }

changePhysicalPortServiceSigDegPeriodSdhSection OBJECT-TYPE
    SYNTAX      Unsigned32 (2..10)
    UNITS       "s"
    MAX-ACCESS  read-create
    STATUS      current
    DESCRIPTION
        "Provisionable Signal Degrade Integration Period for SDH"
    ::=  { changePhysicalPortServiceEntry 43 }

changePhysicalPortServiceSigDegPeriodOduTcmA OBJECT-TYPE
    SYNTAX      Unsigned32 (2..10)
    UNITS       "s"
    MAX-ACCESS  read-create
    STATUS      current
    DESCRIPTION
        "Integration Period for Signal degrade"
    ::=  { changePhysicalPortServiceEntry 44 }

changePhysicalPortServiceSigDegPeriodOduTcmB OBJECT-TYPE
    SYNTAX      Unsigned32 (2..10)
    UNITS       "s"
    MAX-ACCESS  read-create
    STATUS      current
    DESCRIPTION
        "Integration Period of TCMB Signal Segrade"
    ::=  { changePhysicalPortServiceEntry 45 }

changePhysicalPortServiceSigDegPeriodOduTcmC OBJECT-TYPE
    SYNTAX      Unsigned32 (2..10)
    UNITS       "s"
    MAX-ACCESS  read-create
    STATUS      current
    DESCRIPTION
        "Integration Period of TCMC Signal Segrade"
    ::=  { changePhysicalPortServiceEntry 46 }

changePhysicalPortServiceOtnStuffing OBJECT-TYPE
    SYNTAX      FspR7Stuff
    MAX-ACCESS  read-create
    STATUS      current
    DESCRIPTION
        "Indicates if bit/byte stuffing is used in the transport signal."
    ::=  { changePhysicalPortServiceEntry 47 }

changePhysicalPortServiceTcmALevel OBJECT-TYPE
    SYNTAX      OtnTcmLevel
    MAX-ACCESS  read-create
    STATUS      current
    DESCRIPTION
        "Activation of Tandem Connection Monitoring Instance A"
    ::=  { changePhysicalPortServiceEntry 48 }

changePhysicalPortServiceTcmBLevel OBJECT-TYPE
    SYNTAX      OtnTcmLevel
    MAX-ACCESS  read-create
    STATUS      current
    DESCRIPTION
        "Activation of Tandem Connection Monitoring Instance B"
    ::=  { changePhysicalPortServiceEntry 49 }

changePhysicalPortServiceTcmCLevel OBJECT-TYPE
    SYNTAX      OtnTcmLevel
    MAX-ACCESS  read-create
    STATUS      current
    DESCRIPTION
        "Activation of Tandem Connection Monitoring Instance C"
    ::=  { changePhysicalPortServiceEntry 50 }

changePhysicalPortServiceTerminationLevel OBJECT-TYPE
    SYNTAX      OhTerminationLevel
    MAX-ACCESS  read-create
    STATUS      current
    DESCRIPTION
        "The entity is Addressable by Management [because its supporting entity is defined in the database and therefore its address existsSignal Tremination Level of Intrusive Access to Header Information.
         Not used in 7.0, monitoring is one layer higher than TERM level,
         if applicable. All conditions detected on monitoring layer will not
         be reported (severity degradated to NR)."
    ::=  { changePhysicalPortServiceEntry 51 }

changePhysicalPortServiceTimingSource OBJECT-TYPE
    SYNTAX      SonetTimingSource
    MAX-ACCESS  read-create
    STATUS      current
    DESCRIPTION   "The timing source for this interface.
         - internal: used in stand-alone, point-to-point topologies stand-alone (dedicated fiber operation).
         - loopTiming: e.g. used in point-to-point via SONET network and feeder topologies. The default is
         internal(1)."
    ::=  { changePhysicalPortServiceEntry 52 }

changePhysicalPortServiceTimModeOdu OBJECT-TYPE
    SYNTAX      TimMode
    MAX-ACCESS  read-create
    STATUS      current
    DESCRIPTION
        "Detection of TIM-ODU Condition can be configured"
    ::=  { changePhysicalPortServiceEntry 53 }

changePhysicalPortServiceTimModeOtu OBJECT-TYPE
    SYNTAX      TimMode
    MAX-ACCESS  read-create
    STATUS      current
    DESCRIPTION
        "Detection of TIM-OTU Condition can be configured"
    ::=  { changePhysicalPortServiceEntry 54 }

changePhysicalPortServiceTimModeSonetSection OBJECT-TYPE
    SYNTAX      TimMode
    MAX-ACCESS  read-create
    STATUS      current
    DESCRIPTION
        "Detection of TIM Sonet Section Condition can be configured"
    ::=  { changePhysicalPortServiceEntry 55 }

changePhysicalPortServiceTimModeOduTcmA OBJECT-TYPE
    SYNTAX      TimMode
    MAX-ACCESS  read-create
    STATUS      current
    DESCRIPTION
        "Detection of TIM-TCMA Condition can be configured"
    ::=  { changePhysicalPortServiceEntry 56 }

changePhysicalPortServiceTimModeOduTcmB OBJECT-TYPE
    SYNTAX      TimMode
    MAX-ACCESS  read-create
    STATUS      current
    DESCRIPTION
        "Detection of TIM-TCMB Condition can be configured"
    ::=  { changePhysicalPortServiceEntry 57 }

changePhysicalPortServiceTimModeOduTcmC OBJECT-TYPE
    SYNTAX      TimMode
    MAX-ACCESS  read-create
    STATUS      current
    DESCRIPTION
        "Detection of TIM-TCMC Condition can be configured"
    ::=  { changePhysicalPortServiceEntry 58 }

changePhysicalPortServiceTraceFormSonetSection OBJECT-TYPE
    SYNTAX      SonetTraceForm
    MAX-ACCESS  read-create
    STATUS      current
    DESCRIPTION
        "Byte-Length of Trace Compared to Expected"
    ::=  { changePhysicalPortServiceEntry 59 }

changePhysicalPortServiceTraceExpectedSonetSection OBJECT-TYPE
    SYNTAX      OCTET STRING (SIZE(0..62))
    MAX-ACCESS  read-create
    STATUS      current
    DESCRIPTION
        "Expected Sec/RS trace. NULL TRACE implies that no trace comparison is made."
    ::=  { changePhysicalPortServiceEntry 60 }

changePhysicalPortServiceTraceTransmitSonetSection OBJECT-TYPE
    SYNTAX      OCTET STRING (SIZE(0..62))
    MAX-ACCESS  read-create
    STATUS      current
    DESCRIPTION
        "Sec/RS Trace to be Transmitted"
    ::=  { changePhysicalPortServiceEntry 61 }

changePhysicalPortServiceTraceExpectedOtu OBJECT-TYPE
    SYNTAX      OCTET STRING (SIZE(0..15))
    MAX-ACCESS  read-create
    STATUS      current
    DESCRIPTION
        "Expected SAPI part of the OTU trace (15 character). NULL TRACE implies that no trace comparison is made."
    ::=  { changePhysicalPortServiceEntry 62 }

changePhysicalPortServiceTraceTransmitSapiOtu OBJECT-TYPE
    SYNTAX      OCTET STRING (SIZE(0..15))
    MAX-ACCESS  read-create
    STATUS      current
    DESCRIPTION
        "The transmitted SAPI part of the OTU trace (15 character)"
    ::=  { changePhysicalPortServiceEntry 63 }

changePhysicalPortServiceTraceTransmitDapiOtu OBJECT-TYPE
    SYNTAX      OCTET STRING (SIZE(0..15))
    MAX-ACCESS  read-create
    STATUS      current
    DESCRIPTION
        "The transmitted DAPI part of the OTU trace (15 character)"
    ::=  { changePhysicalPortServiceEntry 64 }

changePhysicalPortServiceTraceTransmitOpspOtu OBJECT-TYPE
    SYNTAX      OCTET STRING (SIZE(0..32))
    MAX-ACCESS  read-create
    STATUS      current
    DESCRIPTION
        "The transmitted Operator Specific part of the OTU trace (32 character)"
    ::=  { changePhysicalPortServiceEntry 65 }

changePhysicalPortServiceTraceExpectedOdu OBJECT-TYPE
    SYNTAX      OCTET STRING (SIZE(0..15))
    MAX-ACCESS  read-create
    STATUS      current
    DESCRIPTION
        "Expected SAPI part of the ODU trace (15 character). NULL TRACE implies that no trace comparison is made."
    ::=  { changePhysicalPortServiceEntry 66 }

changePhysicalPortServiceTraceTransmitSapiOdu OBJECT-TYPE
    SYNTAX      OCTET STRING (SIZE(0..15))
    MAX-ACCESS  read-create
    STATUS      current
    DESCRIPTION
        "The transmitted SAPI part of the ODU trace (15 character)"
    ::=  { changePhysicalPortServiceEntry 67 }

changePhysicalPortServiceTraceTransmitDapiOdu OBJECT-TYPE
    SYNTAX      OCTET STRING (SIZE(0..15))
    MAX-ACCESS  read-create
    STATUS      current
    DESCRIPTION
        "The transmitted DAPI part of the ODU trace (15 character)"
    ::=  { changePhysicalPortServiceEntry 68 }

changePhysicalPortServiceTraceTransmitOpspOdu OBJECT-TYPE
    SYNTAX      OCTET STRING (SIZE(0..32))
    MAX-ACCESS  read-create
    STATUS      current
    DESCRIPTION
        "The transmitted Operator Specific part of the ODU trace (32 character)"
    ::=  { changePhysicalPortServiceEntry 69 }

changePhysicalPortServiceTraceExpectedOduTcmA OBJECT-TYPE
    SYNTAX      OCTET STRING (SIZE(0..15))
    MAX-ACCESS  read-create
    STATUS      current
    DESCRIPTION
        "Expected SAPI part of the TCMA trace (15 character). NULL TRACE-TCM implies that no trace comparison is made."
    ::=  { changePhysicalPortServiceEntry 70 }

changePhysicalPortServiceTraceTransmitSapiOduTcmA OBJECT-TYPE
    SYNTAX      OCTET STRING (SIZE(0..15))
    MAX-ACCESS  read-create
    STATUS      current
    DESCRIPTION
        "The transmitted SAPI part of the TCMA trace (15 character)"
    ::=  { changePhysicalPortServiceEntry 71 }

changePhysicalPortServiceTraceTransmitDapiOduTcmA OBJECT-TYPE
    SYNTAX      OCTET STRING (SIZE(0..15))
    MAX-ACCESS  read-create
    STATUS      current
    DESCRIPTION
        "The transmitted DAPI part of the TCMA trace (15 character)"
    ::=  { changePhysicalPortServiceEntry 72 }

changePhysicalPortServiceTraceTransmitOpspOduTcmA OBJECT-TYPE
    SYNTAX      OCTET STRING (SIZE(0..32))
    MAX-ACCESS  read-create
    STATUS      current
    DESCRIPTION
        "The transmitted Operator Specific part of the TCMA trace (32 character)"
    ::=  { changePhysicalPortServiceEntry 73 }

changePhysicalPortServiceTraceExpectedOduTcmB OBJECT-TYPE
    SYNTAX      OCTET STRING (SIZE(0..15))
    MAX-ACCESS  read-create
    STATUS      current
    DESCRIPTION
        "Expected SAPI part of the TCMB trace (15 character). NULL TRACE-TCM implies that no trace comparison is made."
    ::=  { changePhysicalPortServiceEntry 74 }

changePhysicalPortServiceTraceTransmitSapiOduTcmB OBJECT-TYPE
    SYNTAX      OCTET STRING (SIZE(0..15))
    MAX-ACCESS  read-create
    STATUS      current
    DESCRIPTION
        "The transmitted SAPI part of the TCMB trace (15 character)"
    ::=  { changePhysicalPortServiceEntry 75 }

changePhysicalPortServiceTraceTransmitDapiOduTcmB OBJECT-TYPE
    SYNTAX      OCTET STRING (SIZE(0..15))
    MAX-ACCESS  read-create
    STATUS      current
    DESCRIPTION
        "The transmitted DAPI part of the TCMB trace (15 character)"
    ::=  { changePhysicalPortServiceEntry 76 }

changePhysicalPortServiceTraceTransmitOpspOduTcmB OBJECT-TYPE
    SYNTAX      OCTET STRING (SIZE(0..32))
    MAX-ACCESS  read-create
    STATUS      current
    DESCRIPTION
        "The transmitted Operator Specific part of the TCMB trace (32 character)"
    ::=  { changePhysicalPortServiceEntry 77 }

changePhysicalPortServiceTraceExpectedOduTcmC OBJECT-TYPE
    SYNTAX      OCTET STRING (SIZE(0..15))
    MAX-ACCESS  read-create
    STATUS      current
    DESCRIPTION
        "Expected SAPI part of the TCMC trace (15 character). NULL TRACE-TCM implies that no trace comparison is made."
    ::=  { changePhysicalPortServiceEntry 78 }

changePhysicalPortServiceTraceTransmitSapiOduTcmC OBJECT-TYPE
    SYNTAX      OCTET STRING (SIZE(0..15))
    MAX-ACCESS  read-create
    STATUS      current
    DESCRIPTION
        "The transmitted SAPI part of the TCMC trace (15 character)"
    ::=  { changePhysicalPortServiceEntry 79 }

changePhysicalPortServiceTraceTransmitDapiOduTcmC OBJECT-TYPE
    SYNTAX      OCTET STRING (SIZE(0..15))
    MAX-ACCESS  read-create
    STATUS      current
    DESCRIPTION
        "The transmitted DAPI part of the TCMC trace (15 character)"
    ::=  { changePhysicalPortServiceEntry 80 }

changePhysicalPortServiceTraceTransmitOpspOduTcmC OBJECT-TYPE
    SYNTAX      OCTET STRING (SIZE(0..32))
    MAX-ACCESS  read-create
    STATUS      current
    DESCRIPTION
        "The transmitted Operator Specific part of the TCMC trace (32 character)"
    ::=  { changePhysicalPortServiceEntry 81 }

changePhysicalPortServiceTxOffDelay OBJECT-TYPE
    SYNTAX      FspR7EnableDisable
    MAX-ACCESS  read-create
    STATUS      current
    DESCRIPTION
        "Enable or disable TXOFFHOLD Period for Error Forwarding and LKDO-OFF Consequent Action."
    ::=  { changePhysicalPortServiceEntry 82 }

changePhysicalPortServiceVoaMode OBJECT-TYPE
    SYNTAX      FspR7VoaMode
    MAX-ACCESS  read-create
    STATUS      current
    DESCRIPTION
        "VOA operating mode"
    ::=  { changePhysicalPortServiceEntry 83 }

changePhysicalPortServiceVoaSetpoint OBJECT-TYPE
    SYNTAX      Unsigned32 (0..300)
    UNITS       "0.1 dB"
    MAX-ACCESS  read-create
    STATUS      current
    DESCRIPTION
        "Sets the optical attenuation of VOA"
    ::=  { changePhysicalPortServiceEntry 84 }

changePhysicalPortServiceTxOffOnTm OBJECT-TYPE
    SYNTAX      FspR7TxOffOnTm
    MAX-ACCESS  read-create
    STATUS      current
    DESCRIPTION
        "Relevant only when ERRFWD=TXOFF. Enables/disables the
         possibility to delay turning off and on the the transmitter.
         This applies to the case when turning off the transmitter
         is done as an error forwarding mechanism."
    ::=  { changePhysicalPortServiceEntry 85 }

changePhysicalPortServiceTxOffTimer OBJECT-TYPE
    SYNTAX      Unsigned32 (1..1000)
    UNITS       "ms"
    MAX-ACCESS  read-create
    STATUS      current
    DESCRIPTION
        "Delay before transmitter is swiched off"
    ::=  { changePhysicalPortServiceEntry 86 }

changePhysicalPortServiceTxOnTimer OBJECT-TYPE
    SYNTAX      Unsigned32 (1..1000)
    UNITS       "ms"
    MAX-ACCESS  read-create
    STATUS      current
    DESCRIPTION
        "Delay before transmitter is switched on"
    ::=  { changePhysicalPortServiceEntry 87 }

endOfChangeService OBJECT-TYPE
    SYNTAX      Integer32
    MAX-ACCESS  read-only
    STATUS      current
    DESCRIPTION
        ""
    ::=  { changeService 10000 }

haTable OBJECT-TYPE
    SYNTAX      SEQUENCE OF HaEntry
    MAX-ACCESS  not-accessible
    STATUS      current
    DESCRIPTION   ""
    ::=  { protection 1 }

haEntry OBJECT-TYPE
    SYNTAX      HaEntry
    MAX-ACCESS  not-accessible
    STATUS      current
    DESCRIPTION   ""
    INDEX       {
                  entityEqptShelfNo,
                  entityEqptSlotNo,
                  entityEqptPortNo,
                  entityEqptExtNo,
                  entityEqptClassName
                }
    ::=  { haTable 1 }

HaEntry ::=  SEQUENCE
  { haProtectionIndexAid SnmpAdminString,
    haInhSwitching FspR7YesNo,
    haSwitchToDuplex FspR7APSCommand,
    haSwitchOverCause FspR7SwitchOverCause,
    haSoftwareVersion SnmpAdminString }

haProtectionIndexAid OBJECT-TYPE
    SYNTAX      SnmpAdminString
    MAX-ACCESS  read-only
    STATUS      current
    DESCRIPTION
        "(Protection AID) AID of protection entity involved in the protection group."
    ::=  { haEntry 1 }

haInhSwitching OBJECT-TYPE
    SYNTAX      FspR7YesNo
    MAX-ACCESS  read-write
    STATUS      current
    DESCRIPTION
        "(Inhibit Controller Switching) Prevents protection switch to partner controller."
    ::=  { haEntry 2 }

haSwitchToDuplex OBJECT-TYPE
    SYNTAX      FspR7APSCommand
    MAX-ACCESS  read-write
    STATUS      current
    DESCRIPTION
        "Switch to Parnter Controller"
    ::=  { haEntry 3 }

haSwitchOverCause OBJECT-TYPE
    SYNTAX      FspR7SwitchOverCause
    MAX-ACCESS  read-only
    STATUS      current
    DESCRIPTION
        "Cause of Fail-Over or Switch-Over to Partner Controller"
    ::=  { haEntry 4 }

haSoftwareVersion OBJECT-TYPE
    SYNTAX      SnmpAdminString
    MAX-ACCESS  read-only
    STATUS      current
    DESCRIPTION
        "Software Version of the NCU software. <"
    ::=  { haEntry 5 }

endOfHaTable OBJECT-TYPE
    SYNTAX      Integer32
    MAX-ACCESS  read-only
    STATUS      current
    DESCRIPTION
        ""
    ::=  { protection 2 }

ffpTable OBJECT-TYPE
    SYNTAX      SEQUENCE OF FfpEntry
    MAX-ACCESS  not-accessible
    STATUS      current
    DESCRIPTION   "FfpTable"
    ::=  { protection 3 }

ffpEntry OBJECT-TYPE
    SYNTAX      FfpEntry
    MAX-ACCESS  not-accessible
    STATUS      current
    DESCRIPTION   "Entry of FfpTable"
    INDEX       {
                  entityFfpShelfNo,
                  entityFfpSlotNo,
                  entityFfpPortNo,
                  entityFfpExtNo,
                  entityFfpClassName
                }
    ::=  { ffpTable 1 }

FfpEntry ::=  SEQUENCE
  { ffpRowStatus RowStatus,
    ffpCreationMethod FfpType,
    ffpSDswitching EnableState,
    ffpHoldOffTime ApsHoldoffTime,
    ffpProtectionMech ProtectionMech,
    ffpWorkingAid SnmpAdminString,
    ffpProtectionAid SnmpAdminString,
    ffpSignalDegradeSwitching EnableState,
    ffpSignalFailureSwitching EnableState,
    ffpFarEndIp IpAddress,
    ffpPeerAid SnmpAdminString,
    ffpApsType ApsType,
    ffpRevertMode ApsRevertMode,
    ffpWaitToRestore Unsigned32,
    ffpDirection ApsDirection,
    ffpProtectionType FspR7ProtectionType,
    ffpApsChannel FspR7ApsChannel }

ffpRowStatus OBJECT-TYPE
    SYNTAX      RowStatus
    MAX-ACCESS  read-create
    STATUS      current
    DESCRIPTION   "RowStatus"
    ::=  { ffpEntry 1 }

ffpCreationMethod OBJECT-TYPE
    SYNTAX      FfpType
    MAX-ACCESS  read-create
    STATUS      current
    DESCRIPTION   "Type of protection (normal/forced)"
    ::=  { ffpEntry 2 }

ffpSDswitching OBJECT-TYPE
    SYNTAX      EnableState
    MAX-ACCESS  read-create
    STATUS      current
    DESCRIPTION   "This state controls whether the switch criteria for the APS group will
         include the Signal Degrade alarm."
    ::=  { ffpEntry 3 }

ffpHoldOffTime OBJECT-TYPE
    SYNTAX      ApsHoldoffTime
    MAX-ACCESS  read-create
    STATUS      current
    DESCRIPTION   "This value controls the switch delay (0 to 10 seconds in
         100ms steps) for the protection group. Changing the hold-off
         time when the timer is active will not affect the active
         timer. The change will take effect the next time the timer
         is active."
    ::=  { ffpEntry 4 }

ffpProtectionMech OBJECT-TYPE
    SYNTAX      ProtectionMech
    MAX-ACCESS  read-create
    STATUS      current
    DESCRIPTION   "The protection type of this protection group."
    ::=  { ffpEntry 5 }

ffpWorkingAid OBJECT-TYPE
    SYNTAX      SnmpAdminString
    MAX-ACCESS  read-create
    STATUS      current
    DESCRIPTION
        "AID of working port involved in the protection group."
    ::=  { ffpEntry 6 }

ffpProtectionAid OBJECT-TYPE
    SYNTAX      SnmpAdminString
    MAX-ACCESS  read-create
    STATUS      current
    DESCRIPTION
        "(Protection AID) AID of protection entity involved in the protection group."
    ::=  { ffpEntry 7 }

ffpSignalDegradeSwitching OBJECT-TYPE
    SYNTAX      EnableState
    MAX-ACCESS  read-create
    STATUS      current
    DESCRIPTION
        "Switch Trigger Additionally on Signal Degrade Link Detection"
    ::=  { ffpEntry 8 }

ffpSignalFailureSwitching OBJECT-TYPE
    SYNTAX      EnableState
    MAX-ACCESS  read-only
    STATUS      current
    DESCRIPTION
        "Switch Trigger on Signal Failure Link Detection"
    ::=  { ffpEntry 9 }

ffpFarEndIp OBJECT-TYPE
    SYNTAX      IpAddress
    MAX-ACCESS  read-create
    STATUS      current
    DESCRIPTION   "IP Address assigned to PPP Termination Point on Far-End NE. Default
         is set by NE System on LINK establishment if FENDIPACPT = Y"
    ::=  { ffpEntry 10 }

ffpPeerAid OBJECT-TYPE
    SYNTAX      SnmpAdminString
    MAX-ACCESS  read-create
    STATUS      current
    DESCRIPTION
        "AID of Protection Partner involved in the protection group."
    ::=  { ffpEntry 11 }

ffpApsType OBJECT-TYPE
    SYNTAX      ApsType
    MAX-ACCESS  read-create
    STATUS      current
    DESCRIPTION   "The type of APS implemented in this protection group."
    ::=  { ffpEntry 12 }

ffpRevertMode OBJECT-TYPE
    SYNTAX      ApsRevertMode
    MAX-ACCESS  read-create
    STATUS      current
    DESCRIPTION
        "Revertive Protection Switching"
    ::=  { ffpEntry 13 }

ffpWaitToRestore OBJECT-TYPE
    SYNTAX      Unsigned32 (5..12)
    UNITS       "min"
    MAX-ACCESS  read-create
    STATUS      current
    DESCRIPTION
        "Wait to Restore Timer value"
    ::=  { ffpEntry 14 }

ffpDirection OBJECT-TYPE
    SYNTAX      ApsDirection
    MAX-ACCESS  read-create
    STATUS      current
    DESCRIPTION   "Indicates whether the APS function is 'unidirectional' (single-ended)
         or 'bidirectional' (dual-ended)."
    ::=  { ffpEntry 15 }

ffpProtectionType OBJECT-TYPE
    SYNTAX      FspR7ProtectionType
    MAX-ACCESS  read-only
    STATUS      current
    DESCRIPTION
        ""
    ::=  { ffpEntry 16 }

ffpApsChannel OBJECT-TYPE
    SYNTAX      FspR7ApsChannel
    MAX-ACCESS  read-only
    STATUS      current
    DESCRIPTION
        "Selection of the location of the APS channel"
    ::=  { ffpEntry 17 }

endOfFfpTable OBJECT-TYPE
    SYNTAX      Integer32
    MAX-ACCESS  read-only
    STATUS      current
    DESCRIPTION
        ""
    ::=  { protection 4 }

endOfProtection OBJECT-TYPE
    SYNTAX      Integer32
    MAX-ACCESS  read-only
    STATUS      current
    DESCRIPTION
        ""
    ::=  { protection 10000 }

aidMappingTable OBJECT-TYPE
    SYNTAX      SEQUENCE OF AidMappingEntry
    MAX-ACCESS  not-accessible
    STATUS      current
    DESCRIPTION   "Contains entries that represent string format of valid AID in F7 systems.
         This table contains entries only for those strings that were requested using snmpget from this table within last 1ms."
    ::=  { translation 1 }

aidMappingEntry OBJECT-TYPE
    SYNTAX      AidMappingEntry
    MAX-ACCESS  not-accessible
    STATUS      current
    DESCRIPTION   ""
    INDEX       {
                  aidMappingAidString
                }
    ::=  { aidMappingTable 1 }

AidMappingEntry ::=  SEQUENCE
  { aidMappingAidString SnmpAdminString,
    aidMappingId RowPointer,
    aidMappingString SnmpAdminString }

aidMappingAidString OBJECT-TYPE
    SYNTAX      SnmpAdminString
    MAX-ACCESS  not-accessible
    STATUS      current
    DESCRIPTION
        ""
    ::=  { aidMappingEntry 1 }

aidMappingId OBJECT-TYPE
    SYNTAX      RowPointer
    MAX-ACCESS  read-only
    STATUS      current
    DESCRIPTION   "RowPointer to the entity."
    ::=  { aidMappingEntry 2 }

aidMappingString OBJECT-TYPE
    SYNTAX      SnmpAdminString
    MAX-ACCESS  read-only
    STATUS      current
    DESCRIPTION   "String representation of the entity. Example: '20.7.33152.19420.18'."
    ::=  { aidMappingEntry 3 }

endOfAidMappingTable OBJECT-TYPE
    SYNTAX      Integer32
    MAX-ACCESS  read-only
    STATUS      current
    DESCRIPTION
        ""
    ::=  { translation 2 }

endOfTranslation OBJECT-TYPE
    SYNTAX      Integer32
    MAX-ACCESS  read-only
    STATUS      current
    DESCRIPTION
        ""
    ::=  { translation 10000 }

sshHostKeyLength OBJECT-TYPE
    SYNTAX      FspR7SshHostKeyLength
    MAX-ACCESS  read-write
    STATUS      current
    DESCRIPTION
        "Generated SSH host key length"
    ::=  { advaSecurity 1 }

newSshHostKey OBJECT-TYPE
    SYNTAX      FspR7NewSshHostKey
    MAX-ACCESS  read-write
    STATUS      current
    DESCRIPTION
        "Apply generated SSH host key"
    ::=  { advaSecurity 2 }

accessWarning OBJECT-TYPE
    SYNTAX      FspR7EnableDisable
    MAX-ACCESS  read-write
    STATUS      current
    DESCRIPTION
        "Unauthorized Access Warning Switch"
    ::=  { advaSecurity 3 }

accessWarningMessage OBJECT-TYPE
    SYNTAX      FspR7SnmpLongString
    MAX-ACCESS  read-write
    STATUS      current
    DESCRIPTION
        "Unauthorized Access Warning Message"
    ::=  { advaSecurity 4 }

showLastLoginSuccess OBJECT-TYPE
    SYNTAX      FspR7EnableDisable
    MAX-ACCESS  read-write
    STATUS      current
    DESCRIPTION
        "Enable/disable displaying information about last successful login attempt immediately after logging in."
    ::=  { advaSecurity 5 }

showLastLoginFail OBJECT-TYPE
    SYNTAX      FspR7EnableDisable
    MAX-ACCESS  read-write
    STATUS      current
    DESCRIPTION
        "Enable/disable displaying information about last failed login attempt immediately after logging in."
    ::=  { advaSecurity 6 }

writeAccessStatus OBJECT-TYPE
    SYNTAX      FspR7DisableEnable
    MAX-ACCESS  read-write
    STATUS      current
    DESCRIPTION
        "Enable/Disable Central Access Control - temporary write access for monitor users."
    ::=  { advaSecurity 7 }

writeAccessRequestTimeout OBJECT-TYPE
    SYNTAX      Unsigned32 (100..3600 | 4294967295)
    UNITS       "s"
    MAX-ACCESS  read-write
    STATUS      current
    DESCRIPTION
        "Timeout of write access request"
    ::=  { advaSecurity 8 }

virtualSessionTable OBJECT-TYPE
    SYNTAX      SEQUENCE OF VirtualSessionEntry
    MAX-ACCESS  not-accessible
    STATUS      current
    DESCRIPTION   ""
    ::=  { advaSecurity 15 }

virtualSessionEntry OBJECT-TYPE
    SYNTAX      VirtualSessionEntry
    MAX-ACCESS  not-accessible
    STATUS      current
    DESCRIPTION   ""
    INDEX       {
                  virtualSessionId
                }
    ::=  { virtualSessionTable 1 }

VirtualSessionEntry ::=  SEQUENCE
  { virtualSessionId Unsigned32,
    virtualSessionStatus FspR7VSessStatus,
    virtualSessionTimeout Integer32,
    virtualSessionWriteAccess FspR7VSessWriteAccess,
    virtualSessionUserName SnmpAdminString,
    virtualSessionIpAddress IpAddress,
    virtualSessionChangeReason FspR7VSessChangeReason,
    virtualSessionChangeTime TimeTicks }

virtualSessionId OBJECT-TYPE
    SYNTAX      Unsigned32
    MAX-ACCESS  accessible-for-notify
    STATUS      current
    DESCRIPTION   ""
    ::=  { virtualSessionEntry 1 }

virtualSessionStatus OBJECT-TYPE
    SYNTAX      FspR7VSessStatus
    MAX-ACCESS  read-only
    STATUS      current
    DESCRIPTION
        "Read-only object that describes current status of user session.
         There are 3 possible valid values of this object:
         - Normal(1) - default session status.
         - writeAcsRequested(2) - status assigned to session that requested write access and is waiting for ADMIN response
         After time equal 'write access request timeout' if session status has not been changed it will automatically change back to normal(1) and fspR7WriteAccessRequestTimeout trap will be sent.
         - writeAcsGranted(3) - write access has been granted by ADMIN user. Session can act as if it had PROVISION privilege level.
         After time equal virtualSessionTimeout session status will be automatically changed to normal(1) and fspR7WriteAccessTimeout trap will be sent."
    ::=  { virtualSessionEntry 2 }

virtualSessionTimeout OBJECT-TYPE
    SYNTAX      Integer32 (1..480)
    MAX-ACCESS  read-write
    STATUS      current
    DESCRIPTION
        "Read-write parameter describing time for which write access will be granted to the session. This parameter can be edited only if sessionStatus is equal 1 (normal).
         Can be edited only by user with privilege level MONITOR."
    ::=  { virtualSessionEntry 3 }

virtualSessionWriteAccess OBJECT-TYPE
    SYNTAX      FspR7VSessWriteAccess
    MAX-ACCESS  read-write
    STATUS      current
    DESCRIPTION
        "Read-write parameter used to manipulate write access of the user. SNMPGET/SNMPGETNEXT will always return none(4) value for this parameter. It can be set to multiple values depending of sessionStatus:
         - request(1) - settable only by MONITOR if his sessionStatus is equal normal. Causes change of sessionStatus to writeAcsRequested(2). Trap FspR7WriteAccessRequest will be sent.
         - revoke(2) - settable both by MONITOR user and ADMIN user, only if session status is equal writeAcsRequested(2) or writeAcsGranted(3).
         If session status is equal writeAcsRequested(2) setting this value will change session status back to normal(1). Depending on author of action fspR7WriteAccessRevoked (MONITOR) or fspR7WriteAccessDenied (ADMIN) trap will be sent.
         If session status is equal writeAcsGranted(3) it will be changed to normal(1). fspR7WriteAccessRevoked trap will be sent.
         - Grant(3) - settable only by ADMIN user only when session status is equal writeAcsRequested(2). Setting this value will change session staus to writeAcsGranted (3), additionally fspR7WriteAccessGranted trap will be sent.
        "
    ::=  { virtualSessionEntry 4 }

virtualSessionUserName OBJECT-TYPE
    SYNTAX      SnmpAdminString
    MAX-ACCESS  read-only
    STATUS      current
    DESCRIPTION   "Name of the user owning the virtual session."
    ::=  { virtualSessionEntry 5 }

virtualSessionIpAddress OBJECT-TYPE
    SYNTAX      IpAddress
    MAX-ACCESS  read-only
    STATUS      current
    DESCRIPTION   "IP of the user owning the virtual session."
    ::=  { virtualSessionEntry 6 }

virtualSessionChangeReason OBJECT-TYPE
    SYNTAX      FspR7VSessChangeReason
    MAX-ACCESS  read-only
    STATUS      current
    DESCRIPTION
        "Last operation status"
    ::=  { virtualSessionEntry 7 }

virtualSessionChangeTime OBJECT-TYPE
    SYNTAX      TimeTicks
    MAX-ACCESS  read-only
    STATUS      current
    DESCRIPTION
        "Time of last operation status"
    ::=  { virtualSessionEntry 8 }

packetFiltering OBJECT-TYPE
    SYNTAX      FspR7EnableDisable
    MAX-ACCESS  read-write
    STATUS      current
    DESCRIPTION
        "Enable/disable packet filtering."
    ::=  { advaSecurity 16 }

whitelistFiltering OBJECT-TYPE
    SYNTAX      FspR7EnableDisable
    MAX-ACCESS  read-write
    STATUS      current
    DESCRIPTION
        "Enable/disable whitelist rules filtering."
    ::=  { advaSecurity 17 }

restrictToSysIP OBJECT-TYPE
    SYNTAX      FspR7EnableDisable
    MAX-ACCESS  read-write
    STATUS      current
    DESCRIPTION
        "Enable/disable whitelist restriction, that only packets are accepted, which are targeted to the System IP."
    ::=  { advaSecurity 18 }

icmpFiltering OBJECT-TYPE
    SYNTAX      FspR7EnableDisable
    MAX-ACCESS  read-write
    STATUS      current
    DESCRIPTION
        "Enable/disable ICMP filtering."
    ::=  { advaSecurity 19 }

icmpEchoRequests OBJECT-TYPE
    SYNTAX      FspR7EnableDisable
    MAX-ACCESS  read-write
    STATUS      current
    DESCRIPTION
        "Enable/disable blocking incoming ICMP echo requests."
    ::=  { advaSecurity 20 }

icmpSourceQuench OBJECT-TYPE
    SYNTAX      FspR7EnableDisable
    MAX-ACCESS  read-write
    STATUS      current
    DESCRIPTION
        "Enable/disable blocking incoming ICMP Source-Quench messages."
    ::=  { advaSecurity 21 }

icmpRedirect OBJECT-TYPE
    SYNTAX      FspR7EnableDisable
    MAX-ACCESS  read-write
    STATUS      current
    DESCRIPTION
        "Enable/disable blocking incoming ICMP redirect messages."
    ::=  { advaSecurity 22 }

ocmpTimestampRequest OBJECT-TYPE
    SYNTAX      FspR7EnableDisable
    MAX-ACCESS  read-write
    STATUS      current
    DESCRIPTION
        "Enable/disable blocking incoming ICMP timestamp request messages."
    ::=  { advaSecurity 23 }

icmpAddrMask OBJECT-TYPE
    SYNTAX      FspR7EnableDisable
    MAX-ACCESS  read-write
    STATUS      current
    DESCRIPTION
        "Enable/disable blocking incoming ICMP address-mask request messages."
    ::=  { advaSecurity 24 }

dosProtection OBJECT-TYPE
    SYNTAX      FspR7EnableDisable
    MAX-ACCESS  read-write
    STATUS      current
    DESCRIPTION
        "Enable/disable denial-of-service protection."
    ::=  { advaSecurity 25 }

isolateInbandChan OBJECT-TYPE
    SYNTAX      FspR7EnableDisable
    MAX-ACCESS  read-write
    STATUS      current
    DESCRIPTION
        "Enable/disable blocking routing between inband channels."
    ::=  { advaSecurity 26 }

ipForwarding OBJECT-TYPE
    SYNTAX      FspR7EnableDisable
    MAX-ACCESS  read-write
    STATUS      current
    DESCRIPTION
        "Enable/disable IP forwarding."
    ::=  { advaSecurity 27 }

whitelistTable OBJECT-TYPE
    SYNTAX      SEQUENCE OF WhitelistEntry
    MAX-ACCESS  not-accessible
    STATUS      current
    DESCRIPTION   "entityOptLineTable"
    ::=  { advaSecurity 30 }

whitelistEntry OBJECT-TYPE
    SYNTAX      WhitelistEntry
    MAX-ACCESS  not-accessible
    STATUS      current
    DESCRIPTION   "Entry of entityOptLineTable"
    INDEX       {
                  whitelistId
                }
    ::=  { whitelistTable 1 }

WhitelistEntry ::=  SEQUENCE
  { whitelistId Unsigned32,
    whitelistRowStatus RowStatus,
    whitelistAdmin FspR7AdminState,
    whitelistIpMask IpAddress,
    whitelistIpAddr IpAddress }

whitelistId OBJECT-TYPE
    SYNTAX      Unsigned32
    MAX-ACCESS  accessible-for-notify
    STATUS      current
    DESCRIPTION   ""
    ::=  { whitelistEntry 1 }

whitelistRowStatus OBJECT-TYPE
    SYNTAX      RowStatus
    MAX-ACCESS  read-create
    STATUS      current
    DESCRIPTION   "RowStatus object is used to create or delete a row in the table."
    ::=  { whitelistEntry 2 }

whitelistAdmin OBJECT-TYPE
    SYNTAX      FspR7AdminState
    MAX-ACCESS  read-create
    STATUS      current
    DESCRIPTION
        "The Administrative State will be displayed in the GUI with full
         name values; it will be differently displayed in TL1 syntax according
         to TL1 display rules. The transaction into the UAS state requires
         a special destroy/delete function"
    ::=  { whitelistEntry 3 }

whitelistIpMask OBJECT-TYPE
    SYNTAX      IpAddress
    MAX-ACCESS  read-create
    STATUS      current
    DESCRIPTION
        "IP MASK assigned to LAN IP Interface"
    ::=  { whitelistEntry 4 }

whitelistIpAddr OBJECT-TYPE
    SYNTAX      IpAddress
    MAX-ACCESS  read-create
    STATUS      current
    DESCRIPTION
        "IP Address assigned to LAN IP Interface"
    ::=  { whitelistEntry 5 }

lockSafety OBJECT-TYPE
    SYNTAX      FspR7EnableDisable
    MAX-ACCESS  read-write
    STATUS      current
    DESCRIPTION
        "The last admin account is protected by locking."
    ::=  { advaSecurity 31 }

unlockTime OBJECT-TYPE
    SYNTAX      Unsigned32 (0..99999 | 4294967295)
    UNITS       "s"
    MAX-ACCESS  read-write
    STATUS      current
    DESCRIPTION
        "Time that the user account is locked (after the maximum number of failed login attempts has been exceeded)."
    ::=  { advaSecurity 32 }

sslRenewMode OBJECT-TYPE
    SYNTAX      FspR7RenewMode
    MAX-ACCESS  read-write
    STATUS      current
    DESCRIPTION
        "Defines SSL certificate renew mode. In AUTOMATIC mode SSL certificate is verified and generated (if needed) at every system startup. In MANUAL mode the user is responsible for generation new SSL certificate when needed."
    ::=  { advaSecurity 33 }

sslKeyLength OBJECT-TYPE
    SYNTAX      FspR7KeyLength
    MAX-ACCESS  read-write
    STATUS      current
    DESCRIPTION
        "SSL certificate key length (in bits)."
    ::=  { advaSecurity 34 }

sslValidityPeriod OBJECT-TYPE
    SYNTAX      FspR7ValidityPeriod
    MAX-ACCESS  read-write
    STATUS      current
    DESCRIPTION
        "Period of time (in years) a generated SSL certificate is valid."
    ::=  { advaSecurity 35 }

sslCertApply OBJECT-TYPE
    SYNTAX      FspR7CertApply
    MAX-ACCESS  read-write
    STATUS      current
    DESCRIPTION
        "Apply generated SSL certificate."
    ::=  { advaSecurity 36 }

sslCertIp OBJECT-TYPE
    SYNTAX      SnmpAdminString
    MAX-ACCESS  read-write
    STATUS      current
    DESCRIPTION
        "User defined IP address used in SSL certificate."
    ::=  { advaSecurity 37 }

trapSource OBJECT-TYPE
    SYNTAX      FspR7AppType
    MAX-ACCESS  accessible-for-notify
    STATUS      current
    DESCRIPTION   "This parameter contains source application on which trap was created."
    ::=  { advaSecurity 38 }

trapUser OBJECT-TYPE
    SYNTAX      SnmpAdminString
    MAX-ACCESS  accessible-for-notify
    STATUS      current
    DESCRIPTION   "This parameter contains user name of preson who created trap."
    ::=  { advaSecurity 39 }

knownHostIPv6Table OBJECT-TYPE
    SYNTAX      SEQUENCE OF KnownHostIPv6Entry
    MAX-ACCESS  not-accessible
    STATUS      current
    DESCRIPTION   "KnownHost Table for IPv6 addresses. The first index has fixed length to 16"
    ::=  { ipSettings 3 }

knownHostIPv6Entry OBJECT-TYPE
    SYNTAX      KnownHostIPv6Entry
    MAX-ACCESS  not-accessible
    STATUS      current
    DESCRIPTION   "Entry of knownHostIPv6Table"
    INDEX       {
                  knownHostIPv6IP,
                  knownHostIPv6KeyEncryptAlgorithm
                }
    ::=  { knownHostIPv6Table 1 }

KnownHostIPv6Entry ::=  SEQUENCE
  { knownHostIPv6IP FspR7Ipv6Address,
    knownHostIPv6KeyEncryptAlgorithm FspR7SshHostKeyEncryptAlgorithm,
    knownHostIPv6RowStatus RowStatus,
    knownHostIPv6FingerPrint FspR7SnmpHexString }

knownHostIPv6IP OBJECT-TYPE
    SYNTAX      FspR7Ipv6Address
    MAX-ACCESS  accessible-for-notify
    STATUS      current
    DESCRIPTION   "IPv6 Address of known host"
    ::=  { knownHostIPv6Entry 1 }

knownHostIPv6KeyEncryptAlgorithm OBJECT-TYPE
    SYNTAX      FspR7SshHostKeyEncryptAlgorithm
    MAX-ACCESS  read-only
    STATUS      current
    DESCRIPTION
        "ssh host key encryption alogrithm"
    ::=  { knownHostIPv6Entry 2 }

knownHostIPv6RowStatus OBJECT-TYPE
    SYNTAX      RowStatus
    MAX-ACCESS  read-create
    STATUS      current
    DESCRIPTION   "This object is used to create, or delete a row in this table"
    ::=  { knownHostIPv6Entry 3 }

knownHostIPv6FingerPrint OBJECT-TYPE
    SYNTAX      FspR7SnmpHexString
    MAX-ACCESS  read-create
    STATUS      current
    DESCRIPTION
        "Fingerprint of ssh host key"
    ::=  { knownHostIPv6Entry 4 }

ipv6ActRoutesTable OBJECT-TYPE
    SYNTAX      SEQUENCE OF Ipv6ActRoutesEntry
    MAX-ACCESS  not-accessible
    STATUS      current
    DESCRIPTION   "Routing Table for IPv6 (active routes)"
    ::=  { ipSettings 14 }

ipv6ActRoutesEntry OBJECT-TYPE
    SYNTAX      Ipv6ActRoutesEntry
    MAX-ACCESS  not-accessible
    STATUS      current
    DESCRIPTION   "Entry of ipv6ActRoutesTable"
    INDEX       {
                  ipv6ActRoutesDestination,
                  ipv6ActRoutesPrefix,
                  ipv6ActRoutesNextHop,
                  ipv6ActRoutesShelfNo,
                  ipv6ActRoutesSlotNo,
                  ipv6ActRoutesPortNo,
                  ipv6ActRoutesExtNo,
                  ipv6ActRoutesClassName
                }
    ::=  { ipv6ActRoutesTable 1 }

Ipv6ActRoutesEntry ::=  SEQUENCE
  { ipv6ActRoutesDestination FspR7Ipv6Address,
    ipv6ActRoutesPrefix Unsigned32,
    ipv6ActRoutesNextHop FspR7Ipv6Address,
    ipv6ActRoutesShelfNo Unsigned32,
    ipv6ActRoutesSlotNo Unsigned32,
    ipv6ActRoutesPortNo Unsigned32,
    ipv6ActRoutesExtNo Unsigned32,
    ipv6ActRoutesClassName EntityClassName,
    ipv6ActRoutesRowStatus RowStatus,
    ipv6ActRoutesType FspR7Protocol,
    ipv6ActRoutesMetric Unsigned32,
    ipv6ActRoutesDestIp SnmpAdminString,
    ipv6ActRoutesPrefixLen Unsigned32,
    ipv6ActRoutesNextHopIp SnmpAdminString,
    ipv6ActRoutesPort SnmpAdminString }

ipv6ActRoutesDestination OBJECT-TYPE
    SYNTAX      FspR7Ipv6Address
    MAX-ACCESS  not-accessible
    STATUS      current
    DESCRIPTION
        "Destination IPv6 Address"
    ::=  { ipv6ActRoutesEntry 1 }

ipv6ActRoutesPrefix OBJECT-TYPE
    SYNTAX      Unsigned32 (0..128)
    MAX-ACCESS  not-accessible
    STATUS      current
    DESCRIPTION
        "IPv6 Subnet Prefix Length"
    ::=  { ipv6ActRoutesEntry 2 }

ipv6ActRoutesNextHop OBJECT-TYPE
    SYNTAX      FspR7Ipv6Address
    MAX-ACCESS  not-accessible
    STATUS      current
    DESCRIPTION
        "Gateway IPv6 Address"
    ::=  { ipv6ActRoutesEntry 3 }

ipv6ActRoutesShelfNo OBJECT-TYPE
    SYNTAX      Unsigned32
    MAX-ACCESS  not-accessible
    STATUS      current
    DESCRIPTION   "Adress index."
    ::=  { ipv6ActRoutesEntry 4 }

ipv6ActRoutesSlotNo OBJECT-TYPE
    SYNTAX      Unsigned32
    MAX-ACCESS  not-accessible
    STATUS      current
    DESCRIPTION   "Adress index."
    ::=  { ipv6ActRoutesEntry 5 }

ipv6ActRoutesPortNo OBJECT-TYPE
    SYNTAX      Unsigned32
    MAX-ACCESS  not-accessible
    STATUS      current
    DESCRIPTION   "Adress index."
    ::=  { ipv6ActRoutesEntry 6 }

ipv6ActRoutesExtNo OBJECT-TYPE
    SYNTAX      Unsigned32
    MAX-ACCESS  not-accessible
    STATUS      current
    DESCRIPTION   "Adress index."
    ::=  { ipv6ActRoutesEntry 7 }

ipv6ActRoutesClassName OBJECT-TYPE
    SYNTAX      EntityClassName
    MAX-ACCESS  not-accessible
    STATUS      current
    DESCRIPTION
        "Entity Class Name"
    ::=  { ipv6ActRoutesEntry 8 }

ipv6ActRoutesRowStatus OBJECT-TYPE
    SYNTAX      RowStatus
    MAX-ACCESS  read-create
    STATUS      current
    DESCRIPTION   "This object is used to create, or delete a row in this table."
    ::=  { ipv6ActRoutesEntry 9 }

ipv6ActRoutesType OBJECT-TYPE
    SYNTAX      FspR7Protocol
    MAX-ACCESS  read-create
    STATUS      current
    DESCRIPTION
        "The Type of the IP Route."
    ::=  { ipv6ActRoutesEntry 10 }

ipv6ActRoutesMetric OBJECT-TYPE
    SYNTAX      Unsigned32 (0..65535)
    MAX-ACCESS  read-create
    STATUS      current
    DESCRIPTION
        "Routing Metric"
    ::=  { ipv6ActRoutesEntry 11 }

ipv6ActRoutesDestIp OBJECT-TYPE
    SYNTAX      SnmpAdminString
    MAX-ACCESS  read-only
    STATUS      current
    DESCRIPTION
        "Destination IPv6 Address"
    ::=  { ipv6ActRoutesEntry 12 }

ipv6ActRoutesPrefixLen OBJECT-TYPE
    SYNTAX      Unsigned32 (0..128)
    MAX-ACCESS  read-only
    STATUS      current
    DESCRIPTION
        "IPv6 Subnet Prefix Length"
    ::=  { ipv6ActRoutesEntry 13 }

ipv6ActRoutesNextHopIp OBJECT-TYPE
    SYNTAX      SnmpAdminString
    MAX-ACCESS  read-only
    STATUS      current
    DESCRIPTION
        "Gateway IPv6 Address"
    ::=  { ipv6ActRoutesEntry 14 }

ipv6ActRoutesPort OBJECT-TYPE
    SYNTAX      SnmpAdminString
    MAX-ACCESS  read-only
    STATUS      current
    DESCRIPTION
        "Address Identifier of IP Entity. E.g SC-1-A-C or LINK-1-A-1."
    ::=  { ipv6ActRoutesEntry 15 }

ipv6InActRoutesTable OBJECT-TYPE
    SYNTAX      SEQUENCE OF Ipv6InActRoutesEntry
    MAX-ACCESS  not-accessible
    STATUS      current
    DESCRIPTION   "Routing Table for IPv6 (inactive routes)"
    ::=  { ipSettings 16 }

ipv6InActRoutesEntry OBJECT-TYPE
    SYNTAX      Ipv6InActRoutesEntry
    MAX-ACCESS  not-accessible
    STATUS      current
    DESCRIPTION   "Entry of ipv6InActRoutesTable"
    INDEX       {
                  ipv6InActRoutesDestination,
                  ipv6InActRoutesPrefix,
                  ipv6InActRoutesNextHop,
                  ipv6InActRoutesShelfNo,
                  ipv6InActRoutesSlotNo,
                  ipv6InActRoutesPortNo,
                  ipv6InActRoutesExtNo,
                  ipv6InActRoutesClassName
                }
    ::=  { ipv6InActRoutesTable 1 }

Ipv6InActRoutesEntry ::=  SEQUENCE
  { ipv6InActRoutesDestination FspR7Ipv6Address,
    ipv6InActRoutesPrefix Unsigned32,
    ipv6InActRoutesNextHop FspR7Ipv6Address,
    ipv6InActRoutesShelfNo Unsigned32,
    ipv6InActRoutesSlotNo Unsigned32,
    ipv6InActRoutesPortNo Unsigned32,
    ipv6InActRoutesExtNo Unsigned32,
    ipv6InActRoutesClassName EntityClassName,
    ipv6InActRoutesRowStatus RowStatus,
    ipv6InActRoutesType FspR7Protocol,
    ipv6InActRoutesMetric Unsigned32,
    ipv6InActRoutesDestIp SnmpAdminString,
    ipv6InActRoutesPrefixLen Unsigned32,
    ipv6InActRoutesNextHopIp SnmpAdminString,
    ipv6InActRoutesPort SnmpAdminString }

ipv6InActRoutesDestination OBJECT-TYPE
    SYNTAX      FspR7Ipv6Address
    MAX-ACCESS  not-accessible
    STATUS      current
    DESCRIPTION
        "Destination IPv6 Address"
    ::=  { ipv6InActRoutesEntry 1 }

ipv6InActRoutesPrefix OBJECT-TYPE
    SYNTAX      Unsigned32 (0..128)
    MAX-ACCESS  not-accessible
    STATUS      current
    DESCRIPTION
        "IPv6 Subnet Prefix Length"
    ::=  { ipv6InActRoutesEntry 2 }

ipv6InActRoutesNextHop OBJECT-TYPE
    SYNTAX      FspR7Ipv6Address
    MAX-ACCESS  not-accessible
    STATUS      current
    DESCRIPTION
        "Gateway IPv6 Address"
    ::=  { ipv6InActRoutesEntry 3 }

ipv6InActRoutesShelfNo OBJECT-TYPE
    SYNTAX      Unsigned32
    MAX-ACCESS  not-accessible
    STATUS      current
    DESCRIPTION   "Adress index."
    ::=  { ipv6InActRoutesEntry 4 }

ipv6InActRoutesSlotNo OBJECT-TYPE
    SYNTAX      Unsigned32
    MAX-ACCESS  not-accessible
    STATUS      current
    DESCRIPTION   "Adress index."
    ::=  { ipv6InActRoutesEntry 5 }

ipv6InActRoutesPortNo OBJECT-TYPE
    SYNTAX      Unsigned32
    MAX-ACCESS  not-accessible
    STATUS      current
    DESCRIPTION   "Adress index."
    ::=  { ipv6InActRoutesEntry 6 }

ipv6InActRoutesExtNo OBJECT-TYPE
    SYNTAX      Unsigned32
    MAX-ACCESS  not-accessible
    STATUS      current
    DESCRIPTION   "Adress index."
    ::=  { ipv6InActRoutesEntry 7 }

ipv6InActRoutesClassName OBJECT-TYPE
    SYNTAX      EntityClassName
    MAX-ACCESS  not-accessible
    STATUS      current
    DESCRIPTION
        "Entity Class Name"
    ::=  { ipv6InActRoutesEntry 8 }

ipv6InActRoutesRowStatus OBJECT-TYPE
    SYNTAX      RowStatus
    MAX-ACCESS  read-create
    STATUS      current
    DESCRIPTION   "This object is used to create, or delete a row in this table."
    ::=  { ipv6InActRoutesEntry 9 }

ipv6InActRoutesType OBJECT-TYPE
    SYNTAX      FspR7Protocol
    MAX-ACCESS  read-create
    STATUS      current
    DESCRIPTION
        "The Type of the IP Route."
    ::=  { ipv6InActRoutesEntry 10 }

ipv6InActRoutesMetric OBJECT-TYPE
    SYNTAX      Unsigned32 (0..65535)
    MAX-ACCESS  read-create
    STATUS      current
    DESCRIPTION
        "Routing Metric"
    ::=  { ipv6InActRoutesEntry 11 }

ipv6InActRoutesDestIp OBJECT-TYPE
    SYNTAX      SnmpAdminString
    MAX-ACCESS  read-only
    STATUS      current
    DESCRIPTION
        "Destination IPv6 Address"
    ::=  { ipv6InActRoutesEntry 12 }

ipv6InActRoutesPrefixLen OBJECT-TYPE
    SYNTAX      Unsigned32 (0..128)
    MAX-ACCESS  read-only
    STATUS      current
    DESCRIPTION
        "IPv6 Subnet Prefix Length"
    ::=  { ipv6InActRoutesEntry 13 }

ipv6InActRoutesNextHopIp OBJECT-TYPE
    SYNTAX      SnmpAdminString
    MAX-ACCESS  read-only
    STATUS      current
    DESCRIPTION
        "Gateway IPv6 Address"
    ::=  { ipv6InActRoutesEntry 14 }

ipv6InActRoutesPort OBJECT-TYPE
    SYNTAX      SnmpAdminString
    MAX-ACCESS  read-only
    STATUS      current
    DESCRIPTION
        "Address Identifier of IP Entity. E.g SC-1-A-C or LINK-1-A-1."
    ::=  { ipv6InActRoutesEntry 15 }

syslogIPv4Table OBJECT-TYPE
    SYNTAX      SEQUENCE OF SyslogIPv4Entry
    MAX-ACCESS  not-accessible
    STATUS      current
    DESCRIPTION   "The Syslog Server configuration table for IPv4"
    ::=  { ipSettings 30 }

syslogIPv4Entry OBJECT-TYPE
    SYNTAX      SyslogIPv4Entry
    MAX-ACCESS  not-accessible
    STATUS      current
    DESCRIPTION   "The Syslog IPv4 Server entity"
    INDEX       {
                  syslogIPv4Ip
                }
    ::=  { syslogIPv4Table 1 }

SyslogIPv4Entry ::=  SEQUENCE
  { syslogIPv4Ip IpAddress,
    syslogIPv4RowStatus RowStatus,
    syslogIPv4Reporting FspR7EnableDisable,
    syslogIPv4DbchgReports FspR7EnableDisable,
    syslogIPv4SecurityReports FspR7EnableDisable,
    syslogIPv4IpAddr IpAddress }

syslogIPv4Ip OBJECT-TYPE
    SYNTAX      IpAddress
    MAX-ACCESS  accessible-for-notify
    STATUS      current
    DESCRIPTION   "The IPv4 address of the remote Syslog server"
    ::=  { syslogIPv4Entry 1 }

syslogIPv4RowStatus OBJECT-TYPE
    SYNTAX      RowStatus
    MAX-ACCESS  read-create
    STATUS      current
    DESCRIPTION   "RowStatus"
    ::=  { syslogIPv4Entry 2 }

syslogIPv4Reporting OBJECT-TYPE
    SYNTAX      FspR7EnableDisable
    MAX-ACCESS  read-create
    STATUS      current
    DESCRIPTION
        "Syslog"
    ::=  { syslogIPv4Entry 3 }

syslogIPv4DbchgReports OBJECT-TYPE
    SYNTAX      FspR7EnableDisable
    MAX-ACCESS  read-create
    STATUS      current
    DESCRIPTION
        "Enable or disable sending DB change events"
    ::=  { syslogIPv4Entry 4 }

syslogIPv4SecurityReports OBJECT-TYPE
    SYNTAX      FspR7EnableDisable
    MAX-ACCESS  read-create
    STATUS      current
    DESCRIPTION
        "Enable or disable sending security-related events."
    ::=  { syslogIPv4Entry 5 }

syslogIPv4IpAddr OBJECT-TYPE
    SYNTAX      IpAddress
    MAX-ACCESS  read-only
    STATUS      current
    DESCRIPTION   "The IP address of the IP host where Syslog notifications should be sent. Derived from AID"
    ::=  { syslogIPv4Entry 6 }

syslogIPv6Table OBJECT-TYPE
    SYNTAX      SEQUENCE OF SyslogIPv6Entry
    MAX-ACCESS  not-accessible
    STATUS      current
    DESCRIPTION   "The Syslog Server configuration table for IPv6"
    ::=  { ipSettings 32 }

syslogIPv6Entry OBJECT-TYPE
    SYNTAX      SyslogIPv6Entry
    MAX-ACCESS  not-accessible
    STATUS      current
    DESCRIPTION   "The Syslog IPv6 Server entity"
    INDEX       {
                  syslogIPv6Ip
                }
    ::=  { syslogIPv6Table 1 }

SyslogIPv6Entry ::=  SEQUENCE
  { syslogIPv6Ip FspR7Ipv6Address,
    syslogIPv6RowStatus RowStatus,
    syslogIPv6Reporting FspR7EnableDisable,
    syslogIPv6DbchgReports FspR7EnableDisable,
    syslogIPv6SecurityReports FspR7EnableDisable,
    syslogIPv6IpAddr SnmpAdminString }

syslogIPv6Ip OBJECT-TYPE
    SYNTAX      FspR7Ipv6Address
    MAX-ACCESS  accessible-for-notify
    STATUS      current
    DESCRIPTION   "The IPv6 address of the remote Syslog server"
    ::=  { syslogIPv6Entry 1 }

syslogIPv6RowStatus OBJECT-TYPE
    SYNTAX      RowStatus
    MAX-ACCESS  read-create
    STATUS      current
    DESCRIPTION   "RowStatus"
    ::=  { syslogIPv6Entry 2 }

syslogIPv6Reporting OBJECT-TYPE
    SYNTAX      FspR7EnableDisable
    MAX-ACCESS  read-create
    STATUS      current
    DESCRIPTION
        "Syslog"
    ::=  { syslogIPv6Entry 3 }

syslogIPv6DbchgReports OBJECT-TYPE
    SYNTAX      FspR7EnableDisable
    MAX-ACCESS  read-create
    STATUS      current
    DESCRIPTION
        "Enable or disable sending DB change events"
    ::=  { syslogIPv6Entry 4 }

syslogIPv6SecurityReports OBJECT-TYPE
    SYNTAX      FspR7EnableDisable
    MAX-ACCESS  read-create
    STATUS      current
    DESCRIPTION
        "Enable or disable sending security-related events."
    ::=  { syslogIPv6Entry 5 }

syslogIPv6IpAddr OBJECT-TYPE
    SYNTAX      SnmpAdminString
    MAX-ACCESS  read-only
    STATUS      current
    DESCRIPTION   "The IP address of the IP host where Syslog notifications should be sent. Derived from AID"
    ::=  { syslogIPv6Entry 6 }

ntpIPv4Table OBJECT-TYPE
    SYNTAX      SEQUENCE OF NtpIPv4Entry
    MAX-ACCESS  not-accessible
    STATUS      current
    DESCRIPTION   "The NTP Server configuration table for IPv4"
    ::=  { dateAndTime 20 }

ntpIPv4Entry OBJECT-TYPE
    SYNTAX      NtpIPv4Entry
    MAX-ACCESS  not-accessible
    STATUS      current
    DESCRIPTION   "The NTP IPv4 Server entity"
    INDEX       {
                  ntpIPv4Ip
                }
    ::=  { ntpIPv4Table 1 }

NtpIPv4Entry ::=  SEQUENCE
  { ntpIPv4Ip IpAddress,
    ntpIPv4RowStatus RowStatus,
    ntpIPv4SourceIp SourceIpAddress,
    ntpIPv4Test FspR7NtpTest,
    ntpIPv4TestStatus FspR7NtpTestStatus,
    ntpIPv4SyncStatus FspR7NtpSyncStatus,
    ntpIPv4Admin FspR7NtpAdminState,
    ntpIPv4OperState FspR7OperState,
    ntpIPv4IpAddr IpAddress }

ntpIPv4Ip OBJECT-TYPE
    SYNTAX      IpAddress
    MAX-ACCESS  accessible-for-notify
    STATUS      current
    DESCRIPTION   "The IPv4 address of the remote NTP server"
    ::=  { ntpIPv4Entry 1 }

ntpIPv4RowStatus OBJECT-TYPE
    SYNTAX      RowStatus
    MAX-ACCESS  read-create
    STATUS      current
    DESCRIPTION   "Row status used for managing a NTP server entity. All values defined for
         RowStatus TC can be used
        "
    ::=  { ntpIPv4Entry 2 }

ntpIPv4SourceIp OBJECT-TYPE
    SYNTAX      SourceIpAddress
    MAX-ACCESS  read-create
    STATUS      current
    DESCRIPTION   "Network interface type used for NTP connection. Two interface types are defined:
         sysIp(1) and defaultIp(2)
        "
    ::=  { ntpIPv4Entry 3 }

ntpIPv4Test OBJECT-TYPE
    SYNTAX      FspR7NtpTest
    MAX-ACCESS  read-write
    STATUS      current
    DESCRIPTION   "Operational parameter for invoking a connection test procedure. If set
         to ntpTest(2) then a connection with remote NTP server is being checked.
         Result of this operation is saved under ntpServerTestStatus column. When
         operation finish then value is automaticaly set to rls(1). It cannot
         be set to rls(1) by hand
        "
    ::=  { ntpIPv4Entry 4 }

ntpIPv4TestStatus OBJECT-TYPE
    SYNTAX      FspR7NtpTestStatus
    MAX-ACCESS  read-only
    STATUS      current
    DESCRIPTION   "Result of NTP availability check command invoked by setting ntpServerTest to ntpTest(2)"
    ::=  { ntpIPv4Entry 5 }

ntpIPv4SyncStatus OBJECT-TYPE
    SYNTAX      FspR7NtpSyncStatus
    MAX-ACCESS  read-only
    STATUS      current
    DESCRIPTION   "The NTP Synchronization status"
    ::=  { ntpIPv4Entry 6 }

ntpIPv4Admin OBJECT-TYPE
    SYNTAX      FspR7NtpAdminState
    MAX-ACCESS  read-create
    STATUS      current
    DESCRIPTION   "Administrative state of remote NTP server. It can be set to is(2) or to dsbld(6)"
    ::=  { ntpIPv4Entry 7 }

ntpIPv4OperState OBJECT-TYPE
    SYNTAX      FspR7OperState
    MAX-ACCESS  read-only
    STATUS      current
    DESCRIPTION   "Operative state of remote NTP server"
    ::=  { ntpIPv4Entry 8 }

ntpIPv4IpAddr OBJECT-TYPE
    SYNTAX      IpAddress
    MAX-ACCESS  read-only
    STATUS      current
    DESCRIPTION   "The IPv4 address of the remote NTP server"
    ::=  { ntpIPv4Entry 9 }

ntpIPv6Table OBJECT-TYPE
    SYNTAX      SEQUENCE OF NtpIPv6Entry
    MAX-ACCESS  not-accessible
    STATUS      current
    DESCRIPTION   "The NTP Server configuration table for IPv6"
    ::=  { dateAndTime 22 }

ntpIPv6Entry OBJECT-TYPE
    SYNTAX      NtpIPv6Entry
    MAX-ACCESS  not-accessible
    STATUS      current
    DESCRIPTION   "The NTP IPv6 Server entity"
    INDEX       {
                  ntpIPv6Ip
                }
    ::=  { ntpIPv6Table 1 }

NtpIPv6Entry ::=  SEQUENCE
  { ntpIPv6Ip FspR7Ipv6Address,
    ntpIPv6RowStatus RowStatus,
    ntpIPv6SourceIp SourceIpAddress,
    ntpIPv6Test FspR7NtpTest,
    ntpIPv6TestStatus FspR7NtpTestStatus,
    ntpIPv6SyncStatus FspR7NtpSyncStatus,
    ntpIPv6Admin FspR7NtpAdminState,
    ntpIPv6OperState FspR7OperState,
    ntpIPv6IpAddr SnmpAdminString }

ntpIPv6Ip OBJECT-TYPE
    SYNTAX      FspR7Ipv6Address
    MAX-ACCESS  accessible-for-notify
    STATUS      current
    DESCRIPTION   "The IPv6 address of the remote NTP server"
    ::=  { ntpIPv6Entry 1 }

ntpIPv6RowStatus OBJECT-TYPE
    SYNTAX      RowStatus
    MAX-ACCESS  read-create
    STATUS      current
    DESCRIPTION   "Row status used for managing a NTP server entity. All values defined for
         RowStatus TC can be used
        "
    ::=  { ntpIPv6Entry 2 }

ntpIPv6SourceIp OBJECT-TYPE
    SYNTAX      SourceIpAddress
    MAX-ACCESS  read-create
    STATUS      current
    DESCRIPTION   "Network interface type used for NTP connection. Two interface types are defined:
         sysIp(1) and defaultIp(2)
        "
    ::=  { ntpIPv6Entry 3 }

ntpIPv6Test OBJECT-TYPE
    SYNTAX      FspR7NtpTest
    MAX-ACCESS  read-write
    STATUS      current
    DESCRIPTION   "Operational parameter for invoking a connection test procedure. If set
         to ntpTest(2) then a connection with remote NTP server is being checked.
         Result of this operation is saved under ntpServerTestStatus column. When
         operation finish then value is automaticaly set to rls(1). It cannot
         be set to rls(1) by hand
        "
    ::=  { ntpIPv6Entry 4 }

ntpIPv6TestStatus OBJECT-TYPE
    SYNTAX      FspR7NtpTestStatus
    MAX-ACCESS  read-only
    STATUS      current
    DESCRIPTION   "Result of NTP availability check command invoked by setting ntpServerTest to ntpTest(2)"
    ::=  { ntpIPv6Entry 5 }

ntpIPv6SyncStatus OBJECT-TYPE
    SYNTAX      FspR7NtpSyncStatus
    MAX-ACCESS  read-only
    STATUS      current
    DESCRIPTION   "The NTP Synchronization status"
    ::=  { ntpIPv6Entry 6 }

ntpIPv6Admin OBJECT-TYPE
    SYNTAX      FspR7NtpAdminState
    MAX-ACCESS  read-create
    STATUS      current
    DESCRIPTION   "Administrative state of remote NTP server. It can be set to is(2) or to dsbld(6)"
    ::=  { ntpIPv6Entry 7 }

ntpIPv6OperState OBJECT-TYPE
    SYNTAX      FspR7OperState
    MAX-ACCESS  read-only
    STATUS      current
    DESCRIPTION   "Operative state of remote NTP server"
    ::=  { ntpIPv6Entry 8 }

ntpIPv6IpAddr OBJECT-TYPE
    SYNTAX      SnmpAdminString
    MAX-ACCESS  read-only
    STATUS      current
    DESCRIPTION   "The IPv6 address of the remote NTP server"
    ::=  { ntpIPv6Entry 9 }

endOfFeatureSpecific OBJECT-TYPE
    SYNTAX      Integer32
    MAX-ACCESS  read-only
    STATUS      current
    DESCRIPTION
        ""
    ::=  { featureSpecific 10000 }

upwardEqptTable OBJECT-TYPE
    SYNTAX      SEQUENCE OF UpwardEqptEntry
    MAX-ACCESS  not-accessible
    STATUS      current
    DESCRIPTION   "upwardEqptTable"
    ::=  { relationship 1 }

upwardEqptEntry OBJECT-TYPE
    SYNTAX      UpwardEqptEntry
    MAX-ACCESS  not-accessible
    STATUS      current
    DESCRIPTION   "Entry of upwardEqptTable"
    INDEX       {
                  upwardEqptShelfNo,
                  upwardEqptSlotNo,
                  upwardEqptPortNo,
                  upwardEqptExtNo,
                  upwardEqptClassName,
                  upwardEqptIndex
                }
    ::=  { upwardEqptTable 1 }

UpwardEqptEntry ::=  SEQUENCE
  { upwardEqptShelfNo Unsigned32,
    upwardEqptSlotNo Unsigned32,
    upwardEqptPortNo Unsigned32,
    upwardEqptExtNo Unsigned32,
    upwardEqptClassName EntityClassName,
    upwardEqptIndex Unsigned32,
    upwardEqptParentId RowPointer }

upwardEqptShelfNo OBJECT-TYPE
    SYNTAX      Unsigned32
    MAX-ACCESS  not-accessible
    STATUS      current
    DESCRIPTION   "Adress index."
    ::=  { upwardEqptEntry 1 }

upwardEqptSlotNo OBJECT-TYPE
    SYNTAX      Unsigned32
    MAX-ACCESS  not-accessible
    STATUS      current
    DESCRIPTION   "Adress index."
    ::=  { upwardEqptEntry 2 }

upwardEqptPortNo OBJECT-TYPE
    SYNTAX      Unsigned32
    MAX-ACCESS  not-accessible
    STATUS      current
    DESCRIPTION   "Adress index."
    ::=  { upwardEqptEntry 3 }

upwardEqptExtNo OBJECT-TYPE
    SYNTAX      Unsigned32
    MAX-ACCESS  not-accessible
    STATUS      current
    DESCRIPTION   "Adress index."
    ::=  { upwardEqptEntry 4 }

upwardEqptClassName OBJECT-TYPE
    SYNTAX      EntityClassName
    MAX-ACCESS  not-accessible
    STATUS      current
    DESCRIPTION
        "Entity Class Name"
    ::=  { upwardEqptEntry 5 }

upwardEqptIndex OBJECT-TYPE
    SYNTAX      Unsigned32
    MAX-ACCESS  not-accessible
    STATUS      current
    DESCRIPTION   "Number of sequence."
    ::=  { upwardEqptEntry 6 }

upwardEqptParentId OBJECT-TYPE
    SYNTAX      RowPointer
    MAX-ACCESS  read-only
    STATUS      current
    DESCRIPTION   "RowPointer to parent entity reported in corresponding entity table."
    ::=  { upwardEqptEntry 7 }

endOfUpwardEqptTable OBJECT-TYPE
    SYNTAX      Integer32
    MAX-ACCESS  read-only
    STATUS      current
    DESCRIPTION
        ""
    ::=  { relationship 2 }

downwardEqptTable OBJECT-TYPE
    SYNTAX      SEQUENCE OF DownwardEqptEntry
    MAX-ACCESS  not-accessible
    STATUS      current
    DESCRIPTION   "downwardEqptTable"
    ::=  { relationship 3 }

downwardEqptEntry OBJECT-TYPE
    SYNTAX      DownwardEqptEntry
    MAX-ACCESS  not-accessible
    STATUS      current
    DESCRIPTION   "Entry of downwardEqptTable"
    INDEX       {
                  downwardEqptShelfNo,
                  downwardEqptSlotNo,
                  downwardEqptPortNo,
                  downwardEqptExtNo,
                  downwardEqptClassName,
                  downwardEqptIndex
                }
    ::=  { downwardEqptTable 1 }

DownwardEqptEntry ::=  SEQUENCE
  { downwardEqptShelfNo Unsigned32,
    downwardEqptSlotNo Unsigned32,
    downwardEqptPortNo Unsigned32,
    downwardEqptExtNo Unsigned32,
    downwardEqptClassName EntityClassName,
    downwardEqptIndex Unsigned32,
    downwardEqptChildId RowPointer }

downwardEqptShelfNo OBJECT-TYPE
    SYNTAX      Unsigned32
    MAX-ACCESS  not-accessible
    STATUS      current
    DESCRIPTION   "Adress index."
    ::=  { downwardEqptEntry 1 }

downwardEqptSlotNo OBJECT-TYPE
    SYNTAX      Unsigned32
    MAX-ACCESS  not-accessible
    STATUS      current
    DESCRIPTION   "Adress index."
    ::=  { downwardEqptEntry 2 }

downwardEqptPortNo OBJECT-TYPE
    SYNTAX      Unsigned32
    MAX-ACCESS  not-accessible
    STATUS      current
    DESCRIPTION   "Adress index."
    ::=  { downwardEqptEntry 3 }

downwardEqptExtNo OBJECT-TYPE
    SYNTAX      Unsigned32
    MAX-ACCESS  not-accessible
    STATUS      current
    DESCRIPTION   "Adress index."
    ::=  { downwardEqptEntry 4 }

downwardEqptClassName OBJECT-TYPE
    SYNTAX      EntityClassName
    MAX-ACCESS  not-accessible
    STATUS      current
    DESCRIPTION
        "Entity Class Name"
    ::=  { downwardEqptEntry 5 }

downwardEqptIndex OBJECT-TYPE
    SYNTAX      Unsigned32
    MAX-ACCESS  not-accessible
    STATUS      current
    DESCRIPTION   "Number of sequence."
    ::=  { downwardEqptEntry 6 }

downwardEqptChildId OBJECT-TYPE
    SYNTAX      RowPointer
    MAX-ACCESS  read-only
    STATUS      current
    DESCRIPTION   "RowPointer to child entity."
    ::=  { downwardEqptEntry 7 }

endOfDownwardEqptTable OBJECT-TYPE
    SYNTAX      Integer32
    MAX-ACCESS  read-only
    STATUS      current
    DESCRIPTION
        ""
    ::=  { relationship 4 }

upwardDcnTable OBJECT-TYPE
    SYNTAX      SEQUENCE OF UpwardDcnEntry
    MAX-ACCESS  not-accessible
    STATUS      current
    DESCRIPTION   "upwardDcnTable"
    ::=  { relationship 5 }

upwardDcnEntry OBJECT-TYPE
    SYNTAX      UpwardDcnEntry
    MAX-ACCESS  not-accessible
    STATUS      current
    DESCRIPTION   "Entry of upwardDcnTable"
    INDEX       {
                  upwardDcnShelfNo,
                  upwardDcnSlotNo,
                  upwardDcnPortNo,
                  upwardDcnExtNo,
                  upwardDcnClassName,
                  upwardDcnIndex
                }
    ::=  { upwardDcnTable 1 }

UpwardDcnEntry ::=  SEQUENCE
  { upwardDcnShelfNo Unsigned32,
    upwardDcnSlotNo Unsigned32,
    upwardDcnPortNo Unsigned32,
    upwardDcnExtNo Unsigned32,
    upwardDcnClassName EntityClassName,
    upwardDcnIndex Unsigned32,
    upwardDcnParentId RowPointer }

upwardDcnShelfNo OBJECT-TYPE
    SYNTAX      Unsigned32
    MAX-ACCESS  not-accessible
    STATUS      current
    DESCRIPTION   "Adress index."
    ::=  { upwardDcnEntry 1 }

upwardDcnSlotNo OBJECT-TYPE
    SYNTAX      Unsigned32
    MAX-ACCESS  not-accessible
    STATUS      current
    DESCRIPTION   "Adress index."
    ::=  { upwardDcnEntry 2 }

upwardDcnPortNo OBJECT-TYPE
    SYNTAX      Unsigned32
    MAX-ACCESS  not-accessible
    STATUS      current
    DESCRIPTION   "Adress index."
    ::=  { upwardDcnEntry 3 }

upwardDcnExtNo OBJECT-TYPE
    SYNTAX      Unsigned32
    MAX-ACCESS  not-accessible
    STATUS      current
    DESCRIPTION   "Adress index."
    ::=  { upwardDcnEntry 4 }

upwardDcnClassName OBJECT-TYPE
    SYNTAX      EntityClassName
    MAX-ACCESS  not-accessible
    STATUS      current
    DESCRIPTION
        "Entity Class Name"
    ::=  { upwardDcnEntry 5 }

upwardDcnIndex OBJECT-TYPE
    SYNTAX      Unsigned32
    MAX-ACCESS  not-accessible
    STATUS      current
    DESCRIPTION   "Number of sequence."
    ::=  { upwardDcnEntry 6 }

upwardDcnParentId OBJECT-TYPE
    SYNTAX      RowPointer
    MAX-ACCESS  read-only
    STATUS      current
    DESCRIPTION   "RowPointer to parent entity reported in corresponding entity table."
    ::=  { upwardDcnEntry 7 }

endOfUpwardDcnTable OBJECT-TYPE
    SYNTAX      Integer32
    MAX-ACCESS  read-only
    STATUS      current
    DESCRIPTION
        ""
    ::=  { relationship 6 }

downwardDcnTable OBJECT-TYPE
    SYNTAX      SEQUENCE OF DownwardDcnEntry
    MAX-ACCESS  not-accessible
    STATUS      current
    DESCRIPTION   "downwardDcnTable"
    ::=  { relationship 7 }

downwardDcnEntry OBJECT-TYPE
    SYNTAX      DownwardDcnEntry
    MAX-ACCESS  not-accessible
    STATUS      current
    DESCRIPTION   "Entry of downwardDcnTable"
    INDEX       {
                  downwardDcnShelfNo,
                  downwardDcnSlotNo,
                  downwardDcnPortNo,
                  downwardDcnExtNo,
                  downwardDcnClassName,
                  downwardDcnIndex
                }
    ::=  { downwardDcnTable 1 }

DownwardDcnEntry ::=  SEQUENCE
  { downwardDcnShelfNo Unsigned32,
    downwardDcnSlotNo Unsigned32,
    downwardDcnPortNo Unsigned32,
    downwardDcnExtNo Unsigned32,
    downwardDcnClassName EntityClassName,
    downwardDcnIndex Unsigned32,
    downwardDcnChildId RowPointer }

downwardDcnShelfNo OBJECT-TYPE
    SYNTAX      Unsigned32
    MAX-ACCESS  not-accessible
    STATUS      current
    DESCRIPTION   "Adress index."
    ::=  { downwardDcnEntry 1 }

downwardDcnSlotNo OBJECT-TYPE
    SYNTAX      Unsigned32
    MAX-ACCESS  not-accessible
    STATUS      current
    DESCRIPTION   "Adress index."
    ::=  { downwardDcnEntry 2 }

downwardDcnPortNo OBJECT-TYPE
    SYNTAX      Unsigned32
    MAX-ACCESS  not-accessible
    STATUS      current
    DESCRIPTION   "Adress index."
    ::=  { downwardDcnEntry 3 }

downwardDcnExtNo OBJECT-TYPE
    SYNTAX      Unsigned32
    MAX-ACCESS  not-accessible
    STATUS      current
    DESCRIPTION   "Adress index."
    ::=  { downwardDcnEntry 4 }

downwardDcnClassName OBJECT-TYPE
    SYNTAX      EntityClassName
    MAX-ACCESS  not-accessible
    STATUS      current
    DESCRIPTION
        "Entity Class Name"
    ::=  { downwardDcnEntry 5 }

downwardDcnIndex OBJECT-TYPE
    SYNTAX      Unsigned32
    MAX-ACCESS  not-accessible
    STATUS      current
    DESCRIPTION   "Number of sequence."
    ::=  { downwardDcnEntry 6 }

downwardDcnChildId OBJECT-TYPE
    SYNTAX      RowPointer
    MAX-ACCESS  read-only
    STATUS      current
    DESCRIPTION   "RowPointer to child entity."
    ::=  { downwardDcnEntry 7 }

endOfDownwardDcnTable OBJECT-TYPE
    SYNTAX      Integer32
    MAX-ACCESS  read-only
    STATUS      current
    DESCRIPTION
        ""
    ::=  { relationship 8 }

upwardEnvTable OBJECT-TYPE
    SYNTAX      SEQUENCE OF UpwardEnvEntry
    MAX-ACCESS  not-accessible
    STATUS      current
    DESCRIPTION   "upwardEnvTable"
    ::=  { relationship 9 }

upwardEnvEntry OBJECT-TYPE
    SYNTAX      UpwardEnvEntry
    MAX-ACCESS  not-accessible
    STATUS      current
    DESCRIPTION   "Entry of upwardEnvTable"
    INDEX       {
                  upwardEnvShelfNo,
                  upwardEnvSlotNo,
                  upwardEnvPortNo,
                  upwardEnvExtNo,
                  upwardEnvClassName,
                  upwardEnvIndex
                }
    ::=  { upwardEnvTable 1 }

UpwardEnvEntry ::=  SEQUENCE
  { upwardEnvShelfNo Unsigned32,
    upwardEnvSlotNo Unsigned32,
    upwardEnvPortNo Unsigned32,
    upwardEnvExtNo Unsigned32,
    upwardEnvClassName EntityClassName,
    upwardEnvIndex Unsigned32,
    upwardEnvParentId RowPointer }

upwardEnvShelfNo OBJECT-TYPE
    SYNTAX      Unsigned32
    MAX-ACCESS  not-accessible
    STATUS      current
    DESCRIPTION   "Adress index."
    ::=  { upwardEnvEntry 1 }

upwardEnvSlotNo OBJECT-TYPE
    SYNTAX      Unsigned32
    MAX-ACCESS  not-accessible
    STATUS      current
    DESCRIPTION   "Adress index."
    ::=  { upwardEnvEntry 2 }

upwardEnvPortNo OBJECT-TYPE
    SYNTAX      Unsigned32
    MAX-ACCESS  not-accessible
    STATUS      current
    DESCRIPTION   "Adress index."
    ::=  { upwardEnvEntry 3 }

upwardEnvExtNo OBJECT-TYPE
    SYNTAX      Unsigned32
    MAX-ACCESS  not-accessible
    STATUS      current
    DESCRIPTION   "Adress index."
    ::=  { upwardEnvEntry 4 }

upwardEnvClassName OBJECT-TYPE
    SYNTAX      EntityClassName
    MAX-ACCESS  not-accessible
    STATUS      current
    DESCRIPTION
        "Entity Class Name"
    ::=  { upwardEnvEntry 5 }

upwardEnvIndex OBJECT-TYPE
    SYNTAX      Unsigned32
    MAX-ACCESS  not-accessible
    STATUS      current
    DESCRIPTION   "Number of sequence."
    ::=  { upwardEnvEntry 6 }

upwardEnvParentId OBJECT-TYPE
    SYNTAX      RowPointer
    MAX-ACCESS  read-only
    STATUS      current
    DESCRIPTION   "RowPointer to parent entity reported in corresponding entity table."
    ::=  { upwardEnvEntry 7 }

endOfUpwardEnvTable OBJECT-TYPE
    SYNTAX      Integer32
    MAX-ACCESS  read-only
    STATUS      current
    DESCRIPTION
        ""
    ::=  { relationship 10 }

downwardEnvTable OBJECT-TYPE
    SYNTAX      SEQUENCE OF DownwardEnvEntry
    MAX-ACCESS  not-accessible
    STATUS      current
    DESCRIPTION   "downwardEnvTable"
    ::=  { relationship 11 }

downwardEnvEntry OBJECT-TYPE
    SYNTAX      DownwardEnvEntry
    MAX-ACCESS  not-accessible
    STATUS      current
    DESCRIPTION   "Entry of downwardEnvTable"
    INDEX       {
                  downwardEnvShelfNo,
                  downwardEnvSlotNo,
                  downwardEnvPortNo,
                  downwardEnvExtNo,
                  downwardEnvClassName,
                  downwardEnvIndex
                }
    ::=  { downwardEnvTable 1 }

DownwardEnvEntry ::=  SEQUENCE
  { downwardEnvShelfNo Unsigned32,
    downwardEnvSlotNo Unsigned32,
    downwardEnvPortNo Unsigned32,
    downwardEnvExtNo Unsigned32,
    downwardEnvClassName EntityClassName,
    downwardEnvIndex Unsigned32,
    downwardEnvChildId RowPointer }

downwardEnvShelfNo OBJECT-TYPE
    SYNTAX      Unsigned32
    MAX-ACCESS  not-accessible
    STATUS      current
    DESCRIPTION   "Adress index."
    ::=  { downwardEnvEntry 1 }

downwardEnvSlotNo OBJECT-TYPE
    SYNTAX      Unsigned32
    MAX-ACCESS  not-accessible
    STATUS      current
    DESCRIPTION   "Adress index."
    ::=  { downwardEnvEntry 2 }

downwardEnvPortNo OBJECT-TYPE
    SYNTAX      Unsigned32
    MAX-ACCESS  not-accessible
    STATUS      current
    DESCRIPTION   "Adress index."
    ::=  { downwardEnvEntry 3 }

downwardEnvExtNo OBJECT-TYPE
    SYNTAX      Unsigned32
    MAX-ACCESS  not-accessible
    STATUS      current
    DESCRIPTION   "Adress index."
    ::=  { downwardEnvEntry 4 }

downwardEnvClassName OBJECT-TYPE
    SYNTAX      EntityClassName
    MAX-ACCESS  not-accessible
    STATUS      current
    DESCRIPTION
        "Entity Class Name"
    ::=  { downwardEnvEntry 5 }

downwardEnvIndex OBJECT-TYPE
    SYNTAX      Unsigned32
    MAX-ACCESS  not-accessible
    STATUS      current
    DESCRIPTION   "Number of sequence."
    ::=  { downwardEnvEntry 6 }

downwardEnvChildId OBJECT-TYPE
    SYNTAX      RowPointer
    MAX-ACCESS  read-only
    STATUS      current
    DESCRIPTION   "RowPointer to child entity."
    ::=  { downwardEnvEntry 7 }

endOfDownwardEnvTable OBJECT-TYPE
    SYNTAX      Integer32
    MAX-ACCESS  read-only
    STATUS      current
    DESCRIPTION
        ""
    ::=  { relationship 12 }

upwardFacilityTable OBJECT-TYPE
    SYNTAX      SEQUENCE OF UpwardFacilityEntry
    MAX-ACCESS  not-accessible
    STATUS      current
    DESCRIPTION   "upwardFacilityTable"
    ::=  { relationship 13 }

upwardFacilityEntry OBJECT-TYPE
    SYNTAX      UpwardFacilityEntry
    MAX-ACCESS  not-accessible
    STATUS      current
    DESCRIPTION   "Entry of upwardFacilityTable"
    INDEX       {
                  upwardFacilityShelfNo,
                  upwardFacilitySlotNo,
                  upwardFacilityPortNo,
                  upwardFacilityExtNo,
                  upwardFacilityClassName,
                  upwardFacilityIndex
                }
    ::=  { upwardFacilityTable 1 }

UpwardFacilityEntry ::=  SEQUENCE
  { upwardFacilityShelfNo Unsigned32,
    upwardFacilitySlotNo Unsigned32,
    upwardFacilityPortNo Unsigned32,
    upwardFacilityExtNo Unsigned32,
    upwardFacilityClassName EntityClassName,
    upwardFacilityIndex Unsigned32,
    upwardFacilityParentId RowPointer }

upwardFacilityShelfNo OBJECT-TYPE
    SYNTAX      Unsigned32
    MAX-ACCESS  not-accessible
    STATUS      current
    DESCRIPTION   "Adress index."
    ::=  { upwardFacilityEntry 1 }

upwardFacilitySlotNo OBJECT-TYPE
    SYNTAX      Unsigned32
    MAX-ACCESS  not-accessible
    STATUS      current
    DESCRIPTION   "Adress index."
    ::=  { upwardFacilityEntry 2 }

upwardFacilityPortNo OBJECT-TYPE
    SYNTAX      Unsigned32
    MAX-ACCESS  not-accessible
    STATUS      current
    DESCRIPTION   "Adress index."
    ::=  { upwardFacilityEntry 3 }

upwardFacilityExtNo OBJECT-TYPE
    SYNTAX      Unsigned32
    MAX-ACCESS  not-accessible
    STATUS      current
    DESCRIPTION   "Adress index."
    ::=  { upwardFacilityEntry 4 }

upwardFacilityClassName OBJECT-TYPE
    SYNTAX      EntityClassName
    MAX-ACCESS  not-accessible
    STATUS      current
    DESCRIPTION
        "Entity Class Name"
    ::=  { upwardFacilityEntry 5 }

upwardFacilityIndex OBJECT-TYPE
    SYNTAX      Unsigned32
    MAX-ACCESS  not-accessible
    STATUS      current
    DESCRIPTION   "Number of sequence."
    ::=  { upwardFacilityEntry 6 }

upwardFacilityParentId OBJECT-TYPE
    SYNTAX      RowPointer
    MAX-ACCESS  read-only
    STATUS      current
    DESCRIPTION   "RowPointer to parent entity reported in corresponding entity table."
    ::=  { upwardFacilityEntry 7 }

downwardFacilityTable OBJECT-TYPE
    SYNTAX      SEQUENCE OF DownwardFacilityEntry
    MAX-ACCESS  not-accessible
    STATUS      current
    DESCRIPTION   "downwardFacilityTable"
    ::=  { relationship 14 }

downwardFacilityEntry OBJECT-TYPE
    SYNTAX      DownwardFacilityEntry
    MAX-ACCESS  not-accessible
    STATUS      current
    DESCRIPTION   "Entry of downwardFacilityTable"
    INDEX       {
                  downwardFacilityShelfNo,
                  downwardFacilitySlotNo,
                  downwardFacilityPortNo,
                  downwardFacilityExtNo,
                  downwardFacilityClassName,
                  downwardFacilityIndex
                }
    ::=  { downwardFacilityTable 1 }

DownwardFacilityEntry ::=  SEQUENCE
  { downwardFacilityShelfNo Unsigned32,
    downwardFacilitySlotNo Unsigned32,
    downwardFacilityPortNo Unsigned32,
    downwardFacilityExtNo Unsigned32,
    downwardFacilityClassName EntityClassName,
    downwardFacilityIndex Unsigned32,
    downwardFacilityChildId RowPointer }

downwardFacilityShelfNo OBJECT-TYPE
    SYNTAX      Unsigned32
    MAX-ACCESS  not-accessible
    STATUS      current
    DESCRIPTION   "Adress index."
    ::=  { downwardFacilityEntry 1 }

downwardFacilitySlotNo OBJECT-TYPE
    SYNTAX      Unsigned32
    MAX-ACCESS  not-accessible
    STATUS      current
    DESCRIPTION   "Adress index."
    ::=  { downwardFacilityEntry 2 }

downwardFacilityPortNo OBJECT-TYPE
    SYNTAX      Unsigned32
    MAX-ACCESS  not-accessible
    STATUS      current
    DESCRIPTION   "Adress index."
    ::=  { downwardFacilityEntry 3 }

downwardFacilityExtNo OBJECT-TYPE
    SYNTAX      Unsigned32
    MAX-ACCESS  not-accessible
    STATUS      current
    DESCRIPTION   "Adress index."
    ::=  { downwardFacilityEntry 4 }

downwardFacilityClassName OBJECT-TYPE
    SYNTAX      EntityClassName
    MAX-ACCESS  not-accessible
    STATUS      current
    DESCRIPTION
        "Entity Class Name"
    ::=  { downwardFacilityEntry 5 }

downwardFacilityIndex OBJECT-TYPE
    SYNTAX      Unsigned32
    MAX-ACCESS  not-accessible
    STATUS      current
    DESCRIPTION   "Number of sequence."
    ::=  { downwardFacilityEntry 6 }

downwardFacilityChildId OBJECT-TYPE
    SYNTAX      RowPointer
    MAX-ACCESS  read-only
    STATUS      current
    DESCRIPTION   "RowPointer to child entity."
    ::=  { downwardFacilityEntry 7 }

endOfDownwardFacilityTable OBJECT-TYPE
    SYNTAX      Integer32
    MAX-ACCESS  read-only
    STATUS      current
    DESCRIPTION
        ""
    ::=  { relationship 15 }

upwardOptLineTable OBJECT-TYPE
    SYNTAX      SEQUENCE OF UpwardOptLineEntry
    MAX-ACCESS  not-accessible
    STATUS      current
    DESCRIPTION   "upwardOptLineTable"
    ::=  { relationship 16 }

upwardOptLineEntry OBJECT-TYPE
    SYNTAX      UpwardOptLineEntry
    MAX-ACCESS  not-accessible
    STATUS      current
    DESCRIPTION   "Entry of upwardOptLineTable"
    INDEX       {
                  upwardOptLineShelfNo,
                  upwardOptLineSlotNo,
                  upwardOptLinePortNo,
                  upwardOptLineExtNo,
                  upwardOptLineClassName,
                  upwardOptLineIndex
                }
    ::=  { upwardOptLineTable 1 }

UpwardOptLineEntry ::=  SEQUENCE
  { upwardOptLineShelfNo Unsigned32,
    upwardOptLineSlotNo Unsigned32,
    upwardOptLinePortNo Unsigned32,
    upwardOptLineExtNo Unsigned32,
    upwardOptLineClassName EntityClassName,
    upwardOptLineIndex Unsigned32,
    upwardOptLineParentId RowPointer }

upwardOptLineShelfNo OBJECT-TYPE
    SYNTAX      Unsigned32
    MAX-ACCESS  not-accessible
    STATUS      current
    DESCRIPTION   "Adress index."
    ::=  { upwardOptLineEntry 1 }

upwardOptLineSlotNo OBJECT-TYPE
    SYNTAX      Unsigned32
    MAX-ACCESS  not-accessible
    STATUS      current
    DESCRIPTION   "Adress index."
    ::=  { upwardOptLineEntry 2 }

upwardOptLinePortNo OBJECT-TYPE
    SYNTAX      Unsigned32
    MAX-ACCESS  not-accessible
    STATUS      current
    DESCRIPTION   "Adress index."
    ::=  { upwardOptLineEntry 3 }

upwardOptLineExtNo OBJECT-TYPE
    SYNTAX      Unsigned32
    MAX-ACCESS  not-accessible
    STATUS      current
    DESCRIPTION   "Adress index."
    ::=  { upwardOptLineEntry 4 }

upwardOptLineClassName OBJECT-TYPE
    SYNTAX      EntityClassName
    MAX-ACCESS  not-accessible
    STATUS      current
    DESCRIPTION
        "Entity Class Name"
    ::=  { upwardOptLineEntry 5 }

upwardOptLineIndex OBJECT-TYPE
    SYNTAX      Unsigned32
    MAX-ACCESS  not-accessible
    STATUS      current
    DESCRIPTION   "Number of sequence."
    ::=  { upwardOptLineEntry 6 }

upwardOptLineParentId OBJECT-TYPE
    SYNTAX      RowPointer
    MAX-ACCESS  read-only
    STATUS      current
    DESCRIPTION   "RowPointer to parent entity reported in corresponding entity table."
    ::=  { upwardOptLineEntry 7 }

endOfUpwardOptLineTable OBJECT-TYPE
    SYNTAX      Integer32
    MAX-ACCESS  read-only
    STATUS      current
    DESCRIPTION
        ""
    ::=  { relationship 17 }

downwardOptLineTable OBJECT-TYPE
    SYNTAX      SEQUENCE OF DownwardOptLineEntry
    MAX-ACCESS  not-accessible
    STATUS      current
    DESCRIPTION   "downwardOptLineTable"
    ::=  { relationship 18 }

downwardOptLineEntry OBJECT-TYPE
    SYNTAX      DownwardOptLineEntry
    MAX-ACCESS  not-accessible
    STATUS      current
    DESCRIPTION   "Entry of downwardOptLineTable"
    INDEX       {
                  downwardOptLineShelfNo,
                  downwardOptLineSlotNo,
                  downwardOptLinePortNo,
                  downwardOptLineExtNo,
                  downwardOptLineClassName,
                  downwardOptLineIndex
                }
    ::=  { downwardOptLineTable 1 }

DownwardOptLineEntry ::=  SEQUENCE
  { downwardOptLineShelfNo Unsigned32,
    downwardOptLineSlotNo Unsigned32,
    downwardOptLinePortNo Unsigned32,
    downwardOptLineExtNo Unsigned32,
    downwardOptLineClassName EntityClassName,
    downwardOptLineIndex Unsigned32,
    downwardOptLineChildId RowPointer }

downwardOptLineShelfNo OBJECT-TYPE
    SYNTAX      Unsigned32
    MAX-ACCESS  not-accessible
    STATUS      current
    DESCRIPTION   "Adress index."
    ::=  { downwardOptLineEntry 1 }

downwardOptLineSlotNo OBJECT-TYPE
    SYNTAX      Unsigned32
    MAX-ACCESS  not-accessible
    STATUS      current
    DESCRIPTION   "Adress index."
    ::=  { downwardOptLineEntry 2 }

downwardOptLinePortNo OBJECT-TYPE
    SYNTAX      Unsigned32
    MAX-ACCESS  not-accessible
    STATUS      current
    DESCRIPTION   "Adress index."
    ::=  { downwardOptLineEntry 3 }

downwardOptLineExtNo OBJECT-TYPE
    SYNTAX      Unsigned32
    MAX-ACCESS  not-accessible
    STATUS      current
    DESCRIPTION   "Adress index."
    ::=  { downwardOptLineEntry 4 }

downwardOptLineClassName OBJECT-TYPE
    SYNTAX      EntityClassName
    MAX-ACCESS  not-accessible
    STATUS      current
    DESCRIPTION
        "Entity Class Name"
    ::=  { downwardOptLineEntry 5 }

downwardOptLineIndex OBJECT-TYPE
    SYNTAX      Unsigned32
    MAX-ACCESS  not-accessible
    STATUS      current
    DESCRIPTION   "Number of sequence."
    ::=  { downwardOptLineEntry 6 }

downwardOptLineChildId OBJECT-TYPE
    SYNTAX      RowPointer
    MAX-ACCESS  read-only
    STATUS      current
    DESCRIPTION   "RowPointer to child entity."
    ::=  { downwardOptLineEntry 7 }

upwardTerminPointTable OBJECT-TYPE
    SYNTAX      SEQUENCE OF UpwardTerminPointEntry
    MAX-ACCESS  not-accessible
    STATUS      current
    DESCRIPTION   "upwardTerminPointTable"
    ::=  { relationship 19 }

upwardTerminPointEntry OBJECT-TYPE
    SYNTAX      UpwardTerminPointEntry
    MAX-ACCESS  not-accessible
    STATUS      current
    DESCRIPTION   "Entry of upwardTerminPointTable"
    INDEX       {
                  upwardTerminPointIndexNo1,
                  upwardTerminPointIndexNo2,
                  upwardTerminPointIndexNo3,
                  upwardTerminPointIndexNo4,
                  upwardTerminPointClassName,
                  upwardTerminPointIndex
                }
    ::=  { upwardTerminPointTable 1 }

UpwardTerminPointEntry ::=  SEQUENCE
  { upwardTerminPointIndexNo1 Unsigned32,
    upwardTerminPointIndexNo2 Unsigned32,
    upwardTerminPointIndexNo3 Unsigned32,
    upwardTerminPointIndexNo4 Unsigned32,
    upwardTerminPointClassName EntityClassName,
    upwardTerminPointIndex Unsigned32,
    upwardTerminPointParentId RowPointer }

upwardTerminPointIndexNo1 OBJECT-TYPE
    SYNTAX      Unsigned32
    MAX-ACCESS  not-accessible
    STATUS      current
    DESCRIPTION   "Adress index."
    ::=  { upwardTerminPointEntry 1 }

upwardTerminPointIndexNo2 OBJECT-TYPE
    SYNTAX      Unsigned32
    MAX-ACCESS  not-accessible
    STATUS      current
    DESCRIPTION   "Adress index."
    ::=  { upwardTerminPointEntry 2 }

upwardTerminPointIndexNo3 OBJECT-TYPE
    SYNTAX      Unsigned32
    MAX-ACCESS  not-accessible
    STATUS      current
    DESCRIPTION   "Adress index."
    ::=  { upwardTerminPointEntry 3 }

upwardTerminPointIndexNo4 OBJECT-TYPE
    SYNTAX      Unsigned32
    MAX-ACCESS  not-accessible
    STATUS      current
    DESCRIPTION   "Adress index."
    ::=  { upwardTerminPointEntry 4 }

upwardTerminPointClassName OBJECT-TYPE
    SYNTAX      EntityClassName
    MAX-ACCESS  not-accessible
    STATUS      current
    DESCRIPTION
        "Entity Class Name"
    ::=  { upwardTerminPointEntry 5 }

upwardTerminPointIndex OBJECT-TYPE
    SYNTAX      Unsigned32
    MAX-ACCESS  not-accessible
    STATUS      current
    DESCRIPTION   "Number of sequence."
    ::=  { upwardTerminPointEntry 6 }

upwardTerminPointParentId OBJECT-TYPE
    SYNTAX      RowPointer
    MAX-ACCESS  read-only
    STATUS      current
    DESCRIPTION   "RowPointer to parent entity reported in corresponding entity table."
    ::=  { upwardTerminPointEntry 7 }

downwardTerminPointTable OBJECT-TYPE
    SYNTAX      SEQUENCE OF DownwardTerminPointEntry
    MAX-ACCESS  not-accessible
    STATUS      current
    DESCRIPTION   "downwardTerminPointTable"
    ::=  { relationship 20 }

downwardTerminPointEntry OBJECT-TYPE
    SYNTAX      DownwardTerminPointEntry
    MAX-ACCESS  not-accessible
    STATUS      current
    DESCRIPTION   "Entry of downwardTerminPointTable"
    INDEX       {
                  downwardTerminPointIndexNo1,
                  downwardTerminPointIndexNo2,
                  downwardTerminPointIndexNo3,
                  downwardTerminPointIndexNo4,
                  downwardTerminPointClassName,
                  downwardTerminPointIndex
                }
    ::=  { downwardTerminPointTable 1 }

DownwardTerminPointEntry ::=  SEQUENCE
  { downwardTerminPointIndexNo1 Unsigned32,
    downwardTerminPointIndexNo2 Unsigned32,
    downwardTerminPointIndexNo3 Unsigned32,
    downwardTerminPointIndexNo4 Unsigned32,
    downwardTerminPointClassName EntityClassName,
    downwardTerminPointIndex Unsigned32,
    downwardTerminPointChildId RowPointer }

downwardTerminPointIndexNo1 OBJECT-TYPE
    SYNTAX      Unsigned32
    MAX-ACCESS  not-accessible
    STATUS      current
    DESCRIPTION   "Adress index."
    ::=  { downwardTerminPointEntry 1 }

downwardTerminPointIndexNo2 OBJECT-TYPE
    SYNTAX      Unsigned32
    MAX-ACCESS  not-accessible
    STATUS      current
    DESCRIPTION   "Adress index."
    ::=  { downwardTerminPointEntry 2 }

downwardTerminPointIndexNo3 OBJECT-TYPE
    SYNTAX      Unsigned32
    MAX-ACCESS  not-accessible
    STATUS      current
    DESCRIPTION   "Adress index."
    ::=  { downwardTerminPointEntry 3 }

downwardTerminPointIndexNo4 OBJECT-TYPE
    SYNTAX      Unsigned32
    MAX-ACCESS  not-accessible
    STATUS      current
    DESCRIPTION   "Adress index."
    ::=  { downwardTerminPointEntry 4 }

downwardTerminPointClassName OBJECT-TYPE
    SYNTAX      EntityClassName
    MAX-ACCESS  not-accessible
    STATUS      current
    DESCRIPTION
        "Entity Class Name"
    ::=  { downwardTerminPointEntry 5 }

downwardTerminPointIndex OBJECT-TYPE
    SYNTAX      Unsigned32
    MAX-ACCESS  not-accessible
    STATUS      current
    DESCRIPTION   "Number of sequence."
    ::=  { downwardTerminPointEntry 6 }

downwardTerminPointChildId OBJECT-TYPE
    SYNTAX      RowPointer
    MAX-ACCESS  read-only
    STATUS      current
    DESCRIPTION   "RowPointer to child entity."
    ::=  { downwardTerminPointEntry 7 }

endOfDownwardTerminPointTable OBJECT-TYPE
    SYNTAX      Integer32
    MAX-ACCESS  read-only
    STATUS      current
    DESCRIPTION
        ""
    ::=  { relationship 21 }

upwardExternalPortTable OBJECT-TYPE
    SYNTAX      SEQUENCE OF UpwardExternalPortEntry
    MAX-ACCESS  not-accessible
    STATUS      current
    DESCRIPTION   "upwardExternalPortTable"
    ::=  { relationship 23 }

upwardExternalPortEntry OBJECT-TYPE
    SYNTAX      UpwardExternalPortEntry
    MAX-ACCESS  not-accessible
    STATUS      current
    DESCRIPTION   "Entry of upwardExternalPortTable"
    INDEX       {
                  upwardExternalPortShelfNo,
                  upwardExternalPortSlotNo,
                  upwardExternalPortPortNo,
                  upwardExternalPortExtNo,
                  upwardExternalPortClassName,
                  upwardExternalPortIndex
                }
    ::=  { upwardExternalPortTable 1 }

UpwardExternalPortEntry ::=  SEQUENCE
  { upwardExternalPortShelfNo Unsigned32,
    upwardExternalPortSlotNo Unsigned32,
    upwardExternalPortPortNo Unsigned32,
    upwardExternalPortExtNo Unsigned32,
    upwardExternalPortClassName EntityClassName,
    upwardExternalPortIndex Unsigned32,
    upwardExternalPortParentId RowPointer }

upwardExternalPortShelfNo OBJECT-TYPE
    SYNTAX      Unsigned32
    MAX-ACCESS  not-accessible
    STATUS      current
    DESCRIPTION   "Adress index."
    ::=  { upwardExternalPortEntry 1 }

upwardExternalPortSlotNo OBJECT-TYPE
    SYNTAX      Unsigned32
    MAX-ACCESS  not-accessible
    STATUS      current
    DESCRIPTION   "Adress index."
    ::=  { upwardExternalPortEntry 2 }

upwardExternalPortPortNo OBJECT-TYPE
    SYNTAX      Unsigned32
    MAX-ACCESS  not-accessible
    STATUS      current
    DESCRIPTION   "Adress index."
    ::=  { upwardExternalPortEntry 3 }

upwardExternalPortExtNo OBJECT-TYPE
    SYNTAX      Unsigned32
    MAX-ACCESS  not-accessible
    STATUS      current
    DESCRIPTION   "Adress index."
    ::=  { upwardExternalPortEntry 4 }

upwardExternalPortClassName OBJECT-TYPE
    SYNTAX      EntityClassName
    MAX-ACCESS  not-accessible
    STATUS      current
    DESCRIPTION
        "Entity Class Name"
    ::=  { upwardExternalPortEntry 5 }

upwardExternalPortIndex OBJECT-TYPE
    SYNTAX      Unsigned32
    MAX-ACCESS  not-accessible
    STATUS      current
    DESCRIPTION   "Number of sequence."
    ::=  { upwardExternalPortEntry 6 }

upwardExternalPortParentId OBJECT-TYPE
    SYNTAX      RowPointer
    MAX-ACCESS  read-only
    STATUS      current
    DESCRIPTION   "RowPointer to parent entity reported in corresponding entity table."
    ::=  { upwardExternalPortEntry 7 }

downwardExternalPortTable OBJECT-TYPE
    SYNTAX      SEQUENCE OF DownwardExternalPortEntry
    MAX-ACCESS  not-accessible
    STATUS      current
    DESCRIPTION   "downwardExternalPortTable"
    ::=  { relationship 24 }

downwardExternalPortEntry OBJECT-TYPE
    SYNTAX      DownwardExternalPortEntry
    MAX-ACCESS  not-accessible
    STATUS      current
    DESCRIPTION   "Entry of downwardExternalPortTable"
    INDEX       {
                  downwardExternalPortShelfNo,
                  downwardExternalPortSlotNo,
                  downwardExternalPortPortNo,
                  downwardExternalPortExtNo,
                  downwardExternalPortClassName,
                  downwardExternalPortIndex
                }
    ::=  { downwardExternalPortTable 1 }

DownwardExternalPortEntry ::=  SEQUENCE
  { downwardExternalPortShelfNo Unsigned32,
    downwardExternalPortSlotNo Unsigned32,
    downwardExternalPortPortNo Unsigned32,
    downwardExternalPortExtNo Unsigned32,
    downwardExternalPortClassName EntityClassName,
    downwardExternalPortIndex Unsigned32,
    downwardExternalPortChildId RowPointer }

downwardExternalPortShelfNo OBJECT-TYPE
    SYNTAX      Unsigned32
    MAX-ACCESS  not-accessible
    STATUS      current
    DESCRIPTION   "Adress index."
    ::=  { downwardExternalPortEntry 1 }

downwardExternalPortSlotNo OBJECT-TYPE
    SYNTAX      Unsigned32
    MAX-ACCESS  not-accessible
    STATUS      current
    DESCRIPTION   "Adress index."
    ::=  { downwardExternalPortEntry 2 }

downwardExternalPortPortNo OBJECT-TYPE
    SYNTAX      Unsigned32
    MAX-ACCESS  not-accessible
    STATUS      current
    DESCRIPTION   "Adress index."
    ::=  { downwardExternalPortEntry 3 }

downwardExternalPortExtNo OBJECT-TYPE
    SYNTAX      Unsigned32
    MAX-ACCESS  not-accessible
    STATUS      current
    DESCRIPTION   "Adress index."
    ::=  { downwardExternalPortEntry 4 }

downwardExternalPortClassName OBJECT-TYPE
    SYNTAX      EntityClassName
    MAX-ACCESS  not-accessible
    STATUS      current
    DESCRIPTION
        "Entity Class Name"
    ::=  { downwardExternalPortEntry 5 }

downwardExternalPortIndex OBJECT-TYPE
    SYNTAX      Unsigned32
    MAX-ACCESS  not-accessible
    STATUS      current
    DESCRIPTION   "Number of sequence."
    ::=  { downwardExternalPortEntry 6 }

downwardExternalPortChildId OBJECT-TYPE
    SYNTAX      RowPointer
    MAX-ACCESS  read-only
    STATUS      current
    DESCRIPTION   "RowPointer to child entity."
    ::=  { downwardExternalPortEntry 7 }

endOfDownwardExternalPortTable OBJECT-TYPE
    SYNTAX      Integer32
    MAX-ACCESS  read-only
    STATUS      current
    DESCRIPTION
        ""
    ::=  { relationship 25 }

upwardContainerTable OBJECT-TYPE
    SYNTAX      SEQUENCE OF UpwardContainerEntry
    MAX-ACCESS  not-accessible
    STATUS      current
    DESCRIPTION   "upwardContainerTable"
    ::=  { relationship 27 }

upwardContainerEntry OBJECT-TYPE
    SYNTAX      UpwardContainerEntry
    MAX-ACCESS  not-accessible
    STATUS      current
    DESCRIPTION   "Entry of upwardContainerTable"
    INDEX       {
                  upwardContainerShelfNo,
                  upwardContainerSlotNo,
                  upwardContainerPortNo,
                  upwardContainerExtNo,
                  upwardContainerClassName,
                  upwardContainerIndex
                }
    ::=  { upwardContainerTable 1 }

UpwardContainerEntry ::=  SEQUENCE
  { upwardContainerShelfNo Unsigned32,
    upwardContainerSlotNo Unsigned32,
    upwardContainerPortNo Unsigned32,
    upwardContainerExtNo Unsigned32,
    upwardContainerClassName EntityClassName,
    upwardContainerIndex Unsigned32,
    upwardContainerParentId RowPointer }

upwardContainerShelfNo OBJECT-TYPE
    SYNTAX      Unsigned32
    MAX-ACCESS  not-accessible
    STATUS      current
    DESCRIPTION   "Adress index."
    ::=  { upwardContainerEntry 1 }

upwardContainerSlotNo OBJECT-TYPE
    SYNTAX      Unsigned32
    MAX-ACCESS  not-accessible
    STATUS      current
    DESCRIPTION   "Adress index."
    ::=  { upwardContainerEntry 2 }

upwardContainerPortNo OBJECT-TYPE
    SYNTAX      Unsigned32
    MAX-ACCESS  not-accessible
    STATUS      current
    DESCRIPTION   "Adress index."
    ::=  { upwardContainerEntry 3 }

upwardContainerExtNo OBJECT-TYPE
    SYNTAX      Unsigned32
    MAX-ACCESS  not-accessible
    STATUS      current
    DESCRIPTION   "Adress index."
    ::=  { upwardContainerEntry 4 }

upwardContainerClassName OBJECT-TYPE
    SYNTAX      EntityClassName
    MAX-ACCESS  not-accessible
    STATUS      current
    DESCRIPTION
        "Entity Class Name"
    ::=  { upwardContainerEntry 5 }

upwardContainerIndex OBJECT-TYPE
    SYNTAX      Unsigned32
    MAX-ACCESS  not-accessible
    STATUS      current
    DESCRIPTION   "Number of sequence."
    ::=  { upwardContainerEntry 6 }

upwardContainerParentId OBJECT-TYPE
    SYNTAX      RowPointer
    MAX-ACCESS  read-only
    STATUS      current
    DESCRIPTION   "RowPointer to parent entity reported in corresponding entity table."
    ::=  { upwardContainerEntry 7 }

endOfUpwardContainerTable OBJECT-TYPE
    SYNTAX      Integer32
    MAX-ACCESS  read-only
    STATUS      current
    DESCRIPTION
        ""
    ::=  { relationship 28 }

downwardContainerTable OBJECT-TYPE
    SYNTAX      SEQUENCE OF DownwardContainerEntry
    MAX-ACCESS  not-accessible
    STATUS      current
    DESCRIPTION   "downwardContainerTable"
    ::=  { relationship 29 }

downwardContainerEntry OBJECT-TYPE
    SYNTAX      DownwardContainerEntry
    MAX-ACCESS  not-accessible
    STATUS      current
    DESCRIPTION   "Entry of downwardContainerTable"
    INDEX       {
                  downwardContainerShelfNo,
                  downwardContainerSlotNo,
                  downwardContainerPortNo,
                  downwardContainerExtNo,
                  downwardContainerClassName,
                  downwardContainerIndex
                }
    ::=  { downwardContainerTable 1 }

DownwardContainerEntry ::=  SEQUENCE
  { downwardContainerShelfNo Unsigned32,
    downwardContainerSlotNo Unsigned32,
    downwardContainerPortNo Unsigned32,
    downwardContainerExtNo Unsigned32,
    downwardContainerClassName EntityClassName,
    downwardContainerIndex Unsigned32,
    downwardContainerChildId RowPointer }

downwardContainerShelfNo OBJECT-TYPE
    SYNTAX      Unsigned32
    MAX-ACCESS  not-accessible
    STATUS      current
    DESCRIPTION   "Adress index."
    ::=  { downwardContainerEntry 1 }

downwardContainerSlotNo OBJECT-TYPE
    SYNTAX      Unsigned32
    MAX-ACCESS  not-accessible
    STATUS      current
    DESCRIPTION   "Adress index."
    ::=  { downwardContainerEntry 2 }

downwardContainerPortNo OBJECT-TYPE
    SYNTAX      Unsigned32
    MAX-ACCESS  not-accessible
    STATUS      current
    DESCRIPTION   "Adress index."
    ::=  { downwardContainerEntry 3 }

downwardContainerExtNo OBJECT-TYPE
    SYNTAX      Unsigned32
    MAX-ACCESS  not-accessible
    STATUS      current
    DESCRIPTION   "Adress index."
    ::=  { downwardContainerEntry 4 }

downwardContainerClassName OBJECT-TYPE
    SYNTAX      EntityClassName
    MAX-ACCESS  not-accessible
    STATUS      current
    DESCRIPTION
        "Entity Class Name"
    ::=  { downwardContainerEntry 5 }

downwardContainerIndex OBJECT-TYPE
    SYNTAX      Unsigned32
    MAX-ACCESS  not-accessible
    STATUS      current
    DESCRIPTION   "Number of sequence."
    ::=  { downwardContainerEntry 6 }

downwardContainerChildId OBJECT-TYPE
    SYNTAX      RowPointer
    MAX-ACCESS  read-only
    STATUS      current
    DESCRIPTION   "RowPointer to child entity."
    ::=  { downwardContainerEntry 7 }

endOfDownwardContainerTable OBJECT-TYPE
    SYNTAX      Integer32
    MAX-ACCESS  read-only
    STATUS      current
    DESCRIPTION
        ""
    ::=  { relationship 30 }

upwardOpticalMuxTable OBJECT-TYPE
    SYNTAX      SEQUENCE OF UpwardOpticalMuxEntry
    MAX-ACCESS  not-accessible
    STATUS      current
    DESCRIPTION   "upwardOpticalMuxTable"
    ::=  { relationship 31 }

upwardOpticalMuxEntry OBJECT-TYPE
    SYNTAX      UpwardOpticalMuxEntry
    MAX-ACCESS  not-accessible
    STATUS      current
    DESCRIPTION   "Entry of upwardOpticalMuxTable"
    INDEX       {
                  upwardOpticalMuxShelfNo,
                  upwardOpticalMuxSlotNo,
                  upwardOpticalMuxPortNo,
                  upwardOpticalMuxExtNo,
                  upwardOpticalMuxClassName,
                  upwardOpticalMuxIndex
                }
    ::=  { upwardOpticalMuxTable 1 }

UpwardOpticalMuxEntry ::=  SEQUENCE
  { upwardOpticalMuxShelfNo Unsigned32,
    upwardOpticalMuxSlotNo Unsigned32,
    upwardOpticalMuxPortNo Unsigned32,
    upwardOpticalMuxExtNo Unsigned32,
    upwardOpticalMuxClassName EntityClassName,
    upwardOpticalMuxIndex Unsigned32,
    upwardOpticalMuxParentId RowPointer }

upwardOpticalMuxShelfNo OBJECT-TYPE
    SYNTAX      Unsigned32
    MAX-ACCESS  not-accessible
    STATUS      current
    DESCRIPTION   "Adress index."
    ::=  { upwardOpticalMuxEntry 1 }

upwardOpticalMuxSlotNo OBJECT-TYPE
    SYNTAX      Unsigned32
    MAX-ACCESS  not-accessible
    STATUS      current
    DESCRIPTION   "Adress index."
    ::=  { upwardOpticalMuxEntry 2 }

upwardOpticalMuxPortNo OBJECT-TYPE
    SYNTAX      Unsigned32
    MAX-ACCESS  not-accessible
    STATUS      current
    DESCRIPTION   "Adress index."
    ::=  { upwardOpticalMuxEntry 3 }

upwardOpticalMuxExtNo OBJECT-TYPE
    SYNTAX      Unsigned32
    MAX-ACCESS  not-accessible
    STATUS      current
    DESCRIPTION   "Adress index."
    ::=  { upwardOpticalMuxEntry 4 }

upwardOpticalMuxClassName OBJECT-TYPE
    SYNTAX      EntityClassName
    MAX-ACCESS  not-accessible
    STATUS      current
    DESCRIPTION
        "Entity Class Name"
    ::=  { upwardOpticalMuxEntry 5 }

upwardOpticalMuxIndex OBJECT-TYPE
    SYNTAX      Unsigned32
    MAX-ACCESS  not-accessible
    STATUS      current
    DESCRIPTION   "Number of sequence."
    ::=  { upwardOpticalMuxEntry 6 }

upwardOpticalMuxParentId OBJECT-TYPE
    SYNTAX      RowPointer
    MAX-ACCESS  read-only
    STATUS      current
    DESCRIPTION   "RowPointer to parent entity reported in corresponding entity table."
    ::=  { upwardOpticalMuxEntry 7 }

endOfUpwardOpticalMuxTable OBJECT-TYPE
    SYNTAX      Integer32
    MAX-ACCESS  read-only
    STATUS      current
    DESCRIPTION
        ""
    ::=  { relationship 32 }

downwardOpticalMuxTable OBJECT-TYPE
    SYNTAX      SEQUENCE OF DownwardOpticalMuxEntry
    MAX-ACCESS  not-accessible
    STATUS      current
    DESCRIPTION   "downwardOpticalMuxTable"
    ::=  { relationship 33 }

downwardOpticalMuxEntry OBJECT-TYPE
    SYNTAX      DownwardOpticalMuxEntry
    MAX-ACCESS  not-accessible
    STATUS      current
    DESCRIPTION   "Entry of downwardOpticalMuxTable"
    INDEX       {
                  downwardOpticalMuxShelfNo,
                  downwardOpticalMuxSlotNo,
                  downwardOpticalMuxPortNo,
                  downwardOpticalMuxExtNo,
                  downwardOpticalMuxClassName,
                  downwardOpticalMuxIndex
                }
    ::=  { downwardOpticalMuxTable 1 }

DownwardOpticalMuxEntry ::=  SEQUENCE
  { downwardOpticalMuxShelfNo Unsigned32,
    downwardOpticalMuxSlotNo Unsigned32,
    downwardOpticalMuxPortNo Unsigned32,
    downwardOpticalMuxExtNo Unsigned32,
    downwardOpticalMuxClassName EntityClassName,
    downwardOpticalMuxIndex Unsigned32,
    downwardOpticalMuxChildId RowPointer }

downwardOpticalMuxShelfNo OBJECT-TYPE
    SYNTAX      Unsigned32
    MAX-ACCESS  not-accessible
    STATUS      current
    DESCRIPTION   "Adress index."
    ::=  { downwardOpticalMuxEntry 1 }

downwardOpticalMuxSlotNo OBJECT-TYPE
    SYNTAX      Unsigned32
    MAX-ACCESS  not-accessible
    STATUS      current
    DESCRIPTION   "Adress index."
    ::=  { downwardOpticalMuxEntry 2 }

downwardOpticalMuxPortNo OBJECT-TYPE
    SYNTAX      Unsigned32
    MAX-ACCESS  not-accessible
    STATUS      current
    DESCRIPTION   "Adress index."
    ::=  { downwardOpticalMuxEntry 3 }

downwardOpticalMuxExtNo OBJECT-TYPE
    SYNTAX      Unsigned32
    MAX-ACCESS  not-accessible
    STATUS      current
    DESCRIPTION   "Adress index."
    ::=  { downwardOpticalMuxEntry 4 }

downwardOpticalMuxClassName OBJECT-TYPE
    SYNTAX      EntityClassName
    MAX-ACCESS  not-accessible
    STATUS      current
    DESCRIPTION
        "Entity Class Name"
    ::=  { downwardOpticalMuxEntry 5 }

downwardOpticalMuxIndex OBJECT-TYPE
    SYNTAX      Unsigned32
    MAX-ACCESS  not-accessible
    STATUS      current
    DESCRIPTION   "Number of sequence."
    ::=  { downwardOpticalMuxEntry 6 }

downwardOpticalMuxChildId OBJECT-TYPE
    SYNTAX      RowPointer
    MAX-ACCESS  read-only
    STATUS      current
    DESCRIPTION   "RowPointer to child entity."
    ::=  { downwardOpticalMuxEntry 7 }

endOfDownwardOpticalMuxTable OBJECT-TYPE
    SYNTAX      Integer32
    MAX-ACCESS  read-only
    STATUS      current
    DESCRIPTION
        ""
    ::=  { relationship 34 }

upwardShelfConnTable OBJECT-TYPE
    SYNTAX      SEQUENCE OF UpwardShelfConnEntry
    MAX-ACCESS  not-accessible
    STATUS      current
    DESCRIPTION   "upwardShelfConnTable"
    ::=  { relationship 35 }

upwardShelfConnEntry OBJECT-TYPE
    SYNTAX      UpwardShelfConnEntry
    MAX-ACCESS  not-accessible
    STATUS      current
    DESCRIPTION   "Entry of upwardShelfConnTable"
    INDEX       {
                  upwardShelfConnShelfNo,
                  upwardShelfConnSlotNo,
                  upwardShelfConnPortNo,
                  upwardShelfConnExtNo,
                  upwardShelfConnClassName,
                  upwardShelfConnIndex
                }
    ::=  { upwardShelfConnTable 1 }

UpwardShelfConnEntry ::=  SEQUENCE
  { upwardShelfConnShelfNo Unsigned32,
    upwardShelfConnSlotNo Unsigned32,
    upwardShelfConnPortNo Unsigned32,
    upwardShelfConnExtNo Unsigned32,
    upwardShelfConnClassName EntityClassName,
    upwardShelfConnIndex Unsigned32,
    upwardShelfConnParentId RowPointer }

upwardShelfConnShelfNo OBJECT-TYPE
    SYNTAX      Unsigned32
    MAX-ACCESS  not-accessible
    STATUS      current
    DESCRIPTION   "Adress index."
    ::=  { upwardShelfConnEntry 1 }

upwardShelfConnSlotNo OBJECT-TYPE
    SYNTAX      Unsigned32
    MAX-ACCESS  not-accessible
    STATUS      current
    DESCRIPTION   "Adress index."
    ::=  { upwardShelfConnEntry 2 }

upwardShelfConnPortNo OBJECT-TYPE
    SYNTAX      Unsigned32
    MAX-ACCESS  not-accessible
    STATUS      current
    DESCRIPTION   "Adress index."
    ::=  { upwardShelfConnEntry 3 }

upwardShelfConnExtNo OBJECT-TYPE
    SYNTAX      Unsigned32
    MAX-ACCESS  not-accessible
    STATUS      current
    DESCRIPTION   "Adress index."
    ::=  { upwardShelfConnEntry 4 }

upwardShelfConnClassName OBJECT-TYPE
    SYNTAX      EntityClassName
    MAX-ACCESS  not-accessible
    STATUS      current
    DESCRIPTION
        "Entity Class Name"
    ::=  { upwardShelfConnEntry 5 }

upwardShelfConnIndex OBJECT-TYPE
    SYNTAX      Unsigned32
    MAX-ACCESS  not-accessible
    STATUS      current
    DESCRIPTION   "Number of sequence."
    ::=  { upwardShelfConnEntry 6 }

upwardShelfConnParentId OBJECT-TYPE
    SYNTAX      RowPointer
    MAX-ACCESS  read-only
    STATUS      current
    DESCRIPTION   "RowPointer to parent entity reported in corresponding entity table."
    ::=  { upwardShelfConnEntry 7 }

endOfUpwardShelfConnTable OBJECT-TYPE
    SYNTAX      Integer32
    MAX-ACCESS  read-only
    STATUS      current
    DESCRIPTION
        ""
    ::=  { relationship 36 }

downwardShelfConnTable OBJECT-TYPE
    SYNTAX      SEQUENCE OF DownwardShelfConnEntry
    MAX-ACCESS  not-accessible
    STATUS      current
    DESCRIPTION   "downwardShelfConnTable"
    ::=  { relationship 37 }

downwardShelfConnEntry OBJECT-TYPE
    SYNTAX      DownwardShelfConnEntry
    MAX-ACCESS  not-accessible
    STATUS      current
    DESCRIPTION   "Entry of downwardShelfConnTable"
    INDEX       {
                  downwardShelfConnShelfNo,
                  downwardShelfConnSlotNo,
                  downwardShelfConnPortNo,
                  downwardShelfConnExtNo,
                  downwardShelfConnClassName,
                  downwardShelfConnIndex
                }
    ::=  { downwardShelfConnTable 1 }

DownwardShelfConnEntry ::=  SEQUENCE
  { downwardShelfConnShelfNo Unsigned32,
    downwardShelfConnSlotNo Unsigned32,
    downwardShelfConnPortNo Unsigned32,
    downwardShelfConnExtNo Unsigned32,
    downwardShelfConnClassName EntityClassName,
    downwardShelfConnIndex Unsigned32,
    downwardShelfConnChildId RowPointer }

downwardShelfConnShelfNo OBJECT-TYPE
    SYNTAX      Unsigned32
    MAX-ACCESS  not-accessible
    STATUS      current
    DESCRIPTION   "Adress index."
    ::=  { downwardShelfConnEntry 1 }

downwardShelfConnSlotNo OBJECT-TYPE
    SYNTAX      Unsigned32
    MAX-ACCESS  not-accessible
    STATUS      current
    DESCRIPTION   "Adress index."
    ::=  { downwardShelfConnEntry 2 }

downwardShelfConnPortNo OBJECT-TYPE
    SYNTAX      Unsigned32
    MAX-ACCESS  not-accessible
    STATUS      current
    DESCRIPTION   "Adress index."
    ::=  { downwardShelfConnEntry 3 }

downwardShelfConnExtNo OBJECT-TYPE
    SYNTAX      Unsigned32
    MAX-ACCESS  not-accessible
    STATUS      current
    DESCRIPTION   "Adress index."
    ::=  { downwardShelfConnEntry 4 }

downwardShelfConnClassName OBJECT-TYPE
    SYNTAX      EntityClassName
    MAX-ACCESS  not-accessible
    STATUS      current
    DESCRIPTION
        "Entity Class Name"
    ::=  { downwardShelfConnEntry 5 }

downwardShelfConnIndex OBJECT-TYPE
    SYNTAX      Unsigned32
    MAX-ACCESS  not-accessible
    STATUS      current
    DESCRIPTION   "Number of sequence."
    ::=  { downwardShelfConnEntry 6 }

downwardShelfConnChildId OBJECT-TYPE
    SYNTAX      RowPointer
    MAX-ACCESS  read-only
    STATUS      current
    DESCRIPTION   "RowPointer to child entity."
    ::=  { downwardShelfConnEntry 7 }

endOfDownwardShelfConnTable OBJECT-TYPE
    SYNTAX      Integer32
    MAX-ACCESS  read-only
    STATUS      current
    DESCRIPTION
        ""
    ::=  { relationship 38 }

dependentTable OBJECT-TYPE
    SYNTAX      SEQUENCE OF DependentEntry
    MAX-ACCESS  not-accessible
    STATUS      current
    DESCRIPTION   "dependentTable"
    ::=  { relationship 100 }

dependentEntry OBJECT-TYPE
    SYNTAX      DependentEntry
    MAX-ACCESS  not-accessible
    STATUS      current
    DESCRIPTION   "Entry of dependentTable"
    INDEX       {
                  dependentIndexNo1,
                  dependentIndexNo2,
                  dependentIndexNo3,
                  dependentIndexNo4,
                  dependentClassName,
                  dependentIndex
                }
    ::=  { dependentTable 1 }

DependentEntry ::=  SEQUENCE
  { dependentIndexNo1 Unsigned32,
    dependentIndexNo2 Unsigned32,
    dependentIndexNo3 Unsigned32,
    dependentIndexNo4 Unsigned32,
    dependentClassName EntityClassName,
    dependentIndex Unsigned32,
    dependentAid SnmpAdminString,
    dependentId RowPointer }

dependentIndexNo1 OBJECT-TYPE
    SYNTAX      Unsigned32
    MAX-ACCESS  not-accessible
    STATUS      current
    DESCRIPTION   "Adress index."
    ::=  { dependentEntry 1 }

dependentIndexNo2 OBJECT-TYPE
    SYNTAX      Unsigned32
    MAX-ACCESS  not-accessible
    STATUS      current
    DESCRIPTION   "Adress index."
    ::=  { dependentEntry 2 }

dependentIndexNo3 OBJECT-TYPE
    SYNTAX      Unsigned32
    MAX-ACCESS  not-accessible
    STATUS      current
    DESCRIPTION   "Adress index."
    ::=  { dependentEntry 3 }

dependentIndexNo4 OBJECT-TYPE
    SYNTAX      Unsigned32
    MAX-ACCESS  not-accessible
    STATUS      current
    DESCRIPTION   "Adress index."
    ::=  { dependentEntry 4 }

dependentClassName OBJECT-TYPE
    SYNTAX      EntityClassName
    MAX-ACCESS  not-accessible
    STATUS      current
    DESCRIPTION
        "Entity Class Name"
    ::=  { dependentEntry 5 }

dependentIndex OBJECT-TYPE
    SYNTAX      Unsigned32
    MAX-ACCESS  not-accessible
    STATUS      current
    DESCRIPTION   "Number of sequence."
    ::=  { dependentEntry 6 }

dependentAid OBJECT-TYPE
    SYNTAX      SnmpAdminString
    MAX-ACCESS  read-only
    STATUS      current
    DESCRIPTION   "Aid string of entity."
    ::=  { dependentEntry 7 }

dependentId OBJECT-TYPE
    SYNTAX      RowPointer
    MAX-ACCESS  read-only
    STATUS      current
    DESCRIPTION   "RowPointer to the dependent entity."
    ::=  { dependentEntry 8 }

endOfDependentTable OBJECT-TYPE
    SYNTAX      Integer32
    MAX-ACCESS  read-only
    STATUS      current
    DESCRIPTION
        ""
    ::=  { relationship 101 }

endOfRelationship OBJECT-TYPE
    SYNTAX      Integer32
    MAX-ACCESS  read-only
    STATUS      current
    DESCRIPTION
        ""
    ::=  { relationship 10000 }

notAssignableEqptTable OBJECT-TYPE
    SYNTAX      SEQUENCE OF NotAssignableEqptEntry
    MAX-ACCESS  not-accessible
    STATUS      current
    DESCRIPTION   "notAssignableEqpt"
    ::=  { notAssignables 2 }

notAssignableEqptEntry OBJECT-TYPE
    SYNTAX      NotAssignableEqptEntry
    MAX-ACCESS  not-accessible
    STATUS      current
    DESCRIPTION   "Entry of notAssignableEqpt"
    INDEX       {
                  notAssignableEqptIndexNo1,
                  notAssignableEqptIndexNo2,
                  notAssignableEqptIndexNo3,
                  notAssignableEqptIndexNo4,
                  notAssignableEqptClassName
                }
    ::=  { notAssignableEqptTable 1 }

NotAssignableEqptEntry ::=  SEQUENCE
  { notAssignableEqptIndexNo1 Unsigned32,
    notAssignableEqptIndexNo2 Unsigned32,
    notAssignableEqptIndexNo3 Unsigned32,
    notAssignableEqptIndexNo4 Unsigned32,
    notAssignableEqptClassName EntityClassName,
    notAssignableEqptAidString SnmpAdminString,
    notAssignableEqptParentId RowPointer,
    notAssignableEqptClass EntityClass }

notAssignableEqptIndexNo1 OBJECT-TYPE
    SYNTAX      Unsigned32
    MAX-ACCESS  not-accessible
    STATUS      current
    DESCRIPTION   "Adress index."
    ::=  { notAssignableEqptEntry 1 }

notAssignableEqptIndexNo2 OBJECT-TYPE
    SYNTAX      Unsigned32
    MAX-ACCESS  not-accessible
    STATUS      current
    DESCRIPTION   "Adress index."
    ::=  { notAssignableEqptEntry 2 }

notAssignableEqptIndexNo3 OBJECT-TYPE
    SYNTAX      Unsigned32
    MAX-ACCESS  not-accessible
    STATUS      current
    DESCRIPTION   "Adress index."
    ::=  { notAssignableEqptEntry 3 }

notAssignableEqptIndexNo4 OBJECT-TYPE
    SYNTAX      Unsigned32
    MAX-ACCESS  not-accessible
    STATUS      current
    DESCRIPTION   "Adress index."
    ::=  { notAssignableEqptEntry 4 }

notAssignableEqptClassName OBJECT-TYPE
    SYNTAX      EntityClassName
    MAX-ACCESS  not-accessible
    STATUS      current
    DESCRIPTION
        "Entity Class Name"
    ::=  { notAssignableEqptEntry 5 }

notAssignableEqptAidString OBJECT-TYPE
    SYNTAX      SnmpAdminString
    MAX-ACCESS  read-only
    STATUS      current
    DESCRIPTION   "Aid string of entity."
    ::=  { notAssignableEqptEntry 6 }

notAssignableEqptParentId OBJECT-TYPE
    SYNTAX      RowPointer
    MAX-ACCESS  read-only
    STATUS      current
    DESCRIPTION   "RowPointer to parent entity reported in corresponding entity table."
    ::=  { notAssignableEqptEntry 7 }

notAssignableEqptClass OBJECT-TYPE
    SYNTAX      EntityClass
    MAX-ACCESS  read-only
    STATUS      current
    DESCRIPTION   "EntityClass"
    ::=  { notAssignableEqptEntry 8 }

endOfNotAssignableEqptTable OBJECT-TYPE
    SYNTAX      Integer32
    MAX-ACCESS  read-only
    STATUS      current
    DESCRIPTION
        ""
    ::=  { notAssignables 3 }

notAssignableDcnTable OBJECT-TYPE
    SYNTAX      SEQUENCE OF NotAssignableDcnEntry
    MAX-ACCESS  not-accessible
    STATUS      current
    DESCRIPTION   "notAssignableDcn"
    ::=  { notAssignables 4 }

notAssignableDcnEntry OBJECT-TYPE
    SYNTAX      NotAssignableDcnEntry
    MAX-ACCESS  not-accessible
    STATUS      current
    DESCRIPTION   "Entry of notAssignableDcn"
    INDEX       {
                  notAssignableDcnIndexNo1,
                  notAssignableDcnIndexNo2,
                  notAssignableDcnIndexNo3,
                  notAssignableDcnIndexNo4,
                  notAssignableDcnClassName
                }
    ::=  { notAssignableDcnTable 1 }

NotAssignableDcnEntry ::=  SEQUENCE
  { notAssignableDcnIndexNo1 Unsigned32,
    notAssignableDcnIndexNo2 Unsigned32,
    notAssignableDcnIndexNo3 Unsigned32,
    notAssignableDcnIndexNo4 Unsigned32,
    notAssignableDcnClassName EntityClassName,
    notAssignableDcnAidString SnmpAdminString,
    notAssignableDcnParentId RowPointer,
    notAssignableDcnClass EntityClass }

notAssignableDcnIndexNo1 OBJECT-TYPE
    SYNTAX      Unsigned32
    MAX-ACCESS  not-accessible
    STATUS      current
    DESCRIPTION   "Adress index."
    ::=  { notAssignableDcnEntry 1 }

notAssignableDcnIndexNo2 OBJECT-TYPE
    SYNTAX      Unsigned32
    MAX-ACCESS  not-accessible
    STATUS      current
    DESCRIPTION   "Adress index."
    ::=  { notAssignableDcnEntry 2 }

notAssignableDcnIndexNo3 OBJECT-TYPE
    SYNTAX      Unsigned32
    MAX-ACCESS  not-accessible
    STATUS      current
    DESCRIPTION   "Adress index."
    ::=  { notAssignableDcnEntry 3 }

notAssignableDcnIndexNo4 OBJECT-TYPE
    SYNTAX      Unsigned32
    MAX-ACCESS  not-accessible
    STATUS      current
    DESCRIPTION   "Adress index."
    ::=  { notAssignableDcnEntry 4 }

notAssignableDcnClassName OBJECT-TYPE
    SYNTAX      EntityClassName
    MAX-ACCESS  not-accessible
    STATUS      current
    DESCRIPTION
        "Entity Class Name"
    ::=  { notAssignableDcnEntry 5 }

notAssignableDcnAidString OBJECT-TYPE
    SYNTAX      SnmpAdminString
    MAX-ACCESS  read-only
    STATUS      current
    DESCRIPTION   "Aid string of entity."
    ::=  { notAssignableDcnEntry 6 }

notAssignableDcnParentId OBJECT-TYPE
    SYNTAX      RowPointer
    MAX-ACCESS  read-only
    STATUS      current
    DESCRIPTION   "RowPointer to parent entity reported in corresponding entity table."
    ::=  { notAssignableDcnEntry 7 }

notAssignableDcnClass OBJECT-TYPE
    SYNTAX      EntityClass
    MAX-ACCESS  read-only
    STATUS      current
    DESCRIPTION   "EntityClass"
    ::=  { notAssignableDcnEntry 8 }

endOfNotAssignableDcnTable OBJECT-TYPE
    SYNTAX      Integer32
    MAX-ACCESS  read-only
    STATUS      current
    DESCRIPTION
        ""
    ::=  { notAssignables 5 }

notAssignableFacilityTable OBJECT-TYPE
    SYNTAX      SEQUENCE OF NotAssignableFacilityEntry
    MAX-ACCESS  not-accessible
    STATUS      current
    DESCRIPTION   "notAssignableFacility"
    ::=  { notAssignables 7 }

notAssignableFacilityEntry OBJECT-TYPE
    SYNTAX      NotAssignableFacilityEntry
    MAX-ACCESS  not-accessible
    STATUS      current
    DESCRIPTION   "Entry of notAssignableFacility"
    INDEX       {
                  notAssignableFacilityIndexNo1,
                  notAssignableFacilityIndexNo2,
                  notAssignableFacilityIndexNo3,
                  notAssignableFacilityIndexNo4,
                  notAssignableFacilityClassName
                }
    ::=  { notAssignableFacilityTable 1 }

NotAssignableFacilityEntry ::=  SEQUENCE
  { notAssignableFacilityIndexNo1 Unsigned32,
    notAssignableFacilityIndexNo2 Unsigned32,
    notAssignableFacilityIndexNo3 Unsigned32,
    notAssignableFacilityIndexNo4 Unsigned32,
    notAssignableFacilityClassName EntityClassName,
    notAssignableFacilityAidString SnmpAdminString,
    notAssignableFacilityParentId RowPointer,
    notAssignableFacilityClass EntityClass }

notAssignableFacilityIndexNo1 OBJECT-TYPE
    SYNTAX      Unsigned32
    MAX-ACCESS  not-accessible
    STATUS      current
    DESCRIPTION   "Adress index."
    ::=  { notAssignableFacilityEntry 1 }

notAssignableFacilityIndexNo2 OBJECT-TYPE
    SYNTAX      Unsigned32
    MAX-ACCESS  not-accessible
    STATUS      current
    DESCRIPTION   "Adress index."
    ::=  { notAssignableFacilityEntry 2 }

notAssignableFacilityIndexNo3 OBJECT-TYPE
    SYNTAX      Unsigned32
    MAX-ACCESS  not-accessible
    STATUS      current
    DESCRIPTION   "Adress index."
    ::=  { notAssignableFacilityEntry 3 }

notAssignableFacilityIndexNo4 OBJECT-TYPE
    SYNTAX      Unsigned32
    MAX-ACCESS  not-accessible
    STATUS      current
    DESCRIPTION   "Adress index."
    ::=  { notAssignableFacilityEntry 4 }

notAssignableFacilityClassName OBJECT-TYPE
    SYNTAX      EntityClassName
    MAX-ACCESS  not-accessible
    STATUS      current
    DESCRIPTION
        "Entity Class Name"
    ::=  { notAssignableFacilityEntry 5 }

notAssignableFacilityAidString OBJECT-TYPE
    SYNTAX      SnmpAdminString
    MAX-ACCESS  read-only
    STATUS      current
    DESCRIPTION   "Aid string of entity."
    ::=  { notAssignableFacilityEntry 6 }

notAssignableFacilityParentId OBJECT-TYPE
    SYNTAX      RowPointer
    MAX-ACCESS  read-only
    STATUS      current
    DESCRIPTION   "RowPointer to parent entity reported in corresponding entity table."
    ::=  { notAssignableFacilityEntry 7 }

notAssignableFacilityClass OBJECT-TYPE
    SYNTAX      EntityClass
    MAX-ACCESS  read-only
    STATUS      current
    DESCRIPTION   "EntityClass"
    ::=  { notAssignableFacilityEntry 8 }

endOfNotAssignableFacilityTable OBJECT-TYPE
    SYNTAX      Integer32
    MAX-ACCESS  read-only
    STATUS      current
    DESCRIPTION
        ""
    ::=  { notAssignables 8 }

notAssignableOptLineTable OBJECT-TYPE
    SYNTAX      SEQUENCE OF NotAssignableOptLineEntry
    MAX-ACCESS  not-accessible
    STATUS      current
    DESCRIPTION   "notAssignableOptLine"
    ::=  { notAssignables 9 }

notAssignableOptLineEntry OBJECT-TYPE
    SYNTAX      NotAssignableOptLineEntry
    MAX-ACCESS  not-accessible
    STATUS      current
    DESCRIPTION   "Entry of notAssignableOptLine"
    INDEX       {
                  notAssignableOptLineIndexNo1,
                  notAssignableOptLineIndexNo2,
                  notAssignableOptLineIndexNo3,
                  notAssignableOptLineIndexNo4,
                  notAssignableOptLineClassName
                }
    ::=  { notAssignableOptLineTable 1 }

NotAssignableOptLineEntry ::=  SEQUENCE
  { notAssignableOptLineIndexNo1 Unsigned32,
    notAssignableOptLineIndexNo2 Unsigned32,
    notAssignableOptLineIndexNo3 Unsigned32,
    notAssignableOptLineIndexNo4 Unsigned32,
    notAssignableOptLineClassName EntityClassName,
    notAssignableOptLineAidString SnmpAdminString,
    notAssignableOptLineParentId RowPointer,
    notAssignableOptLineClass EntityClass }

notAssignableOptLineIndexNo1 OBJECT-TYPE
    SYNTAX      Unsigned32
    MAX-ACCESS  not-accessible
    STATUS      current
    DESCRIPTION   "Adress index."
    ::=  { notAssignableOptLineEntry 1 }

notAssignableOptLineIndexNo2 OBJECT-TYPE
    SYNTAX      Unsigned32
    MAX-ACCESS  not-accessible
    STATUS      current
    DESCRIPTION   "Adress index."
    ::=  { notAssignableOptLineEntry 2 }

notAssignableOptLineIndexNo3 OBJECT-TYPE
    SYNTAX      Unsigned32
    MAX-ACCESS  not-accessible
    STATUS      current
    DESCRIPTION   "Adress index."
    ::=  { notAssignableOptLineEntry 3 }

notAssignableOptLineIndexNo4 OBJECT-TYPE
    SYNTAX      Unsigned32
    MAX-ACCESS  not-accessible
    STATUS      current
    DESCRIPTION   "Adress index."
    ::=  { notAssignableOptLineEntry 4 }

notAssignableOptLineClassName OBJECT-TYPE
    SYNTAX      EntityClassName
    MAX-ACCESS  not-accessible
    STATUS      current
    DESCRIPTION
        "Entity Class Name"
    ::=  { notAssignableOptLineEntry 5 }

notAssignableOptLineAidString OBJECT-TYPE
    SYNTAX      SnmpAdminString
    MAX-ACCESS  read-only
    STATUS      current
    DESCRIPTION   "Aid string of entity."
    ::=  { notAssignableOptLineEntry 6 }

notAssignableOptLineParentId OBJECT-TYPE
    SYNTAX      RowPointer
    MAX-ACCESS  read-only
    STATUS      current
    DESCRIPTION   "RowPointer to parent entity reported in corresponding entity table."
    ::=  { notAssignableOptLineEntry 7 }

notAssignableOptLineClass OBJECT-TYPE
    SYNTAX      EntityClass
    MAX-ACCESS  read-only
    STATUS      current
    DESCRIPTION   "EntityClass"
    ::=  { notAssignableOptLineEntry 8 }

endOfNotAssignableOptLineTable OBJECT-TYPE
    SYNTAX      Integer32
    MAX-ACCESS  read-only
    STATUS      current
    DESCRIPTION
        ""
    ::=  { notAssignables 10 }

notAssignableEnvTable OBJECT-TYPE
    SYNTAX      SEQUENCE OF NotAssignableEnvEntry
    MAX-ACCESS  not-accessible
    STATUS      current
    DESCRIPTION   "notAssignableEnv"
    ::=  { notAssignables 11 }

notAssignableEnvEntry OBJECT-TYPE
    SYNTAX      NotAssignableEnvEntry
    MAX-ACCESS  not-accessible
    STATUS      current
    DESCRIPTION   "Entry of notAssignableEnv"
    INDEX       {
                  notAssignableEnvIndexNo1,
                  notAssignableEnvIndexNo2,
                  notAssignableEnvIndexNo3,
                  notAssignableEnvIndexNo4,
                  notAssignableEnvClassName
                }
    ::=  { notAssignableEnvTable 1 }

NotAssignableEnvEntry ::=  SEQUENCE
  { notAssignableEnvIndexNo1 Unsigned32,
    notAssignableEnvIndexNo2 Unsigned32,
    notAssignableEnvIndexNo3 Unsigned32,
    notAssignableEnvIndexNo4 Unsigned32,
    notAssignableEnvClassName EntityClassName,
    notAssignableEnvAidString SnmpAdminString,
    notAssignableEnvParentId RowPointer,
    notAssignableEnvClass EntityClass }

notAssignableEnvIndexNo1 OBJECT-TYPE
    SYNTAX      Unsigned32
    MAX-ACCESS  not-accessible
    STATUS      current
    DESCRIPTION   "Adress index."
    ::=  { notAssignableEnvEntry 1 }

notAssignableEnvIndexNo2 OBJECT-TYPE
    SYNTAX      Unsigned32
    MAX-ACCESS  not-accessible
    STATUS      current
    DESCRIPTION   "Adress index."
    ::=  { notAssignableEnvEntry 2 }

notAssignableEnvIndexNo3 OBJECT-TYPE
    SYNTAX      Unsigned32
    MAX-ACCESS  not-accessible
    STATUS      current
    DESCRIPTION   "Adress index."
    ::=  { notAssignableEnvEntry 3 }

notAssignableEnvIndexNo4 OBJECT-TYPE
    SYNTAX      Unsigned32
    MAX-ACCESS  not-accessible
    STATUS      current
    DESCRIPTION   "Adress index."
    ::=  { notAssignableEnvEntry 4 }

notAssignableEnvClassName OBJECT-TYPE
    SYNTAX      EntityClassName
    MAX-ACCESS  not-accessible
    STATUS      current
    DESCRIPTION
        "Entity Class Name"
    ::=  { notAssignableEnvEntry 5 }

notAssignableEnvAidString OBJECT-TYPE
    SYNTAX      SnmpAdminString
    MAX-ACCESS  read-only
    STATUS      current
    DESCRIPTION   "Aid string of entity."
    ::=  { notAssignableEnvEntry 6 }

notAssignableEnvParentId OBJECT-TYPE
    SYNTAX      RowPointer
    MAX-ACCESS  read-only
    STATUS      current
    DESCRIPTION   "RowPointer to parent entity reported in corresponding entity table."
    ::=  { notAssignableEnvEntry 7 }

notAssignableEnvClass OBJECT-TYPE
    SYNTAX      EntityClass
    MAX-ACCESS  read-only
    STATUS      current
    DESCRIPTION   "EntityClass"
    ::=  { notAssignableEnvEntry 8 }

endOfNotAssignableEnvTable OBJECT-TYPE
    SYNTAX      Integer32
    MAX-ACCESS  read-only
    STATUS      current
    DESCRIPTION
        ""
    ::=  { notAssignables 12 }

notAssignableExternalPortTable OBJECT-TYPE
    SYNTAX      SEQUENCE OF NotAssignableExternalPortEntry
    MAX-ACCESS  not-accessible
    STATUS      current
    DESCRIPTION   "notAssignableExternalPort"
    ::=  { notAssignables 13 }

notAssignableExternalPortEntry OBJECT-TYPE
    SYNTAX      NotAssignableExternalPortEntry
    MAX-ACCESS  not-accessible
    STATUS      current
    DESCRIPTION   "Entry of notAssignableExternalPort"
    INDEX       {
                  notAssignableExternalPortIndexNo1,
                  notAssignableExternalPortIndexNo2,
                  notAssignableExternalPortIndexNo3,
                  notAssignableExternalPortIndexNo4,
                  notAssignableExternalPortClassName
                }
    ::=  { notAssignableExternalPortTable 1 }

NotAssignableExternalPortEntry ::=  SEQUENCE
  { notAssignableExternalPortIndexNo1 Unsigned32,
    notAssignableExternalPortIndexNo2 Unsigned32,
    notAssignableExternalPortIndexNo3 Unsigned32,
    notAssignableExternalPortIndexNo4 Unsigned32,
    notAssignableExternalPortClassName EntityClassName,
    notAssignableExternalPortAidString SnmpAdminString,
    notAssignableExternalPortParentId RowPointer,
    notAssignableExternalPortClass EntityClass }

notAssignableExternalPortIndexNo1 OBJECT-TYPE
    SYNTAX      Unsigned32
    MAX-ACCESS  not-accessible
    STATUS      current
    DESCRIPTION   "Adress index."
    ::=  { notAssignableExternalPortEntry 1 }

notAssignableExternalPortIndexNo2 OBJECT-TYPE
    SYNTAX      Unsigned32
    MAX-ACCESS  not-accessible
    STATUS      current
    DESCRIPTION   "Adress index."
    ::=  { notAssignableExternalPortEntry 2 }

notAssignableExternalPortIndexNo3 OBJECT-TYPE
    SYNTAX      Unsigned32
    MAX-ACCESS  not-accessible
    STATUS      current
    DESCRIPTION   "Adress index."
    ::=  { notAssignableExternalPortEntry 3 }

notAssignableExternalPortIndexNo4 OBJECT-TYPE
    SYNTAX      Unsigned32
    MAX-ACCESS  not-accessible
    STATUS      current
    DESCRIPTION   "Adress index."
    ::=  { notAssignableExternalPortEntry 4 }

notAssignableExternalPortClassName OBJECT-TYPE
    SYNTAX      EntityClassName
    MAX-ACCESS  not-accessible
    STATUS      current
    DESCRIPTION
        "Entity Class Name"
    ::=  { notAssignableExternalPortEntry 5 }

notAssignableExternalPortAidString OBJECT-TYPE
    SYNTAX      SnmpAdminString
    MAX-ACCESS  read-only
    STATUS      current
    DESCRIPTION   "Aid string of entity."
    ::=  { notAssignableExternalPortEntry 6 }

notAssignableExternalPortParentId OBJECT-TYPE
    SYNTAX      RowPointer
    MAX-ACCESS  read-only
    STATUS      current
    DESCRIPTION   "RowPointer to parent entity reported in corresponding entity table."
    ::=  { notAssignableExternalPortEntry 7 }

notAssignableExternalPortClass OBJECT-TYPE
    SYNTAX      EntityClass
    MAX-ACCESS  read-only
    STATUS      current
    DESCRIPTION   "EntityClass"
    ::=  { notAssignableExternalPortEntry 8 }

endOfNotAssignableExternalPortTable OBJECT-TYPE
    SYNTAX      Integer32
    MAX-ACCESS  read-only
    STATUS      current
    DESCRIPTION
        ""
    ::=  { notAssignables 14 }

notAssignableContainerTable OBJECT-TYPE
    SYNTAX      SEQUENCE OF NotAssignableContainerEntry
    MAX-ACCESS  not-accessible
    STATUS      current
    DESCRIPTION   "notAssignableContainer"
    ::=  { notAssignables 15 }

notAssignableContainerEntry OBJECT-TYPE
    SYNTAX      NotAssignableContainerEntry
    MAX-ACCESS  not-accessible
    STATUS      current
    DESCRIPTION   "Entry of notAssignableContainer"
    INDEX       {
                  notAssignableContainerIndexNo1,
                  notAssignableContainerIndexNo2,
                  notAssignableContainerIndexNo3,
                  notAssignableContainerIndexNo4,
                  notAssignableContainerClassName
                }
    ::=  { notAssignableContainerTable 1 }

NotAssignableContainerEntry ::=  SEQUENCE
  { notAssignableContainerIndexNo1 Unsigned32,
    notAssignableContainerIndexNo2 Unsigned32,
    notAssignableContainerIndexNo3 Unsigned32,
    notAssignableContainerIndexNo4 Unsigned32,
    notAssignableContainerClassName EntityClassName,
    notAssignableContainerAidString SnmpAdminString,
    notAssignableContainerParentId RowPointer,
    notAssignableContainerClass EntityClass }

notAssignableContainerIndexNo1 OBJECT-TYPE
    SYNTAX      Unsigned32
    MAX-ACCESS  not-accessible
    STATUS      current
    DESCRIPTION   "Adress index."
    ::=  { notAssignableContainerEntry 1 }

notAssignableContainerIndexNo2 OBJECT-TYPE
    SYNTAX      Unsigned32
    MAX-ACCESS  not-accessible
    STATUS      current
    DESCRIPTION   "Adress index."
    ::=  { notAssignableContainerEntry 2 }

notAssignableContainerIndexNo3 OBJECT-TYPE
    SYNTAX      Unsigned32
    MAX-ACCESS  not-accessible
    STATUS      current
    DESCRIPTION   "Adress index."
    ::=  { notAssignableContainerEntry 3 }

notAssignableContainerIndexNo4 OBJECT-TYPE
    SYNTAX      Unsigned32
    MAX-ACCESS  not-accessible
    STATUS      current
    DESCRIPTION   "Adress index."
    ::=  { notAssignableContainerEntry 4 }

notAssignableContainerClassName OBJECT-TYPE
    SYNTAX      EntityClassName
    MAX-ACCESS  not-accessible
    STATUS      current
    DESCRIPTION
        "Entity Class Name"
    ::=  { notAssignableContainerEntry 5 }

notAssignableContainerAidString OBJECT-TYPE
    SYNTAX      SnmpAdminString
    MAX-ACCESS  read-only
    STATUS      current
    DESCRIPTION   "Aid string of entity."
    ::=  { notAssignableContainerEntry 6 }

notAssignableContainerParentId OBJECT-TYPE
    SYNTAX      RowPointer
    MAX-ACCESS  read-only
    STATUS      current
    DESCRIPTION   "RowPointer to parent entity reported in corresponding entity table."
    ::=  { notAssignableContainerEntry 7 }

notAssignableContainerClass OBJECT-TYPE
    SYNTAX      EntityClass
    MAX-ACCESS  read-only
    STATUS      current
    DESCRIPTION   "EntityClass"
    ::=  { notAssignableContainerEntry 8 }

endOfNotAssignableContainerTable OBJECT-TYPE
    SYNTAX      Integer32
    MAX-ACCESS  read-only
    STATUS      current
    DESCRIPTION
        ""
    ::=  { notAssignables 16 }

notAssignableOpticalMuxTable OBJECT-TYPE
    SYNTAX      SEQUENCE OF NotAssignableOpticalMuxEntry
    MAX-ACCESS  not-accessible
    STATUS      current
    DESCRIPTION   "notAssignableOpticalMux"
    ::=  { notAssignables 17 }

notAssignableOpticalMuxEntry OBJECT-TYPE
    SYNTAX      NotAssignableOpticalMuxEntry
    MAX-ACCESS  not-accessible
    STATUS      current
    DESCRIPTION   "Entry of notAssignableOpticalMux"
    INDEX       {
                  notAssignableOpticalMuxIndexNo1,
                  notAssignableOpticalMuxIndexNo2,
                  notAssignableOpticalMuxIndexNo3,
                  notAssignableOpticalMuxIndexNo4,
                  notAssignableOpticalMuxClassName
                }
    ::=  { notAssignableOpticalMuxTable 1 }

NotAssignableOpticalMuxEntry ::=  SEQUENCE
  { notAssignableOpticalMuxIndexNo1 Unsigned32,
    notAssignableOpticalMuxIndexNo2 Unsigned32,
    notAssignableOpticalMuxIndexNo3 Unsigned32,
    notAssignableOpticalMuxIndexNo4 Unsigned32,
    notAssignableOpticalMuxClassName EntityClassName,
    notAssignableOpticalMuxAidString SnmpAdminString,
    notAssignableOpticalMuxParentId RowPointer,
    notAssignableOpticalMuxClass EntityClass }

notAssignableOpticalMuxIndexNo1 OBJECT-TYPE
    SYNTAX      Unsigned32
    MAX-ACCESS  not-accessible
    STATUS      current
    DESCRIPTION   "Adress index."
    ::=  { notAssignableOpticalMuxEntry 1 }

notAssignableOpticalMuxIndexNo2 OBJECT-TYPE
    SYNTAX      Unsigned32
    MAX-ACCESS  not-accessible
    STATUS      current
    DESCRIPTION   "Adress index."
    ::=  { notAssignableOpticalMuxEntry 2 }

notAssignableOpticalMuxIndexNo3 OBJECT-TYPE
    SYNTAX      Unsigned32
    MAX-ACCESS  not-accessible
    STATUS      current
    DESCRIPTION   "Adress index."
    ::=  { notAssignableOpticalMuxEntry 3 }

notAssignableOpticalMuxIndexNo4 OBJECT-TYPE
    SYNTAX      Unsigned32
    MAX-ACCESS  not-accessible
    STATUS      current
    DESCRIPTION   "Adress index."
    ::=  { notAssignableOpticalMuxEntry 4 }

notAssignableOpticalMuxClassName OBJECT-TYPE
    SYNTAX      EntityClassName
    MAX-ACCESS  not-accessible
    STATUS      current
    DESCRIPTION
        "Entity Class Name"
    ::=  { notAssignableOpticalMuxEntry 5 }

notAssignableOpticalMuxAidString OBJECT-TYPE
    SYNTAX      SnmpAdminString
    MAX-ACCESS  read-only
    STATUS      current
    DESCRIPTION   "Aid string of entity."
    ::=  { notAssignableOpticalMuxEntry 6 }

notAssignableOpticalMuxParentId OBJECT-TYPE
    SYNTAX      RowPointer
    MAX-ACCESS  read-only
    STATUS      current
    DESCRIPTION   "RowPointer to parent entity reported in corresponding entity table."
    ::=  { notAssignableOpticalMuxEntry 7 }

notAssignableOpticalMuxClass OBJECT-TYPE
    SYNTAX      EntityClass
    MAX-ACCESS  read-only
    STATUS      current
    DESCRIPTION   "EntityClass"
    ::=  { notAssignableOpticalMuxEntry 8 }

endOfNotAssignableOpticalMuxTable OBJECT-TYPE
    SYNTAX      Integer32
    MAX-ACCESS  read-only
    STATUS      current
    DESCRIPTION
        ""
    ::=  { notAssignables 18 }

notAssignableShelfConnTable OBJECT-TYPE
    SYNTAX      SEQUENCE OF NotAssignableShelfConnEntry
    MAX-ACCESS  not-accessible
    STATUS      current
    DESCRIPTION   "notAssignableShelfConn"
    ::=  { notAssignables 20 }

notAssignableShelfConnEntry OBJECT-TYPE
    SYNTAX      NotAssignableShelfConnEntry
    MAX-ACCESS  not-accessible
    STATUS      current
    DESCRIPTION   "Entry of notAssignableShelfConn"
    INDEX       {
                  notAssignableShelfConnIndexNo1,
                  notAssignableShelfConnIndexNo2,
                  notAssignableShelfConnIndexNo3,
                  notAssignableShelfConnIndexNo4,
                  notAssignableShelfConnClassName
                }
    ::=  { notAssignableShelfConnTable 1 }

NotAssignableShelfConnEntry ::=  SEQUENCE
  { notAssignableShelfConnIndexNo1 Unsigned32,
    notAssignableShelfConnIndexNo2 Unsigned32,
    notAssignableShelfConnIndexNo3 Unsigned32,
    notAssignableShelfConnIndexNo4 Unsigned32,
    notAssignableShelfConnClassName EntityClassName,
    notAssignableShelfConnAidString SnmpAdminString,
    notAssignableShelfConnParentId RowPointer,
    notAssignableShelfConnClass EntityClass }

notAssignableShelfConnIndexNo1 OBJECT-TYPE
    SYNTAX      Unsigned32
    MAX-ACCESS  not-accessible
    STATUS      current
    DESCRIPTION   "Adress index."
    ::=  { notAssignableShelfConnEntry 1 }

notAssignableShelfConnIndexNo2 OBJECT-TYPE
    SYNTAX      Unsigned32
    MAX-ACCESS  not-accessible
    STATUS      current
    DESCRIPTION   "Adress index."
    ::=  { notAssignableShelfConnEntry 2 }

notAssignableShelfConnIndexNo3 OBJECT-TYPE
    SYNTAX      Unsigned32
    MAX-ACCESS  not-accessible
    STATUS      current
    DESCRIPTION   "Adress index."
    ::=  { notAssignableShelfConnEntry 3 }

notAssignableShelfConnIndexNo4 OBJECT-TYPE
    SYNTAX      Unsigned32
    MAX-ACCESS  not-accessible
    STATUS      current
    DESCRIPTION   "Adress index."
    ::=  { notAssignableShelfConnEntry 4 }

notAssignableShelfConnClassName OBJECT-TYPE
    SYNTAX      EntityClassName
    MAX-ACCESS  not-accessible
    STATUS      current
    DESCRIPTION
        "Entity Class Name"
    ::=  { notAssignableShelfConnEntry 5 }

notAssignableShelfConnAidString OBJECT-TYPE
    SYNTAX      SnmpAdminString
    MAX-ACCESS  read-only
    STATUS      current
    DESCRIPTION   "Aid string of entity."
    ::=  { notAssignableShelfConnEntry 6 }

notAssignableShelfConnParentId OBJECT-TYPE
    SYNTAX      RowPointer
    MAX-ACCESS  read-only
    STATUS      current
    DESCRIPTION   "RowPointer to parent entity reported in corresponding entity table."
    ::=  { notAssignableShelfConnEntry 7 }

notAssignableShelfConnClass OBJECT-TYPE
    SYNTAX      EntityClass
    MAX-ACCESS  read-only
    STATUS      current
    DESCRIPTION   "EntityClass"
    ::=  { notAssignableShelfConnEntry 8 }

endOfNotAssignableShelfConnTable OBJECT-TYPE
    SYNTAX      Integer32
    MAX-ACCESS  read-only
    STATUS      current
    DESCRIPTION
        ""
    ::=  { notAssignables 21 }

endOfNotAssignables OBJECT-TYPE
    SYNTAX      Integer32
    MAX-ACCESS  read-only
    STATUS      current
    DESCRIPTION
        ""
    ::=  { notAssignables 10000 }

advaInventoryTable OBJECT-TYPE
    SYNTAX      SEQUENCE OF AdvaInventoryEntry
    MAX-ACCESS  not-accessible
    STATUS      current
    DESCRIPTION   "This table lists all physically present (equipped) equipment in the NE"
    ::=  { inventory 1 }

advaInventoryEntry OBJECT-TYPE
    SYNTAX      AdvaInventoryEntry
    MAX-ACCESS  not-accessible
    STATUS      current
    DESCRIPTION   ""
    INDEX       {
                  advaInventoryShelfNo,
                  advaInventorySlotNo,
                  advaInventoryPortNo,
                  advaInventoryExtNo,
                  advaInventoryClassName
                }
    ::=  { advaInventoryTable 1 }

AdvaInventoryEntry ::=  SEQUENCE
  { advaInventoryShelfNo Unsigned32,
    advaInventorySlotNo Unsigned32,
    advaInventoryPortNo Unsigned32,
    advaInventoryExtNo Unsigned32,
    advaInventoryClassName EntityClassName,
    advaInventoryAidString SnmpAdminString,
    advaInventoryUnitName SnmpAdminString,
    advaInventoryFirmwarePackageRev SnmpAdminString,
    advaInventoryHardwareRev SnmpAdminString,
    advaInventorySoftwareRev SnmpAdminString,
    advaInventoryFpgaRev SnmpAdminString,
    advaInventorySerialNum SnmpAdminString,
    advaInventoryPartnumber SnmpAdminString,
    advaInventoryCleiCode SnmpAdminString,
    advaInventoryVendorId SnmpAdminString,
    advaInventoryType EntityType,
    advaInventoryUniversalSerialIdent SnmpAdminString,
    advaInventoryGradeInventory Grade,
    advaInventoryClass EntityClass,
    advaInventoryInventoryDescription SnmpAdminString,
    advaInventoryCapabilityLevel FspR7CapInventory }

advaInventoryShelfNo OBJECT-TYPE
    SYNTAX      Unsigned32
    MAX-ACCESS  not-accessible
    STATUS      current
    DESCRIPTION   "Adress index."
    ::=  { advaInventoryEntry 1 }

advaInventorySlotNo OBJECT-TYPE
    SYNTAX      Unsigned32
    MAX-ACCESS  not-accessible
    STATUS      current
    DESCRIPTION   "Adress index."
    ::=  { advaInventoryEntry 2 }

advaInventoryPortNo OBJECT-TYPE
    SYNTAX      Unsigned32
    MAX-ACCESS  not-accessible
    STATUS      current
    DESCRIPTION   "Adress index."
    ::=  { advaInventoryEntry 3 }

advaInventoryExtNo OBJECT-TYPE
    SYNTAX      Unsigned32
    MAX-ACCESS  not-accessible
    STATUS      current
    DESCRIPTION   "Adress index."
    ::=  { advaInventoryEntry 4 }

advaInventoryClassName OBJECT-TYPE
    SYNTAX      EntityClassName
    MAX-ACCESS  not-accessible
    STATUS      current
    DESCRIPTION   "Entity Class Name."
    ::=  { advaInventoryEntry 5 }

advaInventoryAidString OBJECT-TYPE
    SYNTAX      SnmpAdminString
    MAX-ACCESS  read-only
    STATUS      current
    DESCRIPTION   "Aid string of entity."
    ::=  { advaInventoryEntry 6 }

advaInventoryUnitName OBJECT-TYPE
    SYNTAX      SnmpAdminString
    MAX-ACCESS  read-only
    STATUS      current
    DESCRIPTION
        "ADVA Official Equipment Name"
    ::=  { advaInventoryEntry 7 }

advaInventoryFirmwarePackageRev OBJECT-TYPE
    SYNTAX      SnmpAdminString
    MAX-ACCESS  read-only
    STATUS      current
    DESCRIPTION   "Firmware Package Revision Number"
    ::=  { advaInventoryEntry 8 }

advaInventoryHardwareRev OBJECT-TYPE
    SYNTAX      SnmpAdminString
    MAX-ACCESS  read-only
    STATUS      current
    DESCRIPTION
        "Equipment Revision Number"
    ::=  { advaInventoryEntry 9 }

advaInventorySoftwareRev OBJECT-TYPE
    SYNTAX      SnmpAdminString
    MAX-ACCESS  read-only
    STATUS      current
    DESCRIPTION   "The active Application software version on the unit/module."
    ::=  { advaInventoryEntry 10 }

advaInventoryFpgaRev OBJECT-TYPE
    SYNTAX      SnmpAdminString
    MAX-ACCESS  read-only
    STATUS      current
    DESCRIPTION   "The active FPGA version on the unit/module."
    ::=  { advaInventoryEntry 11 }

advaInventorySerialNum OBJECT-TYPE
    SYNTAX      SnmpAdminString
    MAX-ACCESS  read-only
    STATUS      current
    DESCRIPTION
        "Equipment Serial Number"
    ::=  { advaInventoryEntry 12 }

advaInventoryPartnumber OBJECT-TYPE
    SYNTAX      SnmpAdminString
    MAX-ACCESS  read-only
    STATUS      current
    DESCRIPTION   "ADVA Part Number"
    ::=  { advaInventoryEntry 13 }

advaInventoryCleiCode OBJECT-TYPE
    SYNTAX      SnmpAdminString
    MAX-ACCESS  read-only
    STATUS      current
    DESCRIPTION
        "Common Language Equipment Identifier"
    ::=  { advaInventoryEntry 14 }

advaInventoryVendorId OBJECT-TYPE
    SYNTAX      SnmpAdminString
    MAX-ACCESS  read-only
    STATUS      current
    DESCRIPTION
        "OEM Vendor Code"
    ::=  { advaInventoryEntry 15 }

advaInventoryType OBJECT-TYPE
    SYNTAX      EntityType
    MAX-ACCESS  read-only
    STATUS      current
    DESCRIPTION   "Type of a physical entity: shelf/module/plug"
    ::=  { advaInventoryEntry 16 }

advaInventoryUniversalSerialIdent OBJECT-TYPE
    SYNTAX      SnmpAdminString
    MAX-ACCESS  read-only
    STATUS      current
    DESCRIPTION
        "Unique Serial Identifier"
    ::=  { advaInventoryEntry 17 }

advaInventoryGradeInventory OBJECT-TYPE
    SYNTAX      Grade
    MAX-ACCESS  read-only
    STATUS      current
    DESCRIPTION
        "Used to distinguish between NCU capabilities (range of supported services or applications)"
    ::=  { advaInventoryEntry 18 }

advaInventoryClass OBJECT-TYPE
    SYNTAX      EntityClass
    MAX-ACCESS  read-only
    STATUS      current
    DESCRIPTION
        "Entity Class"
    ::=  { advaInventoryEntry 19 }

advaInventoryInventoryDescription OBJECT-TYPE
    SYNTAX      SnmpAdminString
    MAX-ACCESS  read-only
    STATUS      current
    DESCRIPTION
        "Description string of capability level reported by hw"
    ::=  { advaInventoryEntry 20 }

advaInventoryCapabilityLevel OBJECT-TYPE
    SYNTAX      FspR7CapInventory
    MAX-ACCESS  read-only
    STATUS      current
    DESCRIPTION
        "Capability level reported by HW"
    ::=  { advaInventoryEntry 21 }

unassignedInventoryTable OBJECT-TYPE
    SYNTAX      SEQUENCE OF UnassignedInventoryEntry
    MAX-ACCESS  not-accessible
    STATUS      current
    DESCRIPTION   ""
    ::=  { inventory 2 }

unassignedInventoryEntry OBJECT-TYPE
    SYNTAX      UnassignedInventoryEntry
    MAX-ACCESS  not-accessible
    STATUS      current
    DESCRIPTION   ""
    INDEX       {
                  advaInventoryShelfNo,
                  advaInventorySlotNo,
                  advaInventoryPortNo,
                  advaInventoryExtNo,
                  advaInventoryClassName
                }
    ::=  { unassignedInventoryTable 1 }

UnassignedInventoryEntry ::=  SEQUENCE
  { unassignedInventoryAidString SnmpAdminString,
    unassignedInventoryType EntityType,
    unassignedInventoryParentId RowPointer,
    unassignedInventoryClass EntityClass,
    unassignedInventoryAssignState FspR7EquipmentAssignState,
    unassignedInventoryOneIndex Unsigned32,
    unassignedInventoryTableId RowPointer }

unassignedInventoryAidString OBJECT-TYPE
    SYNTAX      SnmpAdminString
    MAX-ACCESS  read-only
    STATUS      current
    DESCRIPTION   "Aid string of entity."
    ::=  { unassignedInventoryEntry 1 }

unassignedInventoryType OBJECT-TYPE
    SYNTAX      EntityType
    MAX-ACCESS  read-only
    STATUS      current
    DESCRIPTION   "Type of a physical entity: shelf/module/plug"
    ::=  { unassignedInventoryEntry 2 }

unassignedInventoryParentId OBJECT-TYPE
    SYNTAX      RowPointer
    MAX-ACCESS  read-only
    STATUS      current
    DESCRIPTION   "RowPointer to parent entity reported in corresponding entity table."
    ::=  { unassignedInventoryEntry 3 }

unassignedInventoryClass OBJECT-TYPE
    SYNTAX      EntityClass
    MAX-ACCESS  read-only
    STATUS      current
    DESCRIPTION
        "Entity Class"
    ::=  { unassignedInventoryEntry 4 }

unassignedInventoryAssignState OBJECT-TYPE
    SYNTAX      FspR7EquipmentAssignState
    MAX-ACCESS  read-only
    STATUS      current
    DESCRIPTION   "Assignment state of entity."
    ::=  { unassignedInventoryEntry 5 }

unassignedInventoryOneIndex OBJECT-TYPE
    SYNTAX      Unsigned32
    MAX-ACCESS  read-only
    STATUS      current
    DESCRIPTION
        "One Index Aid representation"
    ::=  { unassignedInventoryEntry 6 }

unassignedInventoryTableId OBJECT-TYPE
    SYNTAX      RowPointer
    MAX-ACCESS  read-only
    STATUS      current
    DESCRIPTION   "RowPointer to managment table of entity."
    ::=  { unassignedInventoryEntry 7 }


END
