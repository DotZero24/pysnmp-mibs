ADVA-MIB DEFINITIONS ::= BEGIN

IMPORTS
    MODULE-IDENTITY,
    OBJECT-IDENTITY,
    OBJECT-TYPE,
    NOTIFICATION-TYPE,
    enterprises,
    Integer32,
    Unsigned32,
    IpAddress,
    Counter32,
    Counter64,
    Gauge32,
    TimeTicks,
    mib-2,
    snmpModules
                                        FROM  SNMPv2-SMI
    ifIndex
                                        FROM  IF-MIB
    entPhysicalIndex
                                        FROM  ENTITY-MIB
    DisplayString,
    RowStatus,
    TEXTUAL-CONVENTION,
    DateAndTime,
    TestAndIncr,
    TimeStamp,
    MacAddress
                                        FROM  SNMPv2-TC
    SnmpAdminString
                                        FROM  SNMP-FRAMEWORK-MIB
    MODULE-COMPLIANCE,
    NOTIFICATION-GROUP,
    OBJECT-GROUP
                                        FROM  SNMPv2-CONF;


advaMIB MODULE-IDENTITY
    LAST-UPDATED "201409290000Z"  -- September 29, 2014
    ORGANIZATION "ADVA AG Optical Networking"
    CONTACT-INFO
        "ADVA AG Optical Networking
        Justus-von-Liebig-Str. 7
        12489 Berlin, Germany

        Support Europe:
        Phone:  +49 89 89 0665 848
        Fax:    +49 89 89 0665 22848
        e-mail: support@advaoptical.com

        Support USA:
        Phone:  +1 201 995 0080
        Fax:    +1 201 995 0081
        e-mail: support-usa@advaoptical.com

        Support Asia:
        Phone:  +81 3 5408 5891
        Fax:    +81 3 5408 5899
        e-mail: support-asia@advaoptical.com"
    DESCRIPTION
        "The ADVA Common MIB version 2.3."

    REVISION    "201409290000Z" -- October 07, 2003
    DESCRIPTION
        "The ADVA Optical Networking base MIB."

    REVISION    "201202070000Z"  -- February 7, 2012
    DESCRIPTION
        "Revised ADVA Common MIB version 2.1."

    REVISION    "200802210000Z"  -- February 21, 2008
    DESCRIPTION
        "Revised ADVA Common MIB version 2.0."

    REVISION    "200412140000Z"  -- December 14, 2004
    DESCRIPTION
        "The ADVA Common MIB version 1.7."

    REVISION    "200402200000Z" -- February 20, 2004
    DESCRIPTION
        "The ADVA Common MIB version 1.6."

    REVISION    "200312120000Z" -- December 12, 2003
    DESCRIPTION
        "The ADVA Common MIB version 1.5."

    REVISION    "200310070000Z" -- October 07, 2003
    DESCRIPTION
        "The ADVA Common MIB version 1.4."

    REVISION    "200306270000Z" -- June 27, 2003
    DESCRIPTION
        "The ADVA Common MIB version 1.3"

    REVISION    "200207220000Z" -- July 22, 2002
    DESCRIPTION
        "The ADVA MIB version 1.3."
        ::= { enterprises 2544 }

products        OBJECT IDENTIFIER ::= { advaMIB 1 }
common          OBJECT IDENTIFIER ::= { advaMIB 2 }


-- **************************************************************************
-- **************************  ADVA Products  *******************************
-- **************************************************************************

fsp3000         OBJECT IDENTIFIER ::= { products 4 }
fsp1000         OBJECT IDENTIFIER ::= { products 6 }
fsp2000         OBJECT IDENTIFIER ::= { products 7 }
fsp1000adm      OBJECT IDENTIFIER ::= { products 8 }
fsp1500         OBJECT IDENTIFIER ::= { products 9 }
fsp150          OBJECT IDENTIFIER ::= { products 10 }
fspR7           OBJECT IDENTIFIER ::= { products 11 }
fsp150cm        OBJECT IDENTIFIER ::= { products 12 }
fspNm           OBJECT IDENTIFIER ::= { products 13 }
fsp3000alm            OBJECT IDENTIFIER ::= { products 14 }

aos                   OBJECT IDENTIFIER ::= { products 20 }
aosCommon             OBJECT IDENTIFIER ::= { aos 1 }
aosProducts           OBJECT IDENTIFIER ::= { aos 2 }

fsp3000c              OBJECT IDENTIFIER ::= { aosProducts 1 }
fspxg480              OBJECT IDENTIFIER ::= { aosProducts 2 }
fspxg404              OBJECT IDENTIFIER ::= { aosProducts 3 }
fspxg418              OBJECT IDENTIFIER ::= { aosProducts 4 }
fspxg480-25g-100g              OBJECT IDENTIFIER ::= { aosProducts 5 }
fspxg480-100g                  OBJECT IDENTIFIER ::= { aosProducts 6 }
fspxg480-100gcfp2              OBJECT IDENTIFIER ::= { aosProducts 7 }
fspxg404-100g                  OBJECT IDENTIFIER ::= { aosProducts 8 }
fspxg404-100gcfp2              OBJECT IDENTIFIER ::= { aosProducts 9 }
fspxg418-100g                  OBJECT IDENTIFIER ::= { aosProducts 10 }
fspxg418-100gcfp2              OBJECT IDENTIFIER ::= { aosProducts 11 }
fspxg118pro-cshac              OBJECT IDENTIFIER ::= { aosProducts 12 }
fspxg118pro-cshdc              OBJECT IDENTIFIER ::= { aosProducts 13 }
fspxg118pro-cshac-g            OBJECT IDENTIFIER ::= { aosProducts 14 }
fspxg118pro-cshdc-g            OBJECT IDENTIFIER ::= { aosProducts 15 }

-- **************************************************************************
-- ***********************  The ADVA Common MIB  ****************************
-- **************************************************************************

neInfo          OBJECT IDENTIFIER ::= { common 1 }
admin           OBJECT IDENTIFIER ::= { common 2 }
events          OBJECT IDENTIFIER ::= { common 3 }
software        OBJECT IDENTIFIER ::= { common 4 }
config          OBJECT IDENTIFIER ::= { common 5 }

transportStandards 		 	OBJECT IDENTIFIER ::= { config 4 }
inventoryMib   					OBJECT IDENTIFIER ::= { config 5 }
updateBackupRestoreMib 	OBJECT IDENTIFIER ::= { config 6 }
snmpAgent               OBJECT IDENTIFIER ::= { config 7 }

sonet   				OBJECT IDENTIFIER ::= { transportStandards 1 }
otn   					OBJECT IDENTIFIER ::= { transportStandards 2 }
sonetConfig			OBJECT IDENTIFIER ::= { sonet 1 }
otuConfig   		OBJECT IDENTIFIER ::= { otn 1 }
oduConfig   		OBJECT IDENTIFIER ::= { otn 2 }

swAdmin					OBJECT IDENTIFIER ::= { updateBackupRestoreMib 1 }
dbAdmin   			OBJECT IDENTIFIER ::= { updateBackupRestoreMib 2 }

-- **************************************************************************
-- ***********************  Textual Conventions  ****************************
-- **************************************************************************

OnOff ::= TEXTUAL-CONVENTION
    STATUS      current
    DESCRIPTION
        "Variable for representing a state and is for general use."
    SYNTAX      INTEGER {
        on (1),
        off (2)
    }

AvailState ::= TEXTUAL-CONVENTION
    STATUS      current
    DESCRIPTION
        "Variable for representing availability state and is for
        general use."
    SYNTAX      INTEGER {
        available (1),
        notAvailable (2)
    }

EnableState ::= TEXTUAL-CONVENTION
    STATUS      current
    DESCRIPTION
        "Describes whether a feature is enabled or disabled."
    SYNTAX      INTEGER {
        stateNotApplicable (0),
        stateEnabled (1),
        stateDisabled (2)
    }

ArcState ::= TEXTUAL-CONVENTION
    STATUS      current
    DESCRIPTION
        "Variable for representing the Alarm Report Control (ARC)
        state for an entity."
    SYNTAX      INTEGER {
        alm (1),        -- Reporting turned on (i.e., alarm traps sent).
                        -- Alarms are present in current alarm table
                        -- with own severity.
                        -- Transition nalm->alm: active alarm traps
                        -- sent with own severity.
        nalm (2)        -- Reporting turned off (i.e., no alarm traps).
                        -- Alarms are present in current alarm table
                        -- with severity 'notReported'.
                        -- Transition alm->nalm: active alarms are
                        -- 'cleared' by sending alarm clear traps with
                        -- severity 'notReported'.
        -- nalmTI (3),   - reporting turned off for time interval
        -- nalmQI (4),   - reporting turned off for qualified interval
        -- nalmQICD (5)  - substate of nalmQI with countdown interval
    }

TrapAlarmSeverity ::= TEXTUAL-CONVENTION
    STATUS      current
    DESCRIPTION
        "This object identifies the severity of an alarm. The state
        'cleared' is not a severity, but is used for reporting that
        an alarm condition is no longer present. The state
        'notReported' is used for current alarms which are not
        reported because of ARC.
        The state 'indeterminate' is used when the severity value
        cannot be determined due to an internal error."
    SYNTAX      INTEGER {
        indeterminate (1),
        critical (2),
        major (3),
        minor (4),
        warning (5),
        cleared (6),
        notReported (7)
    }

ServiceImpairment ::= TEXTUAL-CONVENTION
    STATUS      current
    DESCRIPTION
        "This object identifies the potential service impairment of
        an alarm."
    SYNTAX      INTEGER {
        serviceAffecting (1),
        nonServiceAffecting (2),
        serviceAffectingInstall (3),
        serviceAffectingActivate (4)
    }

TrapCounter ::= TEXTUAL-CONVENTION
    STATUS      current
    DESCRIPTION
        "The sequence number of sent notifications (traps)."
    SYNTAX      Counter32

Counter64String ::= TEXTUAL-CONVENTION
    DISPLAY-HINT "20a"
    STATUS      current
    DESCRIPTION
        "A string representation of a 64 bit counter.
        This TC is provided solely for SNMPv1 compliance."
    SYNTAX      OCTET STRING (SIZE (1..20))

KBytes ::= TEXTUAL-CONVENTION
    STATUS      current
    DESCRIPTION
        "A memory size, expressed in units of 1024 bytes."
    SYNTAX      Gauge32

IdentityTranslation ::= TEXTUAL-CONVENTION
    STATUS      current
    DESCRIPTION
        "Translation of an index (entPhysicalIndex, ifIndex etc.)
        to a string.
            Slot/Module/Port location (product specific notation)
            Service/Bundle Name

        If no index available a string with:
            IP address (for neTrapsinkTable etc.)

        If nothing appropriate available
            zero length string

        Further info in product documentation."
    SYNTAX      OCTET STRING (SIZE (0..255))

NeSwUpgradeStatusType ::= TEXTUAL-CONVENTION
    STATUS      current
    DESCRIPTION
        "The status of a NE software upgrade command. The states 2 - 7 and 15, 18-29  are only used
         when the NE is used as FTP client. States from 30 to 36 are used for reporting the
         installation failure in case of revised F7 upgrade procedure, 37-28 are introduce for F7
         schedule backup."
    SYNTAX      INTEGER {
        none (1),
        downloading (2),
        downloadLoginFailed (3),
        downloadFileNotFound (4),
        downloadFileNoAccess (5),
        downloadFailure (6),
        downloadReadyForInstallation (7),
        installingSoftware (8),
        installationFailed (9),
        softwareReadyForActivation (10),
        activatingSoftware (11),
        activationFailed (12),
        softwareActivated (13),
        rebooting (14),
        downloadServerUnreachable (15),
        noSpaceLeft (16),       -- applicable for download and activate
        internalError (17),
        downloadFileProtocolFailed (18),
        downloadFileCheckFailed (19),
        downloadSSHHostkeyFailed(20),
        uploading(21),
        uploadLoginFailed(22),
        uploadFileNotFound(23),
        uploadFileNoAccess(24),
        uploadFailure(25),
        uploadServerUnreachable(26),
        uploadFileProtocolFailed(27),
        uploadFileCheckFailed(28),
        uploadSSHHostkeyFailed(29),
        installationFailedDeny(30),
        installationFailedWrongCrc(31),
        installationFailedVersionMismatch(32),
        installationFailedStbyInWrongState(33),
        installationFailedDamagedConfFile(34),
        installationFailedFsckFailed(35),
        installationFailedNotExist(36),
        downloadFileFailedProtocolDisabled(37),
        uploadFileFailedProtocolDisabled(38),
        backupFailedGeneration(39)
    }

NeSwInstallStatusType ::= TEXTUAL-CONVENTION
    STATUS      current
    DESCRIPTION
        "Software installation status."
    SYNTAX      INTEGER
                {
                  undefined(0),
                  idle(1),
                  downloadingCon(2),
                  installingCon(3),
                  downloadingNcu(4),
                  installingNcu(5),
                  downloadingFwp(6),
                  installingFwp(7),
                  downloadingPgm(8),
                  installingPgm(9)
                }

FileTransferProtocol ::= TEXTUAL-CONVENTION
STATUS      current
DESCRIPTION
    "The protocol used for a file transfer."
SYNTAX      INTEGER {
    -- tftp (1),
    ftp (2),
    scp (3)
}

SourceIpAddress ::= TEXTUAL-CONVENTION
  STATUS        current
  DESCRIPTION
         "IP address used as source IP address in FTP Client session"
  SYNTAX        INTEGER
                {
                  undefined(0),
                  sysIp(1),
                  defaultIp(2)
                }

F7FileTimeStamp ::= TEXTUAL-CONVENTION
  STATUS        current
  DESCRIPTION
         "Add Timestamp to File Name"
  SYNTAX        INTEGER
                {
                  undefined(0),
                  add(1),
                  omit(2)
                }

F7AutoBackupInterval ::= TEXTUAL-CONVENTION
  STATUS        current
  DESCRIPTION
         "Scheduled Database Backup Interval"
  SYNTAX        INTEGER
                {
                  undefined(0),
                  none(1),
                  every1Day(2),
                  every2Day(3),
                  every3Day(4),
                  every4Day(5),
                  every5Day(6),
                  every6Day(7),
                  every1Week(8),
                  every2Week(9),
                  every3Week(10),
                  every1Month(11),
                  every2Month(12),
                  every3Month(13)
                }


F7AutoBackupRunState ::= TEXTUAL-CONVENTION
  STATUS        current
  DESCRIPTION
         ""
  SYNTAX        INTEGER
                {
                  undefined(0),
                  no(1),
                  yes(2)
                }


PartitionStatus ::= TEXTUAL-CONVENTION
  STATUS        current
  DESCRIPTION
         "Partition State"
  SYNTAX        INTEGER
                {
                  undefined(0),
                  empty(1),
                  configFileInstalled(2),
                  ncuFileInstalled(3),
                  softwareReadyForActivation(4),
                  fwpsInstalled(5)
                }


FspDate ::= TEXTUAL-CONVENTION
  DISPLAY-HINT "2d-1d-1d"
  STATUS        current
  DESCRIPTION
         "A date specification.
         field octets contents range
         ----- ------ -------- -----
         1 1-2 year* 0..65536
         2 3 month 1..12
         3 4 day 1..31
         * Notes: - the value of year is in network-byte order
         For example, Tuesday May 26, 1992 would be
         displayed as:
         1992-5-26"
  SYNTAX        OCTET STRING (SIZE(4..4))


FspTime ::= TEXTUAL-CONVENTION
  DISPLAY-HINT "1d-1d-1d"
  STATUS        current
  DESCRIPTION
         "A time specification.
         field octets contents range
         ----- ------ -------- -----
         1 1 hour 0..23
         2 2 minutes 0..59
         3 3 seconds 0..60
         (use 60 for leap-second)
         For example: 13-10-26"
  SYNTAX        OCTET STRING (SIZE(3..3))


ApsDirection ::= TEXTUAL-CONVENTION
  STATUS        current
  DESCRIPTION
         "Bi-Directional | Unidirectional setup used in protection setup: Not to be used by others"
  SYNTAX        INTEGER
                {
                  undefined(0),
                  bidirectional(1),  --bidirectional
                  unidirectional(2)  --unidirectional
                }

ApsDirectionCaps ::= TEXTUAL-CONVENTION
  STATUS        current
  DESCRIPTION
         "Bi-Directional | Unidirectional setup used in protection setup: Not to be used by others"
  SYNTAX        BITS
                {
                  capUndefined(0),
                  capBidirectional(1),
                  capUnidirectional(2)
                }

ApsHoldoffTime ::= TEXTUAL-CONVENTION
  STATUS        current
  DESCRIPTION
         "Soak period before switch after trigger."
  SYNTAX        INTEGER
                {
                  undefined(0),
                  none(1),
                  e20ms(2),
                  e100ms(3),
                  e200ms(4),
                  e300ms(5),
                  e400ms(6),
                  e500ms(7),
                  e600ms(8),
                  e700ms(9),
                  e800ms(10),
                  e900ms(11),
                  e1000ms(12),
                  e1100ms(13),
                  e1200ms(14),
                  e1300ms(15),
                  e1400ms(16),
                  e1500ms(17),
                  e1600ms(18),
                  e1700ms(19),
                  e1800ms(20),
                  e1900ms(21),
                  e2000ms(22),
                  e2100ms(23),
                  e2200ms(24),
                  e2300ms(25),
                  e2400ms(26),
                  e2500ms(27),
                  e2600ms(28),
                  e2700ms(29),
                  e2800ms(30),
                  e2900ms(31),
                  e3000ms(32),
                  e3100ms(33),
                  e3200ms(34),
                  e3300ms(35),
                  e3400ms(36),
                  e3500ms(37),
                  e3600ms(38),
                  e3700ms(39),
                  e3800ms(40),
                  e3900ms(41),
                  e4000ms(42),
                  e4100ms(43),
                  e4200ms(44),
                  e4300ms(45),
                  e4400ms(46),
                  e4500ms(47),
                  e4600ms(48),
                  e4700ms(49),
                  e4800ms(50),
                  e4900ms(51),
                  e5000ms(52),
                  e5100ms(53),
                  e5200ms(54),
                  e5300ms(55),
                  e5400ms(56),
                  e5500ms(57),
                  e5600ms(58),
                  e5700ms(59),
                  e5800ms(60),
                  e5900ms(61),
                  e6000ms(62),
                  e6100ms(63),
                  e6200ms(64),
                  e6300ms(65),
                  e6400ms(66),
                  e6500ms(67),
                  e6600ms(68),
                  e6700ms(69),
                  e6800ms(70),
                  e6900ms(71),
                  e7000ms(72),
                  e7100ms(73),
                  e7200ms(74),
                  e7300ms(75),
                  e7400ms(76),
                  e7500ms(77),
                  e7600ms(78),
                  e7700ms(79),
                  e7800ms(80),
                  e7900ms(81),
                  e8000ms(82),
                  e8100ms(83),
                  e8200ms(84),
                  e8300ms(85),
                  e8400ms(86),
                  e8500ms(87),
                  e8600ms(88),
                  e8700ms(89),
                  e8800ms(90),
                  e8900ms(91),
                  e9000ms(92),
                  e9100ms(93),
                  e9200ms(94),
                  e9300ms(95),
                  e9400ms(96),
                  e9500ms(97),
                  e9600ms(98),
                  e9700ms(99),
                  e9800ms(100),
                  e9900ms(101),
                  e10000ms(102)
                }

ApsHoldoffTimeCaps ::= TEXTUAL-CONVENTION
  STATUS        current
  DESCRIPTION
         "Soak period before switch after trigger."
  SYNTAX        BITS
                {
                  capUndefined(0),
                  capNone(1),
                  capE20ms(2),
                  capE100ms(3),
                  capE200ms(4),
                  capE300ms(5),
                  capE400ms(6),
                  capE500ms(7),
                  capE600ms(8),
                  capE700ms(9),
                  capE800ms(10),
                  capE900ms(11),
                  capE1000ms(12),
                  capE1100ms(13),
                  capE1200ms(14),
                  capE1300ms(15),
                  capE1400ms(16),
                  capE1500ms(17),
                  capE1600ms(18),
                  capE1700ms(19),
                  capE1800ms(20),
                  capE1900ms(21),
                  capE2000ms(22),
                  capE2100ms(23),
                  capE2200ms(24),
                  capE2300ms(25),
                  capE2400ms(26),
                  capE2500ms(27),
                  capE2600ms(28),
                  capE2700ms(29),
                  capE2800ms(30),
                  capE2900ms(31),
                  capE3000ms(32),
                  capE3100ms(33),
                  capE3200ms(34),
                  capE3300ms(35),
                  capE3400ms(36),
                  capE3500ms(37),
                  capE3600ms(38),
                  capE3700ms(39),
                  capE3800ms(40),
                  capE3900ms(41),
                  capE4000ms(42),
                  capE4100ms(43),
                  capE4200ms(44),
                  capE4300ms(45),
                  capE4400ms(46),
                  capE4500ms(47),
                  capE4600ms(48),
                  capE4700ms(49),
                  capE4800ms(50),
                  capE4900ms(51),
                  capE5000ms(52),
                  capE5100ms(53),
                  capE5200ms(54),
                  capE5300ms(55),
                  capE5400ms(56),
                  capE5500ms(57),
                  capE5600ms(58),
                  capE5700ms(59),
                  capE5800ms(60),
                  capE5900ms(61),
                  capE6000ms(62),
                  capE6100ms(63),
                  capE6200ms(64),
                  capE6300ms(65),
                  capE6400ms(66),
                  capE6500ms(67),
                  capE6600ms(68),
                  capE6700ms(69),
                  capE6800ms(70),
                  capE6900ms(71),
                  capE7000ms(72),
                  capE7100ms(73),
                  capE7200ms(74),
                  capE7300ms(75),
                  capE7400ms(76),
                  capE7500ms(77),
                  capE7600ms(78),
                  capE7700ms(79),
                  capE7800ms(80),
                  capE7900ms(81),
                  capE8000ms(82),
                  capE8100ms(83),
                  capE8200ms(84),
                  capE8300ms(85),
                  capE8400ms(86),
                  capE8500ms(87),
                  capE8600ms(88),
                  capE8700ms(89),
                  capE8800ms(90),
                  capE8900ms(91),
                  capE9000ms(92),
                  capE9100ms(93),
                  capE9200ms(94),
                  capE9300ms(95),
                  capE9400ms(96),
                  capE9500ms(97),
                  capE9600ms(98),
                  capE9700ms(99),
                  capE9800ms(100),
                  capE9900ms(101),
                  capE10000ms(102)
                }

AssignmentState ::= TEXTUAL-CONVENTION
  STATUS        current
  DESCRIPTION
         "Assignment State. Describes an entity' state."
  SYNTAX        INTEGER
                {
                  undefined(0),
                  assigned(1), --Entity is provisioned
                  unassigned(2), --Entity is not provisioned
                  notassignable(3) --Entity cannot be provisioned due to some dependencies
                }

BootState ::= TEXTUAL-CONVENTION
  STATUS        current
  DESCRIPTION
         "Boot State. Every state change (excluding IDLE) does generate a corresponding transient condition."
  SYNTAX        INTEGER
                {
                  undefined(0),
                  complete(1),  --Booting has been completed successfully
                  started(2),  --Booting has just started
                  failed(3),  --Fail occurred during the booting operation
                  reject(4),  --Booting operation has been rejected
                  install(5),  --Installation has just started
                  installFail(6),  --Fail occurred during the installation operation
                  installComplete(7),  --Installation has been completed
                  activate(8),  --Activation has just started
                  activateFail(9),  --Fail occurred during the activation operation
                  activateReject(10),  --Activation has been rejected
                  activateComplete(11)  --Activation has been completed
                }

CommandEqpt ::= TEXTUAL-CONVENTION
  STATUS        current
  DESCRIPTION
         "Update, Install and Reboot commands."
  SYNTAX        INTEGER
                {
                  undefined(0),
                  none(1),
                  install(2),  --New FWPREV will become STBY-FWPREV.
                  reboot(3),  --EQPT Reboot.
                  activate(4),  --STBY-FWPREV will become active FWPREV.
                  update(5),  --New FWPREV will become active FWPREV.
                  installFromStby(6),  --New FWPREV-SYS-STBY will become active FWPREV-STBY.
                  forceInstall(7)  --New FWPREV will become STBY-FWPREV. This is forced operation so will be executed for all modules specified by AIDE and TYPE__EQPT no matter what is an active running FWPREV.
                }

CpWdmEntityClass ::= TEXTUAL-CONVENTION
  STATUS        current
  DESCRIPTION
         "Control Plane WDM Entity Class"
  SYNTAX        INTEGER
                {
                  undefined(0),
                  cp(1),
                  tunnel(2),
                  connection(3),
                  path(4),
                  pathElement(5),
                  logicalInterface(6),
                  remoteAlarm(7),
                  portBinding(8),
                  reservation(9)
                }

EnableStateCaps ::= TEXTUAL-CONVENTION
  STATUS        current
  DESCRIPTION
         "Usage of 3rd Party Plugs"
  SYNTAX        BITS
                {
                  capUndefined(0),
                  capStateEnabled(1),
                  capStateDisabled(2)
                }

EntityClass ::= TEXTUAL-CONVENTION
  STATUS        current
  DESCRIPTION
         "Entity Class"
  SYNTAX        INTEGER
                {
                  undefined(0),
                  other(1),
                  unknown(2),
                  chassis(3),
                  backplane(4),
                  container(5),
                  powerSupply(6),
                  fan(7),
                  sensor(8),
                  module(9),
                  plug(10),
                  stack(11),
                  group(12),
                  clientPort(13),
                  networkPort(14),
                  virtualChannel(15),
                  connection(16),
                  vc4Container(17),
                  vc3sts1Container(18),
                  vc12vt15Container(19),
                  dcnChannel(20),
                  routerConfig(21),
                  environmentPort(22),
                  internalPort(23),
                  upgradePort(24),
                  midstagePort(25),
                  serialPort(26),
                  pppIpInterface(27),
                  lanIp(28),
                  vs1Container(29),
                  sts3cContainer(30),
                  payloadChannel(31),
                  passiveShelf(32),
                  sts24cContainer(33),
                  sts48cContainer(34),
                  vs2cContainer(35),
                  vs4cContainer(36),
                  tifInputPort(37),
                  tifOutputPort(38),
                  opticalLink(39),
                  virtualOpticalChannel(40),
                  logicalInterface(41),
                  physicalTerminationPoint(42),
                  ethClient(43),
                  ethNetwork(44),
                  veth(45),
                  flow(47),
                  ctrans(48),
                  policerOnFlow(50),
                  queueOnPort(51),
                  queueOnFlow(52),
                  farEndPlug(53),
                  farEndChannel(54),
                  vc4c8Container(55),
                  vc4c16Container(56),
                  vs0Container(57),
                  virtualSubChannel(58),
                  bridge(59),
                  queueOnBridge(60),
                  backwardVirtualOptMux(61),
                  forwardVirtualOptMux(62),
                  optChannelTransportLane(63),
                  virtualChannelN(64),
                  externalChannel(65),
                  virtualTerminationPoint(66),
                  virtualConnection(67),
                  virtualOptMux(68),
                  optTransportLaneGroup(69),
                  optWaveLengthGroup(70),
                  crossConnectionChannel(71),
                  crossOpticalLineChannel(72),
                  versatilePort(73),
                  system(74),
                  crossConnectionDcn(75),
                  protectionFfp(76),
                  protectionCable(77),
                  unidirectionalChannel(78),
                  filterCable(79)
                }

EntityIndex ::= TEXTUAL-CONVENTION
  STATUS        current
  DESCRIPTION
         "The index of an entity. EntityIndex is used to index the following:
         Entities which are provisioned but unequipped (existing in the database but
         not physically present),
         Entities which are equipped but non-provisioned (physically present but not in
         the database),
         Entities which are both provisioned and equipped (existing in the database and
         physically present),
         Entities which are non-provisioned and unequipped (not existing in the database
         and not physically present).
         These will have an entry in the entityTable, but their EntityType will
         be undefined.
         The EntityIndex is used similarly to how the entPhysicalIndex in
         RFC2737 (Entity MIB) is used to address entities and containers of entities."
  SYNTAX        Integer32 (0..2147483647)

EntityType ::= TEXTUAL-CONVENTION
  STATUS        current
  DESCRIPTION
         "Identifies the entity type. Each NE may have their own use of
         this INTEGER value, which will defined in the conformance document
         for each individual NE MIB."
  SYNTAX        Integer32

EquipmentState ::= TEXTUAL-CONVENTION
  STATUS        current
  DESCRIPTION
         ""
  SYNTAX        INTEGER
                {
                  undefined(0),
                  equipped(1),
                  unequipped(2)
                }

EthDuplexMode ::= TEXTUAL-CONVENTION
  STATUS        current
  DESCRIPTION
         "Duplex Mode Provision."
  SYNTAX        INTEGER
                {
                  undefined(0),
                  ethHalfDuplex(1),  --Half Duplex mode
                  ethFullDuplex(2)  --Full Duplex mode
                }

EthDuplexModeCaps ::= TEXTUAL-CONVENTION
  STATUS        current
  DESCRIPTION
         "Duplex Mode Provision."
  SYNTAX        BITS
                {
                  capUndefined(0),
                  capEthHalfDuplex(1),
                  capEthFullDuplex(2)
                }

FileArea ::= TEXTUAL-CONVENTION
  STATUS        current
  DESCRIPTION
         "Type of Area"
  SYNTAX        INTEGER
                {
                  undefined(0),
                  activeArea(1), --Partition on a disk which is currently in use.
                  standbyArea(2), --Partition on a disk which is currently not active.
                  rDisk(3), --Partition on a disk, which is used in software download/upload procedure.
                  backupDisk(4), --Disk/partition where backup files are stored.
                  alpDisk(5), --Disk/partition where alarm profile files are stored.
                  pDisk(6), --Disk/partition where external channel interface and module profile files are stored.
                  cfDisk(7), --Partition on CF disk, which is used in software download/upload procedure.
                  paDisk(8) --Disk/partition where Path Analazyer files are stored.
                }

FileType ::= TEXTUAL-CONVENTION
  STATUS        current
  DESCRIPTION
         "Type of File"
  SYNTAX        INTEGER
                {
                  undefined(0),
                  pgm(1),  --Portable Gray Map image file (file containing a system image)
                  dbs(2),  --Database file type
                  unknown(3),  --Unknown file type
                  alp(4),  --Alarm profile file type
                  ncu(5),  --PGM image file with NCU-SW
                  fwps(6),  --PGM image file with FWPS
                  con(7),  --Configuration file
                  prf(8)  --Profile (ECH or MOD) file
                }

FspR7AdminStateSnmpProxy ::= TEXTUAL-CONVENTION
  STATUS        current
  DESCRIPTION
         "The Administrative State will be displayed in the GUI with full
         name values; it will be differently displayed in TL1 syntax according
         to TL1 display rules. The transaction into the UAS state requires
         a special destroy/delete function"
  SYNTAX        INTEGER
                {
                  undefined(0),
                  is(2),
                  dsbld(6)
                }

FspR7AdminStateSnmpProxyCaps ::= TEXTUAL-CONVENTION
  STATUS        current
  DESCRIPTION
         "The Administrative State will be displayed in the GUI with full
         name values; it will be differently displayed in TL1 syntax according
         to TL1 display rules. The transaction into the UAS state requires
         a special destroy/delete function"
  SYNTAX        BITS
                {
                  capUndefined(0),
                  capIs(2),
                  capDsbld(6)
                }

FspR7Date ::= TEXTUAL-CONVENTION
  DISPLAY-HINT "2d-1d-1d"
  STATUS        current
  DESCRIPTION
         "A date specification.
         field octets contents range
         ----- ------ -------- -----
         1 1-2 year* 0..65536
         2 3 month 1..12
         3 4 day 1..31
         * Notes: - the value of year is in network-byte order
         For example, Tuesday May 26, 1992 would be
         displayed as:
         1992-5-26"
  SYNTAX        OCTET STRING (SIZE(4..4))

FspR7EquipmentType ::= TEXTUAL-CONVENTION
  STATUS        current
  DESCRIPTION
         "The TYPE of Equipment and the MODE setting determine uniquely
         the number and allowed TYPE's of the provisionable dependent
         entities (plugs, interfaces, modules)"
  SYNTAX        INTEGER
                {
                  undefined(0),
                  eqpSh1hu(1),
                  eqpSh1huDc(2),
                  eqpSh3hu(3),  --deprecated
                  eqpSh7hu(4),
                  eqpF2kSh5hu(5),  --deprecated
                  eqpF2kSh6hu(6),  --deprecated
                  eqpDcm(7),
                  eqpSh9hu(8),
                  eqpUnknown(19),
                  eqpNcu(20),
                  eqpNcutif(21),  --deprecated
                  eqpScu(22),
                  eqpScue(23),
                  eqpR6cu(24),  --deprecated
                  eqpPsu1huac(25),
                  eqpPsu7huac(26),
                  eqpPsu7hudc(27),
                  eqpFcu7hu(28),
                  eqp2clsmd(29),
                  eqp2absmc(30),
                  eqp2bsmd(31),
                  eqp1Gsmud(32),
                  eqp4gsmd(33),
                  eqp8gsmd(34),
                  eqp1csmuc(35),
                  eqp1csmuewc(36),
                  eqp4csmd(37),
                  eqp4csmud(38),
                  eqp4csmc(39),
                  eqpOsfm(40),
                  eqp1pm(41),
                  eqp2pm(42),
                  eqp40csmd(43),
                  eqpDcf(44),
                  eqpEdfas(45),
                  eqpEdfasgc(46),
                  eqpEdfadgc(47),
                  eqpRaman(48),
                  eqp4tcc2g5(49),
                  eqp4tcc2g5d(50),
                  eqp4tcc10gd(51),
                  eqp4tcc10gc(52),
                  eqpWcc10gd(53),
                  eqpWcc10gc(54),
                  eqpWcc2g71N(55),
                  eqpWcc2g7d(56),
                  eqp2tcm2g5(57),
                  eqp2tca2g5(58),
                  eqp8tca10gd(59),
                  eqp8tca10gc(60),
                  eqpWca10gd(61),
                  eqpWca10gc(62),
                  eqp4tca4gd(63),
                  eqp4tca4gc(64),
                  eqpwca2g5(65),
                  eqp4tca1g3d(66),
                  eqp4tca1g3c(67),
                  eqp8tce2g5d(68),
                  eqp8tce2g5c(69),
                  eqpWcelsd(70),
                  eqpWcelsc(71),
                  eqpVsm(72),
                  eqpRsmolm(73),
                  eqpRsmsf(74),
                  eqpOscm(75),
                  eqp2oscm(76),
                  eqpDrm(77),  --deprecated
                  eqpXfpG(78),
                  eqpsfpd(79),
                  eqpSfpc(80),
                  eqpSfpg(81),
                  eqpSfpe(82),
                  eqpSh1hudcm(83),
                  eqpCustomc(84),
                  eqpCustomd(85),
                  eqpPsu1hudc(86),
                  eqpWcc2g7c(87),
                  eqp1csmuEwD(88),
                  eqp1csmuG(89),
                  eqp3BsmC(90),
                  eqp2Tca2g5s(91),
                  eqp8Csmuc(92),
                  eqpEdfaDgcb(93),  --deprecated
                  eqpOscmPn(94),
                  eqp4Tcc10gtd(95),
                  eqp4Tca4g(96),
                  eqpDcg(97),
                  eqp2Tcm2g5d(98),
                  eqp2Tcm2g5c(99),
                  eqpWcm2g5d(100),
                  eqpWcm2g5c(101),
                  eqpEdfmSgc(102),  --deprecated
                  eqpF2kDemiV2(103),  --deprecated
                  eqpPsm(104),
                  eqpNcu2e(105),
                  eqp8TceGl2g5d(106),
                  eqp8TceGl2g5c(107),
                  eqpDcf1hu(108),
                  eqp10tcc10gtd(109),
                  eqp10tcc10gd(110),
                  eqp10tcc10gc(111),
                  eqp16csmSfd(112),
                  eqpOsfmSf(113),
                  eqp2clsmSfd(114),
                  eqp3bsmEwc(115),
                  eqpEdfaSgcb(116),
                  eqpEdfaDgcv(117),
                  eqpWcc10gtd(118),
                  eqp2csmuEwc(119),
                  eqpEroadmDc(120),
                  eqpScuS(122),
                  eqp4opcm(123),
                  eqpUtm(124),
                  eqpPscu(125),
                  eqp40Csm2hu(126),
                  eqp2Twcc2g7(127),
                  eqp2Wca10g(130),
                  eqpNcuHp(131),
                  eqpNcu20085hu(132),  --deprecated
                  eqp20Pca10G(133),
                  eqpXfpC(137),
                  eqpXfpD(138),
                  eqpWcc40gtd(140),
                  eqpIlm(141),
                  eqpNcuII(142),
                  eqpCem9hu(143),
                  eqp8roadmC40(148),
                  eqp4Tcc40gtd(149),
                  eqp2pca10g(150),
                  eqp10pca10g(151),
                  eqp1csmuD(152),
                  eqpSfpOsC(153),
                  eqpSfpOdC(154),
                  eqpSfpOsG(155),
                  eqpSfpOdG(156),
                  eqpRoadmC80(157),
                  eqpccm8(158),
                  eqpPsu9hudc(159),
                  eqp4tca4gus(160),
                  eqp40Csm3huD(161),
                  eqp5psm(162),
                  eqpFan9hu(163),
                  eqp5tce10gtd(164),
                  eqp10tccs10gtd(165),
                  eqp40Csm3hudcD(166),
                  eqp40Csm3hudcDi(167),
                  eqp5gsmD(169),
                  eqp8csmD(170),
                  eqp2otfm(171),
                  eqp8otdr3hu(172),
                  eqpXfptD(173),
                  eqp40Csm3huDi(174),
                  eqp8CcmC80(175),
                  eqpEdfaD27(176),
                  eqp2Wcc10g(177),
                  eqp8RoadmC80(178),
                  eqp2Wcc10gAes(180),  --deprecated
                  eqp5tce10gtaesd(182),
                  eqpSh1hupf(183),
                  eqpFan1hu(185),
                  eqp10tcc10g(186),
                  eqpXfpOtnD(187),
                  eqpNcu2p(188),
                  eqpPsu9huac(190),
                  eqp2Raman(192),
                  eqpEdfaS26(193),
                  eqp5tces10gtd(194),
                  eqpScuII(195),
                  eqp11RoadmC96(196),
                  eqp8AdmC96(197),
                  eqp8CxmC96(198),
                  eqp8Shm(199),
                  eqpAmpShgcv(200),
                  eqpAmpSlgcv(201),
                  eqp2RamanC15(202),
                  eqpWcc100gtD(203),
                  eqpCfp4g(204),
                  eqpCfp10g(205),
                  eqpXfpTlnD(213),
                  eqp5tces10gtaesd(214),
                  eqp10tce100g(215),
                  eqp96Csm4HuD(216),
                  eqp4CfptD(217),
                  eqp2psm(218),
                  eqpWce100G(219),
                  eqp10Wxc10g(220),
                  eqp10tcc100gtbD(223),
                  eqp9RoadmC96(224),
                  eqp4Wce16g(225),
                  eqpSfpBG(226),
                  eqpSfpCdrG(227),
                  eqp10tce100gGf(228),
                  eqpSfpCdrC(229),
                  eqp5tce10gaes(234),
                  eqp5tce10g(235),
                  eqp5tces10gaes(236),
                  eqp5tces10g(237),
                  eqp4roadmC96(239),
                  eqpWcc100gtbD(240),
                  eqpEdfaS20(241),
                  eqp10tccSdi10g(242),
                  eqp4roadmEC96(243),
                  eqpSfptD(245),
                  eqpSfp2TxG(246),
                  eqpSfp2RxG(247),
                  eqpSfp2Txe(248),
                  eqpSfp2Rxe(249),
                  eqp2EdfaS20S10(250),
                  eqp10Tce100Gb(251),
                  eqp10Tce100gAes(252),
                  eqpSfpCdrD(253),
                  eqpSh1huDcEtemp(254),
                  eqp8psm(255),
                  eqp9ccmC96(256),
                  eqpWce100GB(257),
                  eqp5wca16G(260),
                  eqpCfptCd(261),
                  eqpPtp(499)
                }

FspR7EquipmentTypeCaps ::= TEXTUAL-CONVENTION
  STATUS        current
  DESCRIPTION
         "The TYPE of Equipment and the MODE setting determine uniquely
         the number and allowed TYPE's of the provisionable dependent
         entities (plugs, interfaces, modules)"
  SYNTAX        BITS
                {
                  capUndefined(0),
                  capEqpSh1hu(1),
                  capEqpSh1huDc(2),
                  capEqpSh3hu(3),
                  capEqpSh7hu(4),
                  capEqpF2kSh5hu(5),
                  capEqpF2kSh6hu(6),
                  capEqpDcm(7),
                  capEqpSh9hu(8),
                  capEqpUnknown(19),
                  capEqpNcu(20),
                  capEqpNcutif(21),
                  capEqpScu(22),
                  capEqpScue(23),
                  capEqpR6cu(24),
                  capEqpPsu1huac(25),
                  capEqpPsu7huac(26),
                  capEqpPsu7hudc(27),
                  capEqpFcu7hu(28),
                  capEqp2clsmd(29),
                  capEqp2absmc(30),
                  capEqp2bsmd(31),
                  capEqp1Gsmud(32),
                  capEqp4gsmd(33),
                  capEqp8gsmd(34),
                  capEqp1csmuc(35),
                  capEqp1csmuewc(36),
                  capEqp4csmd(37),
                  capEqp4csmud(38),
                  capEqp4csmc(39),
                  capEqpOsfm(40),
                  capEqp1pm(41),
                  capEqp2pm(42),
                  capEqp40csmd(43),
                  capEqpDcf(44),
                  capEqpEdfas(45),
                  capEqpEdfasgc(46),
                  capEqpEdfadgc(47),
                  capEqpRaman(48),
                  capEqp4tcc2g5(49),
                  capEqp4tcc2g5d(50),
                  capEqp4tcc10gd(51),
                  capEqp4tcc10gc(52),
                  capEqpWcc10gd(53),
                  capEqpWcc10gc(54),
                  capEqpWcc2g71N(55),
                  capEqpWcc2g7d(56),
                  capEqp2tcm2g5(57),
                  capEqp2tca2g5(58),
                  capEqp8tca10gd(59),
                  capEqp8tca10gc(60),
                  capEqpWca10gd(61),
                  capEqpWca10gc(62),
                  capEqp4tca4gd(63),
                  capEqp4tca4gc(64),
                  capEqpwca2g5(65),
                  capEqp4tca1g3d(66),
                  capEqp4tca1g3c(67),
                  capEqp8tce2g5d(68),
                  capEqp8tce2g5c(69),
                  capEqpWcelsd(70),
                  capEqpWcelsc(71),
                  capEqpVsm(72),
                  capEqpRsmolm(73),
                  capEqpRsmsf(74),
                  capEqpOscm(75),
                  capEqp2oscm(76),
                  capEqpDrm(77),
                  capEqpXfpG(78),
                  capEqpsfpd(79),
                  capEqpSfpc(80),
                  capEqpSfpg(81),
                  capEqpSfpe(82),
                  capEqpSh1hudcm(83),
                  capEqpCustomc(84),
                  capEqpCustomd(85),
                  capEqpPsu1hudc(86),
                  capEqpWcc2g7c(87),
                  capEqp1csmuEwD(88),
                  capEqp1csmuG(89),
                  capEqp3BsmC(90),
                  capEqp2Tca2g5s(91),
                  capEqp8Csmuc(92),
                  capEqpEdfaDgcb(93),
                  capEqpOscmPn(94),
                  capEqp4Tcc10gtd(95),
                  capEqp4Tca4g(96),
                  capEqpDcg(97),
                  capEqp2Tcm2g5d(98),
                  capEqp2Tcm2g5c(99),
                  capEqpWcm2g5d(100),
                  capEqpWcm2g5c(101),
                  capEqpEdfmSgc(102),
                  capEqpF2kDemiV2(103),
                  capEqpPsm(104),
                  capEqpNcu2e(105),
                  capEqp8TceGl2g5d(106),
                  capEqp8TceGl2g5c(107),
                  capEqpDcf1hu(108),
                  capEqp10tcc10gtd(109),
                  capEqp10tcc10gd(110),
                  capEqp10tcc10gc(111),
                  capEqp16csmSfd(112),
                  capEqpOsfmSf(113),
                  capEqp2clsmSfd(114),
                  capEqp3bsmEwc(115),
                  capEqpEdfaSgcb(116),
                  capEqpEdfaDgcv(117),
                  capEqpWcc10gtd(118),
                  capEqp2csmuEwc(119),
                  capEqpEroadmDc(120),
                  capEqpScuS(122),
                  capEqp4opcm(123),
                  capEqpUtm(124),
                  capEqpPscu(125),
                  capEqp40Csm2hu(126),
                  capEqp2Twcc2g7(127),
                  capEqp2Wca10g(130),
                  capEqpNcuHp(131),
                  capEqpNcu20085hu(132),
                  capEqp20Pca10G(133),
                  capEqpXfpC(137),
                  capEqpXfpD(138),
                  capEqpWcc40gtd(140),
                  capEqpIlm(141),
                  capEqpNcuII(142),
                  capEqpCem9hu(143),
                  capEqp8roadmC40(148),
                  capEqp4Tcc40gtd(149),
                  capEqp2pca10g(150),
                  capEqp10pca10g(151),
                  capEqp1csmuD(152),
                  capEqpSfpOsC(153),
                  capEqpSfpOdC(154),
                  capEqpSfpOsG(155),
                  capEqpSfpOdG(156),
                  capEqpRoadmC80(157),
                  capEqpccm8(158),
                  capEqpPsu9hudc(159),
                  capEqp4tca4gus(160),
                  capEqp40Csm3huD(161),
                  capEqp5psm(162),
                  capEqpFan9hu(163),
                  capEqp5tce10gtd(164),
                  capEqp10tccs10gtd(165),
                  capEqp40Csm3hudcD(166),
                  capEqp40Csm3hudcDi(167),
                  capEqp5gsmD(169),
                  capEqp8csmD(170),
                  capEqp2otfm(171),
                  capEqp8otdr3hu(172),
                  capEqpXfptD(173),
                  capEqp40Csm3huDi(174),
                  capEqp8CcmC80(175),
                  capEqpEdfaD27(176),
                  capEqp2Wcc10g(177),
                  capEqp8RoadmC80(178),
                  capEqp2Wcc10gAes(180),
                  capEqp5tce10gtaesd(182),
                  capEqpSh1hupf(183),
                  capEqpFan1hu(185),
                  capEqp10tcc10g(186),
                  capEqpXfpOtnD(187),
                  capEqpNcu2p(188),
                  capEqpPsu9huac(190),
                  capEqp2Raman(192),
                  capEqpEdfaS26(193),
                  capEqp5tces10gtd(194),
                  capEqpScuII(195),
                  capEqp11RoadmC96(196),
                  capEqp8AdmC96(197),
                  capEqp8CxmC96(198),
                  capEqp8Shm(199),
                  capEqpAmpShgcv(200),
                  capEqpAmpSlgcv(201),
                  capEqp2RamanC15(202),
                  capEqpWcc100gtD(203),
                  capEqpCfp4g(204),
                  capEqpCfp10g(205),
                  capEqpXfpTlnD(213),
                  capEqp5tces10gtaesd(214),
                  capEqp10tce100g(215),
                  capEqp96Csm4HuD(216),
                  capEqp4CfptD(217),
                  capEqp2psm(218),
                  capEqpWce100G(219),
                  capEqp10Wxc10g(220),
                  capEqp10tcc100gtbD(223),
                  capEqp9RoadmC96(224),
                  capEqp4Wce16g(225),
                  capEqpSfpBG(226),
                  capEqpSfpCdrG(227),
                  capEqp10tce100gGf(228),
                  capEqpSfpCdrC(229),
                  capEqp5tce10gaes(234),
                  capEqp5tce10g(235),
                  capEqp5tces10gaes(236),
                  capEqp5tces10g(237),
                  capEqp4roadmC96(239),
                  capEqpWcc100gtbD(240),
                  capEqpEdfaS20(241),
                  capEqp10tccSdi10g(242),
                  capEqp4roadmEC96(243),
                  capEqpSfptD(245),
                  capEqpSfp2TxG(246),
                  capEqpSfp2RxG(247),
                  capEqpSfp2Txe(248),
                  capEqpSfp2Rxe(249),
                  capEqp2EdfaS20S10(250),
                  capEqp10Tce100Gb(251),
                  capEqp10Tce100gAes(252),
                  capEqpSfpCdrD(253),
                  capEqpSh1huDcEtemp(254),
                  capEqp8psm(255),
                  capEqp9ccmC96(256),
                  capEqpWce100GB(257),
                  capEqp5wca16G(260),
                  capEqpCfptCd(261),
                  capEqpPtp(499)
                }

FspR7FalseTrue ::= TEXTUAL-CONVENTION
  STATUS        current
  DESCRIPTION
         "False True variable."
  SYNTAX        INTEGER

                {
                  undefined(0),
                  false(1),
                  true(2)
                }

FspR7Time ::= TEXTUAL-CONVENTION
  DISPLAY-HINT "1d-1d-1d"
  STATUS        current
  DESCRIPTION
         "A time specification.
         field octets contents range
         ----- ------ -------- -----
         1 1 hour 0..23
         2 2 minutes 0..59
         3 3 seconds 0..60
         (use 60 for leap-second)
         For example: 13-10-26"
  SYNTAX        OCTET STRING (SIZE(3..3))

FspR7YesNo ::= TEXTUAL-CONVENTION
  STATUS        current
  DESCRIPTION
         "YesNo variable."
  SYNTAX        INTEGER

                {
                  undefined(0),
                  yes(1),
                  no(2)
                }

FspR7UsersDb ::= TEXTUAL-CONVENTION
  STATUS        current
  DESCRIPTION
         "Users Database"
  SYNTAX        INTEGER
                {
                  undefined(0),
                  yes(1),
                  no(2),
                  keepCurrent(3)
                }

Grade ::= TEXTUAL-CONVENTION
  STATUS        current
  DESCRIPTION
         "Used to distinguish between NCU capabilities (range of supported services or applications)"
  SYNTAX        INTEGER
                {
                  undefined(0),
                  gradeA(1),  --Supports: CWDM / WCA* and xTCA* (access type) modules
                  gradeB(2),  --Supports: same as Grade A and additionally DWDM /  WCE* and xTCE* (enterprise type) modules / WCC* and xTCC* (core type) modules / FC facilities
                  gradeGdps(3),  --Supports: same as Grade B and additionally GDPS
                  gradeC(4)
                }

LoopConfig ::= TEXTUAL-CONVENTION
  STATUS        current
  DESCRIPTION
         "External or Facility Loopback"
  SYNTAX        INTEGER
                {
                  undefined(0),
                  noLoop(1),  --Loopback is not configured
                  lineLoop(2),  --Line loopback
                  inwardLoop(3)  --Inward loopback
                }

LoopConfigCaps ::= TEXTUAL-CONVENTION
  STATUS        current
  DESCRIPTION
         "External or Facility Loopback"
  SYNTAX        BITS
                {
                  capUndefined(0),
                  capNoLoop(1),
                  capLineLoop(2),
                  capInwardLoop(3)
                }

DestinationNodeOrAgentState ::= TEXTUAL-CONVENTION
  STATUS        current
  DESCRIPTION
         ""
  SYNTAX        INTEGER
                {
                  undefined(0),
                  inactive(1)
                }

NcuAutoActivation ::= TEXTUAL-CONVENTION
  STATUS        current
  DESCRIPTION
         "Enable scheduled activation of the standby PGM partition."
  SYNTAX        INTEGER
                {
                  undefined(0),
                  no(1),
                  yes(2)
                }

NoYesNA ::= TEXTUAL-CONVENTION
  STATUS        current
  DESCRIPTION
         "Enumerator values no(1), yes(2), notApplicable(3)."
  SYNTAX        INTEGER

                {
                  undefined(0),
                  no(1),
                  yes(2),
                  notApplicable(3)
                }

OhTerminationLevel ::= TEXTUAL-CONVENTION
  STATUS        current
  DESCRIPTION
         "The entity is Addressable by Management [because its supporting entity is defined in the database and therefore its address existsSignal Tremination Level of Intrusive Access to Header Information.
         Not used in 7.0, monitoring is one layer higher than TERM level,
         if applicable. All conditions detected on monitoring layer will not
         be reported (severity degradated to NR)."
  SYNTAX        INTEGER
                {
                  undefined(0),
                  phys(1),
                  otnOtu(2),
                  otnOdu(3),
                  otnOpu(4),
                  sonetSection(5),
                  sonetLine(6),
                  sonetPath(7),
                  none(8),  --This is used in virtual interfaces
                  pcs(9)
                }

OhTerminationLevelCaps ::= TEXTUAL-CONVENTION
  STATUS        current
  DESCRIPTION
         "The entity is Addressable by Management [because its supporting entity is defined in the database and therefore its address existsSignal Tremination Level of Intrusive Access to Header Information.
         Not used in 7.0, monitoring is one layer higher than TERM level,
         if applicable. All conditions detected on monitoring layer will not
         be reported (severity degradated to NR)."
  SYNTAX        BITS
                {
                  capUndefined(0),
                  capPhys(1),
                  capOtnOtu(2),
                  capOtnOdu(3),
                  capOtnOpu(4),
                  capSonetSection(5),
                  capSonetLine(6),
                  capSonetPath(7),
                  capNone(8),
                  capPcs(9)
                }

OtnPayloadType ::= TEXTUAL-CONVENTION
  STATUS        current
  DESCRIPTION
         "The PAYLOAD defines the transport service type of the payload"
  SYNTAX        INTEGER
                {
                  undefined(0),
                  ifType10GbE(3),
                  ifTypeOc192(4),
                  ifTypeOc48(5),
                  ifTypeStm16(6),
                  ifTypeStm64(7),
                  ifType10GFC(8),
                  ifType1GFC(12),
                  ifTypeF9953(15),
                  ifTypeF10312(16),
                  ifTypeF10518(17),
                  ifTypeF2488(18),
                  ifType2GFC(39),
                  ifType1GbE(41),
                  ifTypeF4250(52),
                  ifTypeStm1(85),
                  ifTypeStm4(86),
                  ifTypeOc3(87),
                  ifTypeOc12(88),
                  ifTypeF8500(110),
                  ifTypeF10000(129),
                  ifTypeF5000(150),
                  ifTypeF14025(178),
                  ifType40GbE(192),
                  ifTypeF41250(194),
                  ifTypeF103125(195)
                }

OtnPayloadTypeCaps ::= TEXTUAL-CONVENTION
  STATUS        current
  DESCRIPTION
         "The PAYLOAD defines the transport service type of the payload"
  SYNTAX        BITS
                {
                  capUndefined(0),
                  capIfType10GbE(3),
                  capIfTypeOc192(4),
                  capIfTypeOc48(5),
                  capIfTypeStm16(6),
                  capIfTypeStm64(7),
                  capIfType10GFC(8),
                  capIfType1GFC(12),
                  capIfTypeF9953(15),
                  capIfTypeF10312(16),
                  capIfTypeF10518(17),
                  capIfTypeF2488(18),
                  capIfType2GFC(39),
                  capIfType1GbE(41),
                  capIfTypeF4250(52),
                  capIfTypeStm1(85),
                  capIfTypeStm4(86),
                  capIfTypeOc3(87),
                  capIfTypeOc12(88),
                  capIfTypeF8500(110),
                  capIfTypeF10000(129),
                  capIfTypeF5000(150),
                  capIfTypeF14025(178),
                  capIfType40GbE(192),
                  capIfTypeF41250(194),
                  capIfTypeF103125(195)
                }

OtnTcmLevel ::= TEXTUAL-CONVENTION
  STATUS        current
  DESCRIPTION
         "Activation of Tandem Connection Monitoring Instance A. 6 Tandem Connection Monitoring levels are available."
  SYNTAX        INTEGER
                {
                  undefined(0),
                  tcm1(1),
                  tcm2(2),
                  tcm3(3),
                  tcm4(4),
                  tcm5(5),
                  tcm6(6),
                  disabled(7)
                }

OtnTcmLevelCaps ::= TEXTUAL-CONVENTION
  STATUS        current
  DESCRIPTION
         "Activation of Tandem Connection Monitoring Instance A. 6 Tandem Connection Monitoring levels are available."
  SYNTAX        BITS
                {
                  capUndefined(0),
                  capTcm1(1),
                  capTcm2(2),
                  capTcm3(3),
                  capTcm4(4),
                  capTcm5(5),
                  capTcm6(6),
                  capDisabled(7)
                }

PgmType ::= TEXTUAL-CONVENTION
  STATUS        current
  DESCRIPTION
         "Program Type"
  SYNTAX        INTEGER
                {
                  undefined(0),
                  null(1),
                  ncu(2),
                  ncuHp(3),
                  fwps(4),
                  legacy(5)
                }

ProtectionMech ::= TEXTUAL-CONVENTION
  STATUS        current
  DESCRIPTION
         "Port Based refers to HST Cards and Switches: Card Based refers to additional equipment protection"
  SYNTAX        INTEGER
                {
                  undefined(0),
                  pathProtection(1),  --Path protection
                  channelCardProtection(2),  --Channel card protection
                  channelProtection(3),  --Channel protection
                  versatileSwitchedProtection(4),
                  flowProtection(5),  --ELINE Flow (EVC) protection
                  clientCardProtection(6)
                }

ProtectionMechCaps ::= TEXTUAL-CONVENTION
  STATUS        current
  DESCRIPTION
         "Port Based refers to HST Cards and Switches: Card Based refers to additional equipment protection"
  SYNTAX        BITS
                {
                  capUndefined(0),
                  capPathProtection(1),
                  capChannelCardProtection(2),
                  capChannelProtection(3),
                  capVersatileSwitchedProtection(4),
                  capFlowProtection(5),
                  capClientCardProtection(6)
                }

RestoreActivation ::= TEXTUAL-CONVENTION
  STATUS        current
  DESCRIPTION
         "Shows whether the last activation was(will be) a database restore or a new software activation"
  SYNTAX        INTEGER
                {
                  undefined(0),
                  notRestore(1),  --ACT-DBS will not be affected.
                  restoreFromStdBy(2),  --STBY-DBS will become ACT-DBS and vice versa (ACT-DBS will become STBY-DBS).
                  restoreToFactory(3),  --Reset to factory default.
                  restoreFromEqpt(4),  --7.0.2 - see DBINIT
                  acceptDatabase(5)  --upon ACTIVATE or REBOOT as command (TL1 INIT-SYS) ACCEPT will cause the physical SERNO of SHELF-1 to override the SERNO of SHELF1 in the database oan activate the database in ACT
                }

RestoreActivationCaps ::= TEXTUAL-CONVENTION
  STATUS        current
  DESCRIPTION
         "Shows whether the last activation was(will be) a database restore or a new software activation"
  SYNTAX        BITS
                {
                  capUndefined(0),
                  capNotRestore(1),
                  capRestoreFromStdBy(2),
                  capRestoreToFactory(3),
                  capRestoreFromEqpt(4),
                  capAcceptDatabase(5)
                }

ServiceAffecting ::= TEXTUAL-CONVENTION
  STATUS        current
  DESCRIPTION
         "Service Affecting Change during FWP upgrade and Restart operation"
  SYNTAX        INTEGER
                {
                  undefined(0),
                  nsa(1),  --Change is not service affecting
                  sa(2),  --Change is service affecting
                  saActivate(3),  --Activation (reboot) is service affecting
                  saInstall(4),  --Installation is service affecting
                  none(5)  --Update is not needed
                }

ServiceAffectingCaps ::= TEXTUAL-CONVENTION
  STATUS        current
  DESCRIPTION
         "Service Affecting Change during FWP upgrade and Restart operation"
  SYNTAX        BITS
                {
                  capUndefined(0),
                  capNsa(1),
                  capSa(2),
                  capSaActivate(3),
                  capSaInstall(4),
                  capNone(5)
                }

StandbyServiceAffecting ::= TEXTUAL-CONVENTION
  STATUS        current
  DESCRIPTION
         "Service Affecting Change during FWP upgrade after activation of STBY PGM partition."
  SYNTAX        INTEGER
                {
                  undefined(0),
                  nsa(1),  --Change is not service affecting
                  sa(2),  --Change is service affecting
                  saActivate(3),  --Activation (reboot) is service affecting
                  saInstall(4),  --Installation is service affecting
                  none(5)  --Update is not needed
                }

SnmpProxySynchronizationState ::= TEXTUAL-CONVENTION
  STATUS        current
  DESCRIPTION
         "This parameter is used to synchronize proxy table on GNE with destination NE's
         availability.
        "
  SYNTAX        INTEGER
                {
                  undefined(0),
                  inactive(1),
                  active(2)
                }

SnmpProxySynchronizationStage ::= TEXTUAL-CONVENTION
  STATUS        current
  DESCRIPTION
         "This parameter is used to indicate stage of synchronization process.
        "
  SYNTAX        INTEGER
                {
                  undefined(0),
                  started(1),
                  finished(2)
                }

SonetSectSigDegThres ::= TEXTUAL-CONVENTION
  STATUS        current
  DESCRIPTION
         "The SONET signal degrade threshold as a bit error rate."
  SYNTAX        INTEGER

                {
                  undefined(0),
                  ber10exp5(1),   --Bit error rate given in 10^5 form
                  ber10exp6(2),   --Bit error rate given in 10^6 form
                  ber10exp7(3),   --Bit error rate given in 10^7 form
                  ber10exp8(4),   --Bit error rate given in 10^8 form
                  ber10exp9(5)   --Bit error rate given in 10^9 form
                }

SonetSectSigDegThresCaps ::= TEXTUAL-CONVENTION
  STATUS        current
  DESCRIPTION
         "The SONET signal degrade threshold as a bit error rate."
  SYNTAX        INTEGER

                {
                  undefined(0),
                  capBer10exp5(1),
                  capBer10exp6(2),
                  capBer10exp7(3),
                  capBer10exp8(4),
                  capBer10exp9(5)
                }

SonetTimingSource ::= TEXTUAL-CONVENTION
  STATUS        current
  DESCRIPTION
         "Interface Timing Source Selection"
  SYNTAX        INTEGER
                {
                  undefined(0),
                  loopTiming(1),  --Loop source
                  internal(2)  --Internal source
                }

SonetTimingSourceCaps ::= TEXTUAL-CONVENTION
  STATUS        current
  DESCRIPTION
         "Interface Timing Source Selection"
  SYNTAX        BITS
                {
                  capUndefined(0),
                  capLoopTiming(1),
                  capInternal(2)
                }

SonetTraceForm ::= TEXTUAL-CONVENTION
  STATUS        current
  DESCRIPTION
         "Byte-Length of Trace Compared to Expected"
  SYNTAX        INTEGER
                {
                  undefined(0),
                  form64CRLF(1),  --note: only 62 byte available for user
                  form16CRC7(2),  --note: only 15 byte available for user
                  form1Byte(3)  --note: [000...255] consits of 3 strings of decimal numbers
                }

SonetTraceFormCaps ::= TEXTUAL-CONVENTION
  STATUS        current
  DESCRIPTION
         "Byte-Length of Trace Compared to Expected"
  SYNTAX        BITS
                {
                  capUndefined(0),
                  capForm64CRLF(1),
                  capForm16CRC7(2),
                  capForm1Byte(3)
                }

SonetVcBundleAllocation ::= TEXTUAL-CONVENTION
  STATUS        current
  DESCRIPTION
         "Each byte represents one sequence position in the VC bundle, always assigned
         consecutively. The sequence identifies the order in which the individual VCs are combined
         within the VC-4-Xv/VC-3-Xv. Each VC has a fixed unique sequence number in the range of 0
         to (X-1): byte 0: VC4/VC3 transporting the first container of the VC-4-Xv/VC-3-Xv is
         assigned sequence number 0, byte 1: VC4/VC3 transporting the second container of the
         VC-4-Xv/VC-3-Xv is assigned sequence number 1, etc. byte (X-1): VC4/VC3 transporting
         container X of the VC-4-Xv/VC-3-Xv is assigned sequence number (X-1).
        "
  SYNTAX        OCTET STRING (SIZE(0..64))

SonetVcBundleAllocationCaps ::= TEXTUAL-CONVENTION
  STATUS        current
  DESCRIPTION
         "Each bit set in the bitmask represents the number
         of a free VC. Bit 0 = VC #1, and so on.
        "
  SYNTAX        BITS

                {
                  vc1(0),
                  vc2(1),
                  vc3(2),
                  vc4(3),
                  vc5(4),
                  vc6(5),
                  vc7(6),
                  vc8(7),
                  vc9(8),
                  vc10(9),
                  vc11(10),
                  vc12(11),
                  vc13(12),
                  vc14(13),
                  vc15(14),
                  vc16(15),
                  vc17(16),
                  vc18(17),
                  vc19(18),
                  vc20(19),
                  vc21(20),
                  vc22(21),
                  vc23(22),
                  vc24(23),
                  vc25(24),
                  vc26(25),
                  vc27(26),
                  vc28(27),
                  vc29(28),
                  vc30(29),
                  vc31(30),
                  vc32(31),
                  vc33(32),
                  vc34(33),
                  vc35(34),
                  vc36(35),
                  vc37(36),
                  vc38(37),
                  vc39(38),
                  vc40(39),
                  vc41(40),
                  vc42(41),
                  vc43(42),
                  vc44(43),
                  vc45(44),
                  vc46(45),
                  vc47(46),
                  vc48(47),
                  vc49(48),
                  vc50(49),
                  vc51(50),
                  vc52(51),
                  vc53(52),
                  vc54(53),
                  vc55(54),
                  vc56(55),
                  vc57(56),
                  vc58(57),
                  vc59(58),
                  vc60(59),
                  vc61(60),
                  vc62(61),
                  vc63(62),
                  vc64(63)
                }

TimMode ::= TEXTUAL-CONVENTION
  STATUS        current
  DESCRIPTION
         "Detection of TIM-OTU Condition can be configured"
  SYNTAX        INTEGER
                {
                  undefined(0),
                  disabled(1),
                  enableAisDisabled(2),
                  enableAisEnabled(3)
                }

TimModeCaps ::= TEXTUAL-CONVENTION
  STATUS        current
  DESCRIPTION
         "Detection of TIM-OTU Condition can be configured"
  SYNTAX        BITS
                {
                  capUndefined(0),
                  capDisabled(1),
                  capEnableAisDisabled(2),
                  capEnableAisEnabled(3)
                }

FspR7TrapsinkLifetime ::= TEXTUAL-CONVENTION
  STATUS        current
  DESCRIPTION
         "Lifetime of Trapsink"
  SYNTAX        INTEGER
                {
                  undefined(0),
                  duration1hour(1),
                  duration1day(2),
                  duration3days(3),
                  duration1week(4),
                  duration1month(5),
                  unlimited(6)
                }

VirtualContainerType ::= TEXTUAL-CONVENTION
  STATUS        current
  DESCRIPTION
         "Virtual Container Group Type"
  SYNTAX        INTEGER
                {
                  undefined(0),
                  vc4Type(1),  --Virtual Container-4; 149.76 Mbit bit rate
                  vc3Au4Type(2),  --Virtual Container-3; 48.384 Mbit bit rate
                  sts1(3),  --Synchronous Transport Signal-1; 48.384 Mbit bit rate
                  sts3c(4),  --Synchronous Transport Signal-3, concatenated; 149.79 Mbit bit rate
                  vs1(5),  --1 Gbit rate
                  vs2c(6),  --2 Gbit rate
                  sts24c(7),
                  sts48c(8),
                  vs4c(9),
                  vc4c8(10),
                  vc4c16(11),
                  vs0(12),
                  vs3c(13),
                  vs5c(14),
                  vs8c(15),
                  vs6c(16),
                  oduFlex(19)
                }

VirtualContainerTypeCaps ::= TEXTUAL-CONVENTION
  STATUS        current
  DESCRIPTION
         "Virtual Container Group Type"
  SYNTAX        BITS
                {
                  capUndefined(0),
                  capVc4Type(1),
                  capVc3Au4Type(2),
                  capSts1(3),
                  capSts3c(4),
                  capVs1(5),
                  capVs2c(6),
                  capSts24c(7),
                  capSts48c(8),
                  capVs4c(9),
                  capVc4c8(10),
                  capVc4c16(11),
                  capVs0(12),
                  capVs3c(13),
                  capVs5c(14),
                  capVs8c(15),
                  capVs6c(16),
                  capOduFlex(19)
                }

YesNoNA ::= TEXTUAL-CONVENTION
  STATUS        current
  DESCRIPTION
         "Enumerator values yes(1), no(2), notApplicable(3)."
  SYNTAX        INTEGER

                {
                  undefined(0),
                  yes(1),
                  no(2),
                  notApplicable(3)
                }

LogicalIfTransport ::= TEXTUAL-CONVENTION
  STATUS        current
  DESCRIPTION
         ""
  SYNTAX        OCTET STRING (SIZE(1..64))

LogicalIfTransportCaps ::= TEXTUAL-CONVENTION
  STATUS        current
  DESCRIPTION
         ""
  SYNTAX        BITS

                {
                  lif1(0),
                  lif2(1),
                  lif3(2),
                  lif4(3),
                  lif5(4),
                  lif6(5),
                  lif7(6),
                  lif8(7),
                  lif9(8),
                  lif10(9),
                  lif11(10),
                  lif12(11),
                  lif13(12),
                  lif14(13),
                  lif15(14),
                  lif16(15)
                }

ModuleForm ::= TEXTUAL-CONVENTION
  STATUS        current
  DESCRIPTION
         "Form of module"
  SYNTAX        INTEGER
                {
                  undefined(0),
                  native(1),
                  legacy(2),
                  compatible(3)
                }


-- **************************************************************************
-- *************************  NE Information  *******************************
-- **************************************************************************

neMibVariant OBJECT-TYPE
    SYNTAX      Integer32 (0..9999)
    MAX-ACCESS  read-only
    STATUS      current
    DESCRIPTION
        "The variant of the SNMP enterprise MIB. This object will
        together with sysObjectID [RFC1213] uniquely identify the
        revision and variant of the enterprise MIB used by the NE."
    ::= { neInfo 1 }

neManufacturer OBJECT-TYPE
    SYNTAX      SnmpAdminString
    MAX-ACCESS  read-only
    STATUS      current
    DESCRIPTION
        "Manufacturer of the system. This value is used to present
        in clear text the manufacturer of the system."
    ::= { neInfo 2 }

neDateAndTime OBJECT-TYPE
    SYNTAX      DateAndTime
    MAX-ACCESS  read-write
    STATUS      current
    DESCRIPTION
        "Reports the current local time on the Network Element.
        It also allows to set the local time. However, SET
        requests may not be supported by all products."
    ::= { neInfo 3 }

neMemorySizeTotal OBJECT-TYPE
    SYNTAX      KBytes
    UNITS       "kBytes"
    MAX-ACCESS  read-only
    STATUS      current
    DESCRIPTION
        "The total amount of physical main memory contained in
        the NEMI."
    ::= { neInfo 4 }

neMemorySizeFree OBJECT-TYPE
    SYNTAX      KBytes
    UNITS       "kBytes"
    MAX-ACCESS  read-only
    STATUS      current
    DESCRIPTION
        "The amount of unused physical main memory contained in
        the NEMI."
    ::= { neInfo 5 }

neStorageTable OBJECT-TYPE
    SYNTAX SEQUENCE OF NeStorageEntry
    MAX-ACCESS  not-accessible
    STATUS      current
    DESCRIPTION
        "The table of long-term storage partitions contained in
        the NE."
    ::= { neInfo 6 }

neStorageEntry OBJECT-TYPE
    SYNTAX      NeStorageEntry
    MAX-ACCESS  not-accessible
    STATUS      current
    DESCRIPTION
        "An entry for one long-term storage partition contained in
        the NE."
    INDEX { neStorageIndex }
    ::= { neStorageTable 1 }

NeStorageEntry ::= SEQUENCE {
    neStorageIndex      Unsigned32,
    neStorageDescr      SnmpAdminString,
    neStorageCapacity   KBytes,
    neStorageAvailable  KBytes
    }

neStorageIndex OBJECT-TYPE
    SYNTAX      Unsigned32
    MAX-ACCESS  not-accessible
    STATUS      current
    DESCRIPTION
        "The index of the NE storage partition."
    ::= { neStorageEntry 1 }

neStorageDescr OBJECT-TYPE
    SYNTAX      SnmpAdminString
    MAX-ACCESS  read-only
    STATUS      current
    DESCRIPTION
        "The product specific description of the NE storage
        partition."
    ::= { neStorageEntry 2 }

neStorageCapacity OBJECT-TYPE
    SYNTAX      KBytes
    UNITS       "kBytes"
    MAX-ACCESS  read-only
    STATUS      current
    DESCRIPTION
        "The total capacity of the NE storage partition."
    ::= { neStorageEntry 3 }

neStorageAvailable OBJECT-TYPE
    SYNTAX      KBytes
    UNITS       "kBytes"
    MAX-ACCESS  read-only
    STATUS      current
    DESCRIPTION
        "The free space on the NE storage partition."
    ::= { neStorageEntry 4 }

neAlarmStatus OBJECT-TYPE
    SYNTAX      TrapAlarmSeverity
    MAX-ACCESS  read-only
    STATUS      current
    DESCRIPTION
        "The highest severity of all currently active alarms on the
        NE. Alarms that are not reported because of Alarm Report
        Control (ARC) or any other administrative state are not
        considered active. The values indeterminate(1) and
        notReported(7) are not applicable for this object. The value
        cleared(6) indicates that the NE reports no alarm
        (i.e. Alarm LED(s) off)."
    ::= { neInfo 7 }

-- **************************************************************************
-- ********************  Administration & Security **************************
-- **************************************************************************

snmpWriteAccessRestriction OBJECT-TYPE
    SYNTAX      EnableState
    MAX-ACCESS  read-only
    STATUS      current
    DESCRIPTION
        "This value is used in combination with the
        snmpWriteAccessTable for additional security for SNMP set
        requests. When the status is Disabled, SNMP set requests
        from any NMS (using the correct write community) are
        accepted (ie, the snmpWriteAccessTable entries do not
        apply).
        When the status is Enabled, however, only SNMP set requests
        from NMSs (using the correct write community) which are
        listed in the snmpWriteAccessTable are accepted.
        This object is read-only, meaning that it cannot be updated
        via the SNMP interface. The operator must configure SNMP
        write access permissions via a non-SNMP interface."
    ::= { admin 1 }


snmpWriteAccessTable OBJECT-TYPE
    SYNTAX      SEQUENCE OF SnmpWriteAccessEntry
    MAX-ACCESS  not-accessible
    STATUS      current
    DESCRIPTION
        "Table of authorized NMSs (identified by IP address) for
        SNMP set requests.
        This table is not relevant if snmpWriteAccessRestriction is
        set to Disabled.
        The entries of this table are read-only. This means
        that the SNMP write access permissions cannot be updated via
        the SNMP interface. The operator must configure them via a
        non-SNMP interface."
    ::= { admin 2 }

snmpWriteAccessEntry OBJECT-TYPE
    SYNTAX      SnmpWriteAccessEntry
    MAX-ACCESS  not-accessible
    STATUS      current
    DESCRIPTION
        "Entries in the SNMP Write Access Table.
        The maximum of rows in this table is product specific,
        typically 10."
    INDEX { snmpWriteAccessNmsAddress }
    ::= { snmpWriteAccessTable 1 }

SnmpWriteAccessEntry ::= SEQUENCE {
    snmpWriteAccessNmsAddress   IpAddress,
    snmpWriteAccessNmsName      SnmpAdminString
    }

snmpWriteAccessNmsAddress OBJECT-TYPE
    SYNTAX      IpAddress
    MAX-ACCESS  not-accessible
    STATUS      current
    DESCRIPTION
        "IP Address of the NMS which has SNMP write permission."
    ::= { snmpWriteAccessEntry 1 }

snmpWriteAccessNmsName OBJECT-TYPE
    SYNTAX      SnmpAdminString
    MAX-ACCESS  read-only
    STATUS      current
    DESCRIPTION
        "Name of the NMS."
    ::= { snmpWriteAccessEntry 2 }


-- **************************************************************************
-- *************************  Event Handling  *******************************
-- **************************************************************************

neEventsLogged OBJECT-TYPE
    SYNTAX      TrapCounter
    MAX-ACCESS  read-only
    STATUS      current
    DESCRIPTION
        "This value is the sum of all notified events (trap counter).
        It is also the event number of the most recent event
        (neEventLogIndex) found in the neEventLog tables. It can,
        for example, be used to check if a notification (trap) is
        lost.
        The value is reset to 0 after a cold start. The counter is
        increased even if no trap sinks are specified."
    ::= { events 1 }


-- **************************************************************************
-- *************************   neEventLog Table   ***************************
-- **************************************************************************
-- All enterprise-specific events are logged in the log table, even if a
-- trap was not sent to any trapsinks.
-- The events are indexed by the neEventLogIndex (used as a trap counter)
-- and include a timestamp indicating when the event occurred.
-- The corresponding neEventLogTimeStamp is included in each trap, thus
-- allowing the possibility of tracking (and detecting lost messages by
-- comparing to neEventsLogged) traps at a management station.
-- The neEventLogIdentityTranslation is also included in each trap.
-- This table is a simplified version of the nlmLogTable in [RFC3014].
--
-- Note: since this table can be very large, the management systems
-- should use caution when requesting information from this table
-- to reduce the load on the network (ie, always use getnext with the
-- last received trap counter as index).
--
-- The number of available records is product specific.
-- **************************************************************************

neEventLogTable OBJECT-TYPE
    SYNTAX      SEQUENCE OF NeEventLogEntry
    MAX-ACCESS  not-accessible
    STATUS      current
    DESCRIPTION
        "Table of events issued by the NE's SNMP agent. The eventLog
        entries are read-only."
    ::= { events 2 }

neEventLogEntry OBJECT-TYPE
    SYNTAX      NeEventLogEntry
    MAX-ACCESS  not-accessible
    STATUS      current
    DESCRIPTION
        "Entries in the neEventLog Table. Enterprise traps are
        always logged; logging of Generic traps is product specific."
    INDEX { neEventLogIndex }
    ::= { neEventLogTable 1 }

NeEventLogEntry ::= SEQUENCE {
    neEventLogIndex                 TrapCounter,
    neEventLogTimeStamp             DateAndTime,
    neEventLogNotificationOID       OBJECT IDENTIFIER,
    neEventLogIdentityTranslation   IdentityTranslation
    }

neEventLogIndex OBJECT-TYPE
    SYNTAX      TrapCounter
    MAX-ACCESS  not-accessible
    STATUS      current
    DESCRIPTION
        "The associated neEventsLogged counter for the logged
        event (trap)."
    ::= { neEventLogEntry 1 }

neEventLogTimeStamp OBJECT-TYPE
    SYNTAX      DateAndTime
    MAX-ACCESS  read-only
    STATUS      current
    DESCRIPTION
        "The NE Date and Time when the event (trap) occurred. This
        object is used in the trap varbind."
    ::= { neEventLogEntry 2 }

neEventLogNotificationOID OBJECT-TYPE
    SYNTAX      OBJECT IDENTIFIER
    MAX-ACCESS  read-only
    STATUS      current
    DESCRIPTION
        "The NOTIFICATION-TYPE object identifier of the event that
        occurred. The last part of the OID corresponds to the
        specific trap type value in the trap PDU."
    ::= { neEventLogEntry 3 }

neEventLogIdentityTranslation OBJECT-TYPE
    SYNTAX      IdentityTranslation
    MAX-ACCESS  read-only
    STATUS      current
    DESCRIPTION
        "Translation of entPhysicalIndex/ifIndex or other identifier
        to a string used in the trap varbind following the timestamp
        varbind."
    ::= { neEventLogEntry 4 }


-- **************************************************************************
-- ************************   neEventLogVar Table   *************************
-- **************************************************************************
-- The variables of an entry in the neEventLogTable are logged in this table.
-- Note: the OctetString syntax is also used to represent DataAndTime
-- SnmpAdminString and DisplayString objects. Integer32 is also used to
-- represent INTEGER. This table is a simplified version of
-- nlmLogVariableTable in [RFC3014].
-- **************************************************************************

neEventLogVarTable OBJECT-TYPE
    SYNTAX      SEQUENCE OF NeEventLogVarEntry
    MAX-ACCESS  not-accessible
    STATUS      current
    DESCRIPTION
        "Table of variables corresponding to events logged in the
        neEventLog."
    ::= { events 3 }

neEventLogVarEntry OBJECT-TYPE
    SYNTAX      NeEventLogVarEntry
    MAX-ACCESS  not-accessible
    STATUS      current
    DESCRIPTION
        "Entries in the neEventLogVar Table. An entry appears in
        this table for each variable in the varbind list of an entry
        in the neEventLogTable. For an event having no variables,
        no entries are found in this table."
    INDEX { neEventLogIndex, neEventLogVarIndex }
    ::= { neEventLogVarTable 1 }

NeEventLogVarEntry ::= SEQUENCE {
    neEventLogVarIndex          Unsigned32,
    neEventLogVarId             OBJECT IDENTIFIER,
    neEventLogVarType           INTEGER,
    neEventLogVarInteger32Val   Integer32,
    neEventLogVarIpAddressVal   IpAddress,
    neEventLogVarOctetStringVal OCTET STRING,
    neEventLogVarOidVal         OBJECT IDENTIFIER,
    neEventLogVarCounter64Val   Counter64,
    neEventLogVarUnsigned32Val  Unsigned32
}

neEventLogVarIndex OBJECT-TYPE
    SYNTAX      Unsigned32
    MAX-ACCESS  not-accessible
    STATUS      current
    DESCRIPTION
        "A monotonically increasing integer, starting at 1 for a
        given neEventLogIndex, for indexing a variable contained in
        the varbind list of a logged event."
    ::= { neEventLogVarEntry 1 }

neEventLogVarId OBJECT-TYPE
    SYNTAX      OBJECT IDENTIFIER
    MAX-ACCESS  read-only
    STATUS      current
    DESCRIPTION
        "The object identifier of the variable in the varbind list."
    ::= { neEventLogVarEntry 2 }

neEventLogVarType OBJECT-TYPE
    SYNTAX      INTEGER {
        integer32 (1),
        ipAddress (2),
        octetString (3),
        objectId (4),
        counter64 (5),
        -- counter32,
        unsigned32 (7)
        -- timeTicks,
        -- opaque
    }
    MAX-ACCESS  read-only
    STATUS      current
    DESCRIPTION
        "The type of variable. One and only one of the value objects
        that follow must be instantiated, based on this type. The
        used types depend on the enterprise traps defined for the
        specific product."
    ::= { neEventLogVarEntry 3 }

neEventLogVarInteger32Val OBJECT-TYPE
    SYNTAX      Integer32
    MAX-ACCESS  read-only
    STATUS      current
    DESCRIPTION
        "The value when neEventLogVarType is 'integer32'. Integer32
        is also used to represent INTEGER types.
        Otherwise, 0 is returned."
    ::= { neEventLogVarEntry 4 }

neEventLogVarIpAddressVal OBJECT-TYPE
    SYNTAX      IpAddress
    MAX-ACCESS  read-only
    STATUS      current
    DESCRIPTION
        "The value when neEventLogVarType is 'ipAddress'.
        Otherwise, an empty address is returned."
    ::= { neEventLogVarEntry 5 }

neEventLogVarOctetStringVal OBJECT-TYPE
    SYNTAX      OCTET STRING (SIZE (0..255))
    MAX-ACCESS  read-only
    STATUS      current
    DESCRIPTION
        "The value when neEventLogVarType is 'octetString'.
        OctetString is used for all string types, including
        DisplayString, SnmpAdminString and DateAndTime.
        Otherwise, an empty string is returned."
    ::= { neEventLogVarEntry 6 }

neEventLogVarOidVal OBJECT-TYPE
    SYNTAX      OBJECT IDENTIFIER
    MAX-ACCESS  read-only
    STATUS      current
    DESCRIPTION
        "The value when neEventLogVarType is 'objectId'.
        Otherwise, an objectId { 0.0 } is returned."
    ::= { neEventLogVarEntry 7 }

neEventLogVarCounter64Val OBJECT-TYPE
    SYNTAX      Counter64
    MAX-ACCESS  read-only
    STATUS      current
    DESCRIPTION
        "The value when neEventLogVarType is 'counter64'."
    ::= { neEventLogVarEntry 8 }

neEventLogVarUnsigned32Val OBJECT-TYPE
    SYNTAX      Unsigned32
    MAX-ACCESS  read-only
    STATUS      current
    DESCRIPTION
        "The value when neEventLogVarType is 'unsigned32'."
    ::= { neEventLogVarEntry 10 }

-- Trap Sink Table

neTrapsinkTable OBJECT-TYPE
    SYNTAX      SEQUENCE OF NeTrapsinkEntry
    MAX-ACCESS  not-accessible
    STATUS      current
    DESCRIPTION
        "Table of Trapsinks. A neTrapsinkTable entry can be created,
        deleted or modified via the SNMP interface for a specific
        address and port."
    ::= { events 4 }

neTrapsinkEntry OBJECT-TYPE
    SYNTAX      NeTrapsinkEntry
    MAX-ACCESS  not-accessible
    STATUS      current
    DESCRIPTION
        "Entries in the Trapsink Table. Entries are created and
        deleted using the neTrapsinkRowStatus object. The maximum of
        rows in this table is product specific."
    INDEX { neTrapsinkAddress, neTrapsinkPort }
    ::= { neTrapsinkTable 1 }

NeTrapsinkEntry ::= SEQUENCE {
    neTrapsinkAddress       IpAddress,
    neTrapsinkPort          Integer32,
    neTrapsinkCommunity     DisplayString,
    neTrapsinkRowStatus     RowStatus,
    neTrapsinkVersion 			Unsigned32,
    neTrapsinkUserName 			DisplayString,
	neTrapsinkType 			FspR7TrapsinkLifetime
    }

neTrapsinkAddress OBJECT-TYPE
    SYNTAX      IpAddress
    MAX-ACCESS  not-accessible
    STATUS      current
    DESCRIPTION
        "IP Address of the Management System which should receive
        SNMP Traps."
    ::= { neTrapsinkEntry 1 }

neTrapsinkPort OBJECT-TYPE
    SYNTAX      Integer32 (0..65535)
    MAX-ACCESS  not-accessible
    STATUS      current
    DESCRIPTION
        "The port number where the specified trap sink will receive
        SNMP traps."
    ::= { neTrapsinkEntry 2 }

neTrapsinkCommunity OBJECT-TYPE
    SYNTAX      DisplayString (SIZE(0..128))
    MAX-ACCESS  read-write
    STATUS      current
    DESCRIPTION
        "Community String which is sent with an SNMP Trap to the
        Management Station. If no community is specified, the
        default (public) is used."
    ::= { neTrapsinkEntry 3 }

neTrapsinkRowStatus OBJECT-TYPE
    SYNTAX      RowStatus
    MAX-ACCESS  read-write
    STATUS      current
    DESCRIPTION
        "The status of this conceptual row. To create a row in this
        table, set this object to createAndGo(4). To remove a row,
        set this object to destroy(6)."
    ::= { neTrapsinkEntry 4 }

neTrapsinkVersion OBJECT-TYPE
    SYNTAX      Unsigned32
    UNITS       ""
    MAX-ACCESS  read-write
    STATUS      current
    DESCRIPTION
        ""
    ::=  { neTrapsinkEntry 5 }

neTrapsinkUserName OBJECT-TYPE
    SYNTAX      DisplayString
    MAX-ACCESS  read-write
    STATUS      current
    DESCRIPTION
        "A human readable string representing the name of the user."
    ::=  { neTrapsinkEntry 6 }

neTrapsinkType OBJECT-TYPE
    SYNTAX      FspR7TrapsinkLifetime
    MAX-ACCESS  read-write
    STATUS      current
    DESCRIPTION
        "Lifetime of Trapsink."
    ::= { neTrapsinkEntry 7 }

-- **************************************************************************
-- *************************  System Software  ******************************
-- **************************************************************************

swVersionTable OBJECT-TYPE
    SYNTAX      SEQUENCE OF SwVersionEntry
    MAX-ACCESS  not-accessible
    STATUS      current
    DESCRIPTION
        "Software version information table for units/modules which
        run a management Operating System. This includes the
        Application software and Operating System software."
    ::= { software 1 }

swVersionEntry OBJECT-TYPE
    SYNTAX      SwVersionEntry
    MAX-ACCESS  not-accessible
    STATUS      current
    DESCRIPTION
        "Entries in the swVersion Table."
    INDEX { entPhysicalIndex }
    ::= { swVersionTable 1 }

SwVersionEntry ::= SEQUENCE {
    swVersionActiveApplSw           SnmpAdminString,
    swVersionInactiveApplSw         SnmpAdminString,
    swVersionActiveOperatingSw      SnmpAdminString,
    swVersionInactiveOperatingSw    SnmpAdminString,
    swVersionNextBoot               INTEGER
    }

swVersionActiveApplSw OBJECT-TYPE
    SYNTAX      SnmpAdminString
    MAX-ACCESS  read-only
    STATUS      current
    DESCRIPTION
        "Reports the active Application software version on the
        unit/module."
    ::= { swVersionEntry 1 }

swVersionInactiveApplSw OBJECT-TYPE
    SYNTAX      SnmpAdminString
    MAX-ACCESS  read-only
    STATUS      current
    DESCRIPTION
        "Reports the inactive Application software version available
        on the unit/module."
    ::= { swVersionEntry 2 }

swVersionActiveOperatingSw OBJECT-TYPE
    SYNTAX      SnmpAdminString
    MAX-ACCESS  read-only
    STATUS      current
    DESCRIPTION
        "Reports the active Operating System software version on the
        unit/module."
    ::= { swVersionEntry 3 }

swVersionInactiveOperatingSw OBJECT-TYPE
    SYNTAX      SnmpAdminString
    MAX-ACCESS  read-only
    STATUS      current
    DESCRIPTION
        "Reports the inactive Operating System software version
        available on the unit/module."
    ::= { swVersionEntry 4 }

swVersionNextBoot OBJECT-TYPE
    SYNTAX      INTEGER {
        activeVersion (1),
        inactiveVersion (2)
    }
    MAX-ACCESS  read-only
    STATUS      current
    DESCRIPTION
        "Reports which software will be run at next
        boot, either the currently active one again
        or the alternative (currently inactive) one."
    ::= { swVersionEntry 5 }

neSoftwareUpgrade OBJECT IDENTIFIER ::= { software 2 }

neSwUpgradeRequest OBJECT-TYPE
    SYNTAX      INTEGER {
        none (1),                          -- none
        download (2),                      -- download new software
        install (3),                       -- install new software
        activate (4),                      -- enable installed software for next reboot
        revertToPrevious (5),              -- activate previously installed software
        reboot (6),                        -- run activated software
        downloadInstallActivateReboot(7),  -- shortcut (NE is FTP client)
        installActivateReboot (8),         -- shortcut (NE is FTP server)
        revertToPreviousReboot (9),        -- shortcut (revert to previous)
        activateAlp (10),                  -- activate alarm profile severities
        activateDefaultAlp (11),           -- activate default alarm profile severities
        upload (12),                       -- upload file from NE to remote location
        autoDownloadInstall (13),          -- auto download and install from remote location
        autoInstall (14),                  -- auto install from RDISK
        encryptionFwpInstall (15),         -- install firmware package for encryption-capable module
        encryptionFwpDownloadInstall (16), -- download and install firmware package for encryption-capable module
        downloadCf (17),                   -- download file from remote location to CF Disk
        uploadCf (18),                     -- upload file from CF Disk to remote location
        installCf (19),                    -- install new software from CF Disk
        autoInstallCf (20),                -- auto install from CF Disk
        uploadPa (21),                     -- upload file to PA Disk
        activateWithFwp (22)               -- activate with firmware
    }
    MAX-ACCESS  read-write
    STATUS      current
    DESCRIPTION
        "The request to the software upgrade function.
        Request 2..6 are single step requests while requests 7..9
        are batch commands for common upgrade scenarios. Requests 13,14
        are defined for automatic install process for F7 platform.

        If the NE is the FTP server, the file must then have been
        downloaded to the neSwUpgradeNeDirectory on the NE using the
        'netadmin' account."
    ::= { neSoftwareUpgrade 1 }

neSwUpgradeState OBJECT-TYPE
    SYNTAX      NeSwUpgradeStatusType
    MAX-ACCESS  read-only
    STATUS      current
    DESCRIPTION
        "The current status of the SW upgrade process.
        NOTE: All failures that are caused by malfunctioning
              hardware are reported as internalError(17)."
    ::= { neSoftwareUpgrade 2 }

neSwUpgradeServerAddress OBJECT-TYPE
    SYNTAX      IpAddress
    MAX-ACCESS  read-write
    STATUS      current
    DESCRIPTION
        "The IP address of the external FTP server."
    ::= { neSoftwareUpgrade 3 }

neSwUpgradeServerLogin OBJECT-TYPE
    SYNTAX      SnmpAdminString
    MAX-ACCESS  read-write
    STATUS      current
    DESCRIPTION
        "The login name on the external FTP server."
    ::= { neSoftwareUpgrade 4 }

neSwUpgradeServerPasswd OBJECT-TYPE
    SYNTAX      SnmpAdminString
    MAX-ACCESS  read-write
    STATUS      current
    DESCRIPTION
        "The password on the external FTP server. Read requests on
        this object will return a zero-length string."
    ::= { neSoftwareUpgrade 5 }

neSwUpgradeServerDirectory OBJECT-TYPE
    SYNTAX      SnmpAdminString
    MAX-ACCESS  read-write
    STATUS      current
    DESCRIPTION
        "The SW file location (path) on the external FTP server."
   ::= { neSoftwareUpgrade 6 }

neSwUpgradeFileName OBJECT-TYPE
    SYNTAX      SnmpAdminString
    MAX-ACCESS  read-write
    STATUS      current
    DESCRIPTION
        "The SW file name (without path) on the external FTP server
        or the name of the file which has been downloaded to the NE."
    ::= { neSoftwareUpgrade 7 }

neSwUpgradeNeDirectory OBJECT-TYPE
    SYNTAX      SnmpAdminString
    MAX-ACCESS  read-only
    STATUS      current
    DESCRIPTION
        "The SW file location (path) on the NE."
    ::= { neSoftwareUpgrade 8 }

neSwUpgradeTransferProtocol OBJECT-TYPE
    SYNTAX      FileTransferProtocol
    MAX-ACCESS  read-write
    STATUS      current
    DESCRIPTION
        "The transfer protocol to be used."
    ::= { neSoftwareUpgrade 9 }

sourceIpAddress OBJECT-TYPE
    SYNTAX      SourceIpAddress
    MAX-ACCESS  read-write
    STATUS      current
    DESCRIPTION
        "IP address used as source IP address in FTP Client session"
    ::=  { neSoftwareUpgrade 10 }

neSwInstallState OBJECT-TYPE
    SYNTAX      NeSwInstallStatusType
    MAX-ACCESS  read-only
    STATUS      current
    DESCRIPTION
        "Software installation state."
    ::=  { neSoftwareUpgrade 11 }

neSwUpgradeType OBJECT-TYPE
    SYNTAX      INTEGER
                {
                  undefined(0),
                  legacy(1),
                  revised(2)
                }
    MAX-ACCESS  read-write
    STATUS      current
    DESCRIPTION
        "Required procedure type to be used for software download. legacy(1) is the default value.
         This parameter MUST be set before any other parameters will be set for software upgrade
         procedure (for example IP address, user name, password etc.). revised(2) value corresponds
         to Revised Upgrade Procedure which uses new PGM format. This parameter is NOT stored in the
         database and will be reset to default after SNMP Agent restart.
        "
    ::=  { neSoftwareUpgrade 12 }

neSwDownloadProgress OBJECT-TYPE
    SYNTAX      Integer32 (0..100 | -2147483648)
    UNITS       "%"
    MAX-ACCESS  not-accessible
    STATUS      current
    DESCRIPTION
        "Operational progress in % i.e. file transfer"
    ::=  { neSoftwareUpgrade 13 }

neSwUpgradeCommonIpSrv OBJECT-TYPE
    SYNTAX      SnmpAdminString
    MAX-ACCESS  read-write
    STATUS      current
    DESCRIPTION
        "IPv4/v6 Server Address"
    ::=  { neSoftwareUpgrade 14 }

-- **************************************************************************
-- **************************  Configuration  *******************************
-- **************************************************************************

provContainerTable OBJECT-TYPE
    SYNTAX      SEQUENCE OF ProvContainerEntry
    MAX-ACCESS  not-accessible
    STATUS      current
    DESCRIPTION
        "This table defines the objects that support provisioning of
        'container' class physical entities.  Provisioning sets up a
        'container' to hold a specified physical entity.  This allows
        a management client to configure the specified physical entity,
        including all of its subordinates physical entities, before
        installation.

        Provisioning allows the network manager to 'create' the
        physical entities that represent the new modules. In
        essence, the device simulates the installation of the new
        modules into the system.  This has the effect of creating all
        conceptual rows in all the necessary tables that support the
        physical entity and all its subordinate physical entities (e.g.,
        entPhysicalTable, and ifTable).

        The table extends some entries in the entPhysicalTable
        (see ENTITY-MIB for further details). A entry appears in
        this table for a physical entity matching the following
        criteria:

        1)  Its entPhysicalClass object has a value of 'container';

        2)  It can contain one (but not multiple) physical entity;
            and,

        3)  It supports provisioning.


        The following states cause an alarm to be raised at the level
        of the containing module:

        IF  provAssignmentState = assigned(1)
              AND
            provEquipmentState = unequipped(2)
        THEN  'eqMissing' alarm

        IF    provEquipmentState = invalid(3)
        THEN  'eqNotAccepted' alarm
        "
::= { config 1 }

provContainerEntry OBJECT-TYPE
    SYNTAX      ProvContainerEntry
    MAX-ACCESS  not-accessible
    STATUS      current
    DESCRIPTION
        "Entries in the provContainer Table."
    INDEX { entPhysicalIndex }
    ::= { provContainerTable 1 }

ProvContainerEntry ::= SEQUENCE {
    provAssignmentState   INTEGER,
    provEquipmentState    INTEGER
    }

provAssignmentState OBJECT-TYPE
    SYNTAX      INTEGER {
        assigned (1),     -- a module type has been assigned to the container
        unassigned (2)    -- the container is unassigned (not provisioned)
    }
    MAX-ACCESS  read-only
    STATUS      current
    DESCRIPTION
        "This status indicates the assignment (provisioning) of a
        module type to the container."
    ::= { provContainerEntry 1 }

provEquipmentState OBJECT-TYPE
    SYNTAX      INTEGER {
        equipped (1),
        unequipped (2),
        invalid (3)
    }
    MAX-ACCESS  read-only
    STATUS      current
    DESCRIPTION
        "This status indicates how the container is equipped:

        'equipped'      The container holds a module that fits to the
                        container.

        'unequipped'    The container does not hold any hardware.

        'invalid'       The container holds a recognized module that
                        the container is not capable of supporting,
                        or the container holds an unrecognized
                        module.
        "
    ::= { provContainerEntry 2 }

neBackupRestore OBJECT IDENTIFIER ::= { config 2 }

neBackupRestoreRequest OBJECT-TYPE
    SYNTAX      INTEGER {
        none (1),          -- no operation,
        runBackup (2),     -- backup database file to RDISK,
        runRestore (3),    -- restore database from file,
        dBdownload (4),    -- download database file to RDISK from remote location,
        dBupload (5),      -- upload database file to remote location,
        dbDownloadScu (6), -- download database file to SCU from remote location,
        dbUploadScu (7),   -- upload database file from SCU to remote location,
        alpDownload (8),   -- download alarm severities from alarm profile,
        alpUpload (9),     -- upload alarm severities from alarm profile,
        runBackupScu (10)  -- backup database file to SCU
    }
    MAX-ACCESS  read-write
    STATUS      current
    DESCRIPTION
        "Run network element configuration Backup/Restore operation:

        - none(1):       No action (read only)

        - runBackup(2):  Save the network element configuration to
                         a file (write only)

        - runRestore(3): Restore the network element configuration
                         from a file (write only)

        The Restore operation does not overwrite settings which are
        required to reestablish contact to the NE via SNMP and
        Telnet."
    ::= { neBackupRestore 1 }

neBackupRestoreState OBJECT-TYPE
    SYNTAX      INTEGER {
        noBackupAvailable (1),
        backupInProgress (2),
        backupAvailable (3),
        restoreInProgress (4),

        backupRestoreFail (5),
        backupRestoreIdle (6),
        backupRestoreCompleted (7),
        dbActivationFailed (8),
        dbActivationInProgress (9)
    }
    MAX-ACCESS  read-only
    STATUS      current
    DESCRIPTION
        "The status of the current NE configuration backup/restore
        operation activated by 'neBackupRestoreRequest'."
    ::= { neBackupRestore 2 }

neBackupRestoreFile OBJECT-TYPE
    SYNTAX      SnmpAdminString
    MAX-ACCESS  read-only
    STATUS      current
    DESCRIPTION
        "The full local path of the network element configuration
        backup file.
        This file is generated during the Backup operation and is
        also used for the Restore operation."
    ::= { neBackupRestore 3 }

neRestoreFileBackupDate OBJECT-TYPE
    SYNTAX      DateAndTime
    MAX-ACCESS  read-only
    STATUS      current
    DESCRIPTION
        "The backup time of the current file to be used for Restore.
        If no backup is available, this object reports 8 zero-octets."
    ::= { neBackupRestore 4 }

-- The MIB part 'neF7AutomaticRemoteBackup' and 'neF7AutomaticBackup' provides access to regular
-- F7 network element configuration backup.

neF7AutomaticRemoteBackupSrvIp OBJECT-TYPE
    SYNTAX      IpAddress
    MAX-ACCESS  read-write
    STATUS      current
    DESCRIPTION
        "Remote server IP as a backup destination address."
    ::=  { neBackupRestore 5 }

neF7AutomaticRemoteBackupSrvDir OBJECT-TYPE
    SYNTAX      SnmpAdminString
    MAX-ACCESS  read-write
    STATUS      current
    DESCRIPTION
        "Remote server directory."
    ::=  { neBackupRestore 6 }

neF7AutomaticRemoteBackupSrvLogin OBJECT-TYPE
    SYNTAX      SnmpAdminString
    MAX-ACCESS  read-write
    STATUS      current
    DESCRIPTION
        "Remote user login."
    ::=  { neBackupRestore 7 }

neF7AutomaticRemoteBackupSrvPass OBJECT-TYPE
    SYNTAX      SnmpAdminString
    MAX-ACCESS  read-write
    STATUS      current
    DESCRIPTION
        "Remote user password."
    ::=  { neBackupRestore 8 }

neF7AutomaticRemoteBackupProtocol OBJECT-TYPE
    SYNTAX      FileTransferProtocol
    MAX-ACCESS  read-write
    STATUS      current
    DESCRIPTION
        "Connection protocol to be used for remote backup."
    ::=  { neBackupRestore 10 }

neF7AutomaticRemoteBackupSrcIp OBJECT-TYPE
    SYNTAX      SourceIpAddress
    MAX-ACCESS  read-write
    STATUS      current
    DESCRIPTION
        "Source IP address to be used for remote backup."
    ::=  { neBackupRestore 11 }

neF7AutomaticRemoteBackupTimeStamp OBJECT-TYPE
    SYNTAX      F7FileTimeStamp
    MAX-ACCESS  read-write
    STATUS      deprecated
    DESCRIPTION
        "Add or omit the time stamp in the backuped filename."
    ::=  { neBackupRestore 12 }

neF7AutomaticRemoteBackupCommonIpSrv OBJECT-TYPE
    SYNTAX      SnmpAdminString
    MAX-ACCESS  read-write
    STATUS      current
    DESCRIPTION   "Remote server IPv4/IPv6 as a backup destination address."
    ::=  { neBackupRestore 13 }

neF7AutomaticBackupTable OBJECT-TYPE
    SYNTAX      SEQUENCE OF NeF7AutomaticBackupEntry
    MAX-ACCESS  not-accessible
    STATUS      current
    DESCRIPTION
        "Table releated to SCU/Remote backup."
    ::=  { neBackupRestore 20 }

neF7AutomaticBackupEntry OBJECT-TYPE
    SYNTAX      NeF7AutomaticBackupEntry
    MAX-ACCESS  not-accessible
    STATUS      current
    DESCRIPTION
        "Entry releated to SCU/Remote backup."
    INDEX       { neF7AutomaticBackupIndex }
    ::=  { neF7AutomaticBackupTable 1 }

NeF7AutomaticBackupEntry ::=  SEQUENCE
  { neF7AutomaticBackupIndex EntityIndex,
    neF7AutomaticBackupInterval F7AutoBackupInterval,
    neF7AutomaticBackupStartDate FspDate,
    neF7AutomaticBackupStartTime FspTime,
    neF7AutomaticBackupNextDate FspDate,
    neF7AutomaticBackupRunState F7AutoBackupRunState,
    neF7AutomaticBackupTimeStamp F7FileTimeStamp }

neF7AutomaticBackupIndex OBJECT-TYPE
    SYNTAX      EntityIndex
    MAX-ACCESS  not-accessible
    STATUS      current
    DESCRIPTION
        "Index of the backup entity. May be the Backup SCU
         entity index or Backup Remote entity index."
    ::=  { neF7AutomaticBackupEntry 1 }

neF7AutomaticBackupInterval OBJECT-TYPE
    SYNTAX      F7AutoBackupInterval
    MAX-ACCESS  read-write
    STATUS      current
    DESCRIPTION
        "Schedule database backup interval."
    ::=  { neF7AutomaticBackupEntry 2 }

neF7AutomaticBackupStartDate OBJECT-TYPE
    SYNTAX      FspDate
    MAX-ACCESS  read-write
    STATUS      current
    DESCRIPTION
        "Schedule database backup start date."
    ::=  { neF7AutomaticBackupEntry 3 }

neF7AutomaticBackupStartTime OBJECT-TYPE
    SYNTAX      FspTime
    MAX-ACCESS  read-write
    STATUS      current
    DESCRIPTION
        "Schedule database backup start time."
    ::=  { neF7AutomaticBackupEntry 4 }

neF7AutomaticBackupNextDate OBJECT-TYPE
    SYNTAX      FspDate
    MAX-ACCESS  read-only
    STATUS      current
    DESCRIPTION
        "Next schedule database backup date."
    ::=  { neF7AutomaticBackupEntry 5 }

neF7AutomaticBackupRunState OBJECT-TYPE
    SYNTAX      F7AutoBackupRunState
    MAX-ACCESS  read-write
    STATUS      current
    DESCRIPTION
        "Automatic Backup running state."
    ::=  { neF7AutomaticBackupEntry 6 }

neF7AutomaticBackupTimeStamp OBJECT-TYPE
    SYNTAX      F7FileTimeStamp
    MAX-ACCESS  read-write
    STATUS      current
    DESCRIPTION
        "Add or omit the time stamp in the backuped filename."
    ::=  { neF7AutomaticBackupEntry 7 }

-- The MIB part 'neAutoBackup' provides access to regular network element
-- configuration backup.

neAutoBackup    OBJECT IDENTIFIER ::= { config 3 }

neAutoBackupConfig OBJECT-TYPE
    SYNTAX      INTEGER {
        disabled (1),
        autoBackup (2),
        autoBackupAndUpload
     (3)
    }
    MAX-ACCESS  read-write
    STATUS      current
    DESCRIPTION
        "The configuration of the regular network element
        configuration Backup/Restore:

        - disabled(1):            No regular backup

        - autoBackup(2):          Regular backup to a local file
                                  is active

        - autoBackupAndUpload(3): Regular backup and upload to
                                  external FTP server is active

        The default is autoBackup(2).

        If this object is not disabled(1) all other auto-backup
        objects are read-only. I.e., all neAutoBackupServerXxx
        objects must be set before changing this object to
        autoBackupAndUpload(3)."
    ::= { neAutoBackup 1 }

neAutoBackupInterval OBJECT-TYPE
    SYNTAX      Unsigned32
    UNITS       "hours"
    MAX-ACCESS  read-write
    STATUS      current
    DESCRIPTION
        "The interval between two subsequent backup actions in
        hours (default: 24 hours)."
    ::= { neAutoBackup 2 }

neAutoBackupNextActionAt OBJECT-TYPE
    SYNTAX      DateAndTime
    MAX-ACCESS  read-write
    STATUS      current
    DESCRIPTION
        "The sliding time of the next backup action (default:
        midnight local NE time)."
    ::= { neAutoBackup 3 }

neAutoBackupServerAddress OBJECT-TYPE
    SYNTAX      IpAddress
    MAX-ACCESS  read-write
    STATUS      current
    DESCRIPTION
        "The IP address of the external FTP server for backup files."
    ::= { neAutoBackup 4 }

neAutoBackupServerLogin OBJECT-TYPE
    SYNTAX      SnmpAdminString
    MAX-ACCESS  read-write
    STATUS      current
    DESCRIPTION
        "The login name on the external FTP server for backup files."
    ::= { neAutoBackup 5 }

neAutoBackupServerPasswd OBJECT-TYPE
    SYNTAX      SnmpAdminString
    MAX-ACCESS  read-write
    STATUS      current
    DESCRIPTION
        "The password on the external FTP server for backup files.
        Read requests on this object will return a zero-length
        string."
    ::= { neAutoBackup 6 }

neAutoBackupServerDirectory OBJECT-TYPE
    SYNTAX      SnmpAdminString
    MAX-ACCESS  read-write
    STATUS      current
    DESCRIPTION
        "The directory on the external FTP server to which the
        backup files will be uploaded. The file name will be
        generated automatically (containing NE IP addres and backup
        time)."
    ::= { neAutoBackup 7 }

inventoryTable OBJECT-TYPE
    SYNTAX      SEQUENCE OF InventoryEntry
    MAX-ACCESS  not-accessible
    STATUS      current
    DESCRIPTION   "This table lists all physically present (equipped) equipment in the NE"
    ::=  { inventoryMib 1 }

inventoryEntry OBJECT-TYPE
    SYNTAX      InventoryEntry
    MAX-ACCESS  not-accessible
    STATUS      current
    DESCRIPTION   ""
    INDEX       {
                  entityIndex
                }
    ::=  { inventoryTable 1 }

InventoryEntry ::=  SEQUENCE
  { inventoryUnitName SnmpAdminString,
    inventoryFirmwarePackageRev SnmpAdminString,
    inventoryHardwareRev SnmpAdminString,
    inventorySoftwareRev SnmpAdminString,
    inventoryFpgaRev SnmpAdminString,
    inventorySerialNum SnmpAdminString,
    inventoryPartnumber SnmpAdminString,
    inventoryCleiCode SnmpAdminString,
    inventoryVendorId SnmpAdminString,
    inventoryType EntityType,
    inventoryUniversalSerialIdent SnmpAdminString,
    inventoryMacAddress MacAddress,
    inventoryGradeInventory Grade }

inventoryUnitName OBJECT-TYPE
    SYNTAX      SnmpAdminString
    MAX-ACCESS  read-only
    STATUS      current
    DESCRIPTION
        "ADVA Official Equipment Name"
    ::=  { inventoryEntry 1 }

inventoryFirmwarePackageRev OBJECT-TYPE
    SYNTAX      SnmpAdminString
    MAX-ACCESS  read-only
    STATUS      current
    DESCRIPTION   "Firmware Package Revision Number"
    ::=  { inventoryEntry 2 }

inventoryHardwareRev OBJECT-TYPE
    SYNTAX      SnmpAdminString
    MAX-ACCESS  read-only
    STATUS      current
    DESCRIPTION
        "Equipment Revision Number"
    ::=  { inventoryEntry 3 }

inventorySoftwareRev OBJECT-TYPE
    SYNTAX      SnmpAdminString
    MAX-ACCESS  read-only
    STATUS      current
    DESCRIPTION   "The active Application software version on the unit/module."
    ::=  { inventoryEntry 4 }

inventoryFpgaRev OBJECT-TYPE
    SYNTAX      SnmpAdminString
    MAX-ACCESS  read-only
    STATUS      current
    DESCRIPTION   "The active FPGA version on the unit/module."
    ::=  { inventoryEntry 5 }

inventorySerialNum OBJECT-TYPE
    SYNTAX      SnmpAdminString
    MAX-ACCESS  read-only
    STATUS      current
    DESCRIPTION
        "Equipment Serial Number"
    ::=  { inventoryEntry 6 }

inventoryPartnumber OBJECT-TYPE
    SYNTAX      SnmpAdminString
    MAX-ACCESS  read-only
    STATUS      current
    DESCRIPTION   "ADVA Part Number"
    ::=  { inventoryEntry 7 }

inventoryCleiCode OBJECT-TYPE
    SYNTAX      SnmpAdminString
    MAX-ACCESS  read-only
    STATUS      current
    DESCRIPTION
        "Common Language Equipment Identifier"
    ::=  { inventoryEntry 8 }

inventoryVendorId OBJECT-TYPE
    SYNTAX      SnmpAdminString
    MAX-ACCESS  read-only
    STATUS      current
    DESCRIPTION
        "OEM Vendor Code"
    ::=  { inventoryEntry 9 }

inventoryType OBJECT-TYPE
    SYNTAX      EntityType
    MAX-ACCESS  read-only
    STATUS      current
    DESCRIPTION   "Type of a physical entity: shelf/module/plug"
    ::=  { inventoryEntry 10 }

inventoryUniversalSerialIdent OBJECT-TYPE
    SYNTAX      SnmpAdminString
    MAX-ACCESS  read-only
    STATUS      current
    DESCRIPTION
        "Unique Serial Identifier"
    ::=  { inventoryEntry 11 }

inventoryMacAddress OBJECT-TYPE
    SYNTAX      MacAddress
    MAX-ACCESS  read-only
    STATUS      current
    DESCRIPTION
        "Ethernet MAC address"
    ::=  { inventoryEntry 12 }

inventoryGradeInventory OBJECT-TYPE
    SYNTAX      Grade
    MAX-ACCESS  read-only
    STATUS      current
    DESCRIPTION
        "Used to distinguish between NCU capabilities (range of supported services or applications)"
    ::=  { inventoryEntry 13 }

entityTable OBJECT-TYPE
    SYNTAX      SEQUENCE OF EntityEntry
    MAX-ACCESS  not-accessible
    STATUS      current
    DESCRIPTION   "Table for all existing addresses. Entities in this table are either
         provisioned, equipped, both of these or neither of these. Containers
         are always present in the table as long as their supporting entity
         is provisioned or equipped."
    ::=  { inventoryMib 2 }

entityEntry OBJECT-TYPE
    SYNTAX      EntityEntry
    MAX-ACCESS  not-accessible
    STATUS      current
    DESCRIPTION   "Entry for all existing addresses."
    INDEX       {
                  entityIndex
                }
    ::=  { entityTable 1 }

EntityEntry ::=  SEQUENCE
  { entityIndex EntityIndex,
    entityContainedIn EntityIndex,
    entityClass EntityClass,
    entityClassInstanceNumber Integer32,
    entityIndexAid SnmpAdminString,
    entityType EntityType,
    entityAssignmentState AssignmentState,
    entityEquipmentState EquipmentState }

entityIndex OBJECT-TYPE
    SYNTAX      EntityIndex
    MAX-ACCESS  accessible-for-notify
    STATUS      current
    DESCRIPTION   "Existing adress index"
    ::=  { entityEntry 1 }

entityContainedIn OBJECT-TYPE
    SYNTAX      EntityIndex
    MAX-ACCESS  read-only
    STATUS      current
    DESCRIPTION
        "Contained in"
    ::=  { entityEntry 2 }

entityClass OBJECT-TYPE
    SYNTAX      EntityClass
    MAX-ACCESS  read-only
    STATUS      current
    DESCRIPTION   "See EntityClass"
    ::=  { entityEntry 3 }

entityClassInstanceNumber OBJECT-TYPE
    SYNTAX      Integer32 (1..2000 | -2147483648)
    MAX-ACCESS  read-only
    STATUS      current
    DESCRIPTION
        "The class instance number of this entity within the module(card)"
    ::=  { entityEntry 4 }

entityIndexAid OBJECT-TYPE
    SYNTAX      SnmpAdminString
    MAX-ACCESS  read-only
    STATUS      current
    DESCRIPTION
        "Name"
    ::=  { entityEntry 5 }

entityType OBJECT-TYPE
    SYNTAX      EntityType
    MAX-ACCESS  read-only
    STATUS      current
    DESCRIPTION   "The type of FspR7 entity. Please refer to EntityType for further deails."
    ::=  { entityEntry 6 }

entityAssignmentState OBJECT-TYPE
    SYNTAX      AssignmentState
    MAX-ACCESS  read-only
    STATUS      current
    DESCRIPTION   "See AssignmentState."
    ::=  { entityEntry 7 }

entityEquipmentState OBJECT-TYPE
    SYNTAX      EquipmentState
    MAX-ACCESS  read-only
    STATUS      current
    DESCRIPTION   "See EquipmentState."
    ::=  { entityEntry 8 }

containsTable OBJECT-TYPE
    SYNTAX      SEQUENCE OF ContainsEntry
    MAX-ACCESS  not-accessible
    STATUS      current
    DESCRIPTION   "Table for all existing addresses. Gives the index of the subtending
         entity in the containment."
    ::=  { inventoryMib 3 }

containsEntry OBJECT-TYPE
    SYNTAX      ContainsEntry
    MAX-ACCESS  not-accessible
    STATUS      current
    DESCRIPTION   ""
    INDEX       {
                  entityIndex,
                  containsIndex
                }
    ::=  { containsTable 1 }

ContainsEntry ::=  SEQUENCE
  { containsIndex EntityIndex }

containsIndex OBJECT-TYPE
    SYNTAX      EntityIndex
    MAX-ACCESS  read-only
    STATUS      current
    DESCRIPTION
        ""
    ::=  { containsEntry 1 }

controlPlaneWdmEntityTable OBJECT-TYPE
    SYNTAX      SEQUENCE OF ControlPlaneWdmEntityEntry
    MAX-ACCESS  not-accessible
    STATUS      current
    DESCRIPTION   "Table for all existing addresses. Entities in this table are either
         provisioned, equipped, both of these or neither of these. Containers
         are always present in the table as long as their supporting entity
         is provisioned or equipped."
    ::=  { inventoryMib 4 }

controlPlaneWdmEntityEntry OBJECT-TYPE
    SYNTAX      ControlPlaneWdmEntityEntry
    MAX-ACCESS  not-accessible
    STATUS      current
    DESCRIPTION   "Entry for all existing addresses."
    INDEX       {
                  controlPlaneWdmEntityIndex
                }
    ::=  { controlPlaneWdmEntityTable 1 }

ControlPlaneWdmEntityEntry ::=  SEQUENCE
  { controlPlaneWdmEntityIndex EntityIndex,
    controlPlaneWdmEntityContainedIn EntityIndex,
    controlPlaneWdmEntityClass CpWdmEntityClass,
    controlPlaneWdmEntityClassInstanceNumber Integer32,
    controlPlaneWdmEntityIndexAid SnmpAdminString,
    controlPlaneWdmEntityAssignmentState AssignmentState }

controlPlaneWdmEntityIndex OBJECT-TYPE
    SYNTAX      EntityIndex
    MAX-ACCESS  accessible-for-notify
    STATUS      current
    DESCRIPTION   "Existing adress index"
    ::=  { controlPlaneWdmEntityEntry 1 }

controlPlaneWdmEntityContainedIn OBJECT-TYPE
    SYNTAX      EntityIndex
    MAX-ACCESS  read-only
    STATUS      current
    DESCRIPTION
        "Contained in"
    ::=  { controlPlaneWdmEntityEntry 2 }

controlPlaneWdmEntityClass OBJECT-TYPE
    SYNTAX      CpWdmEntityClass
    MAX-ACCESS  read-only
    STATUS      current
    DESCRIPTION   "See EntityClass"
    ::=  { controlPlaneWdmEntityEntry 3 }

controlPlaneWdmEntityClassInstanceNumber OBJECT-TYPE
    SYNTAX      Integer32 (1..2000 | -2147483648)
    MAX-ACCESS  read-only
    STATUS      current
    DESCRIPTION
        "The class instance number of this entity within the module(card)"
    ::=  { controlPlaneWdmEntityEntry 4 }

controlPlaneWdmEntityIndexAid OBJECT-TYPE
    SYNTAX      SnmpAdminString
    MAX-ACCESS  read-only
    STATUS      current
    DESCRIPTION
        "Name"
    ::=  { controlPlaneWdmEntityEntry 5 }

controlPlaneWdmEntityAssignmentState OBJECT-TYPE
    SYNTAX      AssignmentState
    MAX-ACCESS  read-only
    STATUS      current
    DESCRIPTION   "See AssignmentState."
    ::=  { controlPlaneWdmEntityEntry 6 }

controlPlaneWdmContainsTable OBJECT-TYPE
    SYNTAX      SEQUENCE OF ControlPlaneWdmContainsEntry
    MAX-ACCESS  not-accessible
    STATUS      current
    DESCRIPTION   "Table for all existing addresses. Gives the index of the subtending
         entity in the containment."
    ::=  { inventoryMib 5 }

controlPlaneWdmContainsEntry OBJECT-TYPE
    SYNTAX      ControlPlaneWdmContainsEntry
    MAX-ACCESS  not-accessible
    STATUS      current
    DESCRIPTION   ""
    INDEX       {
                  controlPlaneWdmEntityIndex,
                  controlPlaneWdmContainsIndex
                }
    ::=  { controlPlaneWdmContainsTable 1 }

ControlPlaneWdmContainsEntry ::=  SEQUENCE
  { controlPlaneWdmContainsIndex EntityIndex }

controlPlaneWdmContainsIndex OBJECT-TYPE
    SYNTAX      EntityIndex
    MAX-ACCESS  read-only
    STATUS      current
    DESCRIPTION
        ""
    ::=  { controlPlaneWdmContainsEntry 1 }

controlPlaneEthEntityTable OBJECT-TYPE
    SYNTAX      SEQUENCE OF ControlPlaneEthEntityEntry
    MAX-ACCESS  not-accessible
    STATUS      current
    DESCRIPTION   "Table for all existing addresses. Entities in this table are either
         provisioned, equipped, both of these or neither of these. Containers
         are always present in the table as long as their supporting entity
         is provisioned or equipped."
    ::=  { inventoryMib 6 }

controlPlaneEthEntityEntry OBJECT-TYPE
    SYNTAX      ControlPlaneEthEntityEntry
    MAX-ACCESS  not-accessible
    STATUS      current
    DESCRIPTION   "Entry for all existing addresses."
    INDEX       {
                  controlPlaneEthEntityIndex
                }
    ::=  { controlPlaneEthEntityTable 1 }

ControlPlaneEthEntityEntry ::=  SEQUENCE
  { controlPlaneEthEntityIndex EntityIndex,
    controlPlaneEthEntityContainedIn EntityIndex,
    controlPlaneEthEntityClass CpWdmEntityClass,
    controlPlaneEthEntityClassInstanceNumber Integer32,
    controlPlaneEthEntityIndexAid SnmpAdminString,
    controlPlaneEthEntityAssignmentState AssignmentState }

controlPlaneEthEntityIndex OBJECT-TYPE
    SYNTAX      EntityIndex
    MAX-ACCESS  accessible-for-notify
    STATUS      current
    DESCRIPTION   "Existing adress index"
    ::=  { controlPlaneEthEntityEntry 1 }

controlPlaneEthEntityContainedIn OBJECT-TYPE
    SYNTAX      EntityIndex
    MAX-ACCESS  read-only
    STATUS      current
    DESCRIPTION
        "Contained in"
    ::=  { controlPlaneEthEntityEntry 2 }

controlPlaneEthEntityClass OBJECT-TYPE
    SYNTAX      CpWdmEntityClass
    MAX-ACCESS  read-only
    STATUS      current
    DESCRIPTION   "See EntityClass"
    ::=  { controlPlaneEthEntityEntry 3 }

controlPlaneEthEntityClassInstanceNumber OBJECT-TYPE
    SYNTAX      Integer32 (1..2000 | -2147483648)
    MAX-ACCESS  read-only
    STATUS      current
    DESCRIPTION
        "The class instance number of this entity within the module(card)"
    ::=  { controlPlaneEthEntityEntry 4 }

controlPlaneEthEntityIndexAid OBJECT-TYPE
    SYNTAX      SnmpAdminString
    MAX-ACCESS  read-only
    STATUS      current
    DESCRIPTION
        "Name"
    ::=  { controlPlaneEthEntityEntry 5 }

controlPlaneEthEntityAssignmentState OBJECT-TYPE
    SYNTAX      AssignmentState
    MAX-ACCESS  read-only
    STATUS      current
    DESCRIPTION   "See AssignmentState."
    ::=  { controlPlaneEthEntityEntry 6 }

controlPlaneEthContainsTable OBJECT-TYPE
    SYNTAX      SEQUENCE OF ControlPlaneEthContainsEntry
    MAX-ACCESS  not-accessible
    STATUS      current
    DESCRIPTION   "Table for all existing addresses. Gives the index of the subtending
         entity in the containment."
    ::=  { inventoryMib 7 }

controlPlaneEthContainsEntry OBJECT-TYPE
    SYNTAX      ControlPlaneEthContainsEntry
    MAX-ACCESS  not-accessible
    STATUS      current
    DESCRIPTION   ""
    INDEX       {
                  controlPlaneEthEntityIndex,
                  controlPlaneEthContainsIndex
                }
    ::=  { controlPlaneEthContainsTable 1 }

ControlPlaneEthContainsEntry ::=  SEQUENCE
  { controlPlaneEthContainsIndex EntityIndex }

controlPlaneEthContainsIndex OBJECT-TYPE
    SYNTAX      EntityIndex
    MAX-ACCESS  read-only
    STATUS      current
    DESCRIPTION
        ""
    ::=  { controlPlaneEthContainsEntry 1 }

ptpEntityTable OBJECT-TYPE
    SYNTAX      SEQUENCE OF PtpEntityEntry
    MAX-ACCESS  not-accessible
    STATUS      current
    DESCRIPTION   "Table for PTP existing addresses. Entities in this table are either
         provisioned, equipped, both of these or neither of these. Containers
         are always present in the table as long as their supporting entity
         is provisioned or equipped."
    ::=  { inventoryMib 10 }

ptpEntityEntry OBJECT-TYPE
    SYNTAX      PtpEntityEntry
    MAX-ACCESS  not-accessible
    STATUS      current
    DESCRIPTION   ""
    INDEX       {
                  ptpEntityIndex
                }
    ::=  { ptpEntityTable 1 }

PtpEntityEntry ::=  SEQUENCE
  { ptpEntityIndex EntityIndex,
    ptpEntityContainedIn EntityIndex,
    ptpEntityClass EntityClass,
    ptpEntityClassInstanceNumber Integer32,
    ptpEntityIndexAid SnmpAdminString,
    ptpEntityType EntityType,
    ptpEntityAssignmentState AssignmentState,
    ptpEntityEquipmentState EquipmentState,
    ptpEntityReferencedTo EntityIndex }

ptpEntityIndex OBJECT-TYPE
    SYNTAX      EntityIndex
    MAX-ACCESS  accessible-for-notify
    STATUS      current
    DESCRIPTION   "Existing adress index"
    ::=  { ptpEntityEntry 1 }

ptpEntityContainedIn OBJECT-TYPE
    SYNTAX      EntityIndex
    MAX-ACCESS  read-only
    STATUS      current
    DESCRIPTION
        "Contained in"
    ::=  { ptpEntityEntry 2 }

ptpEntityClass OBJECT-TYPE
    SYNTAX      EntityClass
    MAX-ACCESS  read-only
    STATUS      current
    DESCRIPTION   "See EntityClass"
    ::=  { ptpEntityEntry 3 }

ptpEntityClassInstanceNumber OBJECT-TYPE
    SYNTAX      Integer32 (1..2000 | -2147483648)
    MAX-ACCESS  read-only
    STATUS      current
    DESCRIPTION
        "The class instance number of this entity within the module(card)"
    ::=  { ptpEntityEntry 4 }

ptpEntityIndexAid OBJECT-TYPE
    SYNTAX      SnmpAdminString
    MAX-ACCESS  read-only
    STATUS      current
    DESCRIPTION
        "Name"
    ::=  { ptpEntityEntry 5 }

ptpEntityType OBJECT-TYPE
    SYNTAX      EntityType
    MAX-ACCESS  read-only
    STATUS      current
    DESCRIPTION   "The type of FspR7 entity. Please refer to EntityType for further deails."
    ::=  { ptpEntityEntry 6 }

ptpEntityAssignmentState OBJECT-TYPE
    SYNTAX      AssignmentState
    MAX-ACCESS  read-only
    STATUS      current
    DESCRIPTION   "See AssignmentState."
    ::=  { ptpEntityEntry 7 }

ptpEntityEquipmentState OBJECT-TYPE
    SYNTAX      EquipmentState
    MAX-ACCESS  read-only
    STATUS      current
    DESCRIPTION   "See EquipmentState."
    ::=  { ptpEntityEntry 8 }

ptpEntityReferencedTo OBJECT-TYPE
    SYNTAX      EntityIndex
    MAX-ACCESS  read-only
    STATUS      current
    DESCRIPTION   ""
    ::=  { ptpEntityEntry 9 }

vtpEntityTable OBJECT-TYPE
    SYNTAX      SEQUENCE OF VtpEntityEntry
    MAX-ACCESS  not-accessible
    STATUS      current
    DESCRIPTION   "Table for VTP existing addresses. Entities in this table are either
         provisioned, equipped, both of these or neither of these. Containers
         are always present in the table as long as their supporting entity
         is provisioned or equipped."
    ::=  { inventoryMib 11 }

vtpEntityEntry OBJECT-TYPE
    SYNTAX      VtpEntityEntry
    MAX-ACCESS  not-accessible
    STATUS      current
    DESCRIPTION   ""
    INDEX       {
                  vtpEntityIndex
                }
    ::=  { vtpEntityTable 1 }

VtpEntityEntry ::=  SEQUENCE
  { vtpEntityIndex EntityIndex,
    vtpEntityContainedIn EntityIndex,
    vtpEntityClass EntityClass,
    vtpEntityClassInstanceNumber Integer32,
    vtpEntityIndexAid SnmpAdminString,
    vtpEntityType EntityType,
    vtpEntityAssignmentState AssignmentState,
    vtpEntityEquipmentState EquipmentState,
    vtpEntityReferencedTo EntityIndex }

vtpEntityIndex OBJECT-TYPE
    SYNTAX      EntityIndex
    MAX-ACCESS  accessible-for-notify
    STATUS      current
    DESCRIPTION   "Existing adress index"
    ::=  { vtpEntityEntry 1 }

vtpEntityContainedIn OBJECT-TYPE
    SYNTAX      EntityIndex
    MAX-ACCESS  read-only
    STATUS      current
    DESCRIPTION
        "Contained in"
    ::=  { vtpEntityEntry 2 }

vtpEntityClass OBJECT-TYPE
    SYNTAX      EntityClass
    MAX-ACCESS  read-only
    STATUS      current
    DESCRIPTION   "See EntityClass"
    ::=  { vtpEntityEntry 3 }

vtpEntityClassInstanceNumber OBJECT-TYPE
    SYNTAX      Integer32 (1..2000 | -2147483648)
    MAX-ACCESS  read-only
    STATUS      current
    DESCRIPTION
        "The class instance number of this entity within the module(card)"
    ::=  { vtpEntityEntry 4 }

vtpEntityIndexAid OBJECT-TYPE
    SYNTAX      SnmpAdminString
    MAX-ACCESS  read-only
    STATUS      current
    DESCRIPTION
        "Name"
    ::=  { vtpEntityEntry 5 }

vtpEntityType OBJECT-TYPE
    SYNTAX      EntityType
    MAX-ACCESS  read-only
    STATUS      current
    DESCRIPTION   "The type of FspR7 entity. Please refer to EntityType for further deails."
    ::=  { vtpEntityEntry 6 }

vtpEntityAssignmentState OBJECT-TYPE
    SYNTAX      AssignmentState
    MAX-ACCESS  read-only
    STATUS      current
    DESCRIPTION   "See AssignmentState."
    ::=  { vtpEntityEntry 7 }

vtpEntityEquipmentState OBJECT-TYPE
    SYNTAX      EquipmentState
    MAX-ACCESS  read-only
    STATUS      current
    DESCRIPTION   "See EquipmentState."
    ::=  { vtpEntityEntry 8 }

vtpEntityReferencedTo OBJECT-TYPE
    SYNTAX      EntityIndex
    MAX-ACCESS  read-only
    STATUS      current
    DESCRIPTION   ""
    ::=  { vtpEntityEntry 9 }

controlPlaneOtnEntityTable OBJECT-TYPE
    SYNTAX      SEQUENCE OF ControlPlaneOtnEntityEntry
    MAX-ACCESS  not-accessible
    STATUS      current
    DESCRIPTION   "Table for all existing addresses. Entities in this table are either
         provisioned, equipped, both of these or neither of these. Containers
         are always present in the table as long as their supporting entity
         is provisioned or equipped."
    ::=  { inventoryMib 12 }

controlPlaneOtnEntityEntry OBJECT-TYPE
    SYNTAX      ControlPlaneOtnEntityEntry
    MAX-ACCESS  not-accessible
    STATUS      current
    DESCRIPTION   "Entry for all existing addresses."
    INDEX       {
                  controlPlaneOtnEntityIndex
                }
    ::=  { controlPlaneOtnEntityTable 1 }

ControlPlaneOtnEntityEntry ::=  SEQUENCE
  { controlPlaneOtnEntityIndex EntityIndex,
    controlPlaneOtnEntityContainedIn EntityIndex,
    controlPlaneOtnEntityClass CpWdmEntityClass,
    controlPlaneOtnEntityClassInstanceNumber Integer32,
    controlPlaneOtnEntityIndexAid SnmpAdminString,
    controlPlaneOtnEntityAssignmentState AssignmentState }

controlPlaneOtnEntityIndex OBJECT-TYPE
    SYNTAX      EntityIndex
    MAX-ACCESS  accessible-for-notify
    STATUS      current
    DESCRIPTION   "Existing adress index"
    ::=  { controlPlaneOtnEntityEntry 1 }

controlPlaneOtnEntityContainedIn OBJECT-TYPE
    SYNTAX      EntityIndex
    MAX-ACCESS  read-only
    STATUS      current
    DESCRIPTION
        "Contained in"
    ::=  { controlPlaneOtnEntityEntry 2 }

controlPlaneOtnEntityClass OBJECT-TYPE
    SYNTAX      CpWdmEntityClass
    MAX-ACCESS  read-only
    STATUS      current
    DESCRIPTION   "See EntityClass"
    ::=  { controlPlaneOtnEntityEntry 3 }

controlPlaneOtnEntityClassInstanceNumber OBJECT-TYPE
    SYNTAX      Integer32 (1..2000 | -2147483648)
    MAX-ACCESS  read-only
    STATUS      current
    DESCRIPTION
        "The class instance number of this entity within the module(card)"
    ::=  { controlPlaneOtnEntityEntry 4 }

controlPlaneOtnEntityIndexAid OBJECT-TYPE
    SYNTAX      SnmpAdminString
    MAX-ACCESS  read-only
    STATUS      current
    DESCRIPTION
        "Name"
    ::=  { controlPlaneOtnEntityEntry 5 }

controlPlaneOtnEntityAssignmentState OBJECT-TYPE
    SYNTAX      AssignmentState
    MAX-ACCESS  read-only
    STATUS      current
    DESCRIPTION   "See AssignmentState."
    ::=  { controlPlaneOtnEntityEntry 6 }

controlPlaneOtnContainsTable OBJECT-TYPE
    SYNTAX      SEQUENCE OF ControlPlaneOtnContainsEntry
    MAX-ACCESS  not-accessible
    STATUS      current
    DESCRIPTION   "Table for all existing addresses. Gives the index of the subtending
         entity in the containment."
    ::=  { inventoryMib 13 }

controlPlaneOtnContainsEntry OBJECT-TYPE
    SYNTAX      ControlPlaneOtnContainsEntry
    MAX-ACCESS  not-accessible
    STATUS      current
    DESCRIPTION   ""
    INDEX       {
                  controlPlaneOtnEntityIndex,
                  controlPlaneOtnContainsIndex
                }
    ::=  { controlPlaneOtnContainsTable 1 }

ControlPlaneOtnContainsEntry ::=  SEQUENCE
  { controlPlaneOtnContainsIndex EntityIndex }

controlPlaneOtnContainsIndex OBJECT-TYPE
    SYNTAX      EntityIndex
    MAX-ACCESS  read-only
    STATUS      current
    DESCRIPTION
        ""
    ::=  { controlPlaneOtnContainsEntry 1 }

sonetSectionConfigTable OBJECT-TYPE
    SYNTAX      SEQUENCE OF SonetSectionConfigEntry
    MAX-ACCESS  not-accessible
    STATUS      current
    DESCRIPTION   "Contains entries for the configuration of SONET interfaces. In the naming of
         parameters, only sonet (and not sdh) is used for simplification.
         This table extends the entries in
         the ifTable (RFC 2863)."
    ::=  { sonetConfig 1 }

sonetSectionConfigEntry OBJECT-TYPE
    SYNTAX      SonetSectionConfigEntry
    MAX-ACCESS  not-accessible
    STATUS      current
    DESCRIPTION   "SDH/SONET interfaces will have an entry
         in this table."
    INDEX       {
                  entityIndex
                }
    ::=  { sonetSectionConfigTable 1 }

SonetSectionConfigEntry ::=  SEQUENCE
  { sonetSectionConfigTimingSource SonetTimingSource,
    sonetSectionConfigSignalDegradeThreshhold Unsigned32,
    sonetSectionConfigSignalDegradePeriod Unsigned32,
    sonetSectionConfigTraceForm SonetTraceForm,
    sonetSectionConfigTraceExpected OCTET STRING,
    sonetSectionConfigTraceTransmit OCTET STRING,
    sonetSectionConfigTimMode TimMode }

sonetSectionConfigTimingSource OBJECT-TYPE
    SYNTAX      SonetTimingSource
    MAX-ACCESS  read-write
    STATUS      current
    DESCRIPTION   "The SDH/SONET timing source for this interface.
         - internal: used in stand-alone, point-to-point topologies
         stand-alone (dedicated fiber operation)
         - loopTiming: used in point-to-point via SDH network and
         feeder topologies. The default is internal(1)."
    ::=  { sonetSectionConfigEntry 1 }

sonetSectionConfigSignalDegradeThreshhold OBJECT-TYPE
    SYNTAX      Unsigned32 (1..100 | 4294967295)
    UNITS       "%"
    MAX-ACCESS  read-write
    STATUS      current
    DESCRIPTION   "Block-Error-Based Degradation Definition for SDH (standard integration period).
         Defined as percentage Background Block Errors (30% default) evaluated
         over a defined period (SDPER-RS)."
    ::=  { sonetSectionConfigEntry 2 }

sonetSectionConfigSignalDegradePeriod OBJECT-TYPE
    SYNTAX      Unsigned32 (2..10 | 4294967295)
    UNITS       "s"
    MAX-ACCESS  read-write
    STATUS      current
    DESCRIPTION   "The measurement period in seconds used together with
         the sonetSectionConfigSignalDegradeThreshold based on the
         block error counting method.
         The valid range is 2..10, The default being 7."
    ::=  { sonetSectionConfigEntry 3 }

sonetSectionConfigTraceForm OBJECT-TYPE
    SYNTAX      SonetTraceForm
    MAX-ACCESS  read-write
    STATUS      current
    DESCRIPTION
        "Byte-Length of Trace Compared to Expected"
    ::=  { sonetSectionConfigEntry 4 }

sonetSectionConfigTraceExpected OBJECT-TYPE
    SYNTAX      OCTET STRING (SIZE(0..62))
    MAX-ACCESS  read-write
    STATUS      current
    DESCRIPTION
        "Expected Sec/RS trace. NULL TRACE implies that no trace comparison is made."
    ::=  { sonetSectionConfigEntry 5 }

sonetSectionConfigTraceTransmit OBJECT-TYPE
    SYNTAX      OCTET STRING (SIZE(0..62))
    MAX-ACCESS  read-write
    STATUS      current
    DESCRIPTION
        "Sec/RS Trace to be Transmitted"
    ::=  { sonetSectionConfigEntry 6 }

sonetSectionConfigTimMode OBJECT-TYPE
    SYNTAX      TimMode
    MAX-ACCESS  read-write
    STATUS      current
    DESCRIPTION
        "Detection of TIM Sonet Section Condition can be configured"
    ::=  { sonetSectionConfigEntry 7 }

sonetSectionDataTable OBJECT-TYPE
    SYNTAX      SEQUENCE OF SonetSectionDataEntry
    MAX-ACCESS  not-accessible
    STATUS      current
    DESCRIPTION   "Contains entries for the status of SONET interfaces. In the naming of
         parameters, only sonet (and not sdh) is used for simplification.
         This table extends the entries in
         the ifTable (RFC 2863)."
    ::=  { sonetConfig 3 }

sonetSectionDataEntry OBJECT-TYPE
    SYNTAX      SonetSectionDataEntry
    MAX-ACCESS  not-accessible
    STATUS      current
    DESCRIPTION   "SDH/SONET interfaces will have an entry
         in this table."
    INDEX       {
                  entityIndex
                }
    ::=  { sonetSectionDataTable 1 }

SonetSectionDataEntry ::=  SEQUENCE
  { sonetSectionDataTraceReceived OCTET STRING }

sonetSectionDataTraceReceived OBJECT-TYPE
    SYNTAX      OCTET STRING (SIZE(0..62))
    MAX-ACCESS  read-only
    STATUS      current
    DESCRIPTION
        "The received Sec/RS Trace"
    ::=  { sonetSectionDataEntry 1 }

otuSectionConfigTable OBJECT-TYPE
    SYNTAX      SEQUENCE OF OtuSectionConfigEntry
    MAX-ACCESS  not-accessible
    STATUS      current
    DESCRIPTION   "Contains entries for the configuration of OTU interfaces.
         This table extends the entries in
         the ifTable (RFC 2863)."
    ::=  { otuConfig 1 }

otuSectionConfigEntry OBJECT-TYPE
    SYNTAX      OtuSectionConfigEntry
    MAX-ACCESS  not-accessible
    STATUS      current
    DESCRIPTION   "OTU interfaces will have an entry
         in this table."
    INDEX       {
                  entityIndex
                }
    ::=  { otuSectionConfigTable 1 }

OtuSectionConfigEntry ::=  SEQUENCE
  { otuSectionConfigSignalDegradeThreshold Integer32,
    otuSectionConfigSignalDegradePeriod Unsigned32,
    otuSectionConfigPayload OtnPayloadType,
    otuSectionConfigStuffing EnableState,
    otuSectionConfigTraceExpected OCTET STRING,
    otuSectionConfigTraceTransmitSapi OCTET STRING,
    otuSectionConfigTraceTransmitDapi OCTET STRING,
    otuSectionConfigTraceTransmitOpsp OCTET STRING,
    otuSectionConfigTimMode TimMode }

otuSectionConfigSignalDegradeThreshold OBJECT-TYPE
    SYNTAX      Integer32 (1..100 | -2147483648)
    UNITS       "%"
    MAX-ACCESS  read-write
    STATUS      current
    DESCRIPTION   "Threshold for OTU SM-SD alarm (threshold level 0..100%, default value 15 %).
         Ref. table 24/G.7710."
    ::=  { otuSectionConfigEntry 1 }

otuSectionConfigSignalDegradePeriod OBJECT-TYPE
    SYNTAX      Unsigned32 (2..10 | 4294967295)
    UNITS       "s"
    MAX-ACCESS  read-write
    STATUS      current
    DESCRIPTION   "Measuring period for OTU SM-SD alarm: 2..10 sec) (bursty)
         Ref. table 24/G.7710. Default value: 7.
        "
    ::=  { otuSectionConfigEntry 2 }

otuSectionConfigPayload OBJECT-TYPE
    SYNTAX      OtnPayloadType
    MAX-ACCESS  read-write
    STATUS      current
    DESCRIPTION   "The payload of the interface (inside a transport overhead).
         Relevant e. g. for OTN cards which wrap a payload into an OTU1/2 wrapper."
    ::=  { otuSectionConfigEntry 3 }

otuSectionConfigStuffing OBJECT-TYPE
    SYNTAX      EnableState
    MAX-ACCESS  read-write
    STATUS      current
    DESCRIPTION
        "Indicates if bit/byte stuffing is used in the transport signal."
    ::=  { otuSectionConfigEntry 4 }

otuSectionConfigTraceExpected OBJECT-TYPE
    SYNTAX      OCTET STRING (SIZE(0..15))
    MAX-ACCESS  read-write
    STATUS      current
    DESCRIPTION
        "Expected SAPI part of the OTU trace (15 character). NULL TRACE implies that no trace comparison is made."
    ::=  { otuSectionConfigEntry 5 }

otuSectionConfigTraceTransmitSapi OBJECT-TYPE
    SYNTAX      OCTET STRING (SIZE(0..15))
    MAX-ACCESS  read-write
    STATUS      current
    DESCRIPTION
        "The transmitted SAPI part of the OTU trace (15 character)"
    ::=  { otuSectionConfigEntry 6 }

otuSectionConfigTraceTransmitDapi OBJECT-TYPE
    SYNTAX      OCTET STRING (SIZE(0..15))
    MAX-ACCESS  read-write
    STATUS      current
    DESCRIPTION
        "The transmitted DAPI part of the OTU trace (15 character)"
    ::=  { otuSectionConfigEntry 7 }

otuSectionConfigTraceTransmitOpsp OBJECT-TYPE
    SYNTAX      OCTET STRING (SIZE(0..32))
    MAX-ACCESS  read-write
    STATUS      current
    DESCRIPTION
        "The transmitted Operator Specific part of the OTU trace (32 character)"
    ::=  { otuSectionConfigEntry 8 }

otuSectionConfigTimMode OBJECT-TYPE
    SYNTAX      TimMode
    MAX-ACCESS  read-write
    STATUS      current
    DESCRIPTION
        "Detection of TIM-OTU Condition can be configured"
    ::=  { otuSectionConfigEntry 9 }

otuSectionDataTable OBJECT-TYPE
    SYNTAX      SEQUENCE OF OtuSectionDataEntry
    MAX-ACCESS  not-accessible
    STATUS      current
    DESCRIPTION   "Contains entries for the status of OTU interfaces.
         This table extends the entries in
         the ifTable (RFC 2863)."
    ::=  { otuConfig 2 }

otuSectionDataEntry OBJECT-TYPE
    SYNTAX      OtuSectionDataEntry
    MAX-ACCESS  not-accessible
    STATUS      current
    DESCRIPTION   "OTU interfaces will have an entry
         in this table."
    INDEX       {
                  entityIndex
                }
    ::=  { otuSectionDataTable 1 }

OtuSectionDataEntry ::=  SEQUENCE
  { otuSectionDataResultingTotalBitrate Unsigned32,
    otuSectionDataTraceReceivedSapi OCTET STRING,
    otuSectionDataTraceReceivedDapi OCTET STRING,
    otuSectionDataTraceReceivedOpsp OCTET STRING }

otuSectionDataResultingTotalBitrate OBJECT-TYPE
    SYNTAX      Unsigned32
    UNITS       "Mbps"
    MAX-ACCESS  read-only
    STATUS      current
    DESCRIPTION   "This interface bitrate is dependent on the type and the payload of the interface.
         Relevant e. g. for OTN cards which wrap a payload into an OTU1/2 wrapper."
    ::=  { otuSectionDataEntry 1 }

otuSectionDataTraceReceivedSapi OBJECT-TYPE
    SYNTAX      OCTET STRING (SIZE(0..15))
    MAX-ACCESS  read-only
    STATUS      current
    DESCRIPTION
        "The received SAPI part of the OTU trace (15 character)"
    ::=  { otuSectionDataEntry 2 }

otuSectionDataTraceReceivedDapi OBJECT-TYPE
    SYNTAX      OCTET STRING (SIZE(0..15))
    MAX-ACCESS  read-only
    STATUS      current
    DESCRIPTION
        "The received DAPI part of the OTU trace (15 character)"
    ::=  { otuSectionDataEntry 3 }

otuSectionDataTraceReceivedOpsp OBJECT-TYPE
    SYNTAX      OCTET STRING (SIZE(0..32))
    MAX-ACCESS  read-only
    STATUS      current
    DESCRIPTION
        "The received Operator Specific part of the OTU trace (32 character)"
    ::=  { otuSectionDataEntry 4 }

oduSectionConfigTable OBJECT-TYPE
    SYNTAX      SEQUENCE OF OduSectionConfigEntry
    MAX-ACCESS  not-accessible
    STATUS      current
    DESCRIPTION   "Contains entries for the configuration of ODU interfaces.
         This table extends the entries in
         the ifTable (RFC 2863)."
    ::=  { oduConfig 1 }

oduSectionConfigEntry OBJECT-TYPE
    SYNTAX      OduSectionConfigEntry
    MAX-ACCESS  not-accessible
    STATUS      current
    DESCRIPTION   "ODU interfaces will have an entry
         in this table."
    INDEX       {
                  entityIndex
                }
    ::=  { oduSectionConfigTable 1 }

OduSectionConfigEntry ::=  SEQUENCE
  { oduSectionConfigSignalDegradeThres Integer32,
    oduSectionConfigSignalDegradePeriod Unsigned32,
    oduSectionConfigTraceExpected OCTET STRING,
    oduSectionConfigTraceTransmitSapi OCTET STRING,
    oduSectionConfigTraceTransmitDapi OCTET STRING,
    oduSectionConfigTraceTransmitOpsp OCTET STRING,
    oduSectionConfigTimMode TimMode }

oduSectionConfigSignalDegradeThres OBJECT-TYPE
    SYNTAX      Integer32 (1..100 | -2147483648)
    UNITS       "%"
    MAX-ACCESS  read-write
    STATUS      current
    DESCRIPTION   "Threshold for ODU SM-SD alarm (threshold level 0..100%,
         default value 15 %. Ref. table 24/G.7710."
    ::=  { oduSectionConfigEntry 1 }

oduSectionConfigSignalDegradePeriod OBJECT-TYPE
    SYNTAX      Unsigned32 (2..10 | 4294967295)
    UNITS       "s"
    MAX-ACCESS  read-write
    STATUS      current
    DESCRIPTION   "Measuring period for ODU SM-SD alarm: 2..10 sec) (bursty)
         Ref. table 24/G.7710. Default value: 7."
    ::=  { oduSectionConfigEntry 2 }

oduSectionConfigTraceExpected OBJECT-TYPE
    SYNTAX      OCTET STRING (SIZE(0..15))
    MAX-ACCESS  read-write
    STATUS      current
    DESCRIPTION
        "Expected SAPI part of the ODU trace (15 character). NULL TRACE implies that no trace comparison is made."
    ::=  { oduSectionConfigEntry 3 }

oduSectionConfigTraceTransmitSapi OBJECT-TYPE
    SYNTAX      OCTET STRING (SIZE(0..15))
    MAX-ACCESS  read-write
    STATUS      current
    DESCRIPTION
        "The transmitted SAPI part of the ODU trace (15 character)"
    ::=  { oduSectionConfigEntry 4 }

oduSectionConfigTraceTransmitDapi OBJECT-TYPE
    SYNTAX      OCTET STRING (SIZE(0..15))
    MAX-ACCESS  read-write
    STATUS      current
    DESCRIPTION
        "The transmitted DAPI part of the ODU trace (15 character)"
    ::=  { oduSectionConfigEntry 5 }

oduSectionConfigTraceTransmitOpsp OBJECT-TYPE
    SYNTAX      OCTET STRING (SIZE(0..32))
    MAX-ACCESS  read-write
    STATUS      current
    DESCRIPTION
        "The transmitted Operator Specific part of the ODU trace (32 character)"
    ::=  { oduSectionConfigEntry 6 }

oduSectionConfigTimMode OBJECT-TYPE
    SYNTAX      TimMode
    MAX-ACCESS  read-write
    STATUS      current
    DESCRIPTION
        "Detection of TIM-ODU Condition can be configured"
    ::=  { oduSectionConfigEntry 7 }

oduSectionDataTable OBJECT-TYPE
    SYNTAX      SEQUENCE OF OduSectionDataEntry
    MAX-ACCESS  not-accessible
    STATUS      current
    DESCRIPTION   "Contains entries for the status of ODU interfaces.
         This table extends the entries in
         the ifTable (RFC 2863)."
    ::=  { oduConfig 2 }

oduSectionDataEntry OBJECT-TYPE
    SYNTAX      OduSectionDataEntry
    MAX-ACCESS  not-accessible
    STATUS      current
    DESCRIPTION   "ODU interfaces will have an entry
         in this table."
    INDEX       {
                  entityIndex
                }
    ::=  { oduSectionDataTable 1 }

OduSectionDataEntry ::=  SEQUENCE
  { oduSectionDataTraceReceivedSapi OCTET STRING,
    oduSectionDataTraceReceivedDapi OCTET STRING,
    oduSectionDataTraceReceivedOpsp OCTET STRING }

oduSectionDataTraceReceivedSapi OBJECT-TYPE
    SYNTAX      OCTET STRING (SIZE(0..15))
    MAX-ACCESS  read-only
    STATUS      current
    DESCRIPTION
        "The received SAPI part of the ODU trace (15 character)"
    ::=  { oduSectionDataEntry 1 }

oduSectionDataTraceReceivedDapi OBJECT-TYPE
    SYNTAX      OCTET STRING (SIZE(0..15))
    MAX-ACCESS  read-only
    STATUS      current
    DESCRIPTION
        "The received DAPI part of the ODU trace (15 character)"
    ::=  { oduSectionDataEntry 2 }

oduSectionDataTraceReceivedOpsp OBJECT-TYPE
    SYNTAX      OCTET STRING (SIZE(0..32))
    MAX-ACCESS  read-only
    STATUS      current
    DESCRIPTION
        "The received Operator Specific part of the ODU trace (32 character)"
    ::=  { oduSectionDataEntry 3 }

oduTcmAConfigTable OBJECT-TYPE
    SYNTAX      SEQUENCE OF OduTcmAConfigEntry
    MAX-ACCESS  not-accessible
    STATUS      current
    DESCRIPTION   "Contains entries for the configuration of ODU interfaces.
         This table extends the entries in
         the ifTable (RFC 2863)."
    ::=  { oduConfig 3 }

oduTcmAConfigEntry OBJECT-TYPE
    SYNTAX      OduTcmAConfigEntry
    MAX-ACCESS  not-accessible
    STATUS      current
    DESCRIPTION   "ODU interfaces will have an entry in this table."
    INDEX       {
                  entityIndex
                }
    ::=  { oduTcmAConfigTable 1 }

OduTcmAConfigEntry ::=  SEQUENCE
  { oduTcmAConfigSignalDegradeThreshold Integer32,
    oduTcmAConfigSignalDegradePeriod Unsigned32,
    oduTcmAConfigTcmLevel OtnTcmLevel,
    oduTcmAConfigTraceExpected OCTET STRING,
    oduTcmAConfigTraceTransmitSapi OCTET STRING,
    oduTcmAConfigTraceTransmitDapi OCTET STRING,
    oduTcmAConfigTraceTransmitOpsp OCTET STRING,
    oduTcmAConfigTimMode TimMode }

oduTcmAConfigSignalDegradeThreshold OBJECT-TYPE
    SYNTAX      Integer32 (1..100 | -2147483648)
    UNITS       "%"
    MAX-ACCESS  read-write
    STATUS      current
    DESCRIPTION   "Threshold for ODU SM-SD alarm (threshold level 0..100%, default value 15 %).
         Ref. table 24/G.7710."
    ::=  { oduTcmAConfigEntry 1 }

oduTcmAConfigSignalDegradePeriod OBJECT-TYPE
    SYNTAX      Unsigned32 (2..10 | 4294967295)
    UNITS       "s"
    MAX-ACCESS  read-write
    STATUS      current
    DESCRIPTION   "Measuring period for ODU SM-SD alarm: 2..10 sec) (bursty)
         Ref. table 24/G.7710. Default value: 7."
    ::=  { oduTcmAConfigEntry 2 }

oduTcmAConfigTcmLevel OBJECT-TYPE
    SYNTAX      OtnTcmLevel
    MAX-ACCESS  read-write
    STATUS      current
    DESCRIPTION
        "Activation of Tandem Connection Monitoring Instance A"
    ::=  { oduTcmAConfigEntry 3 }

oduTcmAConfigTraceExpected OBJECT-TYPE
    SYNTAX      OCTET STRING (SIZE(0..15))
    MAX-ACCESS  read-write
    STATUS      current
    DESCRIPTION
        "Expected SAPI part of the TCMA trace (15 character). NULL TRACE-TCM implies that no trace comparison is made."
    ::=  { oduTcmAConfigEntry 4 }

oduTcmAConfigTraceTransmitSapi OBJECT-TYPE
    SYNTAX      OCTET STRING (SIZE(0..15))
    MAX-ACCESS  read-write
    STATUS      current
    DESCRIPTION
        "The transmitted SAPI part of the TCMA trace (15 character)"
    ::=  { oduTcmAConfigEntry 5 }

oduTcmAConfigTraceTransmitDapi OBJECT-TYPE
    SYNTAX      OCTET STRING (SIZE(0..15))
    MAX-ACCESS  read-write
    STATUS      current
    DESCRIPTION
        "The transmitted DAPI part of the TCMA trace (15 character)"
    ::=  { oduTcmAConfigEntry 6 }

oduTcmAConfigTraceTransmitOpsp OBJECT-TYPE
    SYNTAX      OCTET STRING (SIZE(0..32))
    MAX-ACCESS  read-write
    STATUS      current
    DESCRIPTION
        "The transmitted Operator Specific part of the TCMA trace (32 character)"
    ::=  { oduTcmAConfigEntry 7 }

oduTcmAConfigTimMode OBJECT-TYPE
    SYNTAX      TimMode
    MAX-ACCESS  read-write
    STATUS      current
    DESCRIPTION
        "Detection of TIM-TCMA Condition can be configured"
    ::=  { oduTcmAConfigEntry 8 }

oduTcmBConfigTable OBJECT-TYPE
    SYNTAX      SEQUENCE OF OduTcmBConfigEntry
    MAX-ACCESS  not-accessible
    STATUS      current
    DESCRIPTION   "Contains entries for the configuration of ODU interfaces.
         This table extends the entries in the ifTable (RFC 2863)."
    ::=  { oduConfig 4 }

oduTcmBConfigEntry OBJECT-TYPE
    SYNTAX      OduTcmBConfigEntry
    MAX-ACCESS  not-accessible
    STATUS      current
    DESCRIPTION   "ODU interfaces will have an entry in this table."
    INDEX       {
                  entityIndex
                }
    ::=  { oduTcmBConfigTable 1 }

OduTcmBConfigEntry ::=  SEQUENCE
  { oduTcmBConfigSignalDegradeThreshold Integer32,
    oduTcmBConfigSignalDegradePeriod Unsigned32,
    oduTcmBConfigTcmLevel OtnTcmLevel,
    oduTcmBConfigTraceExpected OCTET STRING,
    oduTcmBConfigTraceTransmitSapi OCTET STRING,
    oduTcmBConfigTraceTransmitDapi OCTET STRING,
    oduTcmBConfigTraceTransmitOpsp OCTET STRING,
    oduTcmBConfigTimMode TimMode }

oduTcmBConfigSignalDegradeThreshold OBJECT-TYPE
    SYNTAX      Integer32 (1..100 | -2147483648)
    UNITS       "%"
    MAX-ACCESS  read-write
    STATUS      current
    DESCRIPTION   "Threshold for ODU SM-SD alarm (threshold level 0..100%, default value 15 %).
         Ref. table 24/G.7710."
    ::=  { oduTcmBConfigEntry 1 }

oduTcmBConfigSignalDegradePeriod OBJECT-TYPE
    SYNTAX      Unsigned32 (2..10 | 4294967295)
    UNITS       "s"
    MAX-ACCESS  read-write
    STATUS      current
    DESCRIPTION   "Measuring period for ODU SM-SD alarm: 2..10 sec) (bursty)
         Ref. table 24/G.7710. Default value: 7."
    ::=  { oduTcmBConfigEntry 2 }

oduTcmBConfigTcmLevel OBJECT-TYPE
    SYNTAX      OtnTcmLevel
    MAX-ACCESS  read-write
    STATUS      current
    DESCRIPTION
        "Activation of Tandem Connection Monitoring Instance B"
    ::=  { oduTcmBConfigEntry 3 }

oduTcmBConfigTraceExpected OBJECT-TYPE
    SYNTAX      OCTET STRING (SIZE(0..15))
    MAX-ACCESS  read-write
    STATUS      current
    DESCRIPTION
        "Expected SAPI part of the TCMB trace (15 character). NULL TRACE-TCM implies that no trace comparison is made."
    ::=  { oduTcmBConfigEntry 4 }

oduTcmBConfigTraceTransmitSapi OBJECT-TYPE
    SYNTAX      OCTET STRING (SIZE(0..15))
    MAX-ACCESS  read-write
    STATUS      current
    DESCRIPTION
        "The transmitted SAPI part of the TCMB trace (15 character)"
    ::=  { oduTcmBConfigEntry 5 }

oduTcmBConfigTraceTransmitDapi OBJECT-TYPE
    SYNTAX      OCTET STRING (SIZE(0..15))
    MAX-ACCESS  read-write
    STATUS      current
    DESCRIPTION
        "The transmitted DAPI part of the TCMB trace (15 character)"
    ::=  { oduTcmBConfigEntry 6 }

oduTcmBConfigTraceTransmitOpsp OBJECT-TYPE
    SYNTAX      OCTET STRING (SIZE(0..32))
    MAX-ACCESS  read-write
    STATUS      current
    DESCRIPTION
        "The transmitted Operator Specific part of the TCMB trace (32 character)"
    ::=  { oduTcmBConfigEntry 7 }

oduTcmBConfigTimMode OBJECT-TYPE
    SYNTAX      TimMode
    MAX-ACCESS  read-write
    STATUS      current
    DESCRIPTION
        "Detection of TIM-TCMB Condition can be configured"
    ::=  { oduTcmBConfigEntry 8 }

oduTcmCConfigTable OBJECT-TYPE
    SYNTAX      SEQUENCE OF OduTcmCConfigEntry
    MAX-ACCESS  not-accessible
    STATUS      current
    DESCRIPTION   "Contains entries for the configuration of ODU interfaces.
         This table extends the entries in the ifTable (RFC 2863)."
    ::=  { oduConfig 5 }

oduTcmCConfigEntry OBJECT-TYPE
    SYNTAX      OduTcmCConfigEntry
    MAX-ACCESS  not-accessible
    STATUS      current
    DESCRIPTION   "ODU interfaces will have an entry in this table."
    INDEX       {
                  entityIndex
                }
    ::=  { oduTcmCConfigTable 1 }

OduTcmCConfigEntry ::=  SEQUENCE
  { oduTcmCConfigSignalDegradeThreshold Integer32,
    oduTcmCConfigSignalDegradePeriod Unsigned32,
    oduTcmCConfigTcmLevel OtnTcmLevel,
    oduTcmCConfigTraceExpected OCTET STRING,
    oduTcmCConfigTraceTransmitSapi OCTET STRING,
    oduTcmCConfigTraceTransmitDapi OCTET STRING,
    oduTcmCConfigTraceTransmitOpsp OCTET STRING,
    oduTcmCConfigTimMode TimMode }

oduTcmCConfigSignalDegradeThreshold OBJECT-TYPE
    SYNTAX      Integer32 (1..100 | -2147483648)
    UNITS       "%"
    MAX-ACCESS  read-write
    STATUS      current
    DESCRIPTION   "Threshold for ODU SM-SD alarm (threshold level 0..100%, default value 15 %).
         Ref. table 24/G.7710."
    ::=  { oduTcmCConfigEntry 1 }

oduTcmCConfigSignalDegradePeriod OBJECT-TYPE
    SYNTAX      Unsigned32 (2..10 | 4294967295)
    UNITS       "s"
    MAX-ACCESS  read-write
    STATUS      current
    DESCRIPTION   "Measuring period for ODU SM-SD alarm: 2..10 sec) (bursty)
         Ref. table 24/G.7710. Default value: 7."
    ::=  { oduTcmCConfigEntry 2 }

oduTcmCConfigTcmLevel OBJECT-TYPE
    SYNTAX      OtnTcmLevel
    MAX-ACCESS  read-write
    STATUS      current
    DESCRIPTION
        "Activation of Tandem Connection Monitoring Instance C"
    ::=  { oduTcmCConfigEntry 3 }

oduTcmCConfigTraceExpected OBJECT-TYPE
    SYNTAX      OCTET STRING (SIZE(0..15))
    MAX-ACCESS  read-write
    STATUS      current
    DESCRIPTION
        "Expected SAPI part of the TCMC trace (15 character). NULL TRACE-TCM implies that no trace comparison is made."
    ::=  { oduTcmCConfigEntry 4 }

oduTcmCConfigTraceTransmitSapi OBJECT-TYPE
    SYNTAX      OCTET STRING (SIZE(0..15))
    MAX-ACCESS  read-write
    STATUS      current
    DESCRIPTION
        "The transmitted SAPI part of the TCMC trace (15 character)"
    ::=  { oduTcmCConfigEntry 5 }

oduTcmCConfigTraceTransmitDapi OBJECT-TYPE
    SYNTAX      OCTET STRING (SIZE(0..15))
    MAX-ACCESS  read-write
    STATUS      current
    DESCRIPTION
        "The transmitted DAPI part of the TCMC trace (15 character)"
    ::=  { oduTcmCConfigEntry 6 }

oduTcmCConfigTraceTransmitOpsp OBJECT-TYPE
    SYNTAX      OCTET STRING (SIZE(0..32))
    MAX-ACCESS  read-write
    STATUS      current
    DESCRIPTION
        "The transmitted Operator Specific part of the TCMC trace (32 character)"
    ::=  { oduTcmCConfigEntry 7 }

oduTcmCConfigTimMode OBJECT-TYPE
    SYNTAX      TimMode
    MAX-ACCESS  read-write
    STATUS      current
    DESCRIPTION
        "Detection of TIM-TCMC Condition can be configured"
    ::=  { oduTcmCConfigEntry 8 }

oduTcmADataTable OBJECT-TYPE
    SYNTAX      SEQUENCE OF OduTcmADataEntry
    MAX-ACCESS  not-accessible
    STATUS      current
    DESCRIPTION   "Contains entries for the status of ODU interfaces.
         This table extends the entries in the ifTable (RFC 2863)."
    ::=  { oduConfig 6 }

oduTcmADataEntry OBJECT-TYPE
    SYNTAX      OduTcmADataEntry
    MAX-ACCESS  not-accessible
    STATUS      current
    DESCRIPTION   "ODU interfaces will have an entry in this table."
    INDEX       {
                  entityIndex
                }
    ::=  { oduTcmADataTable 1 }

OduTcmADataEntry ::=  SEQUENCE
  { oduTcmADataTraceReceivedSapi OCTET STRING,
    oduTcmADataTraceReceivedDapi OCTET STRING,
    oduTcmADataTraceReceivedOpsp OCTET STRING }

oduTcmADataTraceReceivedSapi OBJECT-TYPE
    SYNTAX      OCTET STRING (SIZE(0..15))
    MAX-ACCESS  read-only
    STATUS      current
    DESCRIPTION
        "The received SAPI part of the TCMA trace (15 character)"
    ::=  { oduTcmADataEntry 1 }

oduTcmADataTraceReceivedDapi OBJECT-TYPE
    SYNTAX      OCTET STRING (SIZE(0..15))
    MAX-ACCESS  read-only
    STATUS      current
    DESCRIPTION
        "The received DAPI part of the TCMA trace (15 character)"
    ::=  { oduTcmADataEntry 2 }

oduTcmADataTraceReceivedOpsp OBJECT-TYPE
    SYNTAX      OCTET STRING (SIZE(0..32))
    MAX-ACCESS  read-only
    STATUS      current
    DESCRIPTION
        "The received Operator Specific part of the TCMA trace (32 character)"
    ::=  { oduTcmADataEntry 3 }

oduTcmBDataTable OBJECT-TYPE
    SYNTAX      SEQUENCE OF OduTcmBDataEntry
    MAX-ACCESS  not-accessible
    STATUS      current
    DESCRIPTION   "Contains entries for the status of ODU interfaces.
         This table extends the entries in the ifTable (RFC 2863)."
    ::=  { oduConfig 7 }

oduTcmBDataEntry OBJECT-TYPE
    SYNTAX      OduTcmBDataEntry
    MAX-ACCESS  not-accessible
    STATUS      current
    DESCRIPTION   "ODU interfaces will have an entry in this table."
    INDEX       {
                  entityIndex
                }
    ::=  { oduTcmBDataTable 1 }

OduTcmBDataEntry ::=  SEQUENCE
  { oduTcmBDataTraceReceivedSapi OCTET STRING,
    oduTcmBDataTraceReceivedDapi OCTET STRING,
    oduTcmBDataTraceReceivedOpsp OCTET STRING }

oduTcmBDataTraceReceivedSapi OBJECT-TYPE
    SYNTAX      OCTET STRING (SIZE(0..15))
    MAX-ACCESS  read-only
    STATUS      current
    DESCRIPTION
        "The received SAPI part of the TCMB trace (15 character)"
    ::=  { oduTcmBDataEntry 1 }

oduTcmBDataTraceReceivedDapi OBJECT-TYPE
    SYNTAX      OCTET STRING (SIZE(0..15))
    MAX-ACCESS  read-only
    STATUS      current
    DESCRIPTION
        "The received DAPI part of the TCMB trace (15 character)"
    ::=  { oduTcmBDataEntry 2 }

oduTcmBDataTraceReceivedOpsp OBJECT-TYPE
    SYNTAX      OCTET STRING (SIZE(0..32))
    MAX-ACCESS  read-only
    STATUS      current
    DESCRIPTION
        "The received Operator Specific part of the TCMB trace (32 character)"
    ::=  { oduTcmBDataEntry 3 }

oduTcmCDataTable OBJECT-TYPE
    SYNTAX      SEQUENCE OF OduTcmCDataEntry
    MAX-ACCESS  not-accessible
    STATUS      current
    DESCRIPTION   "Contains entries for the status of ODU interfaces.
         This table extends the entries in the ifTable (RFC 2863)."
    ::=  { oduConfig 8 }

oduTcmCDataEntry OBJECT-TYPE
    SYNTAX      OduTcmCDataEntry
    MAX-ACCESS  not-accessible
    STATUS      current
    DESCRIPTION   "ODU interfaces will have an entry in this table."
    INDEX       {
                  entityIndex
                }
    ::=  { oduTcmCDataTable 1 }

OduTcmCDataEntry ::=  SEQUENCE
  { oduTcmCDataTraceReceivedSapi OCTET STRING,
    oduTcmCDataTraceReceivedDapi OCTET STRING,
    oduTcmCDataTraceReceivedOpsp OCTET STRING }

oduTcmCDataTraceReceivedSapi OBJECT-TYPE
    SYNTAX      OCTET STRING (SIZE(0..15))
    MAX-ACCESS  read-only
    STATUS      current
    DESCRIPTION
        "The received SAPI part of the TCMC trace (15 character)"
    ::=  { oduTcmCDataEntry 1 }

oduTcmCDataTraceReceivedDapi OBJECT-TYPE
    SYNTAX      OCTET STRING (SIZE(0..15))
    MAX-ACCESS  read-only
    STATUS      current
    DESCRIPTION
        "The received DAPI part of the TCMC trace (15 character)"
    ::=  { oduTcmCDataEntry 2 }

oduTcmCDataTraceReceivedOpsp OBJECT-TYPE
    SYNTAX      OCTET STRING (SIZE(0..32))
    MAX-ACCESS  read-only
    STATUS      current
    DESCRIPTION
        "The received Operator Specific part of the TCMC trace (32 character)"
    ::=  { oduTcmCDataEntry 3 }

swDbFileTable OBJECT-TYPE
    SYNTAX      SEQUENCE OF SwDbFileEntry
    MAX-ACCESS  not-accessible
    STATUS      current
    DESCRIPTION   ""
    ::=  { swAdmin 1 }

swDbFileEntry OBJECT-TYPE
    SYNTAX      SwDbFileEntry
    MAX-ACCESS  not-accessible
    STATUS      current
    DESCRIPTION   ""
    INDEX       {
                  swDbFileIndex
                }
    ::=  { swDbFileTable 1 }

SwDbFileEntry ::=  SEQUENCE
  { swDbFileIndex EntityIndex,
    swDbFileArea FileArea,
    swDbFileType FileType,
    swDbFileSize Unsigned32,
    swDbFileCreationTime DateAndTime,
    swDbFileVersion SnmpAdminString,
    swDbFileGrade Grade,
    swDbFileComment SnmpAdminString,
    swDbFileFileName SnmpAdminString,
    swDbFileRowStatus RowStatus,
    swDbFilePgmType PgmType }

swDbFileIndex OBJECT-TYPE
    SYNTAX      EntityIndex
    MAX-ACCESS  not-accessible
    STATUS      current
    DESCRIPTION   "Index"
    ::=  { swDbFileEntry 1 }

swDbFileArea OBJECT-TYPE
    SYNTAX      FileArea
    MAX-ACCESS  read-only
    STATUS      current
    DESCRIPTION
        "Type of Area"
    ::=  { swDbFileEntry 2 }

swDbFileType OBJECT-TYPE
    SYNTAX      FileType
    MAX-ACCESS  read-only
    STATUS      current
    DESCRIPTION
        "Type of File"
    ::=  { swDbFileEntry 3 }

swDbFileSize OBJECT-TYPE
    SYNTAX      Unsigned32
    UNITS       "Byte"
    MAX-ACCESS  read-only
    STATUS      current
    DESCRIPTION
        "Size of Memory = USED + AVAILABLE"
    ::=  { swDbFileEntry 4 }

swDbFileCreationTime OBJECT-TYPE
    SYNTAX      DateAndTime
    MAX-ACCESS  read-only
    STATUS      current
    DESCRIPTION
        "Creation Time"
    ::=  { swDbFileEntry 5 }

swDbFileVersion OBJECT-TYPE
    SYNTAX      SnmpAdminString
    MAX-ACCESS  read-only
    STATUS      current
    DESCRIPTION
        "General Release Issue Number of software in the ACT or STBY memory location. Format: XX-YY-Z"
    ::=  { swDbFileEntry 6 }

swDbFileGrade OBJECT-TYPE
    SYNTAX      Grade
    MAX-ACCESS  read-only
    STATUS      current
    DESCRIPTION
        "Used to distinguish between NCU capabilities (range of supported services or applications)"
    ::=  { swDbFileEntry 7 }

swDbFileComment OBJECT-TYPE
    SYNTAX      SnmpAdminString
    MAX-ACCESS  read-write
    STATUS      current
    DESCRIPTION
        "Comment of PGM or DBS files."
    ::=  { swDbFileEntry 8 }

swDbFileFileName OBJECT-TYPE
    SYNTAX      SnmpAdminString
    MAX-ACCESS  read-only
    STATUS      current
    DESCRIPTION
        "File Name"
    ::=  { swDbFileEntry 9 }

swDbFileRowStatus OBJECT-TYPE
    SYNTAX      RowStatus
    MAX-ACCESS  read-write
    STATUS      current
    DESCRIPTION
        "RowStatus"
    ::=  { swDbFileEntry 10 }

swDbFilePgmType OBJECT-TYPE
    SYNTAX      PgmType
    MAX-ACCESS  read-only
    STATUS      current
    DESCRIPTION
        "Program Type"
    ::=  { swDbFileEntry 11 }

fwDataTable OBJECT-TYPE
    SYNTAX      SEQUENCE OF FwDataEntry
    MAX-ACCESS  not-accessible
    STATUS      current
    DESCRIPTION   ""
    ::=  { swAdmin 2 }

fwDataEntry OBJECT-TYPE
    SYNTAX      FwDataEntry
    MAX-ACCESS  not-accessible
    STATUS      current
    DESCRIPTION   ""
    INDEX       {
                  entityIndex
                }
    ::=  { fwDataTable 1 }

FwDataEntry ::=  SEQUENCE
  { fwDataNewVersion SnmpAdminString,
    fwDataStandbyVersion SnmpAdminString,
    fwDataServiceImpairment ServiceAffecting,
    fwDataBootStatus BootState,
    fwDataFirmwarePackageRev SnmpAdminString,
    fwDataStandbyServiceImpairment StandbyServiceAffecting,
    fwDataFirmwareAvailable NoYesNA,
    fwDataFirmwareApproved NoYesNA,
    fwDataFirmwarePackageRevBackup SnmpAdminString,
    fwDataReadyForActivation YesNoNA,
    fwDataActivationReadyOnStandby YesNoNA,
    fwDataProtectionPart FspR7YesNo,
    fwDataForm ModuleForm }

fwDataNewVersion OBJECT-TYPE
    SYNTAX      SnmpAdminString
    MAX-ACCESS  read-only
    STATUS      current
    DESCRIPTION
        "New Firmware Package Revision Number of file which resides on ACT PGM partition."
    ::=  { fwDataEntry 1 }

fwDataStandbyVersion OBJECT-TYPE
    SYNTAX      SnmpAdminString
    MAX-ACCESS  read-only
    STATUS      current
    DESCRIPTION
        "New Firmware Package Revision Number of file which resides on STBY PGM partition."
    ::=  { fwDataEntry 2 }

fwDataServiceImpairment OBJECT-TYPE
    SYNTAX      ServiceAffecting
    MAX-ACCESS  read-only
    STATUS      current
    DESCRIPTION
        "Service Affecting Change during FWP upgrade and Restart operation"
    ::=  { fwDataEntry 3 }

fwDataBootStatus OBJECT-TYPE
    SYNTAX      BootState
    MAX-ACCESS  read-only
    STATUS      current
    DESCRIPTION
        "Boot State. Every state change (excluding IDLE) does generate a corresponding transient condition."
    ::=  { fwDataEntry 4 }

fwDataFirmwarePackageRev OBJECT-TYPE
    SYNTAX      SnmpAdminString
    MAX-ACCESS  read-only
    STATUS      current
    DESCRIPTION
        "Active Firmware Package Revision Number of module software."
    ::=  { fwDataEntry 5 }

fwDataStandbyServiceImpairment OBJECT-TYPE
    SYNTAX      StandbyServiceAffecting
    MAX-ACCESS  read-only
    STATUS      current
    DESCRIPTION
        "Service Affecting Change during FWP upgrade after activation of STBY PGM partition."
    ::=  { fwDataEntry 6 }

fwDataFirmwareAvailable OBJECT-TYPE
    SYNTAX      NoYesNA
    MAX-ACCESS  read-only
    STATUS      current
    DESCRIPTION
        "Firmware package for Encryption module available on RDISK"
    ::=  { fwDataEntry 7 }

fwDataFirmwareApproved OBJECT-TYPE
    SYNTAX      NoYesNA
    MAX-ACCESS  read-only
    STATUS      current
    DESCRIPTION
        "Firmware package update for Encryption module is approved by Crypto Officer"
    ::=  { fwDataEntry 8 }

fwDataFirmwarePackageRevBackup OBJECT-TYPE
    SYNTAX      SnmpAdminString
    MAX-ACCESS  read-only
    STATUS      current
    DESCRIPTION
        "Standbay Firmware Package Revision Number, Format XX.YY.ZZ (X,Y,Z are decimal characters, leading 0 are omitted)."
    ::=  { fwDataEntry 9 }

fwDataReadyForActivation OBJECT-TYPE
    SYNTAX      YesNoNA
    MAX-ACCESS  read-only
    STATUS      current
    DESCRIPTION
        "FWPREV-STBY == FWPREV-SYS-ACT"
    ::=  { fwDataEntry 10 }

fwDataActivationReadyOnStandby OBJECT-TYPE
    SYNTAX      YesNoNA
    MAX-ACCESS  read-only
    STATUS      current
    DESCRIPTION
        "FWPREV-STBY == FWPREV-SYS-STBY"
    ::=  { fwDataEntry 11 }

fwDataProtectionPart OBJECT-TYPE
    SYNTAX      FspR7YesNo
    MAX-ACCESS  read-only
    STATUS      current
    DESCRIPTION
        "Module is active part of Channel Card Protection Group."
    ::=  { fwDataEntry 12 }

fwDataForm OBJECT-TYPE
    SYNTAX      ModuleForm
    MAX-ACCESS  read-only
    STATUS      current
    DESCRIPTION
        "Form of module"
    ::=  { fwDataEntry 13 }

coldRestartCapTable OBJECT-TYPE
    SYNTAX      SEQUENCE OF ColdRestartCapEntry
    MAX-ACCESS  not-accessible
    STATUS      current
    DESCRIPTION   ""
    ::=  { swAdmin 3 }

coldRestartCapEntry OBJECT-TYPE
    SYNTAX      ColdRestartCapEntry
    MAX-ACCESS  not-accessible
    STATUS      current
    DESCRIPTION   ""
    INDEX       {
                  entityIndex
                }
    ::=  { coldRestartCapTable 1 }

ColdRestartCapEntry ::=  SEQUENCE
  { coldRestartCapServiceAffectingCap ServiceAffectingCaps }

coldRestartCapServiceAffectingCap OBJECT-TYPE
    SYNTAX      ServiceAffectingCaps
    MAX-ACCESS  read-only
    STATUS      current
    DESCRIPTION
        "Service Affecting Change during FWP upgrade and Restart operation"
    ::=  { coldRestartCapEntry 1 }

eqpFwUpgradeRequest OBJECT-TYPE
    SYNTAX      CommandEqpt
    MAX-ACCESS  read-write
    STATUS      current
    DESCRIPTION
        "Update, Install and Reboot commands."
    ::=  { swAdmin 10 }

eqpFwServiceImpairment OBJECT-TYPE
    SYNTAX      ServiceAffecting
    MAX-ACCESS  read-write
    STATUS      current
    DESCRIPTION
        "Service Affecting Change during FWP upgrade and Restart operation"
    ::=  { swAdmin 11 }

eqpFwNextEqpForUpdate OBJECT-TYPE
    SYNTAX      EntityIndex
    MAX-ACCESS  read-write
    STATUS      current
    DESCRIPTION
        "The valid address of physically available Equipment part."
    ::=  { swAdmin 12 }

eqpFwEqpType OBJECT-TYPE
    SYNTAX      FspR7EquipmentType
    MAX-ACCESS  read-write
    STATUS      current
    DESCRIPTION
        "The TYPE of Equipment and the MODE setting determine uniquely the number and allowed TYPE's of the provisionable dependent entities (plugs, interfaces, modules)"
    ::=  { swAdmin 13 }

eqpFwNcuServerBusy OBJECT-TYPE
    SYNTAX      FspR7FalseTrue
    MAX-ACCESS  read-only
    STATUS      current
    DESCRIPTION
        "NCU SW download busy"
    ::=  { swAdmin 14 }

eqpFwEqpServerBusy OBJECT-TYPE
    SYNTAX      FspR7FalseTrue
    MAX-ACCESS  read-only
    STATUS      current
    DESCRIPTION
        "Firmware package download busy"
    ::=  { swAdmin 15 }

updateEqpt OBJECT-TYPE
    SYNTAX      Unsigned32
    MAX-ACCESS  read-only
    STATUS      current
    DESCRIPTION
        "Number of equipment which have to be updated"
    ::=  { swAdmin 16 }

installedEqpt OBJECT-TYPE
    SYNTAX      Unsigned32
    MAX-ACCESS  read-only
    STATUS      current
    DESCRIPTION
        "Number of equipment is already installed"
    ::=  { swAdmin 17 }

selectedFile OBJECT-TYPE
    SYNTAX      SnmpAdminString
    MAX-ACCESS  read-write
    STATUS      current
    DESCRIPTION
        "File Name"
    ::=  { swAdmin 18 }

ncuActivationDate OBJECT-TYPE
    SYNTAX      FspR7Date
    MAX-ACCESS  read-write
    STATUS      current
    DESCRIPTION
        "Activation Date in local time. Format: YY-MM-DD"
    ::=  { swAdmin 19 }

ncuActivationTime OBJECT-TYPE
    SYNTAX      FspR7Time
    MAX-ACCESS  read-write
    STATUS      current
    DESCRIPTION
        "Activation Time in local time. Format HH-MM-SS"
    ::=  { swAdmin 20 }

ncuScheduledActivation OBJECT-TYPE
    SYNTAX      NcuAutoActivation
    MAX-ACCESS  read-write
    STATUS      current
    DESCRIPTION
        "Enable scheduled activation of the standby PGM partition."
    ::=  { swAdmin 21 }

ncuScheduledDbRestore OBJECT-TYPE
    SYNTAX      RestoreActivation
    MAX-ACCESS  read-write
    STATUS      current
    DESCRIPTION
        "Shows whether scheduled activtion will be a database restore or a new software activation"
    ::=  { swAdmin 22 }

encryptionFwpFile OBJECT-TYPE
    SYNTAX      SnmpAdminString
    MAX-ACCESS  read-only
    STATUS      current
    DESCRIPTION
        "The name FWP for encryption capable modules."
    ::=  { swAdmin 23 }

clearRdiskRequest OBJECT-TYPE
    SYNTAX      INTEGER
                {
                  undefined(0),
                  active(1),
                  inactive(2)
                }
    MAX-ACCESS  read-write
    STATUS      current
    DESCRIPTION
        "This object initiate RDISK clearance."
    ::=  { swAdmin 24 }

ncuActivationDateUtc OBJECT-TYPE
    SYNTAX      FspR7Date
    MAX-ACCESS  read-write
    STATUS      current
    DESCRIPTION
        "Activation Date Format: YY-MM-DD"
    ::=  { swAdmin 25 }

ncuActivationTimeUtc OBJECT-TYPE
    SYNTAX      FspR7Time
    MAX-ACCESS  read-write
    STATUS      current
    DESCRIPTION
        "Activation Time Format: HH-MM-SS"
    ::=  { swAdmin 26 }

neBackupEncryption OBJECT-TYPE
    SYNTAX      EnableState
    MAX-ACCESS  read-write
    STATUS      current
    DESCRIPTION
        "Beckup Encryption"
    ::=  { swAdmin 38 }

neBackupPassword OBJECT-TYPE
    SYNTAX      SnmpAdminString
    MAX-ACCESS  read-write
    STATUS      current
    DESCRIPTION
        "Secret, case-sensitive password to for encryption"
    ::=  { swAdmin 39 }

neF7AutomaticRemoteBackupEncryption OBJECT-TYPE
    SYNTAX      EnableState
    MAX-ACCESS  read-write
    STATUS      current
    DESCRIPTION
        "Beckup Encryption"
    ::=  { swAdmin 40 }

neF7AutomaticRemoteBackupPassword OBJECT-TYPE
    SYNTAX      SnmpAdminString
    MAX-ACCESS  read-write
    STATUS      current
    DESCRIPTION
        "Secret, case-sensitive password to for encryption"
    ::=  { swAdmin 41 }

neBackupUsers OBJECT-TYPE
    SYNTAX      FspR7UsersDb
    MAX-ACCESS  read-write
    STATUS      current
    DESCRIPTION
        "Users Database"
    ::=  { swAdmin 42 }

neRestoreConfig OBJECT-TYPE
    SYNTAX      RestoreActivation
    MAX-ACCESS  read-write
    STATUS      current
    DESCRIPTION
        "Shows whether the last activation was(will be) a database restore or a new software activation"
    ::=  { dbAdmin 1 }

swDbDataTable OBJECT-TYPE
    SYNTAX      SEQUENCE OF SwDbDataEntry
    MAX-ACCESS  not-accessible
    STATUS      current
    DESCRIPTION   ""
    ::=  { dbAdmin 2 }

swDbDataEntry OBJECT-TYPE
    SYNTAX      SwDbDataEntry
    MAX-ACCESS  not-accessible
    STATUS      current
    DESCRIPTION   ""
    INDEX       {
                  swDbDataIndex
                }
    ::=  { swDbDataTable 1 }

SwDbDataEntry ::=  SEQUENCE
  { swDbDataIndex EntityIndex,
    swDbDataArea FileArea,
    swDbDataProgramVersion SnmpAdminString,
    swDbDataDatabaseVersion SnmpAdminString,
    swDbDataActivationTime DateAndTime,
    swDbDataRestoreConfig RestoreActivation,
    swDbDataFirmwareSetVersion SnmpAdminString,
    swDbDataNcuSoftwareVersion SnmpAdminString,
    swDbDataStandbyPartitionStatus PartitionStatus,
    swDbDataNumEqpt Unsigned32,
    swDbDataNumLegacyEqpt Unsigned32,
    swDbDataNumNativeSaUpdate Unsigned32,
    swDbDataNumNativeNsaUpdate Unsigned32,
    swDbDataNumLegacyUpdate Unsigned32,
    swDbDataNumSaNotReady Unsigned32,
    swDbDataNumNsaNotReady Unsigned32 }

swDbDataIndex OBJECT-TYPE
    SYNTAX      EntityIndex
    MAX-ACCESS  not-accessible
    STATUS      current
    DESCRIPTION   "Index"
    ::=  { swDbDataEntry 1 }

swDbDataArea OBJECT-TYPE
    SYNTAX      FileArea
    MAX-ACCESS  read-only
    STATUS      current
    DESCRIPTION
        "Type of Area"
    ::=  { swDbDataEntry 2 }

swDbDataProgramVersion OBJECT-TYPE
    SYNTAX      SnmpAdminString
    MAX-ACCESS  read-only
    STATUS      current
    DESCRIPTION
        "General Release Issue Number of software in the ACT or STBY memory location. Format: XX-YY-Z"
    ::=  { swDbDataEntry 3 }

swDbDataDatabaseVersion OBJECT-TYPE
    SYNTAX      SnmpAdminString
    MAX-ACCESS  read-only
    STATUS      current
    DESCRIPTION
        "General Release Issue Number of Database in the ACT or STBY memory location. Typically this will be the same as the GISSUE."
    ::=  { swDbDataEntry 4 }

swDbDataActivationTime OBJECT-TYPE
    SYNTAX      DateAndTime
    MAX-ACCESS  read-only
    STATUS      current
    DESCRIPTION
        "Activation Time"
    ::=  { swDbDataEntry 5 }

swDbDataRestoreConfig OBJECT-TYPE
    SYNTAX      RestoreActivation
    MAX-ACCESS  read-only
    STATUS      current
    DESCRIPTION
        "Shows whether the last activation was(will be) a database restore or a new software activation"
    ::=  { swDbDataEntry 6 }

swDbDataFirmwareSetVersion OBJECT-TYPE
    SYNTAX      SnmpAdminString
    MAX-ACCESS  read-only
    STATUS      current
    DESCRIPTION
        "Firmware Package Set Version"
    ::=  { swDbDataEntry 7 }

swDbDataNcuSoftwareVersion OBJECT-TYPE
    SYNTAX      SnmpAdminString
    MAX-ACCESS  read-only
    STATUS      current
    DESCRIPTION
        "NCU Software Version ACT or STBY memory location. Format: XX-YY-Z"
    ::=  { swDbDataEntry 8 }

swDbDataStandbyPartitionStatus OBJECT-TYPE
    SYNTAX      PartitionStatus
    MAX-ACCESS  read-only
    STATUS      current
    DESCRIPTION
        "Partition State"
    ::=  { swDbDataEntry 9 }

swDbDataNumEqpt OBJECT-TYPE
    SYNTAX      Unsigned32
    MAX-ACCESS  read-only
    STATUS      current
    DESCRIPTION
        "Number of all provisioned and equipped equipment in system"
    ::=  { swDbDataEntry 10 }

swDbDataNumLegacyEqpt OBJECT-TYPE
    SYNTAX      Unsigned32
    MAX-ACCESS  read-only
    STATUS      current
    DESCRIPTION
        "Number of all legacy provisioned and equipped modules in system,"
    ::=  { swDbDataEntry 11 }

swDbDataNumNativeSaUpdate OBJECT-TYPE
    SYNTAX      Unsigned32
    MAX-ACCESS  read-only
    STATUS      current
    DESCRIPTION
        "Number of all native modules which have to be updated (SA), both with already properly installed pak on standby image and those which need installation."
    ::=  { swDbDataEntry 12 }

swDbDataNumNativeNsaUpdate OBJECT-TYPE
    SYNTAX      Unsigned32
    MAX-ACCESS  read-only
    STATUS      current
    DESCRIPTION
        "Number of all modules which have to be updated (NSA),both with already properly installed pak on standby image and those which need installation."
    ::=  { swDbDataEntry 13 }

swDbDataNumLegacyUpdate OBJECT-TYPE
    SYNTAX      Unsigned32
    MAX-ACCESS  read-only
    STATUS      current
    DESCRIPTION
        "Number of all legacy modules which have to be updated."
    ::=  { swDbDataEntry 14 }

swDbDataNumSaNotReady OBJECT-TYPE
    SYNTAX      Unsigned32
    MAX-ACCESS  read-only
    STATUS      current
    DESCRIPTION
        "Number of modules which have to be SA updated on which new pak need to be installed."
    ::=  { swDbDataEntry 15 }

swDbDataNumNsaNotReady OBJECT-TYPE
    SYNTAX      Unsigned32
    MAX-ACCESS  read-only
    STATUS      current
    DESCRIPTION
        "Number of modules which have to be NSA updated on which new pak need to be installed."
    ::=  { swDbDataEntry 16 }

swDbDataCapTable OBJECT-TYPE
    SYNTAX      SEQUENCE OF SwDbDataCapEntry
    MAX-ACCESS  not-accessible
    STATUS      current
    DESCRIPTION   ""
    ::=  { dbAdmin 3 }

swDbDataCapEntry OBJECT-TYPE
    SYNTAX      SwDbDataCapEntry
    MAX-ACCESS  not-accessible
    STATUS      current
    DESCRIPTION   ""
    INDEX       {
                  swDbDataCapUpgradeRequest
                }
    ::=  { swDbDataCapTable 1 }

SwDbDataCapEntry ::=  SEQUENCE
  { swDbDataCapUpgradeRequest INTEGER,
    swDbDataCapRestoreConfig RestoreActivationCaps }

swDbDataCapUpgradeRequest OBJECT-TYPE
    SYNTAX      INTEGER
                {
                  undefined(0),
                  none(1),
                  download(2),
                  install(3),
                  activate(4),
                  revertToPrevious(5),
                  reboot(6),
                  downloadInstallActivateReboot(7),
                  installActivateReboot(8),
                  revertToPreviousReboot(9),
                  activateAlp(10),
                  activateDefaultAlp(11),
                  upload(12),
                  autoDownloadInstall(13),
                  autoInstall(14),
                  encryptionFwpInstall(15),
                  encryptionFwpDownloadInstall(16),
                  downloadCf(17),
                  uploadCf(18),
                  installCf(19),
                  autoInstallCf(20),
                  uploadPa(21),
                  activateWithFwp(22)
                }
    MAX-ACCESS  not-accessible
    STATUS      current
    DESCRIPTION   "Index value is a requested upgrade type from neSwUpgradeRequest object,
         where following values are applicable:
         - install(3)
         - activate(4)
         - reboot(6)
         - activateAlp(10)
         - activateDefaultAlp(11)
        "
    ::=  { swDbDataCapEntry 1 }

swDbDataCapRestoreConfig OBJECT-TYPE
    SYNTAX      RestoreActivationCaps
    MAX-ACCESS  read-only
    STATUS      current
    DESCRIPTION
        "Shows whether the last activation was(will be) a database restore or a new software activation"
    ::=  { swDbDataCapEntry 2 }

swDbDataDefaultsTable OBJECT-TYPE
    SYNTAX      SEQUENCE OF SwDbDataDefaultsEntry
    MAX-ACCESS  not-accessible
    STATUS      current
    DESCRIPTION   ""
    ::=  { dbAdmin 4 }

swDbDataDefaultsEntry OBJECT-TYPE
    SYNTAX      SwDbDataDefaultsEntry
    MAX-ACCESS  not-accessible
    STATUS      current
    DESCRIPTION   ""
    INDEX       {
                  swDbDataDefaultsUpgradeRequest
                }
    ::=  { swDbDataDefaultsTable 1 }

SwDbDataDefaultsEntry ::=  SEQUENCE
  { swDbDataDefaultsUpgradeRequest INTEGER,
    swDbDataDefaultsRestoreConfig RestoreActivation }

swDbDataDefaultsUpgradeRequest OBJECT-TYPE
    SYNTAX      INTEGER
                {
                  undefined(0),
                  none(1),
                  download(2),
                  install(3),
                  activate(4),
                  revertToPrevious(5),
                  reboot(6),
                  downloadInstallActivateReboot(7),
                  installActivateReboot(8),
                  revertToPreviousReboot(9),
                  activateAlp(10),
                  activateDefaultAlp(11),
                  upload(12),
                  autoDownloadInstall(13),
                  autoInstall(14),
                  encryptionFwpInstall(15),
                  encryptionFwpDownloadInstall(16),
                  downloadCf(17),
                  uploadCf(18),
                  installCf(19),
                  autoInstallCf(20),
                  uploadPa(21),
                  activateWithFwp(22)
                }
    MAX-ACCESS  not-accessible
    STATUS      current
    DESCRIPTION   "Index value is a requested upgrade type from neSwUpgradeRequest object,
         where following values are applicable:
         - install(3)
         - activate(4)
         - reboot(6)
         - activateAlp(10)
         - activateDefaultAlp(11)
        "
    ::=  { swDbDataDefaultsEntry 1 }

swDbDataDefaultsRestoreConfig OBJECT-TYPE
    SYNTAX      RestoreActivation
    MAX-ACCESS  read-only
    STATUS      current
    DESCRIPTION
        "Shows whether the last activation was(will be) a database restore or a new software activation"
    ::=  { swDbDataDefaultsEntry 2 }

snmpServerPort OBJECT-TYPE
    SYNTAX      Integer32
    MAX-ACCESS  read-write
    STATUS      current
    DESCRIPTION
        "The TCP or UDP port on which a server is listening"
    ::=  { snmpAgent 2 }

snmpProxyServerAdminState OBJECT-TYPE
    SYNTAX      FspR7AdminStateSnmpProxy
    MAX-ACCESS  read-write
    STATUS      current
    DESCRIPTION
        "The Administrative State will be displayed in the GUI with full
         name values; it will be differently displayed in TL1 syntax according
         to TL1 display rules. The transaction into the UAS state requires
         a special destroy/delete function"
    ::=  { snmpAgent 3 }

snmpProxyServerPort OBJECT-TYPE
    SYNTAX      Integer32
    MAX-ACCESS  read-only
    STATUS      current
    DESCRIPTION
        "The TCP or UDP port on which a server is listening"
    ::=  { snmpAgent 4 }

snmpProxyServerSynchroState OBJECT-TYPE
    SYNTAX      SnmpProxySynchronizationState
    MAX-ACCESS  read-write
    STATUS      current
    DESCRIPTION
        "This parameter is used to synchronize proxy table on GNE with destination NE's
         availability.
        "
    ::=  { snmpAgent 5 }

snmpProxyServerSynchroStage OBJECT-TYPE
    SYNTAX      SnmpProxySynchronizationStage
    MAX-ACCESS  not-accessible
    STATUS      current
    DESCRIPTION
        "This parameter is used to indicate stage of synchronization process.
        "
    ::=  { snmpAgent 6 }

snmpProxyEntrySingleTargetOutTable OBJECT-TYPE
    SYNTAX      SEQUENCE OF SnmpProxyEntrySingleTargetOutEntry
    MAX-ACCESS  not-accessible
    STATUS      current
    DESCRIPTION   ""
    ::=  { snmpAgent 10 }

snmpProxyEntrySingleTargetOutEntry OBJECT-TYPE
    SYNTAX      SnmpProxyEntrySingleTargetOutEntry
    MAX-ACCESS  not-accessible
    STATUS      current
    DESCRIPTION   ""
    INDEX       {
                  snmpProxyEntrySingleTargetOutAddress,
                  snmpProxyEntrySingleTargetOutPort
                }
    ::=  { snmpProxyEntrySingleTargetOutTable 1 }

SnmpProxyEntrySingleTargetOutEntry ::=  SEQUENCE
  { snmpProxyEntrySingleTargetOutAddress IpAddress,
    snmpProxyEntrySingleTargetOutPort Unsigned32,
    snmpProxyEntrySingleTargetOutNodeAgentStatus DestinationNodeOrAgentState,
    snmpProxyEntrySingleTargetOutContext SnmpAdminString,
    snmpProxyEntrySingleTargetOutRowStatus RowStatus,
    snmpProxyEntrySingleTargetOutAdminState FspR7AdminStateSnmpProxy,
    snmpProxyEntrySingleTargetOutUserName SnmpAdminString }

snmpProxyEntrySingleTargetOutAddress OBJECT-TYPE
    SYNTAX      IpAddress
    MAX-ACCESS  not-accessible
    STATUS      current
    DESCRIPTION
        "IP Address assigned to LAN IP Interface"
    ::=  { snmpProxyEntrySingleTargetOutEntry 1 }

snmpProxyEntrySingleTargetOutPort OBJECT-TYPE
    SYNTAX      Unsigned32
    MAX-ACCESS  not-accessible
    STATUS      current
    DESCRIPTION
        "The destination port"
    ::=  { snmpProxyEntrySingleTargetOutEntry 2 }

snmpProxyEntrySingleTargetOutNodeAgentStatus OBJECT-TYPE
    SYNTAX      DestinationNodeOrAgentState
    MAX-ACCESS  not-accessible
    STATUS      current
    DESCRIPTION
        ""
    ::=  { snmpProxyEntrySingleTargetOutEntry 3 }

snmpProxyEntrySingleTargetOutContext OBJECT-TYPE
    SYNTAX      SnmpAdminString
    MAX-ACCESS  read-only
    STATUS      current
    DESCRIPTION
        "The contextName used in SNMP messages to an SNMP Proxy Forwarder to indicate for which SNMP Proxy Client the SNMP messages is meant"
    ::=  { snmpProxyEntrySingleTargetOutEntry 4 }

snmpProxyEntrySingleTargetOutRowStatus OBJECT-TYPE
    SYNTAX      RowStatus
    MAX-ACCESS  read-write
    STATUS      current
    DESCRIPTION
        "RowStatus"
    ::=  { snmpProxyEntrySingleTargetOutEntry 5 }

snmpProxyEntrySingleTargetOutAdminState OBJECT-TYPE
    SYNTAX      FspR7AdminStateSnmpProxy
    MAX-ACCESS  read-write
    STATUS      current
    DESCRIPTION
        "The Administrative State will be displayed in the GUI with full
         name values; it will be differently displayed in TL1 syntax according
         to TL1 display rules. The transaction into the UAS state requires
         a special destroy/delete function"
    ::=  { snmpProxyEntrySingleTargetOutEntry 6 }

snmpProxyEntrySingleTargetOutUserName OBJECT-TYPE
    SYNTAX      SnmpAdminString
    MAX-ACCESS  read-write
    STATUS      current
    DESCRIPTION
        "The name string for user authentication purposes"
    ::=  { snmpProxyEntrySingleTargetOutEntry 7 }


END
