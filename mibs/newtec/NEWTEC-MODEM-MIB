NEWTEC-MODEM-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF

    ntcFunction
        FROM NEWTEC-MAIN-MIB;


--
--  Module Identification
--

ntcModem   MODULE-IDENTITY
    LAST-UPDATED "201402031200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Modem MIB containing definitions for generic Modem
        functionality"

    REVISION  "201402031200Z"
    DESCRIPTION
        "Parameters applicable to modems"
    ::= { ntcFunction  6500 }


--
-- Top-Level Structure
--

-- ntcModem content

ntcModemObjects                  OBJECT-IDENTITY
    STATUS        current
    DESCRIPTION   "Container holding ntcModemObjects definitions."
    ::= { ntcModem 1 }

ntcModemConformance              OBJECT-IDENTITY
    STATUS        current
    DESCRIPTION   "Conformance requirements."
    ::= { ntcModem 2 }

-- ntcModemConformance content

ntcModemConfCompliance           OBJECT-IDENTITY
    STATUS        current
    DESCRIPTION   "Device compliance statements."
    ::= { ntcModemConformance 1 }

ntcModemConfGroup                OBJECT-IDENTITY
    STATUS        current
    DESCRIPTION   "Groups used by device compliance statements."
    ::= { ntcModemConformance 2 }


--
-- Managed Objects
--

ntcModemTxCtrlDemodLockAlarm     OBJECT-TYPE
    SYNTAX      INTEGER { disableTransmit(0), noImpact(1) }
    MAX-ACCESS  read-write
    STATUS      current
    DESCRIPTION
        "Configure the impact of a General Device alarm on the Modulator Transmit."
    DEFVAL { noImpact }
    ::= { ntcModemObjects 1 }


--
--  Module Conformance
--

ntcModemConfGrpV1Standard        OBJECT-GROUP
    OBJECTS    {
                   ntcModemTxCtrlDemodLockAlarm
               }
    STATUS      current
    DESCRIPTION
        "Managed objects that constitute version 1 of a system device with standard capabilities."
    ::= { ntcModemConfGroup 1}

ntcModemConfCompV1Standard       MODULE-COMPLIANCE
    STATUS      current
    DESCRIPTION
        "Compliance statement for Newtec device MIB implementations."
    MODULE  -- this module
    MANDATORY-GROUPS
                  {
                      ntcModemConfGrpV1Standard
                  }
    ::= { ntcModemConfCompliance  1 }


END
