NEWTEC-BBCONV-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF

    ntcFunction
        FROM NEWTEC-MAIN-MIB;


--
--  Module Identification
--

ntcBBandConverter   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec B Band Converter MIB containing definitions for B Band Converter
        functionality."

    REVISION  "201707101200Z"
    DESCRIPTION
        "Initial release"
    ::= { ntcFunction  10500 }


--
-- Top-Level Structure
--

-- ntcBBandConverter content

ntcBbcObjects                    OBJECT-IDENTITY
    STATUS        current
    DESCRIPTION   "Container holding ntcBbcObjects definitions."
    ::= { ntcBBandConverter 1 }

ntcBbcConformance                OBJECT-IDENTITY
    STATUS        current
    DESCRIPTION   "Conformance requirements."
    ::= { ntcBBandConverter 2 }

-- ntcBbcObjects content

ntcBbcConf                       OBJECT-IDENTITY
    STATUS        current
    DESCRIPTION   "Container holding ntcBbcConf definitions."
    ::= { ntcBbcObjects 1 }

-- ntcBbcConformance content

ntcBbcConfCompliance             OBJECT-IDENTITY
    STATUS        current
    DESCRIPTION   "Device compliance statements."
    ::= { ntcBbcConformance 1 }

ntcBbcConfGroup                  OBJECT-IDENTITY
    STATUS        current
    DESCRIPTION   "Groups used by device compliance statements."
    ::= { ntcBbcConformance 2 }


--
-- Managed Objects
--

ntcBbcConfEnable                 OBJECT-TYPE
    SYNTAX      INTEGER { off(0), on(1) }
    MAX-ACCESS  read-write
    STATUS      current
    DESCRIPTION
        "Enable"
    DEFVAL { off }
    ::= { ntcBbcConf 1 }

ntcBbcConfSelection              OBJECT-TYPE
    SYNTAX      INTEGER { abandRHCP99W(0), abandLHCP99W(1), bbandRHCP99W(2), bbandLHCP99W(3), abandRHCP103W(4), abandLHCP103W(5), bbandRHCP103W(6), bbandLHCP103W(7) }
    MAX-ACCESS  read-write
    STATUS      current
    DESCRIPTION
        "Signal Selection"
    DEFVAL { abandRHCP99W }
    ::= { ntcBbcConf 2 }


--
--  Module Conformance
--

ntcBbcConfGrpV1Standard          OBJECT-GROUP
    OBJECTS    {
                   ntcBbcConfEnable,
                   ntcBbcConfSelection
               }
    STATUS      current
    DESCRIPTION
        "Managed objects that constitute version 1 of a system device with standard capabilities."
    ::= { ntcBbcConfGroup 1}

ntcBbcConfCompV1Standard         MODULE-COMPLIANCE
    STATUS      current
    DESCRIPTION
        "Compliance statement for Newtec device MIB implementations."
    MODULE  -- this module
    MANDATORY-GROUPS
                  {
                      ntcBbcConfGrpV1Standard
                  }
    ::= { ntcBbcConfCompliance  1 }


END
