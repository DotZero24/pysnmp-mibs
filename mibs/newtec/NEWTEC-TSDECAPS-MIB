NEWTEC-TSDECAPS-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF

    NtcEnable
        FROM NEWTEC-TC-MIB

    DisplayString,
    RowStatus
        FROM SNMPv2-TC

    ntcFunction
        FROM NEWTEC-MAIN-MIB;


--
--  Module Identification
--

ntcTsDecaps   MODULE-IDENTITY
    LAST-UPDATED "201905140600Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular TSDECAPS output MIB containing definitions for TS Decapsulation
        functionality."

    REVISION  "201905140600Z"
    DESCRIPTION
        "ntcTsDecMpeCrcVal added"
    REVISION  "201509251100Z"
    DESCRIPTION
        "ntcTsDecChannels column added to ntcTsDecChannelsAccessVlan table"
    REVISION  "201504130700Z"
    DESCRIPTION
        "ntcTsDecChannels table column added + some ranges extended"
    REVISION  "201501300800Z"
    DESCRIPTION
        "only cosmetic changes"
    REVISION  "201407150800Z"
    DESCRIPTION
        "Support filtering of packets without a label"
    REVISION  "201402031200Z"
    DESCRIPTION
        "MPE + ULE decapsulation"
    ::= { ntcFunction  5900 }


--
-- Top-Level Structure
--

-- ntcTsDecaps content

ntcTsDecObjects                  OBJECT-IDENTITY
    STATUS        current
    DESCRIPTION   "Container holding ntcTsDecObjects definitions."
    ::= { ntcTsDecaps 1 }

ntcTsDecConformance              OBJECT-IDENTITY
    STATUS        current
    DESCRIPTION   "Conformance requirements."
    ::= { ntcTsDecaps 2 }

-- ntcTsDecConformance content

ntcTsDecConfCompliance           OBJECT-IDENTITY
    STATUS        current
    DESCRIPTION   "Device compliance statements."
    ::= { ntcTsDecConformance 1 }

ntcTsDecConfGroup                OBJECT-IDENTITY
    STATUS        current
    DESCRIPTION   "Groups used by device compliance statements."
    ::= { ntcTsDecConformance 2 }


--
-- Managed Objects
--

ntcTsDecIsisTable                OBJECT-TYPE
    SYNTAX      SEQUENCE OF NtcTsDecIsisEntry
    MAX-ACCESS  not-accessible
    STATUS      current
    DESCRIPTION
        "A table containing the ntcTsDecIsis"
    ::= { ntcTsDecObjects 1 }

ntcTsDecIsisEntry                OBJECT-TYPE
    SYNTAX      NtcTsDecIsisEntry
    MAX-ACCESS  not-accessible
    STATUS      current
    DESCRIPTION
        "A conceptual row of the ntcTsDecIsisTable."
    INDEX   { ntcTsDecIsisName  }
    ::= { ntcTsDecIsisTable 1 }

NtcTsDecIsisEntry                ::= SEQUENCE {
    ntcTsDecIsisName              DisplayString,
    ntcTsDecIsisRowStatus         RowStatus,
    ntcTsDecIsisEnable            NtcEnable,
    ntcTsDecIsisIsi               Unsigned32,
    ntcTsDecIsisInTypeName        OCTET STRING,
    ntcTsDecIsisInInstanceName    OCTET STRING
    }

ntcTsDecIsisName                 OBJECT-TYPE
    SYNTAX      DisplayString (SIZE(1..100))
    MAX-ACCESS  not-accessible
    STATUS      current
    DESCRIPTION
        "The name of the Isi"
    ::= { ntcTsDecIsisEntry 1 }

ntcTsDecIsisRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsDecIsisEntry 2 }

ntcTsDecIsisEnable               OBJECT-TYPE
    SYNTAX      NtcEnable
    MAX-ACCESS  read-create
    STATUS      current
    DESCRIPTION
        "Enable or disable the corresponding decapsulator isi."
    ::= { ntcTsDecIsisEntry 3 }

ntcTsDecIsisIsi                  OBJECT-TYPE
    SYNTAX      Unsigned32
    MAX-ACCESS  read-create
    STATUS      current
    DESCRIPTION
        "The decapsulator ISI"
    ::= { ntcTsDecIsisEntry 4 }

ntcTsDecIsisInTypeName           OBJECT-TYPE
    SYNTAX      OCTET STRING (SIZE(0..255))
    MAX-ACCESS  read-create
    STATUS      current
    DESCRIPTION
        "The input type."
    ::= { ntcTsDecIsisEntry 5 }

ntcTsDecIsisInInstanceName       OBJECT-TYPE
    SYNTAX      OCTET STRING (SIZE(0..255))
    MAX-ACCESS  read-create
    STATUS      current
    DESCRIPTION
        "The input instance name."
    ::= { ntcTsDecIsisEntry 6 }

ntcTsDecPidsTable                OBJECT-TYPE
    SYNTAX      SEQUENCE OF NtcTsDecPidsEntry
    MAX-ACCESS  not-accessible
    STATUS      current
    DESCRIPTION
        "A table containing the ntcTsDecPids"
    ::= { ntcTsDecObjects 2 }

ntcTsDecPidsEntry                OBJECT-TYPE
    SYNTAX      NtcTsDecPidsEntry
    MAX-ACCESS  not-accessible
    STATUS      current
    DESCRIPTION
        "A conceptual row of the ntcTsDecPidsTable."
    INDEX   { ntcTsDecPidsName  }
    ::= { ntcTsDecPidsTable 1 }

NtcTsDecPidsEntry                ::= SEQUENCE {
    ntcTsDecPidsName              DisplayString,
    ntcTsDecPidsRowStatus         RowStatus,
    ntcTsDecPidsEnable            NtcEnable,
    ntcTsDecPidsPid               Unsigned32,
    ntcTsDecPidsInTypeName        OCTET STRING,
    ntcTsDecPidsInInstanceName    OCTET STRING,
    ntcTsDecPidsProtocol          INTEGER
    }

ntcTsDecPidsName                 OBJECT-TYPE
    SYNTAX      DisplayString (SIZE(1..100))
    MAX-ACCESS  not-accessible
    STATUS      current
    DESCRIPTION
        "The name of the Pid"
    ::= { ntcTsDecPidsEntry 1 }

ntcTsDecPidsRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsDecPidsEntry 2 }

ntcTsDecPidsEnable               OBJECT-TYPE
    SYNTAX      NtcEnable
    MAX-ACCESS  read-create
    STATUS      current
    DESCRIPTION
        "Enable or disable the corresponding decapsulator pid."
    ::= { ntcTsDecPidsEntry 3 }

ntcTsDecPidsPid                  OBJECT-TYPE
    SYNTAX      Unsigned32 (0..8190)
    MAX-ACCESS  read-create
    STATUS      current
    DESCRIPTION
        "PID"
    ::= { ntcTsDecPidsEntry 4 }

ntcTsDecPidsInTypeName           OBJECT-TYPE
    SYNTAX      OCTET STRING (SIZE(0..255))
    MAX-ACCESS  read-create
    STATUS      current
    DESCRIPTION
        "The input type."
    ::= { ntcTsDecPidsEntry 5 }

ntcTsDecPidsInInstanceName       OBJECT-TYPE
    SYNTAX      OCTET STRING (SIZE(0..255))
    MAX-ACCESS  read-create
    STATUS      current
    DESCRIPTION
        "The input instance name."
    ::= { ntcTsDecPidsEntry 6 }

ntcTsDecPidsProtocol             OBJECT-TYPE
    SYNTAX      INTEGER { default(0), mpe(1), ule(2) }
    MAX-ACCESS  read-create
    STATUS      current
    DESCRIPTION
        "The transport stream decapsulation protocol."
    ::= { ntcTsDecPidsEntry 7 }

ntcTsDecChannelsTable            OBJECT-TYPE
    SYNTAX      SEQUENCE OF NtcTsDecChannelsEntry
    MAX-ACCESS  not-accessible
    STATUS      current
    DESCRIPTION
        "A table containing the ntcTsDecChannels"
    ::= { ntcTsDecObjects 3 }

ntcTsDecChannelsEntry            OBJECT-TYPE
    SYNTAX      NtcTsDecChannelsEntry
    MAX-ACCESS  not-accessible
    STATUS      current
    DESCRIPTION
        "A conceptual row of the ntcTsDecChannelsTable."
    INDEX   { ntcTsDecChannelsName  }
    ::= { ntcTsDecChannelsTable 1 }

NtcTsDecChannelsEntry            ::= SEQUENCE {
    ntcTsDecChannelsName              DisplayString,
    ntcTsDecChannelsRowStatus         RowStatus,
    ntcTsDecChannelsEnable            NtcEnable,
    ntcTsDecChannelsInTypeName        OCTET STRING,
    ntcTsDecChannelsInInstanceName    OCTET STRING,
    ntcTsDecChannelsLabel             DisplayString,
    ntcTsDecChannelsVirualNetwork     OCTET STRING,
    ntcTsDecChannelsAccessVlan        Unsigned32
    }

ntcTsDecChannelsName             OBJECT-TYPE
    SYNTAX      DisplayString (SIZE(1..100))
    MAX-ACCESS  not-accessible
    STATUS      current
    DESCRIPTION
        "The name of the channel"
    ::= { ntcTsDecChannelsEntry 1 }

ntcTsDecChannelsRowStatus        OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsDecChannelsEntry 2 }

ntcTsDecChannelsEnable           OBJECT-TYPE
    SYNTAX      NtcEnable
    MAX-ACCESS  read-create
    STATUS      current
    DESCRIPTION
        "Enable or disable the corresponding channel."
    ::= { ntcTsDecChannelsEntry 3 }

ntcTsDecChannelsInTypeName       OBJECT-TYPE
    SYNTAX      OCTET STRING (SIZE(0..255))
    MAX-ACCESS  read-create
    STATUS      current
    DESCRIPTION
        "The input type."
    ::= { ntcTsDecChannelsEntry 4 }

ntcTsDecChannelsInInstanceName   OBJECT-TYPE
    SYNTAX      OCTET STRING (SIZE(0..255))
    MAX-ACCESS  read-create
    STATUS      current
    DESCRIPTION
        "The input instance name."
    ::= { ntcTsDecChannelsEntry 5 }

ntcTsDecChannelsLabel            OBJECT-TYPE
    SYNTAX      DisplayString (SIZE(0..30))
    MAX-ACCESS  read-create
    STATUS      current
    DESCRIPTION
        "Label filter to be applied."
    ::= { ntcTsDecChannelsEntry 6 }

ntcTsDecChannelsVirualNetwork    OBJECT-TYPE
    SYNTAX      OCTET STRING (SIZE(0..255))
    MAX-ACCESS  read-create
    STATUS      current
    DESCRIPTION
        "The virtual network (addressing scope)"
    ::= { ntcTsDecChannelsEntry 7 }

ntcTsDecChannelsAccessVlan       OBJECT-TYPE
    SYNTAX      Unsigned32 (0..4095)
    MAX-ACCESS  read-create
    STATUS      current
    DESCRIPTION
        "If a non-zero Access VLAN is associated to an decapsulation channel, traffic
        from this channel is tagged with this VLAN"
    ::= { ntcTsDecChannelsEntry 8 }

ntcTsDecDefEncProt               OBJECT-TYPE
    SYNTAX      INTEGER { mpe(0), ule(1) }
    MAX-ACCESS  read-write
    STATUS      current
    DESCRIPTION
        "The default transport stream decapsulation protocol."
    DEFVAL { mpe }
    ::= { ntcTsDecObjects 4 }

ntcTsDecMpeCrcVal                OBJECT-TYPE
    SYNTAX      NtcEnable
    MAX-ACCESS  read-write
    STATUS      current
    DESCRIPTION
        "Enable or disable the MPE CRC checksum validation in the decapsulator. If the
        check is enabled (default), packets are only decapsulated if their checksum is
        correct. If disabled, the checksums are ignored and decapsulation happens in
        any case with the risk of forwarding corrupted payload."
    DEFVAL { on }
    ::= { ntcTsDecObjects 5 }


--
--  Module Conformance
--

ntcTsDecConfGrpV1Standard        OBJECT-GROUP
    OBJECTS    {
                   ntcTsDecIsisRowStatus,
                   ntcTsDecIsisEnable,
                   ntcTsDecIsisIsi,
                   ntcTsDecIsisInTypeName,
                   ntcTsDecIsisInInstanceName,
                   ntcTsDecPidsRowStatus,
                   ntcTsDecPidsEnable,
                   ntcTsDecPidsPid,
                   ntcTsDecPidsInTypeName,
                   ntcTsDecPidsInInstanceName,
                   ntcTsDecPidsProtocol,
                   ntcTsDecChannelsRowStatus,
                   ntcTsDecChannelsEnable,
                   ntcTsDecChannelsInTypeName,
                   ntcTsDecChannelsInInstanceName,
                   ntcTsDecChannelsLabel,
                   ntcTsDecChannelsVirualNetwork,
                   ntcTsDecChannelsAccessVlan,
                   ntcTsDecDefEncProt,
                   ntcTsDecMpeCrcVal
               }
    STATUS      current
    DESCRIPTION
        "Managed objects that constitute version 1 of a system device with standard capabilities."
    ::= { ntcTsDecConfGroup 1}

ntcTsDecConfCompV1Standard       MODULE-COMPLIANCE
    STATUS      current
    DESCRIPTION
        "Compliance statement for Newtec device MIB implementations."
    MODULE  -- this module
    MANDATORY-GROUPS
                  {
                      ntcTsDecConfGrpV1Standard
                  }
    ::= { ntcTsDecConfCompliance  1 }


END
