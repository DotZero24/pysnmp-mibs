NEWTEC-MULTIACMCLIENT-MIB DEFINITIONS ::= BEGIN

IMPORTS
    Integer32,
    Unsigned32,
    Counter32,
    MODULE-IDENTITY,
    OBJECT-IDENTITY,
    OBJECT-TYPE
        FROM SNMPv2-SMI

    MODULE-COMPLIANCE,
    OBJECT-GROUP
        FROM SNMPv2-CONF

    ntcFunction
        FROM NEWTEC-MAIN-MIB;


--
--  Module Identification
--

ntcMultiAcmClient   MODULE-IDENTITY
    LAST-UPDATED "201802020900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DVB modulator MIB containing definitions for the ACM
        multiclient."

    REVISION  "201802020900Z"
    DESCRIPTION
        "Only cosmetic change in units of ntcMltAcmClntMonErrStatsSec and
        ntcMltAcmClntMonErrStatsMtbe"
    REVISION  "201407150800Z"
    DESCRIPTION
        "DVB-S2X support"
    REVISION  "201402031200Z"
    DESCRIPTION
        "Delta Margin default value changed"
    REVISION  "201307050600Z"
    DESCRIPTION
        "Margin Logging added"
    REVISION  "201302261200Z"
    DESCRIPTION
        "Initial release for MDM6000 R1.1"
    ::= { ntcFunction  4700 }


--
-- Top-Level Structure
--

-- ntcMultiAcmClient content

ntcMltAcmClntObjects             OBJECT-IDENTITY
    STATUS        current
    DESCRIPTION   "Container holding ntcMltAcmClntObjects definitions."
    ::= { ntcMultiAcmClient 1 }

ntcMltAcmClntConformance         OBJECT-IDENTITY
    STATUS        current
    DESCRIPTION   "Conformance requirements."
    ::= { ntcMultiAcmClient 2 }

-- ntcMltAcmClntConformance content

ntcMltAcmClntConfCompliance      OBJECT-IDENTITY
    STATUS        current
    DESCRIPTION   "Device compliance statements."
    ::= { ntcMltAcmClntConformance 1 }

ntcMltAcmClntConfGroup           OBJECT-IDENTITY
    STATUS        current
    DESCRIPTION   "Groups used by device compliance statements."
    ::= { ntcMltAcmClntConformance 2 }


--
-- Managed Objects
--

ntcMltAcmClntCfgTable            OBJECT-TYPE
    SYNTAX      SEQUENCE OF NtcMltAcmClntCfgEntry
    MAX-ACCESS  not-accessible
    STATUS      current
    DESCRIPTION
        "A table containing the ntcMltAcmClntCfg"
    ::= { ntcMltAcmClntObjects 1 }

ntcMltAcmClntCfgEntry            OBJECT-TYPE
    SYNTAX      NtcMltAcmClntCfgEntry
    MAX-ACCESS  not-accessible
    STATUS      current
    DESCRIPTION
        "A conceptual row of the ntcMltAcmClntCfgTable."
    INDEX   { ntcMltAcmClntCfgDemodId  }
    ::= { ntcMltAcmClntCfgTable 1 }

NtcMltAcmClntCfgEntry            ::= SEQUENCE {
    ntcMltAcmClntCfgDemodId          INTEGER,
    ntcMltAcmClntCfgModCodAlgor      INTEGER,
    ntcMltAcmClntCfgMDeltaMargin     Integer32,
    ntcMltAcmClntCfgRemoteTermId     Unsigned32,
    ntcMltAcmClntCfgMarginLogging    INTEGER
    }

ntcMltAcmClntCfgDemodId          OBJECT-TYPE
    SYNTAX      INTEGER { demod1(1), demod2(2), demod3(3) }
    MAX-ACCESS  not-accessible
    STATUS      current
    DESCRIPTION
        "The id of the demodulator"
    ::= { ntcMltAcmClntCfgEntry 1 }

ntcMltAcmClntCfgModCodAlgor      OBJECT-TYPE
    SYNTAX      INTEGER { auto(0), headerEsno(1), linkMargin(2), linearCarrier(3), nonLinearCarrier(4), coND(5) }
    MAX-ACCESS  read-write
    STATUS      current
    DESCRIPTION
        "MODCOD selection algorithm. Different algorithms exist, each optimized for a
        different set of link conditions (e.g. saturated transponder)."
    DEFVAL { auto }
    ::= { ntcMltAcmClntCfgEntry 2 }

ntcMltAcmClntCfgMDeltaMargin     OBJECT-TYPE
    SYNTAX      Integer32 (-1000..3000)
    UNITS       "dB"
    MAX-ACCESS  read-write
    STATUS      current
    DESCRIPTION
        "The delta margin allows you to operate with a larger or smaller link margin as
        is configured system-wide. It can be negative and positive."
    DEFVAL { 0 }
    ::= { ntcMltAcmClntCfgEntry 3 }

ntcMltAcmClntCfgRemoteTermId     OBJECT-TYPE
    SYNTAX      Unsigned32 (0..65277)
    MAX-ACCESS  read-write
    STATUS      current
    DESCRIPTION
        "Identification of the controller terminal"
    DEFVAL { 0 }
    ::= { ntcMltAcmClntCfgEntry 4 }

ntcMltAcmClntCfgMarginLogging    OBJECT-TYPE
    SYNTAX      INTEGER { off(0), on(1) }
    MAX-ACCESS  read-write
    STATUS      current
    DESCRIPTION
        "Enable detailed margin logging"
    DEFVAL { off }
    ::= { ntcMltAcmClntCfgEntry 5 }

ntcMltAcmClntMonTable            OBJECT-TYPE
    SYNTAX      SEQUENCE OF NtcMltAcmClntMonEntry
    MAX-ACCESS  not-accessible
    STATUS      current
    DESCRIPTION
        "A table containing the ntcMltAcmClntMon"
    ::= { ntcMltAcmClntObjects 2 }

ntcMltAcmClntMonEntry            OBJECT-TYPE
    SYNTAX      NtcMltAcmClntMonEntry
    MAX-ACCESS  not-accessible
    STATUS      current
    DESCRIPTION
        "A conceptual row of the ntcMltAcmClntMonTable."
    INDEX   { ntcMltAcmClntMonDemodId  }
    ::= { ntcMltAcmClntMonTable 1 }

NtcMltAcmClntMonEntry            ::= SEQUENCE {
    ntcMltAcmClntMonDemodId          INTEGER,
    ntcMltAcmClntMonFadEstMg         Integer32,
    ntcMltAcmClntMonShrtRefEsno      Integer32,
    ntcMltAcmClntMonShrtReqModcod    INTEGER,
    ntcMltAcmClntMonShrtReqEsno      Integer32,
    ntcMltAcmClntMonNrmlRefEsno      Integer32,
    ntcMltAcmClntMonNrmlReqModcod    INTEGER,
    ntcMltAcmClntMonNrmlReqEsno      Integer32
    }

ntcMltAcmClntMonDemodId          OBJECT-TYPE
    SYNTAX      INTEGER { demod1(1), demod2(2), demod3(3) }
    MAX-ACCESS  not-accessible
    STATUS      current
    DESCRIPTION
        "The id of the demodulator"
    ::= { ntcMltAcmClntMonEntry 1 }

ntcMltAcmClntMonFadEstMg         OBJECT-TYPE
    SYNTAX      Integer32 (-1000..3000)
    UNITS       "dB"
    MAX-ACCESS  read-only
    STATUS      current
    DESCRIPTION
        "The dynamic margin calculated by the fading estimator."
    ::= { ntcMltAcmClntMonEntry 2 }

ntcMltAcmClntMonShrtRefEsno      OBJECT-TYPE
    SYNTAX      Integer32 (-1000..3000)
    UNITS       "dB"
    MAX-ACCESS  read-only
    STATUS      current
    DESCRIPTION
        "The measured Es/N0 (possibly corrected by the NoDE function) at the time the
        MODCOD request was calculated."
    ::= { ntcMltAcmClntMonEntry 3 }

ntcMltAcmClntMonShrtReqModcod    OBJECT-TYPE
    SYNTAX      INTEGER { noRequest(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The most recently requested MODCOD for short frames"
    ::= { ntcMltAcmClntMonEntry 4 }

ntcMltAcmClntMonShrtReqEsno      OBJECT-TYPE
    SYNTAX      Integer32 (-1000..3000)
    UNITS       "dB"
    MAX-ACCESS  read-only
    STATUS      current
    DESCRIPTION
        "The QEF (Quasi Error Free) Es/N0 that corresponds to the requested MODCOD."
    ::= { ntcMltAcmClntMonEntry 5 }

ntcMltAcmClntMonNrmlRefEsno      OBJECT-TYPE
    SYNTAX      Integer32 (-1000..3000)
    UNITS       "dB"
    MAX-ACCESS  read-only
    STATUS      current
    DESCRIPTION
        "The measured Es/N0 (possibly corrected by the NoDE function) at the time the
        MODCOD request was calculated."
    ::= { ntcMltAcmClntMonEntry 6 }

ntcMltAcmClntMonNrmlReqModcod    OBJECT-TYPE
    SYNTAX      INTEGER { noRequest(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The most recently requested MODCOD for normal frames"
    ::= { ntcMltAcmClntMonEntry 7 }

ntcMltAcmClntMonNrmlReqEsno      OBJECT-TYPE
    SYNTAX      Integer32 (-1000..3000)
    UNITS       "dB"
    MAX-ACCESS  read-only
    STATUS      current
    DESCRIPTION
        "The QEF (Quasi Error Free) Es/N0 that corresponds to the requested MODCOD."
    ::= { ntcMltAcmClntMonEntry 8 }

ntcMltAcmClntMonErrStatsTable    OBJECT-TYPE
    SYNTAX      SEQUENCE OF NtcMltAcmClntMonErrStatsEntry
    MAX-ACCESS  not-accessible
    STATUS      current
    DESCRIPTION
        "ACM Error statistics table"
    ::= { ntcMltAcmClntObjects 3 }

ntcMltAcmClntMonErrStatsEntry    OBJECT-TYPE
    SYNTAX      NtcMltAcmClntMonErrStatsEntry
    MAX-ACCESS  not-accessible
    STATUS      current
    DESCRIPTION
        "A conceptual row of the ntcMltAcmClntMonErrStatsTable."
    INDEX   { ntcMltAcmClntMonErrStatsStatCtr  }
    ::= { ntcMltAcmClntMonErrStatsTable 1 }

NtcMltAcmClntMonErrStatsEntry    ::= SEQUENCE {
    ntcMltAcmClntMonErrStatsStatCtr     Unsigned32,
    ntcMltAcmClntMonErrStatsDemodId     INTEGER,
    ntcMltAcmClntMonErrStatsInterval    INTEGER,
    ntcMltAcmClntMonErrStatsSec         Counter32,
    ntcMltAcmClntMonErrStatsMtbe        Counter32
    }

ntcMltAcmClntMonErrStatsStatCtr  OBJECT-TYPE
    SYNTAX      Unsigned32
    MAX-ACCESS  not-accessible
    STATUS      current
    DESCRIPTION
        "The index of the row"
    ::= { ntcMltAcmClntMonErrStatsEntry 1 }

ntcMltAcmClntMonErrStatsDemodId  OBJECT-TYPE
    SYNTAX      INTEGER { demod1(1), demod2(2), demod3(3) }
    MAX-ACCESS  read-only
    STATUS      current
    DESCRIPTION
        "The id of the demodulator"
    ::= { ntcMltAcmClntMonErrStatsEntry 2 }

ntcMltAcmClntMonErrStatsInterval OBJECT-TYPE
    SYNTAX      INTEGER { today(0), e1dayago(1), e2daysago(2), e3daysago(3), e4daysago(4), e5daysago(5) }
    MAX-ACCESS  read-only
    STATUS      current
    DESCRIPTION
        "ACM error interval identifier"
    ::= { ntcMltAcmClntMonErrStatsEntry 3 }

ntcMltAcmClntMonErrStatsSec      OBJECT-TYPE
    SYNTAX      Counter32
    UNITS       "s"
    MAX-ACCESS  read-only
    STATUS      current
    DESCRIPTION
        "Errored seconds counter. An errored second is defined as a second where the
        requested MODCOD could not be received error free."
    ::= { ntcMltAcmClntMonErrStatsEntry 4 }

ntcMltAcmClntMonErrStatsMtbe     OBJECT-TYPE
    SYNTAX      Counter32
    UNITS       "s"
    MAX-ACCESS  read-only
    STATUS      current
    DESCRIPTION
        "Mean time between error events. This is the average time in seconds between 2
        ACM error events, averaged during a day."
    ::= { ntcMltAcmClntMonErrStatsEntry 5 }


--
--  Module Conformance
--

ntcMltAcmClntConfGrpV1Standard   OBJECT-GROUP
    OBJECTS    {
                   ntcMltAcmClntCfgModCodAlgor,
                   ntcMltAcmClntCfgMDeltaMargin,
                   ntcMltAcmClntCfgRemoteTermId,
                   ntcMltAcmClntCfgMarginLogging,
                   ntcMltAcmClntMonFadEstMg,
                   ntcMltAcmClntMonShrtRefEsno,
                   ntcMltAcmClntMonShrtReqModcod,
                   ntcMltAcmClntMonShrtReqEsno,
                   ntcMltAcmClntMonNrmlRefEsno,
                   ntcMltAcmClntMonNrmlReqModcod,
                   ntcMltAcmClntMonNrmlReqEsno,
                   ntcMltAcmClntMonErrStatsDemodId,
                   ntcMltAcmClntMonErrStatsInterval,
                   ntcMltAcmClntMonErrStatsSec,
                   ntcMltAcmClntMonErrStatsMtbe
               }
    STATUS      current
    DESCRIPTION
        "Managed objects that constitute version 1 of a system device with standard capabilities."
    ::= { ntcMltAcmClntConfGroup 1}

ntcMltAcmClntConfCompV1Standard  MODULE-COMPLIANCE
    STATUS      current
    DESCRIPTION
        "Compliance statement for Newtec device MIB implementations."
    MODULE  -- this module
    MANDATORY-GROUPS
                  {
                      ntcMltAcmClntConfGrpV1Standard
                  }
    ::= { ntcMltAcmClntConfCompliance  1 }


END
