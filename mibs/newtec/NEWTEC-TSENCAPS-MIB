NEWTEC-TSENCAPS-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF

    NtcEnable
        FROM NEWTEC-TC-MIB

    DisplayString,
    RowStatus
        FROM SNMPv2-TC

    ntcFunction
        FROM NEWTEC-MAIN-MIB;


--
--  Module Identification
--

ntcTsEncaps   MODULE-IDENTITY
    LAST-UPDATED "201509251100Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular TSENCAPS input MIB containing definitions for TS Encapsulation
        functionality."

    REVISION  "201509251100Z"
    DESCRIPTION
        "ntcTsEncChannels column added to ntcTsEncChannelsAccessVlan table"
    REVISION  "201504130700Z"
    DESCRIPTION
        "Some ranges extended"
    REVISION  "201501300800Z"
    DESCRIPTION
        "only cosmetic changes"
    REVISION  "201407150800Z"
    DESCRIPTION
        "DVB-S2X support"
    REVISION  "201402031200Z"
    DESCRIPTION
        "MPE + ULE encapsulation"
    ::= { ntcFunction  5800 }


--
-- Top-Level Structure
--

-- ntcTsEncaps content

ntcTsEncObjects                  OBJECT-IDENTITY
    STATUS        current
    DESCRIPTION   "Container holding ntcTsEncObjects definitions."
    ::= { ntcTsEncaps 1 }

ntcTsEncConformance              OBJECT-IDENTITY
    STATUS        current
    DESCRIPTION   "Conformance requirements."
    ::= { ntcTsEncaps 2 }

-- ntcTsEncConformance content

ntcTsEncConfCompliance           OBJECT-IDENTITY
    STATUS        current
    DESCRIPTION   "Device compliance statements."
    ::= { ntcTsEncConformance 1 }

ntcTsEncConfGroup                OBJECT-IDENTITY
    STATUS        current
    DESCRIPTION   "Groups used by device compliance statements."
    ::= { ntcTsEncConformance 2 }


--
-- Managed Objects
--

ntcTsEncIsisTable                OBJECT-TYPE
    SYNTAX      SEQUENCE OF NtcTsEncIsisEntry
    MAX-ACCESS  not-accessible
    STATUS      current
    DESCRIPTION
        "A table containing the ntcTsEncIsis"
    ::= { ntcTsEncObjects 1 }

ntcTsEncIsisEntry                OBJECT-TYPE
    SYNTAX      NtcTsEncIsisEntry
    MAX-ACCESS  not-accessible
    STATUS      current
    DESCRIPTION
        "A conceptual row of the ntcTsEncIsisTable."
    INDEX   { ntcTsEncIsisName  }
    ::= { ntcTsEncIsisTable 1 }

NtcTsEncIsisEntry                ::= SEQUENCE {
    ntcTsEncIsisName         DisplayString,
    ntcTsEncIsisRowStatus    RowStatus,
    ntcTsEncIsisEnable       NtcEnable,
    ntcTsEncIsisIsi          Unsigned32,
    ntcTsEncIsisFrmTp        INTEGER
    }

ntcTsEncIsisName                 OBJECT-TYPE
    SYNTAX      DisplayString (SIZE(1..100))
    MAX-ACCESS  not-accessible
    STATUS      current
    DESCRIPTION
        "The name of the Isi"
    ::= { ntcTsEncIsisEntry 1 }

ntcTsEncIsisRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsEncIsisEntry 2 }

ntcTsEncIsisEnable               OBJECT-TYPE
    SYNTAX      NtcEnable
    MAX-ACCESS  read-create
    STATUS      current
    DESCRIPTION
        "Enable or disable the corresponding encapsulator isi."
    ::= { ntcTsEncIsisEntry 3 }

ntcTsEncIsisIsi                  OBJECT-TYPE
    SYNTAX      Unsigned32
    MAX-ACCESS  read-create
    STATUS      current
    DESCRIPTION
        "The encapsulator ISI"
    ::= { ntcTsEncIsisEntry 4 }

ntcTsEncIsisFrmTp                OBJECT-TYPE
    SYNTAX      INTEGER { short(0), normal(1) }
    MAX-ACCESS  read-create
    STATUS      current
    DESCRIPTION
        "The type of frames for this encapsulator."
    ::= { ntcTsEncIsisEntry 5 }

ntcTsEncPidsTable                OBJECT-TYPE
    SYNTAX      SEQUENCE OF NtcTsEncPidsEntry
    MAX-ACCESS  not-accessible
    STATUS      current
    DESCRIPTION
        "A table containing the ntcTsEncPids"
    ::= { ntcTsEncObjects 2 }

ntcTsEncPidsEntry                OBJECT-TYPE
    SYNTAX      NtcTsEncPidsEntry
    MAX-ACCESS  not-accessible
    STATUS      current
    DESCRIPTION
        "A conceptual row of the ntcTsEncPidsTable."
    INDEX   { ntcTsEncPidsName  }
    ::= { ntcTsEncPidsTable 1 }

NtcTsEncPidsEntry                ::= SEQUENCE {
    ntcTsEncPidsName               DisplayString,
    ntcTsEncPidsRowStatus          RowStatus,
    ntcTsEncPidsEnable             NtcEnable,
    ntcTsEncPidsPid                Unsigned32,
    ntcTsEncPidsOutTypeName        OCTET STRING,
    ntcTsEncPidsOutInstanceName    OCTET STRING,
    ntcTsEncPidsProtocol           INTEGER,
    ntcTsEncPidsNomS2Modcod        INTEGER,
    ntcTsEncPidsNomS2ExtModcod     INTEGER,
    ntcTsEncPidsAcmEnable          NtcEnable
    }

ntcTsEncPidsName                 OBJECT-TYPE
    SYNTAX      DisplayString (SIZE(1..100))
    MAX-ACCESS  not-accessible
    STATUS      current
    DESCRIPTION
        "The name of the Pid"
    ::= { ntcTsEncPidsEntry 1 }

ntcTsEncPidsRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsEncPidsEntry 2 }

ntcTsEncPidsEnable               OBJECT-TYPE
    SYNTAX      NtcEnable
    MAX-ACCESS  read-create
    STATUS      current
    DESCRIPTION
        "Enable or disable the corresponding encapsulator pid."
    ::= { ntcTsEncPidsEntry 3 }

ntcTsEncPidsPid                  OBJECT-TYPE
    SYNTAX      Unsigned32
    MAX-ACCESS  read-create
    STATUS      current
    DESCRIPTION
        "The encapsulator PID"
    ::= { ntcTsEncPidsEntry 4 }

ntcTsEncPidsOutTypeName          OBJECT-TYPE
    SYNTAX      OCTET STRING (SIZE(0..255))
    MAX-ACCESS  read-create
    STATUS      current
    DESCRIPTION
        "The output type."
    ::= { ntcTsEncPidsEntry 5 }

ntcTsEncPidsOutInstanceName      OBJECT-TYPE
    SYNTAX      OCTET STRING (SIZE(0..255))
    MAX-ACCESS  read-create
    STATUS      current
    DESCRIPTION
        "The output instance name."
    ::= { ntcTsEncPidsEntry 6 }

ntcTsEncPidsProtocol             OBJECT-TYPE
    SYNTAX      INTEGER { default(0), mpe(1), ule(2) }
    MAX-ACCESS  read-create
    STATUS      current
    DESCRIPTION
        "The transport stream encapsulation protocol."
    ::= { ntcTsEncPidsEntry 7 }

ntcTsEncPidsNomS2Modcod          OBJECT-TYPE
    SYNTAX      INTEGER { unspecified(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-create
    STATUS      current
    DESCRIPTION
        "The initial MODCOD that this pid uses in S2 mode."
    ::= { ntcTsEncPidsEntry 8 }

ntcTsEncPidsNomS2ExtModcod       OBJECT-TYPE
    SYNTAX      INTEGER { unspecified(0), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215) }
    MAX-ACCESS  read-create
    STATUS      current
    DESCRIPTION
        "The initial MODCOD that this channel uses in S2 Extensions mode."
    ::= { ntcTsEncPidsEntry 9 }

ntcTsEncPidsAcmEnable            OBJECT-TYPE
    SYNTAX      NtcEnable
    MAX-ACCESS  read-create
    STATUS      current
    DESCRIPTION
        "Enable or disable the ACM for this pid. This only takes effect when the
        encapsulator ACM is on."
    ::= { ntcTsEncPidsEntry 10 }

ntcTsEncChannelsTable            OBJECT-TYPE
    SYNTAX      SEQUENCE OF NtcTsEncChannelsEntry
    MAX-ACCESS  not-accessible
    STATUS      current
    DESCRIPTION
        "A table containing the ntcTsEncChannels"
    ::= { ntcTsEncObjects 3 }

ntcTsEncChannelsEntry            OBJECT-TYPE
    SYNTAX      NtcTsEncChannelsEntry
    MAX-ACCESS  not-accessible
    STATUS      current
    DESCRIPTION
        "A conceptual row of the ntcTsEncChannelsTable."
    INDEX   { ntcTsEncChannelsName  }
    ::= { ntcTsEncChannelsTable 1 }

NtcTsEncChannelsEntry            ::= SEQUENCE {
    ntcTsEncChannelsName               DisplayString,
    ntcTsEncChannelsRowStatus          RowStatus,
    ntcTsEncChannelsEnable             NtcEnable,
    ntcTsEncChannelsOutTypeName        OCTET STRING,
    ntcTsEncChannelsOutInstanceName    OCTET STRING,
    ntcTsEncChannelsLabel              DisplayString,
    ntcTsEncChannelsTermName           DisplayString,
    ntcTsEncChannelsAccessVlan         Unsigned32
    }

ntcTsEncChannelsName             OBJECT-TYPE
    SYNTAX      DisplayString (SIZE(1..100))
    MAX-ACCESS  not-accessible
    STATUS      current
    DESCRIPTION
        "The name of the channel"
    ::= { ntcTsEncChannelsEntry 1 }

ntcTsEncChannelsRowStatus        OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTsEncChannelsEntry 2 }

ntcTsEncChannelsEnable           OBJECT-TYPE
    SYNTAX      NtcEnable
    MAX-ACCESS  read-create
    STATUS      current
    DESCRIPTION
        "Enable or disable the corresponding destination channel."
    ::= { ntcTsEncChannelsEntry 3 }

ntcTsEncChannelsOutTypeName      OBJECT-TYPE
    SYNTAX      OCTET STRING (SIZE(0..255))
    MAX-ACCESS  read-create
    STATUS      current
    DESCRIPTION
        "The output type."
    ::= { ntcTsEncChannelsEntry 4 }

ntcTsEncChannelsOutInstanceName  OBJECT-TYPE
    SYNTAX      OCTET STRING (SIZE(0..255))
    MAX-ACCESS  read-create
    STATUS      current
    DESCRIPTION
        "The output instance name."
    ::= { ntcTsEncChannelsEntry 5 }

ntcTsEncChannelsLabel            OBJECT-TYPE
    SYNTAX      DisplayString (SIZE(0..30))
    MAX-ACCESS  read-create
    STATUS      current
    DESCRIPTION
        "Label of the destination channel or the special identifier 'multicast'."
    ::= { ntcTsEncChannelsEntry 6 }

ntcTsEncChannelsTermName         OBJECT-TYPE
    SYNTAX      DisplayString (SIZE(0..100))
    MAX-ACCESS  read-create
    STATUS      current
    DESCRIPTION
        "The name of the terminal to which this channel is configured"
    ::= { ntcTsEncChannelsEntry 7 }

ntcTsEncChannelsAccessVlan       OBJECT-TYPE
    SYNTAX      Unsigned32 (0..4095)
    MAX-ACCESS  read-create
    STATUS      current
    DESCRIPTION
        "If a non-zero Access VLAN is associated to an encapsulation channel, traffic
        from this VLAN is transmitted untagged to the channel."
    ::= { ntcTsEncChannelsEntry 8 }

ntcTsEncDefEncProt               OBJECT-TYPE
    SYNTAX      INTEGER { mpe(0), ule(1) }
    MAX-ACCESS  read-write
    STATUS      current
    DESCRIPTION
        "The default transport stream encapsulation protocol."
    DEFVAL { mpe }
    ::= { ntcTsEncObjects 4 }


--
--  Module Conformance
--

ntcTsEncConfGrpV1Standard        OBJECT-GROUP
    OBJECTS    {
                   ntcTsEncIsisRowStatus,
                   ntcTsEncIsisEnable,
                   ntcTsEncIsisIsi,
                   ntcTsEncIsisFrmTp,
                   ntcTsEncPidsRowStatus,
                   ntcTsEncPidsEnable,
                   ntcTsEncPidsPid,
                   ntcTsEncPidsOutTypeName,
                   ntcTsEncPidsOutInstanceName,
                   ntcTsEncPidsProtocol,
                   ntcTsEncPidsNomS2Modcod,
                   ntcTsEncPidsNomS2ExtModcod,
                   ntcTsEncPidsAcmEnable,
                   ntcTsEncChannelsRowStatus,
                   ntcTsEncChannelsEnable,
                   ntcTsEncChannelsOutTypeName,
                   ntcTsEncChannelsOutInstanceName,
                   ntcTsEncChannelsLabel,
                   ntcTsEncChannelsTermName,
                   ntcTsEncChannelsAccessVlan,
                   ntcTsEncDefEncProt
               }
    STATUS      current
    DESCRIPTION
        "Managed objects that constitute version 1 of a system device with standard capabilities."
    ::= { ntcTsEncConfGroup 1}

ntcTsEncConfCompV1Standard       MODULE-COMPLIANCE
    STATUS      current
    DESCRIPTION
        "Compliance statement for Newtec device MIB implementations."
    MODULE  -- this module
    MANDATORY-GROUPS
                  {
                      ntcTsEncConfGrpV1Standard
                  }
    ::= { ntcTsEncConfCompliance  1 }


END
