NEWTEC-PIDACTMON-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF

    NtcAlarmState,
    NtcEnable
        FROM NEWTEC-TC-MIB

    DisplayString,
    RowStatus
        FROM SNMPv2-TC

    ntcFunction
        FROM NEWTEC-MAIN-MIB;


--
--  Module Identification
--

ntcPidActivityMonitor   MODULE-IDENTITY
    LAST-UPDATED "201510191100Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing definitions for PID Activity Monitor
        functionality."

    REVISION  "201510191100Z"
    DESCRIPTION
        "Initial release for M6100 R2.6.5"
    ::= { ntcFunction  9200 }


--
-- Top-Level Structure
--

-- ntcPidActivityMonitor content

ntcPAMObjects                    OBJECT-IDENTITY
    STATUS        current
    DESCRIPTION   "Container holding ntcPAMObjects definitions."
    ::= { ntcPidActivityMonitor 1 }

ntcPAMConformance                OBJECT-IDENTITY
    STATUS        current
    DESCRIPTION   "Conformance requirements."
    ::= { ntcPidActivityMonitor 2 }

-- ntcPAMObjects content

ntcPAMConfiguration              OBJECT-IDENTITY
    STATUS        current
    DESCRIPTION   "Container holding ntcPAMConfiguration definitions."
    ::= { ntcPAMObjects 1 }

ntcPAMAlarms                     OBJECT-IDENTITY
    STATUS        current
    DESCRIPTION   "Container holding ntcPAMAlarms definitions."
    ::= { ntcPAMObjects 2 }

-- ntcPAMConformance content

ntcPAMConfCompliance             OBJECT-IDENTITY
    STATUS        current
    DESCRIPTION   "Device compliance statements."
    ::= { ntcPAMConformance 1 }

ntcPAMConfGroup                  OBJECT-IDENTITY
    STATUS        current
    DESCRIPTION   "Groups used by device compliance statements."
    ::= { ntcPAMConformance 2 }


--
-- Managed Objects
--

ntcPAMConfigTable                OBJECT-TYPE
    SYNTAX      SEQUENCE OF NtcPAMConfigEntry
    MAX-ACCESS  not-accessible
    STATUS      current
    DESCRIPTION
        "The configuration table."
    ::= { ntcPAMConfiguration 1 }

ntcPAMConfigEntry                OBJECT-TYPE
    SYNTAX      NtcPAMConfigEntry
    MAX-ACCESS  not-accessible
    STATUS      current
    DESCRIPTION
        "A conceptual row of the ntcPAMConfigTable."
    INDEX   { ntcPAMConfigName  }
    ::= { ntcPAMConfigTable 1 }

NtcPAMConfigEntry                ::= SEQUENCE {
    ntcPAMConfigName         DisplayString,
    ntcPAMConfigRowStatus    RowStatus,
    ntcPAMConfigEnable       NtcEnable,
    ntcPAMConfigPid          Unsigned32
    }

ntcPAMConfigName                 OBJECT-TYPE
    SYNTAX      DisplayString (SIZE(1..32))
    MAX-ACCESS  not-accessible
    STATUS      current
    DESCRIPTION
        "Name of the input configuration"
    ::= { ntcPAMConfigEntry 1 }

ntcPAMConfigRowStatus            OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcPAMConfigEntry 2 }

ntcPAMConfigEnable               OBJECT-TYPE
    SYNTAX      NtcEnable
    MAX-ACCESS  read-create
    STATUS      current
    DESCRIPTION
        "Enable or disable the monitoring for the specified PID."
    ::= { ntcPAMConfigEntry 3 }

ntcPAMConfigPid                  OBJECT-TYPE
    SYNTAX      Unsigned32 (0..8190)
    MAX-ACCESS  read-create
    STATUS      current
    DESCRIPTION
        "PID"
    ::= { ntcPAMConfigEntry 4 }

ntcPAMAlarmStatsTable            OBJECT-TYPE
    SYNTAX      SEQUENCE OF NtcPAMAlarmStatsEntry
    MAX-ACCESS  not-accessible
    STATUS      current
    DESCRIPTION
        "Alarm status table"
    ::= { ntcPAMAlarms 1 }

ntcPAMAlarmStatsEntry            OBJECT-TYPE
    SYNTAX      NtcPAMAlarmStatsEntry
    MAX-ACCESS  not-accessible
    STATUS      current
    DESCRIPTION
        "A conceptual row of the ntcPAMAlarmStatsTable."
    INDEX   { ntcPAMAlarmStatsName  }
    ::= { ntcPAMAlarmStatsTable 1 }

NtcPAMAlarmStatsEntry            ::= SEQUENCE {
    ntcPAMAlarmStatsName         DisplayString,
    ntcPAMAlarmStatsNotActive    NtcAlarmState
    }

ntcPAMAlarmStatsName             OBJECT-TYPE
    SYNTAX      DisplayString (SIZE(1..32))
    MAX-ACCESS  not-accessible
    STATUS      current
    DESCRIPTION
        "Name of the input configuration"
    ::= { ntcPAMAlarmStatsEntry 1 }

ntcPAMAlarmStatsNotActive        OBJECT-TYPE
    SYNTAX      NtcAlarmState
    MAX-ACCESS  read-only
    STATUS      current
    DESCRIPTION
        "This alarm is raised when a monitored PID is no longer active. This variable
        indicates the current status of the alarm."
    ::= { ntcPAMAlarmStatsEntry 2 }

ntcPAMAlNotActive                OBJECT-TYPE
    SYNTAX      NtcAlarmState
    MAX-ACCESS  read-only
    STATUS      current
    DESCRIPTION
        "This alarm is raised when a monitored PID is no longer active. This variable
        indicates the current status of the alarm."
    ::= { ntcPAMAlarms 2 }


--
--  Module Conformance
--

ntcPAMConfGrpV1Standard          OBJECT-GROUP
    OBJECTS    {
                   ntcPAMConfigRowStatus,
                   ntcPAMConfigEnable,
                   ntcPAMConfigPid,
                   ntcPAMAlarmStatsNotActive,
                   ntcPAMAlNotActive
               }
    STATUS      current
    DESCRIPTION
        "Managed objects that constitute version 1 of a system device with standard capabilities."
    ::= { ntcPAMConfGroup 1}

ntcPAMConfCompV1Standard         MODULE-COMPLIANCE
    STATUS      current
    DESCRIPTION
        "Compliance statement for Newtec device MIB implementations."
    MODULE  -- this module
    MANDATORY-GROUPS
                  {
                      ntcPAMConfGrpV1Standard
                  }
    ::= { ntcPAMConfCompliance  1 }


END
