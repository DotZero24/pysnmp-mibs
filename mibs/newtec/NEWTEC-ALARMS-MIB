NEWTEC-ALARMS-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF

    DisplayString
        FROM SNMPv2-TC

    ntcFunction
        FROM NEWTEC-MAIN-MIB;


--
--  Module Identification
--

ntcAlarms   MODULE-IDENTITY
    LAST-UPDATED "201309201000Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Alarm configuration MIB"

    REVISION  "201309201000Z"
    DESCRIPTION
        "General alarm columns added for M6100 R1.4"
    REVISION  "201309200800Z"
    DESCRIPTION
        "Initial release for M6100 R1.3"
    ::= { ntcFunction  5600 }


--
-- Top-Level Structure
--

-- ntcAlarms content

ntcAlmsObjects                   OBJECT-IDENTITY
    STATUS        current
    DESCRIPTION   "Container holding ntcAlmsObjects definitions."
    ::= { ntcAlarms 1 }

ntcAlmsConformance               OBJECT-IDENTITY
    STATUS        current
    DESCRIPTION   "Conformance requirements."
    ::= { ntcAlarms 2 }

-- ntcAlmsConformance content

ntcAlmsConfCompliance            OBJECT-IDENTITY
    STATUS        current
    DESCRIPTION   "Device compliance statements."
    ::= { ntcAlmsConformance 1 }

ntcAlmsConfGroup                 OBJECT-IDENTITY
    STATUS        current
    DESCRIPTION   "Groups used by device compliance statements."
    ::= { ntcAlmsConformance 2 }


--
-- Managed Objects
--

ntcAlmsConfigTable               OBJECT-TYPE
    SYNTAX      SEQUENCE OF NtcAlmsConfigEntry
    MAX-ACCESS  not-accessible
    STATUS      current
    DESCRIPTION
        "A table containing the ntcAlmsConfig"
    ::= { ntcAlmsObjects 1 }

ntcAlmsConfigEntry               OBJECT-TYPE
    SYNTAX      NtcAlmsConfigEntry
    MAX-ACCESS  not-accessible
    STATUS      current
    DESCRIPTION
        "A conceptual row of the ntcAlmsConfigTable."
    INDEX   { ntcAlmsConfigName  }
    ::= { ntcAlmsConfigTable 1 }

NtcAlmsConfigEntry               ::= SEQUENCE {
    ntcAlmsConfigName                DisplayString,
    ntcAlmsConfigMask                INTEGER,
    ntcAlmsConfigGeneralInterface    INTEGER,
    ntcAlmsConfigGeneralDevice       INTEGER
    }

ntcAlmsConfigName                OBJECT-TYPE
    SYNTAX      DisplayString (SIZE(0..30))
    MAX-ACCESS  not-accessible
    STATUS      current
    DESCRIPTION
        "Identifies the alarm entry (=row) of the alarms configuration table"
    ::= { ntcAlmsConfigEntry 1 }

ntcAlmsConfigMask                OBJECT-TYPE
    SYNTAX      INTEGER { off(0), on(1) }
    MAX-ACCESS  read-write
    STATUS      current
    DESCRIPTION
        "Mask or unmask the alarm. A masked alarm acts as if it is continuously in the
        'no-alarm' state."
    DEFVAL { off }
    ::= { ntcAlmsConfigEntry 2 }

ntcAlmsConfigGeneralInterface    OBJECT-TYPE
    SYNTAX      INTEGER { off(0), on(1) }
    MAX-ACCESS  read-write
    STATUS      current
    DESCRIPTION
        "Contribute to the General Interface alarm."
    DEFVAL { off }
    ::= { ntcAlmsConfigEntry 3 }

ntcAlmsConfigGeneralDevice       OBJECT-TYPE
    SYNTAX      INTEGER { off(0), on(1) }
    MAX-ACCESS  read-write
    STATUS      current
    DESCRIPTION
        "Contribute to the General Device alarm."
    DEFVAL { off }
    ::= { ntcAlmsConfigEntry 4 }


--
--  Module Conformance
--

ntcAlmsConfGrpV1Standard         OBJECT-GROUP
    OBJECTS    {
                   ntcAlmsConfigMask,
                   ntcAlmsConfigGeneralInterface,
                   ntcAlmsConfigGeneralDevice
               }
    STATUS      current
    DESCRIPTION
        "Managed objects that constitute version 1 of a system device with standard capabilities."
    ::= { ntcAlmsConfGroup 1}

ntcAlmsConfCompV1Standard        MODULE-COMPLIANCE
    STATUS      current
    DESCRIPTION
        "Compliance statement for Newtec device MIB implementations."
    MODULE  -- this module
    MANDATORY-GROUPS
                  {
                      ntcAlmsConfGrpV1Standard
                  }
    ::= { ntcAlmsConfCompliance  1 }


END
