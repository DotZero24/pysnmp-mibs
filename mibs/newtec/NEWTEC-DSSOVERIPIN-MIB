NEWTEC-DSSOVERIPIN-MIB DEFINITIONS ::= BEGIN

IMPORTS
    IpAddress,
    Unsigned32,
    Counter32,
    MODULE-IDENTITY,
    OBJECT-IDENTITY,
    OBJECT-TYPE
        FROM SNMPv2-SMI

    MODULE-COMPLIANCE,
    OBJECT-GROUP
        FROM SNMPv2-CONF

    NtcAlarmState,
    NtcEnable,
    NtcNetworkAddress
        FROM NEWTEC-TC-MIB

    DisplayString
        FROM SNMPv2-TC

    ntcFunction
        FROM NEWTEC-MAIN-MIB;


--
--  Module Identification
--

ntcDssOverIpIn   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DSSoIP input MIB containing definitions for DSS over IP input
        functionality."

    REVISION  "201707101200Z"
    DESCRIPTION
        "Descriptions updated with regex"
    REVISION  "201502190900Z"
    DESCRIPTION
        "initial version."
    ::= { ntcFunction  8700 }


--
-- Top-Level Structure
--

-- ntcDssOverIpIn content

ntcDssOIpInObjects               OBJECT-IDENTITY
    STATUS        current
    DESCRIPTION   "Container holding ntcDssOIpInObjects definitions."
    ::= { ntcDssOverIpIn 1 }

ntcDssOIpInConformance           OBJECT-IDENTITY
    STATUS        current
    DESCRIPTION   "Conformance requirements."
    ::= { ntcDssOverIpIn 2 }

-- ntcDssOIpInObjects content

ntcDssOIpInMonitor               OBJECT-IDENTITY
    STATUS        current
    DESCRIPTION   "Container holding ntcDssOIpInMonitor definitions."
    ::= { ntcDssOIpInObjects 10 }

ntcDssOIpInAlarm                 OBJECT-IDENTITY
    STATUS        current
    DESCRIPTION   "Container holding ntcDssOIpInAlarm definitions."
    ::= { ntcDssOIpInObjects 11 }

-- ntcDssOIpInConformance content

ntcDssOIpInConfCompliance        OBJECT-IDENTITY
    STATUS        current
    DESCRIPTION   "Device compliance statements."
    ::= { ntcDssOIpInConformance 1 }

ntcDssOIpInConfGroup             OBJECT-IDENTITY
    STATUS        current
    DESCRIPTION   "Groups used by device compliance statements."
    ::= { ntcDssOIpInConformance 2 }


--
-- Managed Objects
--

ntcDssOIpInEnable                OBJECT-TYPE
    SYNTAX      NtcEnable
    MAX-ACCESS  read-write
    STATUS      current
    DESCRIPTION
        "Enable or disable DSS over IP reception."
    DEFVAL { off }
    ::= { ntcDssOIpInObjects 1 }

ntcDssOIpInInputSelection        OBJECT-TYPE
    SYNTAX      INTEGER { none(1), data1(2), data2(3), data(4), any(5) }
    MAX-ACCESS  read-write
    STATUS      current
    DESCRIPTION
        "Select the input interface for the DSS over IP functionality."
    DEFVAL { none }
    ::= { ntcDssOIpInObjects 2 }

ntcDssOIpInDssEncapProtocol      OBJECT-TYPE
    SYNTAX      INTEGER { udp(0), rtp(1), rtpfec(2) }
    MAX-ACCESS  read-write
    STATUS      current
    DESCRIPTION
        "Encapsulation protocol used for the received DSS over IP functionality (UDP,
        RTP and RTP with FEC)."
    DEFVAL { udp }
    ::= { ntcDssOIpInObjects 3 }

ntcDssOIpInIpAddressType         OBJECT-TYPE
    SYNTAX      INTEGER { unicast(0), multicast(1) }
    MAX-ACCESS  read-write
    STATUS      current
    DESCRIPTION
        "Configuration of the IP address type for DSS over IP reception. (unicast or
        multicast)"
    DEFVAL { multicast }
    ::= { ntcDssOIpInObjects 4 }

ntcDssOIpInMulticastAddress      OBJECT-TYPE
    SYNTAX      IpAddress
    MAX-ACCESS  read-write
    STATUS      current
    DESCRIPTION
        "Define the multicast IP address used to receive the DSS over IP data
        functionality. Regular expression :
        (?-mix:^\d{1,3}\.\d{1,3}\.\d{1,3}\.\d{1,3}$)"
    DEFVAL { 'e0010001'h }
    ::= { ntcDssOIpInObjects 5 }

ntcDssOIpInUdpPort               OBJECT-TYPE
    SYNTAX      Unsigned32 (1..65535)
    MAX-ACCESS  read-write
    STATUS      current
    DESCRIPTION
        "Configure the UDP port on which the DSS over IP stream is received."
    DEFVAL { 56789 }
    ::= { ntcDssOIpInObjects 6 }

ntcDssOIpInMaxBufferDelay        OBJECT-TYPE
    SYNTAX      Unsigned32
    UNITS       "ms"
    MAX-ACCESS  read-write
    STATUS      current
    DESCRIPTION
        "The maximum delay introduced by the device to compensate jitter introduced by
        the IP network. This is only relevant for CBR traffic."
    DEFVAL { 250 }
    ::= { ntcDssOIpInObjects 7 }

ntcDssOIpInMulticastSourceA      OBJECT-TYPE
    SYNTAX      NtcNetworkAddress
    MAX-ACCESS  read-write
    STATUS      current
    DESCRIPTION
        "Multicast source Address. Regular expression :
        (?-mix:^\d{1,3}\.\d{1,3}\.\d{1,3}\.\d{1,3}$)"
    DEFVAL { "0.0.0.0" }
    ::= { ntcDssOIpInObjects 8 }

ntcDssOIpInMulticastSourceB      OBJECT-TYPE
    SYNTAX      NtcNetworkAddress
    MAX-ACCESS  read-write
    STATUS      current
    DESCRIPTION
        "Multicast source Address. Regular expression :
        (?-mix:^\d{1,3}\.\d{1,3}\.\d{1,3}\.\d{1,3}$)"
    DEFVAL { "0.0.0.0" }
    ::= { ntcDssOIpInObjects 9 }

ntcDssOIpInMonResetCounters      OBJECT-TYPE
    SYNTAX      INTEGER { counting(0), reset(1) }
    MAX-ACCESS  read-write
    STATUS      current
    DESCRIPTION
        "Reset the DSS over IP traffic and monitor counters."
    DEFVAL { counting }
    ::= { ntcDssOIpInMonitor 1 }

ntcDssOIpInMonInputDssBitRate    OBJECT-TYPE
    SYNTAX      Unsigned32
    UNITS       "bps"
    MAX-ACCESS  read-only
    STATUS      current
    DESCRIPTION
        "Displays the measured DSS over IP input DSS bit rate in bps."
    ::= { ntcDssOIpInMonitor 2 }

ntcDssOIpInMonBufferDelay        OBJECT-TYPE
    SYNTAX      Unsigned32
    UNITS       "ms"
    MAX-ACCESS  read-only
    STATUS      current
    DESCRIPTION
        "The delay introduced by the device to compensate the jitter introduced by the
        IP network. This is only relevant for CBR traffic."
    ::= { ntcDssOIpInMonitor 3 }

ntcDssOIpInMonMinBufferFilling   OBJECT-TYPE
    SYNTAX      Unsigned32
    UNITS       "ms"
    MAX-ACCESS  read-only
    STATUS      current
    DESCRIPTION
        "The measured minimum buffer filling level in the buffer which compensate the
        jitter of the IP network. This is only relevant for CBR traffic."
    ::= { ntcDssOIpInMonitor 4 }

ntcDssOIpInMonMaxBufferFilling   OBJECT-TYPE
    SYNTAX      Unsigned32
    UNITS       "ms"
    MAX-ACCESS  read-only
    STATUS      current
    DESCRIPTION
        "The measured maximum buffer filling level in the buffer which compensate the
        jitter of the IP network. This is only relevant for CBR traffic."
    ::= { ntcDssOIpInMonitor 5 }

ntcDssOIpInMonSourceInfo         OBJECT-TYPE
    SYNTAX      DisplayString (SIZE(0..32))
    MAX-ACCESS  read-only
    STATUS      current
    DESCRIPTION
        "Displays the IP address (and UDP port) of the source that is generating the
        DSS over IP traffic."
    ::= { ntcDssOIpInMonitor 6 }

ntcDssOIpInMonRtpFecScheme       OBJECT-TYPE
    SYNTAX      DisplayString (SIZE(0..32))
    MAX-ACCESS  read-only
    STATUS      current
    DESCRIPTION
        "Displays the type of Rtp FEC Scheme currently used (if any)."
    ::= { ntcDssOIpInMonitor 7 }

ntcDssOIpInMonRtpDropCount       OBJECT-TYPE
    SYNTAX      Counter32
    UNITS       "packets"
    MAX-ACCESS  read-only
    STATUS      current
    DESCRIPTION
        "Displays the number of dropped RTP packets. (This is only applicable when RTP
        is used.)"
    ::= { ntcDssOIpInMonitor 8 }

ntcDssOIpInMonRtpRepairCount     OBJECT-TYPE
    SYNTAX      Counter32
    UNITS       "packets"
    MAX-ACCESS  read-only
    STATUS      current
    DESCRIPTION
        "Displays the number of repaired RTP packets by using the received FEC
        information. (This is only applicable for RTP with FEC)"
    ::= { ntcDssOIpInMonitor 9 }

ntcDssOIpInMonRtpFecDropCount    OBJECT-TYPE
    SYNTAX      Counter32
    UNITS       "packets"
    MAX-ACCESS  read-only
    STATUS      current
    DESCRIPTION
        "Displays the number of dropped uncorrectable packets. (This is only applicable
        when RTP-FEC is used.)"
    ::= { ntcDssOIpInMonitor 10 }

ntcDssOIpInAlmNoInputData        OBJECT-TYPE
    SYNTAX      NtcAlarmState
    MAX-ACCESS  read-only
    STATUS      current
    DESCRIPTION
        "This alarm is raised when no input data is received for the DSS over IP
        functionality. This variable indicates the current status of the alarm."
    ::= { ntcDssOIpInAlarm 1 }

ntcDssOIpInAlmBufferOverflow     OBJECT-TYPE
    SYNTAX      NtcAlarmState
    MAX-ACCESS  read-only
    STATUS      current
    DESCRIPTION
        "This alarm is raised when the input data buffer of DSS over IP is full. This
        variable indicates the current status of the alarm."
    ::= { ntcDssOIpInAlarm 2 }

ntcDssOIpInAlmBufferUnflow       OBJECT-TYPE
    SYNTAX      NtcAlarmState
    MAX-ACCESS  read-only
    STATUS      current
    DESCRIPTION
        "This alarm is raised when the input data buffer is below the minimum value.
        This variable indicates the current status of the alarm."
    ::= { ntcDssOIpInAlarm 3 }

ntcDssOIpInAlmRtpNoSync          OBJECT-TYPE
    SYNTAX      NtcAlarmState
    MAX-ACCESS  read-only
    STATUS      current
    DESCRIPTION
        "This alarm is raised when no valid RTP input data is received. This variable
        indicates the current status of the alarm."
    ::= { ntcDssOIpInAlarm 4 }


--
--  Module Conformance
--

ntcDssOIpInConfGrpV1Standard     OBJECT-GROUP
    OBJECTS    {
                   ntcDssOIpInEnable,
                   ntcDssOIpInInputSelection,
                   ntcDssOIpInDssEncapProtocol,
                   ntcDssOIpInIpAddressType,
                   ntcDssOIpInMulticastAddress,
                   ntcDssOIpInUdpPort,
                   ntcDssOIpInMaxBufferDelay,
                   ntcDssOIpInMulticastSourceA,
                   ntcDssOIpInMulticastSourceB,
                   ntcDssOIpInMonResetCounters,
                   ntcDssOIpInMonInputDssBitRate,
                   ntcDssOIpInMonBufferDelay,
                   ntcDssOIpInMonMinBufferFilling,
                   ntcDssOIpInMonMaxBufferFilling,
                   ntcDssOIpInMonSourceInfo,
                   ntcDssOIpInMonRtpFecScheme,
                   ntcDssOIpInMonRtpDropCount,
                   ntcDssOIpInMonRtpRepairCount,
                   ntcDssOIpInMonRtpFecDropCount,
                   ntcDssOIpInAlmNoInputData,
                   ntcDssOIpInAlmBufferOverflow,
                   ntcDssOIpInAlmBufferUnflow,
                   ntcDssOIpInAlmRtpNoSync
               }
    STATUS      current
    DESCRIPTION
        "Managed objects that constitute version 1 of a system device with standard capabilities."
    ::= { ntcDssOIpInConfGroup 1}

ntcDssOIpInConfCompV1Standard    MODULE-COMPLIANCE
    STATUS      current
    DESCRIPTION
        "Compliance statement for Newtec device MIB implementations."
    MODULE  -- this module
    MANDATORY-GROUPS
                  {
                      ntcDssOIpInConfGrpV1Standard
                  }
    ::= { ntcDssOIpInConfCompliance  1 }


END
