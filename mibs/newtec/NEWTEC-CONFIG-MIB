NEWTEC-CONFIG-MIB DEFINITIONS ::= BEGIN

IMPORTS
    Unsigned32,
    MODULE-IDENTITY,
    OBJECT-IDENTITY,
    OBJECT-TYPE
        FROM SNMPv2-SMI

    MODULE-COMPLIANCE,
    OBJECT-GROUP
        FROM SNMPv2-CONF

    DisplayString,
    TruthValue
        FROM SNMPv2-TC

    ntcFunction
        FROM NEWTEC-MAIN-MIB;


--
--  Module Identification
--

ntcConfig   MODULE-IDENTITY
    LAST-UPDATED "201303271000Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing variables for the management of device
        configurations. These variables support functionality related to configuration
        lifecycle and usage."

    REVISION  "201303271000Z"
    DESCRIPTION
        "Release for M6100 R1.3"
    REVISION  "201206281200Z"
    DESCRIPTION
        "Release for M6100 R1.2"
    ::= { ntcFunction  1500 }


--
-- Top-Level Structure
--

-- ntcConfig content

ntcCfgObjects                    OBJECT-IDENTITY
    STATUS        current
    DESCRIPTION   "Container holding ntcCfgObjects definitions."
    ::= { ntcConfig 1 }

ntcCfgConformance                OBJECT-IDENTITY
    STATUS        current
    DESCRIPTION   "Conformance requirements."
    ::= { ntcConfig 2 }

-- ntcCfgConformance content

ntcCfgConfCompliance             OBJECT-IDENTITY
    STATUS        current
    DESCRIPTION   "Device compliance statements."
    ::= { ntcCfgConformance 1 }

ntcCfgConfGroup                  OBJECT-IDENTITY
    STATUS        current
    DESCRIPTION   "Groups used by device compliance statements."
    ::= { ntcCfgConformance 2 }


--
-- Managed Objects
--

ntcCfgConfigTable                OBJECT-TYPE
    SYNTAX      SEQUENCE OF NtcCfgConfigEntry
    MAX-ACCESS  not-accessible
    STATUS      current
    DESCRIPTION
        "This table contains the names of all persistent stored configuration files."
    ::= { ntcCfgObjects 1 }

ntcCfgConfigEntry                OBJECT-TYPE
    SYNTAX      NtcCfgConfigEntry
    MAX-ACCESS  not-accessible
    STATUS      current
    DESCRIPTION
        "A conceptual row of the ntcCfgConfigTable."
    INDEX   { ntcCfgConfigIndex  }
    ::= { ntcCfgConfigTable 1 }

NtcCfgConfigEntry                ::= SEQUENCE {
    ntcCfgConfigIndex    Unsigned32,
    ntcCfgConfigName     DisplayString
    }

ntcCfgConfigIndex                OBJECT-TYPE
    SYNTAX      Unsigned32 (1..2147483647)
    MAX-ACCESS  not-accessible
    STATUS      current
    DESCRIPTION
        "A unique key, greater than zero, for each configuration."
    ::= { ntcCfgConfigEntry 1 }

ntcCfgConfigName                 OBJECT-TYPE
    SYNTAX      DisplayString (SIZE(0..240))
    MAX-ACCESS  read-only
    STATUS      current
    DESCRIPTION
        "The name of an existing configuration."
    ::= { ntcCfgConfigEntry 2 }

ntcCfgActiveConfig               OBJECT-TYPE
    SYNTAX      DisplayString (SIZE(0..240))
    MAX-ACCESS  read-only
    STATUS      current
    DESCRIPTION
        "The name of the configuration that is currently active. It may contain unsaved
        changes that were made after initial loading. When saved, the name will change
        to reflect what it was saved as."
    ::= { ntcCfgObjects 2 }

ntcCfgUnsavedChanges             OBJECT-TYPE
    SYNTAX      TruthValue
    MAX-ACCESS  read-only
    STATUS      current
    DESCRIPTION
        "A boolean (flag) indicating the presence of unsaved changes in the current
        configuration. When 'false', all changes have been saved."
    ::= { ntcCfgObjects 3 }

ntcCfgBootConfig                 OBJECT-TYPE
    SYNTAX      DisplayString (SIZE(0..240))
    MAX-ACCESS  read-write
    STATUS      current
    DESCRIPTION
        "The name of the configuration that will be loaded when the device is going
        through its next boot sequence. Can be set to select a different available
        configuration."
    DEFVAL { "unknown" }
    ::= { ntcCfgObjects 4 }

ntcCfgLoadConfig                 OBJECT-TYPE
    SYNTAX      DisplayString (SIZE(0..240))
    MAX-ACCESS  read-write
    STATUS      current
    DESCRIPTION
        "A command that loads the configuration with the specified name. Reading this
        variable will always return an empty string."
    DEFVAL { "unknown" }
    ::= { ntcCfgObjects 5 }

ntcCfgSaveConfig                 OBJECT-TYPE
    SYNTAX      DisplayString (SIZE(0..240))
    MAX-ACCESS  read-write
    STATUS      current
    DESCRIPTION
        "A command that saves the active configuration with the name specified. Reading
        this variable will always return an empty string."
    DEFVAL { "unknown" }
    ::= { ntcCfgObjects 6 }

ntcCfgDeleteConfig               OBJECT-TYPE
    SYNTAX      DisplayString (SIZE(0..240))
    MAX-ACCESS  read-write
    STATUS      current
    DESCRIPTION
        "A command that deletes the configuration with the specified name. Reading this
        variable will always return an empty string."
    DEFVAL { "unknown" }
    ::= { ntcCfgObjects 7 }

ntcCfgLoadConfigNotForced        OBJECT-TYPE
    SYNTAX      DisplayString (SIZE(0..240))
    MAX-ACCESS  read-write
    STATUS      current
    DESCRIPTION
        "A command that loads the configuration with the specified name in a not forced
        way. Reading this variable will always return an empty string."
    DEFVAL { "unknown" }
    ::= { ntcCfgObjects 8 }


--
--  Module Conformance
--

ntcCfgConfGrpV1Standard          OBJECT-GROUP
    OBJECTS    {
                   ntcCfgConfigName,
                   ntcCfgActiveConfig,
                   ntcCfgUnsavedChanges,
                   ntcCfgBootConfig,
                   ntcCfgLoadConfig,
                   ntcCfgSaveConfig,
                   ntcCfgDeleteConfig,
                   ntcCfgLoadConfigNotForced
               }
    STATUS      current
    DESCRIPTION
        "Managed objects that constitute version 1 of a system device with standard capabilities."
    ::= { ntcCfgConfGroup 1}

ntcCfgConfCompV1Standard         MODULE-COMPLIANCE
    STATUS      current
    DESCRIPTION
        "Compliance statement for Newtec device MIB implementations."
    MODULE  -- this module
    MANDATORY-GROUPS
                  {
                      ntcCfgConfGrpV1Standard
                  }
    ::= { ntcCfgConfCompliance  1 }


END
