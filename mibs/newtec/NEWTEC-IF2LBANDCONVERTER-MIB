NEWTEC-IF2LBANDCONVERTER-MIB DEFINITIONS ::= BEGIN

IMPORTS
    MODULE-IDENTITY,
    OBJECT-IDENTITY,
    OBJECT-TYPE
        FROM SNMPv2-SMI

    MODULE-COMPLIANCE,
    OBJECT-GROUP
        FROM SNMPv2-CONF

    NtcAlarmState
        FROM NEWTEC-TC-MIB

    ntcFunction
        FROM NEWTEC-MAIN-MIB;


--
--  Module Identification
--

ntcIF2LbandConverter   MODULE-IDENTITY
    LAST-UPDATED "201206281200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular IF2Lband convertor MIB containing definitions for IF2Lband
        convertor functionality."

    REVISION  "201206281200Z"
    DESCRIPTION
        "Release for M6100 R1.2"
    ::= { ntcFunction  4600 }


--
-- Top-Level Structure
--

-- ntcIF2LbandConverter content

ntcIF2LConvObjects               OBJECT-IDENTITY
    STATUS        current
    DESCRIPTION   "Container holding ntcIF2LConvObjects definitions."
    ::= { ntcIF2LbandConverter 1 }

ntcIF2LConvConformance           OBJECT-IDENTITY
    STATUS        current
    DESCRIPTION   "Conformance requirements."
    ::= { ntcIF2LbandConverter 2 }

-- ntcIF2LConvObjects content

ntcIF2LConvAlarm                 OBJECT-IDENTITY
    STATUS        current
    DESCRIPTION   "Container holding ntcIF2LConvAlarm definitions."
    ::= { ntcIF2LConvObjects 1 }

-- ntcIF2LConvConformance content

ntcIF2LConvConfCompliance        OBJECT-IDENTITY
    STATUS        current
    DESCRIPTION   "Device compliance statements."
    ::= { ntcIF2LConvConformance 1 }

ntcIF2LConvConfGroup             OBJECT-IDENTITY
    STATUS        current
    DESCRIPTION   "Groups used by device compliance statements."
    ::= { ntcIF2LConvConformance 2 }


--
-- Managed Objects
--

ntcIF2LConvHardware              OBJECT-TYPE
    SYNTAX      NtcAlarmState
    MAX-ACCESS  read-only
    STATUS      current
    DESCRIPTION
        "This alarm is raised when the converter is not working correctly due to
        hardware failures on the converter module This variable indicates the current
        status of the alarm."
    ::= { ntcIF2LConvAlarm 1 }

ntcIF2LConvCommunication         OBJECT-TYPE
    SYNTAX      NtcAlarmState
    MAX-ACCESS  read-only
    STATUS      current
    DESCRIPTION
        "This alarm is raised when the converter is not working correctly due to
        communication failures on the converter module This variable indicates the
        current status of the alarm."
    ::= { ntcIF2LConvAlarm 2 }


--
--  Module Conformance
--

ntcIF2LConvConfGrpV1Standard     OBJECT-GROUP
    OBJECTS    {
                   ntcIF2LConvHardware,
                   ntcIF2LConvCommunication
               }
    STATUS      current
    DESCRIPTION
        "Managed objects that constitute version 1 of a system device with standard capabilities."
    ::= { ntcIF2LConvConfGroup 1}

ntcIF2LConvConfCompV1Standard    MODULE-COMPLIANCE
    STATUS      current
    DESCRIPTION
        "Compliance statement for Newtec device MIB implementations."
    MODULE  -- this module
    MANDATORY-GROUPS
                  {
                      ntcIF2LConvConfGrpV1Standard
                  }
    ::= { ntcIF2LConvConfCompliance  1 }


END
