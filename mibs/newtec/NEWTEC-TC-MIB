NEWTEC-TC-MIB DEFINITIONS ::= BEGIN

IMPORTS
    Unsigned32,
    Counter32,
    MODULE-IDENTITY
        FROM SNMPv2-SMI

    TEXTUAL-CONVENTION
        FROM SNMPv2-TC

    ntcGeneric
        FROM NEWTEC-MAIN-MIB;


--
--  Module Identification
--

ntcGenTextualConvention   MODULE-IDENTITY
    LAST-UPDATED "201206281200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec MIB generic textual conventions."

    REVISION  "201206281200Z"
    DESCRIPTION
        "Release for M6100 R1.2"
    ::= { ntcGeneric  1 }


--
-- Textual conventions
--

NtcAlarmState                    ::= TEXTUAL-CONVENTION
    STATUS      current
    DESCRIPTION
        "The current state of an alarm."
    SYNTAX      INTEGER
                {
                    off(0),
                    on(1)
                }

NtcEnable                        ::= TEXTUAL-CONVENTION
    STATUS      current
    DESCRIPTION
        "The current activation state of an object."
    SYNTAX      INTEGER
                {
                    off(0),
                    on(1)
                }

NtcNetworkAddress                ::= TEXTUAL-CONVENTION
    DISPLAY-HINT  "7a"
    STATUS      current
    DESCRIPTION
        "A network address is an IPv4 address with an optional prefix (net mask)."
    SYNTAX      OCTET STRING (SIZE(7..18))

NtcPid                           ::= TEXTUAL-CONVENTION
    DISPLAY-HINT  "d"
    STATUS      current
    DESCRIPTION
        "The program ID value in a DVB stream."
    SYNTAX      Unsigned32 (0..65535)

NtcSystemTime                    ::= TEXTUAL-CONVENTION
    DISPLAY-HINT  "d"
    STATUS      current
    DESCRIPTION
        "The number of elapsed seconds since midnight GMT on 1st January, 1970."
    SYNTAX      Counter32


END
