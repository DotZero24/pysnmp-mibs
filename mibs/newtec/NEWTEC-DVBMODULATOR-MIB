NEWTEC-DVBMODULATOR-MIB DEFINITIONS ::= BEGIN

IMPORTS
    Unsigned32,
    Integer32,
    Counter32,
    MODULE-IDENTITY,
    OBJECT-IDENTITY,
    OBJECT-TYPE
        FROM SNMPv2-SMI

    MODULE-COMPLIANCE,
    OBJECT-GROUP
        FROM SNMPv2-CONF

    Float32TC
        FROM FLOAT-TC-MIB

    NtcAlarmState,
    NtcEnable
        FROM NEWTEC-TC-MIB

    DisplayString
        FROM SNMPv2-TC

    ntcFunction
        FROM NEWTEC-MAIN-MIB;


--
--  Module Identification
--

ntcDvbModulator   MODULE-IDENTITY
    LAST-UPDATED "201707101200Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DVB modulator MIB containing definitions for DVB-S and DVB-S2
        modulator functionality."

    REVISION  "201707101200Z"
    DESCRIPTION
        "2% rolloff added and descriptions updated"
    REVISION  "201612051200Z"
    DESCRIPTION
        "ntcDvbModExtCableLoss added"
    REVISION  "201605170900Z"
    DESCRIPTION
        "Internal converter M&C added"
    REVISION  "201509251100Z"
    DESCRIPTION
        "ntcDvbModCarrierModulation enumerations extended with dvbcid"
    REVISION  "201502190900Z"
    DESCRIPTION
        "nlpc support added"
    REVISION  "201501300800Z"
    DESCRIPTION
        "ntcDvbModStreamMode added"
    REVISION  "201409090900Z"
    DESCRIPTION
        "Cosmetic changes in string modifiers"
    REVISION  "201409041200Z"
    DESCRIPTION
        "DSNGProfiles added and some descriptions adapted."
    REVISION  "201407150800Z"
    DESCRIPTION
        "DVB-S2X support"
    REVISION  "201402031200Z"
    DESCRIPTION
        "Equalink extensions, added transponder operation mode. Redundancy behavior of
        connectors in standby mode."
    REVISION  "201310281000Z"
    DESCRIPTION
        "Equalink applicability parameters exposed"
    REVISION  "201307050600Z"
    DESCRIPTION
        "Extra modulation schemes added"
    REVISION  "201305220600Z"
    DESCRIPTION
        "Release for MDM6000 R1.1"
    REVISION  "201303271000Z"
    DESCRIPTION
        "Release for M6100 R1.3"
    REVISION  "201301081200Z"
    DESCRIPTION
        "Release for MDM6000 R1.0"
    REVISION  "201206281200Z"
    DESCRIPTION
        "Release for M6100 R1.2"
    ::= { ntcFunction  1000 }


--
-- Top-Level Structure
--

-- ntcDvbModulator content

ntcDvbModObjects                 OBJECT-IDENTITY
    STATUS        current
    DESCRIPTION   "Container holding ntcDvbModObjects definitions."
    ::= { ntcDvbModulator 1 }

ntcDvbModConformance             OBJECT-IDENTITY
    STATUS        current
    DESCRIPTION   "Conformance requirements."
    ::= { ntcDvbModulator 2 }

-- ntcDvbModObjects content

ntcDvbModDvbs2Acm                OBJECT-IDENTITY
    STATUS        current
    DESCRIPTION   "Container holding ntcDvbModDvbs2Acm definitions."
    ::= { ntcDvbModObjects 15 }

ntcDvbModDvbs2                   OBJECT-IDENTITY
    STATUS        current
    DESCRIPTION   "Container holding ntcDvbModDvbs2 definitions."
    ::= { ntcDvbModObjects 16 }

ntcDvbModDvbs                    OBJECT-IDENTITY
    STATUS        current
    DESCRIPTION   "Container holding ntcDvbModDvbs definitions."
    ::= { ntcDvbModObjects 17 }

ntcDvbModEqualink                OBJECT-IDENTITY
    STATUS        current
    DESCRIPTION   "Container holding ntcDvbModEqualink definitions."
    ::= { ntcDvbModObjects 18 }

ntcDvbModAlarm                   OBJECT-IDENTITY
    STATUS        current
    DESCRIPTION   "Container holding ntcDvbModAlarm definitions."
    ::= { ntcDvbModObjects 19 }

ntcDvbModRfCid                   OBJECT-IDENTITY
    STATUS        current
    DESCRIPTION   "Container holding ntcDvbModRfCid definitions."
    ::= { ntcDvbModObjects 21 }

ntcDvbModDcBuc                   OBJECT-IDENTITY
    STATUS        current
    DESCRIPTION   "Container holding ntcDvbModDcBuc definitions."
    ::= { ntcDvbModObjects 22 }

ntcDvbModS2Ext                   OBJECT-IDENTITY
    STATUS        current
    DESCRIPTION   "Container holding ntcDvbModS2Ext definitions."
    ::= { ntcDvbModObjects 29 }

ntcDvbModTurbo                   OBJECT-IDENTITY
    STATUS        current
    DESCRIPTION   "Container holding ntcDvbModTurbo definitions."
    ::= { ntcDvbModObjects 30 }

ntcDvbModAmcDvbs                 OBJECT-IDENTITY
    STATUS        current
    DESCRIPTION   "Container holding ntcDvbModAmcDvbs definitions."
    ::= { ntcDvbModObjects 31 }

ntcDvbModAmcNbc                  OBJECT-IDENTITY
    STATUS        current
    DESCRIPTION   "Container holding ntcDvbModAmcNbc definitions."
    ::= { ntcDvbModObjects 32 }

ntcDvbModLinkOpt                 OBJECT-IDENTITY
    STATUS        current
    DESCRIPTION   "Container holding ntcDvbModLinkOpt definitions."
    ::= { ntcDvbModObjects 35 }

ntcDvbModDSNGProfiles            OBJECT-IDENTITY
    STATUS        current
    DESCRIPTION   "Container holding ntcDvbModDSNGProfiles definitions."
    ::= { ntcDvbModObjects 38 }

ntcDvbModAmcDl                   OBJECT-IDENTITY
    STATUS        current
    DESCRIPTION   "Container holding ntcDvbModAmcDl definitions."
    ::= { ntcDvbModObjects 40 }

ntcDvbModExtConv                 OBJECT-IDENTITY
    STATUS        current
    DESCRIPTION   "Container holding ntcDvbModExtConv definitions."
    ::= { ntcDvbModObjects 48 }

ntcDvbModConv                    OBJECT-IDENTITY
    STATUS        current
    DESCRIPTION   "Container holding ntcDvbModConv definitions."
    ::= { ntcDvbModObjects 49 }

-- ntcDvbModEqualink content

ntcDvbModEqlnkLinear             OBJECT-IDENTITY
    STATUS        current
    DESCRIPTION   "Container holding ntcDvbModEqlnkLinear definitions."
    ::= { ntcDvbModEqualink 1 }

ntcDvbModEqlnkNonlinear          OBJECT-IDENTITY
    STATUS        current
    DESCRIPTION   "Container holding ntcDvbModEqlnkNonlinear definitions."
    ::= { ntcDvbModEqualink 2 }

-- ntcDvbModEqlnkLinear content

ntcDvbModEqlnkLinConf            OBJECT-IDENTITY
    STATUS        current
    DESCRIPTION   "Container holding ntcDvbModEqlnkLinConf definitions."
    ::= { ntcDvbModEqlnkLinear 4 }

-- ntcDvbModEqlnkLinConf content

ntcDvbModEqlnkLinApp             OBJECT-IDENTITY
    STATUS        current
    DESCRIPTION   "Container holding ntcDvbModEqlnkLinApp definitions."
    ::= { ntcDvbModEqlnkLinConf 1 }

-- ntcDvbModEqlnkNonlinear content

ntcDvbModEqlnkNonlinConf         OBJECT-IDENTITY
    STATUS        current
    DESCRIPTION   "Container holding ntcDvbModEqlnkNonlinConf definitions."
    ::= { ntcDvbModEqlnkNonlinear 4 }

-- ntcDvbModEqlnkNonlinConf content

ntcDvbModEqlnkNonlinApp          OBJECT-IDENTITY
    STATUS        current
    DESCRIPTION   "Container holding ntcDvbModEqlnkNonlinApp definitions."
    ::= { ntcDvbModEqlnkNonlinConf 1 }

-- ntcDvbModConformance content

ntcDvbModConfCompliance          OBJECT-IDENTITY
    STATUS        current
    DESCRIPTION   "Device compliance statements."
    ::= { ntcDvbModConformance 1 }

ntcDvbModConfGroup               OBJECT-IDENTITY
    STATUS        current
    DESCRIPTION   "Groups used by device compliance statements."
    ::= { ntcDvbModConformance 2 }


--
-- Managed Objects
--

ntcDvbModMode                    OBJECT-TYPE
    SYNTAX      INTEGER { dvbs(0), dvbs2(1), s2ext(3), turbo(4), amcdvbs(5), amcnbc(6), dvbs2x(7), amcdl(8) }
    MAX-ACCESS  read-write
    STATUS      current
    DESCRIPTION
        "The modulation standard defines the operating mode of the modulator.
        - DVB-S2 : compatible with EN302307. Single Stream Transport Stream
        Broadcasting Applications
        - DVB-S : compatible with EN300421 for QPSK (DVB-S) and EN301210 for 8-PSK and
        16QAM (DVB-DSNG).
        - S2 Extensions : Newtec proprietary DVB-S2 extensions"
    DEFVAL { dvbs2 }
    ::= { ntcDvbModObjects 1 }

ntcDvbModTransmit                OBJECT-TYPE
    SYNTAX      NtcEnable
    MAX-ACCESS  read-write
    STATUS      current
    DESCRIPTION
        "Enable or disable the modulator output transmit signal. When it is enabled the
        actual output can still be switched-off upon detection of e.g. general device
        alarm of the modulator."
    DEFVAL { off }
    ::= { ntcDvbModObjects 2 }

ntcDvbModTransmitState           OBJECT-TYPE
    SYNTAX      INTEGER { off(0), on(1) }
    MAX-ACCESS  read-only
    STATUS      current
    DESCRIPTION
        "Current transmit status of the modulator (on or off). The actual transmit
        status is determined by the transmit configuration parameter and by other
        events. Note that the transmit is also automatically switched-off upon
        detection of a general device alarm of the modulator."
    ::= { ntcDvbModObjects 3 }

ntcDvbModTxCtrlGenDeviceAlarm    OBJECT-TYPE
    SYNTAX      INTEGER { disableTransmit(0), noImpact(1) }
    MAX-ACCESS  read-write
    STATUS      current
    DESCRIPTION
        "Configure the impact of a General Device alarm on the Modulator Transmit."
    DEFVAL { disableTransmit }
    ::= { ntcDvbModObjects 4 }

ntcDvbModTxCtrlGenInterfaceAlarm OBJECT-TYPE
    SYNTAX      INTEGER { disableTransmit(0), noImpact(1) }
    MAX-ACCESS  read-write
    STATUS      current
    DESCRIPTION
        "Configure the impact of a General Interface Alarm on the Modulator Transmit"
    DEFVAL { noImpact }
    ::= { ntcDvbModObjects 5 }

ntcDvbModAllowChangesWhileTxOn   OBJECT-TYPE
    SYNTAX      NtcEnable
    MAX-ACCESS  read-write
    STATUS      current
    DESCRIPTION
        "This field allows you to choose if the main modulation parameters can be
        altered while the transmit is on."
    DEFVAL { off }
    ::= { ntcDvbModObjects 36 }

ntcDvbModStandbyRedundancyState  OBJECT-TYPE
    SYNTAX      INTEGER { standby(0), active(1) }
    MAX-ACCESS  read-write
    STATUS      current
    DESCRIPTION
        "Default connector redundancy state when the Device Redundancy is in standby
        mode."
    DEFVAL { standby }
    ::= { ntcDvbModObjects 37 }

ntcDvbModOutputFrequency         OBJECT-TYPE
    SYNTAX      Unsigned32
    UNITS       "Hz"
    MAX-ACCESS  read-write
    STATUS      current
    DESCRIPTION
        "Modulator output frequency setting. Current devices support a frequency range
        of 50..180 Mhz or 960..2150 MHz."
    DEFVAL { 2000000000 }
    ::= { ntcDvbModObjects 6 }

ntcDvbModRollOff                 OBJECT-TYPE
    SYNTAX      INTEGER { rolloff2(0), rolloff5(1), rolloff10(2), rolloff15(3), rolloff20(4), rolloff25(5), rolloff35(6) }
    MAX-ACCESS  read-write
    STATUS      current
    DESCRIPTION
        "The transmit filter Roll-off factor setting determines the output spectrum
        excess bandwidth by controlling the RCRO (Root Cosine Roll-off) factor of the
        matched filter at the modulator output. The lower the Roll-off factor the
        higher the throughput. Note that increasing the throughput (higher symbolrate)
        requires more power from the satellite or will result in a lower
        carrier-to-noise. All Roll-off factor settings can also be applied for DVB-S."
    DEFVAL { rolloff20 }
    ::= { ntcDvbModObjects 7 }

ntcDvbModOccupiedBandWidth       OBJECT-TYPE
    SYNTAX      Unsigned32
    UNITS       "Hz"
    MAX-ACCESS  read-only
    STATUS      current
    DESCRIPTION
        "The '-26 dB' bandwidth of the signal. This is calculated as the symbol rate
        multiplied with (1 + a) with a = the selected roll-off factor."
    ::= { ntcDvbModObjects 8 }

ntcDvbModOutputBand              OBJECT-TYPE
    SYNTAX      INTEGER { lBand(0), ifBand(1) }
    MAX-ACCESS  read-only
    STATUS      current
    DESCRIPTION
        "Indicates the used output frequency band: IF band or L band."
    ::= { ntcDvbModObjects 9 }

ntcDvbModSpectrumPolarity        OBJECT-TYPE
    SYNTAX      INTEGER { directSpectrum(1), invertedSpectrum(2) }
    MAX-ACCESS  read-write
    STATUS      current
    DESCRIPTION
        "Transmit spectrum polarity selection. The spectrum at IFL and at RF is coupled
        by the installed upconverter module. This can be deduced from the frequency
        conversion formula. If the L-band frequency is subtracted from the LO (Local
        Oscillator), then the spectrum is inverted in the converter module. If a
        direct spectrum is required in this case, the spectrum must also be inverted
        at IFL."
    DEFVAL { directSpectrum }
    ::= { ntcDvbModObjects 10 }

ntcDvbModOutputLevel             OBJECT-TYPE
    SYNTAX      Integer32 (-400..100)
    UNITS       "dBm"
    MAX-ACCESS  read-write
    STATUS      current
    DESCRIPTION
        "Modulator output level setting in dBm. Adjustable in steps of 0.1 dBm. Float
        represented as integer is scaled by a factor of 10. i.e. a value of '-103'
        means '-10.3' dBm Note that the range normally starts from
        -35.0, there is one exceptional product that allows it to start from
        -40.0 in a very special use case."
    DEFVAL { -150 }
    ::= { ntcDvbModObjects 11 }

ntcDvbModClockOutput             OBJECT-TYPE
    SYNTAX      INTEGER { off(0), e10Mhz(1) }
    MAX-ACCESS  read-write
    STATUS      current
    DESCRIPTION
        "Enables or disables the transmission of a 10MHz clock signal on the RF output
        cable."
    DEFVAL { off }
    ::= { ntcDvbModObjects 12 }

ntcDvbModCarrierModulation       OBJECT-TYPE
    SYNTAX      INTEGER { purecarrier(0), on(1), testclkdiv4(3), testclkdiv8(4), testclkdiv16(5), dvbcid(6) }
    MAX-ACCESS  read-write
    STATUS      current
    DESCRIPTION
        "Carrier modulation selection :
        - modulation on: Operational modulated carrier signal
        - pure carrier: unmodulated output signal
        - 'test modulation CLK/n': Carrier modulated by a rotating vector with a
        period of baudrate/n, results in a single spectral line at +clock/n offset
        from carrier. This mode is used for calibration and verification of the
        spectrum polarity."
    DEFVAL { on }
    ::= { ntcDvbModObjects 13 }

ntcDvbModAmplSlopeEqualizer      OBJECT-TYPE
    SYNTAX      Integer32 (-7..7)
    MAX-ACCESS  read-write
    STATUS      current
    DESCRIPTION
        "Configuration of the amplitude slope equalizer. An amplitude slope in the
        up-converter or in the high power amplifier can be compensated by using this
        equalizer which has a maximum range of +- 2 dB/50 MHz. This is done by chaning
        the corresponding parameter in steps of 1 unit, in the range of
        -7 to +7."
    DEFVAL { 0 }
    ::= { ntcDvbModObjects 14 }

ntcDvbModDvbs2AcmSymbolRate      OBJECT-TYPE
    SYNTAX      Unsigned32
    UNITS       "baud"
    MAX-ACCESS  read-write
    STATUS      deprecated
    DESCRIPTION
        "Define the required symbol rate in baud."
    DEFVAL { 10000000 }
    ::= { ntcDvbModDvbs2Acm 1 }

ntcDvbModDvbs2Isi                OBJECT-TYPE
    SYNTAX      Unsigned32 (0..255)
    MAX-ACCESS  read-write
    STATUS      deprecated
    DESCRIPTION
        "The DVB-S2 Input Stream Identifier (ISI) is present in the second byte
        position of the MATYPE field in the baseband header of a DVB-S2 baseband
        frame. It is a single byte identifying the encapsulated stream in case of
        Multiple Input Streams (MIS)."
    DEFVAL { 171 }
    ::= { ntcDvbModDvbs2 1 }

ntcDvbModDvbs2FrameType          OBJECT-TYPE
    SYNTAX      INTEGER { short(0), normal(1) }
    MAX-ACCESS  read-write
    STATUS      current
    DESCRIPTION
        "Dvb-S2 defines 2 FEC-frame types :
        - normal: FECframes of 64800 bits or 8100 bytes
        - short: FECframes of 16200 bits or 2025 bytes Short frames are used when
        working with low symbol rates or with latency sensitive applications."
    DEFVAL { normal }
    ::= { ntcDvbModDvbs2 2 }

ntcDvbModDvbs2ModCod             OBJECT-TYPE
    SYNTAX      INTEGER { qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk1345(29), qpsk920(30), qpsk1120(31), e8apsk59l(32), e8apsk2645l(33), e8psk2336(34), e8psk2536(35), e8psk1318(36), e16apsk12l(37), e16apsk815l(38), e16apsk59l(39), e16apsk2645(40), e16apsk35(41), e16apsk35l(42), e16apsk2845(43), e16apsk2336(44), e16apsk23l(45), e16apsk2536(46), e16apsk1318(47), e16apsk79(48), e16apsk7790(49), e32apsk23l(50), e32apsk3245(51), e32apsk1115(52), e32apsk79(53), e64apsk3245l(54), e64apsk1115(55), e64apsk79(56), e64apsk45(57), e64apsk56(58), e128apsk34(59), e128apsk79(60), e256apsk2945l(61), e256apsk23l(62), e256apsk3145l(63), e256apsk3245(64), e256apsk1115l(65), e256apsk34(66), qpsk1145(67), qpsk415(68), qpsk1445(69), qpsk715(70), qpsk815(71), qpsk3245(72), e8psk715(73), e8psk815(74), e8psk2645(75), e8psk3245(76), e16apsk715(77), e16apsk815(78), e16apsk3245(79), e32apsk23(80) }
    MAX-ACCESS  read-write
    STATUS      current
    DESCRIPTION
        "The selection of modulation type and the FEC rate."
    DEFVAL { qpsk34 }
    ::= { ntcDvbModDvbs2 3 }

ntcDvbModDvbs2Pilots             OBJECT-TYPE
    SYNTAX      NtcEnable
    MAX-ACCESS  read-write
    STATUS      current
    DESCRIPTION
        "Dvb-S2 Physical Layer Pilot insertion. When enabled, every 16 slots (of 90
        symbols) the modulator will insert 36 unmodulated symbols to aid in receiver
        synchronization. Set Pilots on in the following cases:
        - ACM model
        - High amount of phase noise is present
        - At low data rates
        - When distortion is present
        - When using one of the following MODCODs 8-PSK 3/5 and 2/3, 16-APSK and
        32-APSK (due to MODCOD structure)."
    DEFVAL { off }
    ::= { ntcDvbModDvbs2 4 }

ntcDvbModDvbs2RatePriority       OBJECT-TYPE
    SYNTAX      INTEGER { symbolrate(0), bitrate(1) }
    MAX-ACCESS  read-write
    STATUS      deprecated
    DESCRIPTION
        "Select the rate mode (symbol rate or bit rate). The selected rate will be kept
        constant when other parameters have impact a the modulator rate. Only the
        selected rate can be changed explicitly by the operator."
    DEFVAL { symbolrate }
    ::= { ntcDvbModDvbs2 5 }

ntcDvbModDvbs2SymbolRate         OBJECT-TYPE
    SYNTAX      Unsigned32
    UNITS       "baud"
    MAX-ACCESS  read-write
    STATUS      deprecated
    DESCRIPTION
        "Define the required symbol rate in baud."
    DEFVAL { 10000000 }
    ::= { ntcDvbModDvbs2 6 }

ntcDvbModDvbs2BitRate            OBJECT-TYPE
    SYNTAX      Unsigned32
    UNITS       "bps"
    MAX-ACCESS  read-write
    STATUS      deprecated
    DESCRIPTION
        "Define the required bit rate of the modulator. Current devices support a range
        of 50000 to 250000000 bps."
    DEFVAL { 5000000 }
    ::= { ntcDvbModDvbs2 7 }

ntcDvbModDvbs2MeasuredPktCount   OBJECT-TYPE
    SYNTAX      Counter32
    UNITS       "packets"
    MAX-ACCESS  read-only
    STATUS      deprecated
    DESCRIPTION
        "Measured TS packet count of the modulator."
    ::= { ntcDvbModDvbs2 8 }

ntcDvbModDvbs2MeasuredBitRate    OBJECT-TYPE
    SYNTAX      Unsigned32
    UNITS       "bps"
    MAX-ACCESS  read-only
    STATUS      deprecated
    DESCRIPTION
        "Measured bitrate of the modulator."
    ::= { ntcDvbModDvbs2 9 }

ntcDvbModDvbs2PhyLayerEfficiency OBJECT-TYPE
    SYNTAX      Integer32 (0..10000)
    UNITS       "%"
    MAX-ACCESS  read-only
    STATUS      current
    DESCRIPTION
        "The measured physical layer efficiency, equal to the percentage of non-dummy
        physical layer frames. Float represented as integer is scaled by a factor of
        100. i.e. a value of 5000 in SNMP means a physical layer efficiency of 50.00 %"
    ::= { ntcDvbModDvbs2 10 }

ntcDvbModDvbs2BbLayerEfficiency  OBJECT-TYPE
    SYNTAX      Integer32 (0..10000)
    UNITS       "%"
    MAX-ACCESS  read-only
    STATUS      current
    DESCRIPTION
        "The measured baseband layer efficiency, equal to the percentage user data in
        tbe baseband frames. Float represented as integer is scaled by a factor of
        100. i.e. a value of 5000 in SNMP means a baseband layer efficiency of 50.00 %"
    ::= { ntcDvbModDvbs2 11 }

ntcDvbModDvbs2DumPlScramblMode   OBJECT-TYPE
    SYNTAX      INTEGER { dvbs2standard(0), continuous(1) }
    MAX-ACCESS  read-write
    STATUS      current
    DESCRIPTION
        "The dummy physical layer scrambler mode can be set to continuous, to achieve
        more randomness in the carrier data as required for bandwidth cancellation."
    DEFVAL { dvbs2standard }
    ::= { ntcDvbModDvbs2 12 }

ntcDvbModDvbs2PlScrambSig        OBJECT-TYPE
    SYNTAX      Unsigned32
    MAX-ACCESS  read-write
    STATUS      current
    DESCRIPTION
        "The physical layer scrambler signature."
    DEFVAL { 0 }
    ::= { ntcDvbModDvbs2 13 }

ntcDvbModDvbs2Reset              OBJECT-TYPE
    SYNTAX      INTEGER { counting(0), reset(1) }
    MAX-ACCESS  read-write
    STATUS      deprecated
    DESCRIPTION
        "Reset the modulator monitoring counters."
    DEFVAL { counting }
    ::= { ntcDvbModDvbs2 14 }

ntcDvbModDvbs2RollOffSignalling  OBJECT-TYPE
    SYNTAX      INTEGER { standard(0), reserved(1) }
    MAX-ACCESS  read-write
    STATUS      current
    DESCRIPTION
        "When a Roll-off <20% is configured, this setting is used to put the Roll-off
        bits in the baseband header to reserved (11) or to a standardized value. Some
        receivers accept only specific Roll-off bits."
    DEFVAL { standard }
    ::= { ntcDvbModDvbs2 15 }

ntcDvbModDvbsModCod              OBJECT-TYPE
    SYNTAX      INTEGER { qpsk12(1), qpsk23(2), qpsk34(3), qpsk56(4), qpsk67(5), qpsk78(6), e8psk23(7), e8psk56(8), e8psk89(9), e16qam34(10), e16qam78(11) }
    MAX-ACCESS  read-write
    STATUS      current
    DESCRIPTION
        "The selection of the FEC code-rate and modulation scheme supported by DVB-S"
    DEFVAL { qpsk34 }
    ::= { ntcDvbModDvbs 1 }

ntcDvbModDvbsRatePriority        OBJECT-TYPE
    SYNTAX      INTEGER { symbolrate(0), bitrate(1) }
    MAX-ACCESS  read-write
    STATUS      deprecated
    DESCRIPTION
        "Select the rate mode (symbol rate or bit rate). The selected rate will be kept
        constant when other parameters have impact a the modulator rate. Only the
        selected rate can be changed explicitly by the operator."
    DEFVAL { symbolrate }
    ::= { ntcDvbModDvbs 2 }

ntcDvbModDvbsSymbolRate          OBJECT-TYPE
    SYNTAX      Unsigned32
    UNITS       "baud"
    MAX-ACCESS  read-write
    STATUS      deprecated
    DESCRIPTION
        "Define the required symbol rate in baud."
    DEFVAL { 10000000 }
    ::= { ntcDvbModDvbs 3 }

ntcDvbModDvbsBitRate             OBJECT-TYPE
    SYNTAX      Unsigned32
    UNITS       "bps"
    MAX-ACCESS  read-write
    STATUS      deprecated
    DESCRIPTION
        "Define the required bit rate of the modulator. Current devices support a range
        of 50000 to 250000000 bps."
    DEFVAL { 5000000 }
    ::= { ntcDvbModDvbs 4 }

ntcDvbModDvbsMeasuredPktCount    OBJECT-TYPE
    SYNTAX      Counter32
    UNITS       "packets"
    MAX-ACCESS  read-only
    STATUS      deprecated
    DESCRIPTION
        "Measured TS packet count of the modulator."
    ::= { ntcDvbModDvbs 5 }

ntcDvbModDvbsMeasuredBitRate     OBJECT-TYPE
    SYNTAX      Unsigned32
    UNITS       "bps"
    MAX-ACCESS  read-only
    STATUS      deprecated
    DESCRIPTION
        "Measured bitrate of the modulator."
    ::= { ntcDvbModDvbs 6 }

ntcDvbModDvbsReset               OBJECT-TYPE
    SYNTAX      INTEGER { counting(0), reset(1) }
    MAX-ACCESS  read-write
    STATUS      deprecated
    DESCRIPTION
        "Reset the modulator monitoring counters."
    DEFVAL { counting }
    ::= { ntcDvbModDvbs 7 }

ntcDvbModEqlnkLinMode            OBJECT-TYPE
    SYNTAX      NtcEnable
    MAX-ACCESS  read-write
    STATUS      current
    DESCRIPTION
        "Enable or disable linear equalink. Enable this component to compensate
        amplitude distorions and group delay distortions. This improves the
        transponder throughput, the link performance and re-lock time after fading."
    DEFVAL { off }
    ::= { ntcDvbModEqlnkLinear 1 }

ntcDvbModEqlnkLinState           OBJECT-TYPE
    SYNTAX      INTEGER { off(0), on(1) }
    MAX-ACCESS  read-only
    STATUS      current
    DESCRIPTION
        "Displays the current linear predistortion status. The actual linear
        predistortion status is determined by the configuration parameter but is also
        automatically switched-off when a the operator request the transmission of a
        pure carrier."
    ::= { ntcDvbModEqlnkLinear 2 }

ntcDvbModEqlnkLinInfo            OBJECT-TYPE
    SYNTAX      DisplayString (SIZE(0..250))
    MAX-ACCESS  read-only
    STATUS      current
    DESCRIPTION
        "Detailed info for linear equalink."
    ::= { ntcDvbModEqlnkLinear 3 }

ntcDvbModEqlnkLinAppOutFreq      OBJECT-TYPE
    SYNTAX      Unsigned32
    UNITS       "Hz"
    MAX-ACCESS  read-write
    STATUS      current
    DESCRIPTION
        "Modulator output frequency that was used during the calibration."
    DEFVAL { 1450000000 }
    ::= { ntcDvbModEqlnkLinApp 1 }

ntcDvbModEqlnkLinAppRollOff      OBJECT-TYPE
    SYNTAX      INTEGER { rolloff2(0), rolloff5(1), rolloff10(2), rolloff15(3), rolloff20(4), rolloff25(5), rolloff35(6) }
    MAX-ACCESS  read-write
    STATUS      current
    DESCRIPTION
        "The transmit filter roll-off factor setting determines the output spectrum
        excess bandwidth by controlling the RCRO (Root Cosine Roll-Off) factor of the
        matched filter at the modulator output. The lower the roll-off factor the
        higher the throughput. Note that increasing the throughput (higher symbolrate)
        requires more power from the satellite or will result in a lower
        carrier-to-noise)."
    DEFVAL { rolloff25 }
    ::= { ntcDvbModEqlnkLinApp 2 }

ntcDvbModEqlnkLinAppSymRate      OBJECT-TYPE
    SYNTAX      Unsigned32
    UNITS       "baud"
    MAX-ACCESS  read-write
    STATUS      current
    DESCRIPTION
        "The Symbol Rate that was used during the calibration."
    DEFVAL { 5000000 }
    ::= { ntcDvbModEqlnkLinApp 3 }

ntcDvbModEqlnkNonlinMode         OBJECT-TYPE
    SYNTAX      NtcEnable
    MAX-ACCESS  read-write
    STATUS      current
    DESCRIPTION
        "Enable or disable non-linear equalink. Non-linear distortion is typically
        caused by non-linearity in the amplifier of the satellite. Enable this
        parameter to compensate for this non linearity."
    DEFVAL { off }
    ::= { ntcDvbModEqlnkNonlinear 1 }

ntcDvbModEqlnkNonlinState        OBJECT-TYPE
    SYNTAX      INTEGER { off(0), on(1) }
    MAX-ACCESS  read-only
    STATUS      current
    DESCRIPTION
        "Displays the current non-linear predistortion status. The actual non-linear
        predistortion status is determined by the configuration parameter but is also
        automatically switched-off when a the operator request the transmission of a
        pure carrier."
    ::= { ntcDvbModEqlnkNonlinear 2 }

ntcDvbModEqlnkNonlinInfo         OBJECT-TYPE
    SYNTAX      DisplayString (SIZE(0..250))
    MAX-ACCESS  read-only
    STATUS      current
    DESCRIPTION
        "Detailed info for non-linear equalink"
    ::= { ntcDvbModEqlnkNonlinear 3 }

ntcDvbModEqlnkNonlinAppOutFreq   OBJECT-TYPE
    SYNTAX      Unsigned32
    UNITS       "Hz"
    MAX-ACCESS  read-write
    STATUS      current
    DESCRIPTION
        "Modulator output frequency that was used during the calibration."
    DEFVAL { 1450000000 }
    ::= { ntcDvbModEqlnkNonlinApp 1 }

ntcDvbModEqlnkNonlinAppVersion   OBJECT-TYPE
    SYNTAX      Unsigned32
    MAX-ACCESS  read-write
    STATUS      current
    DESCRIPTION
        "Equalink version that was used during calibration"
    DEFVAL { 2 }
    ::= { ntcDvbModEqlnkNonlinApp 2 }

ntcDvbModAlmGeneralModulator     OBJECT-TYPE
    SYNTAX      NtcAlarmState
    MAX-ACCESS  read-only
    STATUS      current
    DESCRIPTION
        "This alarm is raised when there is a general modulator alarm. This variable
        indicates the current status of the alarm."
    ::= { ntcDvbModAlarm 1 }

ntcDvbModAlmNoInputSignal        OBJECT-TYPE
    SYNTAX      NtcAlarmState
    MAX-ACCESS  read-only
    STATUS      current
    DESCRIPTION
        "This alarm is raised when no input signal is detected at the input of the
        modulator. This variable indicates the current status of the alarm."
    ::= { ntcDvbModAlarm 2 }

ntcDvbModAlmBufferUnderflow      OBJECT-TYPE
    SYNTAX      NtcAlarmState
    MAX-ACCESS  read-only
    STATUS      current
    DESCRIPTION
        "This alarm is raised when the input data buffer to the modulator is empty.
        This variable indicates the current status of the alarm."
    ::= { ntcDvbModAlarm 3 }

ntcDvbModAlmBufferOverflow       OBJECT-TYPE
    SYNTAX      NtcAlarmState
    MAX-ACCESS  read-only
    STATUS      current
    DESCRIPTION
        "This alarm is raised when the input data buffer of the modulator is full. This
        variable indicates the current status of the alarm."
    ::= { ntcDvbModAlarm 4 }

ntcDvbModAlmNoInputFrameSync     OBJECT-TYPE
    SYNTAX      NtcAlarmState
    MAX-ACCESS  read-only
    STATUS      current
    DESCRIPTION
        "This alarm indicates loss of input framing on the incoming data of the
        modulator. This variable indicates the current status of the alarm."
    ::= { ntcDvbModAlarm 5 }

ntcDvbModAlmNoBaseBandFrameSync  OBJECT-TYPE
    SYNTAX      NtcAlarmState
    MAX-ACCESS  read-only
    STATUS      current
    DESCRIPTION
        "This alarm indicates synchronization loss of the baseband framer on the
        incoming data. This variable indicates the current status of the alarm."
    ::= { ntcDvbModAlarm 6 }

ntcDvbModAlmNoPhyLayerFrameSync  OBJECT-TYPE
    SYNTAX      NtcAlarmState
    MAX-ACCESS  read-only
    STATUS      current
    DESCRIPTION
        "This alarm indicates loss of synchronization between the physical layer
        framing and the baseband frames. This variable indicates the current status of
        the alarm."
    ::= { ntcDvbModAlarm 7 }

ntcDvbModAlmSynthFail            OBJECT-TYPE
    SYNTAX      NtcAlarmState
    MAX-ACCESS  read-only
    STATUS      current
    DESCRIPTION
        "This alarm is raised when there is a failure with a synthesizer. It indicates
        a malfunction of the synthesizer hardware which generates the IFL carrier
        frequency. The presence of this alarm suppresses the IFL transmit output of
        the modulator. This variable indicates the current status of the alarm."
    ::= { ntcDvbModAlarm 8 }

ntcDvbModAlmRefSynthOutOfLock    OBJECT-TYPE
    SYNTAX      NtcAlarmState
    MAX-ACCESS  read-only
    STATUS      current
    DESCRIPTION
        "This alarm is raised when the reference synthesizer is out of lock. It
        indicates a malfunction of the reference synthesizer hardware which generates
        the IFL carrier frequency. The presence of this alarm suppresses the IFL
        transmit of the the modulator. This variable indicates the current status of
        the alarm."
    ::= { ntcDvbModAlarm 9 }

ntcDvbModAlmLo1SynthOutOfLock    OBJECT-TYPE
    SYNTAX      NtcAlarmState
    MAX-ACCESS  read-only
    STATUS      current
    DESCRIPTION
        "This alarm is raised when the synthesizer of the first Local Oscillator is out
        of lock. It indicates a malfunction of the synthesizer hardware which
        generates the IFL carrier frequency. The presence of this alarm suppresses the
        IFL transmit. This variable indicates the current status of the alarm."
    ::= { ntcDvbModAlarm 10 }

ntcDvbModAlmLo2SynthOutOfLock    OBJECT-TYPE
    SYNTAX      NtcAlarmState
    MAX-ACCESS  read-only
    STATUS      current
    DESCRIPTION
        "This alarm is raised when the synthesizer of the second Local Oscillator is
        out of lock. It indicates a malfunction of the synthesizer hardware which
        generates the IFL carrier frequency. The presence of this alarm suppresses the
        IFL transmit. This variable indicates the current status of the alarm."
    ::= { ntcDvbModAlarm 11 }

ntcDvbModAlmNoCalibrationData    OBJECT-TYPE
    SYNTAX      NtcAlarmState
    MAX-ACCESS  read-only
    STATUS      current
    DESCRIPTION
        "This alarm is raised when there is no Calibration data available for the
        modulator. This variable indicates the current status of the alarm."
    ::= { ntcDvbModAlarm 12 }

ntcDvbModAlmDacFailure           OBJECT-TYPE
    SYNTAX      NtcAlarmState
    MAX-ACCESS  read-only
    STATUS      current
    DESCRIPTION
        "This alarm is raised when there is a general DAC Failure. This variable
        indicates the current status of the alarm."
    ::= { ntcDvbModAlarm 13 }

ntcDvbModAlmBucPowerMinCurrent   OBJECT-TYPE
    SYNTAX      NtcAlarmState
    MAX-ACCESS  read-only
    STATUS      current
    DESCRIPTION
        "This alarm is raised when measured current for block up converter power is
        below specified minimal value. This variable indicates the current status of
        the alarm."
    ::= { ntcDvbModAlarm 14 }

ntcDvbModAlmBucPowerOverload     OBJECT-TYPE
    SYNTAX      NtcAlarmState
    MAX-ACCESS  read-only
    STATUS      current
    DESCRIPTION
        "This alarm is raised when overload is detected. This variable indicates the
        current status of the alarm."
    ::= { ntcDvbModAlarm 15 }

ntcDvbModAlmBucPowerSupply       OBJECT-TYPE
    SYNTAX      NtcAlarmState
    MAX-ACCESS  read-only
    STATUS      current
    DESCRIPTION
        "This alarm is raised when 24V/48V supply is not operational This variable
        indicates the current status of the alarm."
    ::= { ntcDvbModAlarm 16 }

ntcDvbModAlmBucPowerCap          OBJECT-TYPE
    SYNTAX      NtcAlarmState
    MAX-ACCESS  read-only
    STATUS      current
    DESCRIPTION
        "This alarm is raised when there is too much output capacitance connected. This
        variable indicates the current status of the alarm."
    ::= { ntcDvbModAlarm 17 }

ntcDvbModAlmBucPowerShortCircuit OBJECT-TYPE
    SYNTAX      NtcAlarmState
    MAX-ACCESS  read-only
    STATUS      current
    DESCRIPTION
        "This alarm is raised when short circuit is detected. This variable indicates
        the current status of the alarm."
    ::= { ntcDvbModAlarm 18 }

ntcDvbModAlmBucPowerHardware     OBJECT-TYPE
    SYNTAX      NtcAlarmState
    MAX-ACCESS  read-only
    STATUS      current
    DESCRIPTION
        "This alarm is raised when communication with block up converter power unit is
        lost. This variable indicates the current status of the alarm."
    ::= { ntcDvbModAlarm 19 }

ntcDvbModInputType               OBJECT-TYPE
    SYNTAX      INTEGER { ts(0), bbf(1) }
    MAX-ACCESS  read-write
    STATUS      current
    DESCRIPTION
        "The type of input packets or frames for the modulator."
    DEFVAL { ts }
    ::= { ntcDvbModObjects 20 }

ntcDvbModRfCidEnable             OBJECT-TYPE
    SYNTAX      INTEGER { off(0), on(1) }
    MAX-ACCESS  read-write
    STATUS      current
    DESCRIPTION
        "Enable or disable the RF Carrier ID insertion."
    DEFVAL { off }
    ::= { ntcDvbModRfCid 1 }

ntcDvbModRfCidId                 OBJECT-TYPE
    SYNTAX      DisplayString (SIZE(0..30))
    MAX-ACCESS  read-only
    STATUS      current
    DESCRIPTION
        "The 64-bit DVB CID Global Unique Identifier is based on the IEEE EUI-64
        derived from a 48 bit MAC address of the management interface."
    ::= { ntcDvbModRfCid 2 }

ntcDvbModRfCidFormat             OBJECT-TYPE
    SYNTAX      Unsigned32
    MAX-ACCESS  read-only
    STATUS      current
    DESCRIPTION
        "Revision code anticipating possible changes in the number and possible content
        of the fields."
    ::= { ntcDvbModRfCid 3 }

ntcDvbModRfCidSendGeoCord        OBJECT-TYPE
    SYNTAX      INTEGER { off(0), on(1) }
    MAX-ACCESS  read-write
    STATUS      current
    DESCRIPTION
        "Enable or disable sending geo coordinates (longitude/latitude) in a DVB-CID
        message."
    DEFVAL { off }
    ::= { ntcDvbModRfCid 4 }

ntcDvbModRfCidLatitude           OBJECT-TYPE
    SYNTAX      Float32TC
    UNITS       "deg."
    MAX-ACCESS  read-write
    STATUS      current
    DESCRIPTION
        "Geo coordinates of modulator in degrees (latitude from +00.0000 to +/-90.0000)"
    DEFVAL { '00000000'H }
    ::= { ntcDvbModRfCid 5 }

ntcDvbModRfCidLongitude          OBJECT-TYPE
    SYNTAX      Float32TC
    UNITS       "deg."
    MAX-ACCESS  read-write
    STATUS      current
    DESCRIPTION
        "Geo coordinates of modulator in degrees (longitude from +000.0000 to
        +/-180.0000)"
    DEFVAL { '00000000'H }
    ::= { ntcDvbModRfCid 6 }

ntcDvbModRfCidPhone              OBJECT-TYPE
    SYNTAX      DisplayString (SIZE(0..30))
    MAX-ACCESS  read-write
    STATUS      current
    DESCRIPTION
        "Operators telephone number (for example +323 780 65 00 ext. 0) Regular
        expression : (?-mix:(\+?[ \d]+(ext\.)?[ \d]*)?)"
    DEFVAL { "" }
    ::= { ntcDvbModRfCid 7 }

ntcDvbModRfCidData               OBJECT-TYPE
    SYNTAX      DisplayString (SIZE(0..24))
    MAX-ACCESS  read-write
    STATUS      current
    DESCRIPTION
        "Custom user data (up to 24 ASCII chars)"
    ::= { ntcDvbModRfCid 8 }

ntcDvbModRfCidLatitudeString     OBJECT-TYPE
    SYNTAX      DisplayString (SIZE(1..9))
    MAX-ACCESS  read-write
    STATUS      current
    DESCRIPTION
        "Geo coordinates of modulator in degrees (latitude from +00.0000 to +/-90.0000)"
    DEFVAL { "0.0000" }
    ::= { ntcDvbModRfCid 9 }

ntcDvbModRfCidLongitudeString    OBJECT-TYPE
    SYNTAX      DisplayString (SIZE(1..9))
    MAX-ACCESS  read-write
    STATUS      current
    DESCRIPTION
        "Geo coordinates of modulator in degrees (longitude from +000.0000 to
        +/-180.0000)"
    DEFVAL { "0.0000" }
    ::= { ntcDvbModRfCid 10 }

ntcDvbModDcBucEnable             OBJECT-TYPE
    SYNTAX      INTEGER { off(0), on(1) }
    MAX-ACCESS  read-write
    STATUS      current
    DESCRIPTION
        "Enable or disable block up converter power."
    DEFVAL { off }
    ::= { ntcDvbModDcBuc 1 }

ntcDvbModDcBucVoltage            OBJECT-TYPE
    SYNTAX      INTEGER { e24V(0), e48V(1) }
    MAX-ACCESS  read-write
    STATUS      current
    DESCRIPTION
        "Select block up converter power voltage."
    DEFVAL { e24V }
    ::= { ntcDvbModDcBuc 2 }

ntcDvbModDcBucOutVoltage         OBJECT-TYPE
    SYNTAX      Integer32 (0..64000)
    UNITS       "mV"
    MAX-ACCESS  read-only
    STATUS      current
    DESCRIPTION
        "Block up converter power measured output voltage."
    ::= { ntcDvbModDcBuc 3 }

ntcDvbModDcBucOutCurrent         OBJECT-TYPE
    SYNTAX      Integer32 (0..8000)
    UNITS       "mA"
    MAX-ACCESS  read-only
    STATUS      current
    DESCRIPTION
        "Block up converter power measured output current."
    ::= { ntcDvbModDcBuc 4 }

ntcDvbModDcBucMinCurrent         OBJECT-TYPE
    SYNTAX      Integer32 (0..8000)
    UNITS       "mA"
    MAX-ACCESS  read-write
    STATUS      current
    DESCRIPTION
        "Minimal value for operational block up converter power current. If measured
        value drops below this value alarm will be raised."
    DEFVAL { 0 }
    ::= { ntcDvbModDcBuc 5 }

ntcDvbModRatePriority            OBJECT-TYPE
    SYNTAX      INTEGER { symbolrate(0), bitrate(1) }
    MAX-ACCESS  read-write
    STATUS      current
    DESCRIPTION
        "Select the rate mode (symbol rate or bit rate). The selected rate will be kept
        constant when other parameters have impact a the modulator rate. Only the
        selected rate can be changed explicitly by the operator."
    DEFVAL { symbolrate }
    ::= { ntcDvbModObjects 23 }

ntcDvbModSymbolRate              OBJECT-TYPE
    SYNTAX      Unsigned32
    UNITS       "baud"
    MAX-ACCESS  read-write
    STATUS      current
    DESCRIPTION
        "Define the required symbol rate in baud."
    DEFVAL { 10000000 }
    ::= { ntcDvbModObjects 24 }

ntcDvbModBitRate                 OBJECT-TYPE
    SYNTAX      Unsigned32
    UNITS       "bps"
    MAX-ACCESS  read-write
    STATUS      current
    DESCRIPTION
        "Define the required bit rate of the modulator. Current devices support a range
        of 50000 to 250000000 bps."
    DEFVAL { 5000000 }
    ::= { ntcDvbModObjects 25 }

ntcDvbModMeasuredPktCount        OBJECT-TYPE
    SYNTAX      Counter32
    UNITS       "packets"
    MAX-ACCESS  read-only
    STATUS      current
    DESCRIPTION
        "Measured TS packet count of the modulator."
    ::= { ntcDvbModObjects 26 }

ntcDvbModMeasuredBitRate         OBJECT-TYPE
    SYNTAX      Unsigned32
    UNITS       "bps"
    MAX-ACCESS  read-only
    STATUS      current
    DESCRIPTION
        "Measured bitrate of the modulator."
    ::= { ntcDvbModObjects 27 }

ntcDvbModReset                   OBJECT-TYPE
    SYNTAX      INTEGER { counting(0), reset(1) }
    MAX-ACCESS  read-write
    STATUS      current
    DESCRIPTION
        "Reset the modulator monitoring counters."
    DEFVAL { counting }
    ::= { ntcDvbModObjects 28 }

ntcDvbModS2ExtModCod             OBJECT-TYPE
    SYNTAX      INTEGER { unspecified(0), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215) }
    MAX-ACCESS  read-write
    STATUS      current
    DESCRIPTION
        "The list of S2 Extensions MODCODs is an extension to the standard DVB-S2
        MODCODs. The new MODCODs offer improved efficiency if transmission conditions
        allow it."
    DEFVAL { qpsk45180 }
    ::= { ntcDvbModS2Ext 1 }

ntcDvbModS2ExtPhyLayerEfficiency OBJECT-TYPE
    SYNTAX      Integer32 (0..10000)
    UNITS       "%"
    MAX-ACCESS  read-only
    STATUS      current
    DESCRIPTION
        "The measured physical layer efficiency, equal to the percentage of non-dummy
        physical layer frames. Float represented as integer is scaled by a factor of
        100. i.e. a value of 5000 in SNMP means a physical layer efficiency of 50.00 %"
    ::= { ntcDvbModS2Ext 2 }

ntcDvbModS2ExtBbLayerEfficiency  OBJECT-TYPE
    SYNTAX      Integer32 (0..10000)
    UNITS       "%"
    MAX-ACCESS  read-only
    STATUS      current
    DESCRIPTION
        "The measured baseband layer efficiency, equal to the percentage user data in
        tbe baseband frames. Float represented as integer is scaled by a factor of
        100. i.e. a value of 5000 in SNMP means a baseband layer efficiency of 50.00 %"
    ::= { ntcDvbModS2Ext 3 }

ntcDvbModS2ExtDumPlScramblMode   OBJECT-TYPE
    SYNTAX      INTEGER { dvbs2standard(0), continuous(1) }
    MAX-ACCESS  read-write
    STATUS      current
    DESCRIPTION
        "The dummy physical layer scrambler mode can be set to continuous, to achieve
        more randomness in the carrier data as required for bandwidth cancellation."
    DEFVAL { dvbs2standard }
    ::= { ntcDvbModS2Ext 4 }

ntcDvbModS2ExtPlScrambSig        OBJECT-TYPE
    SYNTAX      Unsigned32
    MAX-ACCESS  read-write
    STATUS      current
    DESCRIPTION
        "The physical layer scrambler signature."
    DEFVAL { 0 }
    ::= { ntcDvbModS2Ext 5 }

ntcDvbModS2ExtRollOffSignalling  OBJECT-TYPE
    SYNTAX      INTEGER { standard(0), reserved(1) }
    MAX-ACCESS  read-write
    STATUS      current
    DESCRIPTION
        "When a Roll-off <20% is configured, this setting is used to put the Roll-off
        bits in the baseband header to reserved (11) or to a standardized value. Some
        receivers accept only specific Roll-off bits."
    DEFVAL { standard }
    ::= { ntcDvbModS2Ext 6 }

ntcDvbModTurboModCod             OBJECT-TYPE
    SYNTAX      INTEGER { qpsk12(1), qpsk34(2), qpsk23(3), qpsk56(4), qpsk78(5), e8psk23(6), e8psk34(7), e8psk45(8), e8psk56(9), e8psk89(10) }
    MAX-ACCESS  read-write
    STATUS      current
    DESCRIPTION
        "The selection of the FEC code-rate and modulation scheme supported by TURBO"
    DEFVAL { qpsk34 }
    ::= { ntcDvbModTurbo 1 }

ntcDvbModTurboDeleteSync         OBJECT-TYPE
    SYNTAX      INTEGER { off(0), on(1) }
    MAX-ACCESS  read-write
    STATUS      current
    DESCRIPTION
        "Enable or disable deletion of the sync byte"
    DEFVAL { off }
    ::= { ntcDvbModTurbo 2 }

ntcDvbModAmcDvbsModCod           OBJECT-TYPE
    SYNTAX      INTEGER { qpsk12(1), qpsk23(2), qpsk34(3), qpsk56(4), qpsk78(5) }
    MAX-ACCESS  read-write
    STATUS      current
    DESCRIPTION
        "The selection of the FEC code-rate and modulation scheme supported by AMC-S"
    DEFVAL { qpsk34 }
    ::= { ntcDvbModAmcDvbs 1 }

ntcDvbModAmcNbcFrameType         OBJECT-TYPE
    SYNTAX      INTEGER { short(0), normal(1) }
    MAX-ACCESS  read-write
    STATUS      current
    DESCRIPTION
        "Dvb-S2 defines 2 FEC-frame types :
        - normal: FECframes of 64800 bits or 8100 bytes
        - short: FECframes of 16200 bits or 2025 bytes Short frames are used when
        working with low symbol rates or with latency sensitive applications."
    DEFVAL { normal }
    ::= { ntcDvbModAmcNbc 1 }

ntcDvbModAmcNbcModCod            OBJECT-TYPE
    SYNTAX      INTEGER { qpsk12(1), qpsk35(2), qpsk23(3), qpsk34(4), qpsk45(5), qpsk56(6), qpsk89(7), qpsk910(8), e8psk35(9), e8psk23(10), e8psk34(11), e8psk56(12), e8psk89(13), e8psk910(14) }
    MAX-ACCESS  read-write
    STATUS      current
    DESCRIPTION
        "The selection of modulation type and the FEC rate."
    DEFVAL { qpsk34 }
    ::= { ntcDvbModAmcNbc 2 }

ntcDvbModAmcNbcPilots            OBJECT-TYPE
    SYNTAX      NtcEnable
    MAX-ACCESS  read-write
    STATUS      current
    DESCRIPTION
        "Dvb-S2 Physical Layer Pilot insertion. When enabled, every 16 slots (of 90
        symbols) the modulator will insert 36 unmodulated symbols to aid in receiver
        synchronization. Set Pilots on in the following cases:
        - ACM model
        - High amount of phase noise is present
        - At low data rates
        - When distortion is present
        - When using one of the following MODCODs 8-PSK 3/5 and 2/3, 16-APSK and
        32-APSK (due to MODCOD structure)."
    DEFVAL { off }
    ::= { ntcDvbModAmcNbc 3 }

ntcDvbModAmcNbcPLEfficiency      OBJECT-TYPE
    SYNTAX      Integer32 (0..10000)
    UNITS       "%"
    MAX-ACCESS  read-only
    STATUS      current
    DESCRIPTION
        "The measured physical layer efficiency, equal to the percentage of non-dummy
        physical layer frames. Float represented as integer is scaled by a factor of
        100. i.e. a value of 5000 in SNMP means a physical layer efficiency of 50.00 %"
    ::= { ntcDvbModAmcNbc 4 }

ntcDvbModAmcNbcBbLayerEfficiency OBJECT-TYPE
    SYNTAX      Integer32 (0..10000)
    UNITS       "%"
    MAX-ACCESS  read-only
    STATUS      current
    DESCRIPTION
        "The measured baseband layer efficiency, equal to the percentage user data in
        tbe baseband frames. Float represented as integer is scaled by a factor of
        100. i.e. a value of 5000 in SNMP means a baseband layer efficiency of 50.00 %"
    ::= { ntcDvbModAmcNbc 5 }

ntcDvbModAmcNbcPlHdrScrmSeq      OBJECT-TYPE
    SYNTAX      Unsigned32
    MAX-ACCESS  read-write
    STATUS      current
    DESCRIPTION
        "Physical layer scrambling sequence key"
    DEFVAL { 0 }
    ::= { ntcDvbModAmcNbc 6 }

ntcDvbModAmcNbcRollOffSignalling OBJECT-TYPE
    SYNTAX      INTEGER { standard(0), reserved(1) }
    MAX-ACCESS  read-write
    STATUS      current
    DESCRIPTION
        "When a Roll-off <20% is configured, this setting is used to put the Roll-off
        bits in the baseband header to reserved (11) or to a standardized value. Some
        receivers accept only specific Roll-off bits."
    DEFVAL { standard }
    ::= { ntcDvbModAmcNbc 7 }

ntcDvbModActualOutputLevel       OBJECT-TYPE
    SYNTAX      Integer32 (-350..100)
    UNITS       "dBm"
    MAX-ACCESS  read-only
    STATUS      current
    DESCRIPTION
        "Modulator output level setting in dBm. Adjustable in steps of 0.1 dBm. Float
        represented as integer is scaled by a factor of 10. i.e. a value of '-103'
        means '-10.3' dBm"
    ::= { ntcDvbModObjects 33 }

ntcDvbModTransmitStateReason     OBJECT-TYPE
    SYNTAX      DisplayString (SIZE(0..255))
    MAX-ACCESS  read-only
    STATUS      current
    DESCRIPTION
        "Reason for current Transmit State"
    ::= { ntcDvbModObjects 34 }

ntcDvbModLinkOptTransMode        OBJECT-TYPE
    SYNTAX      INTEGER { single(1), multiple(2), singlelin(3) }
    MAX-ACCESS  read-write
    STATUS      current
    DESCRIPTION
        "Transponder Operation Mode selection."
    DEFVAL { multiple }
    ::= { ntcDvbModLinkOpt 1 }

ntcDvbModMaxModulation           OBJECT-TYPE
    SYNTAX      INTEGER { unspecified(0), e4ary(2), e8ary(3), e16ary(4), e32ary(5), e64ary(6), e128ary(7), e256ary(8) }
    MAX-ACCESS  read-write
    STATUS      current
    DESCRIPTION
        "The maximum modulation order to which the outbound carrier is optimized."
    DEFVAL { unspecified }
    ::= { ntcDvbModLinkOpt 2 }

ntcDvbModDSNGProfilesProfile     OBJECT-TYPE
    SYNTAX      OCTET STRING (SIZE(0..255))
    MAX-ACCESS  read-write
    STATUS      current
    DESCRIPTION
        "DSNG profile is named after its occupied bandwidth"
    DEFVAL { "" }
    ::= { ntcDvbModDSNGProfiles 38 }

ntcDvbModDSNGProfilesLevel       OBJECT-TYPE
    SYNTAX      OCTET STRING (SIZE(0..255))
    MAX-ACCESS  read-write
    STATUS      current
    DESCRIPTION
        "DSNG profile level that defines the proposed application"
    DEFVAL { "" }
    ::= { ntcDvbModDSNGProfiles 39 }

ntcDvbModStreamMode              OBJECT-TYPE
    SYNTAX      INTEGER { multistream(1), singlestream(2) }
    MAX-ACCESS  read-write
    STATUS      current
    DESCRIPTION
        "Specify if more than one input stream is multiplexed into the modulator or
        not. This sometimes impacts receiver compatibility."
    DEFVAL { multistream }
    ::= { ntcDvbModObjects 39 }

ntcDvbModAmcDlModCod             OBJECT-TYPE
    SYNTAX      INTEGER { qpsk12(1), qpsk23(2), qpsk67(3) }
    MAX-ACCESS  read-write
    STATUS      current
    DESCRIPTION
        "The selection of the FEC code-rate and modulation scheme supported by AMC-DL"
    DEFVAL { qpsk12 }
    ::= { ntcDvbModAmcDl 1 }

ntcDvbModIfOutputLevel           OBJECT-TYPE
    SYNTAX      Integer32 (-350..50)
    UNITS       "dBm"
    MAX-ACCESS  read-write
    STATUS      current
    DESCRIPTION
        "Modulator output level setting in dBm. Adjustable in steps of 0.1 dBm. Float
        represented as integer is scaled by a factor of 10. i.e. a value of '-103'
        means '-10.3' dBm"
    DEFVAL { -150 }
    ::= { ntcDvbModObjects 41 }

ntcDvbModLbandOutputLevel        OBJECT-TYPE
    SYNTAX      Integer32 (-300..50)
    UNITS       "dBm"
    MAX-ACCESS  read-write
    STATUS      current
    DESCRIPTION
        "Modulator output level setting in dBm. Adjustable in steps of 0.1 dBm. Float
        represented as integer is scaled by a factor of 10. i.e. a value of '-103'
        means '-10.3' dBm"
    DEFVAL { -150 }
    ::= { ntcDvbModObjects 42 }

ntcDvbModIfOutputFrequency       OBJECT-TYPE
    SYNTAX      INTEGER { e70MHz(1), e140MHz(2) }
    MAX-ACCESS  read-write
    STATUS      current
    DESCRIPTION
        "When the IF to L-Band converter is inside the device, then both IF and L-Band
        is available at the same time at the output of the device. This means that 2
        independent paramaters exist to define the both frequencies, where this
        parameter is used to define the IF frequency. If this IF to L-Band converter
        is not present in the device then this configuration parameter will not be
        applicable."
    DEFVAL { e70MHz }
    ::= { ntcDvbModObjects 43 }

ntcDvbModLbandOutputFrequency    OBJECT-TYPE
    SYNTAX      Unsigned32
    UNITS       "Hz"
    MAX-ACCESS  read-write
    STATUS      current
    DESCRIPTION
        "When the IF to L-Band converter is inside the device, then both IF and L-Band
        is available at the same time at the output of the device. This means that 2
        independent paramaters exist to define the both frequencies, where this
        parameter is used to define the L-Band frequency. If this IF to L-Band
        converter is not present in the device then this configuration parameter will
        not be applicable."
    DEFVAL { 1250000000 }
    ::= { ntcDvbModObjects 44 }

ntcDvbModLbandTx                 OBJECT-TYPE
    SYNTAX      NtcEnable
    MAX-ACCESS  read-write
    STATUS      current
    DESCRIPTION
        "Enable or disable the modulator L-Band output transmit signal. When it is
        enabled the actual output can still be switched-off upon detection of e.g.
        general device alarm of the modulator."
    DEFVAL { off }
    ::= { ntcDvbModObjects 45 }

ntcDvbModLbandTxState            OBJECT-TYPE
    SYNTAX      INTEGER { off(0), on(1) }
    MAX-ACCESS  read-only
    STATUS      current
    DESCRIPTION
        "Current L-Band transmit status of the modulator (on or off). The actual
        transmit status is determined by the transmit configuration parameter and by
        other events. Note that the transmit is also automatically switched-off upon
        detection of a general device alarm of the modulator."
    ::= { ntcDvbModObjects 46 }

ntcDvbModLbandTxStateReason      OBJECT-TYPE
    SYNTAX      DisplayString (SIZE(0..255))
    MAX-ACCESS  read-only
    STATUS      current
    DESCRIPTION
        "Reason for current L-Band Transmit State"
    ::= { ntcDvbModObjects 47 }

ntcDvbModExtConvEnable           OBJECT-TYPE
    SYNTAX      INTEGER { off(0), on(1) }
    MAX-ACCESS  read-write
    STATUS      current
    DESCRIPTION
        "Enable or disable the external convertor frequency specification"
    DEFVAL { off }
    ::= { ntcDvbModExtConv 1 }

ntcDvbModExtConvRfFrequency      OBJECT-TYPE
    SYNTAX      DisplayString (SIZE(0..20))
    UNITS       "Hz"
    MAX-ACCESS  read-write
    STATUS      current
    DESCRIPTION
        "RF frequency"
    DEFVAL { "0" }
    ::= { ntcDvbModExtConv 2 }

ntcDvbModExtConvLoFrequency      OBJECT-TYPE
    SYNTAX      DisplayString (SIZE(0..20))
    UNITS       "Hz"
    MAX-ACCESS  read-write
    STATUS      current
    DESCRIPTION
        "LO frequency"
    DEFVAL { "0" }
    ::= { ntcDvbModExtConv 3 }

ntcDvbModExtConvSpectrumInv      OBJECT-TYPE
    SYNTAX      INTEGER { directSpectrum(1), invertedSpectrum(2) }
    MAX-ACCESS  read-write
    STATUS      current
    DESCRIPTION
        "Specifies in the external LO converter inverts the spectrum or not."
    DEFVAL { directSpectrum }
    ::= { ntcDvbModExtConv 4 }

ntcDvbModConvRfFrequency         OBJECT-TYPE
    SYNTAX      DisplayString (SIZE(0..20))
    UNITS       "Hz"
    MAX-ACCESS  read-write
    STATUS      current
    DESCRIPTION
        "RF frequency"
    DEFVAL { "0" }
    ::= { ntcDvbModConv 1 }

ntcDvbModConvExtLbandTx          OBJECT-TYPE
    SYNTAX      INTEGER { off(0), on(1) }
    MAX-ACCESS  read-write
    STATUS      current
    DESCRIPTION
        "Enables or disables block upconverter output of the external L-band input
        signal."
    DEFVAL { off }
    ::= { ntcDvbModConv 2 }

ntcDvbModConvLoFrequency         OBJECT-TYPE
    SYNTAX      DisplayString (SIZE(0..20))
    UNITS       "Hz"
    MAX-ACCESS  read-only
    STATUS      current
    DESCRIPTION
        "Converter module LO frequency"
    ::= { ntcDvbModConv 3 }

ntcDvbModConvRfGain              OBJECT-TYPE
    SYNTAX      Integer32 (-500..500)
    UNITS       "dB"
    MAX-ACCESS  read-only
    STATUS      current
    DESCRIPTION
        "Gain of the installed converter module."
    ::= { ntcDvbModConv 4 }

ntcDvbModConvOutputLevel         OBJECT-TYPE
    SYNTAX      Integer32 (-500..500)
    UNITS       "dBm"
    MAX-ACCESS  read-write
    STATUS      current
    DESCRIPTION
        "Converter output level setting in dBm. Adjustable in steps of 0.1 dBm. Float
        represented as integer is scaled by a factor of 10. i.e. a value of '-103'
        means '-10.3' dBm"
    DEFVAL { -150 }
    ::= { ntcDvbModConv 5 }

ntcDvbModExtCableLoss            OBJECT-TYPE
    SYNTAX      Integer32 (-990..990)
    UNITS       "dBm"
    MAX-ACCESS  read-write
    STATUS      current
    DESCRIPTION
        "Modulator external cable loss in dBm. Adjustable in steps of 0.1 dBm. Float
        represented as integer is scaled by a factor of 10. i.e. a value of '-103'
        means '-10.3' dBm"
    DEFVAL { 0 }
    ::= { ntcDvbModObjects 50 }


--
--  Module Conformance
--

ntcDvbModConfGrpV1Standard       OBJECT-GROUP
    OBJECTS    {
                   ntcDvbModMode,
                   ntcDvbModTransmit,
                   ntcDvbModTransmitState,
                   ntcDvbModTxCtrlGenDeviceAlarm,
                   ntcDvbModTxCtrlGenInterfaceAlarm,
                   ntcDvbModAllowChangesWhileTxOn,
                   ntcDvbModStandbyRedundancyState,
                   ntcDvbModOutputFrequency,
                   ntcDvbModRollOff,
                   ntcDvbModOccupiedBandWidth,
                   ntcDvbModOutputBand,
                   ntcDvbModSpectrumPolarity,
                   ntcDvbModOutputLevel,
                   ntcDvbModClockOutput,
                   ntcDvbModCarrierModulation,
                   ntcDvbModAmplSlopeEqualizer,
                   ntcDvbModDvbs2FrameType,
                   ntcDvbModDvbs2ModCod,
                   ntcDvbModDvbs2Pilots,
                   ntcDvbModDvbs2PhyLayerEfficiency,
                   ntcDvbModDvbs2BbLayerEfficiency,
                   ntcDvbModDvbs2DumPlScramblMode,
                   ntcDvbModDvbs2PlScrambSig,
                   ntcDvbModDvbs2RollOffSignalling,
                   ntcDvbModDvbsModCod,
                   ntcDvbModEqlnkLinMode,
                   ntcDvbModEqlnkLinState,
                   ntcDvbModEqlnkLinInfo,
                   ntcDvbModEqlnkLinAppOutFreq,
                   ntcDvbModEqlnkLinAppRollOff,
                   ntcDvbModEqlnkLinAppSymRate,
                   ntcDvbModEqlnkNonlinMode,
                   ntcDvbModEqlnkNonlinState,
                   ntcDvbModEqlnkNonlinInfo,
                   ntcDvbModEqlnkNonlinAppOutFreq,
                   ntcDvbModEqlnkNonlinAppVersion,
                   ntcDvbModAlmGeneralModulator,
                   ntcDvbModAlmNoInputSignal,
                   ntcDvbModAlmBufferUnderflow,
                   ntcDvbModAlmBufferOverflow,
                   ntcDvbModAlmNoInputFrameSync,
                   ntcDvbModAlmNoBaseBandFrameSync,
                   ntcDvbModAlmNoPhyLayerFrameSync,
                   ntcDvbModAlmSynthFail,
                   ntcDvbModAlmRefSynthOutOfLock,
                   ntcDvbModAlmLo1SynthOutOfLock,
                   ntcDvbModAlmLo2SynthOutOfLock,
                   ntcDvbModAlmNoCalibrationData,
                   ntcDvbModAlmDacFailure,
                   ntcDvbModAlmBucPowerMinCurrent,
                   ntcDvbModAlmBucPowerOverload,
                   ntcDvbModAlmBucPowerSupply,
                   ntcDvbModAlmBucPowerCap,
                   ntcDvbModAlmBucPowerShortCircuit,
                   ntcDvbModAlmBucPowerHardware,
                   ntcDvbModInputType,
                   ntcDvbModRfCidEnable,
                   ntcDvbModRfCidId,
                   ntcDvbModRfCidFormat,
                   ntcDvbModRfCidSendGeoCord,
                   ntcDvbModRfCidLatitude,
                   ntcDvbModRfCidLongitude,
                   ntcDvbModRfCidPhone,
                   ntcDvbModRfCidData,
                   ntcDvbModRfCidLatitudeString,
                   ntcDvbModRfCidLongitudeString,
                   ntcDvbModDcBucEnable,
                   ntcDvbModDcBucVoltage,
                   ntcDvbModDcBucOutVoltage,
                   ntcDvbModDcBucOutCurrent,
                   ntcDvbModDcBucMinCurrent,
                   ntcDvbModRatePriority,
                   ntcDvbModSymbolRate,
                   ntcDvbModBitRate,
                   ntcDvbModMeasuredPktCount,
                   ntcDvbModMeasuredBitRate,
                   ntcDvbModReset,
                   ntcDvbModS2ExtModCod,
                   ntcDvbModS2ExtPhyLayerEfficiency,
                   ntcDvbModS2ExtBbLayerEfficiency,
                   ntcDvbModS2ExtDumPlScramblMode,
                   ntcDvbModS2ExtPlScrambSig,
                   ntcDvbModS2ExtRollOffSignalling,
                   ntcDvbModTurboModCod,
                   ntcDvbModTurboDeleteSync,
                   ntcDvbModAmcDvbsModCod,
                   ntcDvbModAmcNbcFrameType,
                   ntcDvbModAmcNbcModCod,
                   ntcDvbModAmcNbcPilots,
                   ntcDvbModAmcNbcPLEfficiency,
                   ntcDvbModAmcNbcBbLayerEfficiency,
                   ntcDvbModAmcNbcPlHdrScrmSeq,
                   ntcDvbModAmcNbcRollOffSignalling,
                   ntcDvbModActualOutputLevel,
                   ntcDvbModTransmitStateReason,
                   ntcDvbModLinkOptTransMode,
                   ntcDvbModMaxModulation,
                   ntcDvbModDSNGProfilesProfile,
                   ntcDvbModDSNGProfilesLevel,
                   ntcDvbModStreamMode,
                   ntcDvbModAmcDlModCod,
                   ntcDvbModIfOutputLevel,
                   ntcDvbModLbandOutputLevel,
                   ntcDvbModIfOutputFrequency,
                   ntcDvbModLbandOutputFrequency,
                   ntcDvbModLbandTx,
                   ntcDvbModLbandTxState,
                   ntcDvbModLbandTxStateReason,
                   ntcDvbModExtConvEnable,
                   ntcDvbModExtConvRfFrequency,
                   ntcDvbModExtConvLoFrequency,
                   ntcDvbModExtConvSpectrumInv,
                   ntcDvbModConvRfFrequency,
                   ntcDvbModConvExtLbandTx,
                   ntcDvbModConvLoFrequency,
                   ntcDvbModConvRfGain,
                   ntcDvbModConvOutputLevel,
                   ntcDvbModExtCableLoss
               }
    STATUS      current
    DESCRIPTION
        "Managed objects that constitute version 1 of a system device with standard capabilities."
    ::= { ntcDvbModConfGroup 1}

ntcDvbModConfGrpObsolete         OBJECT-GROUP
    OBJECTS    {
                   ntcDvbModDvbs2AcmSymbolRate,
                   ntcDvbModDvbs2Isi,
                   ntcDvbModDvbs2RatePriority,
                   ntcDvbModDvbs2SymbolRate,
                   ntcDvbModDvbs2BitRate,
                   ntcDvbModDvbs2MeasuredPktCount,
                   ntcDvbModDvbs2MeasuredBitRate,
                   ntcDvbModDvbs2Reset,
                   ntcDvbModDvbsRatePriority,
                   ntcDvbModDvbsSymbolRate,
                   ntcDvbModDvbsBitRate,
                   ntcDvbModDvbsMeasuredPktCount,
                   ntcDvbModDvbsMeasuredBitRate,
                   ntcDvbModDvbsReset
               }
    STATUS      obsolete
    DESCRIPTION
        "Managed objects which are deprecated or obsolete"
    ::= { ntcDvbModConfGroup 2}

ntcDvbModConfCompV1Standard      MODULE-COMPLIANCE
    STATUS      current
    DESCRIPTION
        "Compliance statement for Newtec device MIB implementations."
    MODULE  -- this module
    MANDATORY-GROUPS
                  {
                      ntcDvbModConfGrpV1Standard
                  }
    ::= { ntcDvbModConfCompliance  1 }


END
