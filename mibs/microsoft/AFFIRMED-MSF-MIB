--
--  Affirmed Networks Mediation Service Function MIB
--
AFFIRMED-MSF-MIB DEFINITIONS ::= BEGIN
IMPORTS
       MODULE-IDENTITY,
       enterprises;

affirmedMsf MODULE-IDENTITY
       LAST-UPDATED
          "201807180000Z"
       ORGANIZATION
          "Affirmed Networks, Inc."
       CONTACT-INFO
          "Affirmed Networks, Inc. 35 Nagog Park Acton, MA USA "
       DESCRIPTION "Mediation Service Function MIB"
       REVISION
          "201807180000Z"
       DESCRIPTION "MSF Initial Release"
       ::= { enterprises 37963 8}

--
--  AFFIRMED-MSF textual conventions
--
affirmedMsfTc                      OBJECT IDENTIFIER ::= {affirmedMsf 1}

END
