AFFIRMED-SNMP-AN3000-TRAPS-MIB DEFINITIONS ::= BEGIN
IMPORTS
	MODULE-IDENTITY,
	OBJECT-TYPE,
	Integer32,
	NOTIFICATION-TYPE                       FROM SNMPv2-SMI
	DisplayString                           FROM SNMPv2-TC
	affirmedSnmp                            FROM AFFIRMED-SNMP-MIB
	affirmedSnmpNotifications               FROM AFFIRMED-SNMP-MIB
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName,
	name,
	chassis,
	slot,
	cpu,
	dirname,
	adminstate,
	resource,
	sensor,
	data,
	taskname,
	cid,
	sid,
	type,
	subtype,
	level,
	time,
	services,
	actions,
	ledname,
	ledcolor,
	usid,
	hardorsoft,
	readerrors,
	writeerrors,
	slotnumber,
	failuredescription,
	suggestedrecovery,
	netcontext,
	info,
	nodename,
	realmname,
	localhostidentity,
	peerrealmname,
	peerhostidentity,
	peername,
	clientid,
	servicename,
	apnname,
	imsi,
	statestring,
	filepath,
	ip,
	port,
	chassisid,
	slotid,
	cpuid,
	prefix,
	numpurged,
	node,
	diskid,
	interfacename,
	threshold,
	uepoolutilization,
	ipversiontype,
	ifindex,
	ifadminstatus,
	ifoperstatus,
	netctxtname,
	peeringname,
	localpeeripaddr,
	remotepeeripaddr,
	lasterrorcode,
	lasterrosubcode,
	currentstate,
	role,
	groupname,
	operation,
	state,
	status,
	activesize,
	standbysize,
	mcmslotnumber,
	requiredsize,
	availablesize,
	reason,
	importnum,
	resultstr,
	datetime,
	fault,
	action,
	unused,
	clusterid,
	nodeid,
	subsgroupname,
	subsidfilename,
	alarmid,
	xpath,
	ifname,
	sessionthreshold,
	sessionutilization,
	ipaddressthreshold,
	ipaddressutilization,
	portchunkthreshold,
	portchunkutilization,
	parent,
	destination,
	peeripaddress,
	gatewayname,
	gatewayipaddress,
	bfdsessiondescription,
	cafilename,
	expirydate,
	index                    FROM AFFIRMED-ALARM-MIB;


affirmedSnmpAn3000Traps MODULE-IDENTITY
	LAST-UPDATED "201105160000Z"
	ORGANIZATION
	"Affirmed Networks, Inc."
	CONTACT-INFO
	"Affirmed Networks, Inc.
	     35 Nagog Park
	     Acton, MA
	     USA "
	DESCRIPTION
	"Traps MIB objects"
	::= { affirmedSnmpNotifications 4}
-- top level structure
--
affirmedSnmpAn3000TrapsScalars       OBJECT IDENTIFIER ::= { affirmedSnmpAn3000Traps 1 }
affirmedSnmpAn3000TrapsTables        OBJECT IDENTIFIER ::= { affirmedSnmpAn3000Traps 2 }
affirmedSnmpAn3000TrapsNotifications OBJECT IDENTIFIER ::= { affirmedSnmpAn3000Traps 3 }
affirmedSnmpAn3000TrapsNotificationPrefix  OBJECT IDENTIFIER
                                   ::= { affirmedSnmpAn3000TrapsNotifications 0 }
affirmedSnmpAn3000TrapsNotificationObjects OBJECT IDENTIFIER
                                   ::= { affirmedSnmpAn3000TrapsNotifications 1 }

fmCntnFilterCategoryFileTooBig NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF category failed as file is too large."
::= { affirmedSnmpAn3000TrapsNotificationPrefix 39}




fmCntnFilterCategoryFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF category failed as file does not exist on NE."
::= { affirmedSnmpAn3000TrapsNotificationPrefix 40}




fmCntnFilterCategoryFileOverflow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF category failed as exceeded max supported filter entries per filter database size."
::= { affirmedSnmpAn3000TrapsNotificationPrefix 41}




fmCntnFilterBlacklistFileOverflow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF blacklist failed as exceeded max supported filter entries per filter database size."
::= { affirmedSnmpAn3000TrapsNotificationPrefix 42}




fmCntnFilterBlacklistFileTooBig NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF blacklist failed as file is too large."
::= { affirmedSnmpAn3000TrapsNotificationPrefix 44}




fmCntnFilterBlacklistFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF blacklist failed as file does not exist on NE."
::= { affirmedSnmpAn3000TrapsNotificationPrefix 45}




fmCntnFilterCategoryFileInvalidEntry NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF category got error as file has invalid entry."
::= { affirmedSnmpAn3000TrapsNotificationPrefix 47}




fmCntnFilterBlacklistFileInvalidEntry NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF blacklist got error as file has invalid entry."
::= { affirmedSnmpAn3000TrapsNotificationPrefix 48}




fmCntnHttpProxyServerConnectFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS obsolete
DESCRIPTION
"http-proxy failed to connect server."
::= { affirmedSnmpAn3000TrapsNotificationPrefix 49}




anCntnFilterWhitelistFileInvalidEntry NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF whitelist got error as file has invalid entry."
::= { affirmedSnmpAn3000TrapsNotificationPrefix 56}




anCntnFilterWhitelistFileOverflow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF whitelist failed as exceeded max supported filter entries per filter database size."
::= { affirmedSnmpAn3000TrapsNotificationPrefix 57}




anCntnFilterWhitelistFileTooBig NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF whitelist failed as file is too large."
::= { affirmedSnmpAn3000TrapsNotificationPrefix 58}




anCntnFilterWhitelistFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding CF whitelist failed as file does not exist on NE."
::= { affirmedSnmpAn3000TrapsNotificationPrefix 59}




anCacheDiskOperationalStateAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Monitor the cache SSD operational state."
::= { affirmedSnmpAn3000TrapsNotificationPrefix 61}




anCntnUrlListFileInvalidEntry NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding urlList got error as file has invalid entry."
::= { affirmedSnmpAn3000TrapsNotificationPrefix 62}




anCntnUrlListFileOverflow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding UrlList failed as exceeded max supported filter entries per filter database size."
::= { affirmedSnmpAn3000TrapsNotificationPrefix 63}




anCntnUrlListFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding urlList failed as file does not exist on NE."
::= { affirmedSnmpAn3000TrapsNotificationPrefix 64}




anCntnUrlListFileTooBig NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding urlList failed as file is too big."
::= { affirmedSnmpAn3000TrapsNotificationPrefix 65}




anPlaFileDownloadFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Policy lists agent failed to download a policy file from external server."
::= { affirmedSnmpAn3000TrapsNotificationPrefix 67}




anCacheDiskErrorStateAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	readerrors,
	writeerrors,
	affirmedVmSourceIpAddress,
	affirmedVmSourceName
}
STATUS current
DESCRIPTION
"Monitor the Cache SSD read/write error state."
::= { affirmedSnmpAn3000TrapsNotificationPrefix 79}




anLDAPServerConnectFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	netcontext,
	affirmedVmSourceIpAddress,
	affirmedVmSourceName
}
STATUS current
DESCRIPTION
"Failed to connect LDAP server."
::= { affirmedSnmpAn3000TrapsNotificationPrefix 81}




anLDAPServerConnectLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	netcontext,
	affirmedVmSourceIpAddress,
	affirmedVmSourceName
}
STATUS current
DESCRIPTION
"LDAP server connection lost."
::= { affirmedSnmpAn3000TrapsNotificationPrefix 82}




anLDAPProfNoServerConnected NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"LDAP profile does not have a connection to remote server."
::= { affirmedSnmpAn3000TrapsNotificationPrefix 83}




anCntnUaProfDefaultAttsMissing NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Missing required attributes in the default UA profile."
::= { affirmedSnmpAn3000TrapsNotificationPrefix 86}




anSMSCServerConnectFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	affirmedVmSourceIpAddress,
	affirmedVmSourceName
}
STATUS current
DESCRIPTION
"Failed to connect to SMSC server."
::= { affirmedSnmpAn3000TrapsNotificationPrefix 95}




anSMSCProfNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	affirmedVmSourceIpAddress,
	affirmedVmSourceName
}
STATUS current
DESCRIPTION
"SMSC profile not found."
::= { affirmedSnmpAn3000TrapsNotificationPrefix 96}




anSMSCServerConnectLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	affirmedVmSourceIpAddress,
	affirmedVmSourceName
}
STATUS current
DESCRIPTION
"SMSC server connection lost."
::= { affirmedSnmpAn3000TrapsNotificationPrefix 97}




anCntnUaProfFileInvalid NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding UA profile file failed due to invalid profile file."
::= { affirmedSnmpAn3000TrapsNotificationPrefix 109}




anSpsServerConnectFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	affirmedVmSourceIpAddress,
	affirmedVmSourceName
}
STATUS current
DESCRIPTION
"Failed to connect to SPS server."
::= { affirmedSnmpAn3000TrapsNotificationPrefix 131}




anSpsServerConnectLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	info,
	name,
	affirmedVmSourceIpAddress,
	affirmedVmSourceName
}
STATUS obsolete
DESCRIPTION
"SPS server connection lost."
::= { affirmedSnmpAn3000TrapsNotificationPrefix 132}




anCntnOnlineCatDBInstallationFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	importnum,
	resultstr,
	slotid,
	affirmedVmSourceIpAddress,
	affirmedVmSourceName
}
STATUS current
DESCRIPTION
"Online Categorization Database Installation Failed"
::= { affirmedSnmpAn3000TrapsNotificationPrefix 218}




anCntnFilterHashListFileInvalidEntry NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding filterHashList got error as file has invalid entry."
::= { affirmedSnmpAn3000TrapsNotificationPrefix 291}




anCntnFilterHashListFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding filterHashList failed as file does not exist on NE."
::= { affirmedSnmpAn3000TrapsNotificationPrefix 292}




anCntnFilterHashListFileOverflow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding FilterHashList failed as exceeded max supported filter entries per filter database size."
::= { affirmedSnmpAn3000TrapsNotificationPrefix 293}




anCntnFilterHashListFileTooBig NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Adding filterHashList failed as file is too big."
::= { affirmedSnmpAn3000TrapsNotificationPrefix 294}




anCntnHealthCheckStateDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	destination,
	parent,
	affirmedVmSourceIpAddress,
	affirmedVmSourceName
}
STATUS current
DESCRIPTION
"The service monitored by content health check is not reachable."
::= { affirmedSnmpAn3000TrapsNotificationPrefix 320}




anCntnCACertExpired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cafilename,
	expirydate,
	index,
	affirmedVmSourceIpAddress,
	affirmedVmSourceName
}
STATUS current
DESCRIPTION
"One or multiple CA (Certificate Authority) certificates have expired."
::= { affirmedSnmpAn3000TrapsNotificationPrefix 335}




anDnsServerConfigLoadFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Loading the config file for Dns Server Failed."
::= { affirmedSnmpAn3000TrapsNotificationPrefix 348}




anDnsServerRecClientHardLimitExceeded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Hard quota for recursive clients reached. Incoming requests are dropped, and for each one, a pending request is dropped. "
::= { affirmedSnmpAn3000TrapsNotificationPrefix 349}




anDnsServerRecClientSoftLimitExceeded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Soft quota for recursive clients reached. Incoming requests are accepted, but for each one, a pending request is dropped. If recursive-clients is set greater than 1000, soft quota is recursive-clients minus 100; else it is 90% of recursive-clients."
::= { affirmedSnmpAn3000TrapsNotificationPrefix 350}




anDnsServerZoneLoadFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Loading the zone file for Dns Server Failed."
::= { affirmedSnmpAn3000TrapsNotificationPrefix 351}




fmHmCacheOperStateDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"CSM cache operationally down."
::= { affirmedSnmpAn3000TrapsNotificationPrefix 28}




anTemperatureAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising temperature alarm."
::= { affirmedSnmpAn3000TrapsNotificationPrefix 29}




anVoltageAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising voltage alarm."
::= { affirmedSnmpAn3000TrapsNotificationPrefix 30}




anHotSwapAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising hot swap alarm."
::= { affirmedSnmpAn3000TrapsNotificationPrefix 31}




anTelcoAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS deprecated
DESCRIPTION
"HW Sensor Raising Telco Alarm"
::= { affirmedSnmpAn3000TrapsNotificationPrefix 32}




anWatchdogAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS deprecated
DESCRIPTION
"HW Sensor Raising Watchdog Alarm"
::= { affirmedSnmpAn3000TrapsNotificationPrefix 33}




anFanAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS deprecated
DESCRIPTION
"HW Sensor Raising Fan Alarm"
::= { affirmedSnmpAn3000TrapsNotificationPrefix 34}




anAirFilterAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising air filter alarm."
::= { affirmedSnmpAn3000TrapsNotificationPrefix 35}




anTachAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising tach alarm.."
::= { affirmedSnmpAn3000TrapsNotificationPrefix 36}




anHWAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	data,
	resource,
	sensor,
	slot,
	affirmedVmSourceIpAddress,
	affirmedVmSourceName
}
STATUS current
DESCRIPTION
"HW sensor raising hardware alarm."
::= { affirmedSnmpAn3000TrapsNotificationPrefix 37}




anCardNotBootingUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"Card is plugged in but not operational"
::= { affirmedSnmpAn3000TrapsNotificationPrefix 46}




anLedStateChange NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ledcolor,
	ledname,
	resource,
	slot,
	affirmedVmSourceIpAddress,
	affirmedVmSourceName
}
STATUS current
DESCRIPTION
"LED state change."
::= { affirmedSnmpAn3000TrapsNotificationPrefix 74}




anRebootEvent NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	hardorsoft,
	slot,
	affirmedVmSourceIpAddress,
	affirmedVmSourceName
}
STATUS current
DESCRIPTION
"Module rebooted."
::= { affirmedSnmpAn3000TrapsNotificationPrefix 78}




anPayloadFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	failuredescription,
	slotnumber,
	suggestedrecovery,
	affirmedVmSourceIpAddress,
	affirmedVmSourceName
}
STATUS current
DESCRIPTION
"The specified payload has experienced a hardware or firmware failure."
::= { affirmedSnmpAn3000TrapsNotificationPrefix 80}




anFmSlotFrequentReboot NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassisid,
	cpuid,
	slotid,
	affirmedVmSourceIpAddress,
	affirmedVmSourceName
}
STATUS current
DESCRIPTION
"Slot (CSM or SSM) has exceeded reboot frequency threshold."
::= { affirmedSnmpAn3000TrapsNotificationPrefix 114}




anPortStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	port,
	slot,
	affirmedVmSourceIpAddress,
	affirmedVmSourceName
}
STATUS deprecated
DESCRIPTION
"Port Status is Down"
::= { affirmedSnmpAn3000TrapsNotificationPrefix 128}




anPortStatusUP NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	port,
	slot,
	affirmedVmSourceIpAddress,
	affirmedVmSourceName
}
STATUS deprecated
DESCRIPTION
"Port Status is UP"
::= { affirmedSnmpAn3000TrapsNotificationPrefix 129}




anHwNodeDepartureEventData NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Node has departed from cluster."
::= { affirmedSnmpAn3000TrapsNotificationPrefix 142}




anHwExtStorageCreateFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	operation,
	state,
	status,
	affirmedVmSourceIpAddress,
	affirmedVmSourceName
}
STATUS current
DESCRIPTION
"Failure during the creation of an extended-storage disk partition"
::= { affirmedSnmpAn3000TrapsNotificationPrefix 199}




anHwExtStorageSizeMismatch NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	activesize,
	standbysize,
	affirmedVmSourceIpAddress,
	affirmedVmSourceName
}
STATUS current
DESCRIPTION
"Alarm is generated when the extended-storage disk size is not matched between the Active and Standby MCMs"
::= { affirmedSnmpAn3000TrapsNotificationPrefix 200}




anHwNoExtStorageDiskAvailable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	mcmslotnumber,
	affirmedVmSourceIpAddress,
	affirmedVmSourceName
}
STATUS current
DESCRIPTION
"This alarm is generated when an ext-storage disk is required but none has been created"
::= { affirmedSnmpAn3000TrapsNotificationPrefix 201}




anHwNotEnoughFreeStorageSpace NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	availablesize,
	requiredsize,
	affirmedVmSourceIpAddress,
	affirmedVmSourceName
}
STATUS current
DESCRIPTION
"Lack of sufficient free storage space available"
::= { affirmedSnmpAn3000TrapsNotificationPrefix 202}




anHwExtStorageMoveFilesTimeout NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	operation,
	affirmedVmSourceIpAddress,
	affirmedVmSourceName
}
STATUS current
DESCRIPTION
"Event generated when moving files from one storage site to another exceeds timeout."
::= { affirmedSnmpAn3000TrapsNotificationPrefix 203}




anHwExtStorageCloseFilesTimeout NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	operation,
	affirmedVmSourceIpAddress,
	affirmedVmSourceName
}
STATUS current
DESCRIPTION
"Event generated when waiting for files to close on a disk partition exceeds a timeout"
::= { affirmedSnmpAn3000TrapsNotificationPrefix 204}




anExtractionPending NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	resource,
	slot,
	affirmedVmSourceIpAddress,
	affirmedVmSourceName
}
STATUS current
DESCRIPTION
"Fru entered Extraction pending state"
::= { affirmedSnmpAn3000TrapsNotificationPrefix 208}




anInsertionPending NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	resource,
	slot,
	affirmedVmSourceIpAddress,
	affirmedVmSourceName
}
STATUS current
DESCRIPTION
"Fru entered insertion pending state"
::= { affirmedSnmpAn3000TrapsNotificationPrefix 209}




anIsolCpusMismatch NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Incorrect number of Isol Cpus for this platform"
::= { affirmedSnmpAn3000TrapsNotificationPrefix 242}




anIpInterfaceOperStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"The operational status of an IP interface is down."
::= { affirmedSnmpAn3000TrapsNotificationPrefix 88}




anDataFabricOperStateDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Communication over the data fabric is down."
::= { affirmedSnmpAn3000TrapsNotificationPrefix 110}




anGeoRedundancyStandbyOperStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Indicates a Geo-redundant standby cluster is not ready and the active peer is not currently protected."
::= { affirmedSnmpAn3000TrapsNotificationPrefix 117}




anGeoRedundancyActiveOperStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Geo-redundant active cluster is not fully functional due to link health status with neighboring network elements."
::= { affirmedSnmpAn3000TrapsNotificationPrefix 118}




anGeoRedundancyPrimaryNodeStandby NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Geo-redundant node designated as HA-Role primary has entered HA-State standby."
::= { affirmedSnmpAn3000TrapsNotificationPrefix 133}




anGeoRedundancySecondaryNodeActive NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Geo-redundant node designated as HA-Role secondary has entered HA-State active."
::= { affirmedSnmpAn3000TrapsNotificationPrefix 134}




anGeoRedundancyLinkDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Geo-redundancy link is down."
::= { affirmedSnmpAn3000TrapsNotificationPrefix 136}




anGeoRedundancyLinkVersionMismatch NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Geo-redundant peers running incompatible software versions."
::= { affirmedSnmpAn3000TrapsNotificationPrefix 137}




anDataFabricOperStateDownPathA NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check over data fabric path A is down."
::= { affirmedSnmpAn3000TrapsNotificationPrefix 144}




anDataFabricOperStateDownPathB NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check over data fabric path B is down."
::= { affirmedSnmpAn3000TrapsNotificationPrefix 145}




anBaseSwitchOperStateDownPathA NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check over base switch path A is down."
::= { affirmedSnmpAn3000TrapsNotificationPrefix 147}




anBaseSwitchOperStateDownPathB NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check over base switch path B is down."
::= { affirmedSnmpAn3000TrapsNotificationPrefix 148}




anBaseSwitchOperStateDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check over base switch paths A and B are down."
::= { affirmedSnmpAn3000TrapsNotificationPrefix 149}




anNtpSyncError NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Cannot sync with configured NTP servers."
::= { affirmedSnmpAn3000TrapsNotificationPrefix 151}




anBaseSwitchReachabilityDiffersPathAPathB NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Base switch node reachability differs between path A and path B."
::= { affirmedSnmpAn3000TrapsNotificationPrefix 168}




anDataFabricReachabilityDiffersPathAPathB NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Map of reachable nodes over data fabric path A differs from path B."
::= { affirmedSnmpAn3000TrapsNotificationPrefix 169}




anIpBgpPeerOperStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	currentstate,
	lasterrorcode,
	lasterrosubcode,
	localpeeripaddr,
	netctxtname,
	peeringname,
	remotepeeripaddr,
	affirmedVmSourceIpAddress,
	affirmedVmSourceName
}
STATUS current
DESCRIPTION
"A BGP peering is not in Established state. The alarm is raised when peering starts, restarts, cleared, or when a peering leaves Established state due to a protocol or networking event. The alarm is cleared when a peering enters Established state."
::= { affirmedSnmpAn3000TrapsNotificationPrefix 186}




anPacketEngineError NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	info,
	sid,
	affirmedVmSourceIpAddress,
	affirmedVmSourceName
}
STATUS current
DESCRIPTION
"The network packet engine has encountered an error preventing any data plane communication on the current node (control plane is not affected)"
::= { affirmedSnmpAn3000TrapsNotificationPrefix 206}




anPacketEngineCongestion NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	info,
	sid,
	affirmedVmSourceIpAddress,
	affirmedVmSourceName
}
STATUS current
DESCRIPTION
"The packet network engine is experiencing congestion, no impact at warning level. At critical alarm level, priority based packet drops are possible. Reception is affected until packet memory returns to an acceptable level."
::= { affirmedSnmpAn3000TrapsNotificationPrefix 207}




anDataFabricPartialReachabilityPathA NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	sid,
	affirmedVmSourceIpAddress,
	affirmedVmSourceName
}
STATUS current
DESCRIPTION
"Inter-node connectivity health check detects partial connectivity with peer nodes over data plane path A."
::= { affirmedSnmpAn3000TrapsNotificationPrefix 210}




anPacketEngineWatchdogAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	info,
	sid,
	affirmedVmSourceIpAddress,
	affirmedVmSourceName
}
STATUS current
DESCRIPTION
"The packet network engine has experienced a critical error that is preventing packet processing.  Packet processing is stopped."
::= { affirmedSnmpAn3000TrapsNotificationPrefix 239}




anPacketEngineKNIConfigurationMismatch NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"A mismatch exists between the provisioned packet processing resources and what node booted with."
::= { affirmedSnmpAn3000TrapsNotificationPrefix 241}




anIpsecTunnelOperStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	unused,
	affirmedVmSourceIpAddress,
	affirmedVmSourceName
}
STATUS current
DESCRIPTION
"IPsec TUNNEL-DOWN"
::= { affirmedSnmpAn3000TrapsNotificationPrefix 246}




anIpsecTunnelOperStatusUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	unused,
	affirmedVmSourceIpAddress,
	affirmedVmSourceName
}
STATUS current
DESCRIPTION
"IPsec TUNNEL-UP"
::= { affirmedSnmpAn3000TrapsNotificationPrefix 247}




anIpOspfv2NbrDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	unused,
	affirmedVmSourceIpAddress,
	affirmedVmSourceName
}
STATUS current
DESCRIPTION
"An OSPFv2 neighbor is not in Full/2-Way state. The alarm will be generated when a neighbor leaves Full/2-Way state. The alarm is cleared when neighbor enters Full/2-Way state. "
::= { affirmedSnmpAn3000TrapsNotificationPrefix 302}




anIpOspfv3NbrDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	unused,
	affirmedVmSourceIpAddress,
	affirmedVmSourceName
}
STATUS current
DESCRIPTION
"An OSPFv3 neighbor is not in Full/2-Way state. The alarm will be generated when a neighbor leaves Full/2-Way state. The alarm is cleared when neighbor enters Full/2-Way state. "
::= { affirmedSnmpAn3000TrapsNotificationPrefix 303}




anNatPoolSessionAlarmThreshold NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	sessionthreshold,
	sessionutilization,
	affirmedVmSourceIpAddress,
	affirmedVmSourceName
}
STATUS current
DESCRIPTION
"The nat-pool session utilization has exceeded threshold. This may potentially lead to session or connection setup failures."
::= { affirmedSnmpAn3000TrapsNotificationPrefix 304}




anNatPoolIpAddressAlarmThreshold NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ipaddressthreshold,
	ipaddressutilization,
	affirmedVmSourceIpAddress,
	affirmedVmSourceName
}
STATUS current
DESCRIPTION
"The nat-pool IP address utilization has exceeded threshold. This may potentially lead to session or connection setup failures."
::= { affirmedSnmpAn3000TrapsNotificationPrefix 305}




anNatPoolPortChunkAlarmThreshold NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	portchunkthreshold,
	portchunkutilization,
	affirmedVmSourceIpAddress,
	affirmedVmSourceName
}
STATUS current
DESCRIPTION
"The nat-pool Port chunk utilization has exceeded threshold. This may potentially lead to session or connection setup failures."
::= { affirmedSnmpAn3000TrapsNotificationPrefix 306}




anBfdSessionDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	bfdsessiondescription,
	affirmedVmSourceIpAddress,
	affirmedVmSourceName
}
STATUS current
DESCRIPTION
"This event is generated when a BFD session goes down. It is cleared when the BFD session goes up. A gratuitous clear will happen the first time the BFD session goes up. Toggled by ip-protocols/bfd/enable-bfd-session-down-alarms"
::= { affirmedSnmpAn3000TrapsNotificationPrefix 329}




anPortmapFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	failuredescription,
	slotnumber,
	affirmedVmSourceIpAddress,
	affirmedVmSourceName
}
STATUS current
DESCRIPTION
"The network ports are not in the correct order, which causes connectivity to the desired network to appear broken."
::= { affirmedSnmpAn3000TrapsNotificationPrefix 333}




fmNmAn3000ColdStart NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A ColdStart trap signifies that the an3000/MCC is reinitializing itself and that its configuration may have been altered."
::= { affirmedSnmpAn3000TrapsNotificationPrefix 23}




fmNmAn3000Test NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A test event"
::= { affirmedSnmpAn3000TrapsNotificationPrefix 24}




fmNmAn3000Commit NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An NMD configuration has been committed."
::= { affirmedSnmpAn3000TrapsNotificationPrefix 25}




an3000WarmStart NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A WarmStart trap signifies that the an3000/MCC is reinitializing itself such that its configuration is unaltered."
::= { affirmedSnmpAn3000TrapsNotificationPrefix 152}




anLinkUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ifadminstatus,
	ifindex,
	ifoperstatus,
	affirmedVmSourceIpAddress,
	affirmedVmSourceName
}
STATUS current
DESCRIPTION
"A logical link has transitioned from state down to state up."
::= { affirmedSnmpAn3000TrapsNotificationPrefix 153}




anLinkDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ifadminstatus,
	ifindex,
	ifoperstatus,
	affirmedVmSourceIpAddress,
	affirmedVmSourceName
}
STATUS current
DESCRIPTION
"A logical link has transitioned from state up to state down."
::= { affirmedSnmpAn3000TrapsNotificationPrefix 154}




anNmLoginFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Failed login attempt"
::= { affirmedSnmpAn3000TrapsNotificationPrefix 155}




anTaskOverload NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	cpu,
	level,
	sid,
	subtype,
	taskname,
	time,
	type,
	affirmedVmSourceIpAddress,
	affirmedVmSourceName
}
STATUS current
DESCRIPTION
"A task has generated an overload event."
::= { affirmedSnmpAn3000TrapsNotificationPrefix 69}




anBladeOverload NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	actions,
	cid,
	cpu,
	level,
	services,
	sid,
	affirmedVmSourceIpAddress,
	affirmedVmSourceName
}
STATUS current
DESCRIPTION
"This blade has generated an overload event."
::= { affirmedSnmpAn3000TrapsNotificationPrefix 70}




anSystemOverload NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	level,
	subtype,
	type,
	affirmedVmSourceIpAddress,
	affirmedVmSourceName
}
STATUS obsolete
DESCRIPTION
"This system has generated an overload event"
::= { affirmedSnmpAn3000TrapsNotificationPrefix 71}




anGtpPeerDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"GTP peer down.  This indicates that the remote GTP peer is not responding to any GTP messages sent to it.  If the peer is statically provisioned, the severity is Major.  If the peer is dynamic, the severity is Info."
::= { affirmedSnmpAn3000TrapsNotificationPrefix 60}




anCantPageSubscriberOutOfBuffers NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassis,
	cpu,
	slot,
	affirmedVmSourceIpAddress,
	affirmedVmSourceName
}
STATUS deprecated
DESCRIPTION
"FP ran out of paging buffers"
::= { affirmedSnmpAn3000TrapsNotificationPrefix 73}




anDiameterPeerLinkDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	localhostidentity,
	nodename,
	peerhostidentity,
	peerrealmname,
	realmname,
	affirmedVmSourceIpAddress,
	affirmedVmSourceName
}
STATUS current
DESCRIPTION
"Transport connection to the diameter peer is down."
::= { affirmedSnmpAn3000TrapsNotificationPrefix 89}




anDiameterPeerLinkUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	localhostidentity,
	nodename,
	peerhostidentity,
	peerrealmname,
	realmname,
	affirmedVmSourceIpAddress,
	affirmedVmSourceName
}
STATUS deprecated
DESCRIPTION
"Diameter Peer Transport Connection Up Event"
::= { affirmedSnmpAn3000TrapsNotificationPrefix 90}




anRadiusPeerDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	clientid,
	peername,
	affirmedVmSourceIpAddress,
	affirmedVmSourceName
}
STATUS current
DESCRIPTION
"The RADIUS peer health check failed and this RADIUS peer is declared down."
::= { affirmedSnmpAn3000TrapsNotificationPrefix 91}




anRadiusPeerUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	clientid,
	peername,
	affirmedVmSourceIpAddress,
	affirmedVmSourceName
}
STATUS deprecated
DESCRIPTION
"Radius Peer Up Event"
::= { affirmedSnmpAn3000TrapsNotificationPrefix 92}




anGtppPeerDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	peername,
	affirmedVmSourceIpAddress,
	affirmedVmSourceName
}
STATUS current
DESCRIPTION
"The Transport connection to Gtpp peer is down."
::= { affirmedSnmpAn3000TrapsNotificationPrefix 93}




anGtppPeerUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	peername,
	affirmedVmSourceIpAddress,
	affirmedVmSourceName
}
STATUS deprecated
DESCRIPTION
"Gtpp Peer Up Event"
::= { affirmedSnmpAn3000TrapsNotificationPrefix 94}




anPdnSessionAntiSpoofing NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	imsi,
	servicename,
	affirmedVmSourceIpAddress,
	affirmedVmSourceName
}
STATUS current
DESCRIPTION
"The UE sent an IP packet with an unassigned source address."
::= { affirmedSnmpAn3000TrapsNotificationPrefix 98}




anSgwServiceUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A SGW service is operationally up."
::= { affirmedSnmpAn3000TrapsNotificationPrefix 99}




anSgwServiceDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A SGW service is operationally down."
::= { affirmedSnmpAn3000TrapsNotificationPrefix 100}




anPgwServiceUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A PGW service is operationally up."
::= { affirmedSnmpAn3000TrapsNotificationPrefix 101}




anPgwServiceDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A PGW service is operationally down."
::= { affirmedSnmpAn3000TrapsNotificationPrefix 102}




anGgsnServiceUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A GGSN service is operationally up."
::= { affirmedSnmpAn3000TrapsNotificationPrefix 103}




anGgsnServiceDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A GGSN service is operationally down."
::= { affirmedSnmpAn3000TrapsNotificationPrefix 104}




anApnAvailable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	apnname,
	servicename,
	affirmedVmSourceIpAddress,
	affirmedVmSourceName
}
STATUS current
DESCRIPTION
"An APN is available for use by a specific GW service."
::= { affirmedSnmpAn3000TrapsNotificationPrefix 105}




anApnNotAvailable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	apnname,
	servicename,
	affirmedVmSourceIpAddress,
	affirmedVmSourceName
}
STATUS current
DESCRIPTION
"An APN is not available for use by a specific GW service."
::= { affirmedSnmpAn3000TrapsNotificationPrefix 106}




anCaleaPeerLinkDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	interfacename,
	affirmedVmSourceIpAddress,
	affirmedVmSourceName
}
STATUS current
DESCRIPTION
"The alarm is generated when the transport connection to the CALEA peer is down. It is cleared when connectivity to the CALEA peer is restored."
::= { affirmedSnmpAn3000TrapsNotificationPrefix 140}




anCaleaPeerLinkUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	interfacename,
	affirmedVmSourceIpAddress,
	affirmedVmSourceName
}
STATUS deprecated
DESCRIPTION
"Indicates when the transport connection to the CALEA peer comes up. It is deprecated and will be removed in future releases, as the anCaleaPeerLinkDown alarm delivers all link status change notifications. It is not used by the existing code."
::= { affirmedSnmpAn3000TrapsNotificationPrefix 141}




anGtpPeerUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"GTP Peer Up Event"
::= { affirmedSnmpAn3000TrapsNotificationPrefix 143}




anCaleaTargetsCleared NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The trap is generated when all CALEA targets have been removed and the size of the CALEA target data base becomes zero. It is an informational trap and therefore never cleared."
::= { affirmedSnmpAn3000TrapsNotificationPrefix 162}




anCaleaInterfacesCleared NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This alarm is generated when all Legal Intercept Mediation device Interfaces have been deleted. It is an informational alarm and is never cleared."
::= { affirmedSnmpAn3000TrapsNotificationPrefix 163}




anCaleaUtilizationLow NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The alarm is generated when the Configured Legal Intercept Targets Utilization is greater than 60% and less than 70% of the maximum capacity. It is cleared when the utilization becomes less than or equal to 60%."
::= { affirmedSnmpAn3000TrapsNotificationPrefix 164}




anCaleaUtilizationMedium NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This Alarm is generated when Configured Legal Intercept Targets are above 70% but below 80% of maximum allowed configurable targets. It is cleared when the utilization is less than or equal to 70%."
::= { affirmedSnmpAn3000TrapsNotificationPrefix 165}




anCaleaUtilizationHigh NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This Alarm is generated when Configured Legal Intercept Targets are above 80% but below 90% of maximum allowed targets. It is cleared when the utilization is less than or equal to 80%."
::= { affirmedSnmpAn3000TrapsNotificationPrefix 166}




anCaleaUtilizationCritical NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This Alarm is generated when Configured Legal Intercept Targets are above 90% but below 100% of maximum allowed targets. It is cleared when the utilization is less than or equal to 90%."
::= { affirmedSnmpAn3000TrapsNotificationPrefix 167}




anCaleaCCBufferConfiguredSizeBelowThreshold NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"The alarm is generated when the configured size for the CC buffer on the interface group is less than the minimum threshold value (10MB)."
::= { affirmedSnmpAn3000TrapsNotificationPrefix 189}




anCaleaCCBufferUtilizationThresholdReached NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"This alarm is generated when the buffer utilization threshold is reached for the CC buffer on the interface group."
::= { affirmedSnmpAn3000TrapsNotificationPrefix 190}




anCaleaIRIBufferUtilizationThresholdReached NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"This alarm is generated when the buffer utilization threshold is reached for the IRI buffer on the interface group."
::= { affirmedSnmpAn3000TrapsNotificationPrefix 191}




anCaleaTargetDBMaxSubsLimitReached NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The alarm is generated when the number of entries in the target DB reaches the maximum allowed value of 32,768."
::= { affirmedSnmpAn3000TrapsNotificationPrefix 192}




anCaleaIRIBufferConfiguredSizeBelowThreshold NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"The alarm is generated when the configured size for the IRI buffer on the interface group is less than the minimum threshold value (1 MB)."
::= { affirmedSnmpAn3000TrapsNotificationPrefix 193}




anCaleaIfOrIfGroupConfigChange NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"The alarm is raised when the configuration for a CALEA interface/interface group is modified in any way (added, changed or deleted)."
::= { affirmedSnmpAn3000TrapsNotificationPrefix 194}




anCaleaLITargetCreatedOrDeleted NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The alarm is generated whenever a CALEA Lawful Intercept target is created or deleted."
::= { affirmedSnmpAn3000TrapsNotificationPrefix 195}




anCaleaInterfaceGroupStatusDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	role,
	affirmedVmSourceIpAddress,
	affirmedVmSourceName
}
STATUS current
DESCRIPTION
"The alarm is generated whenever the interface group status changes from up to down. It is cleared when the status changes back to up."
::= { affirmedSnmpAn3000TrapsNotificationPrefix 196}




anCaleaCCBufferDataLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"The alarm is generated whenever CC buffer data is lost because the buffer size was exceeded and inserting additional data in the buffer caused earlier packets to be lost."
::= { affirmedSnmpAn3000TrapsNotificationPrefix 197}




anCaleaIRIBufferDataLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	groupname,
	affirmedVmSourceIpAddress,
	affirmedVmSourceName
}
STATUS current
DESCRIPTION
"The alarm is generated whenever IRI buffer data is lost because the buffer size was exceeded and inserting additional data in the buffer caused earlier packets to be lost."
::= { affirmedSnmpAn3000TrapsNotificationPrefix 198}




anEmergencyCallAttemptFailed NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	reason,
	affirmedVmSourceIpAddress,
	affirmedVmSourceName
}
STATUS current
DESCRIPTION
"This alarm is generated when the system fails to setup emergency bearers for a session due to reasons such as lack of resources or memory or other call processing errors."
::= { affirmedSnmpAn3000TrapsNotificationPrefix 214}




anEmergencyCallDropped NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	reason,
	affirmedVmSourceIpAddress,
	affirmedVmSourceName
}
STATUS current
DESCRIPTION
"This alarm is generated when active emergency bearers are deactivated due to operator intervention such as deactivation initiated through CLI."
::= { affirmedSnmpAn3000TrapsNotificationPrefix 215}




anWagServiceDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A WAG service is operationally down."
::= { affirmedSnmpAn3000TrapsNotificationPrefix 220}




anWagServiceUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"A WAG service is operationally up."
::= { affirmedSnmpAn3000TrapsNotificationPrefix 221}




anEpdgServiceUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"An ePDG service is operationally up."
::= { affirmedSnmpAn3000TrapsNotificationPrefix 230}




anEpdgServiceDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	servicename,
	affirmedVmSourceIpAddress,
	affirmedVmSourceName
}
STATUS current
DESCRIPTION
"An ePDG service is operationally down."
::= { affirmedSnmpAn3000TrapsNotificationPrefix 231}




anGwSubsGrpFileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	subsgroupname,
	subsidfilename,
	affirmedVmSourceIpAddress,
	affirmedVmSourceName
}
STATUS current
DESCRIPTION
"File containing Subscriber IDs configured for the subscriber-group does not exist on the MCC."
::= { affirmedSnmpAn3000TrapsNotificationPrefix 296}




anCaleaUserBanFeatureConfigChange NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	state,
	affirmedVmSourceIpAddress,
	affirmedVmSourceName
}
STATUS current
DESCRIPTION
"This alarm is generated when admin state of Calea User Ban Feature is changed"
::= { affirmedSnmpAn3000TrapsNotificationPrefix 299}




anCaleaCCDataLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ifname,
	affirmedVmSourceIpAddress,
	affirmedVmSourceName
}
STATUS current
DESCRIPTION
"The alarm is generated when CC data is first lost on an interface which is down (and no interface-group is provisioned for target)"
::= { affirmedSnmpAn3000TrapsNotificationPrefix 300}




anCaleaIRIDataLost NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ifname,
	affirmedVmSourceIpAddress,
	affirmedVmSourceName
}
STATUS current
DESCRIPTION
"The alarm is generated when IRI data is first lost on an interface which is down (and no interface-group is provisioned for target)"
::= { affirmedSnmpAn3000TrapsNotificationPrefix 301}




anPfcpPeerDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	gatewayipaddress,
	gatewayname,
	peeripaddress,
	peername,
	affirmedVmSourceIpAddress,
	affirmedVmSourceName
}
STATUS current
DESCRIPTION
"PFCP Peer down indicates that the remote PFCP Peer is not responding to any of the PFCP messages sent to it."
::= { affirmedSnmpAn3000TrapsNotificationPrefix 321}




anPfcpPeerUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	gatewayipaddress,
	gatewayname,
	peeripaddress,
	peername,
	affirmedVmSourceIpAddress,
	affirmedVmSourceName
}
STATUS deprecated
DESCRIPTION
"PFCP Peer is up, running and reachable."
::= { affirmedSnmpAn3000TrapsNotificationPrefix 322}




anCaleaIfGrpSourceProfileConfigChange NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"The alarm is raised when the configuration for a CALEA interface-group-source-profile is modified in any way (added, changed or deleted)."
::= { affirmedSnmpAn3000TrapsNotificationPrefix 323}




anCaleaIfGrpSourceProfileNotFound NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"The alarm is raised when the CALEA subsystem is unable to find an interface-group-source-profile for a dynamic target interface/group."
::= { affirmedSnmpAn3000TrapsNotificationPrefix 324}




anCaleaPdhirNotSupportedForSx3lifTunnelToCPF NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This alarm is generated to indicate control plane will not deliver PDHIR events when CALEA target config is having PDHIR enabled in SX3LIF mode"
::= { affirmedSnmpAn3000TrapsNotificationPrefix 342}




anCaleaDecryptFail NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The alarm is generated when encrypted CALEA Lawful Intercept data can not be decrypted (could be security key mismatch between CPF and UPF)"
::= { affirmedSnmpAn3000TrapsNotificationPrefix 343}




fmSWCompMCMSwitchoverEventData NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassis,
	cpu,
	slot,
	affirmedVmSourceIpAddress,
	affirmedVmSourceName
}
STATUS current
DESCRIPTION
"An MCM switchover has taken place."
::= { affirmedSnmpAn3000TrapsNotificationPrefix 19}




anRedundancyOperState NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	statestring,
	affirmedVmSourceIpAddress,
	affirmedVmSourceName
}
STATUS current
DESCRIPTION
"Indicates whether MCM redundancy is operational. When the standby boots it has 10 minutes to establish redundancy before raising this alarm. If a standby task fails, the system gives 3 minutes to re-established redundancy before raising this alarm."
::= { affirmedSnmpAn3000TrapsNotificationPrefix 107}




anCpuTosTaskState NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	cpu,
	sid,
	statestring,
	affirmedVmSourceIpAddress,
	affirmedVmSourceName
}
STATUS current
DESCRIPTION
"Indicates whether all tos tasks are operationally UP on this CPU. After a card is booted all tasks have 10 minutes to come up before an alarm is issued. If a task goes down, the system gives 3 minutes for the task to come up before issuing this alarm."
::= { affirmedSnmpAn3000TrapsNotificationPrefix 108}




anNewCoreFileDetected NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassis,
	affirmedVmSourceIpAddress,
	affirmedVmSourceName
}
STATUS deprecated
DESCRIPTION
"A new core file is detected on the chassis."
::= { affirmedSnmpAn3000TrapsNotificationPrefix 111}




anfileftpfailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	filepath,
	ip,
	port,
	affirmedVmSourceIpAddress,
	affirmedVmSourceName
}
STATUS current
DESCRIPTION
"Last try to ftp files to remote server failed."
::= { affirmedSnmpAn3000TrapsNotificationPrefix 112}




anForcedSyncStart NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Forced sync of images from active to standby."
::= { affirmedSnmpAn3000TrapsNotificationPrefix 125}




anForcedSyncFailed NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Forced sync failed or timed-out."
::= { affirmedSnmpAn3000TrapsNotificationPrefix 126}




anPortStatusUp NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	port,
	slot,
	affirmedVmSourceIpAddress,
	affirmedVmSourceName
}
STATUS deprecated
DESCRIPTION
"Port Status is UP"
::= { affirmedSnmpAn3000TrapsNotificationPrefix 127}




anfilepurgedduetodiskfull NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	numpurged,
	prefix,
	affirmedVmSourceIpAddress,
	affirmedVmSourceName
}
STATUS current
DESCRIPTION
"Files have been purged from disk since disk purge threshold was crossed (disk was getting close to full)."
::= { affirmedSnmpAn3000TrapsNotificationPrefix 130}




anKernelOptionsModified NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	cpu,
	info,
	sid,
	affirmedVmSourceIpAddress,
	affirmedVmSourceName
}
STATUS current
DESCRIPTION
"Kernel options have been automatically modified on the current module. They will take effect on the reboot. "
::= { affirmedSnmpAn3000TrapsNotificationPrefix 135}




anFormatDisk NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	diskid,
	node,
	affirmedVmSourceIpAddress,
	affirmedVmSourceName
}
STATUS deprecated
DESCRIPTION
"Disk format operation took place."
::= { affirmedSnmpAn3000TrapsNotificationPrefix 138}




anDiskFull NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	diskid,
	slot,
	affirmedVmSourceIpAddress,
	affirmedVmSourceName
}
STATUS obsolete
DESCRIPTION
"Disk full"
::= { affirmedSnmpAn3000TrapsNotificationPrefix 139}




anUEPoolThresholdAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ipversiontype,
	threshold,
	uepoolutilization,
	affirmedVmSourceIpAddress,
	affirmedVmSourceName
}
STATUS current
DESCRIPTION
"This alarm is generated when the configured threshold for UE pool utilization is crossed."
::= { affirmedSnmpAn3000TrapsNotificationPrefix 146}




anDataRecordFailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The system failed to log a data record (i.e. local CDR, HTDR or other such data records).  This failure can occur either at the source generating the data record or at the agent which is responsible for flush the data record to the disk."
::= { affirmedSnmpAn3000TrapsNotificationPrefix 205}




anRemoteMountFailed NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"This alarm is raised when a node cannot reach over the nfs mount to the disk on peer MCM.   For active MCM, the peer MCM is the standby MCM.  For all nodes, the peer MCM is the active MCM."
::= { affirmedSnmpAn3000TrapsNotificationPrefix 211}




anEdrServerConnectionFailed NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	ip,
	name,
	port,
	affirmedVmSourceIpAddress,
	affirmedVmSourceName
}
STATUS current
DESCRIPTION
"The connection to the EDR server has failed."
::= { affirmedSnmpAn3000TrapsNotificationPrefix 222}




anPkix509expiring NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An X509 certificate is approaching expiration"
::= { affirmedSnmpAn3000TrapsNotificationPrefix 232}




anPkix509expired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An X509 certificate has expired"
::= { affirmedSnmpAn3000TrapsNotificationPrefix 233}




anPkix509revoked NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An X509 certificate has been revoked"
::= { affirmedSnmpAn3000TrapsNotificationPrefix 234}




anPkiobjunreachable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Attempts to update a pki object from a remote source have failed for more than 24 hours"
::= { affirmedSnmpAn3000TrapsNotificationPrefix 235}




anPkiobjadded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A new pki object has been added to the system"
::= { affirmedSnmpAn3000TrapsNotificationPrefix 236}




anPkiobjupdated NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An existing pki object has been updated"
::= { affirmedSnmpAn3000TrapsNotificationPrefix 237}




anPkiobjremoved NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A pki object has been removed from the system"
::= { affirmedSnmpAn3000TrapsNotificationPrefix 238}




anPkix509crlnextupdateavailable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The next update of this x509 certificate revocation list is available"
::= { affirmedSnmpAn3000TrapsNotificationPrefix 240}




anReleaseMismatch NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"one or more nodes are running a different tos release than they are intended to be running and neither an upgrade nor a rollback is in progress."
::= { affirmedSnmpAn3000TrapsNotificationPrefix 244}




anPkiobjupdatenotavailable NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Attempts to get an updated version of a pki object from a remote source have failed for more than 24 hours"
::= { affirmedSnmpAn3000TrapsNotificationPrefix 248}




anPkisshauthorizedkeyaddedtouser NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been configured to authenticate ssh for a user"
::= { affirmedSnmpAn3000TrapsNotificationPrefix 249}




anPkisshauthorizedkeyremovedfromuser NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been removed from those that may authenticate ssh for a user"
::= { affirmedSnmpAn3000TrapsNotificationPrefix 250}




anPkisshauthorizedkeyaddedtogroup NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been configured to authenticate ssh for all users in a group"
::= { affirmedSnmpAn3000TrapsNotificationPrefix 251}




anPkisshauthorizedkeyremovedfromgroup NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been removed from those that may authenticate ssh for all users in a group"
::= { affirmedSnmpAn3000TrapsNotificationPrefix 252}




anPkisshtrustedcakeyaddedtocluster NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been trusted as a certificate authority key to validate certificates used to authenticate ssh for any user in the cluster"
::= { affirmedSnmpAn3000TrapsNotificationPrefix 253}




anPkisshtrustedcakeyremovedfromcluster NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key that had been trusted as a certificate authority key to validate certificates used to authenticate ssh for any user in the cluster has been removed"
::= { affirmedSnmpAn3000TrapsNotificationPrefix 254}




anPkisshtrustedcakeyaddedtogroup NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been trusted as a certificate authority key to validate certificates used to authenticate ssh for all users in a group"
::= { affirmedSnmpAn3000TrapsNotificationPrefix 255}




anPkisshtrustedcakeyremovedfromgroup NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key that had been trusted as a certificate authority key to validate certificates used to authenticate ssh for all users in a group has been removed"
::= { affirmedSnmpAn3000TrapsNotificationPrefix 256}




anPkisshuseraddedtoauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"A user has been added to the group list of authorized principals"
::= { affirmedSnmpAn3000TrapsNotificationPrefix 257}




anPkisshuserremovedfromauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"A user has been removed from the group list of authorized principals"
::= { affirmedSnmpAn3000TrapsNotificationPrefix 258}




anPkisshgroupaddedtoauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"All users in a group have been added to the group list of authorized principals"
::= { affirmedSnmpAn3000TrapsNotificationPrefix 259}




anPkisshgroupremovedfromauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS deprecated
DESCRIPTION
"All users in a group have been removed from the group list of authorized principals"
::= { affirmedSnmpAn3000TrapsNotificationPrefix 260}




anfileexportfailure NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	filepath,
	affirmedVmSourceIpAddress,
	affirmedVmSourceName
}
STATUS current
DESCRIPTION
"Last try to export files to the export directory (as per configuration) failed."
::= { affirmedSnmpAn3000TrapsNotificationPrefix 261}




anPkisshnamesaddedtogroupauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"One or mores names have been added to a group authorized principals list"
::= { affirmedSnmpAn3000TrapsNotificationPrefix 262}




anPkissherrorapplyingconfigurationtosshcontrolfiles NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An error has occurred converting pki ssh configuration to ssh authorizedkeys/authorizedprincipals/trustedusercakeys files"
::= { affirmedSnmpAn3000TrapsNotificationPrefix 263}




anPkisshnamesremovedfromauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"One or mores names have been removed from a user authorized principals list"
::= { affirmedSnmpAn3000TrapsNotificationPrefix 264}




anPkisshnamesaddedtoauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"One or mores names have been added to a user authorized principals list"
::= { affirmedSnmpAn3000TrapsNotificationPrefix 265}




anPkisshnamesremovedfromgroupauthorizedprincipals NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"One or mores names have been removed from a group authorized principals list"
::= { affirmedSnmpAn3000TrapsNotificationPrefix 266}




anPkisshmaximumsecuritylevelset NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh security level for the cluster has been changed to maximum"
::= { affirmedSnmpAn3000TrapsNotificationPrefix 267}




anPkisshcompatiblesecuritylevelset NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh security level for the cluster has been changed to compatible"
::= { affirmedSnmpAn3000TrapsNotificationPrefix 268}




anPkisshstricthostkeycheckingsettono NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh strict host key checking for the cluster has been changed to no"
::= { affirmedSnmpAn3000TrapsNotificationPrefix 269}




anPkisshstricthostkeycheckingsettoask NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh strict host key checking for the cluster has been changed to ask"
::= { affirmedSnmpAn3000TrapsNotificationPrefix 270}




anPkisshstricthostkeycheckingsettoyes NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh strict host key checking for the cluster has been changed to yes"
::= { affirmedSnmpAn3000TrapsNotificationPrefix 271}




anPkisshverifyhostkeydnssettono NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh verify host key with dns for the cluster has been changed to no"
::= { affirmedSnmpAn3000TrapsNotificationPrefix 272}




anPkisshverifyhostkeydnssettoyes NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh verify host key with dns for the cluster has been changed to yes"
::= { affirmedSnmpAn3000TrapsNotificationPrefix 273}




anPkisshverifyhostkeydnssettoask NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh verify host key with dns for the cluster has been changed to ask"
::= { affirmedSnmpAn3000TrapsNotificationPrefix 274}




anPkisshknownhostcakeyremoved NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh public key of a certificate authority has been removed from ssh_known_hosts."
::= { affirmedSnmpAn3000TrapsNotificationPrefix 275}




anPkisshknownhostcakeyadded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh public key of a certificate authority has been added to ssh_known_hosts to validate the host certificates presented on connection by ssh/scp/sftp to external servers"
::= { affirmedSnmpAn3000TrapsNotificationPrefix 276}




anPkisshknownhostkeyremoved NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been removed from ssh_known_hosts."
::= { affirmedSnmpAn3000TrapsNotificationPrefix 277}




anPkisshknownhostkeyadded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh public key has been added to ssh_known_hosts to validate connections by ssh/scp/sftp to external servers"
::= { affirmedSnmpAn3000TrapsNotificationPrefix 278}




anPkisshlocalhostcertificatereplaced NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The previous local ssh host certificate has been replaced by a new ssh certificate."
::= { affirmedSnmpAn3000TrapsNotificationPrefix 279}




anPkisshlocalhostcertificateremoved NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The local ssh host certificate has been removed."
::= { affirmedSnmpAn3000TrapsNotificationPrefix 280}




anPkisshlocalhostcertificateadded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The local ssh host certificate has been added."
::= { affirmedSnmpAn3000TrapsNotificationPrefix 281}




anPkisshrevoked NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh key or certificate has been revoked by an ssh krl file"
::= { affirmedSnmpAn3000TrapsNotificationPrefix 282}




anPkimanuallyrevoked NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh key or certificate has been manually reported as revoked by a revoke cli command"
::= { affirmedSnmpAn3000TrapsNotificationPrefix 283}




anPkisshuserkrlreplaced NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A new or updated pki ssh krl file has replaced the previous ssh krl as the RevokedKeys file to the sshd servers."
::= { affirmedSnmpAn3000TrapsNotificationPrefix 285}




anPkisshuserkrladded NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A pki ssh krl file has been added as the RevokedKeys file to the sshd servers."
::= { affirmedSnmpAn3000TrapsNotificationPrefix 286}




anPkisshuserkrlremoved NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The ssh krl file that was providing a list of revoked ssh keys has been removed from RevokedKeys on the sshd servers."
::= { affirmedSnmpAn3000TrapsNotificationPrefix 287}




anPkisshcertexpiring NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh certificate is approaching expiration"
::= { affirmedSnmpAn3000TrapsNotificationPrefix 288}




anPkisshcertexpired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"An ssh certificate has expired"
::= { affirmedSnmpAn3000TrapsNotificationPrefix 289}




anNewMemImageFileDetected NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassis,
	affirmedVmSourceIpAddress,
	affirmedVmSourceName
}
STATUS deprecated
DESCRIPTION
"A new memory image file is detected on the chassis"
::= { affirmedSnmpAn3000TrapsNotificationPrefix 298}




anNewFaultFileDetected NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	chassis,
	affirmedVmSourceIpAddress,
	affirmedVmSourceName
}
STATUS current
DESCRIPTION
"A new fault file has been detected on the chassis"
::= { affirmedSnmpAn3000TrapsNotificationPrefix 309}




anNodeRebootRequired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"Node needs to be rebooted because one or more of the following have changed on the node. 1. isolcpus 2. core-layout"
::= { affirmedSnmpAn3000TrapsNotificationPrefix 332}




anRadiusAccountingOnMsgNotSent NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"PGW is not accepting sessions using RADIUS towards peer Radius server due to operator configuration"
::= { affirmedSnmpAn3000TrapsNotificationPrefix 334}




anClusterRebootRequired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	cid,
	affirmedVmSourceIpAddress,
	affirmedVmSourceName
}
STATUS current
DESCRIPTION
"The cluster needs to be rebooted because one or more of the following have changed on one or more nodes in the cluster. 1. isolcpus 2. core-layout 3. max-packet-size"
::= { affirmedSnmpAn3000TrapsNotificationPrefix 338}




anTaskTermination NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	name,
	affirmedVmSourceIpAddress,
	affirmedVmSourceName
}
STATUS current
DESCRIPTION
"A task has been terminated"
::= { affirmedSnmpAn3000TrapsNotificationPrefix 354}




anThresholdCrossingAlarm NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"A threshold has been crossed."
::= { affirmedSnmpAn3000TrapsNotificationPrefix 68}




anLicenseCapacityEnforcement NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Approaching or crossed licensed service capacity enforcement level. Upon reaching X percent of the capacity enforcement level, a major event will be generated. The event will become critical as the enforcement level is crossed."
::= { affirmedSnmpAn3000TrapsNotificationPrefix 223}




anLicenseCapacityLimit NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Approaching or crossed licensed service capacity limit. Upon reaching X percent of the capacity limit, a major event will be generated. The event will become critical as the limit is crossed."
::= { affirmedSnmpAn3000TrapsNotificationPrefix 224}




anLicenseLifetimeEnforcement NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Approaching or passed licensed service enforcement expiration date. Upon reaching X percent of the license expiration date, a major event will be generated. The event will become critical as the expiration is passed."
::= { affirmedSnmpAn3000TrapsNotificationPrefix 225}




anLicenseLifetime NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Approaching or passed licensed service lifetime. Upon reaching X percent of the license lifetime, a major event will be generated. The event will become critical as the lifetime is passed."
::= { affirmedSnmpAn3000TrapsNotificationPrefix 226}




anLicensePlsSeparation NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"The MCC has separated from the PLS server and enter local license management state. During this period, the MCC will manage licenses based on the last PLS view. Services will be impacted if the server is not restored within the grace period."
::= { affirmedSnmpAn3000TrapsNotificationPrefix 227}




anLicensePlsGraceExpired NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails,
	affirmedPotentialImpact,
	affirmedCorrectiveAction,
	affirmedVmSourceIpAddress,
	affirmedVmSourceName
}
STATUS current
DESCRIPTION
"Connection to the PLS server has not reestablished within the grace period so license-able services are terminated."
::= { affirmedSnmpAn3000TrapsNotificationPrefix 228}





END
