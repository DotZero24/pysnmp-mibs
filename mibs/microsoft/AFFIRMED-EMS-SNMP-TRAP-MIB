AFFIRMED-EMS-SNMP-TRAP-MIB DEFINITIONS ::= BEGIN
IMPORTS
	MODULE-IDENTITY,
	OBJECT-TYPE,
	Integer32,
	NOTIFICATION-TYPE                       FROM SNMPv2-SMI
	DisplayString                           FROM SNMPv2-TC
	affirmedSnmp                            FROM AFFIRMED-SNMP-MIB
	affirmedSnmpNotifications               FROM AFFIRMED-SNMP-MIB
	affirmedAlarmSeqId,
	affirmedAlarmDateTime,
	affirmedAlarmChassisName,
	affirmedAlarmSourceId,
	affirmedAlarmSeverity,
	affirmedAlarmRefSeqId,
	affirmedAlarmDetails                    FROM AFFIRMED-ALARM-MIB;


affirmedSnmpTraps MODULE-IDENTITY
	LAST-UPDATED "201105160000Z"
	ORGANIZATION
	"Affired Networks, Inc."
	CONTACT-INFO
	"Affirmed Networks, Inc.
	     35 Nagog Park
	     Acton, MA
	     USA "
	DESCRIPTION
	"Traps MIB objects"
	::= { affirmedSnmpNotifications 5}
-- top level structure
--
affirmedSnmpTrapsScalars       OBJECT IDENTIFIER ::= { affirmedSnmpTraps 1 }
affirmedSnmpTrapsTables        OBJECT IDENTIFIER ::= { affirmedSnmpTraps 2 }
affirmedSnmpTrapsNotifications OBJECT IDENTIFIER ::= { affirmedSnmpTraps 3 }
affirmedSnmpTrapsNotificationPrefix  OBJECT IDENTIFIER
                                   ::= { affirmedSnmpTrapsNotifications 0 }
affirmedSnmpTrapsNotificationObjects OBJECT IDENTIFIER
                                   ::= { affirmedSnmpTrapsNotifications 1 }

emsDBReplicationDown NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails
}
STATUS current
DESCRIPTION
"Database replication is down."
::= { affirmedSnmpTrapsNotificationPrefix 1}

emsDBReplicationLagBehind NOTIFICATION-TYPE
OBJECTS   {
	affirmedAlarmSeqId,
	affirmedAlarmDateTime,
	affirmedAlarmChassisName,
	affirmedAlarmSourceId,
	affirmedAlarmSeverity,
	affirmedAlarmRefSeqId,
	affirmedAlarmDetails
}
STATUS current
DESCRIPTION
"Database replication is lagging behind."
::= { affirmedSnmpTrapsNotificationPrefix 2}

END
