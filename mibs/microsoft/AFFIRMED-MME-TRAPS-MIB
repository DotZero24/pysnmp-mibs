AFFIRMED-MME-TRAPS-MIB DEFINITIONS ::= BEGIN

    IMPORTS
        MODULE-IDENTITY, OBJECT-TYPE, NOTIFICATION-TYPE,
        Integer32, Counter32, Gauge32, Unsigned32, Counter64, enterprises
            FROM SNMPv2-SMI
        mgmt, NetworkAddress, IpAddress,
        Counter, Gauge, TimeTicks
            FROM RFC1155-SMI
        PhysAddress, DisplayString, DateAndTime, TruthValue,
        AutonomousType, RowPointer, RowStatus, TEXTUAL-CONVENTION
            FROM SNMPv2-TC
        SnmpAdminString
            FROM SNMP-FRAMEWORK-MIB          -- [RFC3411]
        Ipv6Address
            FROM IPV6-TC
        alarmListName, alarmModelIndex, alarmModelState,
        alarmActiveDateAndTime, alarmActiveIndex
           FROM ALARM-MIB                    -- [RFC3877]
        ItuPerceivedSeverity
           FROM ITU-ALARM-TC-MIB;


affirmedSnmpMmeTraps MODULE-IDENTITY
    LAST-UPDATED "201609010000Z"
	ORGANIZATION
	"Affirmed Networks, Inc."
	CONTACT-INFO
	"Affirmed Networks, Inc.
	     35 Nagog Park
	     Acton, MA
	     USA "
	DESCRIPTION
	"Traps for MME/SGSN"
	REVISION
	"201609010000Z"
	DESCRIPTION
	"MME10.0 Release"
	::= { enterprises 37963 4 0 6 }


    anMmeTrapAlarms                 OBJECT IDENTIFIER  ::= { affirmedSnmpMmeTraps 1 }

    anMmeTrapEvents                 OBJECT IDENTIFIER  ::= { affirmedSnmpMmeTraps 2 }

    anMmeNotificationVars           OBJECT IDENTIFIER  ::= { affirmedSnmpMmeTraps 3 }


    anMmeAlarmState                 OBJECT-TYPE
        SYNTAX      SnmpAdminString (SIZE(1..6))
        MAX-ACCESS  read-only
        STATUS      current
        DESCRIPTION
            "Alarm state::
             create : alarm is set
             delete : alarm is cleared
             log    : log message"
        ::= { anMmeNotificationVars 1 }

    anMmeAlarmSeverity                 OBJECT-TYPE
        SYNTAX      ItuPerceivedSeverity
        MAX-ACCESS  read-only
        STATUS      current
        DESCRIPTION
            "Alarm severity::
             1: CLEARED
             2: INDETERMINATE
             3: CRITICAL
             4: MAJOR
             5: MINOR
             6: WARNING"
        ::= { anMmeNotificationVars 2 }

     anMmeEntityTag          OBJECT-TYPE
        SYNTAX      SnmpAdminString (SIZE(0..512))
        MAX-ACCESS  read-only
        STATUS      current
        DESCRIPTION
            "location of alarm resource descripted by location-information-type."
        ::= { anMmeNotificationVars 3 }

    anMmeSubentityInfo         OBJECT-TYPE
        SYNTAX      SnmpAdminString (SIZE(0..512))
        MAX-ACCESS  read-only
        STATUS      current
        DESCRIPTION
            "additional information of entity"
        ::= { anMmeNotificationVars 4 }

     anMmeLocationGateway         OBJECT-TYPE
        SYNTAX      SnmpAdminString (SIZE(0..512))
        MAX-ACCESS  read-only
        STATUS      deprecated
        DESCRIPTION
            "Gateway Location Information"
        ::= { anMmeNotificationVars 5 }

     anMmeReason         OBJECT-TYPE
        SYNTAX      SnmpAdminString (SIZE(0..512))
        MAX-ACCESS  read-only
        STATUS      current
        DESCRIPTION
            "Reason Information"
        ::= { anMmeNotificationVars 6 }

     anMmeAlarmDateAndTime        OBJECT-TYPE
        SYNTAX      DateAndTime
        MAX-ACCESS  read-only
        STATUS      current
        DESCRIPTION
            "Reason Information"
        ::= { anMmeNotificationVars 7 }

     anMmeGroupKey                OBJECT-TYPE
        SYNTAX      SnmpAdminString (SIZE(0..512))
        MAX-ACCESS  read-only
        STATUS      current
        DESCRIPTION
            "Group Key"
        ::= { anMmeNotificationVars 8 }

     anMmeSequenceNumber                OBJECT-TYPE
        SYNTAX      Unsigned32
        MAX-ACCESS  read-only
        STATUS      current
        DESCRIPTION
            "Sequence Number"
        ::= { anMmeNotificationVars 9 }

     anMmeFirstEvent                OBJECT-TYPE
        SYNTAX      DateAndTime
        MAX-ACCESS  read-only
        STATUS      current
        DESCRIPTION
            "Time of first occurance of this alarm"
        ::= { anMmeNotificationVars 10 }

      anMmeLastEvent                OBJECT-TYPE
        SYNTAX      DateAndTime
        MAX-ACCESS  read-only
        STATUS      current
        DESCRIPTION
            "Time of last occurance of this alarm"
        ::= { anMmeNotificationVars 11 }

      anMmeLocation                OBJECT-TYPE
        SYNTAX      SnmpAdminString (SIZE(0..512))
        MAX-ACCESS  read-only
        STATUS      current
        DESCRIPTION
            "Location of the entity that generated the alarm"
        ::= { anMmeNotificationVars 12 }

     anMmeService                OBJECT-TYPE
        SYNTAX      SnmpAdminString (SIZE(0..512))
        MAX-ACCESS  read-only
        STATUS      current
        DESCRIPTION
            "Service of the entity that generated the alarm"
        ::= { anMmeNotificationVars 13 }

      anMmeAlarmIndex                OBJECT-TYPE
        SYNTAX      Unsigned32
        MAX-ACCESS  read-only
        STATUS      current
        DESCRIPTION
            "Alarm Index"
        ::= { anMmeNotificationVars 14 }



    anMmeTrapAlarmNm1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "One or more VM types are not available."
     -- REPAIR-ACTION
     --     "Check current status as reflected by the status system command versus configured
     --      services and units. Analyze the list of missing units in the reason text
     --      field of this alarm and add them to the configuration and unlock them."
     -- ENTITY-TYPE
     --     "system"
     --
        ::= { anMmeTrapAlarms 65536001 }

    anMmeTrapAlarmNm1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A configured VM is currently unlocked and disabled."
     -- REPAIR-ACTION
     --     "Check the health of the related server, check cables. Consider locking
     --      and unlocking the callP VM. Contact your next level support if necessary."
     -- ENTITY-TYPE
     --     "system"
     --
        ::= { anMmeTrapAlarms 65536002 }

    anMmeTrapAlarmNm1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Software upgrade state"
     -- REPAIR-ACTION
     --     "This alarm will automatically clear when the upgrade state ends, either
     --      normally or forcibly, as controlled by the software upgrade-state commands."
     -- ENTITY-TYPE
     --     "system"
     --
        ::= { anMmeTrapAlarms 65536003 }

    anMmeTrapAlarmNm1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 65536099 }

    anMmeTrapAlarmResmon1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The Trace file system is full."
     -- REPAIR-ACTION
     --     "Consider changing the parition size."
     -- ENTITY-TYPE
     --     "system"
     --
        ::= { anMmeTrapAlarms 66191361 }

    anMmeTrapAlarmResmon1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 66191459 }

    anMmeTrapAlarmGaBilling1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Collected charging information has crossed disk usage thresholds."
     -- REPAIR-ACTION
     --     "Off-load collected charging information from the disk or adjust the backup
     --      retention interval at epc interface ga ga-if backup-file-retention.  Alarm
     --      thresholds are configurable at epc interface ga ga-if disk-alarm-thresholds.
     --      "
     -- ENTITY-TYPE
     --     "system"
     --
        ::= { anMmeTrapAlarms 133693441 }

    anMmeTrapAlarmGaBilling1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "CGF connection status"
     -- REPAIR-ACTION
     --     "Check the health of the remote equipment and the health of the IP network."
     -- ENTITY-TYPE
     --     "cgf"
     --
        ::= { anMmeTrapAlarms 133693443 }

    anMmeTrapAlarmGaBilling1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 133693539 }

    anMmeTrapAlarmLi1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "LI data is out of synchronization."
     -- REPAIR-ACTION
     --     "No immediate action required. The active and standby callP VMs (if available)
     --      automatically attempt to resynchronize with each other. If condition persists,
     --      contact your next level of support."
     -- ENTITY-TYPE
     --     "system"
     --
        ::= { anMmeTrapAlarms 133758977 }

    anMmeTrapAlarmLi1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Target database is at predefined capacity level or is full."
     -- REPAIR-ACTION
     --     "No action required"
     -- ENTITY-TYPE
     --     "system"
     --
        ::= { anMmeTrapAlarms 133758978 }

    anMmeTrapAlarmLi1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Number of active targets exceed the provisioned active targets."
     -- REPAIR-ACTION
     --     "Increase the provisioning attribute maxActiveTargets value."
     -- ENTITY-TYPE
     --     "system"
     --
        ::= { anMmeTrapAlarms 133758979 }

    anMmeTrapAlarmLi1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failed to establish connection to the ADMF."
     -- REPAIR-ACTION
     --     "Check the configured admf-ip-address and admf-port under "epc interface
     --      x lig", and check the health of the IP network."
     -- ENTITY-TYPE
     --     "x1"
     --
        ::= { anMmeTrapAlarms 133758980 }

    anMmeTrapAlarmLi1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failed to establish connection to one or more DF2s."
     -- REPAIR-ACTION
     --     "Verify the health of DF2 and IP network."
     -- ENTITY-TYPE
     --     "x2"
     --
        ::= { anMmeTrapAlarms 133758981 }

    anMmeTrapAlarmLi1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected in the LI Manager process."
     -- REPAIR-ACTION
     --     "Contact your next level of support. Consider switching over to the standby
     --      callP VM and then locking and unlocking the former active, now standby,
     --      callP VM."
     -- ENTITY-TYPE
     --     "system"
     --
        ::= { anMmeTrapAlarms 133758982 }

    anMmeTrapAlarmLi1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failed to establish connection to one or more DF3s."
     -- REPAIR-ACTION
     --     "Verify the health of DF3 and IP network."
     -- ENTITY-TYPE
     --     "x3"
     --
        ::= { anMmeTrapAlarms 133758983 }

    anMmeTrapAlarmLi1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected in the LI Agent process."
     -- REPAIR-ACTION
     --     "Contact your next level of support. Consider switching over to the standby
     --      callP VM and then locking and unlocking the former active, now standby,
     --      callP VM."
     -- ENTITY-TYPE
     --     "system"
     --
        ::= { anMmeTrapAlarms 133758984 }

    anMmeTrapAlarmLi1308       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failed to establish connection to the named DF2."
     -- REPAIR-ACTION
     --     "Verify the health of DF2 and IP network."
     -- ENTITY-TYPE
     --     "x2-if df"
     --
        ::= { anMmeTrapAlarms 133758985 }

    anMmeTrapAlarmLi1309       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failed to establish connection to the named DF3."
     -- REPAIR-ACTION
     --     "Verify the health of DF3 and IP network."
     -- ENTITY-TYPE
     --     "x3-if df"
     --
        ::= { anMmeTrapAlarms 133758986 }

    anMmeTrapAlarmLi1310       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "LI buffering for IRI messages is occurring, buffer utilization is reported."
     -- REPAIR-ACTION
     --     "Verify the health of DF2 and IP network. If the reason string includes
     --      a warning that the buffer size is reduced due to VM memory size allocation,
     --      please check 'size-mem' from 'show vm service rm detail' and consider redeploying
     --      the RM VM with more memory to accommodate LI buffering."
     -- ENTITY-TYPE
     --     "x2-if df"
     --
        ::= { anMmeTrapAlarms 133758987 }

    anMmeTrapAlarmLi1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 133759075 }

    anMmeTrapAlarmMmeRm1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Data maintained by the MME Resource Manager is out of synchronization."
     -- REPAIR-ACTION
     --     "No immediate action required. The active and standby callP VMs (if available)
     --      automatically attempt to resynchronize with each other. If condition persists,
     --      contact product support organization."
     -- ENTITY-TYPE
     --     "system"
     --
        ::= { anMmeTrapAlarms 133824513 }

    anMmeTrapAlarmMmeRm1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization. Consider switching over to the standby
     --      callP VM and then locking and unlocking the former active, now standby,
     --      callP VM."
     -- ENTITY-TYPE
     --     "system"
     --
        ::= { anMmeTrapAlarms 133824514 }

    anMmeTrapAlarmMmeRm1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A critical MME application is missing."
     -- REPAIR-ACTION
     --     "Verify that for each listed critical application, at least one callP VM
     --      is added, loaded, and unlocked through the AMF CLI."
     -- ENTITY-TYPE
     --     "system"
     --
        ::= { anMmeTrapAlarms 133824515 }

    anMmeTrapAlarmMmeRm1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Unknown RAI received."
     -- REPAIR-ACTION
     --     "Use the CLI command "show epc service-area routing-area-unknown" to list
     --      the unknown RAI. Determine if the access equipment is mis-configured or
     --      if the SGSN needs to support those routing areas. If the latter, then use
     --      the CLI command "set epc service-area routing-area" to configure additional
     --      routing areas for the applicable RNC and NSE on that SGSN. "
     -- ENTITY-TYPE
     --     "system"
     --
        ::= { anMmeTrapAlarms 133824516 }

    anMmeTrapAlarmMmeRm1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 133824611 }

    anMmeTrapAlarmMmeS1M1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected. "
     -- REPAIR-ACTION
     --     "Contact product support organization. Consider switching over to the standby
     --      callP VM and then locking and unlocking the former active, now standby,
     --      callP VM. "
     -- ENTITY-TYPE
     --     "system"
     --
        ::= { anMmeTrapAlarms 133890051 }

    anMmeTrapAlarmMmeS1M1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of enodeBs has been reached."
     -- REPAIR-ACTION
     --     "Correct the configuration on the MME by adding the S1Listener callP VMs
     --      or by reducing the number of enodeBs configured in the network"
     -- ENTITY-TYPE
     --     "system"
     --
        ::= { anMmeTrapAlarms 133890052 }

    anMmeTrapAlarmMmeS1M1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of tracking areas has been reached."
     -- REPAIR-ACTION
     --     "None."
     -- ENTITY-TYPE
     --     "system"
     --
        ::= { anMmeTrapAlarms 133890053 }

    anMmeTrapAlarmMmeS1M1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "One or more enodeB connections are being refused."
     -- REPAIR-ACTION
     --     "Check configuration of eNodeBs and MME."
     -- ENTITY-TYPE
     --     "system"
     --
        ::= { anMmeTrapAlarms 133890054 }

    anMmeTrapAlarmMmeS1M1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "One or more enodeBs are no longer reachable."
     -- REPAIR-ACTION
     --     "Check health of enodeB and IP network."
     -- ENTITY-TYPE
     --     "system"
     --
        ::= { anMmeTrapAlarms 133890055 }

    anMmeTrapAlarmMmeS1M1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "An incorrect MME code was received from the MME."
     -- REPAIR-ACTION
     --     "Verify if MME is configured correctly."
     -- ENTITY-TYPE
     --     "system"
     --
        ::= { anMmeTrapAlarms 133890056 }

    anMmeTrapAlarmMmeS1M1308       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of MCEs has been reached"
     -- REPAIR-ACTION
     --     "Correct the configuration on the MME by adding the S1Listener callP VMs
     --      or by reducing the number of MCEs configured in the network. Or adjusting
     --      the configured limit under epc engineering s1-capacity max-enodebs."
     -- ENTITY-TYPE
     --     "system"
     --
        ::= { anMmeTrapAlarms 133890057 }

    anMmeTrapAlarmMmeS1M1309       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of service areas has been reached"
     -- REPAIR-ACTION
     --     "Contact your next level of support."
     -- ENTITY-TYPE
     --     "system"
     --
        ::= { anMmeTrapAlarms 133890058 }

    anMmeTrapAlarmMmeS1M1310       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "One or more MCEs are no longer reachable"
     -- REPAIR-ACTION
     --     "Check health of MCEs and IP network."
     -- ENTITY-TYPE
     --     "system"
     --
        ::= { anMmeTrapAlarms 133890059 }

    anMmeTrapAlarmMmeS1M1311       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "EnodeB SCTP Congestion."
     -- REPAIR-ACTION
     --     "Check health of eNodeBs and the SCTP associations."
     -- ENTITY-TYPE
     --     "system"
     --
        ::= { anMmeTrapAlarms 133890060 }

    anMmeTrapAlarmMmeS1M1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 133890147 }

    anMmeTrapAlarmMmeUpsm1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All RADIUS peers provisioned for use by the Fxa interface are unreachable."
     -- REPAIR-ACTION
     --     "Verify the health of the remote equipment and the health of the IP network."
     -- ENTITY-TYPE
     --     "system"
     --
        ::= { anMmeTrapAlarms 133955585 }

    anMmeTrapAlarmMmeUpsm1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of S11 paths has been reached."
     -- REPAIR-ACTION
     --     "Contact product support organization."
     -- ENTITY-TYPE
     --     "system"
     --
        ::= { anMmeTrapAlarms 133955587 }

    anMmeTrapAlarmMmeUpsm1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of S10 paths has been reached."
     -- REPAIR-ACTION
     --     "Contact product support organization."
     -- ENTITY-TYPE
     --     "system"
     --
        ::= { anMmeTrapAlarms 133955588 }

    anMmeTrapAlarmMmeUpsm1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of Gn paths has been reached."
     -- REPAIR-ACTION
     --     "Contact product support organization."
     -- ENTITY-TYPE
     --     "system"
     --
        ::= { anMmeTrapAlarms 133955589 }

    anMmeTrapAlarmMmeUpsm1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of S3 paths has been reached."
     -- REPAIR-ACTION
     --     "Contact product support organization."
     -- ENTITY-TYPE
     --     "system"
     --
        ::= { anMmeTrapAlarms 133955590 }

    anMmeTrapAlarmMmeUpsm1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure of one or more GTP paths."
     -- REPAIR-ACTION
     --     "Check health of remote SGWs, MMEs, SGSN eANs or MBMS-GWs, and IP network."
     -- ENTITY-TYPE
     --     "system"
     --
        ::= { anMmeTrapAlarms 133955591 }

    anMmeTrapAlarmMmeUpsm1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of S4 paths has been reached."
     -- REPAIR-ACTION
     --     "Contact product support organization."
     -- ENTITY-TYPE
     --     "system"
     --
        ::= { anMmeTrapAlarms 133955592 }

    anMmeTrapAlarmMmeUpsm1308       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of S16 paths has been reached."
     -- REPAIR-ACTION
     --     "Contact product support organization."
     -- ENTITY-TYPE
     --     "system"
     --
        ::= { anMmeTrapAlarms 133955593 }

    anMmeTrapAlarmMmeUpsm1309       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of Sv paths has been reached."
     -- REPAIR-ACTION
     --     "Contact product support organization."
     -- ENTITY-TYPE
     --     "system"
     --
        ::= { anMmeTrapAlarms 133955594 }

    anMmeTrapAlarmMmeUpsm1310       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Maximum number of Sm paths has been reached."
     -- REPAIR-ACTION
     --     "Contact your next level of support."
     -- ENTITY-TYPE
     --     "system"
     --
        ::= { anMmeTrapAlarms 133955595 }

    anMmeTrapAlarmMmeUpsm1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 133955683 }

    anMmeTrapAlarmMmeIlf1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Data maintained by the MME IMSI Locator Function is out of synchronization."
     -- REPAIR-ACTION
     --     "No immediate action required. The active and standby callP VMs (if available)
     --      automatically attempt to resynchronize with each other. If condition persists,
     --      contact product support organization."
     -- ENTITY-TYPE
     --     "system"
     --
        ::= { anMmeTrapAlarms 134021121 }

    anMmeTrapAlarmMmeIlf1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization. Consider switching over to the standby
     --      callP VM and then locking and unlocking the former active, now standby,
     --      callP VM."
     -- ENTITY-TYPE
     --     "system"
     --
        ::= { anMmeTrapAlarms 134021122 }

    anMmeTrapAlarmMmeIlf1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 134021219 }

    anMmeTrapAlarmMmeS1Server1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "EnodeB Process creation failed."
     -- REPAIR-ACTION
     --     "Check the health of the 'blade/vm' supporting this callP VM (as identified
     --      in the ref-entity-tag of the alarm). "
     -- ENTITY-TYPE
     --     "mme-s1-interface"
     --
        ::= { anMmeTrapAlarms 134086657 }

    anMmeTrapAlarmMmeS1Server1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization.  Consider locking and unlocking the
     --      callP VM."
     -- ENTITY-TYPE
     --     "mme-s1-interface"
     --
        ::= { anMmeTrapAlarms 134086658 }

    anMmeTrapAlarmMmeS1Server1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "mme-s1-interface"
     --
        ::= { anMmeTrapAlarms 134086755 }

    anMmeTrapAlarmMmeS1Enb1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization.  Consider locking and unlocking the
     --      callP VM."
     -- ENTITY-TYPE
     --     "mme-s1-interface"
     --
        ::= { anMmeTrapAlarms 134152193 }

    anMmeTrapAlarmMmeS1Enb1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "mme-s1-interface"
     --
        ::= { anMmeTrapAlarms 134152291 }

    anMmeTrapAlarmMmeDc1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Diameter peer is unreachable."
     -- REPAIR-ACTION
     --     "Verify health of the HSS and/or EIR and the IP network."
     -- ENTITY-TYPE
     --     "mme-diameter-peer"
     --
        ::= { anMmeTrapAlarms 134217729 }

    anMmeTrapAlarmMmeDc1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization.  Consider locking and unlocking the
     --      callP VM."
     -- ENTITY-TYPE
     --     "system"
     --
        ::= { anMmeTrapAlarms 134217730 }

    anMmeTrapAlarmMmeDc1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are no peers on the Diameter Client that supports S6a interface."
     -- REPAIR-ACTION
     --     "Verify health of the HSS and the IP network."
     -- ENTITY-TYPE
     --     "system"
     --
        ::= { anMmeTrapAlarms 134217731 }

    anMmeTrapAlarmMmeDc1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are no peers on the Diameter Client that supports S13 interface."
     -- REPAIR-ACTION
     --     "Verify health of the EIR and the IP network."
     -- ENTITY-TYPE
     --     "system"
     --
        ::= { anMmeTrapAlarms 134217732 }

    anMmeTrapAlarmMmeDc1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The Diameter Client application is experiencing congestion."
     -- REPAIR-ACTION
     --     "No immediate action is required by the operator, but if the condition persists,
     --      investigate the HSS and/or DIAMETER agent's performance."
     -- ENTITY-TYPE
     --     "system"
     --
        ::= { anMmeTrapAlarms 134217733 }

    anMmeTrapAlarmMmeDc1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are no peers on the Diameter Client that support SLg interface."
     -- REPAIR-ACTION
     --     "Verify the correct peers are configured on the MME.  Also verify IP connectivity
     --      to the peer from the MME."
     -- ENTITY-TYPE
     --     "system"
     --
        ::= { anMmeTrapAlarms 134217734 }

    anMmeTrapAlarmMmeDc1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are no peers on the Diameter Client that support SGd interface."
     -- REPAIR-ACTION
     --     "Verify the correct peers are configured on the MME.  Also verify IP connectivity
     --      to the peer from the MME."
     -- ENTITY-TYPE
     --     "system"
     --
        ::= { anMmeTrapAlarms 134217735 }

    anMmeTrapAlarmMmeDc1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are no peers on the Diameter Client that support T6a interface."
     -- REPAIR-ACTION
     --     "Verify the correct peers are configured on the C-SGN/MME.  Also verify
     --      IP connectivity to the peer from the C-SGN/MME."
     -- ENTITY-TYPE
     --     "system"
     --
        ::= { anMmeTrapAlarms 134217736 }

    anMmeTrapAlarmMmeDc1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 134217827 }

    anMmeTrapAlarmMmeSc1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Attach success rate(E-UTRAN) has fallen below the prov threshold."
     -- REPAIR-ACTION
     --     "Examine the mmeMm attach failure counters and verify the health of the
     --      network."
     -- ENTITY-TYPE
     --     "system"
     --
        ::= { anMmeTrapAlarms 134283266 }

    anMmeTrapAlarmMmeSc1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Session act success rate(E-UTRAN) has fallen below the prov threshold."
     -- REPAIR-ACTION
     --     "Examine the mmeSm default bearer activation failure counters and verify
     --      the health of the network."
     -- ENTITY-TYPE
     --     "system"
     --
        ::= { anMmeTrapAlarms 134283267 }

    anMmeTrapAlarmMmeSc1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Bearer act success rate(E-UTRAN) has fallen below the prov threshold."
     -- REPAIR-ACTION
     --     "Examine the mmeSm dedicated bear activation failure counters and verify
     --      the health of the network."
     -- ENTITY-TYPE
     --     "system"
     --
        ::= { anMmeTrapAlarms 134283268 }

    anMmeTrapAlarmMmeSc1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Subscriber data is out of synchronization."
     -- REPAIR-ACTION
     --     "No immediate action required. The active and standby callP VMs (if available)
     --      automatically attempt to resynchronize with each other. If condition persists,
     --      contact product support organization."
     -- ENTITY-TYPE
     --     "system"
     --
        ::= { anMmeTrapAlarms 134283269 }

    anMmeTrapAlarmMmeSc1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization. Consider switching over to the standby
     --      callP VM and then locking and unlocking the former active, now standby,
     --      callP VM."
     -- ENTITY-TYPE
     --     "system"
     --
        ::= { anMmeTrapAlarms 134283270 }

    anMmeTrapAlarmMmeSc1310       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The SC application is experiencing congestion."
     -- REPAIR-ACTION
     --     "No immediate action is required by the operator. The Subscriber Control
     --      function triggers abatement action when the congestion level exceeds the
     --      configured threshold."
     -- ENTITY-TYPE
     --     "system"
     --
        ::= { anMmeTrapAlarms 134283271 }

    anMmeTrapAlarmMmeSc1311       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address congestion overload."
     -- REPAIR-ACTION
     --     "No action required by the operator. The Subscriber Control function is
     --      taking the abatement action described in the alarm."
     -- ENTITY-TYPE
     --     "system"
     --
        ::= { anMmeTrapAlarms 134283272 }

    anMmeTrapAlarmMmeSc1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The no. of attached subscribers is approaching the max allowed for this SU."
     -- REPAIR-ACTION
     --     "No immediate action required by the operator. The Subscriber Control function
     --      triggers abatement action on a per MPU basis when the attached subscriber
     --      count exceeds the configured threshold."
     -- ENTITY-TYPE
     --     "system"
     --
        ::= { anMmeTrapAlarms 134283273 }

    anMmeTrapAlarmMmeSc1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address subscriber overload."
     -- REPAIR-ACTION
     --     "No action required by the operator. The Subscriber Control function is
     --      taking the abatement action described in the alarm."
     -- ENTITY-TYPE
     --     "system"
     --
        ::= { anMmeTrapAlarms 134283274 }

    anMmeTrapAlarmMmeSc1308       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The no. of activated bearers is approaching the max allowed for this SU."
     -- REPAIR-ACTION
     --     "No immediate action required by the  operator. The Subscriber Control function
     --      triggers abatement  action when the number of bearers exceeds the configured
     --      threshold."
     -- ENTITY-TYPE
     --     "system"
     --
        ::= { anMmeTrapAlarms 134283275 }

    anMmeTrapAlarmMmeSc1309       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address bearer overload."
     -- REPAIR-ACTION
     --     "No action required by the operator.  The Subscriber Control function is
     --      taking the abatement action described in the alarm."
     -- ENTITY-TYPE
     --     "system"
     --
        ::= { anMmeTrapAlarms 134283276 }

    anMmeTrapAlarmMmeSc1320       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "eAN not found for CDMA2000 uplink message."
     -- REPAIR-ACTION
     --     "Check the configured 'epc interface s101 ean' table to ensure there is
     --      a mapping for the access-id."
     -- ENTITY-TYPE
     --     "system"
     --
        ::= { anMmeTrapAlarms 134283277 }

    anMmeTrapAlarmMmeSc1312       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Number of MAP dialogues reaches the high water mark."
     -- REPAIR-ACTION
     --     "Contact product support organization personnel."
     -- ENTITY-TYPE
     --     "system"
     --
        ::= { anMmeTrapAlarms 134283278 }

    anMmeTrapAlarmMmeSc1313       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Attach success rate for GPRS subscribers crosses the thresholds."
     -- REPAIR-ACTION
     --     "Examine the GMM attach failure counters and verify the health of the network.
     --      In other cases, contact product support organization."
     -- ENTITY-TYPE
     --     "system"
     --
        ::= { anMmeTrapAlarms 134283279 }

    anMmeTrapAlarmMmeSc1314       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Activation success rate for GPRS subscribers crosses the thresholds."
     -- REPAIR-ACTION
     --     "Examine the SM activation failure counters and verify the health of the
     --      network. In other cases, contact product support organization."
     -- ENTITY-TYPE
     --     "system"
     --
        ::= { anMmeTrapAlarms 134283280 }

    anMmeTrapAlarmMmeSc1315       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Attach success rate for UMTS subscribers crosses the thresholds."
     -- REPAIR-ACTION
     --     "Examine the GMM attach failure counters and verify the health of the network.In
     --      other cases, contact product support organization."
     -- ENTITY-TYPE
     --     "system"
     --
        ::= { anMmeTrapAlarms 134283281 }

    anMmeTrapAlarmMmeSc1316       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Activation success rate for UMTS subscribers crosses the thresholds."
     -- REPAIR-ACTION
     --     "Examine the SM activation failure counters and verify the health of the
     --      network.In other cases contact product support organization."
     -- ENTITY-TYPE
     --     "system"
     --
        ::= { anMmeTrapAlarms 134283282 }

    anMmeTrapAlarmMmeSc1317       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Attach, IRAU, and/or activation attempts have exceeded thresholds."
     -- REPAIR-ACTION
     --     "This alarm is informational and may require no action depending on policies
     --      in place for a particular network regarding traffic levels per network
     --      code and country code. In other cases contact product support organization."
     -- ENTITY-TYPE
     --     "system"
     --
        ::= { anMmeTrapAlarms 134283283 }

    anMmeTrapAlarmMmeSc1318       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Traffic levels have exceeded thresholds for load-controlled PLMNs."
     -- REPAIR-ACTION
     --     "This alarm is informational and may require no action depending on policies
     --      in place for a particular network regarding traffic levels per network
     --      code and country code. In other cases contact product support organization."
     -- ENTITY-TYPE
     --     "system"
     --
        ::= { anMmeTrapAlarms 134283284 }

    anMmeTrapAlarmMmeSc1321       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "IWS not found for CDMA2000 uplink message."
     -- REPAIR-ACTION
     --     "Check the configured 'epc interface s102 iws' table to ensure there is
     --      a mapping for the cell IDs."
     -- ENTITY-TYPE
     --     "system"
     --
        ::= { anMmeTrapAlarms 134283288 }

    anMmeTrapAlarmMmeSc1322       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "MME received A21-Ack message with cause Unknown Cell Identifier from IWS."
     -- REPAIR-ACTION
     --     "Check the network configuration to ensure the cell IDs are correctly set
     --      up across the network."
     -- ENTITY-TYPE
     --     "system"
     --
        ::= { anMmeTrapAlarms 134283289 }

    anMmeTrapAlarmMmeSc1323       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "SLN monitored UE is connected to MME."
     -- REPAIR-ACTION
     --     "None. This alarm is cleared when the UE is not connected, monitoring  of
     --      the UE ends by means of removing the configuration, or upon timer expiration."
     -- ENTITY-TYPE
     --     "system"
     --
        ::= { anMmeTrapAlarms 134283290 }

    anMmeTrapAlarmMmeSc1324       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of CAMEL dialogues exceeds 95% of the configured maximum."
     -- REPAIR-ACTION
     --     "Contact product support organization personnel."
     -- ENTITY-TYPE
     --     "system"
     --
        ::= { anMmeTrapAlarms 134283291 }

    anMmeTrapAlarmMmeSc1325       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "MSC/VLR Discovery for SRVCC."
     -- REPAIR-ACTION
     --     " Check configuration under epc interface sv sv-if for the selected vlr-discovery
     --      method. Then check under epc service-area for tracking-area to location-area
     --      mapping, and location-area to vlr-pool mapping, and vlr-pool to vlr mapping,
     --      and finally check that the desired vlr has an sv-ip-address-list configured."
     -- ENTITY-TYPE
     --     "system"
     --
        ::= { anMmeTrapAlarms 134283292 }

    anMmeTrapAlarmMmeSc1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 134283363 }

    anMmeTrapAlarmMmeUpm1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The UPM application is experiencing congestion."
     -- REPAIR-ACTION
     --     "No immediate action is required by the operator. The Subscriber Control
     --      function triggers abatement action."
     -- ENTITY-TYPE
     --     "system"
     --
        ::= { anMmeTrapAlarms 134545409 }

    anMmeTrapAlarmMmeUpm1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A RADIUS peer used by Fxa interface is unreachable."
     -- REPAIR-ACTION
     --     "Verify the health of the remote equipment and the health of the IP network."
     -- ENTITY-TYPE
     --     "mme-radius-peer"
     --
        ::= { anMmeTrapAlarms 134545410 }

    anMmeTrapAlarmMmeUpm1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "UPM Transaction Rate Congestion"
     -- REPAIR-ACTION
     --     "The operator needs to take an action by relocating the paths using one
     --      or more of the following commands as the case may be "
     -- ENTITY-TYPE
     --     "system"
     --
        ::= { anMmeTrapAlarms 134545411 }

    anMmeTrapAlarmMmeUpm1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure of UDP connection to IWS for S102 interface."
     -- REPAIR-ACTION
     --     "Check if the IP address of the 'epc interface s102 iws' entity is configured
     --      properly and check if the IWS is down."
     -- ENTITY-TYPE
     --     "mme-iws"
     --
        ::= { anMmeTrapAlarms 134545412 }

    anMmeTrapAlarmMmeUpm1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure of GTP connection to MBMS-GW for Sm interface."
     -- REPAIR-ACTION
     --     "Check if the MBMS-GW is down."
     -- ENTITY-TYPE
     --     "mbms-gw"
     --
        ::= { anMmeTrapAlarms 134545413 }

    anMmeTrapAlarmMmeUpm1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 134545507 }

    anMmeTrapAlarmMmeSigtran1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "No destinations are routable."
     -- REPAIR-ACTION
     --     ""Check the details of the remote destination using the command 'show epc
     --      interface ss7 remote-dest  ...' for indication of why the destination is
     --      unreachable.""
     -- ENTITY-TYPE
     --     "system"
     --
        ::= { anMmeTrapAlarms 135593985 }

    anMmeTrapAlarmMmeSigtran1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "No provisioned SIGTRAN signaling gateways are reachable."
     -- REPAIR-ACTION
     --     ""Check the operational status of the remote peers under "epc interface
     --      ss7 peer" for those peers of type sgp. To determine a peer type, check
     --      configuration under "epc interface ss7 peer peer-type""
     -- ENTITY-TYPE
     --     "system"
     --
        ::= { anMmeTrapAlarms 135593986 }

    anMmeTrapAlarmMmeSigtran1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The peer process is unavailable for routing purposes."
     -- REPAIR-ACTION
     --     ""Check the status of the destination by using the command 'show epc interface
     --      ss7 remote-dest  ...' for 'peer' components"."
     -- ENTITY-TYPE
     --     "mme-g-peer"
     --
        ::= { anMmeTrapAlarms 135593987 }

    anMmeTrapAlarmMmeSigtran1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The peer process is blocked."
     -- REPAIR-ACTION
     --     "No immediate action required. Verify the health of the remote equipment
     --      and the health of the SS7/IP network."
     -- ENTITY-TYPE
     --     "mme-g-peer"
     --
        ::= { anMmeTrapAlarms 135593988 }

    anMmeTrapAlarmMmeSigtran1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The peer process is congested."
     -- REPAIR-ACTION
     --     "Address engineering considerations on the remote destination."
     -- ENTITY-TYPE
     --     "mme-g-peer"
     --
        ::= { anMmeTrapAlarms 135593989 }

    anMmeTrapAlarmMmeSigtran1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The destination is in unroutable state."
     -- REPAIR-ACTION
     --     ""Check the details of the peer process components from CLI 'show epc interface
     --      ss7 peer  ...' to help identify the source of the fault."  Check the remote
     --      destination."
     -- ENTITY-TYPE
     --     "mme-remote-destination"
     --
        ::= { anMmeTrapAlarms 135593990 }

    anMmeTrapAlarmMmeSigtran1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The destination is restricted."
     -- REPAIR-ACTION
     --     "The operator must return the destination node to service to clear this
     --      alarm."
     -- ENTITY-TYPE
     --     "mme-remote-destination"
     --
        ::= { anMmeTrapAlarms 135593991 }

    anMmeTrapAlarmMmeSigtran1307       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The destination is congested."
     -- REPAIR-ACTION
     --     "If traffic rates are within normal operating limits and all subsystems
     --      are available, then the processing capacity of the destination has likely
     --      been over-estimated. The resolution is to address engineering considerations
     --      on the remote destination."
     -- ENTITY-TYPE
     --     "mme-remote-destination"
     --
        ::= { anMmeTrapAlarms 135593992 }

    anMmeTrapAlarmMmeSigtran1308       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The remote subsystem is unavailable"
     -- REPAIR-ACTION
     --     "Check the status of the remote subsystem with the command 'show epc interface
     --      ss7 remote-subsystem  ...'. Alternate paths to the subsystem may be possible,
     --      analyze the provisioned network configuration and add appropriate entries.
     --      Also check the remote node and verify the state it is reporting for its
     --      subsystem."
     -- ENTITY-TYPE
     --     "mme-remote-destination"
     --
        ::= { anMmeTrapAlarms 135593993 }

    anMmeTrapAlarmMmeSigtran1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 135594083 }

    anMmeTrapAlarmMmeTcap1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "TCAP is unable to bind to the SGSN MAP subsystem."
     -- REPAIR-ACTION
     --     "Contact product support organization."
     -- ENTITY-TYPE
     --     "system"
     --
        ::= { anMmeTrapAlarms 135659521 }

    anMmeTrapAlarmMmeTcap1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Number of MAP transactions exceeds 95% of provisioned data."
     -- REPAIR-ACTION
     --     "Contact product support organization."
     -- ENTITY-TYPE
     --     "system"
     --
        ::= { anMmeTrapAlarms 135659522 }

    anMmeTrapAlarmMmeTcap1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "TCAP is unable to bind to the SGSN CAP subsystem."
     -- REPAIR-ACTION
     --     "Verify that the configurable attribute 'tcap-max-cap-transactions' value
     --      for the SGSN CAP is set to a value greater than zero."
     -- ENTITY-TYPE
     --     "system"
     --
        ::= { anMmeTrapAlarms 135659523 }

    anMmeTrapAlarmMmeTcap1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Number of CAP transactions exceeds 95% of the configured data."
     -- REPAIR-ACTION
     --     "Verify that the configurable attribute 'tcap-max-cap-transactions' value
     --      is provisioned to an adequate size."
     -- ENTITY-TYPE
     --     "system"
     --
        ::= { anMmeTrapAlarms 135659524 }

    anMmeTrapAlarmMmeTcap1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 135659619 }

    anMmeTrapAlarmSgsnIu1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Mapping table has reached the predefined usage thresholds."
     -- REPAIR-ACTION
     --     "Compare the values of counter SCCP.CurrentNbrOpenConnections under "statistics
     --      iu sccp", versus the configured value  under "epc interface iu rnc max-iu-connections".
     --      If the value of the counter is much higher than the configured limit,
     --      it may indicate that the mapping table has stale connections, and a CALLP
     --      VM switchover may help. Switchover can be performed on the affected compute
     --      node to rejected-connections."
     -- ENTITY-TYPE
     --     "mme-rnc"
     --
        ::= { anMmeTrapAlarms 136314881 }

    anMmeTrapAlarmSgsnIu1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "SCCP connection resource pool reaches predefined usage thresholds."
     -- REPAIR-ACTION
     --     "Determine why so many connections are being used or requested by the RNCs.
     --      RNCs may need to be re-engineered to reduce the number of SCCP connection
     --      requests, especially when the alarms have persisted for a long time during
     --      high traffic period."
     -- ENTITY-TYPE
     --     "mme-rnc"
     --
        ::= { anMmeTrapAlarms 136314882 }

    anMmeTrapAlarmSgsnIu1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure to register with the available M3uaAsp instance(s)."
     -- REPAIR-ACTION
     --     "Verify that the "epc interface iu rnc destination-point-code" is unique
     --      for each SCCP. Also check if any configured "epc interface iu ipsp-instance"
     --      are able to send registration acknowledgements to the RNC."
     -- ENTITY-TYPE
     --     "mme-rnc"
     --
        ::= { anMmeTrapAlarms 136314883 }

    anMmeTrapAlarmSgsnIu1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "RNC connection state."
     -- REPAIR-ACTION
     --     "Verify that the all peers connected to RNC are up. If RNC has backup RNC
     --      configured check the state of peers connected to backup RNC also."
     -- ENTITY-TYPE
     --     "mme-rnc"
     --
        ::= { anMmeTrapAlarms 136314884 }

    anMmeTrapAlarmSgsnIu1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 136314979 }

    anMmeTrapAlarmSgsnIpSp1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure to communicate with the IP-RNC."
     -- REPAIR-ACTION
     --     "If this alarm persists after startup, check the configuration of 'epc interface
     --      iu m3ua' and 'epc interface iu dest-peer-map' to confirm addressing and
     --      naming, and check the health of the network."
     -- ENTITY-TYPE
     --     "system"
     --
        ::= { anMmeTrapAlarms 136380417 }

    anMmeTrapAlarmSgsnIpSp1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The peer process is unavailable for routing purposes."
     -- REPAIR-ACTION
     --     "If this alarm persists after startup, check the status of the destination
     --      represented by this iu peer component."
     -- ENTITY-TYPE
     --     "mme-iu-peer"
     --
        ::= { anMmeTrapAlarms 136380418 }

    anMmeTrapAlarmSgsnIpSp1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The peer process is congested."
     -- REPAIR-ACTION
     --     "The resolution is to address engineering considerations on the remote destination."
     -- ENTITY-TYPE
     --     "mme-iu-peer"
     --
        ::= { anMmeTrapAlarms 136380419 }

    anMmeTrapAlarmSgsnIpSp1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The destination is in unroutable state."
     -- REPAIR-ACTION
     --     "If this alarm persists after startup, check the details of the 'epc interface
     --      iu peer' components that correspond to this destination. Information in
     --      these iu peer components will identify the source of the fault. Check the
     --      remote destination."
     -- ENTITY-TYPE
     --     "system"
     --
        ::= { anMmeTrapAlarms 136380420 }

    anMmeTrapAlarmSgsnIpSp1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The destination is restricted."
     -- REPAIR-ACTION
     --     "The operator must return the destination node to service to clear this
     --      alarm."
     -- ENTITY-TYPE
     --     "system"
     --
        ::= { anMmeTrapAlarms 136380421 }

    anMmeTrapAlarmSgsnIpSp1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 136380515 }

    anMmeTrapAlarmSgsnSd1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The maximum allocated LLEs has been reached."
     -- REPAIR-ACTION
     --     "Verify that the values of the provisionable attribute 'lle-to-mobile-ratio'
     --      under 'epc engineering sd-engineering' component are sufficient to handle
     --      the level of subscriber demand required. Increase if necessary."
     -- ENTITY-TYPE
     --     "system"
     --
        ::= { anMmeTrapAlarms 136445953 }

    anMmeTrapAlarmSgsnSd1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The maximum allocated LLC-ABM data entities has been reached."
     -- REPAIR-ACTION
     --     "Verify that the value of the provisionable attribute 'abm-mode-lle-to-mobile-ratio'
     --      under 'epc interface gb llc' component is sufficient to handle the level
     --      of subscriber demand required. Increase if necessary."
     -- ENTITY-TYPE
     --     "system"
     --
        ::= { anMmeTrapAlarms 136445954 }

    anMmeTrapAlarmSgsnSd1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The maximum allocated session entities has been reached."
     -- REPAIR-ACTION
     --     "Verify that the values of the provisionable attribute 'pdn-average' under
     --      'epc engineering sc-capacity' component are sufficient to handle the level
     --      of subscriber demand required. Increase if necessary."
     -- ENTITY-TYPE
     --     "system"
     --
        ::= { anMmeTrapAlarms 136445955 }

    anMmeTrapAlarmSgsnSd1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 136446051 }

    anMmeTrapAlarmSgsnGb1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of unavailable PTP-BVCs has exceeded the threshold."
     -- REPAIR-ACTION
     --     "Perform a manual PTP-BVC audit on the NSE shown in the alarm on both the
     --      SGSN and PCU. Verify that PTP-BVC configuration is consistent with the
     --      PCU, and verify that the threshold and timer provisionable attributes are
     --      set properly. Additionally, a signaling BVC reset procedure ('epc interface
     --      gb sig-bvc reset ...') can be performed, which will result in a service
     --      outage for the impacted NSE."
     -- ENTITY-TYPE
     --     "mme-nse"
     --
        ::= { anMmeTrapAlarms 136511489 }

    anMmeTrapAlarmSgsnGb1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "No PTP-BVCs were created after a signaling BVC reset procedure."
     -- REPAIR-ACTION
     --     "This alarm is informational in nature. No remedial action is necessary
     --      on the SGSN, corrective action must take place at the PCU. Verify the health
     --      of the network path to the PCU. Verify that the PCU is functioning properly."
     -- ENTITY-TYPE
     --     "mme-nse"
     --
        ::= { anMmeTrapAlarms 136511490 }

    anMmeTrapAlarmSgsnGb1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of unavailable data NS-VCs on an NSE crossed a threshold."
     -- REPAIR-ACTION
     --     "Check the data NS-VCs for the NSE specified in the alarm and try to resolve
     --      any issues with those in unavailable states."
     -- ENTITY-TYPE
     --     "mme-nse"
     --
        ::= { anMmeTrapAlarms 136511491 }

    anMmeTrapAlarmSgsnGb1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of unavailable signaling NS-VCs on an NSE crossed a threshold."
     -- REPAIR-ACTION
     --     "Check the signaling NS-VCs for the NSE specified in the alarm and try to
     --      resolve any issues with those in unavailable states."
     -- ENTITY-TYPE
     --     "mme-nse"
     --
        ::= { anMmeTrapAlarms 136511492 }

    anMmeTrapAlarmSgsnGb1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "There are problems with the dynamic IP configuration procedure."
     -- REPAIR-ACTION
     --     "Verify the health of the network path to the PCU. Verify that the PCU is
     --      functioning properly."
     -- ENTITY-TYPE
     --     "mme-nse"
     --
        ::= { anMmeTrapAlarms 136511493 }

    anMmeTrapAlarmSgsnGb1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "NSE process creation failed."
     -- REPAIR-ACTION
     --     "Check the health of the 'blade/vm' supporting this callP VM (as identified
     --      in the ref-entity-tag of the alarm)."
     -- ENTITY-TYPE
     --     "system"
     --
        ::= { anMmeTrapAlarms 136511494 }

    anMmeTrapAlarmSgsnGb1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of unavailable NS-VCs on an NSE crossed a threshold."
     -- REPAIR-ACTION
     --     "Check the NS-VCs for the NSE specified in the alarm and try to resolve
     --      any issues with those in unavailable states."
     -- ENTITY-TYPE
     --     "mme-nse"
     --
        ::= { anMmeTrapAlarms 136511495 }

    anMmeTrapAlarmSgsnGb1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 136511587 }

    anMmeTrapAlarmCsl1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The maximum records for a CSL file has been exceeded."
     -- REPAIR-ACTION
     --     "Adjust the configuration under "epc csl profile" to either increase the
     --      max-records-per-file limit, or decrease the number of triggers or events
     --      enabled."
     -- ENTITY-TYPE
     --     "system"
     --
        ::= { anMmeTrapAlarms 136642561 }

    anMmeTrapAlarmCsl1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The CSL file system partition is full."
     -- REPAIR-ACTION
     --     "Consider changing the parition size."
     -- ENTITY-TYPE
     --     "system"
     --
        ::= { anMmeTrapAlarms 136642562 }

    anMmeTrapAlarmCsl1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. Consider switching over to the standby
     --      callP VM and then locking and unlocking the former active, now standby,
     --      callP VM."
     -- ENTITY-TYPE
     --     "system"
     --
        ::= { anMmeTrapAlarms 136642563 }

    anMmeTrapAlarmCsl1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The remote CSL server is unreachable or misconfigured."
     -- REPAIR-ACTION
     --     "Check that the remote CSL server(s) and network is operational."
     -- ENTITY-TYPE
     --     "system"
     --
        ::= { anMmeTrapAlarms 136642564 }

    anMmeTrapAlarmCsl1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected in the CSL client process."
     -- REPAIR-ACTION
     --     "Contact your next level of support. Consider switching over to the standby
     --      callP VM and then locking and unlocking the former active, now standby,
     --      callP VM."
     -- ENTITY-TYPE
     --     "system"
     --
        ::= { anMmeTrapAlarms 136642565 }

    anMmeTrapAlarmCsl1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 136642659 }

    anMmeTrapAlarmMmeSbc1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "No connection to the CBC Server."
     -- REPAIR-ACTION
     --     "Verify health of the CBC and the IP network."
     -- ENTITY-TYPE
     --     "mme-sbc-if"
     --
        ::= { anMmeTrapAlarms 137232385 }

    anMmeTrapAlarmMmeSbc1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "MME failed to decode or process the message."
     -- REPAIR-ACTION
     --     "Contact your next level of support to resolve the issue. A manual clear
     --      of the alarm may be required."
     -- ENTITY-TYPE
     --     "mme-sbc-cbc"
     --
        ::= { anMmeTrapAlarms 137232386 }

    anMmeTrapAlarmMmeSbc1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 137232483 }

    anMmeTrapAlarmDns1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "[obsolete] An external DNS server is unreachable"
     -- REPAIR-ACTION
     --     "Verify the health of the remote equipment and the health of the IP network."
     -- ENTITY-TYPE
     --     "dns-server"
     --
        ::= { anMmeTrapAlarms 137297921 }

    anMmeTrapAlarmDns1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support"
     -- ENTITY-TYPE
     --     "system"
     --
        ::= { anMmeTrapAlarms 137297922 }

    anMmeTrapAlarmDns1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "DNS Service Reachability"
     -- REPAIR-ACTION
     --     "Check the network connectivity between the MME/SGSN and the DNS servers
     --      (as configured under epc dns server), and check the health of the DNS servers.
     --      The MME/SGSN provides resilience against DNS server instability by suspending
     --      removal of dynamic cache entries with expired TTL when no servers are reachable,
     --      but for a prolonged outage this can lead to the usage of stale DNS information.
     --      For a network that relies on remote DNS servers (indirectly or directly)
     --      for some domains, it may be necessary to adjust the retry timers and retry
     --      alarm threshold configured under epc dns dns-if. "
     -- ENTITY-TYPE
     --     "dns-server"
     --
        ::= { anMmeTrapAlarms 137297923 }

    anMmeTrapAlarmDns1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 137298019 }

    anMmeTrapAlarmTrace1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. Consider switching over to  the standby
     --      callP VM and then locking and  unlocking the former active, now standby,
     --      callP VM. "
     -- ENTITY-TYPE
     --     "system"
     --
        ::= { anMmeTrapAlarms 137494529 }

    anMmeTrapAlarmTrace1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 137494627 }

    anMmeTrapAlarmOverload1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The MME is experiencing paging overload."
     -- REPAIR-ACTION
     --     "No immediate action required by the operator. The Subscriber Control function
     --      triggers the configured abatement action."
     -- ENTITY-TYPE
     --     "system"
     --
        ::= { anMmeTrapAlarms 138412033 }

    anMmeTrapAlarmOverload1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address paging overload."
     -- REPAIR-ACTION
     --     "No action required by the operator. The Subscriber Control function will
     --      take the abatement action described in the alarm."
     -- ENTITY-TYPE
     --     "system"
     --
        ::= { anMmeTrapAlarms 138412034 }

    anMmeTrapAlarmOverload1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 138412131 }

    anMmeTrapAlarmMmeSgs1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "VLR connection status."
     -- REPAIR-ACTION
     --     "Check the configuration of the VLR (show config epc interface sgs) to determine
     --      if it is multi-home and if there is more than one SCTP association configured.
     --      Check the status of each connection using the command 'show epc interface
     --      sgs vlr', and use the alarm text to determine which particular associations
     --      are down."
     -- ENTITY-TYPE
     --     "mme-vlr"
     --
        ::= { anMmeTrapAlarms 138477569 }

    anMmeTrapAlarmMmeSgs1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected. "
     -- REPAIR-ACTION
     --     "Contact product support organization.  Consider switching over to the standby
     --      callP VM and then locking and unlocking the former active, now standby,
     --      callP VM. "
     -- ENTITY-TYPE
     --     "system"
     --
        ::= { anMmeTrapAlarms 138477570 }

    anMmeTrapAlarmMmeSgs1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 138477667 }

    anMmeTrapAlarmMmeAtam1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization. Consider switching over to the standby
     --      callP VM and then locking and unlocking the former active, now standby,
     --      callP VM."
     -- ENTITY-TYPE
     --     "system"
     --
        ::= { anMmeTrapAlarms 138739713 }

    anMmeTrapAlarmMmeAtam1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 138739811 }

    anMmeTrapAlarmFgwS1Mme1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "FGW is unable to reach MME over S1-MME (SCTP) interface."
     -- REPAIR-ACTION
     --     "Verify that MME is configured correctly. Verify that MME is up and communicating."
     -- ENTITY-TYPE
     --     "mme-s1-mme-peer"
     --
        ::= { anMmeTrapAlarms 140771329 }

    anMmeTrapAlarmFgwS1Mme1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. Consider switching over to the standby
     --      callP VM and then locking and unlocking the former active, now standby,
     --      callP VM."
     -- ENTITY-TYPE
     --     "system"
     --
        ::= { anMmeTrapAlarms 140771330 }

    anMmeTrapAlarmFgwS1Mme1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "No action required by operator."
     -- ENTITY-TYPE
     --     "system"
     --
        ::= { anMmeTrapAlarms 140771427 }

    anMmeTrapAlarmFgwSc1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Connection data is out of synchronization."
     -- REPAIR-ACTION
     --     "No immediate action required. The active and standby callP VMs (if available)
     --      automatically attempt to resynchronize with each other. If condition persists,
     --      contact your next level of support."
     -- ENTITY-TYPE
     --     "system"
     --
        ::= { anMmeTrapAlarms 142344193 }

    anMmeTrapAlarmFgwSc1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. Consider switching over to the standby
     --      callP VM and then locking and unlocking the former active, now standby,
     --      callP VM."
     -- ENTITY-TYPE
     --     "system"
     --
        ::= { anMmeTrapAlarms 142344194 }

    anMmeTrapAlarmFgwSc1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The FGW SC application is experiencing congestion."
     -- REPAIR-ACTION
     --     "No immediate action required by the operator.  The Subscriber Control function
     --      triggers the configured abatement action."
     -- ENTITY-TYPE
     --     "system"
     --
        ::= { anMmeTrapAlarms 142344195 }

    anMmeTrapAlarmFgwSc1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address congestion overload."
     -- REPAIR-ACTION
     --     "No action required by the operator.  The Subscriber Control function is
     --      taking the abatement action described in the alarm."
     -- ENTITY-TYPE
     --     "system"
     --
        ::= { anMmeTrapAlarms 142344196 }

    anMmeTrapAlarmFgwSc1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Attach success rate for FGW has fallen"
     -- REPAIR-ACTION
     --     "Examine the fgwFGW.EpsUeConnectIgn connect failure counters and verify
     --      the health of the network."
     -- ENTITY-TYPE
     --     "system"
     --
        ::= { anMmeTrapAlarms 142344197 }

    anMmeTrapAlarmFgwSc1305       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of connections exceeded the configured no. of connections per VM."
     -- REPAIR-ACTION
     --     "No immediate action required by the operator. The Subscriber Control function
     --      triggers abatement action on a per MPU basis when the attached subscriber
     --      count exceeds the configured threshold."
     -- ENTITY-TYPE
     --     "system"
     --
        ::= { anMmeTrapAlarms 142344198 }

    anMmeTrapAlarmFgwSc1306       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Abatement action is being applied to address subscriber overload."
     -- REPAIR-ACTION
     --     "No action required by the operator.  The Subscriber Control function is
     --      taking the abatement action described in the alarm."
     -- ENTITY-TYPE
     --     "system"
     --
        ::= { anMmeTrapAlarms 142344199 }

    anMmeTrapAlarmFgwSc1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "No action required by operator."
     -- ENTITY-TYPE
     --     "system"
     --
        ::= { anMmeTrapAlarms 142344291 }

    anMmeTrapAlarmFgwS1Enb1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. If only one proccess is reporting this
     --      alarm do nothing else. If several processes have raised this alarm consider
     --      locking and unlocking the callP VM."
     -- ENTITY-TYPE
     --     "system"
     --
        ::= { anMmeTrapAlarms 142409729 }

    anMmeTrapAlarmFgwS1Enb1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "No action required by operator."
     -- ENTITY-TYPE
     --     "system"
     --
        ::= { anMmeTrapAlarms 142409827 }

    anMmeTrapAlarmFgwS1Server1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "ENodeB process creation failed."
     -- REPAIR-ACTION
     --     "Check the health of the 'blade/vm' supporting this callP VM (as identified
     --      in the ref-entity-tag of the alarm)."
     -- ENTITY-TYPE
     --     "system"
     --
        ::= { anMmeTrapAlarms 142475265 }

    anMmeTrapAlarmFgwS1Server1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support. Consider switching over to the standby
     --      callP VM and then locking and unlocking the former active, now standby,
     --      callP VM."
     -- ENTITY-TYPE
     --     "system"
     --
        ::= { anMmeTrapAlarms 142475266 }

    anMmeTrapAlarmFgwS1Server1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 142475363 }

    anMmeTrapAlarmMmeSls1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Failure of SCTP connection to E-SMLC."
     -- REPAIR-ACTION
     --     "Check if the IP address  of the 'e-smlc' entity is configured properly
     --      and check if the E-SMLC is down."
     -- ENTITY-TYPE
     --     "mme-e-smlc"
     --
        ::= { anMmeTrapAlarms 143392769 }

    anMmeTrapAlarmMmeSls1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact product support organization. Consider switching over to the standby
     --      callP VM and then locking and unlocking the former active, now standby,
     --      callP VM."
     -- ENTITY-TYPE
     --     "system"
     --
        ::= { anMmeTrapAlarms 143392770 }

    anMmeTrapAlarmMmeSls1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Current transactions for this E-SMLC exceeds 90% of the configured data."
     -- REPAIR-ACTION
     --     "Verify that the 'max-transactions-per-peer' configured under 'epc interface
     --      sls sls-if' is set to a proper value and the number of E-SMLCs per mmeSls
     --      service group is set to a proper value."
     -- ENTITY-TYPE
     --     "mme-e-smlc"
     --
        ::= { anMmeTrapAlarms 143392771 }

    anMmeTrapAlarmMmeSls1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 143392867 }

    anMmeTrapAlarmPathMon1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "Alarm is raised when virtual machine Ethernet interface is failed."
     -- REPAIR-ACTION
     --     "Check source of alarm."
     -- ENTITY-TYPE
     --     "srm-eth"
     --
        ::= { anMmeTrapAlarms 143917057 }

    anMmeTrapAlarmPathMon1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A network connectivity outage has been detected by the BFD protocol."
     -- REPAIR-ACTION
     --     "Verify that the Next-Hop router is in-service. Verify network connectivity
     --      between this VM and the remote Next-Hop router.Verify that the Next-Hop
     --      router has not administratively removed itself from service via the BFD
     --      protocol."
     -- ENTITY-TYPE
     --     "system"
     --
        ::= { anMmeTrapAlarms 143917058 }

    anMmeTrapAlarmPathMon1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A network connectivity outage has been detected by the BFD protocol."
     -- REPAIR-ACTION
     --     "Verify that at least one Load Balancer instance is in-service. Verify network
     --      connectivity between this VM and the Load Balancer VMs."
     -- ENTITY-TYPE
     --     "srm-eth"
     --
        ::= { anMmeTrapAlarms 143917059 }

    anMmeTrapAlarmPathMon1303       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The number of network interfaces in the VM does not match configured interfaces."
     -- REPAIR-ACTION
     --     "Correctly configure the network on the node or in the VM."
     -- ENTITY-TYPE
     --     "system"
     --
        ::= { anMmeTrapAlarms 143917060 }

    anMmeTrapAlarmPathMon1304       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The virtual network interface connections do not match configuration."
     -- REPAIR-ACTION
     --     "Correctly configure the network. If the next-hop router was not present,
     --      then manually clear the alarm or reset the VM when next-hop router comes
     --      online."
     -- ENTITY-TYPE
     --     "system"
     --
        ::= { anMmeTrapAlarms 143917061 }

    anMmeTrapAlarmPathMon1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "srm-eth"
     --
        ::= { anMmeTrapAlarms 143917155 }

    anMmeTrapAlarmLbCtrl1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contact your next level of support"
     -- ENTITY-TYPE
     --     "system"
     --
        ::= { anMmeTrapAlarms 144113665 }

    anMmeTrapAlarmLbCtrl1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "No Action required by Operator."
     -- ENTITY-TYPE
     --     "system"
     --
        ::= { anMmeTrapAlarms 144113763 }

    anMmeTrapAlarmEdp1300       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "The maximum allocated PDP context/bearer entities has been reached."
     -- REPAIR-ACTION
     --     ""
     -- ENTITY-TYPE
     --     "system"
     --
        ::= { anMmeTrapAlarms 144179201 }

    anMmeTrapAlarmEdp1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously generated by this application instance are cleared."
     -- REPAIR-ACTION
     --     "None."
     -- ENTITY-TYPE
     --     "system"
     --
        ::= { anMmeTrapAlarms 144179299 }

    anMmeTrapAlarmMmeMbms1301       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "MBMS Bearer Context is out of synchronization."
     -- REPAIR-ACTION
     --     "No immediate action required."
     -- ENTITY-TYPE
     --     "system"
     --
        ::= { anMmeTrapAlarms 196673537 }

    anMmeTrapAlarmMmeMbms1302       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "A potential memory leak has been detected."
     -- REPAIR-ACTION
     --     "Contract your next level of support."
     -- ENTITY-TYPE
     --     "system"
     --
        ::= { anMmeTrapAlarms 196673538 }

    anMmeTrapAlarmMmeMbms1399       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeFirstEvent,
                    anMmeLastEvent,
                    anMmeLocation,
                    anMmeService,
                    anMmeAlarmIndex }
        STATUS      current
        DESCRIPTION
            "All alarms previously gererated by this application instance are cleared."
     -- REPAIR-ACTION
     --     "No Action required by Operator"
     -- ENTITY-TYPE
     --     "system"
     --
        ::= { anMmeTrapAlarms 196673635 }

    anMmeTrapEventNm1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "VM administrative state change"
     -- REPAIR-ACTION
     --     "None"
     -- ENTITY-TYPE
     --     "system"
     --
        ::= { anMmeTrapEvents 65536100 }

    anMmeTrapEventNm1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "VM switchover completed"
     -- REPAIR-ACTION
     --     "None"
     -- ENTITY-TYPE
     --     "system"
     --
        ::= { anMmeTrapEvents 65536101 }

    anMmeTrapEventLi1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "LI Reject Pending Switchover."
     -- REPAIR-ACTION
     --     "Try the command again later, or use a "force" option if the resulting data
     --      loss is acceptable.  Synchronization status can be shown using the CLI
     --      command "show vm"."
     -- ENTITY-TYPE
     --     "system"
     --
        ::= { anMmeTrapEvents 133759076 }

    anMmeTrapEventLi1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "LI Activation During Sync Lost."
     -- REPAIR-ACTION
     --     "No repair action required."
     -- ENTITY-TYPE
     --     "system"
     --
        ::= { anMmeTrapEvents 133759077 }

    anMmeTrapEventLi1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "LI Login Failure"
     -- REPAIR-ACTION
     --     "See /var/log/auth.log to get more details about the login failure."
     -- ENTITY-TYPE
     --     "system"
     --
        ::= { anMmeTrapEvents 133759078 }

    anMmeTrapEventMmeRm1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "RM Reject Pending Switchover."
     -- REPAIR-ACTION
     --     "Try the command again later, or use a "force" option if the resulting data
     --      loss is acceptable. Synchronization status can be shown using the CLI command
     --      "show vm"."
     -- ENTITY-TYPE
     --     "system"
     --
        ::= { anMmeTrapEvents 133824612 }

    anMmeTrapEventMmeRm1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "RM Activation During Sync Lost."
     -- REPAIR-ACTION
     --     "None."
     -- ENTITY-TYPE
     --     "system"
     --
        ::= { anMmeTrapEvents 133824613 }

    anMmeTrapEventMmeS1M1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "S1Master Reject Pending Switchover"
     -- REPAIR-ACTION
     --     "Try the command again later, or use a "force" option if the resulting data
     --      loss is acceptable.  Synchronization status can be shown using the CLI
     --      command "show vm.""
     -- ENTITY-TYPE
     --     "system"
     --
        ::= { anMmeTrapEvents 133890148 }

    anMmeTrapEventMmeS1M1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "S1Master Activation During Sync Lost."
     -- REPAIR-ACTION
     --     "None"
     -- ENTITY-TYPE
     --     "system"
     --
        ::= { anMmeTrapEvents 133890149 }

    anMmeTrapEventMmeS1M1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "enodeB Connection Rejected."
     -- REPAIR-ACTION
     --     "S1 service configuration should be checked.  It is possible to increase
     --      capacity by adjusting the max-enodebs per VM limit configured under s1-capacity,
     --      or by adding more sig VMs. "
     -- ENTITY-TYPE
     --     "system"
     --
        ::= { anMmeTrapEvents 133890150 }

    anMmeTrapEventMmeS1M1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "S1 Setup Rejected."
     -- REPAIR-ACTION
     --     "S1 service configuration should be checked.  It is possible to increase
     --      capacity by adjusting the max-enodebs per VM limit configured under s1-capacity,
     --      or by adding more sig VMs."
     -- ENTITY-TYPE
     --     "system"
     --
        ::= { anMmeTrapEvents 133890151 }

    anMmeTrapEventMmeS1M1404       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Unknown PLMNs"
     -- REPAIR-ACTION
     --     "Correct the configuration, either on the MME by adding the 'plmn' entity,
     --      or on the enodeB."
     -- ENTITY-TYPE
     --     "system"
     --
        ::= { anMmeTrapEvents 133890152 }

    anMmeTrapEventMmeS1M1405       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "enodeB Duplicate ID."
     -- REPAIR-ACTION
     --     "Check enodeB configuration in the network. "
     -- ENTITY-TYPE
     --     "mme-enodeb"
     --
        ::= { anMmeTrapEvents 133890153 }

    anMmeTrapEventMmeS1M1406       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Manual eNodeB/MCE relocation"
     -- REPAIR-ACTION
     --     "None"
     -- ENTITY-TYPE
     --     "system"
     --
        ::= { anMmeTrapEvents 133890154 }

    anMmeTrapEventMmeS1M1407       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "MBMS M3 Setup Rejected"
     -- REPAIR-ACTION
     --     "MmeMCE (SIG) service configuration needs to be checked and additional capacity
     --      may be added by changing mce-capacity configuration or adding additional
     --      RM callP VM instances."
     -- ENTITY-TYPE
     --     "system"
     --
        ::= { anMmeTrapEvents 133890155 }

    anMmeTrapEventMmeS1M1408       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "MBMS Duplicate MCE ID"
     -- REPAIR-ACTION
     --     "Correct the configuration on the MCE."
     -- ENTITY-TYPE
     --     "mce"
     --
        ::= { anMmeTrapEvents 133890156 }

    anMmeTrapEventMmeS1M1409       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "MCE Connection Rejected"
     -- REPAIR-ACTION
     --     "MmeS1 (SIG) service configuration needs to be checked and additional capacity
     --      may be added by charging s1-capacity configuration or adding additional
     --      SIG callP VM instances. "
     -- ENTITY-TYPE
     --     "system"
     --
        ::= { anMmeTrapEvents 133890157 }

    anMmeTrapEventMmeUpsm1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A GTP path was rejected due to max number of paths connected being reached."
     -- REPAIR-ACTION
     --     "None."
     -- ENTITY-TYPE
     --     "system"
     --
        ::= { anMmeTrapEvents 133955684 }

    anMmeTrapEventMmeIlf1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "ILF Reject Pending Switchover."
     -- REPAIR-ACTION
     --     "Try the command again later, or use a "force" option if the resulting data
     --      loss is acceptable. Synchronization status can be shown using the CLI command
     --      "show vm"."
     -- ENTITY-TYPE
     --     "system"
     --
        ::= { anMmeTrapEvents 134021220 }

    anMmeTrapEventMmeIlf1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "ILF Activation During Sync Lost."
     -- REPAIR-ACTION
     --     "None."
     -- ENTITY-TYPE
     --     "system"
     --
        ::= { anMmeTrapEvents 134021221 }

    anMmeTrapEventMmeS1Enb1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Received Write-Replace Warning Response."
     -- REPAIR-ACTION
     --     "No repair action required if the ENodeB response was successful. Check
     --      configuration and health of ENodeB if the response indicates failure."
     -- ENTITY-TYPE
     --     "mme-enodeb"
     --
        ::= { anMmeTrapEvents 134152292 }

    anMmeTrapEventMmeS1Enb1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "The MME was unable to relay a warning message from CBC to the ENodeB."
     -- REPAIR-ACTION
     --     "Check the health of the ENodeBs and the IP network."
     -- ENTITY-TYPE
     --     "mme-enodeb"
     --
        ::= { anMmeTrapEvents 134152293 }

    anMmeTrapEventMmeDc1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "HSS reset."
     -- REPAIR-ACTION
     --     "Verify that the HSS is functioning properly."
     -- ENTITY-TYPE
     --     "system"
     --
        ::= { anMmeTrapEvents 134217828 }

    anMmeTrapEventMmeSc1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace Session Started."
     -- REPAIR-ACTION
     --     "No repair action required."
     -- ENTITY-TYPE
     --     "system"
     --
        ::= { anMmeTrapEvents 134283364 }

    anMmeTrapEventMmeSc1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace Session Stopped."
     -- REPAIR-ACTION
     --     "No repair action required."
     -- ENTITY-TYPE
     --     "system"
     --
        ::= { anMmeTrapEvents 134283365 }

    anMmeTrapEventMmeSc1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "SC Reject Pending Switchover."
     -- REPAIR-ACTION
     --     "Try the command again later, or use a "force" option if the resulting data
     --      loss is acceptable. Synchronization status can be shown using the CLI command
     --      "show vm"."
     -- ENTITY-TYPE
     --     "system"
     --
        ::= { anMmeTrapEvents 134283366 }

    anMmeTrapEventMmeSc1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "SC Activation During Sync Lost."
     -- REPAIR-ACTION
     --     "None."
     -- ENTITY-TYPE
     --     "system"
     --
        ::= { anMmeTrapEvents 134283367 }

    anMmeTrapEventMmeSc1404       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace enodeB Failure Indication"
     -- REPAIR-ACTION
     --     "No repair actions required."
     -- ENTITY-TYPE
     --     "mme-enodeb"
     --
        ::= { anMmeTrapEvents 134283368 }

    anMmeTrapEventMmeSc1405       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A black or grey mobile has been detected."
     -- REPAIR-ACTION
     --     "None."
     -- ENTITY-TYPE
     --     "system"
     --
        ::= { anMmeTrapEvents 134283369 }

    anMmeTrapEventMmeSc1406       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "SC process received a PDP context from the HLR that contains invalid data."
     -- REPAIR-ACTION
     --     "Verify the PDP context provisioning in the HLR for the indicated subscriber.
     --      In other cases, contact product support organization personnel."
     -- ENTITY-TYPE
     --     "system"
     --
        ::= { anMmeTrapEvents 134283370 }

    anMmeTrapEventMmeSc1407       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Operator attempts to lock all NRI instances."
     -- REPAIR-ACTION
     --     "If nri-bit-length is 6, then at least 2 NRI instances must be unlocked
     --      in order to avoid a service interruption. If nri-bit-length is 7, then
     --      at least 4 NRI instances must be unlocked in order to avoid a service interruption.
     --      If nri-bit-length is 8, then at least 8 NRI instances must be unlocked
     --      in order to avoid a service interruption. If nri-bit-length is 9, then
     --      at least 16 NRI instances must be unlocked in order to avoid a service
     --      interruption. If nri-bit-length is 10, then at least 32 NRI instances must
     --      be unlocked in order to avoid a service interruption."
     -- ENTITY-TYPE
     --     "system"
     --
        ::= { anMmeTrapEvents 134283371 }

    anMmeTrapEventMmeSc1408       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Location information of a SLN monitored UE."
     -- REPAIR-ACTION
     --     "This log is generated periodically until timer expiration or  monitoring
     --      of the UE ends by means of removing the configuration."
     -- ENTITY-TYPE
     --     "system"
     --
        ::= { anMmeTrapEvents 134283372 }

    anMmeTrapEventMmeSc1409       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Location Report Failure Indication from eNodeB."
     -- REPAIR-ACTION
     --     "No repair actions required."
     -- ENTITY-TYPE
     --     "mme-enodeb"
     --
        ::= { anMmeTrapEvents 134283373 }

    anMmeTrapEventMmeSc1410       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Emergency Call Positioning Failure."
     -- REPAIR-ACTION
     --     "Check the availability of E-SMLC and GMLC usingcommands for epc interface
     --      sls esmlc and epc interface diameter peer respectively."
     -- ENTITY-TYPE
     --     "system"
     --
        ::= { anMmeTrapEvents 134283374 }

    anMmeTrapEventMmeSc1411       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Directional Offload Failed"
     -- REPAIR-ACTION
     --     "Check the target-mme-ip-address/target-sgsn-ip-address and the target node
     --      to see if directional offload is supported"
     -- ENTITY-TYPE
     --     "system"
     --
        ::= { anMmeTrapEvents 134283375 }

    anMmeTrapEventMmeSc1412       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Subscriber move successful"
     -- REPAIR-ACTION
     --     "None"
     -- ENTITY-TYPE
     --     "system"
     --
        ::= { anMmeTrapEvents 134283376 }

    anMmeTrapEventMmeSc1413       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "VLR Reset (Gs type)."
     -- REPAIR-ACTION
     --     "Verify that the VLR is functioning properly. Reset indication from Gs VLR
     --      does not trigger any active recovery action on the SGSN."
     -- ENTITY-TYPE
     --     "system"
     --
        ::= { anMmeTrapEvents 134283377 }

    anMmeTrapEventMmeUpm1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "GW restart counter increment detected. "
     -- REPAIR-ACTION
     --     "Verify that GW is working properly."
     -- ENTITY-TYPE
     --     "system"
     --
        ::= { anMmeTrapEvents 134545508 }

    anMmeTrapEventMmeSigtran1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Sigtran Unauthorized Associate"
     -- REPAIR-ACTION
     --     "Most likely, this customer log will indicate a provisioning error. Check
     --      for mismatches between the IP address and port in the customer log and
     --      those in peer process components. However, in the case of an unsecure or
     --      public network, this customer log indicates that an intrusion has been
     --      successfully defeated. No further action is required."
     -- ENTITY-TYPE
     --     "system"
     --
        ::= { anMmeTrapEvents 135594085 }

    anMmeTrapEventMmeSigtran1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Sigtran Unknown Destination"
     -- REPAIR-ACTION
     --     "Use point code in the customer log to diagnose misconfiguration."
     -- ENTITY-TYPE
     --     "mme-remote-destination"
     --
        ::= { anMmeTrapEvents 135594086 }

    anMmeTrapEventMmeTcap1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "HLR Reset Received"
     -- REPAIR-ACTION
     --     "Verify that the HLR is functioning properly."
     -- ENTITY-TYPE
     --     "system"
     --
        ::= { anMmeTrapEvents 135659621 }

    anMmeTrapEventSgsnIu1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "IU Reject Pending Switchover."
     -- REPAIR-ACTION
     --     "Try the command again later, or use a "force" option if the resulting data
     --      loss is acceptable. Synchronization status can be shown using the CLI command
     --      "show vm"."
     -- ENTITY-TYPE
     --     "system"
     --
        ::= { anMmeTrapEvents 136314980 }

    anMmeTrapEventSgsnIu1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Iu Global CN-ID Mismatch."
     -- REPAIR-ACTION
     --     "Check RNC configuration or configure the 'epc service-area sgsn-pool cn-id'
     --      on the SGSN."
     -- ENTITY-TYPE
     --     "mme-rnc"
     --
        ::= { anMmeTrapEvents 136314981 }

    anMmeTrapEventSgsnIpSp1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Stale SCCP Entry found on IpSp."
     -- REPAIR-ACTION
     --     "No action required."
     -- ENTITY-TYPE
     --     "system"
     --
        ::= { anMmeTrapEvents 136380516 }

    anMmeTrapEventSgsnIpSp1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "M3UA association from unauthorized IP address and port has failed."
     -- REPAIR-ACTION
     --     "No action required."
     -- ENTITY-TYPE
     --     "system"
     --
        ::= { anMmeTrapEvents 136380517 }

    anMmeTrapEventSgsnSd1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Data buffer memory on SD process reached a threshold level."
     -- REPAIR-ACTION
     --     "No repair action required."
     -- ENTITY-TYPE
     --     "system"
     --
        ::= { anMmeTrapEvents 136446052 }

    anMmeTrapEventSgsnSd1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Downlink buffer initialization failed."
     -- REPAIR-ACTION
     --     "No repair action required."
     -- ENTITY-TYPE
     --     "system"
     --
        ::= { anMmeTrapEvents 136446053 }

    anMmeTrapEventSgsnSd1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Memory pool usage reached a threshold (allocating header compression obj)."
     -- REPAIR-ACTION
     --     "Increase the provisioned value of 'max-header-compression-entities' attribute
     --      of the 'epc interface gb sndcp' component."
     -- ENTITY-TYPE
     --     "system"
     --
        ::= { anMmeTrapEvents 136446054 }

    anMmeTrapEventSgsnSd1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Number of allocated PFC leaky buckets reaches the calculated limit."
     -- REPAIR-ACTION
     --     "Verify that the values of the provisionable attributes 'average-pfcs-per-mobile'
     --      under 'epc interface gb packet-flow-management' component and 'pdn-average'
     --      under 'epc engineering sc-capacity' component are sufficient to handle
     --      the level of subscriber demand required. Increase if necessary."
     -- ENTITY-TYPE
     --     "system"
     --
        ::= { anMmeTrapEvents 136446055 }

    anMmeTrapEventSgsnSd1404       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Maximum number of BVCs is reached."
     -- REPAIR-ACTION
     --     "Perform a manual BVC audit across all NSEs and determine which BVC(s) exceed
     --      SGSN engineering limits and remove them from service at the PCU. "
     -- ENTITY-TYPE
     --     "system"
     --
        ::= { anMmeTrapEvents 136446056 }

    anMmeTrapEventSgsnGb1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A signaling BVC reset has occurred."
     -- REPAIR-ACTION
     --     "This log is informational in nature.  No remedial action is necessary."
     -- ENTITY-TYPE
     --     "mme-nse"
     --
        ::= { anMmeTrapEvents 136511588 }

    anMmeTrapEventSgsnGb1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "The limit of PTP-BVCs per NSE has been reached."
     -- REPAIR-ACTION
     --     "Perform a manual PTP-BVC audit across all NSEs and determine which PTP-BVCs
     --      exceed SGSN engineering limits and remove them from service at the PCU."
     -- ENTITY-TYPE
     --     "mme-nse"
     --
        ::= { anMmeTrapEvents 136511589 }

    anMmeTrapEventSgsnGb1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Signaling NS-VCs are unavailable."
     -- REPAIR-ACTION
     --     "Verify the health of the network path to the PCU. Verify that the PCU is
     --      functioning properly."
     -- ENTITY-TYPE
     --     "mme-nse"
     --
        ::= { anMmeTrapEvents 136511590 }

    anMmeTrapEventSgsnGb1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "There are temporary problems with the dynamic IP configuration procedure."
     -- REPAIR-ACTION
     --     "This log is informational in nature. No remedial action is necessary"
     -- ENTITY-TYPE
     --     "mme-nse"
     --
        ::= { anMmeTrapEvents 136511591 }

    anMmeTrapEventSgsnGb1404       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A dynamic config procedure was attempted with static config provisioned."
     -- REPAIR-ACTION
     --     "Verify that the PCU is using a static configuration or reconfigure the
     --      NSE on the SGSN to use a dynamic configuration; i.e., delete all configured
     --      remote endpoints ('epc interface gb static-nse-remote-endpoint' instances)."
     -- ENTITY-TYPE
     --     "mme-nse"
     --
        ::= { anMmeTrapEvents 136511592 }

    anMmeTrapEventSgsnGb1405       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "There is a potential PTP-BVC mismatch."
     -- REPAIR-ACTION
     --     "Perform a manual PTP-BVC audit on the NSE shown in the log on both the
     --      SGSN and PCU. Verify that PTP-BVC state mismatches exist and take appropriate
     --      action on the PCU to unblock any PTP-BVCs with mismatched states. Additionally,
     --      a signaling BVC reset procedure ('epc interface gb sig-bvc reset ...')
     --      can be performed, which will result in a service outage for the impacted
     --      NSE."
     -- ENTITY-TYPE
     --     "mme-nse"
     --
        ::= { anMmeTrapEvents 136511593 }

    anMmeTrapEventMmeSbc1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A message is either received from the CBC or sent to the CBC."
     -- REPAIR-ACTION
     --     "No repair action required."
     -- ENTITY-TYPE
     --     "cbc"
     --
        ::= { anMmeTrapEvents 137232485 }

    anMmeTrapEventMmeSbc1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "CBC Association Status"
     -- REPAIR-ACTION
     --     "Check health of CBC and IP network"
     -- ENTITY-TYPE
     --     "cbc"
     --
        ::= { anMmeTrapEvents 137232486 }

    anMmeTrapEventTrace1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "A 3GPP trace file was closed successfully and is available."
     -- REPAIR-ACTION
     --     "No repair action required."
     -- ENTITY-TYPE
     --     "system"
     --
        ::= { anMmeTrapEvents 137494628 }

    anMmeTrapEventTrace1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "The file system partition used for PCAP filtering is full."
     -- REPAIR-ACTION
     --     "No immediate repair action required."
     -- ENTITY-TYPE
     --     "system"
     --
        ::= { anMmeTrapEvents 137494629 }

    anMmeTrapEventTrace1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace File Bulk Sync Abnormal Termination."
     -- REPAIR-ACTION
     --     "It is recommended to audit the trace files in /usr/local/epc/trace on both
     --      active and standby MGMT/MRM VM for consistency, to ensure there is no loss
     --      of data due to possible abnormal file sync termination."
     -- ENTITY-TYPE
     --     "system"
     --
        ::= { anMmeTrapEvents 137494630 }

    anMmeTrapEventMmeSgs1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Location Area can not be determined."
     -- REPAIR-ACTION
     --     "Configure the TA in the 'tac-range-list' attribute of the 'location-area'
     --      entity or designate a default LA by setting the 'default-la' attribute
     --      to "true" for one of the location-area entities."
     -- ENTITY-TYPE
     --     "mme-tracking-area"
     --
        ::= { anMmeTrapEvents 138477668 }

    anMmeTrapEventMmeSgs1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "VLR Reset."
     -- REPAIR-ACTION
     --     "Verify that the VLR is functioning properly."
     -- ENTITY-TYPE
     --     "mme-vlr"
     --
        ::= { anMmeTrapEvents 138477669 }

    anMmeTrapEventMME1600       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Hung process detected."
     -- REPAIR-ACTION
     --     "No repair action required."
     -- ENTITY-TYPE
     --     "system"
     --
        ::= { anMmeTrapEvents 140640356 }

    anMmeTrapEventMME1601       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Critical config change received, process restarted."
     -- REPAIR-ACTION
     --     "No repair action required."
     -- ENTITY-TYPE
     --     "system"
     --
        ::= { anMmeTrapEvents 140640357 }

    anMmeTrapEventMME1602       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Backup Created."
     -- REPAIR-ACTION
     --     "No repair action required."
     -- ENTITY-TYPE
     --     "system"
     --
        ::= { anMmeTrapEvents 140640358 }

    anMmeTrapEventMME1603       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Support File Created."
     -- REPAIR-ACTION
     --     "No repair action required."
     -- ENTITY-TYPE
     --     "system"
     --
        ::= { anMmeTrapEvents 140640359 }

    anMmeTrapEventMME1604       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Login Failure"
     -- REPAIR-ACTION
     --     "See /var/log/auth.log to get more details about the login failure."
     -- ENTITY-TYPE
     --     "system"
     --
        ::= { anMmeTrapEvents 140640360 }

    anMmeTrapEventFgwSc1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace Session Started."
     -- REPAIR-ACTION
     --     "No repair action required."
     -- ENTITY-TYPE
     --     "system"
     --
        ::= { anMmeTrapEvents 142344292 }

    anMmeTrapEventFgwSc1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace Session Stopped."
     -- REPAIR-ACTION
     --     "No repair action required."
     -- ENTITY-TYPE
     --     "system"
     --
        ::= { anMmeTrapEvents 142344293 }

    anMmeTrapEventFgwSc1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "FGW SC Reject Pending Switchover."
     -- REPAIR-ACTION
     --     "Try the command again later, or use a "force" option if the resulting data
     --      loss is acceptable. Synchronization status can be  shown using the CLI
     --      command "show fgw status system"."
     -- ENTITY-TYPE
     --     "system"
     --
        ::= { anMmeTrapEvents 142344294 }

    anMmeTrapEventFgwSc1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "SC Activation During Sync Lost."
     -- REPAIR-ACTION
     --     "None."
     -- ENTITY-TYPE
     --     "system"
     --
        ::= { anMmeTrapEvents 142344295 }

    anMmeTrapEventFgwSc1404       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Trace eNodeB Failure Indication."
     -- REPAIR-ACTION
     --     "None."
     -- ENTITY-TYPE
     --     "mme-enodeb"
     --
        ::= { anMmeTrapEvents 142344296 }

    anMmeTrapEventLbCtrl1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "VM Steering Registration Failure."
     -- REPAIR-ACTION
     --     "Note the VM type and IP addresses in the reason text and lock/unlock the
     --      reporting LB VM."
     -- ENTITY-TYPE
     --     "system"
     --
        ::= { anMmeTrapEvents 144113764 }

    anMmeTrapEventLbCtrl1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Steering Policy Add Failure."
     -- REPAIR-ACTION
     --     "Analyze the policy 5 tuple and target VM name in the reason text and contact
     --      your next level of support."
     -- ENTITY-TYPE
     --     "system"
     --
        ::= { anMmeTrapEvents 144113765 }

    anMmeTrapEventLbCtrl1402       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Steering Policy Redirect Failure."
     -- REPAIR-ACTION
     --     "Analyze the policy 5 tuple and target VM name in the reason text and contact
     --      your next level of support."
     -- ENTITY-TYPE
     --     "system"
     --
        ::= { anMmeTrapEvents 144113766 }

    anMmeTrapEventLbCtrl1403       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Steering Policy Delete Failure."
     -- REPAIR-ACTION
     --     "Analyze the policy id in the reason text and contact your next level of
     --      support."
     -- ENTITY-TYPE
     --     "system"
     --
        ::= { anMmeTrapEvents 144113767 }

    anMmeTrapEventEdp1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "Data buffer memory on EDP process reached a threshold level."
     -- REPAIR-ACTION
     --     "No repair action required."
     -- ENTITY-TYPE
     --     "system"
     --
        ::= { anMmeTrapEvents 144179300 }

    anMmeTrapEventMmeMbms1400       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "MBMS Reject Pending Swtichover"
     -- REPAIR-ACTION
     --     "Try the command again later, or use a "force" option if the resulting data
     --      loss is acceptable. Synchronization status can be shown using the CLI command
     --      "show vm"."
     -- ENTITY-TYPE
     --     "system"
     --
        ::= { anMmeTrapEvents 196673636 }

    anMmeTrapEventMmeMbms1401       NOTIFICATION-TYPE
        OBJECTS   { anMmeAlarmState,
                    anMmeAlarmSeverity,
                    anMmeEntityTag,
                    anMmeSubentityInfo,
                    anMmeLocationGateway,
                    anMmeReason,
                    anMmeAlarmDateAndTime,
                    anMmeGroupKey,
                    anMmeSequenceNumber,
                    anMmeLocation,
                    anMmeService }
        STATUS      current
        DESCRIPTION
            "MBMS Activation During Sync Lost"
     -- REPAIR-ACTION
     --     "None."
     -- ENTITY-TYPE
     --     "system"
     --
        ::= { anMmeTrapEvents 196673637 }
END
