AFFIRMED-SNMP-MIB DEFINITIONS ::= BEGIN

--
-- Top-level infrastructure of the Affirmed enterprise MIB tree
--

IMPORTS
    MODULE-IDENTITY, enterprises       FROM SNMPv2-SMI;

affirmedSnmp MODULE-IDENTITY
    LAST-UPDATED "201105160000Z"
    ORGANIZATION "www.affirmednetworks.com"
    CONTACT-INFO
	 "postal:   Affirmed Networks, Inc.
		    35 Nagog Park
                    Acton, MA "
    DESCRIPTION
	"Top-level infrastructure of the Affirmed enterprise MIB tree"
    REVISION     "201105160000Z"
    DESCRIPTION
	"First draft"
    ::= { enterprises 37963}


--
--  AFFIRMED-SNMP enterprise-specific management objects
--

affirmedSnmpObjects              OBJECT IDENTIFIER ::= {affirmedSnmp 1}
-- affirmedSnmpExamples             OBJECT IDENTIFIER ::= {affirmedSnmp 2}
affirmedSnmpEnumerations         OBJECT IDENTIFIER ::= {affirmedSnmp 3}
affirmedSnmpModuleIDs            OBJECT IDENTIFIER ::= {affirmedSnmpEnumerations 1}
affirmedSnmpAgentOIDs            OBJECT IDENTIFIER ::= {affirmedSnmpEnumerations 2}
affirmedSnmpDomains              OBJECT IDENTIFIER ::= {affirmedSnmpEnumerations 3}
affirmedSnmpGeneral              OBJECT IDENTIFIER ::= {affirmedSnmp 10}
affirmedSnmpExperimental         OBJECT IDENTIFIER ::= {affirmedSnmp 9999}

--
-- A subtree specifically designed for private testing purposes.
-- No "public" management objects should ever be defined within this tree.
--
-- It is provided for private experimentation, prior to transferring a MIB
-- structure to another part of the overall OID tree
--
affirmedSnmpPlaypen              OBJECT IDENTIFIER ::= {affirmedSnmpExperimental 9999}


--
--  Notifications
--

affirmedSnmpNotificationPrefix   OBJECT IDENTIFIER ::= {affirmedSnmp 4}
affirmedSnmpNotifications        OBJECT IDENTIFIER ::= {affirmedSnmpNotificationPrefix 0}
affirmedSnmpNotificationObjects  OBJECT IDENTIFIER ::= {affirmedSnmpNotificationPrefix 1}


--
--  Conformance
--

affirmedSnmpConformance          OBJECT IDENTIFIER ::= {affirmedSnmp 5}
affirmedSnmpCompliances          OBJECT IDENTIFIER ::= {affirmedSnmpConformance 1}
affirmedSnmpGroups               OBJECT IDENTIFIER ::= {affirmedSnmpConformance 2}

END
