-- ===================================================================
-- Copyright (c) 2004-2022 New H3C Tech. Co., Ltd. All rights reserved.
--
-- Description: V1.0
-- History:
--   V1.0 Created by zhangjitong
--        Initial version 2022-01-25
-- ====================================================================
HH3C-KPI-MIB DEFINITIONS ::= BEGIN

IMPORTS
        hh3cCommon
    FROM HH3C-OID-MIB
        Integer32, OBJECT-TYPE, NOTIFICATION-TYPE, MODULE-IDENTITY
    FROM SNMPv2-SMI;

hh3cKPI MODULE-IDENTITY
    LAST-UPDATED "202204081635Z"
    ORGANIZATION
        "New H3C Tech. Co., Ltd."
    CONTACT-INFO
        "Platform Team New H3C Technologies Co., Ltd.
        Hai-Dian District Beijing P.R. China
        Http://www.h3c.com
        Zip:100085"
    DESCRIPTION
        "The MIB module is used for managing KPI."
    REVISION "202204081635Z"
    DESCRIPTION
        "Modify the SYNTAX of hh3cKPIDataTimeStamp from TimeStamp to OCTET STRING."
    REVISION "202201251502Z"
    DESCRIPTION
        "The initial revision of this KPI module."
    ::= { hh3cCommon 221 }

hh3cKPINotification OBJECT IDENTIFIER ::= {hh3cKPI 1}

hh3cKPINotificationPrefix OBJECT IDENTIFIER ::= { hh3cKPINotification 0 }

-- All Notifications definitions should be placed under this object
hh3cKPIDataOverThreshold NOTIFICATION-TYPE
    OBJECTS
    {
        hh3cKPIDataChassis,
        hh3cKPIDataSlot,
        hh3cKPIDataCPUID,
        hh3cKPIDataModuleName,
        hh3cKPIDataTimeStamp,
        hh3cKPIDataObjectName,
        hh3cKPIDataIndicatorName,
        hh3cKPIDataIndicatorValue,
        hh3cKPIDataThreshold
    }
    STATUS       current
    DESCRIPTION
        "This notification is generated when the KPI value exceeds the threshold."
    ::= { hh3cKPINotificationPrefix 1 }

hh3cKPIDataRecover NOTIFICATION-TYPE
    OBJECTS
    {
        hh3cKPIDataChassis,
        hh3cKPIDataSlot,
        hh3cKPIDataCPUID,
        hh3cKPIDataModuleName,
        hh3cKPIDataTimeStamp,
        hh3cKPIDataObjectName,
        hh3cKPIDataIndicatorName,
        hh3cKPIDataIndicatorValue,
        hh3cKPIDataThreshold
    }
    STATUS       current
    DESCRIPTION
        "This notification is generated when the KPI value returns within the threshold range."
    ::= { hh3cKPINotificationPrefix 2 }

hh3cKPIPredictDataOverThreshold NOTIFICATION-TYPE
    OBJECTS
    {
        hh3cKPIDataChassis,
        hh3cKPIDataSlot,
        hh3cKPIDataCPUID,
        hh3cKPIDataModuleName,
        hh3cKPIDataTimeStamp,
        hh3cKPIDataObjectName,
        hh3cKPIDataIndicatorName,
        hh3cKPIDataIndicatorValue,
        hh3cKPIDataPredictCycle,
        hh3cKPIDataThreshold
    }
    STATUS       current
    DESCRIPTION
        "This notification is generated when the predicted KPI value exceeds the
        threshold after n cycles."
    ::= { hh3cKPINotificationPrefix 3 }

hh3cKPIPredictDataRecover NOTIFICATION-TYPE
    OBJECTS
    {
        hh3cKPIDataChassis,
        hh3cKPIDataSlot,
        hh3cKPIDataCPUID,
        hh3cKPIDataModuleName,
        hh3cKPIDataTimeStamp,
        hh3cKPIDataObjectName,
        hh3cKPIDataIndicatorName,
        hh3cKPIDataIndicatorValue,
        hh3cKPIDataPredictCycle,
        hh3cKPIDataThreshold
    }
    STATUS       current
    DESCRIPTION
        "This notification is generated when the predicted KPI value returns within the threshold range."
    ::= { hh3cKPINotificationPrefix 4 }

hh3cKPINotificationDefinitions OBJECT IDENTIFIER ::= {hh3cKPINotification 1}
-- All objects used for Notification only are defined here

hh3cKPIDataChassis OBJECT-TYPE
    SYNTAX Integer32(0..65535)
    MAX-ACCESS  accessible-for-notify
    STATUS  current
    DESCRIPTION
        "Number of the chassis where the KPI data is collected."
    ::= { hh3cKPINotificationDefinitions 1 }

hh3cKPIDataSlot OBJECT-TYPE
    SYNTAX Integer32(0..65535)
    MAX-ACCESS accessible-for-notify
    STATUS current
    DESCRIPTION
        "Number of the slot where the KPI data is collected."
    ::= { hh3cKPINotificationDefinitions 2 }

hh3cKPIDataCPUID OBJECT-TYPE
    SYNTAX Integer32(0..65535)
    MAX-ACCESS accessible-for-notify
    STATUS current
    DESCRIPTION
        "Number of the CPU where the KPI data is collected."
    ::= { hh3cKPINotificationDefinitions 3 }

hh3cKPIDataModuleName OBJECT-TYPE
    SYNTAX OCTET STRING (SIZE(1..8))
    MAX-ACCESS accessible-for-notify
    STATUS current
    DESCRIPTION
        "Name of the module where the KPI data is collected."
    ::= { hh3cKPINotificationDefinitions 4 }

hh3cKPIDataTimeStamp OBJECT-TYPE
    SYNTAX OCTET STRING (SIZE(1..32))
    MAX-ACCESS accessible-for-notify
    STATUS current
    DESCRIPTION
        "Time when the KPI data is collected."
    ::= { hh3cKPINotificationDefinitions 5 }

hh3cKPIDataObjectName OBJECT-TYPE
    SYNTAX OCTET STRING (SIZE(1..64))
    MAX-ACCESS accessible-for-notify
    STATUS current
    DESCRIPTION
        "Name of the object where the KPI data is collected."
    ::= { hh3cKPINotificationDefinitions 6 }

hh3cKPIDataIndicatorName OBJECT-TYPE
    SYNTAX OCTET STRING (SIZE(1..64))
    MAX-ACCESS accessible-for-notify
    STATUS current
    DESCRIPTION
        "Name of the KPI indicator."
    ::= { hh3cKPINotificationDefinitions 7 }

hh3cKPIDataIndicatorValue OBJECT-TYPE
    SYNTAX OCTET STRING (SIZE(1..32))
    MAX-ACCESS accessible-for-notify
    STATUS current
    DESCRIPTION
        "Value of the KPI indicator."
    ::= { hh3cKPINotificationDefinitions 8 }

hh3cKPIDataPredictCycle OBJECT-TYPE
    SYNTAX Integer32(0..65535)
    MAX-ACCESS accessible-for-notify
    STATUS current
    DESCRIPTION
        "Number of cycles after which the threshold will be exceeded."
    ::= { hh3cKPINotificationDefinitions 9 }

hh3cKPIDataThreshold OBJECT-TYPE
    SYNTAX OCTET STRING (SIZE(1..32))
    MAX-ACCESS accessible-for-notify
    STATUS current
    DESCRIPTION
        "Upper/Lower threshold, that is, the maximum/minimum value of the KPI data."
    ::= { hh3cKPINotificationDefinitions 10 }

END
