-- Dot1x Advanced Features MIB overview:
-- Dot1x Advanced Features MIB falls under MIB node of the private subtree.

DOT1X-ADVANCED-FEATURES-MIB DEFINITIONS ::= BEGIN

-- Quanta Computer Inc. Dot1x Advanced Features MIB
-- Copyright 2004- Quanta Computer, Inc. All rights reserved.

-- This SNMP Management Information Specification
-- embodies Quanta Computer Inc.'s confidential and proprietary
-- intellectual property.  Quanta Computer Inc. retains all title
-- and ownership in the Specification including any revisions.

-- This Specification is supplied "AS IS", Quanta Computer Inc.
-- makes no warranty, either expressed or implied,
-- as to the use, operation, condition, or performance of the
-- Specification.


IMPORTS
    MODULE-IDENTITY, OBJECT-TYPE, NOTIFICATION-TYPE,
    Unsigned32, TimeTicks               FROM SNMPv2-SMI
    dot1xPaePortNumber                  FROM IEEE8021-PAE-MIB
    TEXTUAL-CONVENTION,
    RowStatus,MacAddress,DateAndTime    FROM SNMPv2-TC
    DisplayString, PhysAddress          FROM RFC1213-MIB
    switch                              FROM QUANTA-SWITCH-MIB;


    dot1xAdvanced MODULE-IDENTITY
           LAST-UPDATED "201108310000Z" -- 26 January 2011 12:00:00 GMT
           ORGANIZATION "Quanta Computer Inc."
        CONTACT-INFO
          "                      Customer Support
          Postal:                Quanta Computer Inc.
                                 4, Wen Ming 1 St., Kuei Shan Hsiang,
                                 Tao Yuan Shien, Taiwan, R.O.C.
          Tel:                   +886 3 328 0050
          E-Mail:                support@quantatw.com"

     DESCRIPTION
          "The Private MIB for Dot1x Advanced Features "
      ::= { switch 36 }


Dot1xPortControlMode ::= TEXTUAL-CONVENTION
    STATUS       current
    DESCRIPTION
        "The control values of the Authenticator PAE controlled
        Port."
    SYNTAX      INTEGER {
                    forceUnauthorized(1),
                    auto(2),
                    forceAuthorized(3),
                    macBased(4)
                }

Dot1xSessionTerminationAction ::= TEXTUAL-CONVENTION
        STATUS  current
        DESCRIPTION
              "The action to be taken on session termination ."
        SYNTAX       INTEGER {
                                default(1),
                                reauthenticate(2)
                              }

--**************************************************************************************
-- agentGuestVlanConfigGroup -> Contains MIB objects displaying Guest VLAN and
-- associated Functionality
--
--**************************************************************************************

    agentGuestVlanConfigGroup OBJECT IDENTIFIER ::= { dot1xAdvanced 1 }

    agentGuestVlanSupplMode OBJECT-TYPE
         SYNTAX      INTEGER {
                     enable(1),
                     disable(2)
                     }
         MAX-ACCESS  read-write
         STATUS      current
         DESCRIPTION
               "Mode showing whether at the global level,Guest VLAN Supplicant Mode is
               enabled or not."
         DEFVAL { disable }
         ::= { agentGuestVlanConfigGroup 1 }

--------------------------------------------------------------
-- The PAE Port Table
--------------------------------------------------------------

    agentDot1xGuestVlanPortConfigTable OBJECT-TYPE
         SYNTAX      SEQUENCE OF AgentDot1xGuestVlanPortConfigEntry
         MAX-ACCESS  not-accessible
         STATUS      current
         DESCRIPTION "A table for Guest Vlan and associated functionality."
         ::= { agentGuestVlanConfigGroup 2 }

    agentDot1xGuestVlanPortConfigEntry OBJECT-TYPE
         SYNTAX      AgentDot1xGuestVlanPortConfigEntry
         MAX-ACCESS  not-accessible
         STATUS      current
         DESCRIPTION "Represents entry for guest config table."
         INDEX       { dot1xPaePortNumber }
         ::= { agentDot1xGuestVlanPortConfigTable 1 }

    AgentDot1xGuestVlanPortConfigEntry ::= SEQUENCE {
            agentDot1xGuestVlanId
                 Unsigned32,
            agentDot1xGuestVlanPeriod
                 Unsigned32
          }

    agentDot1xGuestVlanId  OBJECT-TYPE
         SYNTAX      Unsigned32
         MAX-ACCESS   read-write
         STATUS       current
         DESCRIPTION
               "Specifies the Guest Vlan of the interface. An interface will
               be moved to its Guest Vlan if its access is unsucessfully
               authenticated. A value of zero indicates no Guest Vlan
               configured for the interface."
         DEFVAL {0}
         ::= { agentDot1xGuestVlanPortConfigEntry 1}

    agentDot1xGuestVlanPeriod OBJECT-TYPE
         SYNTAX      Unsigned32 (0..65535)
         MAX-ACCESS  read-write
         STATUS      current
         DESCRIPTION
               "The value, in seconds, of the guestVlanPeriod constant
               currently in use for Guest Vlan Assignment for the
               interface ."
         DEFVAL { 90 }
         ::= { agentDot1xGuestVlanPortConfigEntry 2 }

agentDot1xEnhancementConfigGroup OBJECT IDENTIFIER ::= { dot1xAdvanced 2 }

    agentDot1xRadiusVlanAssignment OBJECT-TYPE
         SYNTAX      INTEGER {
                     enable(1),
                     disable(2)
                     }
         MAX-ACCESS  read-write
         STATUS      current
         DESCRIPTION
               "Enable/Disable dot1x Vlan Assignment Support on the switch."
         DEFVAL { disable }
         ::= { agentDot1xEnhancementConfigGroup 1 }

     agentDot1xDynamicVlanCreationMode OBJECT-TYPE
         SYNTAX      INTEGER {
                     enable(1),
                     disable(2)
                     }
         MAX-ACCESS  read-write
         STATUS      current
         DESCRIPTION
               "Enable/Disable dot1x dynamic vlan creation Support on the switch."
         DEFVAL { disable }
         ::= { agentDot1xEnhancementConfigGroup 2 }

--------------------------------------------------------------
-- The client Table
--------------------------------------------------------------

    agentDot1xClientGroup OBJECT IDENTIFIER ::= { dot1xAdvanced 3 }

    agentDot1xClientTable OBJECT-TYPE
         SYNTAX      SEQUENCE OF AgentDot1xClientEntry
         MAX-ACCESS  not-accessible
         STATUS      current
         DESCRIPTION "A table for Guest Vlan and associated functionality."
         ::= { agentDot1xClientGroup 1 }

    agentDot1xClientEntry OBJECT-TYPE
         SYNTAX      AgentDot1xClientEntry
         MAX-ACCESS  not-accessible
         STATUS      current
         DESCRIPTION "Represents entry for guest config table."
         INDEX       { agentDot1xClientLogicalInterface }
         ::= { agentDot1xClientTable 1 }

    AgentDot1xClientEntry ::= SEQUENCE {
            agentDot1xClientLogicalInterface
                 Unsigned32,
            agentDot1xClientInterface
                 DisplayString,
            agentDot1xClientUsername
                 DisplayString,
            agentDot1xClientMacAddress
                 PhysAddress,
            agentDot1xClientSessionTime
                 Unsigned32,
            agentDot1xClientVlanId
                 Unsigned32,
            agentDot1xClientVlanAssigned
                 INTEGER,
            agentDot1xClientSessionTimeout
                 Unsigned32,
            agentDot1xClientSessionTerminationAction
                 INTEGER
          }

    agentDot1xClientLogicalInterface  OBJECT-TYPE
         SYNTAX      Unsigned32
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 1}

    agentDot1xClientInterface  OBJECT-TYPE
         SYNTAX      DisplayString
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 2}

    agentDot1xClientUsername  OBJECT-TYPE
         SYNTAX      DisplayString
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 3}

    agentDot1xClientMacAddress  OBJECT-TYPE
         SYNTAX      PhysAddress
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 4}

    agentDot1xClientSessionTime  OBJECT-TYPE
         SYNTAX      Unsigned32
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 5}

    agentDot1xClientVlanId  OBJECT-TYPE
         SYNTAX      Unsigned32
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 6}

    agentDot1xClientVlanAssigned  OBJECT-TYPE
         SYNTAX      INTEGER {
                     default(1),
                     radius(2),
                     unauthenticated(3)
                     }
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 7}

    agentDot1xClientSessionTimeout  OBJECT-TYPE
         SYNTAX      Unsigned32
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 8}

    agentDot1xClientSessionTerminationAction  OBJECT-TYPE
         SYNTAX      INTEGER {
                     default(1),
                     radius(2)
                     }
         MAX-ACCESS   read-only
         STATUS       current
         DESCRIPTION
               "Specifies the Guest Vlan of the interface. An interface will
               be moved to its Guest Vlan if its access is unsucessfully
               authenticated. A value of zero indicates no Guest Vlan
               configured for the interface."
         ::= { agentDot1xClientEntry 9}


END
