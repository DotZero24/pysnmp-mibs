MULTICAST-MIB DEFINITIONS ::= BEGIN

-- Multicast Routing Package MIB
-- Copyright Quanta Computer Inc. (2002-2007) All rights reserved.

-- This SNMP Management Information Specification
-- embodies Quanta Computer Inc.'s confidential and proprietary
-- intellectual property.  Quanta Computer Inc. retains all title
-- and ownership in the Specification including any revisions.

-- This Specification is supplied "AS IS", Quanta Computer Inc.
-- makes no warranty, either expressed or implied,
-- as to the use, operation, condition, or performance of the
-- Specification.


IMPORTS
    MODULE-IDENTITY,OBJECT-TYPE,
    Integer32,IpAddress,Unsigned32
                                        FROM SNMPv2-SMI
    RowStatus                           FROM SNMPv2-TC
    InetAddress,InetAddressType         FROM INET-ADDRESS-MIB
    Ipv6Address                         FROM IPV6-TC
    InterfaceIndex                      FROM IF-MIB
    quanta, switch                      FROM QUANTA-SWITCH-MIB;

    multicast MODULE-IDENTITY
        LAST-UPDATED "201108310000Z" -- 26 Jan 2011 12:00:00 GMT
        ORGANIZATION "Quanta Computer Inc."
        CONTACT-INFO
          "                      Customer Support
          Postal:                Quanta Computer Inc.
                                 No. 211, Wen Hwa 2nd Rd., Kuei Shan Hsiang,
                                 Tao Yuan Shien, Taiwan, R.O.C.
          Tel:                   +886 3 327 2345"
        DESCRIPTION
          "The MIB definitions for Multicast Routing Flex package."
        REVISION
          "201108310000Z" -- 26 Jan 2011 12:00:00 GMT
        DESCRIPTION
          "Updated for release"


    ::= { switch 4 }


    --**************************************************************************************
    agentMulticastIGMPConfigGroup                      OBJECT IDENTIFIER ::= { multicast 1 }

    agentMulticastIGMPAdminMode OBJECT-TYPE
         SYNTAX      INTEGER {
                     enable(1),
                     disable(2)
                  }
         MAX-ACCESS  read-write
         STATUS      current
         DESCRIPTION
                     "This enables or disables IGMP on the system."
         DEFVAL { disable }
         ::= { agentMulticastIGMPConfigGroup 1 }


    agentMulticastIGMPInterfaceTable OBJECT-TYPE
         SYNTAX      SEQUENCE OF AgentMulticastIGMPInterfaceEntry
         MAX-ACCESS  not-accessible
         STATUS      obsolete
         DESCRIPTION
                     "Provides Per-Interface configuration of IGMP."
         ::= { agentMulticastIGMPConfigGroup 2 }

    agentMulticastIGMPInterfaceEntry OBJECT-TYPE
         SYNTAX      AgentMulticastIGMPInterfaceEntry
         MAX-ACCESS  not-accessible
         STATUS      obsolete
         DESCRIPTION
                     "Information about a table entry."
         INDEX       { agentMulticastIGMPInterfaceIfIndex }
         ::= { agentMulticastIGMPInterfaceTable 1 }

    AgentMulticastIGMPInterfaceEntry ::= SEQUENCE {
         agentMulticastIGMPInterfaceIfIndex
              Integer32,
         agentMulticastIGMPInterfaceAdminMode
              INTEGER
         }

    agentMulticastIGMPInterfaceIfIndex OBJECT-TYPE
         SYNTAX      Integer32 (0..2147483647)
         MAX-ACCESS  read-only
         STATUS      obsolete
         DESCRIPTION
                     "Identifies the external interface number."
         ::= { agentMulticastIGMPInterfaceEntry 1 }

    agentMulticastIGMPInterfaceAdminMode OBJECT-TYPE
         SYNTAX      INTEGER {
                     enable(1),
                     disable(2)
                  }
         MAX-ACCESS  read-write
         STATUS      obsolete
         DESCRIPTION
                     "This enables or disables IGMP on this interface."
         DEFVAL { disable }
         ::= { agentMulticastIGMPInterfaceEntry 2 }

    agentMulticastIGMPProxyInterfaceTable OBJECT-TYPE
         SYNTAX      SEQUENCE OF AgentMulticastIGMPProxyInterfaceEntry
         MAX-ACCESS  not-accessible
         STATUS      obsolete
         DESCRIPTION
                     "Provides Per-Interface configuration of IGMP."
         ::= { agentMulticastIGMPConfigGroup 3 }

    agentMulticastIGMPProxyInterfaceEntry OBJECT-TYPE
         SYNTAX      AgentMulticastIGMPProxyInterfaceEntry
         MAX-ACCESS  not-accessible
         STATUS      obsolete
         DESCRIPTION
                     "Information about a table entry."
         INDEX       { agentMulticastIGMPProxyInterfaceIfIndex }
         ::= { agentMulticastIGMPProxyInterfaceTable 1 }

    AgentMulticastIGMPProxyInterfaceEntry ::= SEQUENCE {
         agentMulticastIGMPProxyInterfaceIfIndex
              Integer32,
         agentMulticastIGMPProxyInterfaceAdminMode
              INTEGER,
         agentMulticastIGMPProxyInterfaceInterval
              Integer32
         }

    agentMulticastIGMPProxyInterfaceIfIndex OBJECT-TYPE
         SYNTAX      Integer32 (0..2147483647)
         MAX-ACCESS  read-only
         STATUS      obsolete
         DESCRIPTION
                     "Identifies the external interface number."
         ::= { agentMulticastIGMPProxyInterfaceEntry 1 }

    agentMulticastIGMPProxyInterfaceAdminMode OBJECT-TYPE
         SYNTAX      INTEGER {
                     enable(1),
                     disable(2)
                  }
         MAX-ACCESS  read-write
         STATUS      obsolete
         DESCRIPTION
                     "This enables or disables IGMP proxy on this interface."
         DEFVAL { disable }
         ::= { agentMulticastIGMPProxyInterfaceEntry 2 }

    agentMulticastIGMPProxyInterfaceInterval OBJECT-TYPE
         SYNTAX      Integer32 (1..260)
         MAX-ACCESS  read-write
         STATUS      obsolete
         DESCRIPTION
                     "IGMP proxy interval on this interface."
         DEFVAL { 1 }
         ::= { agentMulticastIGMPProxyInterfaceEntry 3 }


    --**************************************************************************************
    agentMulticastPIMConfigGroup                      OBJECT IDENTIFIER ::= { multicast 2 }

    agentMulticastPIMConfigMode OBJECT-TYPE
         SYNTAX      INTEGER {
                     none(0),
                     sparse(1),
                     dense(2)
                  }
         MAX-ACCESS  read-only
         STATUS      obsolete
         DESCRIPTION
                     "This shows which PIM mode configuration the PIM-MIB displays."
         DEFVAL { none }
         ::= { agentMulticastPIMConfigGroup 1 }

    --**************************************************************************************
    agentMulticastPIMSMConfigGroup                      OBJECT IDENTIFIER ::= { multicast 3 }

    agentMulticastPIMSMAdminMode OBJECT-TYPE
         SYNTAX      INTEGER {
                     enable(1),
                     disable(2)
                  }
         MAX-ACCESS  read-write
         STATUS      current
         DESCRIPTION
                     "This enables or disables PIM Sparse Mode on the system."
         DEFVAL { disable }
         ::= { agentMulticastPIMSMConfigGroup 1 }

    agentMulticastPIMSMDataThresholdRate OBJECT-TYPE
         SYNTAX      Integer32 (0..1)
         MAX-ACCESS  read-write
         STATUS      obsolete
         DESCRIPTION
                     "Specifies the minimum rate in Kbits/sec for the last hop router to initiate switching to the shortest path.
                      Only support 0 and 1 (infinity)."
         DEFVAL { 0 }
         ::= { agentMulticastPIMSMConfigGroup 2 }

--    agentMulticastPIMSMRegThresholdRate OBJECT-TYPE
--         SYNTAX      Integer32 (0..2000)
--         MAX-ACCESS  read-write
--         STATUS      obsolete
--         DESCRIPTION
--                     "Specifies the minimum rate in Kbits/sec for the RP to switch to the shortest path."
--         DEFVAL { 50 }
--         ::= { agentMulticastPIMSMConfigGroup 3 }

    agentMulticastPIMSMStaticRPTable OBJECT-TYPE
         SYNTAX      SEQUENCE OF AgentMulticastPIMSMStaticRPEntry
         MAX-ACCESS  not-accessible
         STATUS      obsolete
         DESCRIPTION
                     "Provides Per-Interface configuration of PIM-SM."
         ::= { agentMulticastPIMSMConfigGroup 4 }

    agentMulticastPIMSMStaticRPEntry OBJECT-TYPE
         SYNTAX      AgentMulticastPIMSMStaticRPEntry
         MAX-ACCESS  not-accessible
         STATUS      obsolete
         DESCRIPTION
                     "Information about a table entry."
         INDEX       { agentMulticastPIMSMStaticRPIpAddr,
                       agentMulticastPIMSMStaticRPGroupIpAddr,
                       agentMulticastPIMSMStaticRPGroupIpMask }
         ::= { agentMulticastPIMSMStaticRPTable 1 }

    AgentMulticastPIMSMStaticRPEntry ::= SEQUENCE {
         agentMulticastPIMSMStaticRPIpAddr
              IpAddress,
         agentMulticastPIMSMStaticRPGroupIpAddr
              IpAddress,
         agentMulticastPIMSMStaticRPGroupIpMask
              IpAddress,
         agentMulticastPIMSMStaticRPStatus
              RowStatus
         }

    agentMulticastPIMSMStaticRPIpAddr OBJECT-TYPE
         SYNTAX      IpAddress
         MAX-ACCESS  not-accessible
         STATUS      obsolete
         DESCRIPTION
                     "IP Address of the RP."
         ::= { agentMulticastPIMSMStaticRPEntry 1 }

    agentMulticastPIMSMStaticRPGroupIpAddr OBJECT-TYPE
         SYNTAX      IpAddress
         MAX-ACCESS  not-accessible
         STATUS      obsolete
         DESCRIPTION
                     "Group IP Address supported by the RP."
         ::= { agentMulticastPIMSMStaticRPEntry 2 }

    agentMulticastPIMSMStaticRPGroupIpMask OBJECT-TYPE
         SYNTAX      IpAddress
         MAX-ACCESS  not-accessible
         STATUS      obsolete
         DESCRIPTION
                     "Group mask for the group IP Address."
         ::= { agentMulticastPIMSMStaticRPEntry 3 }

    agentMulticastPIMSMStaticRPStatus OBJECT-TYPE
         SYNTAX      RowStatus
         MAX-ACCESS  read-create
         STATUS      obsolete
         DESCRIPTION
                     "Status of this entry in the Static RP Table.

                     Allowed values are:

                     active(1)      - This entry is active
                     destroy(6)     - Setting an entry to this value removes the
                                      entry from the table."
         ::= { agentMulticastPIMSMStaticRPEntry 4 }


    agentMulticastPIMSMCBSRInterfaceTable OBJECT-TYPE
         SYNTAX      SEQUENCE OF AgentMulticastPIMSMCBSRInterfaceEntry
         MAX-ACCESS  not-accessible
         STATUS      obsolete
         DESCRIPTION
                     "Provides Per-Interface configuration of PIM-SM."
         ::= { agentMulticastPIMSMConfigGroup 5 }

    agentMulticastPIMSMCBSRInterfaceEntry OBJECT-TYPE
         SYNTAX      AgentMulticastPIMSMCBSRInterfaceEntry
         MAX-ACCESS  not-accessible
         STATUS      obsolete
         DESCRIPTION
                     "Allows configuration of parameters not provided in the
                      standard PIM-MIB."
         INDEX { agentMulticastPIMSMCBSRInterfaceIndex }
         ::= { agentMulticastPIMSMCBSRInterfaceTable 1 }

    AgentMulticastPIMSMCBSRInterfaceEntry ::= SEQUENCE {
         agentMulticastPIMSMCBSRInterfaceIndex
              Unsigned32,
         agentMulticastPIMSMCBSRInterfaceHashMaskLength
              Unsigned32,
         agentMulticastPIMSMCBSRInterfacePriority
              Integer32
         }

    agentMulticastPIMSMCBSRInterfaceIndex OBJECT-TYPE
         SYNTAX      Unsigned32
         MAX-ACCESS  not-accessible
         STATUS      obsolete
         DESCRIPTION
                     "Routing Interface associated with this PIM SM configuration entry."
         ::= { agentMulticastPIMSMCBSRInterfaceEntry 1 }

    agentMulticastPIMSMCBSRInterfaceHashMaskLength OBJECT-TYPE
         SYNTAX      Unsigned32 (0..32)
         MAX-ACCESS  read-write
         STATUS      obsolete
         DESCRIPTION
                     "The BSR hash mask length to be advertised in bootstrap messages if
                     this interface is elected as the bootstrap router. This hash mask
                     length will be used in the hash algorith for selecting the RP for
                     a particular group."
         DEFVAL      { 30 }
         ::= { agentMulticastPIMSMCBSRInterfaceEntry 2 }

    agentMulticastPIMSMCBSRInterfacePriority OBJECT-TYPE
         SYNTAX      Integer32 (-1..255)
         MAX-ACCESS  read-write
         STATUS      obsolete
         DESCRIPTION
                     "The preference value for the local interface as a Candidate
                     Rendezvous Point. The value of -1 is used to indicate that the local
                     interface is not a Candidate RP interface."
         DEFVAL      { 0 }
         ::= { agentMulticastPIMSMCBSRInterfaceEntry 3 }


    agentMulticastPIMSMSSMTable OBJECT-TYPE
         SYNTAX      SEQUENCE OF AgentMulticastPIMSMSSMEntry
         MAX-ACCESS  not-accessible
         STATUS      obsolete
         DESCRIPTION
                     "Provides Per-Interface configuration of PIM-SM."
         ::= { agentMulticastPIMSMConfigGroup 6 }

    agentMulticastPIMSMSSMEntry OBJECT-TYPE
         SYNTAX      AgentMulticastPIMSMSSMEntry
         MAX-ACCESS  not-accessible
         STATUS      obsolete
         DESCRIPTION
                     "Allows configuration of parameters not provided in the
                      standard PIM-MIB."
         INDEX { agentMulticastPIMSMSSMGroupAddress, agentMulticastPIMSMSSMGroupMask}
         ::= { agentMulticastPIMSMSSMTable 1 }

     AgentMulticastPIMSMSSMEntry ::= SEQUENCE {
         agentMulticastPIMSMSSMGroupAddress
              IpAddress,
         agentMulticastPIMSMSSMGroupMask
              Unsigned32,
         agentMulticastPIMSMSSMStatus
              INTEGER
         }

    agentMulticastPIMSMSSMGroupAddress OBJECT-TYPE
         SYNTAX      IpAddress
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastPIMSMSSMEntry 1 }

    agentMulticastPIMSMSSMGroupMask OBJECT-TYPE
         SYNTAX      Unsigned32(0..32)
         MAX-ACCESS  read-create
         STATUS      obsolete
         DESCRIPTION
                     "The preference value for the local interface as a Candidate
                     Rendezvous Point. The value of -1 is used to indicate that the local
                     interface is not a Candidate RP interface."
         ::= { agentMulticastPIMSMSSMEntry 2 }

    agentMulticastPIMSMSSMStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastPIMSMSSMEntry 3 }

    agentMulticastPIMSMInterfaceTable OBJECT-TYPE
         SYNTAX      SEQUENCE OF AgentMulticastPIMSMInterfaceEntry
         MAX-ACCESS  not-accessible
         STATUS      obsolete
         DESCRIPTION
                     "Provides Per-Interface configuration of PIM-SM."
         ::= { agentMulticastPIMSMConfigGroup 7 }

    agentMulticastPIMSMInterfaceEntry OBJECT-TYPE
         SYNTAX      AgentMulticastPIMSMInterfaceEntry
         MAX-ACCESS  not-accessible
         STATUS      obsolete
         DESCRIPTION
                     "Allows configuration of parameters not provided in the
                      standard PIM-MIB."
         INDEX { agentMulticastPIMSMInterfaceIndex }
         ::= { agentMulticastPIMSMInterfaceTable 1 }

    AgentMulticastPIMSMInterfaceEntry ::= SEQUENCE {
         agentMulticastPIMSMInterfaceIndex
              Unsigned32,
         agentMulticastPIMSMInterfaceAdminMode
              INTEGER,
         agentMulticastPIMSMInterfaceHelloInterval
              Unsigned32,
         agentMulticastPIMSMInterfaceJoinPruneInterval
              Unsigned32,
         agentMulticastPIMSMInterfaceBsrBorder
              INTEGER,
         agentMulticastPIMSMInterfaceDrPriority
              Unsigned32,
         agentMulticastPIMSMInterfaceCBSRHashMaskLength
              Unsigned32,
         agentMulticastPIMSMInterfaceCRPPreference
              Integer32
         }

    agentMulticastPIMSMInterfaceIndex OBJECT-TYPE
         SYNTAX      Unsigned32
         MAX-ACCESS  not-accessible
         STATUS      obsolete
         DESCRIPTION
                     "Routing Interface associated with this PIM SM configuration entry."
         ::= { agentMulticastPIMSMInterfaceEntry 1 }

    agentMulticastPIMSMInterfaceAdminMode OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastPIMSMInterfaceEntry 2 }

    agentMulticastPIMSMInterfaceHelloInterval OBJECT-TYPE
         SYNTAX      Unsigned32 (0..18000)
         MAX-ACCESS  read-write
         STATUS      obsolete
         DESCRIPTION
                     "The BSR hash mask length to be advertised in bootstrap messages if
                     this interface is elected as the bootstrap router. This hash mask
                     length will be used in the hash algorith for selecting the RP for
                     a particular group."
         DEFVAL      { 30 }
         ::= { agentMulticastPIMSMInterfaceEntry 3 }

    agentMulticastPIMSMInterfaceJoinPruneInterval OBJECT-TYPE
         SYNTAX      Unsigned32 (0..18000)
         MAX-ACCESS  read-write
         STATUS      obsolete
         DESCRIPTION
                     "The preference value for the local interface as a Candidate
                     Rendezvous Point. The value of -1 is used to indicate that the local
                     interface is not a Candidate RP interface."
         DEFVAL      { 60 }
         ::= { agentMulticastPIMSMInterfaceEntry 4 }

    agentMulticastPIMSMInterfaceBsrBorder OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastPIMSMInterfaceEntry 5 }

    agentMulticastPIMSMInterfaceDrPriority OBJECT-TYPE
         SYNTAX      Unsigned32
         MAX-ACCESS  read-write
         STATUS      obsolete
         DESCRIPTION
                     "The preference value for the local interface as a Candidate
                     Rendezvous Point. The value of -1 is used to indicate that the local
                     interface is not a Candidate RP interface."
         DEFVAL      { 1 }
         ::= { agentMulticastPIMSMInterfaceEntry 6 }

    agentMulticastPIMSMInterfaceCBSRHashMaskLength OBJECT-TYPE
         SYNTAX      Unsigned32 (0..32)
         MAX-ACCESS  read-write
         STATUS      obsolete
         DESCRIPTION
                     "The BSR hash mask length to be advertised in bootstrap messages if
                     this interface is elected as the bootstrap router. This hash mask
                     length will be used in the hash algorith for selecting the RP for
                     a particular group."
         DEFVAL      { 30 }
         ::= { agentMulticastPIMSMInterfaceEntry 7 }

    agentMulticastPIMSMInterfaceCRPPreference OBJECT-TYPE
         SYNTAX      Integer32 (-1|0..255)
         MAX-ACCESS  read-write
         STATUS      obsolete
         DESCRIPTION
                     "The preference value for the local interface as a Candidate
                     Rendezvous Point. The value of -1 is used to indicate that the local
                     interface is not a Candidate RP interface."
         DEFVAL      { 0 }
         ::= { agentMulticastPIMSMInterfaceEntry 8 }


    agentMulticastPIMSMCandRPTable OBJECT-TYPE
         SYNTAX      SEQUENCE OF AgentMulticastPIMSMCandRPEntry
         MAX-ACCESS  not-accessible
         STATUS      obsolete
         DESCRIPTION
                     "Provides Per-Interface configuration of PIM-SM."
         ::= { agentMulticastPIMSMConfigGroup 8 }

    agentMulticastPIMSMCandRPEntry OBJECT-TYPE
         SYNTAX      AgentMulticastPIMSMCandRPEntry
         MAX-ACCESS  not-accessible
         STATUS      obsolete
         DESCRIPTION
                     "Allows configuration of parameters not provided in the
                      standard PIM-MIB."
         INDEX { agentMulticastPIMSMCandRPAddress, agentMulticastPIMSMCandRPGroupAddress, agentMulticastPIMSMCandRPGroupPrefixLength}
         ::= { agentMulticastPIMSMCandRPTable 1 }

     AgentMulticastPIMSMCandRPEntry ::= SEQUENCE {
         agentMulticastPIMSMCandRPAddress
              IpAddress,
         agentMulticastPIMSMCandRPGroupAddress
              IpAddress,
         agentMulticastPIMSMCandRPGroupPrefixLength
              Unsigned32,
         agentMulticastPIMSMCandRPStatus
              INTEGER
         }

    agentMulticastPIMSMCandRPAddress OBJECT-TYPE
         SYNTAX      IpAddress
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastPIMSMCandRPEntry 1 }

    agentMulticastPIMSMCandRPGroupAddress OBJECT-TYPE
         SYNTAX      IpAddress
         MAX-ACCESS  read-create
         STATUS      obsolete
         DESCRIPTION
                     "The preference value for the local interface as a Candidate
                     Rendezvous Point. The value of -1 is used to indicate that the local
                     interface is not a Candidate RP interface."
         ::= { agentMulticastPIMSMCandRPEntry 2 }

    agentMulticastPIMSMCandRPGroupPrefixLength OBJECT-TYPE
         SYNTAX      Unsigned32(0..32)
         MAX-ACCESS  read-create
         STATUS      obsolete
         DESCRIPTION
                     "The preference value for the local interface as a Candidate
                     Rendezvous Point. The value of -1 is used to indicate that the local
                     interface is not a Candidate RP interface."
         ::= { agentMulticastPIMSMCandRPEntry 3 }

    agentMulticastPIMSMCandRPStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastPIMSMCandRPEntry 4 }


    --**************************************************************************************
    agentMulticastPIMDMConfigGroup                      OBJECT IDENTIFIER ::= { multicast 4 }

    agentMulticastPIMDMAdminMode OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastPIMDMConfigGroup 1 }

    agentMulticastPIMDMInterfaceTable OBJECT-TYPE
         SYNTAX      SEQUENCE OF AgentMulticastPIMDMInterfaceEntry
         MAX-ACCESS  not-accessible
         STATUS      obsolete
         DESCRIPTION
                     "Provides Per-Interface configuration of PIM-DM."
         ::= { agentMulticastPIMDMConfigGroup 2 }

    agentMulticastPIMDMInterfaceEntry OBJECT-TYPE
         SYNTAX      AgentMulticastPIMDMInterfaceEntry
         MAX-ACCESS  not-accessible
         STATUS      obsolete
         DESCRIPTION
                     "Allows configuration of parameters not provided in the
                      standard PIM-MIB."
         INDEX { agentMulticastPIMDMInterfaceIndex }
         ::= { agentMulticastPIMDMInterfaceTable 1 }

    AgentMulticastPIMDMInterfaceEntry ::= SEQUENCE {
         agentMulticastPIMDMInterfaceIndex
              Unsigned32,
         agentMulticastPIMDMInterfaceMode
              INTEGER,
         agentMulticastPIMDMInterfaceHelloInterval
              Integer32
         }

    agentMulticastPIMDMInterfaceIndex OBJECT-TYPE
         SYNTAX      Unsigned32
         MAX-ACCESS  not-accessible
         STATUS      obsolete
         DESCRIPTION
                     "Routing Interface associated with this PIM DM configuration entry."
         ::= { agentMulticastPIMDMInterfaceEntry 1 }

    agentMulticastPIMDMInterfaceMode OBJECT-TYPE
         SYNTAX      INTEGER {
                     enable(1),
                     disable(2)
                  }
         MAX-ACCESS  read-write
         STATUS      obsolete
         DESCRIPTION
                     "This enables or disables PIM Dense Interface Mode on the system."
         ::= { agentMulticastPIMDMInterfaceEntry 2 }

    agentMulticastPIMDMInterfaceHelloInterval OBJECT-TYPE
         SYNTAX      Integer32 (0..18000)
         MAX-ACCESS  read-write
         STATUS      obsolete
         DESCRIPTION
                     "The hello interval of PIM Dense."
         DEFVAL      { 30 }
         ::= { agentMulticastPIMDMInterfaceEntry 3 }

    --**************************************************************************************
    agentMulticastRoutingConfigGroup                      OBJECT IDENTIFIER ::= { multicast 5 }

    agentMulticastRoutingAdminMode OBJECT-TYPE
         SYNTAX      INTEGER {
                     enable(1),
                     disable(2)
                  }
         MAX-ACCESS  read-write
         STATUS      obsolete
         DESCRIPTION
                     "This enables or disables Multicast Routing Mode on the system."
         DEFVAL { disable }
         ::= { agentMulticastRoutingConfigGroup 1 }

    --**************************************************************************************
    agentMulticastDVMRPConfigGroup                      OBJECT IDENTIFIER ::= { multicast 6 }

    agentMulticastDVMRPAdminMode OBJECT-TYPE
         SYNTAX      INTEGER {
                     enable(1),
                     disable(2)
                  }
         MAX-ACCESS  read-write
         STATUS      current
         DESCRIPTION
                     "This enables or disables DVMRP on the system."
         DEFVAL { disable }
         ::= { agentMulticastDVMRPConfigGroup 1 }

    agentMulticastDVMRPInterfaceTable OBJECT-TYPE
         SYNTAX      SEQUENCE OF AgentMulticastDVMRPInterfaceEntry
         MAX-ACCESS  not-accessible
         STATUS      obsolete
         DESCRIPTION
                     "Provides Per-Interface configuration of IGMP."
         ::= { agentMulticastDVMRPConfigGroup 2 }

    agentMulticastDVMRPInterfaceEntry OBJECT-TYPE
         SYNTAX      AgentMulticastDVMRPInterfaceEntry
         MAX-ACCESS  not-accessible
         STATUS      obsolete
         DESCRIPTION
                     "Information about a table entry."
         INDEX       { agentMulticastDVMRPInterfaceIfIndex }
         ::= { agentMulticastDVMRPInterfaceTable 1 }

    AgentMulticastDVMRPInterfaceEntry ::= SEQUENCE {
         agentMulticastDVMRPInterfaceIfIndex
              Integer32,
         agentMulticastDVMRPInterfaceAdminMode
              INTEGER,
         agentMulticastDVMRPInterfaceMetric
              Integer32,
         agentMulticastDVMRPInterfaceGenerationId
              Integer32
         }

    agentMulticastDVMRPInterfaceIfIndex OBJECT-TYPE
         SYNTAX      Integer32 (0..2147483647)
         MAX-ACCESS  read-only
         STATUS      obsolete
         DESCRIPTION
                     "Identifies the external interface number."
         ::= { agentMulticastDVMRPInterfaceEntry 1 }

    agentMulticastDVMRPInterfaceAdminMode OBJECT-TYPE
         SYNTAX      INTEGER {
                     enable(1),
                     disable(2)
                  }
         MAX-ACCESS  read-write
         STATUS      obsolete
         DESCRIPTION
                     "This enables or disables DVMRP on this interface."
         DEFVAL { disable }
         ::= { agentMulticastDVMRPInterfaceEntry 2 }

    agentMulticastDVMRPInterfaceMetric OBJECT-TYPE
         SYNTAX      Integer32 (1..31)
         MAX-ACCESS  read-write
         STATUS      obsolete
         DESCRIPTION
                     "DVMRP metric on this interface."
         DEFVAL { 1 }
         ::= { agentMulticastDVMRPInterfaceEntry 3 }

    agentMulticastDVMRPInterfaceGenerationId OBJECT-TYPE
         SYNTAX      Integer32
         MAX-ACCESS  read-only
         STATUS      obsolete
         DESCRIPTION
                     "DVMRP Generation Id on this interface. The value of -1 is used to indicate NULL."
         ::= { agentMulticastDVMRPInterfaceEntry 4 }

    --**************************************************************************************
    -- agentSnmpTrapFlagsConfigGroupMulticast
    --
    --**************************************************************************************
--    agentSnmpTrapFlagsConfigGroupMulticast       OBJECT IDENTIFIER ::= { multicast 7 }
--
--    agentSnmpDVMRPTrapFlag OBJECT-TYPE
--         SYNTAX      INTEGER {
--                     enable(1),
--                     disable(2)
--                  }
--         MAX-ACCESS  read-write
--         STATUS      obsolete
--         DESCRIPTION
--                     "This enables or disables DVMRP Traps on the system."
--         DEFVAL { disable }
--         ::= { agentSnmpTrapFlagsConfigGroupMulticast 1 }
--
--     OBJECT-TYPE
--         SYNTAX      INTEGER {
--                     enable(1),
--                     disable(2)
--                  }
--         MAX-ACCESS  read-write
--         STATUS      obsolete
--         DESCRIPTION
--                     "This enables or disables PIM Traps on the system."
--         DEFVAL { disable }
--         ::= { agentSnmpTrapFlagsConfigGroupMulticast 2 }

--**************************************************************************************
--  agentMulticastMLDConfigGroup
--
--**************************************************************************************
    agentMulticastMLDConfigGroup                      OBJECT IDENTIFIER ::= { multicast 8 }

    agentMulticastMLDAdminMode OBJECT-TYPE
         SYNTAX      INTEGER {
                     enable(1),
                     disable(2)
                  }
         MAX-ACCESS  read-write
         STATUS      current
         DESCRIPTION
                     "This enables or disables MLD on the system."
         DEFVAL { disable }
         ::= { agentMulticastMLDConfigGroup 1 }

    agentMulticastMLDInterfaceTable OBJECT-TYPE
         SYNTAX      SEQUENCE OF AgentMulticastMLDInterfaceEntry
         MAX-ACCESS  not-accessible
         STATUS      obsolete
         DESCRIPTION
                     "Provides Per-Interface configuration of MLD."
         ::= { agentMulticastMLDConfigGroup 2 }

    agentMulticastMLDInterfaceEntry OBJECT-TYPE
         SYNTAX      AgentMulticastMLDInterfaceEntry
         MAX-ACCESS  not-accessible
         STATUS      obsolete
         DESCRIPTION
                     "Information about a table entry."
         INDEX       { agentMulticastMLDInterfaceIfIndex }
         ::= { agentMulticastMLDInterfaceTable 1 }

    AgentMulticastMLDInterfaceEntry ::= SEQUENCE {
         agentMulticastMLDInterfaceIfIndex
              Integer32,
         agentMulticastMLDInterfaceAdminMode
              INTEGER
         }

    agentMulticastMLDInterfaceIfIndex OBJECT-TYPE
         SYNTAX      Integer32 (0..2147483647)
         MAX-ACCESS  read-only
         STATUS      obsolete
         DESCRIPTION
                     "Identifies the external interface number."
         ::= { agentMulticastMLDInterfaceEntry 1 }

    agentMulticastMLDInterfaceAdminMode OBJECT-TYPE
         SYNTAX      INTEGER {
                     enable(1),
                     disable(2)
                  }
         MAX-ACCESS  read-write
         STATUS      obsolete
         DESCRIPTION
                     "This enables or disables MLD on this interface."
         DEFVAL { disable }
         ::= { agentMulticastMLDInterfaceEntry 2 }

    agentMulticastMLDProxyInterfaceTable OBJECT-TYPE
         SYNTAX      SEQUENCE OF AgentMulticastMLDProxyInterfaceEntry
         MAX-ACCESS  not-accessible
         STATUS      obsolete
         DESCRIPTION
                     "Provides Per-Interface configuration of MLD."
         ::= { agentMulticastMLDConfigGroup 3 }

    agentMulticastMLDProxyInterfaceEntry OBJECT-TYPE
         SYNTAX      AgentMulticastMLDProxyInterfaceEntry
         MAX-ACCESS  not-accessible
         STATUS      obsolete
         DESCRIPTION
                     "Information about a table entry."
         INDEX       { agentMulticastMLDProxyInterfaceIfIndex }
         ::= { agentMulticastMLDProxyInterfaceTable 1 }

    AgentMulticastMLDProxyInterfaceEntry ::= SEQUENCE {
         agentMulticastMLDProxyInterfaceIfIndex
              Integer32,
         agentMulticastMLDProxyInterfaceAdminMode
              INTEGER,
         agentMulticastMLDProxyInterfaceInterval
              Integer32
         }

    agentMulticastMLDProxyInterfaceIfIndex OBJECT-TYPE
         SYNTAX      Integer32 (0..2147483647)
         MAX-ACCESS  read-only
         STATUS      obsolete
         DESCRIPTION
                     "Identifies the external interface number."
         ::= { agentMulticastMLDProxyInterfaceEntry 1 }

    agentMulticastMLDProxyInterfaceAdminMode OBJECT-TYPE
         SYNTAX      INTEGER {
                     enable(1),
                     disable(2)
                  }
         MAX-ACCESS  read-write
         STATUS      obsolete
         DESCRIPTION
                     "This enables or disables MLD proxy on this interface."
         DEFVAL { disable }
         ::= { agentMulticastMLDProxyInterfaceEntry 2 }

    agentMulticastMLDProxyInterfaceInterval OBJECT-TYPE
         SYNTAX      Integer32 (1..260)
         MAX-ACCESS  read-write
         STATUS      obsolete
         DESCRIPTION
                     "MLD proxy interval on this interface."
         DEFVAL { 1 }
         ::= { agentMulticastMLDProxyInterfaceEntry 3 }

--**************************************************************************************
--  agentMulticastIPv6PIMSMConfigGroup
--
--**************************************************************************************
    agentMulticastIPv6PIMSMConfigGroup                      OBJECT IDENTIFIER ::= { multicast 9 }

    agentMulticastIPv6PIMSMAdminMode OBJECT-TYPE
         SYNTAX      INTEGER {
                     enable(1),
                     disable(2)
                  }
         MAX-ACCESS  read-write
         STATUS      current
         DESCRIPTION
                     "This enables or disables PIM Sparse Mode on the system."
         DEFVAL { disable }
         ::= { agentMulticastIPv6PIMSMConfigGroup 1 }

    agentMulticastIPv6PIMSMDataThresholdRate OBJECT-TYPE
         SYNTAX      Integer32 (0..1)
         MAX-ACCESS  read-write
         STATUS      obsolete
         DESCRIPTION
                     "Specifies the minimum rate in Kbits/sec for the last hop router to initiate switching to the shortest path."
         DEFVAL { 0 }
         ::= { agentMulticastIPv6PIMSMConfigGroup 2 }

--    agentMulticastIPv6PIMSMRegThresholdRate OBJECT-TYPE
--         SYNTAX      Integer32 (0..2000)
--         MAX-ACCESS  read-write
--         STATUS      obsolete
--         DESCRIPTION
--                     "Specifies the minimum rate in Kbits/sec for the RP to switch to the shortest path."
--         DEFVAL { 50 }
--         ::= { agentMulticastIPv6PIMSMConfigGroup 3 }

    agentMulticastIPv6PIMSMStaticRPTable OBJECT-TYPE
         SYNTAX      SEQUENCE OF AgentMulticastIPv6PIMSMStaticRPEntry
         MAX-ACCESS  not-accessible
         STATUS      obsolete
         DESCRIPTION
                     "Provides Per-Interface configuration of PIM-SM."
         ::= { agentMulticastIPv6PIMSMConfigGroup 4 }

    agentMulticastIPv6PIMSMStaticRPEntry OBJECT-TYPE
         SYNTAX      AgentMulticastIPv6PIMSMStaticRPEntry
         MAX-ACCESS  not-accessible
         STATUS      obsolete
         DESCRIPTION
                     "Information about a table entry."
         INDEX       { agentMulticastIPv6PIMSMStaticRPIpAddr,
                       agentMulticastIPv6PIMSMStaticRPGroupIpAddr,
                       agentMulticastIPv6PIMSMStaticRPGroupIpPrefix }
         ::= { agentMulticastIPv6PIMSMStaticRPTable 1 }

    AgentMulticastIPv6PIMSMStaticRPEntry ::= SEQUENCE {
         agentMulticastIPv6PIMSMStaticRPIpAddr
              Ipv6Address,
         agentMulticastIPv6PIMSMStaticRPGroupIpAddr
              Ipv6Address,
         agentMulticastIPv6PIMSMStaticRPGroupIpPrefix
              Integer32,
         agentMulticastIPv6PIMSMStaticRPStatus
              RowStatus
         }

    agentMulticastIPv6PIMSMStaticRPIpAddr OBJECT-TYPE
         SYNTAX      Ipv6Address
         MAX-ACCESS  not-accessible
         STATUS      obsolete
         DESCRIPTION
                     "IPv6 Address of the RP."
         ::= { agentMulticastIPv6PIMSMStaticRPEntry 1 }

    agentMulticastIPv6PIMSMStaticRPGroupIpAddr OBJECT-TYPE
         SYNTAX      Ipv6Address
         MAX-ACCESS  not-accessible
         STATUS      obsolete
         DESCRIPTION
                     "Group IPv6 Address supported by the RP."
         ::= { agentMulticastIPv6PIMSMStaticRPEntry 2 }

    agentMulticastIPv6PIMSMStaticRPGroupIpPrefix OBJECT-TYPE
         SYNTAX      Integer32 (0..2147483647)
         MAX-ACCESS  not-accessible
         STATUS      obsolete
         DESCRIPTION
                     "Group mask for the group IP Address."
         ::= { agentMulticastIPv6PIMSMStaticRPEntry 3 }

    agentMulticastIPv6PIMSMStaticRPStatus OBJECT-TYPE
         SYNTAX      RowStatus
         MAX-ACCESS  read-create
         STATUS      obsolete
         DESCRIPTION
                     "Status of this entry in the Static RP Table.

                     Allowed values are:

                     active(1)      - This entry is active
                     destroy(6)     - Setting an entry to this value removes the
                                      entry from the table."
         ::= { agentMulticastIPv6PIMSMStaticRPEntry 4 }


    agentMulticastIPv6PIMSMCBSRInterfaceTable OBJECT-TYPE
         SYNTAX      SEQUENCE OF AgentMulticastIPv6PIMSMCBSRInterfaceEntry
         MAX-ACCESS  not-accessible
         STATUS      obsolete
         DESCRIPTION
                     "Provides Per-Interface configuration of PIM-SM."
         ::= { agentMulticastIPv6PIMSMConfigGroup 5 }

    agentMulticastIPv6PIMSMCBSRInterfaceEntry OBJECT-TYPE
         SYNTAX      AgentMulticastIPv6PIMSMCBSRInterfaceEntry
         MAX-ACCESS  not-accessible
         STATUS      obsolete
         DESCRIPTION
                     "Allows configuration of parameters not provided in the
                      standard PIM-MIB."
         INDEX { agentMulticastIPv6PIMSMCBSRInterfaceIndex }
         ::= { agentMulticastIPv6PIMSMCBSRInterfaceTable 1 }

    AgentMulticastIPv6PIMSMCBSRInterfaceEntry ::= SEQUENCE {
         agentMulticastIPv6PIMSMCBSRInterfaceIndex
              Unsigned32,
         agentMulticastIPv6PIMSMCBSRInterfaceHashMaskLength
              Unsigned32,
         agentMulticastIPv6PIMSMCBSRInterfacePriority
              Integer32
         }

    agentMulticastIPv6PIMSMCBSRInterfaceIndex OBJECT-TYPE
         SYNTAX      Unsigned32
         MAX-ACCESS  not-accessible
         STATUS      obsolete
         DESCRIPTION
                     "Routing Interface associated with this PIM SM configuration entry."
         ::= { agentMulticastIPv6PIMSMCBSRInterfaceEntry 1 }

    agentMulticastIPv6PIMSMCBSRInterfaceHashMaskLength OBJECT-TYPE
         SYNTAX      Unsigned32 (0..128)
         MAX-ACCESS  read-write
         STATUS      obsolete
         DESCRIPTION
                     "The BSR hash mask length to be advertised in bootstrap messages if
                     this interface is elected as the bootstrap router. This hash mask
                     length will be used in the hash algorith for selecting the RP for
                     a particular group."
         DEFVAL      { 30 }
         ::= { agentMulticastIPv6PIMSMCBSRInterfaceEntry 2 }

    agentMulticastIPv6PIMSMCBSRInterfacePriority OBJECT-TYPE
         SYNTAX      Integer32 (-1..255)
         MAX-ACCESS  read-write
         STATUS      obsolete
         DESCRIPTION
                     "The preference value for the local interface as a Candidate
                     Rendezvous Point. The value of -1 is used to indicate that the local
                     interface is not a Candidate RP interface."
         DEFVAL      { 0 }
         ::= { agentMulticastIPv6PIMSMCBSRInterfaceEntry 3 }

   agentMulticastIPv6PIMSMSSMTable OBJECT-TYPE
         SYNTAX      SEQUENCE OF AgentMulticastIPv6PIMSMSSMEntry
         MAX-ACCESS  not-accessible
         STATUS      obsolete
         DESCRIPTION
                     "Provides Per-Interface configuration of PIM-SM."
         ::= { agentMulticastIPv6PIMSMConfigGroup 6 }

    agentMulticastIPv6PIMSMSSMEntry OBJECT-TYPE
         SYNTAX      AgentMulticastIPv6PIMSMSSMEntry
         MAX-ACCESS  not-accessible
         STATUS      obsolete
         DESCRIPTION
                     "Allows configuration of parameters not provided in the
                      standard PIM-MIB."
         INDEX { agentMulticastIPv6PIMSMSSMGroupAddress, agentMulticastIPv6PIMSMSSMGroupMask}
         ::= { agentMulticastIPv6PIMSMSSMTable 1 }

     AgentMulticastIPv6PIMSMSSMEntry ::= SEQUENCE {
         agentMulticastIPv6PIMSMSSMGroupAddress
              Ipv6Address,
         agentMulticastIPv6PIMSMSSMGroupMask
              Unsigned32,
         agentMulticastIPv6PIMSMSSMStatus
              INTEGER
         }

    agentMulticastIPv6PIMSMSSMGroupAddress OBJECT-TYPE
         SYNTAX      Ipv6Address
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastIPv6PIMSMSSMEntry 1 }

    agentMulticastIPv6PIMSMSSMGroupMask OBJECT-TYPE
         SYNTAX      Unsigned32(0..128)
         MAX-ACCESS  read-create
         STATUS      obsolete
         DESCRIPTION
                     "The preference value for the local interface as a Candidate
                     Rendezvous Point. The value of -1 is used to indicate that the local
                     interface is not a Candidate RP interface."
         ::= { agentMulticastIPv6PIMSMSSMEntry 2 }

    agentMulticastIPv6PIMSMSSMStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastIPv6PIMSMSSMEntry 3 }

     agentMulticastIPv6PIMSMInterfaceTable OBJECT-TYPE
         SYNTAX      SEQUENCE OF AgentMulticastIPv6PIMSMInterfaceEntry
         MAX-ACCESS  not-accessible
         STATUS      obsolete
         DESCRIPTION
                     "Provides Per-Interface configuration of PIM-SM."
         ::= { agentMulticastIPv6PIMSMConfigGroup 7 }

    agentMulticastIPv6PIMSMInterfaceEntry OBJECT-TYPE
         SYNTAX      AgentMulticastIPv6PIMSMInterfaceEntry
         MAX-ACCESS  not-accessible
         STATUS      obsolete
         DESCRIPTION
                     "Allows configuration of parameters not provided in the
                      standard PIM-MIB."
         INDEX { agentMulticastIPv6PIMSMInterfaceIndex }
         ::= { agentMulticastIPv6PIMSMInterfaceTable 1 }

    AgentMulticastIPv6PIMSMInterfaceEntry ::= SEQUENCE {
         agentMulticastIPv6PIMSMInterfaceIndex
              Unsigned32,
         agentMulticastIPv6PIMSMInterfaceAdminMode
              INTEGER,
         agentMulticastIPv6PIMSMInterfaceHelloInterval
              Unsigned32,
         agentMulticastIPv6PIMSMInterfaceJoinPruneInterval
              Unsigned32,
         agentMulticastIPv6PIMSMInterfaceBsrBorder
              INTEGER,
         agentMulticastIPv6PIMSMInterfaceDrPriority
              Unsigned32
         }

    agentMulticastIPv6PIMSMInterfaceIndex OBJECT-TYPE
         SYNTAX      Unsigned32
         MAX-ACCESS  not-accessible
         STATUS      obsolete
         DESCRIPTION
                     "Routing Interface associated with this PIM SM configuration entry."
         ::= { agentMulticastIPv6PIMSMInterfaceEntry 1 }

    agentMulticastIPv6PIMSMInterfaceAdminMode OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastIPv6PIMSMInterfaceEntry 2 }

    agentMulticastIPv6PIMSMInterfaceHelloInterval OBJECT-TYPE
         SYNTAX      Unsigned32 (0..18000)
         MAX-ACCESS  read-write
         STATUS      obsolete
         DESCRIPTION
                     "The BSR hash mask length to be advertised in bootstrap messages if
                     this interface is elected as the bootstrap router. This hash mask
                     length will be used in the hash algorith for selecting the RP for
                     a particular group."
         DEFVAL      { 30 }
         ::= { agentMulticastIPv6PIMSMInterfaceEntry 3 }

    agentMulticastIPv6PIMSMInterfaceJoinPruneInterval OBJECT-TYPE
         SYNTAX      Unsigned32 (0..18000)
         MAX-ACCESS  read-write
         STATUS      obsolete
         DESCRIPTION
                     "The preference value for the local interface as a Candidate
                     Rendezvous Point. The value of -1 is used to indicate that the local
                     interface is not a Candidate RP interface."
         DEFVAL      { 60 }
         ::= { agentMulticastIPv6PIMSMInterfaceEntry 4 }

    agentMulticastIPv6PIMSMInterfaceBsrBorder OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastIPv6PIMSMInterfaceEntry 5 }

    agentMulticastIPv6PIMSMInterfaceDrPriority OBJECT-TYPE
         SYNTAX      Unsigned32
         MAX-ACCESS  read-write
         STATUS      obsolete
         DESCRIPTION
                     "The preference value for the local interface as a Candidate
                     Rendezvous Point. The value of -1 is used to indicate that the local
                     interface is not a Candidate RP interface."
         DEFVAL      { 1 }
         ::= { agentMulticastIPv6PIMSMInterfaceEntry 6 }

    agentMulticastIPv6PIMSMCandRPTable OBJECT-TYPE
         SYNTAX      SEQUENCE OF AgentMulticastIPv6PIMSMCandRPEntry
         MAX-ACCESS  not-accessible
         STATUS      obsolete
         DESCRIPTION
                     "Provides Per-Interface configuration of PIM-SM."
         ::= { agentMulticastIPv6PIMSMConfigGroup 8 }

    agentMulticastIPv6PIMSMCandRPEntry OBJECT-TYPE
         SYNTAX      AgentMulticastIPv6PIMSMCandRPEntry
         MAX-ACCESS  not-accessible
         STATUS      obsolete
         DESCRIPTION
                     "Allows configuration of parameters not provided in the
                      standard PIM-MIB."
         INDEX { agentMulticastIPv6PIMSMCandRPAddress, agentMulticastIPv6PIMSMCandRPGroupAddress, agentMulticastIPv6PIMSMCandRPGroupPrefixLength}
         ::= { agentMulticastIPv6PIMSMCandRPTable 1 }

     AgentMulticastIPv6PIMSMCandRPEntry ::= SEQUENCE {
         agentMulticastIPv6PIMSMCandRPAddress
              Ipv6Address,
         agentMulticastIPv6PIMSMCandRPGroupAddress
              Ipv6Address,
         agentMulticastIPv6PIMSMCandRPGroupPrefixLength
              Unsigned32,
         agentMulticastIPv6PIMSMCandRPStatus
              INTEGER
         }

    agentMulticastIPv6PIMSMCandRPAddress OBJECT-TYPE
         SYNTAX      Ipv6Address
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastIPv6PIMSMCandRPEntry 1 }

    agentMulticastIPv6PIMSMCandRPGroupAddress OBJECT-TYPE
         SYNTAX      Ipv6Address
         MAX-ACCESS  read-create
         STATUS      obsolete
         DESCRIPTION
                     "The preference value for the local interface as a Candidate
                     Rendezvous Point. The value of -1 is used to indicate that the local
                     interface is not a Candidate RP interface."
         ::= { agentMulticastIPv6PIMSMCandRPEntry 2 }

    agentMulticastIPv6PIMSMCandRPGroupPrefixLength OBJECT-TYPE
         SYNTAX      Unsigned32(0..32)
         MAX-ACCESS  read-create
         STATUS      obsolete
         DESCRIPTION
                     "The preference value for the local interface as a Candidate
                     Rendezvous Point. The value of -1 is used to indicate that the local
                     interface is not a Candidate RP interface."
         ::= { agentMulticastIPv6PIMSMCandRPEntry 3 }

    agentMulticastIPv6PIMSMCandRPStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastIPv6PIMSMCandRPEntry 4 }

--**************************************************************************************
--  agentMulticastIPv6PIMDMConfigGroup
--
--**************************************************************************************
    agentMulticastIPv6PIMDMConfigGroup                      OBJECT IDENTIFIER ::= { multicast 10 }

    agentMulticastIPv6PIMDMAdminMode OBJECT-TYPE
         SYNTAX      INTEGER {
                     enable(1),
                     disable(2)
                  }
         MAX-ACCESS  read-write
         STATUS      current
         DESCRIPTION
                     "This enables or disables PIM Dense Mode on the system."
         DEFVAL { disable }
         ::= { agentMulticastIPv6PIMDMConfigGroup 1 }

    agentMulticastIPv6PIMDMInterfaceTable OBJECT-TYPE
         SYNTAX      SEQUENCE OF AgentMulticastIPv6PIMDMInterfaceEntry
         MAX-ACCESS  not-accessible
         STATUS      obsolete
         DESCRIPTION
                     "Provides Per-Interface configuration of PIM-DM."
         ::= { agentMulticastIPv6PIMDMConfigGroup 2 }

    agentMulticastIPv6PIMDMInterfaceEntry OBJECT-TYPE
         SYNTAX      AgentMulticastIPv6PIMDMInterfaceEntry
         MAX-ACCESS  not-accessible
         STATUS      obsolete
         DESCRIPTION
                     "Allows configuration of parameters not provided in the
                      standard PIM-MIB."
         INDEX { agentMulticastIPv6PIMDMInterfaceIndex }
         ::= { agentMulticastIPv6PIMDMInterfaceTable 1 }

    AgentMulticastIPv6PIMDMInterfaceEntry ::= SEQUENCE {
         agentMulticastIPv6PIMDMInterfaceIndex
              Unsigned32,
         agentMulticastIPv6PIMDMInterfaceMode
              INTEGER,
         agentMulticastIPv6PIMDMInterfaceHelloInterval
              Integer32
         }

    agentMulticastIPv6PIMDMInterfaceIndex OBJECT-TYPE
         SYNTAX      Unsigned32
         MAX-ACCESS  not-accessible
         STATUS      obsolete
         DESCRIPTION
                     "Routing Interface associated with this PIM DM configuration entry."
         ::= { agentMulticastIPv6PIMDMInterfaceEntry 1 }

    agentMulticastIPv6PIMDMInterfaceMode OBJECT-TYPE
         SYNTAX      INTEGER {
                     enable(1),
                     disable(2)
                  }
         MAX-ACCESS  read-write
         STATUS      obsolete
         DESCRIPTION
                     "This enables or disables PIM Dense Interface Mode on the system."
         ::= { agentMulticastIPv6PIMDMInterfaceEntry 2 }

    agentMulticastIPv6PIMDMInterfaceHelloInterval OBJECT-TYPE
         SYNTAX      Integer32 (0..18000)
         MAX-ACCESS  read-write
         STATUS      obsolete
         DESCRIPTION
                     "The hello interval of PIM Dense."
         DEFVAL      { 30 }
         ::= { agentMulticastIPv6PIMDMInterfaceEntry 3 }



    agentMulticastAdminBoundaryConfigGroup                      OBJECT IDENTIFIER ::= { multicast 11 }

    agentMulticastAdminBoundaryTable OBJECT-TYPE
         SYNTAX      SEQUENCE OF AgentMulticastAdminBoundaryEntry
         MAX-ACCESS  not-accessible
         STATUS      obsolete
         DESCRIPTION
                     "Provides Per-Interface configuration of PIM-DM."
         ::= { agentMulticastAdminBoundaryConfigGroup 1}

    agentMulticastAdminBoundaryEntry OBJECT-TYPE
         SYNTAX      AgentMulticastAdminBoundaryEntry
         MAX-ACCESS  not-accessible
         STATUS      obsolete
         DESCRIPTION
                     "Allows configuration of parameters not provided in the
                      standard PIM-MIB."
         INDEX { agentMulticastAdminBoundaryIndex, agentMulticastAdminBoundaryGroupAddress, agentMulticastAdminBoundaryGroupMask }
         ::= { agentMulticastAdminBoundaryTable 1 }

     AgentMulticastAdminBoundaryEntry ::= SEQUENCE {
         agentMulticastAdminBoundaryIndex
              Unsigned32,
         agentMulticastAdminBoundaryGroupAddress
              IpAddress,
         agentMulticastAdminBoundaryGroupMask
              IpAddress,
         agentMulticastAdminBoundaryStatus
              INTEGER
         }

    agentMulticastAdminBoundaryIndex OBJECT-TYPE
         SYNTAX      Unsigned32
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastAdminBoundaryEntry 1 }

    agentMulticastAdminBoundaryGroupAddress OBJECT-TYPE
         SYNTAX      IpAddress
         MAX-ACCESS  read-create
         STATUS      obsolete
         DESCRIPTION
                     "The preference value for the local interface as a Candidate
                     Rendezvous Point. The value of -1 is used to indicate that the local
                     interface is not a Candidate RP interface."
         ::= { agentMulticastAdminBoundaryEntry 2 }

    agentMulticastAdminBoundaryGroupMask OBJECT-TYPE
         SYNTAX      IpAddress
         MAX-ACCESS  read-create
         STATUS      obsolete
         DESCRIPTION
                     "The preference value for the local interface as a Candidate
                     Rendezvous Point. The value of -1 is used to indicate that the local
                     interface is not a Candidate RP interface."
         ::= { agentMulticastAdminBoundaryEntry 3 }

    agentMulticastAdminBoundaryStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastAdminBoundaryEntry 4 }

    agentMulticastStaticRouteConfigGroup                      OBJECT IDENTIFIER ::= { multicast 12 }

    agentMulticastStaticRouteTable OBJECT-TYPE
         SYNTAX      SEQUENCE OF AgentMulticastStaticRouteEntry
         MAX-ACCESS  not-accessible
         STATUS      obsolete
         DESCRIPTION
                     "Provides Per-Interface configuration of PIM-DM."
         ::= { agentMulticastStaticRouteConfigGroup 1}

    agentMulticastStaticRouteEntry OBJECT-TYPE
         SYNTAX      AgentMulticastStaticRouteEntry
         MAX-ACCESS  not-accessible
         STATUS      obsolete
         DESCRIPTION
                     "Allows configuration of parameters not provided in the
                      standard PIM-MIB."
         INDEX { agentMulticastStaticRouteSourceIP }
         ::= { agentMulticastStaticRouteTable 1 }

     AgentMulticastStaticRouteEntry ::= SEQUENCE {
         agentMulticastStaticRouteSourceIP
              IpAddress,
         agentMulticastStaticRouteSourceMask
              IpAddress,
         agentMulticastStaticRouteRPFNeighbor
              IpAddress,
         agentMulticastStaticRouteMetric
              Unsigned32,
         agentMulticastStaticRouteInterface
              Unsigned32,
         agentMulticastStaticRouteStatus
              INTEGER
         }

    agentMulticastStaticRouteSourceIP OBJECT-TYPE
         SYNTAX      IpAddress
         MAX-ACCESS  read-create
         STATUS      obsolete
         DESCRIPTION
                     "The BSR hash mask length to be advertised in bootstrap messages if
                     this interface is elected as the bootstrap router. This hash mask
                     length will be used in the hash algorith for selecting the RP for
                     a particular group."
         ::= { agentMulticastStaticRouteEntry 1 }

    agentMulticastStaticRouteSourceMask OBJECT-TYPE
         SYNTAX      IpAddress
         MAX-ACCESS  read-create
         STATUS      obsolete
         DESCRIPTION
                     "The preference value for the local interface as a Candidate
                     Rendezvous Point. The value of -1 is used to indicate that the local
                     interface is not a Candidate RP interface."
         ::= { agentMulticastStaticRouteEntry 2 }

    agentMulticastStaticRouteRPFNeighbor OBJECT-TYPE
         SYNTAX      IpAddress
         MAX-ACCESS  read-create
         STATUS      obsolete
         DESCRIPTION
                     "The preference value for the local interface as a Candidate
                     Rendezvous Point. The value of -1 is used to indicate that the local
                     interface is not a Candidate RP interface."
         ::= { agentMulticastStaticRouteEntry 3 }

    agentMulticastStaticRouteMetric OBJECT-TYPE
         SYNTAX      Unsigned32 (0..255)
         MAX-ACCESS  read-create
         STATUS      obsolete
         DESCRIPTION
                     "The preference value for the local interface as a Candidate
                     Rendezvous Point. The value of -1 is used to indicate that the local
                     interface is not a Candidate RP interface."
         ::= { agentMulticastStaticRouteEntry 4 }

    agentMulticastStaticRouteInterface OBJECT-TYPE
         SYNTAX      Unsigned32
         MAX-ACCESS  read-create
         STATUS      obsolete
         DESCRIPTION
                     "The preference value for the local interface as a Candidate
                     Rendezvous Point. The value of -1 is used to indicate that the local
                     interface is not a Candidate RP interface."
         ::= { agentMulticastStaticRouteEntry 5 }

    agentMulticastStaticRouteStatus OBJECT-TYPE
         SYNTAX      INTEGER {
                     active(1),
                     create(4),
                     destory(6)
                     }
         MAX-ACCESS  read-create
         STATUS      obsolete
         DESCRIPTION
                     "The preference value for the local interface as a Candidate
                     Rendezvous Point. The value of -1 is used to indicate that the local
                     interface is not a Candidate RP interface."
         ::= { agentMulticastStaticRouteEntry 6 }

    --**************************************************************************************
    -- The Static Multicast Route Table
    --
    --**************************************************************************************
    agentIpStaticMRouteTable OBJECT-TYPE
         SYNTAX      SEQUENCE OF AgentIpStaticMRouteEntry
         MAX-ACCESS  not-accessible
         STATUS      current
         DESCRIPTION
                     "The table listing the Static Multicast Route Entries."
         ::= { multicast 13 }

    agentIpStaticMRouteEntry OBJECT-TYPE
         SYNTAX      AgentIpStaticMRouteEntry
         MAX-ACCESS  not-accessible
         STATUS      current
         DESCRIPTION
                     "Information about a table entry."
         INDEX       { agentIpStaticMRouteSrcAddressType, agentIpStaticMRouteSrcIpAddr, agentIpStaticMRouteSrcNetMask}
         ::= { agentIpStaticMRouteTable 1 }

    AgentIpStaticMRouteEntry ::= SEQUENCE {
         agentIpStaticMRouteSrcAddressType   InetAddressType,
         agentIpStaticMRouteSrcIpAddr        InetAddress,
         agentIpStaticMRouteSrcNetMask       Integer32,
         agentIpStaticMRouteRpfIpAddr        InetAddress,
         agentIpStaticMRouteIfIndex          InterfaceIndex,
         agentIpStaticMRoutePreference       Integer32,
         agentIpStaticMRouteStatus           RowStatus
         }

    agentIpStaticMRouteSrcAddressType OBJECT-TYPE
         SYNTAX      InetAddressType
         MAX-ACCESS  not-accessible
         STATUS      current
         DESCRIPTION
                     "The address type of this Multicast data source."
         ::= { agentIpStaticMRouteEntry 1 }

    agentIpStaticMRouteSrcIpAddr OBJECT-TYPE
         SYNTAX      InetAddress
         MAX-ACCESS  not-accessible
         STATUS      current
         DESCRIPTION
                     "The address of the Multicast data source."
         ::= { agentIpStaticMRouteEntry 2 }

    agentIpStaticMRouteSrcNetMask OBJECT-TYPE
         SYNTAX      Integer32(1..128)
         MAX-ACCESS  not-accessible
         STATUS      current

         DESCRIPTION
                     "The network mask for the IP address of the Multicast data source."
         ::= { agentIpStaticMRouteEntry 3 }

    agentIpStaticMRouteRpfIpAddr OBJECT-TYPE
         SYNTAX      InetAddress
         MAX-ACCESS  read-create
         STATUS      current
         DESCRIPTION
                     "The RPF Address."
         ::= { agentIpStaticMRouteEntry 4 }

    agentIpStaticMRouteIfIndex OBJECT-TYPE
         SYNTAX      InterfaceIndex
         MAX-ACCESS  read-create
         STATUS      current
         DESCRIPTION
                     "The interface index is valid only for IPv6 and only if RPF address is link-local."
         ::= { agentIpStaticMRouteEntry 5 }

    agentIpStaticMRoutePreference OBJECT-TYPE
         SYNTAX      Integer32(1..255)
         MAX-ACCESS  read-create
         STATUS      current
         DESCRIPTION
                     "The preference of this route entry."
         ::= { agentIpStaticMRouteEntry 6 }

    agentIpStaticMRouteStatus OBJECT-TYPE
         SYNTAX      RowStatus
         MAX-ACCESS  read-create
         STATUS      current
         DESCRIPTION
                     "The preference of this route entry."
         ::= { agentIpStaticMRouteEntry 7 }

END
