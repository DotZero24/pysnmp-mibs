ENTERASYS-FILE-MANAGEMENT-MIB DEFINITIONS ::= BEGIN

IMPORTS
    MODULE-IDENTITY, OBJECT-TYPE, Integer32, Unsigned32, Gauge32,
        Counter32
        FROM SNMPv2-SMI
    DateAndTime, DisplayString, StorageType, RowStatus
        FROM SNMPv2-TC
    MODULE-COMPLIANCE, OBJECT-GROUP
        FROM SNMPv2-CONF
    SnmpAdminString
        FROM SNMP-FRAMEWORK-MIB
    hrFSIndex
        FROM HOST-RESOURCES-MIB
    etsysModules
        FROM ENTERASYS-MIB-NAMES;

etsysFileManagementMIB MODULE-IDENTITY
    LAST-UPDATED "200112031954Z"  -- Mon Dec  3 19:54 GMT 2001
    ORGANIZATION "Enterasys Networks"
    CONTACT-INFO
    "Postal: Enterasys Networks
             35 Industrial Way, P.O. Box 5005
             Rochester, NH 03867-0505

     Phone:  +1 603 332 9400
     E-mail: support@enterasys.com
     WWW:    http://www.enterasys.com"

    DESCRIPTION
        "This MIB module defines a portion of the SNMP enterprise
         MIBs under the Enterasys enterprise OID pertaining to the
         transferring and management of files for Enterasys products."

    REVISION "200112031954Z"  -- Mon Dec  3 19:54 GMT 2001
    DESCRIPTION
        "The initial version of this MIB module."

    ::= { etsysModules 15 }


-- -------------------------------------------------------------
-- The groups defined within this MIB module:
-- -------------------------------------------------------------


etsysFileTransfer               OBJECT IDENTIFIER
                         ::= { etsysFileManagementMIB 1 }

etsysFileListing                OBJECT IDENTIFIER
                         ::= { etsysFileManagementMIB 2 }

etsysFileOperation              OBJECT IDENTIFIER
                         ::= { etsysFileManagementMIB 3 }

etsysFileConformance            OBJECT IDENTIFIER
                         ::= { etsysFileManagementMIB 4 }


-- -------------------------------------------------------------
-- File Transfer Group
-- -------------------------------------------------------------


etsysFileTransferRequestLimit OBJECT-TYPE
    SYNTAX      Unsigned32 (0..4294967295)
    MAX-ACCESS  read-only
    STATUS      current
    DESCRIPTION
        "The maximum number of file transfer requests this entity
         can hold in the etsysFileTransferRequestTable.  A value
         of 0 indicates no configured limit."
    ::= { etsysFileTransfer 1 }

etsysFileTransferRequestsCurrent OBJECT-TYPE
    SYNTAX      Gauge32
    MAX-ACCESS  read-only
    STATUS      current
    DESCRIPTION
        "The number of file transfer requests currently in the
         etsysFileTransferRequestTable."
    ::= { etsysFileTransfer 2 }

etsysFileTransferRequestsCompleted OBJECT-TYPE
    SYNTAX      Counter32
    MAX-ACCESS  read-only
    STATUS      current
    DESCRIPTION
        "The number of file transfer requests that have completed
         successfully or otherwise.  This object SHOULD be stored
         in persistent memory."
    ::= { etsysFileTransfer 3 }

etsysFileTransferRequestSupportedURLs OBJECT-TYPE
    SYNTAX      BITS {
       etsysFileTransferFtp(0),
       etsysFileTransferRcp(1),
       etsysFileTransferHttp(2),
       etsysFileTransferTftp(3),
       etsysFileTransferFile(4)
    }
    MAX-ACCESS  read-only
    STATUS      current
    DESCRIPTION
        "The URLs that this entity supports for transferring files.
         These define the transfer protocols and local file types.
         In the case that any URL is supported only as a source or
         destination file then an appropriate SNMP set failure should
         occur when attempting to use that URL in an unsupported
         manner.

         etsysFileTransferFtp -  As per rfc1738

            ftp://<user>:<password>@<host>:<port>/<url-path>

            url-path: <cwd1>/<cwd2>/.../<cwdN>/<name>;type=<typecode>

            user defaults to anonymous, password to snmp@<domain-name>,
            port to 21, and type to ASCII.  binary and image are both
            valid types which have the same meaning.  domain-name would
            be the IP address or domain name of the managed entity.

         etsysFileTransferRcp -

            rcp://<user>@<host>:<port>/<cwd1>/<cwd2>/.../<cwdN>/<name>

            port defaults to 514.

         etsysFileTransferHttp - As per rfc1738

            http://<host>:<port>/<path>?<searchpart>

            port defaults to 80.

         etsysFileTransferTftp -

            tftp://<host>:<port>/<cwd1>/<cwd2>/.../<cwdN>/<name>

            port defaults to 69.

         etsysFileTransferFile - As per rfc1738

            file://<host>/<path>

            host can only be specified as localhost or the empty
            string.  This will only be used to specify a file on
            the managed entity.  This indicates that the managed
            entity supports some form of a file system."

    REFERENCE
        "RFC 1738 - Uniform Resource Locators (URL),
         RFC 2396 - Uniform Resource Identifiers (URI): Generic Syntax"

    ::= { etsysFileTransfer 4 }

etsysFileTransferRequestNextAvailableIndex OBJECT-TYPE
    SYNTAX      Unsigned32 (0..4294967295)
    MAX-ACCESS  read-only
    STATUS      current
    DESCRIPTION
        "This object indicates the numerically lowest available
         index within this entity, which may be used for the
         value of etsysFileTransferRequestIndex in the creation
         of a new entry in the etsysFileTransferRequestTable.

         An index is considered available if the index value
         falls within the range of 1 to etsysFileTransferRequestLimit
         and is not being used to index an existing entry in the
         etsysFileTransferRequestTable contained within this entity.

         A value of zero indicates that all of the entries in the
         etsysFileTransferRequestTable are currently in use.

         This value should only be considered a guideline for
         management creation of etsysFileTransferRequestTable
         entries, there is no requirement on management to create
         entries based upon this index value."
    ::= { etsysFileTransfer 5 }

-- -------------------------------------------------------------
-- File Transfer Request Table
-- -------------------------------------------------------------


etsysFileTransferRequestTable OBJECT-TYPE
    SYNTAX      SEQUENCE OF EtsysFileTransferRequestEntry
    MAX-ACCESS  not-accessible
    STATUS      current
    DESCRIPTION
        "A table of file transfer requests."
    ::= { etsysFileTransfer 6 }

etsysFileTransferRequestEntry OBJECT-TYPE
    SYNTAX      EtsysFileTransferRequestEntry
    MAX-ACCESS  not-accessible
    STATUS      current
    DESCRIPTION
        "An entry describing a particular file transfer request."
    INDEX { etsysFileTransferRequestIndex }
    ::= { etsysFileTransferRequestTable 1 }

EtsysFileTransferRequestEntry ::=
    SEQUENCE {
        etsysFileTransferRequestIndex
            Unsigned32,
        etsysFileTransferRequestSource
            DisplayString,
        etsysFileTransferRequestDestination
            DisplayString,
        etsysFileTransferRequestOperStatus
            INTEGER,
        etsysFileTransferRequestEnqueuedTime
            DateAndTime,
        etsysFileTransferRequestCompletionTime
            DateAndTime,
        etsysFileTransferRequestBytesTransferred
            Integer32,
        etsysFileTransferRequestErrorDescription
            SnmpAdminString,
        etsysFileTransferRequestStorageType
            StorageType,
        etsysFileTransferRequestRowStatus
            RowStatus
    }

etsysFileTransferRequestIndex       OBJECT-TYPE
    SYNTAX      Unsigned32 (1..4294967295)
    MAX-ACCESS  not-accessible
    STATUS      current
    DESCRIPTION
        "An arbitrary index for this file transfer request."
    ::= { etsysFileTransferRequestEntry 1 }

etsysFileTransferRequestSource       OBJECT-TYPE
    SYNTAX      DisplayString
    MAX-ACCESS  read-create
    STATUS      current
    DESCRIPTION
        "URL of the source file.  Any password information MUST
         NOT be returned on a read.  If a managed entity supports
         some form of a file system and the file URL from rfc1738
         then a file copy can be performed by using the file URL
         for both the source and destination.  Activating the row
         with the URL specifying the same file in the source and
         destination SHOULD cause the file transfer to fail."
    ::= { etsysFileTransferRequestEntry 2 }

etsysFileTransferRequestDestination  OBJECT-TYPE
    SYNTAX      DisplayString
    MAX-ACCESS  read-create
    STATUS      current
    DESCRIPTION
        "URL of the destination file.  Any password information MUST
         NOT be returned on a read.  Two transfer request entries
         SHOULD NOT be allowed to specify the same destination URL.
         To initiate a second transfer to the same destination URL
         the original entry must be reused or destroyed.  Any errors
         with the type or format of these URLs SHOULD be reported in
         the etsysFileTransferRequestErrorDescription object when
         the row is activated."
    ::= { etsysFileTransferRequestEntry 3 }

etsysFileTransferRequestOperStatus OBJECT-TYPE
    SYNTAX      INTEGER {
        inactive(1),
        pending(2),
        running(3),
        success(4),
        failure(5)
    }
    MAX-ACCESS  read-only
    STATUS      current
    DESCRIPTION
        "The operational state of the file transfer.

         inactive - Indicates that the RowStatus of this conceptual
                    row is not in the 'active' state.

         pending  - Indicates that the transfer described by this
                    row is ready to run and waiting in a queue.

         running  - Indicates that the transfer described by this
                    row is running.

         success  - Indicates that the transfer described by this
                    row has successfully run to completion.

         failure  - Indicates that the transfer described by this
                    row has failed to run to completion."
    ::= { etsysFileTransferRequestEntry 4 }

etsysFileTransferRequestEnqueuedTime OBJECT-TYPE
    SYNTAX      DateAndTime
    MAX-ACCESS  read-only
    STATUS      current
    DESCRIPTION
        "The date and time, in device local time, when this transfer
         request was last enqueued for execution.
         The value '0000000000000000'H is returned if this table
         entry has not yet been queued."
    DEFVAL { '0000000000000000'H }
    ::= { etsysFileTransferRequestEntry 5 }

etsysFileTransferRequestCompletionTime OBJECT-TYPE
    SYNTAX      DateAndTime
    MAX-ACCESS  read-only
    STATUS      current
    DESCRIPTION
        "The date and time, in device local time, when this transfer
         request was last completed.  It SHOULD be reset to the
         default value when the RowStatus of this conceptual row
         is set to active.  The value '0000000000000000'H is returned
         if this table entry has not yet run to completion."
    DEFVAL { '0000000000000000'H }
    ::= { etsysFileTransferRequestEntry 6 }

etsysFileTransferRequestBytesTransferred OBJECT-TYPE
    SYNTAX      Integer32 (-1..2147483647)
    MAX-ACCESS  read-only
    STATUS      current
    DESCRIPTION
        "The number of bytes currently transferred.  A value of -1
         indicates that this feature is not supported for the
         protocol currently selected.  This value is reset to its
         initial state when the etsysFileTransferRequestRowStatus
         object is set to the active state."
    DEFVAL { 0 }
    ::= { etsysFileTransferRequestEntry 7 }

etsysFileTransferRequestErrorDescription OBJECT-TYPE
    SYNTAX      SnmpAdminString
    MAX-ACCESS  read-only
    STATUS      current
    DESCRIPTION
           "This object contains a descriptive error message if the
            requested transfer failed.  Implementations must reset
            the error message to a zero-length string when the
            etsysFileTransferRequestRowStatus leaf is set to the
            active state."
    DEFVAL { ''H }
    ::= { etsysFileTransferRequestEntry 8 }

etsysFileTransferRequestStorageType OBJECT-TYPE
    SYNTAX      StorageType
    MAX-ACCESS  read-only
    STATUS      current
    DESCRIPTION
           "Allows applications within the managed entity to define
            nonVolatile or readOnly rows as required."
    DEFVAL { volatile }
    ::= { etsysFileTransferRequestEntry 9 }

etsysFileTransferRequestRowStatus OBJECT-TYPE
    SYNTAX      RowStatus
    MAX-ACCESS  read-create
    STATUS      current
    DESCRIPTION
           "A control that allows entries to be added, activated,
            deactivated, and removed from this table.

            When the value of this object is 'active' none of the
            other objects in this conceptual row can be modified.

            Setting this object to the 'active' state from the
            'notInService' state will cause the requested file
            transfer to be initiated or queued.

            Once the requested file transfer has completed,
            successfully or otherwise, this leaf will be set to
            the 'notInService' state by the managed entity.

            Setting this object to any other valid state from the
            'active' state will interrupt the file transfer request.

            Setting this object to the 'active' state from the
            'active' state will not have any affect.

            Conceptual rows that have been in the 'notInService'
            state for more than a device specific time period
            MAY be destroyed by the managed entity."
    ::= { etsysFileTransferRequestEntry 10 }


-- -------------------------------------------------------------
-- File Listing Table
-- -------------------------------------------------------------


etsysFileListingTable OBJECT-TYPE
    SYNTAX      SEQUENCE OF EtsysFileListingEntry
    MAX-ACCESS  not-accessible
    STATUS      current
    DESCRIPTION
        "A table of user files currently stored in a particular
         file system on this entity.  If the Host Resources MIB
         is not supported and there is only one file system use
         the value of one for the hrFSIndex.  This table should
         represent a minimal set of information that is commonly
         available on most file systems."
    ::= { etsysFileListing 1 }

etsysFileListingEntry OBJECT-TYPE
    SYNTAX      EtsysFileListingEntry
    MAX-ACCESS  not-accessible
    STATUS      current
    DESCRIPTION
        "An entry describing a particular file currently stored
         on this entity."
    INDEX { hrFSIndex, etsysFileListingIndex }
    ::= { etsysFileListingTable 1 }

EtsysFileListingEntry ::=
    SEQUENCE {
        etsysFileListingIndex
            Unsigned32,
        etsysFileListingFileName
            DisplayString,
        etsysFileListingFileSize
            Unsigned32,
        etsysFileListingFileType
            INTEGER,
        etsysFileListingFileDate
            DateAndTime,
        etsysFileListingFileOrigin
            DisplayString
    }

etsysFileListingIndex OBJECT-TYPE
    SYNTAX      Unsigned32
    MAX-ACCESS  not-accessible
    STATUS      current
    DESCRIPTION
        "The locally arbitrary, but unique identifier associated
         with this file entry."
    ::= { etsysFileListingEntry 1 }

etsysFileListingFileName OBJECT-TYPE
    SYNTAX      DisplayString
    MAX-ACCESS  read-only
    STATUS      current
    DESCRIPTION
        "The fully qualified name of the file."
    ::= { etsysFileListingEntry 2 }

etsysFileListingFileSize OBJECT-TYPE
    SYNTAX      Unsigned32 (0..4294967295)
    MAX-ACCESS  read-only
    STATUS      current
    DESCRIPTION
        "The size in bytes of this file."
    ::= { etsysFileListingEntry 3 }

etsysFileListingFileType OBJECT-TYPE
    SYNTAX      INTEGER {
        unsupported(1),
        directory(2),
        ordinary-file(3),
        symbolic-link(4)
    }
    MAX-ACCESS  read-only
    STATUS      current
    DESCRIPTION
        "The type of file that this entry represents."
    DEFVAL { unsupported }
    ::= { etsysFileListingEntry 4 }

etsysFileListingFileDate OBJECT-TYPE
    SYNTAX      DateAndTime
    MAX-ACCESS  read-only
    STATUS      current
    DESCRIPTION
        "The time and date that this file was last modified, if this
         information is unavailable return '0000000000000000'H."
    DEFVAL { '0000000000000000'H }
    ::= { etsysFileListingEntry 5 }

etsysFileListingFileOrigin OBJECT-TYPE
    SYNTAX      DisplayString
    MAX-ACCESS  read-only
    STATUS      current
    DESCRIPTION
        "The source URL of this file, if it was created by a transfer,
         or an application name, if it was created by an application.
         If this information is unavailable return the null string.
         Since most of the user files on our devices are, or would be,
         created by file transfers or applications this would be an
         interesting but otherwise uncommon piece of information."
    DEFVAL { ''H }
    ::= { etsysFileListingEntry 6 }


-- -------------------------------------------------------------
-- File Operation Group
-- -------------------------------------------------------------

etsysFileOperationLimit OBJECT-TYPE
    SYNTAX      Unsigned32 (0..4294967295)
    MAX-ACCESS  read-only
    STATUS      current
    DESCRIPTION
        "The maximum number of requests this entity can hold in
         the etsysFileOperationTable.  A value of 0 indicates no
         configured limit."
    ::= { etsysFileOperation 1 }

etsysFileOperationsCurrent OBJECT-TYPE
    SYNTAX      Gauge32
    MAX-ACCESS  read-only
    STATUS      current
    DESCRIPTION
        "The number of requests currently in the
         etsysFileOperationTable."
    ::= { etsysFileOperation 2 }

etsysFileOperationsCompleted OBJECT-TYPE
    SYNTAX      Counter32
    MAX-ACCESS  read-only
    STATUS      current
    DESCRIPTION
        "The number of file operations that have completed
         successfully or otherwise.  This object SHOULD be
         stored in persistent memory."
    ::= { etsysFileOperation 3 }

etsysFileOperationNextAvailableIndex OBJECT-TYPE
    SYNTAX      Unsigned32 (0..4294967295)
    MAX-ACCESS  read-only
    STATUS      current
    DESCRIPTION
        "This object indicates the numerically lowest available
         index within this entity, which may be used for the
         value of etsysFileOperationIndex in the creation
         of a new entry in the etsysFileOperationTable.

         An index is considered available if the index value falls
         within the range of 1 to etsysFileOperationLimit and is
         not being used to index an existing entry in the
         etsysFileOperationTable contained within this entity.

         A value of zero indicates that all of the entries in the
         etsysFileOperationTable are currently in use.

         This value should only be considered a guideline for
         management creation of etsysFileOperationTable, there is
         no requirement on management to create entries based upon
         this index value."
    ::= { etsysFileOperation 4 }


-- -------------------------------------------------------------
-- File Operation Table
-- -------------------------------------------------------------


etsysFileOperationTable OBJECT-TYPE
    SYNTAX      SEQUENCE OF EtsysFileOperationEntry
    MAX-ACCESS  not-accessible
    STATUS      current
    DESCRIPTION
        "Entries can be created in this table to rename and delete
         files on this entity."
    ::= { etsysFileOperation 5 }

etsysFileOperationEntry OBJECT-TYPE
    SYNTAX      EtsysFileOperationEntry
    MAX-ACCESS  not-accessible
    STATUS      current
    DESCRIPTION
        "An entry describing an operation to be performed on the
         named file on this entity."
    INDEX { etsysFileOperationIndex }
    ::= { etsysFileOperationTable 1 }

EtsysFileOperationEntry ::=
    SEQUENCE {
        etsysFileOperationIndex
            Unsigned32,
        etsysFileOperationType
            INTEGER,
        etsysFileOperationFileName
            SnmpAdminString,
        etsysFileOperationFileNewName
            SnmpAdminString,
        etsysFileOperationErrorDescription
            SnmpAdminString,
        etsysFileOperationRowStatus
            RowStatus
    }

etsysFileOperationIndex OBJECT-TYPE
    SYNTAX      Unsigned32 (0..4294967295)
    MAX-ACCESS  not-accessible
    STATUS      current
    DESCRIPTION
        "The locally arbitrary, but unique identifier associated
         with this file operation entry."
    ::= { etsysFileOperationEntry 1 }

etsysFileOperationType OBJECT-TYPE
    SYNTAX      INTEGER {
        delete(1),
        rename(2)
    }
    MAX-ACCESS  read-create
    STATUS      current
    DESCRIPTION
        "The operation that should be performed on the named file."
    ::= { etsysFileOperationEntry 2 }

etsysFileOperationFileName OBJECT-TYPE
    SYNTAX      SnmpAdminString
    MAX-ACCESS  read-create
    STATUS      current
    DESCRIPTION
        "The fully qualified name of the file that this operation
         will be applied to."
    DEFVAL { ''H }
    ::= { etsysFileOperationEntry 3 }

etsysFileOperationFileNewName OBJECT-TYPE
    SYNTAX      SnmpAdminString
    MAX-ACCESS  read-create
    STATUS      current
    DESCRIPTION
        "The new fully qualified name for this file.  This object is
         only required for the rename operation type."
    DEFVAL { ''H }
    ::= { etsysFileOperationEntry 4 }

etsysFileOperationErrorDescription OBJECT-TYPE
    SYNTAX      SnmpAdminString
    MAX-ACCESS  read-only
    STATUS      current
    DESCRIPTION
           "This object contains a descriptive error message if the
            requested operation failed.  Implementations must reset
            the error message to a zero-length string when the
            etsysFileOperationRowStatus leaf is set to the active
            state."
    DEFVAL { ''H }
    ::= { etsysFileOperationEntry 5 }

etsysFileOperationRowStatus OBJECT-TYPE
    SYNTAX      RowStatus
    MAX-ACCESS  read-create
    STATUS      current
    DESCRIPTION
           "A control that allows entries to be added, activated,
            deactivated, and removed from this table.

            When the value of this object is 'active' none of the
            other objects in this conceptual row can be modified.

            Setting this object to the 'active' state from the
            'notInService' state will cause the requested file
            operation to be initiated or queued.

            Once the requested file operation has completed,
            successfully or otherwise, this leaf will be set to
            the 'notInService' state by the managed entity.

            Setting this object to any other valid state from the
            'active' state will cancel the file operation if it
            has not been started.

            Setting this object to the 'active' state from the
            'active' state will not have any affect.

            Conceptual rows that have been in the 'notInService'
            state for some entity specific time period will be
            destroyed by the managed entity."
    ::= { etsysFileOperationEntry 6 }


-- -------------------------------------------------------------
-- Conformance Information
-- -------------------------------------------------------------

etsysFileGroups                OBJECT IDENTIFIER ::=
                  { etsysFileConformance 1 }

etsysFileCompliances           OBJECT IDENTIFIER ::=
                  { etsysFileConformance 2 }

-- -------------------------------------------------------------
-- units of conformance
-- -------------------------------------------------------------

etsysFileTransferGroup  OBJECT-GROUP
    OBJECTS {
        etsysFileTransferRequestLimit,
        etsysFileTransferRequestsCurrent,
        etsysFileTransferRequestsCompleted,
        etsysFileTransferRequestSupportedURLs,
        etsysFileTransferRequestNextAvailableIndex,
        etsysFileTransferRequestSource,
        etsysFileTransferRequestDestination,
        etsysFileTransferRequestOperStatus,
        etsysFileTransferRequestEnqueuedTime,
        etsysFileTransferRequestCompletionTime,
        etsysFileTransferRequestBytesTransferred,
        etsysFileTransferRequestErrorDescription,
        etsysFileTransferRequestStorageType,
        etsysFileTransferRequestRowStatus
    }
    STATUS      current
    DESCRIPTION
        "A group of objects that provide a means to copy and
         transfer files."
    ::= { etsysFileGroups 1 }

etsysFileListingGroup  OBJECT-GROUP
    OBJECTS {
        etsysFileListingFileName,
        etsysFileListingFileSize,
        etsysFileListingFileType,
        etsysFileListingFileDate,
        etsysFileListingFileOrigin
    }
    STATUS      current
    DESCRIPTION
        "A group of objects that provide a means to list existing
         files."
    ::= { etsysFileGroups 2 }

etsysFileOperationGroup  OBJECT-GROUP
    OBJECTS {
        etsysFileOperationLimit,
        etsysFileOperationsCurrent,
        etsysFileOperationsCompleted,
        etsysFileOperationNextAvailableIndex,
        etsysFileOperationType,
        etsysFileOperationFileName,
        etsysFileOperationFileNewName,
        etsysFileOperationErrorDescription,
        etsysFileOperationRowStatus
    }
    STATUS      current
    DESCRIPTION
        "A group of objects that provide a means to rename and
         delete existing files."
    ::= { etsysFileGroups 3 }

-- -------------------------------------------------------------
-- compliance statements
-- -------------------------------------------------------------

etsysFileCompliance MODULE-COMPLIANCE
    STATUS      current
    DESCRIPTION
        "The compliance statement for entities which implement
        the Enterasys File Management MIB.  Implementation of
        this MIB is based on individual product needs."
    MODULE      -- this module
    MANDATORY-GROUPS {
            etsysFileTransferGroup
    }
    GROUP   etsysFileListingGroup
    DESCRIPTION
        "An optional group for products that support the ability
         to list existing files.  This functionality would be
         important to someone managing a large installation of
         devices that wishes to know if a file already exists on
         all of the devices."
    GROUP   etsysFileOperationGroup
    DESCRIPTION
        "An optional group for products that support the ability
         to rename or delete existing files.  This functionality
         would be important to someone managing a large
         installation of devices that wishes to delete or rename
         a file already exists on all of the devices."
    ::= { etsysFileCompliances 1 }

END
