ENTERASYS-DOT3-LLDP-EXT-MIB DEFINITIONS ::= BEGIN

--  enterasys-dot3-lldp-ext-mib.txt
--
--  Part Number:
--
--

--  This module provides authoritative definitions for Enterasys
--  Networks' IEEE DOT3 LLDP Extension MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright August, 2013 Enterasys Networks, Inc.

IMPORTS
    MODULE-IDENTITY, OBJECT-TYPE, Integer32
        FROM SNMPv2-SMI
    MODULE-COMPLIANCE, OBJECT-GROUP
        FROM SNMPv2-CONF
    lldpV2LocPortIfIndex
        FROM LLDP-V2-MIB
    EnabledStatus
        FROM P-BRIDGE-MIB
    etsysModules
        FROM ENTERASYS-MIB-NAMES;

etsysDot3LldpExtMIB MODULE-IDENTITY
    LAST-UPDATED "201308281751Z"  -- Wed Aug 28 17:51 UTC 2013
    ORGANIZATION "Enterasys Networks, Inc"
    CONTACT-INFO
        "Postal:  Enterasys Networks
                  9 Northeastern Blvd.
                  Salem, NH 03079 USA

         Phone:   +1 603 952 5000
         E-mail:  support@enterasys.com
         WWW:     http://www.enterasys.com"

    DESCRIPTION
        "This MIB module defines a portion of the SNMP MIB
         under the Enterasys Networks enterprise OID pertaining
         to proprietary extensions to the
         IEEE8023-DOT3-LLDP-EXT-V2-MIB MIB module."

    REVISION    "201308281751Z"  -- Wed Aug 28 17:51 UTC 2013
    DESCRIPTION "Initial version of this MIB module."

    ::= { etsysModules 104 }


-- -------------------------------------------------------------
-- Textual Conventions
-- -------------------------------------------------------------


-- -------------------------------------------------------------
-- MIB Objects
-- -------------------------------------------------------------

etsysDot3LldpExtObjects
    OBJECT IDENTIFIER ::= { etsysDot3LldpExtMIB 1 }

etsysDot3LldpExtConformance
    OBJECT IDENTIFIER ::= { etsysDot3LldpExtMIB 2 }


-- -------------------------------------------------------------
-- branches in the etsysDot3LldpExtMIB
-- -------------------------------------------------------------

etsysDot3LldpExtEeePort
    OBJECT IDENTIFIER ::= { etsysDot3LldpExtObjects 2 }

-- -------------------------------------------------------------
-- Objects in the etsysDot3LldpExtEeePort group
-- -------------------------------------------------------------

etsysDot3LldpExtEeeConfigTable OBJECT-TYPE
    SYNTAX      SEQUENCE OF EtsysDot3LldpExtEeeConfigEntry
    MAX-ACCESS  not-accessible
    STATUS      current
    DESCRIPTION
        "A list of entries for interfaces that have support for
         Energy Efficient Ethernet."
    ::= { etsysDot3LldpExtEeePort 1 }

etsysDot3LldpExtEeeConfigEntry OBJECT-TYPE
    SYNTAX      EtsysDot3LldpExtEeeConfigEntry
    MAX-ACCESS  not-accessible
    STATUS      current
    DESCRIPTION
        "An entry containing management information applicable
         to a particular interface that has support for Energy
         Efficient Ethernet.  Objects in this entry which have a
         MAX-ACCESS of read-write MUST be persistent across
         device resets."
    INDEX { lldpV2LocPortIfIndex }
    ::= { etsysDot3LldpExtEeeConfigTable 1 }

EtsysDot3LldpExtEeeConfigEntry ::=
    SEQUENCE {
        etsysDot3LldpExtEeeAdminStatus  EnabledStatus,
        etsysDot3LldpExtEeeOperStatus   INTEGER,
        etsysDot3LldpExtEeeTLVTxEnable  EnabledStatus,
        etsysDot3LldpExtEeeLocRxTwSys   Integer32,
        etsysDot3LldpExtEeeLocFbTwSys   Integer32
    }

etsysDot3LldpExtEeeAdminStatus   OBJECT-TYPE
    SYNTAX      EnabledStatus
    MAX-ACCESS  read-write
    STATUS      current
    DESCRIPTION
        "The administrative enabled/disabled status of
         Energy Efficient Ethernet on this interface."
    DEFVAL { disabled }
    ::= { etsysDot3LldpExtEeeConfigEntry 1 }

etsysDot3LldpExtEeeOperStatus   OBJECT-TYPE
    SYNTAX      INTEGER {
                  enabled(1),
                  disabled(2),
                  unsupported(3)
                }
    MAX-ACCESS  read-only
    STATUS      current
    DESCRIPTION
        "The operational status of Energy Efficient Ethernet
         on this interface."
    ::= { etsysDot3LldpExtEeeConfigEntry 2 }

etsysDot3LldpExtEeeTLVTxEnable OBJECT-TYPE
    SYNTAX      EnabledStatus
    MAX-ACCESS  read-write
    STATUS      current
    DESCRIPTION
        "The Energy Efficient Ethernet LLDP TLV transmission
         status."
    DEFVAL { disabled }
    ::= { etsysDot3LldpExtEeeConfigEntry 3 }

etsysDot3LldpExtEeeLocRxTwSys    OBJECT-TYPE
    SYNTAX      Integer32
    MAX-ACCESS  read-write
    STATUS      current
    DESCRIPTION
        "The value of Tw_sys_tx that the local system is
         requesting in the receive direction.  This object
         maps to the variable LocRxSystemValue as defined in
         IEEE Std 802.3 78.4.2.3.  "
    REFERENCE
            "IEEE Std 802.3 30.12.2.1.24"
    ::= { etsysDot3LldpExtEeeConfigEntry 4 }

etsysDot3LldpExtEeeLocFbTwSys    OBJECT-TYPE
    SYNTAX      Integer32
    MAX-ACCESS  read-write
    STATUS      current
    DESCRIPTION
        "The value of the fallback Tw_sys_tx that the local
         system is advertising to the remote system.  This
         object maps to the variable LocFbSystemValue as
         defined in IEEE Std 802.3 78.4.2.3."
    REFERENCE
            "IEEE Std 802.3 30.12.2.1.26"
    ::= { etsysDot3LldpExtEeeConfigEntry 5 }


-- -------------------------------------------------------------
-- Conformance Information
-- -------------------------------------------------------------

etsysDot3LldpExtGroups      OBJECT IDENTIFIER
           ::= { etsysDot3LldpExtConformance 1 }

etsysDot3LldpExtCompliances OBJECT IDENTIFIER
           ::= { etsysDot3LldpExtConformance 2 }

-- -------------------------------------------------------------
-- Units of conformance
-- -------------------------------------------------------------

etsysDot3LldpExtEeePortGroup OBJECT-GROUP
    OBJECTS {
      etsysDot3LldpExtEeeAdminStatus,
      etsysDot3LldpExtEeeOperStatus,
      etsysDot3LldpExtEeeTLVTxEnable,
      etsysDot3LldpExtEeeLocRxTwSys,
      etsysDot3LldpExtEeeLocFbTwSys
    }
    STATUS      current
    DESCRIPTION
       "Objects in the port required group."
    ::= { etsysDot3LldpExtGroups 1 }

-- -------------------------------------------------------------
-- Compliance statements
-- -------------------------------------------------------------

etsysDot3LldpExtEeePortCompliance MODULE-COMPLIANCE
    STATUS      current
    DESCRIPTION
       "The compliance statement for devices that support
        the etsysDot3LldpExtEeeMibExtMIB module."

    MODULE
        MANDATORY-GROUPS {
            etsysDot3LldpExtEeePortGroup
        }

    ::= { etsysDot3LldpExtCompliances 1 }

END
