EXTREME-NETSIGHT-ALARM-MIB DEFINITIONS ::= BEGIN

--  extreme-netsight-alarm-mib.my
--
--  Part Number:
--

--  This module provides authoritative definitions and defines
--  notifications for Extreme Networks' Netsight Alarm Manager
--  MIB.

--  This module will be extended, as needed.

--  Extreme Networks reserves the right to make changes in this
--  specification and other information contained in this document
--  without prior notice.  The reader should consult Extreme Networks
--  to determine whether any such changes have been made.
--
--  In no event shall Extreme Networks be liable for any incidental,
--  indirect, special, or consequential damages whatsoever (including
--  but not limited to lost profits) arising out of or related to this
--  document or the information contained in it, even if Extreme
--  Networks has been advised of, known, or should have known, the
--  possibility of such damages.
--
--  Extreme Networks grants vendors, end-users, and other interested
--  parties a non-exclusive license to use this Specification in
--  connection with the management of Extreme Networks products.

--  Copyright August, 2016 Extreme Networks, Inc

IMPORTS
    MODULE-IDENTITY, NOTIFICATION-TYPE, OBJECT-TYPE
        FROM SNMPv2-SMI
    DateAndTime
        FROM SNMPv2-TC
    MODULE-COMPLIANCE, NOTIFICATION-GROUP, OBJECT-GROUP
        FROM SNMPv2-CONF
    InetAddressType, InetAddress
        FROM INET-ADDRESS-MIB
    etsysModules
        FROM ENTERASYS-MIB-NAMES;

extremeNetsightAlarmMIB MODULE-IDENTITY
    LAST-UPDATED "201608291138Z"  -- Mon Aug 29 11:38 UTC 2016
    ORGANIZATION "Extreme Networks, Inc."
    CONTACT-INFO
        "Postal:  Extreme Networks, Inc.
                  145 Rio Robles
                  San Jose, CA 95134 USA

         Phone:   +1 408 579 2800
         E-mail:  support@extremenetworks.com
         WWW:     http://www.extremenetworks.com"
    DESCRIPTION
        "This MIB module defines a portion of the SNMP MIB under
         the Enterasys Networks enterprise OID pertaining to
         definitions and notifications for the Extreme Netsight
         network management software.

         This MIB defines a set of notifications that the Netsight
         Alarm Manager can send to another SNMP trap receiver."

    REVISION    "201608291138Z"  -- Mon Aug 29 11:38 UTC 2016
    DESCRIPTION
        "Fixed typographical errors."

    REVISION    "201601261722Z"  -- Tue Jan 26 17:22 UTC 2016
    DESCRIPTION
        "Added new notifications per latest Netsight.
         Fixed some existing alarm names per latest Netsight.
         Changed order of objects under extremeNetsightAlarmVars."

    REVISION    "201601180900Z"  -- Mon Jan 18 09:00 UTC 2016
    DESCRIPTION
        "Initial version of this MIB module."

    ::= { etsysModules 105 }

-- -------------------------------------------------------------- --
-- Textual conventions
-- -------------------------------------------------------------- --

-- -------------------------------------------------------------- --
-- MIB groups
-- -------------------------------------------------------------- --

extremeNetsightAlarmObjects         OBJECT IDENTIFIER
                                    ::= { extremeNetsightAlarmMIB 1 }

extremeNetsightAlarmNotifications   OBJECT IDENTIFIER
                                    ::= { extremeNetsightAlarmObjects 0 }

extremeNetsightAlarmVars            OBJECT IDENTIFIER
                                    ::= { extremeNetsightAlarmObjects 1 }

-- ------------------------------------------------------------- --
-- Objects
-- ------------------------------------------------------------- --

extremeNetsightAlarmMessage OBJECT-TYPE
    SYNTAX      OCTET STRING (SIZE (0..256))
    MAX-ACCESS  accessible-for-notify
    STATUS      current
    DESCRIPTION
        "The message describing the specific alarm triggered."
    ::= { extremeNetsightAlarmVars 1 }

extremeNetsightAlarmSeverity OBJECT-TYPE
    SYNTAX      INTEGER {
                    emergency (0),
                    alert     (1),
                    critical  (2),
                    error     (3),
                    warning   (4),
                    notice    (5),
                    info      (6),
                    debug     (7)
                }
    MAX-ACCESS  accessible-for-notify
    STATUS      current
    DESCRIPTION
        "The severity of an alarm. Lower values signify more serious
         conditions, whereas higher values are less critical."
    ::= { extremeNetsightAlarmVars 2 }

extremeNetsightAlarmTimestamp OBJECT-TYPE
    SYNTAX      DateAndTime
    MAX-ACCESS  accessible-for-notify
    STATUS      current
    DESCRIPTION
        "The date and time, in device local time, when the alarm occurred."
    ::= { extremeNetsightAlarmVars 3 }

extremeNetsightAlarmSourceDeviceAddressType OBJECT-TYPE
    SYNTAX      InetAddressType
    MAX-ACCESS  accessible-for-notify
    STATUS      current
    DESCRIPTION
        "The address type of extremeNetsightAlarmSourceDeviceAddress."
    ::= { extremeNetsightAlarmVars 4 }

extremeNetsightAlarmSourceDeviceAddress OBJECT-TYPE
    SYNTAX      InetAddress
    MAX-ACCESS  accessible-for-notify
    STATUS      current
    DESCRIPTION
        "The address of the device that triggered this alarm.  This
         may be the address of the Netsight server itself or a remote
         device managed by Netsight."
    ::= { extremeNetsightAlarmVars 5 }

extremeNetsightAlarmSubcomponent OBJECT-TYPE
    SYNTAX      OCTET STRING (SIZE (0..256))
    MAX-ACCESS  accessible-for-notify
    STATUS      current
    DESCRIPTION
        "Additional event specific data for this alarm (e.g. interface
         number).  Note that in most cases there is no such data,
         and this object will be an empty string."
    ::= { extremeNetsightAlarmVars 6 }

-- ------------------------------------------------------------- --
-- Notifications
-- ------------------------------------------------------------- --

-- ------------------------------------------------------------- --
-- Generic Netsight Alarm Template
-- ------------------------------------------------------------- --
extremeNetsightAlarmNotification NOTIFICATION-TYPE
    OBJECTS {
            extremeNetsightAlarmMessage,
            extremeNetsightAlarmSeverity,
            extremeNetsightAlarmTimestamp,
            extremeNetsightAlarmSourceDeviceAddressType,
            extremeNetsightAlarmSourceDeviceAddress,
            extremeNetsightAlarmSubcomponent
    }
    STATUS  current
    DESCRIPTION
        "This notification indicates that an alarm was triggered and
         contains information related to that alarm.  Note that this
         notification is generic and MAY not be used when a more
         specific notification is defined for a given alarm.

         NOTE: The list of OBJECTS defined for this alarm will
         act as a template for all other notifications defined in this
         group and they should include the same list."
    ::= { extremeNetsightAlarmNotifications 1 }

-- ------------------------------------------------------------- --
-- Specific Netsight Alarm Notifications
-- ------------------------------------------------------------- --
-- NOTE WELL: The following notifications are intended to behave
-- exactly as extremeNetsightAlarmNotification defined above, but
-- will not reiterate the same OBJECTS list explicitly.  However,
-- they are expected to include the same list at run-time.  The
-- intent of these specific notifications is to provide a unique
-- alarm identifier to receivers that can only parse the snmpTrapOID
-- to distinguish alarms.
-- ------------------------------------------------------------- --

extremeNetsightAlarmDeviceUp NOTIFICATION-TYPE
    STATUS      current
    DESCRIPTION
        "Device Up"
    ::= { extremeNetsightAlarmNotifications 2 }

extremeNetsightAlarmDeviceDown NOTIFICATION-TYPE
    STATUS      current
    DESCRIPTION
        "Device Down"
    ::= { extremeNetsightAlarmNotifications 3 }

extremeNetsightAlarmLinkUp NOTIFICATION-TYPE
    STATUS      current
    DESCRIPTION
        "Link Up"
    ::= { extremeNetsightAlarmNotifications 4 }

extremeNetsightAlarmLinkDown NOTIFICATION-TYPE
    STATUS      current
    DESCRIPTION
        "Link Down"
    ::= { extremeNetsightAlarmNotifications 5 }

extremeNetsightAlarmFanOK NOTIFICATION-TYPE
    STATUS      current
    DESCRIPTION
        "Fan OK"
    ::= { extremeNetsightAlarmNotifications 6 }

extremeNetsightAlarmFanFailure NOTIFICATION-TYPE
    STATUS      current
    DESCRIPTION
        "Fan Failure"
    ::= { extremeNetsightAlarmNotifications 7 }

extremeNetsightAlarmPowerSupplyNormal NOTIFICATION-TYPE
    STATUS      current
    DESCRIPTION
        "Power supply normal"
    ::= { extremeNetsightAlarmNotifications 8 }

extremeNetsightAlarmPowerSupplyFailed NOTIFICATION-TYPE
    STATUS      current
    DESCRIPTION
        "Power supply failed"
    ::= { extremeNetsightAlarmNotifications 9 }

extremeNetsightAlarmMultiAuthMaxUsersReached NOTIFICATION-TYPE
    STATUS      current
    DESCRIPTION
        "MultiAuth max users reached"
    ::= { extremeNetsightAlarmNotifications 10 }

extremeNetsightAlarmMultiAuthModuleMaxUsersReached NOTIFICATION-TYPE
    STATUS      current
    DESCRIPTION
        "MultiAuth module max users reached"
    ::= { extremeNetsightAlarmNotifications 11 }

extremeNetsightAlarmMultiAuthSystemMaxUsersReached NOTIFICATION-TYPE
    STATUS      current
    DESCRIPTION
        "MultiAuth system max users reached"
    ::= { extremeNetsightAlarmNotifications 12 }

extremeNetsightAlarmOSPFConflictingPacket NOTIFICATION-TYPE
    STATUS      current
    DESCRIPTION
        "OSPF Conflicting packet"
    ::= { extremeNetsightAlarmNotifications 13 }

extremeNetsightAlarmSpanguard NOTIFICATION-TYPE
    STATUS      current
    DESCRIPTION
        "Spanguard"
    ::= { extremeNetsightAlarmNotifications 14 }

extremeNetsightAlarmMSTPLoopProtectEvent NOTIFICATION-TYPE
    STATUS      current
    DESCRIPTION
        "MSTP Loop Protect Event"
    ::= { extremeNetsightAlarmNotifications 15 }

extremeNetsightAlarmSTPDiagnosticMSTI NOTIFICATION-TYPE
    STATUS      current
    DESCRIPTION
        "STP Diagnostic MSTI"
    ::= { extremeNetsightAlarmNotifications 16 }

extremeNetsightAlarmSTPDiagnosticCIST NOTIFICATION-TYPE
    STATUS      current
    DESCRIPTION
        "STP Diagnostic CIST"
    ::= { extremeNetsightAlarmNotifications 17 }

extremeNetsightAlarmColdStart NOTIFICATION-TYPE
    STATUS      current
    DESCRIPTION
        "Cold start"
    ::= { extremeNetsightAlarmNotifications 18 }

extremeNetsightAlarmWarmStart NOTIFICATION-TYPE
    STATUS      current
    DESCRIPTION
        "Warm start"
    ::= { extremeNetsightAlarmNotifications 19 }

extremeNetsightAlarmMultiAuthSuccess NOTIFICATION-TYPE
    STATUS      current
    DESCRIPTION
        "MultiAuth Success"
    ::= { extremeNetsightAlarmNotifications 20 }

extremeNetsightAlarmMultiAuthFailed NOTIFICATION-TYPE
    STATUS      current
    DESCRIPTION
        "MultiAuth Failed"
    ::= { extremeNetsightAlarmNotifications 21 }

extremeNetsightAlarmMultiAuthTerminated NOTIFICATION-TYPE
    STATUS      current
    DESCRIPTION
        "MultiAuth terminated"
    ::= { extremeNetsightAlarmNotifications 22 }

extremeNetsightAlarmConfigurationChanged NOTIFICATION-TYPE
    STATUS      current
    DESCRIPTION
        "Configuration Changed"
    ::= { extremeNetsightAlarmNotifications 23 }

extremeNetsightAlarmAPInService NOTIFICATION-TYPE
    STATUS      current
    DESCRIPTION
        "AP In Service"
    ::= { extremeNetsightAlarmNotifications 24 }

extremeNetsightAlarmAPOutOfService NOTIFICATION-TYPE
    STATUS      current
    DESCRIPTION
        "AP Out of Service"
    ::= { extremeNetsightAlarmNotifications 25 }

extremeNetsightAlarmAPRadioChange NOTIFICATION-TYPE
    STATUS      current
    DESCRIPTION
        "AP Radio Change"
    ::= { extremeNetsightAlarmNotifications 26 }

extremeNetsightAlarmAPRadioOnOff NOTIFICATION-TYPE
    STATUS      current
    DESCRIPTION
        "AP Radio OnOff"
    ::= { extremeNetsightAlarmNotifications 27 }

extremeNetsightAlarmInterferenceStopped NOTIFICATION-TYPE
    STATUS      current
    DESCRIPTION
        "Interference Stopped"
    ::= { extremeNetsightAlarmNotifications 28 }

extremeNetsightAlarmInterferenceStarted NOTIFICATION-TYPE
    STATUS      current
    DESCRIPTION
        "Interference Started"
    ::= { extremeNetsightAlarmNotifications 29 }

extremeNetsightAlarmThreatInactive NOTIFICATION-TYPE
    STATUS      current
    DESCRIPTION
        "Threat Inactive"
    ::= { extremeNetsightAlarmNotifications 30 }

extremeNetsightAlarmThreatActive NOTIFICATION-TYPE
    STATUS      current
    DESCRIPTION
        "Threat Active"
    ::= { extremeNetsightAlarmNotifications 31 }

extremeNetsightAlarmApplianceDiskUsage NOTIFICATION-TYPE
    STATUS      current
    DESCRIPTION
        "Appliance Disk Usage"
    ::= { extremeNetsightAlarmNotifications 32 }

extremeNetsightAlarmDatabaseBackupDiskUsage NOTIFICATION-TYPE
    STATUS      current
    DESCRIPTION
        "Database Backup Disk Usage"
    ::= { extremeNetsightAlarmNotifications 33 }

extremeNetsightAlarmRogueInactive NOTIFICATION-TYPE
    STATUS      current
    DESCRIPTION
        "Rogue Inactive"
    ::= { extremeNetsightAlarmNotifications 34 }

extremeNetsightAlarmRogueActive NOTIFICATION-TYPE
    STATUS      current
    DESCRIPTION
        "Rogue Active"
    ::= { extremeNetsightAlarmNotifications 35 }

extremeNetsightAlarmIPMIEvent NOTIFICATION-TYPE
    STATUS      current
    DESCRIPTION
        "IPMI Event"
    ::= { extremeNetsightAlarmNotifications 36 }

extremeNetsightAlarmACPowerRecovered NOTIFICATION-TYPE
    STATUS      current
    DESCRIPTION
        "AC Power Recovered"
    ::= { extremeNetsightAlarmNotifications 37 }

extremeNetsightAlarmACPowerLost NOTIFICATION-TYPE
    STATUS      current
    DESCRIPTION
        "AC Power Lost"
    ::= { extremeNetsightAlarmNotifications 38 }

extremeNetsightAlarmDriveFaultRecovered NOTIFICATION-TYPE
    STATUS      current
    DESCRIPTION
        "Drive Fault Recovered"
    ::= { extremeNetsightAlarmNotifications 39 }

extremeNetsightAlarmDriveFault NOTIFICATION-TYPE
    STATUS      current
    DESCRIPTION
        "Drive Fault"
    ::= { extremeNetsightAlarmNotifications 40 }

extremeNetsightAlarmApplicationAnalyticsLicenseViolationClear NOTIFICATION-TYPE
    STATUS      current
    DESCRIPTION
        "Application Analytics License Violation Clear"
    ::= { extremeNetsightAlarmNotifications 41 }

extremeNetsightAlarmApplicationAnalyticsLicenseViolation NOTIFICATION-TYPE
    STATUS      current
    DESCRIPTION
        "Application Analytics License Violation"
    ::= { extremeNetsightAlarmNotifications 42 }

extremeNetsightAlarmApplicationAnalyticsApplianceUp NOTIFICATION-TYPE
    STATUS      current
    DESCRIPTION
        "Application Analytics Appliance Up"
    ::= { extremeNetsightAlarmNotifications 43 }

extremeNetsightAlarmApplicationAnalyticsApplianceDown NOTIFICATION-TYPE
    STATUS      current
    DESCRIPTION
        "Application Analytics Appliance Down"
    ::= { extremeNetsightAlarmNotifications 44 }

extremeNetsightAlarmNACApplianceUp NOTIFICATION-TYPE
    STATUS      current
    DESCRIPTION
        "NAC Appliance Up"
    ::= { extremeNetsightAlarmNotifications 45 }

extremeNetsightAlarmNACApplianceDown NOTIFICATION-TYPE
    STATUS      current
    DESCRIPTION
        "NAC Appliance Down"
    ::= { extremeNetsightAlarmNotifications 46 }

extremeNetsightAlarmNACLicenseViolationClear NOTIFICATION-TYPE
    STATUS      current
    DESCRIPTION
        "NAC License Violation Clear"
    ::= { extremeNetsightAlarmNotifications 47 }

extremeNetsightAlarmNACLicenseViolation NOTIFICATION-TYPE
    STATUS      current
    DESCRIPTION
        "NAC License Violation"
    ::= { extremeNetsightAlarmNotifications 48 }

extremeNetsightAlarmNACAssessmentLicenseViolationClear NOTIFICATION-TYPE
    STATUS      current
    DESCRIPTION
        "NAC Assessment License Violation Clear"
    ::= { extremeNetsightAlarmNotifications 49 }

extremeNetsightAlarmNACAssessmentLicenseViolation NOTIFICATION-TYPE
    STATUS      current
    DESCRIPTION
        "NAC Assessment License Violation"
    ::= { extremeNetsightAlarmNotifications 50 }

extremeNetsightAlarmNACLostContactWithSwitchClear NOTIFICATION-TYPE
    STATUS      current
    DESCRIPTION
        "NAC Lost Contact with Switch Clear"
    ::= { extremeNetsightAlarmNotifications 51 }

extremeNetsightAlarmNACLostContactWithSwitch NOTIFICATION-TYPE
    STATUS      current
    DESCRIPTION
        "NAC Lost Contact with Switch"
    ::= { extremeNetsightAlarmNotifications 52 }

extremeNetsightAlarmNACLostPartialContactWithSwitchClear NOTIFICATION-TYPE
    STATUS      current
    DESCRIPTION
        "NAC Lost Partial Contact with Switch Clear"
    ::= { extremeNetsightAlarmNotifications 53 }

extremeNetsightAlarmNACLostPartialContactWithSwitch NOTIFICATION-TYPE
    STATUS      current
    DESCRIPTION
        "NAC Lost Partial Contact with Switch"
    ::= { extremeNetsightAlarmNotifications 54 }

extremeNetsightAlarmNACLostContactWithRADIUSServerClear NOTIFICATION-TYPE
    STATUS      current
    DESCRIPTION
        "NAC Lost Contact with RADIUS Server Clear"
    ::= { extremeNetsightAlarmNotifications 55 }

extremeNetsightAlarmNACLostContactWithRADIUSServer NOTIFICATION-TYPE
    STATUS      current
    DESCRIPTION
        "NAC Lost Contact with RADIUS Server"
    ::= { extremeNetsightAlarmNotifications 56 }

extremeNetsightAlarmNACLostContactWithLDAPServiceClear NOTIFICATION-TYPE
    STATUS      current
    DESCRIPTION
        "NAC Lost Contact with LDAP Service Clear"
    ::= { extremeNetsightAlarmNotifications 57 }

extremeNetsightAlarmNACLostContactWithLDAPService NOTIFICATION-TYPE
    STATUS      current
    DESCRIPTION
        "NAC Lost Contact with LDAP Service"
    ::= { extremeNetsightAlarmNotifications 58 }

extremeNetsightAlarmNACLostPartialContactWithLDAPServiceClear NOTIFICATION-TYPE
    STATUS      current
    DESCRIPTION
        "NAC Lost Partial Contact with LDAP Service Clear"
    ::= { extremeNetsightAlarmNotifications 59 }

extremeNetsightAlarmNACLostPartialContactWithLDAPService NOTIFICATION-TYPE
    STATUS      current
    DESCRIPTION
        "NAC Lost Partial Contact with LDAP Service"
    ::= { extremeNetsightAlarmNotifications 60 }

extremeNetsightAlarmNACRFC3576ErrorClear NOTIFICATION-TYPE
    STATUS      current
    DESCRIPTION
        "NAC RFC 3576 Error Clear"
    ::= { extremeNetsightAlarmNotifications 61 }

extremeNetsightAlarmNACRFC3576Error NOTIFICATION-TYPE
    STATUS      current
    DESCRIPTION
        "NAC RFC 3576 Error"
    ::= { extremeNetsightAlarmNotifications 62 }

extremeNetsightAlarmNACDatabaseTableServiceIsUp NOTIFICATION-TYPE
    STATUS      current
    DESCRIPTION
        "NAC Database Table Service is up"
    ::= { extremeNetsightAlarmNotifications 63 }

extremeNetsightAlarmNACDatabaseTableServiceDown NOTIFICATION-TYPE
    STATUS      current
    DESCRIPTION
        "NAC Database Table Service down"
    ::= { extremeNetsightAlarmNotifications 64 }

extremeNetsightAlarmNACRADIUSRequestsWarningThresholdRectified NOTIFICATION-TYPE
    STATUS      current
    DESCRIPTION
        "NAC RADIUS Requests Warning Threshold Rectified"
    ::= { extremeNetsightAlarmNotifications 65 }

extremeNetsightAlarmNACRADIUSRequestsWarningThresholdExceeded NOTIFICATION-TYPE
    STATUS      current
    DESCRIPTION
        "NAC RADIUS Requests Warning Threshold Exceeded"
    ::= { extremeNetsightAlarmNotifications 66 }

extremeNetsightAlarmNACRADIUSRequestsCriticalThresholdRectified NOTIFICATION-TYPE
    STATUS      current
    DESCRIPTION
        "NAC RADIUS Requests Critical Threshold Rectified"
    ::= { extremeNetsightAlarmNotifications 67 }

extremeNetsightAlarmNACRADIUSRequestsCriticalThresholdExceeded NOTIFICATION-TYPE
    STATUS      current
    DESCRIPTION
        "NAC RADIUS Requests Critical Threshold Exceeded"
    ::= { extremeNetsightAlarmNotifications 68 }

extremeNetsightAlarmNACCertificateUpdated NOTIFICATION-TYPE
    STATUS      current
    DESCRIPTION
        "NAC Certificate Updated"
    ::= { extremeNetsightAlarmNotifications 69 }

extremeNetsightAlarmNACCertificateHasInvalidDate NOTIFICATION-TYPE
    STATUS      current
    DESCRIPTION
        "NAC Certificate has Invalid Date"
    ::= { extremeNetsightAlarmNotifications 70 }

extremeNetsightAlarmNACCertificateWarningCleared NOTIFICATION-TYPE
    STATUS      current
    DESCRIPTION
        "NAC Certificate Warning Cleared"
    ::= { extremeNetsightAlarmNotifications 71 }

extremeNetsightAlarmNACCertificateExpiringWarning NOTIFICATION-TYPE
    STATUS      current
    DESCRIPTION
        "NAC Certificate Expiring Warning"
    ::= { extremeNetsightAlarmNotifications 72 }

extremeNetsightAlarmNACCertificateNoticeCleared NOTIFICATION-TYPE
    STATUS      current
    DESCRIPTION
        "NAC Certificate Notice Cleared"
    ::= { extremeNetsightAlarmNotifications 73 }

extremeNetsightAlarmNACCertificateExpiringNotice NOTIFICATION-TYPE
    STATUS      current
    DESCRIPTION
        "NAC Certificate Expiring Notice"
    ::= { extremeNetsightAlarmNotifications 74 }

extremeNetsightAlarmNACDuplicateSNMPEngineIDCleared NOTIFICATION-TYPE
    STATUS      current
    DESCRIPTION
        "NAC Duplicate SNMP Engine ID Cleared"
    ::= { extremeNetsightAlarmNotifications 75 }

extremeNetsightAlarmNACDuplicateSNMPEngineIDFound NOTIFICATION-TYPE
    STATUS      current
    DESCRIPTION
        "NAC Duplicate SNMP Engine ID Found"
    ::= { extremeNetsightAlarmNotifications 76 }

extremeNetsightAlarmDeviceTopologyChange NOTIFICATION-TYPE
    STATUS      current
    DESCRIPTION
        "Device Topology Change"
    ::= { extremeNetsightAlarmNotifications 77 }

extremeNetsightAlarmDevicePercentCPU NOTIFICATION-TYPE
    STATUS      current
    DESCRIPTION
        "Device % CPU"
    ::= { extremeNetsightAlarmNotifications 78 }

extremeNetsightAlarmDeviceMemoryPercentUsage NOTIFICATION-TYPE
    STATUS      current
    DESCRIPTION
        "Device Memory % Usage"
    ::= { extremeNetsightAlarmNotifications 79 }

extremeNetsightAlarmHostPercentCPU NOTIFICATION-TYPE
    STATUS      current
    DESCRIPTION
        "Host % CPU"
    ::= { extremeNetsightAlarmNotifications 80 }

extremeNetsightAlarmHostDiskPercentUsage NOTIFICATION-TYPE
    STATUS      current
    DESCRIPTION
        "Host Disk % Usage"
    ::= { extremeNetsightAlarmNotifications 81 }

extremeNetsightAlarmHostMemoryPercentUsage NOTIFICATION-TYPE
    STATUS      current
    DESCRIPTION
        "Host Memory % Usage"
    ::= { extremeNetsightAlarmNotifications 82 }

extremeNetsightAlarmInterfacePercentUsage NOTIFICATION-TYPE
    STATUS      current
    DESCRIPTION
        "Interface % Usage"
    ::= { extremeNetsightAlarmNotifications 83 }

extremeNetsightAlarmInterfacePercentValidPackets NOTIFICATION-TYPE
    STATUS      current
    DESCRIPTION
        "Interface % Valid Packets"
    ::= { extremeNetsightAlarmNotifications 84 }

extremeNetsightAlarmHistoricalPersistenceResumed NOTIFICATION-TYPE
    STATUS      current
    DESCRIPTION
        "Historical Persistence Resumed"
    ::= { extremeNetsightAlarmNotifications 85 }

extremeNetsightAlarmHistoricalPersistenceSuspended NOTIFICATION-TYPE
    STATUS      current
    DESCRIPTION
        "Historical Persistence Suspended"
    ::= { extremeNetsightAlarmNotifications 86 }

extremeNetsightAlarmAnalyticsPersistenceResumed NOTIFICATION-TYPE
    STATUS      current
    DESCRIPTION
        "Analytics Persistence Resumed"
    ::= { extremeNetsightAlarmNotifications 87 }

extremeNetsightAlarmAnalyticsPersistenceSuspended NOTIFICATION-TYPE
    STATUS      current
    DESCRIPTION
        "Analytics Persistence Suspended"
    ::= { extremeNetsightAlarmNotifications 88 }

extremeNetsightAlarmControllerEstablishedSSHConnection NOTIFICATION-TYPE
    STATUS      current
    DESCRIPTION
        "Controller Established SSH Connection"
    ::= { extremeNetsightAlarmNotifications 89 }

extremeNetsightAlarmControllerFailedSSHConnection NOTIFICATION-TYPE
    STATUS      current
    DESCRIPTION
        "Controller Failed SSH Connection"
    ::= { extremeNetsightAlarmNotifications 90 }

extremeNetsightAlarmServerHeapMemoryOK NOTIFICATION-TYPE
    STATUS      current
    DESCRIPTION
        "Server Heap Memory OK"
    ::= { extremeNetsightAlarmNotifications 91 }

extremeNetsightAlarmServerHeapMemoryLow NOTIFICATION-TYPE
    STATUS      current
    DESCRIPTION
        "Server Heap Memory Low"
    ::= { extremeNetsightAlarmNotifications 92 }

extremeNetsightAlarmClientMACAvailabilityLow NOTIFICATION-TYPE
    STATUS      current
    DESCRIPTION
        "Client MAC Availability Low"
    ::= { extremeNetsightAlarmNotifications 93 }

extremeNetsightAlarmClientMACIPChangesHigh NOTIFICATION-TYPE
    STATUS      current
    DESCRIPTION
        "Client MAC IP Changes High"
    ::= { extremeNetsightAlarmNotifications 94 }

extremeNetsightAlarmNACEntriesPerGroupPerfThresholdRectified NOTIFICATION-TYPE
    STATUS      current
    DESCRIPTION
        "NAC Entries Per Group Performance Threshold Rectified"
    ::= { extremeNetsightAlarmNotifications 95 }

extremeNetsightAlarmNACEntriesPerGroupPerfThresholdExceeded NOTIFICATION-TYPE
    STATUS      current
    DESCRIPTION
        "NAC Entries Per Group Performance Threshold Exceeded"
    ::= { extremeNetsightAlarmNotifications 96 }

extremeNetsightAlarmNACCertificateUsesMD5SignatureCleared NOTIFICATION-TYPE
    STATUS      current
    DESCRIPTION
        "NAC Certificate Uses MD5 Signature Cleared"
    ::= { extremeNetsightAlarmNotifications 97 }

extremeNetsightAlarmNACCertificateUsesMD5SignatureNotice NOTIFICATION-TYPE
    STATUS      current
    DESCRIPTION
        "NAC Certificate Uses MD5 Signature Notice"
    ::= { extremeNetsightAlarmNotifications 98 }

extremeNetsightAlarmNACWinbinddProcessCleared NOTIFICATION-TYPE
    STATUS      current
    DESCRIPTION
        "NAC winbindd Process Cleared"
    ::= { extremeNetsightAlarmNotifications 99 }

extremeNetsightAlarmNACWinbinddProcessDown NOTIFICATION-TYPE
    STATUS      current
    DESCRIPTION
        "NAC winbindd Process Down"
    ::= { extremeNetsightAlarmNotifications 100 }

extremeNetsightAlarmNACSquidProcessCleared NOTIFICATION-TYPE
    STATUS      current
    DESCRIPTION
        "NAC squid Process Cleared"
    ::= { extremeNetsightAlarmNotifications 101 }

extremeNetsightAlarmNACSquidProcessDown NOTIFICATION-TYPE
    STATUS      current
    DESCRIPTION
        "NAC squid Process Down"
    ::= { extremeNetsightAlarmNotifications 102 }

extremeNetsightAlarmNACRadiusdProcessCleared NOTIFICATION-TYPE
    STATUS      current
    DESCRIPTION
        "NAC radiusd Process Cleared"
    ::= { extremeNetsightAlarmNotifications 103 }

extremeNetsightAlarmNACRadiusdProcessDown NOTIFICATION-TYPE
    STATUS      current
    DESCRIPTION
        "NAC radiusd Process Down"
    ::= { extremeNetsightAlarmNotifications 104 }

extremeNetsightAlarmNACDnsproxyProcessCleared NOTIFICATION-TYPE
    STATUS      current
    DESCRIPTION
        "NAC dnsproxy Process Cleared"
    ::= { extremeNetsightAlarmNotifications 105 }

extremeNetsightAlarmNACDnsproxyProcessDown NOTIFICATION-TYPE
    STATUS      current
    DESCRIPTION
        "NAC dnsproxy Process Down"
    ::= { extremeNetsightAlarmNotifications 106 }

extremeNetsightAlarmNACIPMICriticalEventCleared NOTIFICATION-TYPE
    STATUS      current
    DESCRIPTION
        "NAC IPMI Critical Event Cleared"
    ::= { extremeNetsightAlarmNotifications 107 }

extremeNetsightAlarmNACIPMICriticalEvent NOTIFICATION-TYPE
    STATUS      current
    DESCRIPTION
        "NAC IPMI Critical Event"
    ::= { extremeNetsightAlarmNotifications 108 }

extremeNetsightAlarmNACDNSServersUnreachableCleared NOTIFICATION-TYPE
    STATUS      current
    DESCRIPTION
        "NAC DNS Servers Unreachable Cleared"
    ::= { extremeNetsightAlarmNotifications 109 }

extremeNetsightAlarmNACDNSServersUnreachable NOTIFICATION-TYPE
    STATUS      current
    DESCRIPTION
        "NAC DNS Servers Unreachable"
    ::= { extremeNetsightAlarmNotifications 110 }

-- -------------------------------------------------------------
-- Conformance Information
-- -------------------------------------------------------------

extremeNetsightAlarmConformance OBJECT IDENTIFIER
    ::= { extremeNetsightAlarmMIB 2 }

extremeNetsightAlarmGroups OBJECT IDENTIFIER
    ::= { extremeNetsightAlarmConformance 1 }

extremeNetsightAlarmCompliances OBJECT IDENTIFIER
    ::= { extremeNetsightAlarmConformance 2 }

-- -------------------------------------------------------------
-- Units of Conformance
-- -------------------------------------------------------------

extremeNetsightAlarmSettings OBJECT-GROUP
    OBJECTS {
        extremeNetsightAlarmMessage,
        extremeNetsightAlarmSeverity,
        extremeNetsightAlarmTimestamp,
        extremeNetsightAlarmSourceDeviceAddressType,
        extremeNetsightAlarmSourceDeviceAddress,
        extremeNetsightAlarmSubcomponent
	}
    STATUS  current
    DESCRIPTION
        "A collection of objects for formatting notifications
         in the Extreme Netsight Alarm MIB."
    ::= { extremeNetsightAlarmGroups 1 }

extremeNetsightAlarmGenericNotificationGroup NOTIFICATION-GROUP
    NOTIFICATIONS {
        extremeNetsightAlarmNotification
    }
    STATUS  current
    DESCRIPTION
        "A collection of objects required for reporting
         notifications with the Extreme Netsight Alarm MIB."
    ::= { extremeNetsightAlarmGroups 2 }

extremeNetsightAlarmSpecificNotificationGroup NOTIFICATION-GROUP
    NOTIFICATIONS {
        extremeNetsightAlarmDeviceUp,
        extremeNetsightAlarmDeviceDown,
        extremeNetsightAlarmLinkUp,
        extremeNetsightAlarmLinkDown,
        extremeNetsightAlarmFanOK,
        extremeNetsightAlarmFanFailure,
        extremeNetsightAlarmPowerSupplyNormal,
        extremeNetsightAlarmPowerSupplyFailed,
        extremeNetsightAlarmMultiAuthMaxUsersReached,
        extremeNetsightAlarmMultiAuthModuleMaxUsersReached,
        extremeNetsightAlarmMultiAuthSystemMaxUsersReached,
        extremeNetsightAlarmOSPFConflictingPacket,
        extremeNetsightAlarmSpanguard,
        extremeNetsightAlarmMSTPLoopProtectEvent,
        extremeNetsightAlarmSTPDiagnosticMSTI,
        extremeNetsightAlarmSTPDiagnosticCIST,
        extremeNetsightAlarmColdStart,
        extremeNetsightAlarmWarmStart,
        extremeNetsightAlarmMultiAuthSuccess,
        extremeNetsightAlarmMultiAuthFailed,
        extremeNetsightAlarmMultiAuthTerminated,
        extremeNetsightAlarmConfigurationChanged,
        extremeNetsightAlarmAPInService,
        extremeNetsightAlarmAPOutOfService,
        extremeNetsightAlarmAPRadioChange,
        extremeNetsightAlarmAPRadioOnOff,
        extremeNetsightAlarmInterferenceStopped,
        extremeNetsightAlarmInterferenceStarted,
        extremeNetsightAlarmThreatInactive,
        extremeNetsightAlarmThreatActive,
        extremeNetsightAlarmApplianceDiskUsage,
        extremeNetsightAlarmDatabaseBackupDiskUsage,
        extremeNetsightAlarmRogueInactive,
        extremeNetsightAlarmRogueActive,
        extremeNetsightAlarmIPMIEvent,
        extremeNetsightAlarmACPowerRecovered,
        extremeNetsightAlarmACPowerLost,
        extremeNetsightAlarmDriveFaultRecovered,
        extremeNetsightAlarmDriveFault,
        extremeNetsightAlarmApplicationAnalyticsLicenseViolationClear,
        extremeNetsightAlarmApplicationAnalyticsLicenseViolation,
        extremeNetsightAlarmApplicationAnalyticsApplianceUp,
        extremeNetsightAlarmApplicationAnalyticsApplianceDown,
        extremeNetsightAlarmNACApplianceUp,
        extremeNetsightAlarmNACApplianceDown,
        extremeNetsightAlarmNACLicenseViolationClear,
        extremeNetsightAlarmNACLicenseViolation,
        extremeNetsightAlarmNACAssessmentLicenseViolationClear,
        extremeNetsightAlarmNACAssessmentLicenseViolation,
        extremeNetsightAlarmNACLostContactWithSwitchClear,
        extremeNetsightAlarmNACLostContactWithSwitch,
        extremeNetsightAlarmNACLostPartialContactWithSwitchClear,
        extremeNetsightAlarmNACLostPartialContactWithSwitch,
        extremeNetsightAlarmNACLostContactWithRADIUSServerClear,
        extremeNetsightAlarmNACLostContactWithRADIUSServer,
        extremeNetsightAlarmNACLostContactWithLDAPServiceClear,
        extremeNetsightAlarmNACLostContactWithLDAPService,
        extremeNetsightAlarmNACLostPartialContactWithLDAPServiceClear,
        extremeNetsightAlarmNACLostPartialContactWithLDAPService,
        extremeNetsightAlarmNACRFC3576ErrorClear,
        extremeNetsightAlarmNACRFC3576Error,
        extremeNetsightAlarmNACDatabaseTableServiceIsUp,
        extremeNetsightAlarmNACDatabaseTableServiceDown,
        extremeNetsightAlarmNACRADIUSRequestsWarningThresholdRectified,
        extremeNetsightAlarmNACRADIUSRequestsWarningThresholdExceeded,
        extremeNetsightAlarmNACRADIUSRequestsCriticalThresholdRectified,
        extremeNetsightAlarmNACRADIUSRequestsCriticalThresholdExceeded,
        extremeNetsightAlarmNACCertificateUpdated,
        extremeNetsightAlarmNACCertificateHasInvalidDate,
        extremeNetsightAlarmNACCertificateWarningCleared,
        extremeNetsightAlarmNACCertificateExpiringWarning,
        extremeNetsightAlarmNACCertificateNoticeCleared,
        extremeNetsightAlarmNACCertificateExpiringNotice,
        extremeNetsightAlarmNACDuplicateSNMPEngineIDCleared,
        extremeNetsightAlarmNACDuplicateSNMPEngineIDFound,
        extremeNetsightAlarmDeviceTopologyChange,
        extremeNetsightAlarmDevicePercentCPU,
        extremeNetsightAlarmDeviceMemoryPercentUsage,
        extremeNetsightAlarmHostPercentCPU,
        extremeNetsightAlarmHostDiskPercentUsage,
        extremeNetsightAlarmHostMemoryPercentUsage,
        extremeNetsightAlarmInterfacePercentUsage,
        extremeNetsightAlarmInterfacePercentValidPackets,
        extremeNetsightAlarmHistoricalPersistenceResumed,
        extremeNetsightAlarmHistoricalPersistenceSuspended,
        extremeNetsightAlarmAnalyticsPersistenceResumed,
        extremeNetsightAlarmAnalyticsPersistenceSuspended,
        extremeNetsightAlarmControllerEstablishedSSHConnection,
        extremeNetsightAlarmControllerFailedSSHConnection,
        extremeNetsightAlarmServerHeapMemoryOK,
        extremeNetsightAlarmServerHeapMemoryLow,
        extremeNetsightAlarmClientMACAvailabilityLow,
        extremeNetsightAlarmClientMACIPChangesHigh,
        extremeNetsightAlarmNACEntriesPerGroupPerfThresholdRectified,
        extremeNetsightAlarmNACEntriesPerGroupPerfThresholdExceeded,
        extremeNetsightAlarmNACCertificateUsesMD5SignatureCleared,
        extremeNetsightAlarmNACCertificateUsesMD5SignatureNotice,
        extremeNetsightAlarmNACWinbinddProcessCleared,
        extremeNetsightAlarmNACWinbinddProcessDown,
        extremeNetsightAlarmNACSquidProcessCleared,
        extremeNetsightAlarmNACSquidProcessDown,
        extremeNetsightAlarmNACRadiusdProcessCleared,
        extremeNetsightAlarmNACRadiusdProcessDown,
        extremeNetsightAlarmNACDnsproxyProcessCleared,
        extremeNetsightAlarmNACDnsproxyProcessDown,
        extremeNetsightAlarmNACIPMICriticalEventCleared,
        extremeNetsightAlarmNACIPMICriticalEvent,
        extremeNetsightAlarmNACDNSServersUnreachableCleared,
        extremeNetsightAlarmNACDNSServersUnreachable
    }
    STATUS  current
    DESCRIPTION
        "A collection of objects required for reporting
         notifications with the Extreme Netsight Alarm MIB."
    ::= { extremeNetsightAlarmGroups 3 }

extremeNetsightAlarmComplianceGroup MODULE-COMPLIANCE
    STATUS      current
    DESCRIPTION
        "The compliance statement for devices that support
         the Extreme Netsight Alarm MIB."
    MODULE
    MANDATORY-GROUPS {
        extremeNetsightAlarmSettings,
        extremeNetsightAlarmGenericNotificationGroup
    }

    GROUP  extremeNetsightAlarmSpecificNotificationGroup
    DESCRIPTION
        "This group is OPTIONAL."

    ::= { extremeNetsightAlarmCompliances 1}

END
