-- powertek SPS2 MIB
-- MIB for PWT Products
--
-- { iso org(3) dod(6) internet(1) private(4) enterprises(1) powertek(42610)
-- product(1) pdu(4) pwt(5)
-- ==============================================================================================
---
---     Revision History
---
---     v0.10   04-Jan-2021     JimmyYang/FIT Created
---     v0.20   27-Jan-2021     JimmyYang/FIT Modify device tree number.
---     v0.30   16-Mar-2021     JimmyYang/FIT Modify device tree number, Add leak current (RCM) function.
---     v0.40   23-Apr-2021     JimmyYang/FIT Fixed the some bug.
---     v0.50   29-Apr-2021     JimmyYang/FIT Fixed the some bug.
---     v0.60   19-May-2021     JimmyYang/FIT Add daisy chain communication lost/restore trap.
---     v0.70   03-Jun-2021     JimmyYang/FIT Change the string "active energy" in tarp to "energy".
---     v0.80   11-Aug-2021     JimmyYang/FIT Add LDAP & TACACS+ setting.
---     v0.90   05-Nov-2021     JimmyYang/FIT Add PF alarm setting.
---                                           Modify the "pduDaisyCommLost" & "pduDaisyCommRestore" trap id.
---     v0.91   15-Nov-2021     JimmyYang/FIT Modify the description of pf alarm trap.
---     v0.92   12-Jan-2022     JimmyYang/FIT Add power share function.
---     v0.93   13-May-2022     JimmyYang/FIT Modify SMS List.
---     v0.94   13-Oct-2022     GraceWu/FIT change the wrong string "Salve" to "Slave".
-- ==============================================================================================

SPS2v1-MIB DEFINITIONS ::= BEGIN

IMPORTS
  enterprises
    FROM RFC1155-SMI
  OBJECT-TYPE
    FROM RFC-1212
  DisplayString
    FROM RFC1213-MIB
  TRAP-TYPE
    FROM RFC-1215;

powertek            OBJECT IDENTIFIER ::= { enterprises 42610 }
product             OBJECT IDENTIFIER ::= { powertek 1 }
pdu                 OBJECT IDENTIFIER ::= { product 4 }
pwt2                OBJECT IDENTIFIER ::= { pdu 1 }
pduObjects          OBJECT IDENTIFIER ::= { pwt2 1 }
pduTraps            OBJECT IDENTIFIER ::= { pwt2 2 }

pduIdent            OBJECT IDENTIFIER ::= { pduObjects 1 }
pduDevMon           OBJECT IDENTIFIER ::= { pduObjects 2 }
pduDevMgmt          OBJECT IDENTIFIER ::= { pduObjects 3 }
pduNetwork          OBJECT IDENTIFIER ::= { pduObjects 4 }
pduSetting          OBJECT IDENTIFIER ::= { pduObjects 5 }
pduLog              OBJECT IDENTIFIER ::= { pduObjects 6 }
pduAdvanced         OBJECT IDENTIFIER ::= { pduObjects 7 }

-- ===========================================================================
--
-- pduIdent
--
--  pdu Identification Group
--
-- ===========================================================================
pduIdentAgentSoftwareVersion OBJECT-TYPE
       SYNTAX DisplayString (SIZE (0..63))
       ACCESS read-only
       STATUS mandatory
       DESCRIPTION
               "The firmware version of the device."
      ::= { pduIdent 1 }

pduIdentSerialNumber OBJECT-TYPE
      SYNTAX DisplayString (SIZE(0..31))
      ACCESS read-only
      STATUS mandatory
      DESCRIPTION
               "A Model of this device."
      ::= { pduIdent 2 }


-- ===========================================================================
--
-- pduDevMon
--
--  pdu Monoitor Group
--
-- ===========================================================================
pduDevMonInlet      OBJECT IDENTIFIER ::= { pduDevMon 1 }
pduDevMonOutlet     OBJECT IDENTIFIER ::= { pduDevMon 2 }
pduDevMonEmd        OBJECT IDENTIFIER ::= { pduDevMon 3 }


-- ===========================================================================
--
-- pduDevMonInlet
--
--  Inlet Monoitor Group
--
-- ===========================================================================
pduDevMonInletTable OBJECT-TYPE
        SYNTAX SEQUENCE OF PduDevMonInletEntry
        ACCESS not-accessible
        STATUS mandatory
        DESCRIPTION
                "A list to display information of inlet."
        ::= { pduDevMonInlet 1}

pduDevMonInletEntry OBJECT-TYPE
        SYNTAX PduDevMonInletEntry
        ACCESS not-accessible
        STATUS mandatory
        DESCRIPTION
                "A list to display information of inlet."
        INDEX  { pduDevMonInletIndex }
        ::= { pduDevMonInletTable 1 }

PduDevMonInletEntry ::=
        SEQUENCE {
                pduDevMonInletIndex
                        INTEGER,
                pduDevMonInletName
                        DisplayString,
                pduDevMonInletBid
                        INTEGER,
                pduDevMonInletFwType
                        INTEGER,
                pduDevMonInletVoltPh1
                        INTEGER,
                pduDevMonInletVoltPh2
                        INTEGER,
                pduDevMonInletVoltPh3
                        INTEGER,
                pduDevMonInletPfPh1B1
                        INTEGER,
                pduDevMonInletPfPh2B1
                        INTEGER,
                pduDevMonInletPfPh3B1
                        INTEGER,
                pduDevMonInletPfPh1B2
                        INTEGER,
                pduDevMonInletPfPh2B2
                        INTEGER,
                pduDevMonInletPfPh3B2
                        INTEGER,
                pduDevMonInletCurrentPh1B1
                        INTEGER,
                pduDevMonInletCurrentPh2B1
                        INTEGER,
                pduDevMonInletCurrentPh3B1
                        INTEGER,
                pduDevMonInletCurrentPh1B2
                        INTEGER,
                pduDevMonInletCurrentPh2B2
                        INTEGER,
                pduDevMonInletCurrentPh3B2
                        INTEGER,
                pduDevMonInletActPowerPh1
                        INTEGER,
                pduDevMonInletActPowerPh2
                        INTEGER,
                pduDevMonInletActPowerPh3
                        INTEGER,
                pduDevMonInletAppPowerPh1
                        INTEGER,
                pduDevMonInletAppPowerPh2
                        INTEGER,
                pduDevMonInletAppPowerPh3
                        INTEGER,
                pduDevMonInletEnergyPh1
                        INTEGER,
                pduDevMonInletEnergyPh2
                        INTEGER,
                pduDevMonInletEnergyPh3
                        INTEGER,
                pduDevMonInletEnergyTimePh1
                        DisplayString,
                pduDevMonInletEnergyTimePh2
                        DisplayString,
                pduDevMonInletEnergyTimePh3
                        DisplayString,
                pduDevMonInletLoadBalance
                        INTEGER,
                pduDevMonInletEvtOverLoad
                        INTEGER,
                pduDevMonInletEvtStatusPh1
                        INTEGER,
                pduDevMonInletEvtStatusPh2
                        INTEGER,
                pduDevMonInletEvtStatusPh3
                        INTEGER,
                pduDevMonInletEvtLoadBalance
                        INTEGER,
                pduDevMonInletRcmValid
                        INTEGER,
                pduDevMonInletRcmCurrent
                        INTEGER,
                pduDevMonInletRcmAlarm
                        INTEGER,
				pduDevMonInletPowerShare
                        INTEGER
        }

pduDevMonInletIndex OBJECT-TYPE
        SYNTAX INTEGER (0..15)
        ACCESS read-only
        STATUS mandatory
        DESCRIPTION
                "The index to a inlet entry."
        ::= { pduDevMonInletEntry 1 }

pduDevMonInletName OBJECT-TYPE
        SYNTAX DisplayString (SIZE(0..31))
        ACCESS read-only
        STATUS mandatory
        DESCRIPTION
                "The name of inlet."
        ::= { pduDevMonInletEntry 2 }

pduDevMonInletBid OBJECT-TYPE
        SYNTAX INTEGER
        ACCESS read-only
        STATUS mandatory
        DESCRIPTION
                "The board id of inlet."
        ::= { pduDevMonInletEntry 3}

pduDevMonInletFwType OBJECT-TYPE
        SYNTAX INTEGER
        ACCESS read-only
        STATUS mandatory
        DESCRIPTION
                "The firmware type of inlet."
        ::= { pduDevMonInletEntry 4}

pduDevMonInletVoltPh1 OBJECT-TYPE
        SYNTAX INTEGER
        UNITS  "0.1v"
        ACCESS read-only
        STATUS mandatory
        DESCRIPTION
                "The phase1 voltage of inlet."
        ::= { pduDevMonInletEntry 5}

pduDevMonInletVoltPh2 OBJECT-TYPE
        SYNTAX INTEGER
        UNITS  "0.1v"
        ACCESS read-only
        STATUS mandatory
        DESCRIPTION
                "The phase2 voltage of inlet."
        ::= { pduDevMonInletEntry 6}

pduDevMonInletVoltPh3 OBJECT-TYPE
        SYNTAX INTEGER
        UNITS  "0.1v"
        ACCESS read-only
        STATUS mandatory
        DESCRIPTION
                "The phase3 voltage of inlet."
        ::= { pduDevMonInletEntry 7}

pduDevMonInletPfPh1B1 OBJECT-TYPE
        SYNTAX INTEGER
        ACCESS read-only
        STATUS mandatory
        DESCRIPTION
                "The phase1b1 pf of inlet."
        ::= { pduDevMonInletEntry 8}

pduDevMonInletPfPh2B1 OBJECT-TYPE
        SYNTAX INTEGER
        ACCESS read-only
        STATUS mandatory
        DESCRIPTION
                "The phase2b1 pf of inlet."
        ::= { pduDevMonInletEntry 9}

pduDevMonInletPfPh3B1 OBJECT-TYPE
        SYNTAX INTEGER
        ACCESS read-only
        STATUS mandatory
        DESCRIPTION
                "The phase3b1 pf of inlet."
        ::= { pduDevMonInletEntry 10}

pduDevMonInletPfPh1B2 OBJECT-TYPE
        SYNTAX INTEGER
        ACCESS read-only
        STATUS mandatory
        DESCRIPTION
                "The phase1b2 pf of inlet."
        ::= { pduDevMonInletEntry 11}

pduDevMonInletPfPh2B2 OBJECT-TYPE
        SYNTAX INTEGER
        ACCESS read-only
        STATUS mandatory
        DESCRIPTION
                "The phase2b2 pf of inlet."
        ::= { pduDevMonInletEntry 12}

pduDevMonInletPfPh3B2 OBJECT-TYPE
        SYNTAX INTEGER
        ACCESS read-only
        STATUS mandatory
        DESCRIPTION
                "The phase3b2 pf of inlet."
        ::= { pduDevMonInletEntry 13}

pduDevMonInletCurrentPh1B1 OBJECT-TYPE
        SYNTAX INTEGER
        UNITS  "0.01A"
        ACCESS read-only
        STATUS mandatory
        DESCRIPTION
                "The phase1b1 current of inlet."
        ::= { pduDevMonInletEntry 14}

pduDevMonInletCurrentPh2B1 OBJECT-TYPE
        SYNTAX INTEGER
        UNITS  "0.01A"
        ACCESS read-only
        STATUS mandatory
        DESCRIPTION
                "The phase2b1 current of inlet."
        ::= { pduDevMonInletEntry 15}

pduDevMonInletCurrentPh3B1 OBJECT-TYPE
        SYNTAX INTEGER
        UNITS  "0.01A"
        ACCESS read-only
        STATUS mandatory
        DESCRIPTION
                "The phase3b1 current of inlet."
        ::= { pduDevMonInletEntry 16}

pduDevMonInletCurrentPh1B2 OBJECT-TYPE
        SYNTAX INTEGER
        UNITS  "0.01A"
        ACCESS read-only
        STATUS mandatory
        DESCRIPTION
                "The phase1b2 current of inlet."
        ::= { pduDevMonInletEntry 17}

pduDevMonInletCurrentPh2B2 OBJECT-TYPE
        SYNTAX INTEGER
        UNITS  "0.01A"
        ACCESS read-only
        STATUS mandatory
        DESCRIPTION
                "The phase2b2 current of inlet."
        ::= { pduDevMonInletEntry 18}

pduDevMonInletCurrentPh3B2 OBJECT-TYPE
        SYNTAX INTEGER
        UNITS  "0.01A"
        ACCESS read-only
        STATUS mandatory
        DESCRIPTION
                "The phase3b2 voltage of inlet."
        ::= { pduDevMonInletEntry 19}

pduDevMonInletActPowerPh1 OBJECT-TYPE
        SYNTAX INTEGER
        UNITS  "0.1W"
        ACCESS read-only
        STATUS mandatory
        DESCRIPTION
                "The phase1 act power of inlet."
        ::= { pduDevMonInletEntry 20}

pduDevMonInletActPowerPh2 OBJECT-TYPE
        SYNTAX INTEGER
        UNITS  "0.1W"
        ACCESS read-only
        STATUS mandatory
        DESCRIPTION
                "The phase2 act power of inlet."
        ::= { pduDevMonInletEntry 21}

pduDevMonInletActPowerPh3 OBJECT-TYPE
        SYNTAX INTEGER
        UNITS  "0.1W"
        ACCESS read-only
        STATUS mandatory
        DESCRIPTION
                "The phase3 act power of inlet."
        ::= { pduDevMonInletEntry 22}

pduDevMonInletAppPowerPh1 OBJECT-TYPE
        SYNTAX INTEGER
        UNITS  "0.1VA"
        ACCESS read-only
        STATUS mandatory
        DESCRIPTION
                "The phase1 app power of inlet."
        ::= { pduDevMonInletEntry 23}

pduDevMonInletAppPowerPh2 OBJECT-TYPE
        SYNTAX INTEGER
        UNITS  "0.1VA"
        ACCESS read-only
        STATUS mandatory
        DESCRIPTION
                "The phase2 app power of inlet."
        ::= { pduDevMonInletEntry 24}

pduDevMonInletAppPowerPh3 OBJECT-TYPE
        SYNTAX INTEGER
        UNITS  "0.1VA"
        ACCESS read-only
        STATUS mandatory
        DESCRIPTION
                "The phase3 app power of inlet."
        ::= { pduDevMonInletEntry 25}

pduDevMonInletEnergyPh1 OBJECT-TYPE
        SYNTAX INTEGER
        UNITS  "KWH"
        ACCESS read-only
        STATUS mandatory
        DESCRIPTION
                "The phase1 energy of inlet."
        ::= { pduDevMonInletEntry 26}

pduDevMonInletEnergyPh2 OBJECT-TYPE
        SYNTAX INTEGER
        UNITS  "KWH"
        ACCESS read-only
        STATUS mandatory
        DESCRIPTION
                "The phase2 energy of inlet."
        ::= { pduDevMonInletEntry 27}

pduDevMonInletEnergyPh3 OBJECT-TYPE
        SYNTAX INTEGER
        UNITS  "KWH"
        ACCESS read-only
        STATUS mandatory
        DESCRIPTION
                "The phase3 energy of inlet."
        ::= { pduDevMonInletEntry 28}

pduDevMonInletEnergyTimePh1 OBJECT-TYPE
        SYNTAX DisplayString
        ACCESS read-only
        STATUS mandatory
        DESCRIPTION
                "The phase1 energy time of inlet."
        ::= { pduDevMonInletEntry 29}

pduDevMonInletEnergyTimePh2 OBJECT-TYPE
        SYNTAX DisplayString
        ACCESS read-only
        STATUS mandatory
        DESCRIPTION
                "The phase2 energy time of inlet."
        ::= { pduDevMonInletEntry 30}

pduDevMonInletEnergyTimePh3 OBJECT-TYPE
        SYNTAX DisplayString
        ACCESS read-only
        STATUS mandatory
        DESCRIPTION
                "The phase3 energy time of inlet."
        ::= { pduDevMonInletEntry 31}

pduDevMonInletLoadBalance OBJECT-TYPE
        SYNTAX INTEGER
        UNITS  "1%"
        ACCESS read-only
        STATUS mandatory
        DESCRIPTION
                "The load balance of inlet."
        ::= { pduDevMonInletEntry 32}

pduDevMonInletEvtOverLoad OBJECT-TYPE
        SYNTAX INTEGER {
                normal(1),
                warning(2),
                critical(3)
                }
        ACCESS read-only
        STATUS mandatory
        DESCRIPTION
                "The over load of status inlet."
        ::= { pduDevMonInletEntry 33}

pduDevMonInletEvtStatusPh1 OBJECT-TYPE
        SYNTAX INTEGER {
                normal(1),
                warning(2),
                critical(3)
                }
        ACCESS read-only
        STATUS mandatory
        DESCRIPTION
                "The phase1 status of inlet."
        ::= { pduDevMonInletEntry 34}

pduDevMonInletEvtStatusPh2 OBJECT-TYPE
        SYNTAX INTEGER {
                normal(1),
                warning(2),
                critical(3)
                }
        ACCESS read-only
        STATUS mandatory
        DESCRIPTION
                "The phase2 status of inlet."
        ::= { pduDevMonInletEntry 35}

pduDevMonInletEvtStatusPh3 OBJECT-TYPE
        SYNTAX INTEGER {
                normal(1),
                warning(2),
                critical(3)
                }
        ACCESS read-only
        STATUS mandatory
        DESCRIPTION
                "The phase3 status of inlet."
        ::= { pduDevMonInletEntry 36}

pduDevMonInletEvtLoadBalance OBJECT-TYPE
        SYNTAX INTEGER {
                normal(1),
                warning(2),
                critical(3)
                }
        ACCESS read-only
        STATUS mandatory
        DESCRIPTION
                "The load balance of status inlet."
        ::= { pduDevMonInletEntry 37}

pduDevMonInletRcmValid OBJECT-TYPE
        SYNTAX INTEGER {
                invalid(1),
                valid(2)
                }
        ACCESS read-only
        STATUS mandatory
        DESCRIPTION
                "The current leak is valid."
        ::= { pduDevMonInletEntry 38}

pduDevMonInletRcmCurrent OBJECT-TYPE
        SYNTAX INTEGER
        UNITS  "0.1mA"
        ACCESS read-only
        STATUS mandatory
        DESCRIPTION
                "Current value of leakage current."
        ::= { pduDevMonInletEntry 39}

pduDevMonInletRcmAlarm OBJECT-TYPE
        SYNTAX INTEGER {
                normal(1),
                alarm(2)
                }
        ACCESS read-only
        STATUS mandatory
        DESCRIPTION
                "Current leak alarm status."
        ::= { pduDevMonInletEntry 40}

pduDevMonInletPowerShare OBJECT-TYPE
        SYNTAX INTEGER {
                inactive(1),
                activeBackupPower(2),
				activeMainPower(3)
                }
        ACCESS read-only
        STATUS mandatory
        DESCRIPTION
                "Power share status."
        ::= { pduDevMonInletEntry 41}

-- ===========================================================================
--
-- pduDevMonOutlet
--
--  Outlet Monoitor Group
--
-- ===========================================================================
pduDevMonOutletMaster      OBJECT IDENTIFIER ::= { pduDevMonOutlet 1 }
pduDevMonOutletSlave01     OBJECT IDENTIFIER ::= { pduDevMonOutlet 2 }
pduDevMonOutletSlave02     OBJECT IDENTIFIER ::= { pduDevMonOutlet 3 }
pduDevMonOutletSlave03     OBJECT IDENTIFIER ::= { pduDevMonOutlet 4 }
pduDevMonOutletSlave04     OBJECT IDENTIFIER ::= { pduDevMonOutlet 5 }
pduDevMonOutletSlave05     OBJECT IDENTIFIER ::= { pduDevMonOutlet 6 }
pduDevMonOutletSlave06     OBJECT IDENTIFIER ::= { pduDevMonOutlet 7 }
pduDevMonOutletSlave07     OBJECT IDENTIFIER ::= { pduDevMonOutlet 8 }
pduDevMonOutletSlave08     OBJECT IDENTIFIER ::= { pduDevMonOutlet 9 }
pduDevMonOutletSlave09     OBJECT IDENTIFIER ::= { pduDevMonOutlet 10 }
pduDevMonOutletSlave10     OBJECT IDENTIFIER ::= { pduDevMonOutlet 11 }
pduDevMonOutletSlave11     OBJECT IDENTIFIER ::= { pduDevMonOutlet 12 }
pduDevMonOutletSlave12     OBJECT IDENTIFIER ::= { pduDevMonOutlet 13 }
pduDevMonOutletSlave13     OBJECT IDENTIFIER ::= { pduDevMonOutlet 14 }
pduDevMonOutletSlave14     OBJECT IDENTIFIER ::= { pduDevMonOutlet 15 }
pduDevMonOutletSlave15     OBJECT IDENTIFIER ::= { pduDevMonOutlet 16 }


-- ===========================================================================
--
-- pduDevMonOutletMaster
--
--  Master Outlet Monoitor Group
--
-- ===========================================================================
pduDevMonOutletMasterPortSize OBJECT-TYPE
        SYNTAX INTEGER
        ACCESS read-only
        STATUS mandatory
        DESCRIPTION
                "The port size of master."
        ::= { pduDevMonOutletMaster 1}

-- ===========================================================================
--
-- pduDevMonOutletMasterPortTable
--
--  Master Outlet Port Monoitor Group
--
-- ===========================================================================
pduDevMonOutletMasterPortTable OBJECT-TYPE
        SYNTAX SEQUENCE OF PduDevMonOutletMasterPortEntry
        ACCESS not-accessible
        STATUS mandatory
        DESCRIPTION
                "Display the port information list of MasterPort."
        ::= { pduDevMonOutletMaster 2}

pduDevMonOutletMasterPortEntry OBJECT-TYPE
        SYNTAX PduDevMonOutletMasterPortEntry
        ACCESS not-accessible
        STATUS mandatory
        DESCRIPTION
                "Display the port information list of MasterPort.."
        INDEX  { pduDevMonOutletMasterPortIndex}
        ::= { pduDevMonOutletMasterPortTable 1 }

PduDevMonOutletMasterPortEntry ::=
        SEQUENCE {
                pduDevMonOutletMasterPortIndex
                        INTEGER,
                pduDevMonOutletMasterPortName
                        DisplayString,
                pduDevMonOutletMasterPortBid
                        INTEGER,
                pduDevMonOutletMasterPortFwType
                        INTEGER,
                pduDevMonOutletMasterPortRlyState
                        INTEGER,
                pduDevMonOutletMasterPortEvtStatus
                        INTEGER,
                pduDevMonOutletMasterPortVolt
                        INTEGER,
                pduDevMonOutletMasterPortCurrent
                        INTEGER,
                pduDevMonOutletMasterPortPf
                        INTEGER,
                pduDevMonOutletMasterPortActPower
                        INTEGER,
                pduDevMonOutletMasterPortAppPower
                        INTEGER,
                pduDevMonOutletMasterPortEnergy
                        INTEGER,
                pduDevMonOutletMasterPortEnergyTime
                        DisplayString
        }

pduDevMonOutletMasterPortIndex OBJECT-TYPE
        SYNTAX INTEGER (0..63)
        ACCESS read-only
        STATUS mandatory
        DESCRIPTION
                "The index to a outlet entry."
        ::= { pduDevMonOutletMasterPortEntry 1 }

pduDevMonOutletMasterPortName OBJECT-TYPE
        SYNTAX DisplayString (SIZE(0..31))
        ACCESS read-only
        STATUS mandatory
        DESCRIPTION
                "The name of outlet."
        ::= { pduDevMonOutletMasterPortEntry 2 }

pduDevMonOutletMasterPortBid OBJECT-TYPE
        SYNTAX INTEGER
        ACCESS read-only
        STATUS mandatory
        DESCRIPTION
                "The board id of outlet."
        ::= { pduDevMonOutletMasterPortEntry 3}

pduDevMonOutletMasterPortFwType OBJECT-TYPE
        SYNTAX INTEGER
        ACCESS read-only
        STATUS mandatory
        DESCRIPTION
                "The firmware type of outlet."
        ::= { pduDevMonOutletMasterPortEntry 4}

pduDevMonOutletMasterPortRlyState OBJECT-TYPE
        SYNTAX INTEGER {
                off(1),
                on(2)
                }
        ACCESS read-only
        STATUS mandatory
        DESCRIPTION
                "The relay state of outlet."
        ::= { pduDevMonOutletMasterPortEntry 5}

pduDevMonOutletMasterPortEvtStatus OBJECT-TYPE
        SYNTAX INTEGER {
                normal(1),
                warning(2),
                critical(3)
                }
        ACCESS read-only
        STATUS mandatory
        DESCRIPTION
                "The event status of outlet."
        ::= { pduDevMonOutletMasterPortEntry 6}

pduDevMonOutletMasterPortVolt OBJECT-TYPE
        SYNTAX INTEGER
        UNITS  "0.1V"
        ACCESS read-only
        STATUS mandatory
        DESCRIPTION
                "The voltage of outlet."
        ::= { pduDevMonOutletMasterPortEntry 7}

pduDevMonOutletMasterPortCurrent OBJECT-TYPE
        SYNTAX INTEGER
        UNITS  "0.01A"
        ACCESS read-only
        STATUS mandatory
        DESCRIPTION
                "The current of outlet."
        ::= { pduDevMonOutletMasterPortEntry 8}

pduDevMonOutletMasterPortPf OBJECT-TYPE
        SYNTAX INTEGER
        ACCESS read-only
        STATUS mandatory
        DESCRIPTION
                "The pf of outlet."
        ::= { pduDevMonOutletMasterPortEntry 9}

pduDevMonOutletMasterPortActPower OBJECT-TYPE
        SYNTAX INTEGER
        UNITS  "0.1W"
        ACCESS read-only
        STATUS mandatory
        DESCRIPTION
                "The act power of outlet."
        ::= { pduDevMonOutletMasterPortEntry 10}

pduDevMonOutletMasterPortAppPower OBJECT-TYPE
        SYNTAX INTEGER
        UNITS  "0.1VA"
        ACCESS read-only
        STATUS mandatory
        DESCRIPTION
                "The app power of outlet."
        ::= { pduDevMonOutletMasterPortEntry 11}

pduDevMonOutletMasterPortEnergy OBJECT-TYPE
        SYNTAX INTEGER
        UNITS  "KWH"
        ACCESS read-only
        STATUS mandatory
        DESCRIPTION
                "The energy of outlet."
        ::= { pduDevMonOutletMasterPortEntry 12}

pduDevMonOutletMasterPortEnergyTime OBJECT-TYPE
        SYNTAX DisplayString (SIZE(0..31))
        ACCESS read-only
        STATUS mandatory
        DESCRIPTION
                "The energy time of outlet."
        ::= { pduDevMonOutletMasterPortEntry 13}


-- ===========================================================================
--
-- pduDevMonOutletSlave01
--
--  Slave01 Outlet Monoitor Group
--
-- ===========================================================================
pduDevMonOutletSlave01PortSize OBJECT-TYPE
        SYNTAX INTEGER
        ACCESS read-only
        STATUS mandatory
        DESCRIPTION
                "The port size of master."
        ::= { pduDevMonOutletSlave01 1}

-- ===========================================================================
--
-- pduDevMonOutletSlave01PortTable
--
--  Slave01 Outlet Port Monoitor Group
--
-- ===========================================================================
pduDevMonOutletSlave01PortTable OBJECT-TYPE
        SYNTAX SEQUENCE OF PduDevMonOutletSlave01PortEntry
        ACCESS not-accessible
        STATUS mandatory
        DESCRIPTION
                "Display the port information list of Slave01Port."
        ::= { pduDevMonOutletSlave01 2}

pduDevMonOutletSlave01PortEntry OBJECT-TYPE
        SYNTAX PduDevMonOutletSlave01PortEntry
        ACCESS not-accessible
        STATUS mandatory
        DESCRIPTION
                "Display the port information list of Slave01Port.."
        INDEX  { pduDevMonOutletSlave01PortIndex}
        ::= { pduDevMonOutletSlave01PortTable 1 }

PduDevMonOutletSlave01PortEntry ::=
        SEQUENCE {
                pduDevMonOutletSlave01PortIndex
                        INTEGER,
                pduDevMonOutletSlave01PortName
                        DisplayString,
                pduDevMonOutletSlave01PortBid
                        INTEGER,
                pduDevMonOutletSlave01PortFwType
                        INTEGER,
                pduDevMonOutletSlave01PortRlyState
                        INTEGER,
                pduDevMonOutletSlave01PortEvtStatus
                        INTEGER,
                pduDevMonOutletSlave01PortVolt
                        INTEGER,
                pduDevMonOutletSlave01PortCurrent
                        INTEGER,
                pduDevMonOutletSlave01PortPf
                        INTEGER,
                pduDevMonOutletSlave01PortActPower
                        INTEGER,
                pduDevMonOutletSlave01PortAppPower
                        INTEGER,
                pduDevMonOutletSlave01PortEnergy
                        INTEGER,
                pduDevMonOutletSlave01PortEnergyTime
                        DisplayString
        }

pduDevMonOutletSlave01PortIndex OBJECT-TYPE
        SYNTAX INTEGER (0..63)
        ACCESS read-only
        STATUS mandatory
        DESCRIPTION
                "The index to a outlet entry."
        ::= { pduDevMonOutletSlave01PortEntry 1 }

pduDevMonOutletSlave01PortName OBJECT-TYPE
        SYNTAX DisplayString (SIZE(0..31))
        ACCESS read-only
        STATUS mandatory
        DESCRIPTION
                "The name of outlet."
        ::= { pduDevMonOutletSlave01PortEntry 2 }

pduDevMonOutletSlave01PortBid OBJECT-TYPE
        SYNTAX INTEGER
        ACCESS read-only
        STATUS mandatory
        DESCRIPTION
                "The board id of outlet."
        ::= { pduDevMonOutletSlave01PortEntry 3}

pduDevMonOutletSlave01PortFwType OBJECT-TYPE
        SYNTAX INTEGER
        ACCESS read-only
        STATUS mandatory
        DESCRIPTION
                "The firmware type of outlet."
        ::= { pduDevMonOutletSlave01PortEntry 4}

pduDevMonOutletSlave01PortRlyState OBJECT-TYPE
        SYNTAX INTEGER {
                off(1),
                on(2)
                }
        ACCESS read-only
        STATUS mandatory
        DESCRIPTION
                "The relay state of outlet."
        ::= { pduDevMonOutletSlave01PortEntry 5}

pduDevMonOutletSlave01PortEvtStatus OBJECT-TYPE
        SYNTAX INTEGER {
                normal(1),
                warning(2),
                critical(3)
                }
        ACCESS read-only
        STATUS mandatory
        DESCRIPTION
                "The event status of outlet."
        ::= { pduDevMonOutletSlave01PortEntry 6}

pduDevMonOutletSlave01PortVolt OBJECT-TYPE
        SYNTAX INTEGER
        UNITS  "0.1V"
        ACCESS read-only
        STATUS mandatory
        DESCRIPTION
                "The voltage of outlet."
        ::= { pduDevMonOutletSlave01PortEntry 7}

pduDevMonOutletSlave01PortCurrent OBJECT-TYPE
        SYNTAX INTEGER
        UNITS  "0.01A"
        ACCESS read-only
        STATUS mandatory
        DESCRIPTION
                "The current of outlet."
        ::= { pduDevMonOutletSlave01PortEntry 8}

pduDevMonOutletSlave01PortPf OBJECT-TYPE
        SYNTAX INTEGER
        ACCESS read-only
        STATUS mandatory
        DESCRIPTION
                "The pf of outlet."
        ::= { pduDevMonOutletSlave01PortEntry 9}

pduDevMonOutletSlave01PortActPower OBJECT-TYPE
        SYNTAX INTEGER
        UNITS  "0.1W"
        ACCESS read-only
        STATUS mandatory
        DESCRIPTION
                "The act power of outlet."
        ::= { pduDevMonOutletSlave01PortEntry 10}

pduDevMonOutletSlave01PortAppPower OBJECT-TYPE
        SYNTAX INTEGER
        UNITS  "0.1VA"
        ACCESS read-only
        STATUS mandatory
        DESCRIPTION
                "The app power of outlet."
        ::= { pduDevMonOutletSlave01PortEntry 11}

pduDevMonOutletSlave01PortEnergy OBJECT-TYPE
        SYNTAX INTEGER
        UNITS  "KWH"
        ACCESS read-only
        STATUS mandatory
        DESCRIPTION
                "The energy of outlet."
        ::= { pduDevMonOutletSlave01PortEntry 12}

pduDevMonOutletSlave01PortEnergyTime OBJECT-TYPE
        SYNTAX DisplayString (SIZE(0..31))
        ACCESS read-only
        STATUS mandatory
        DESCRIPTION
                "The energy time of outlet."
        ::= { pduDevMonOutletSlave01PortEntry 13}


-- ===========================================================================
--
-- pduDevMonOutletSlave02
--
--  Slave02 Outlet Monoitor Group
--
-- ===========================================================================
pduDevMonOutletSlave02PortSize OBJECT-TYPE
        SYNTAX INTEGER
        ACCESS read-only
        STATUS mandatory
        DESCRIPTION
                "The port size of master."
        ::= { pduDevMonOutletSlave02 1}

-- ===========================================================================
--
-- pduDevMonOutletSlave02PortTable
--
--  Slave02 Outlet Port Monoitor Group
--
-- ===========================================================================
pduDevMonOutletSlave02PortTable OBJECT-TYPE
        SYNTAX SEQUENCE OF PduDevMonOutletSlave02PortEntry
        ACCESS not-accessible
        STATUS mandatory
        DESCRIPTION
                "Display the port information list of Slave02Port."
        ::= { pduDevMonOutletSlave02 2}

pduDevMonOutletSlave02PortEntry OBJECT-TYPE
        SYNTAX PduDevMonOutletSlave02PortEntry
        ACCESS not-accessible
        STATUS mandatory
        DESCRIPTION
                "Display the port information list of Slave02Port.."
        INDEX  { pduDevMonOutletSlave02PortIndex}
        ::= { pduDevMonOutletSlave02PortTable 1 }

PduDevMonOutletSlave02PortEntry ::=
        SEQUENCE {
                pduDevMonOutletSlave02PortIndex
                        INTEGER,
                pduDevMonOutletSlave02PortName
                        DisplayString,
                pduDevMonOutletSlave02PortBid
                        INTEGER,
                pduDevMonOutletSlave02PortFwType
                        INTEGER,
                pduDevMonOutletSlave02PortRlyState
                        INTEGER,
                pduDevMonOutletSlave02PortEvtStatus
                        INTEGER,
                pduDevMonOutletSlave02PortVolt
                        INTEGER,
                pduDevMonOutletSlave02PortCurrent
                        INTEGER,
                pduDevMonOutletSlave02PortPf
                        INTEGER,
                pduDevMonOutletSlave02PortActPower
                        INTEGER,
                pduDevMonOutletSlave02PortAppPower
                        INTEGER,
                pduDevMonOutletSlave02PortEnergy
                        INTEGER,
                pduDevMonOutletSlave02PortEnergyTime
                        DisplayString
        }

pduDevMonOutletSlave02PortIndex OBJECT-TYPE
        SYNTAX INTEGER (0..63)
        ACCESS read-only
        STATUS mandatory
        DESCRIPTION
                "The index to a outlet entry."
        ::= { pduDevMonOutletSlave02PortEntry 1 }

pduDevMonOutletSlave02PortName OBJECT-TYPE
        SYNTAX DisplayString (SIZE(0..31))
        ACCESS read-only
        STATUS mandatory
        DESCRIPTION
                "The name of outlet."
        ::= { pduDevMonOutletSlave02PortEntry 2 }

pduDevMonOutletSlave02PortBid OBJECT-TYPE
        SYNTAX INTEGER
        ACCESS read-only
        STATUS mandatory
        DESCRIPTION
                "The board id of outlet."
        ::= { pduDevMonOutletSlave02PortEntry 3}

pduDevMonOutletSlave02PortFwType OBJECT-TYPE
        SYNTAX INTEGER
        ACCESS read-only
        STATUS mandatory
        DESCRIPTION
                "The firmware type of outlet."
        ::= { pduDevMonOutletSlave02PortEntry 4}

pduDevMonOutletSlave02PortRlyState OBJECT-TYPE
        SYNTAX INTEGER {
                off(1),
                on(2)
                }
        ACCESS read-only
        STATUS mandatory
        DESCRIPTION
                "The relay state of outlet."
        ::= { pduDevMonOutletSlave02PortEntry 5}

pduDevMonOutletSlave02PortEvtStatus OBJECT-TYPE
        SYNTAX INTEGER {
                normal(1),
                warning(2),
                critical(3)
                }
        ACCESS read-only
        STATUS mandatory
        DESCRIPTION
                "The event status of outlet."
        ::= { pduDevMonOutletSlave02PortEntry 6}

pduDevMonOutletSlave02PortVolt OBJECT-TYPE
        SYNTAX INTEGER
        UNITS  "0.1V"
        ACCESS read-only
        STATUS mandatory
        DESCRIPTION
                "The voltage of outlet."
        ::= { pduDevMonOutletSlave02PortEntry 7}

pduDevMonOutletSlave02PortCurrent OBJECT-TYPE
        SYNTAX INTEGER
        UNITS  "0.01A"
        ACCESS read-only
        STATUS mandatory
        DESCRIPTION
                "The current of outlet."
        ::= { pduDevMonOutletSlave02PortEntry 8}

pduDevMonOutletSlave02PortPf OBJECT-TYPE
        SYNTAX INTEGER
        ACCESS read-only
        STATUS mandatory
        DESCRIPTION
                "The pf of outlet."
        ::= { pduDevMonOutletSlave02PortEntry 9}

pduDevMonOutletSlave02PortActPower OBJECT-TYPE
        SYNTAX INTEGER
        UNITS  "0.1W"
        ACCESS read-only
        STATUS mandatory
        DESCRIPTION
                "The act power of outlet."
        ::= { pduDevMonOutletSlave02PortEntry 10}

pduDevMonOutletSlave02PortAppPower OBJECT-TYPE
        SYNTAX INTEGER
        UNITS  "0.1VA"
        ACCESS read-only
        STATUS mandatory
        DESCRIPTION
                "The app power of outlet."
        ::= { pduDevMonOutletSlave02PortEntry 11}

pduDevMonOutletSlave02PortEnergy OBJECT-TYPE
        SYNTAX INTEGER
        UNITS  "KWH"
        ACCESS read-only
        STATUS mandatory
        DESCRIPTION
                "The energy of outlet."
        ::= { pduDevMonOutletSlave02PortEntry 12}

pduDevMonOutletSlave02PortEnergyTime OBJECT-TYPE
        SYNTAX DisplayString (SIZE(0..31))
        ACCESS read-only
        STATUS mandatory
        DESCRIPTION
                "The energy time of outlet."
        ::= { pduDevMonOutletSlave02PortEntry 13}


-- ===========================================================================
--
-- pduDevMonOutletSlave03
--
--  Slave03 Outlet Monoitor Group
--
-- ===========================================================================
pduDevMonOutletSlave03PortSize OBJECT-TYPE
        SYNTAX INTEGER
        ACCESS read-only
        STATUS mandatory
        DESCRIPTION
                "The port size of master."
        ::= { pduDevMonOutletSlave03 1}

-- ===========================================================================
--
-- pduDevMonOutletSlave03PortTable
--
--  Slave03 Outlet Port Monoitor Group
--
-- ===========================================================================
pduDevMonOutletSlave03PortTable OBJECT-TYPE
        SYNTAX SEQUENCE OF PduDevMonOutletSlave03PortEntry
        ACCESS not-accessible
        STATUS mandatory
        DESCRIPTION
                "Display the port information list of Slave03Port."
        ::= { pduDevMonOutletSlave03 2}

pduDevMonOutletSlave03PortEntry OBJECT-TYPE
        SYNTAX PduDevMonOutletSlave03PortEntry
        ACCESS not-accessible
        STATUS mandatory
        DESCRIPTION
                "Display the port information list of Slave03Port.."
        INDEX  { pduDevMonOutletSlave03PortIndex}
        ::= { pduDevMonOutletSlave03PortTable 1 }

PduDevMonOutletSlave03PortEntry ::=
        SEQUENCE {
                pduDevMonOutletSlave03PortIndex
                        INTEGER,
                pduDevMonOutletSlave03PortName
                        DisplayString,
                pduDevMonOutletSlave03PortBid
                        INTEGER,
                pduDevMonOutletSlave03PortFwType
                        INTEGER,
                pduDevMonOutletSlave03PortRlyState
                        INTEGER,
                pduDevMonOutletSlave03PortEvtStatus
                        INTEGER,
                pduDevMonOutletSlave03PortVolt
                        INTEGER,
                pduDevMonOutletSlave03PortCurrent
                        INTEGER,
                pduDevMonOutletSlave03PortPf
                        INTEGER,
                pduDevMonOutletSlave03PortActPower
                        INTEGER,
                pduDevMonOutletSlave03PortAppPower
                        INTEGER,
                pduDevMonOutletSlave03PortEnergy
                        INTEGER,
                pduDevMonOutletSlave03PortEnergyTime
                        DisplayString
        }

pduDevMonOutletSlave03PortIndex OBJECT-TYPE
        SYNTAX INTEGER (0..63)
        ACCESS read-only
        STATUS mandatory
        DESCRIPTION
                "The index to a outlet entry."
        ::= { pduDevMonOutletSlave03PortEntry 1 }

pduDevMonOutletSlave03PortName OBJECT-TYPE
        SYNTAX DisplayString (SIZE(0..31))
        ACCESS read-only
        STATUS mandatory
        DESCRIPTION
                "The name of outlet."
        ::= { pduDevMonOutletSlave03PortEntry 2 }

pduDevMonOutletSlave03PortBid OBJECT-TYPE
        SYNTAX INTEGER
        ACCESS read-only
        STATUS mandatory
        DESCRIPTION
                "The board id of outlet."
        ::= { pduDevMonOutletSlave03PortEntry 3}

pduDevMonOutletSlave03PortFwType OBJECT-TYPE
        SYNTAX INTEGER
        ACCESS read-only
        STATUS mandatory
        DESCRIPTION
                "The firmware type of outlet."
        ::= { pduDevMonOutletSlave03PortEntry 4}

pduDevMonOutletSlave03PortRlyState OBJECT-TYPE
        SYNTAX INTEGER {
                off(1),
                on(2)
                }
        ACCESS read-only
        STATUS mandatory
        DESCRIPTION
                "The relay state of outlet."
        ::= { pduDevMonOutletSlave03PortEntry 5}

pduDevMonOutletSlave03PortEvtStatus OBJECT-TYPE
        SYNTAX INTEGER {
                normal(1),
                warning(2),
                critical(3)
                }
        ACCESS read-only
        STATUS mandatory
        DESCRIPTION
                "The event status of outlet."
        ::= { pduDevMonOutletSlave03PortEntry 6}

pduDevMonOutletSlave03PortVolt OBJECT-TYPE
        SYNTAX INTEGER
        UNITS  "0.1V"
        ACCESS read-only
        STATUS mandatory
        DESCRIPTION
                "The voltage of outlet."
        ::= { pduDevMonOutletSlave03PortEntry 7}

pduDevMonOutletSlave03PortCurrent OBJECT-TYPE
        SYNTAX INTEGER
        UNITS  "0.01A"
        ACCESS read-only
        STATUS mandatory
        DESCRIPTION
                "The current of outlet."
        ::= { pduDevMonOutletSlave03PortEntry 8}

pduDevMonOutletSlave03PortPf OBJECT-TYPE
        SYNTAX INTEGER
        ACCESS read-only
        STATUS mandatory
        DESCRIPTION
                "The pf of outlet."
        ::= { pduDevMonOutletSlave03PortEntry 9}

pduDevMonOutletSlave03PortActPower OBJECT-TYPE
        SYNTAX INTEGER
        UNITS  "0.1W"
        ACCESS read-only
        STATUS mandatory
        DESCRIPTION
                "The act power of outlet."
        ::= { pduDevMonOutletSlave03PortEntry 10}

pduDevMonOutletSlave03PortAppPower OBJECT-TYPE
        SYNTAX INTEGER
        UNITS  "0.1VA"
        ACCESS read-only
        STATUS mandatory
        DESCRIPTION
                "The app power of outlet."
        ::= { pduDevMonOutletSlave03PortEntry 11}

pduDevMonOutletSlave03PortEnergy OBJECT-TYPE
        SYNTAX INTEGER
        UNITS  "KWH"
        ACCESS read-only
        STATUS mandatory
        DESCRIPTION
                "The energy of outlet."
        ::= { pduDevMonOutletSlave03PortEntry 12}

pduDevMonOutletSlave03PortEnergyTime OBJECT-TYPE
        SYNTAX DisplayString (SIZE(0..31))
        ACCESS read-only
        STATUS mandatory
        DESCRIPTION
                "The energy time of outlet."
        ::= { pduDevMonOutletSlave03PortEntry 13}


-- ===========================================================================
--
-- pduDevMonOutletSlave04
--
--  Slave04 Outlet Monoitor Group
--
-- ===========================================================================
pduDevMonOutletSlave04PortSize OBJECT-TYPE
        SYNTAX INTEGER
        ACCESS read-only
        STATUS mandatory
        DESCRIPTION
                "The port size of master."
        ::= { pduDevMonOutletSlave04 1}

-- ===========================================================================
--
-- pduDevMonOutletSlave04PortTable
--
--  Slave04 Outlet Port Monoitor Group
--
-- ===========================================================================
pduDevMonOutletSlave04PortTable OBJECT-TYPE
        SYNTAX SEQUENCE OF PduDevMonOutletSlave04PortEntry
        ACCESS not-accessible
        STATUS mandatory
        DESCRIPTION
                "Display the port information list of Slave04Port."
        ::= { pduDevMonOutletSlave04 2}

pduDevMonOutletSlave04PortEntry OBJECT-TYPE
        SYNTAX PduDevMonOutletSlave04PortEntry
        ACCESS not-accessible
        STATUS mandatory
        DESCRIPTION
                "Display the port information list of Slave04Port.."
        INDEX  { pduDevMonOutletSlave04PortIndex}
        ::= { pduDevMonOutletSlave04PortTable 1 }

PduDevMonOutletSlave04PortEntry ::=
        SEQUENCE {
                pduDevMonOutletSlave04PortIndex
                        INTEGER,
                pduDevMonOutletSlave04PortName
                        DisplayString,
                pduDevMonOutletSlave04PortBid
                        INTEGER,
                pduDevMonOutletSlave04PortFwType
                        INTEGER,
                pduDevMonOutletSlave04PortRlyState
                        INTEGER,
                pduDevMonOutletSlave04PortEvtStatus
                        INTEGER,
                pduDevMonOutletSlave04PortVolt
                        INTEGER,
                pduDevMonOutletSlave04PortCurrent
                        INTEGER,
                pduDevMonOutletSlave04PortPf
                        INTEGER,
                pduDevMonOutletSlave04PortActPower
                        INTEGER,
                pduDevMonOutletSlave04PortAppPower
                        INTEGER,
                pduDevMonOutletSlave04PortEnergy
                        INTEGER,
                pduDevMonOutletSlave04PortEnergyTime
                        DisplayString
        }

pduDevMonOutletSlave04PortIndex OBJECT-TYPE
        SYNTAX INTEGER (0..63)
        ACCESS read-only
        STATUS mandatory
        DESCRIPTION
                "The index to a outlet entry."
        ::= { pduDevMonOutletSlave04PortEntry 1 }

pduDevMonOutletSlave04PortName OBJECT-TYPE
        SYNTAX DisplayString (SIZE(0..31))
        ACCESS read-only
        STATUS mandatory
        DESCRIPTION
                "The name of outlet."
        ::= { pduDevMonOutletSlave04PortEntry 2 }

pduDevMonOutletSlave04PortBid OBJECT-TYPE
        SYNTAX INTEGER
        ACCESS read-only
        STATUS mandatory
        DESCRIPTION
                "The board id of outlet."
        ::= { pduDevMonOutletSlave04PortEntry 3}

pduDevMonOutletSlave04PortFwType OBJECT-TYPE
        SYNTAX INTEGER
        ACCESS read-only
        STATUS mandatory
        DESCRIPTION
                "The firmware type of outlet."
        ::= { pduDevMonOutletSlave04PortEntry 4}

pduDevMonOutletSlave04PortRlyState OBJECT-TYPE
        SYNTAX INTEGER {
                off(1),
                on(2)
                }
        ACCESS read-only
        STATUS mandatory
        DESCRIPTION
                "The relay state of outlet."
        ::= { pduDevMonOutletSlave04PortEntry 5}

pduDevMonOutletSlave04PortEvtStatus OBJECT-TYPE
        SYNTAX INTEGER {
                normal(1),
                warning(2),
                critical(3)
                }
        ACCESS read-only
        STATUS mandatory
        DESCRIPTION
                "The event status of outlet."
        ::= { pduDevMonOutletSlave04PortEntry 6}

pduDevMonOutletSlave04PortVolt OBJECT-TYPE
        SYNTAX INTEGER
        UNITS  "0.1V"
        ACCESS read-only
        STATUS mandatory
        DESCRIPTION
                "The voltage of outlet."
        ::= { pduDevMonOutletSlave04PortEntry 7}

pduDevMonOutletSlave04PortCurrent OBJECT-TYPE
        SYNTAX INTEGER
        UNITS  "0.01A"
        ACCESS read-only
        STATUS mandatory
        DESCRIPTION
                "The current of outlet."
        ::= { pduDevMonOutletSlave04PortEntry 8}

pduDevMonOutletSlave04PortPf OBJECT-TYPE
        SYNTAX INTEGER
        ACCESS read-only
        STATUS mandatory
        DESCRIPTION
                "The pf of outlet."
        ::= { pduDevMonOutletSlave04PortEntry 9}

pduDevMonOutletSlave04PortActPower OBJECT-TYPE
        SYNTAX INTEGER
        UNITS  "0.1W"
        ACCESS read-only
        STATUS mandatory
        DESCRIPTION
                "The act power of outlet."
        ::= { pduDevMonOutletSlave04PortEntry 10}

pduDevMonOutletSlave04PortAppPower OBJECT-TYPE
        SYNTAX INTEGER
        UNITS  "0.1VA"
        ACCESS read-only
        STATUS mandatory
        DESCRIPTION
                "The app power of outlet."
        ::= { pduDevMonOutletSlave04PortEntry 11}

pduDevMonOutletSlave04PortEnergy OBJECT-TYPE
        SYNTAX INTEGER
        UNITS  "KWH"
        ACCESS read-only
        STATUS mandatory
        DESCRIPTION
                "The energy of outlet."
        ::= { pduDevMonOutletSlave04PortEntry 12}

pduDevMonOutletSlave04PortEnergyTime OBJECT-TYPE
        SYNTAX DisplayString (SIZE(0..31))
        ACCESS read-only
        STATUS mandatory
        DESCRIPTION
                "The energy time of outlet."
        ::= { pduDevMonOutletSlave04PortEntry 13}


-- ===========================================================================
--
-- pduDevMonOutletSlave05
--
--  Slave05 Outlet Monoitor Group
--
-- ===========================================================================
pduDevMonOutletSlave05PortSize OBJECT-TYPE
        SYNTAX INTEGER
        ACCESS read-only
        STATUS mandatory
        DESCRIPTION
                "The port size of master."
        ::= { pduDevMonOutletSlave05 1}

-- ===========================================================================
--
-- pduDevMonOutletSlave05PortTable
--
--  Slave05 Outlet Port Monoitor Group
--
-- ===========================================================================
pduDevMonOutletSlave05PortTable OBJECT-TYPE
        SYNTAX SEQUENCE OF PduDevMonOutletSlave05PortEntry
        ACCESS not-accessible
        STATUS mandatory
        DESCRIPTION
                "Display the port information list of Slave05Port."
        ::= { pduDevMonOutletSlave05 2}

pduDevMonOutletSlave05PortEntry OBJECT-TYPE
        SYNTAX PduDevMonOutletSlave05PortEntry
        ACCESS not-accessible
        STATUS mandatory
        DESCRIPTION
                "Display the port information list of Slave05Port.."
        INDEX  { pduDevMonOutletSlave05PortIndex}
        ::= { pduDevMonOutletSlave05PortTable 1 }

PduDevMonOutletSlave05PortEntry ::=
        SEQUENCE {
                pduDevMonOutletSlave05PortIndex
                        INTEGER,
                pduDevMonOutletSlave05PortName
                        DisplayString,
                pduDevMonOutletSlave05PortBid
                        INTEGER,
                pduDevMonOutletSlave05PortFwType
                        INTEGER,
                pduDevMonOutletSlave05PortRlyState
                        INTEGER,
                pduDevMonOutletSlave05PortEvtStatus
                        INTEGER,
                pduDevMonOutletSlave05PortVolt
                        INTEGER,
                pduDevMonOutletSlave05PortCurrent
                        INTEGER,
                pduDevMonOutletSlave05PortPf
                        INTEGER,
                pduDevMonOutletSlave05PortActPower
                        INTEGER,
                pduDevMonOutletSlave05PortAppPower
                        INTEGER,
                pduDevMonOutletSlave05PortEnergy
                        INTEGER,
                pduDevMonOutletSlave05PortEnergyTime
                        DisplayString
        }

pduDevMonOutletSlave05PortIndex OBJECT-TYPE
        SYNTAX INTEGER (0..63)
        ACCESS read-only
        STATUS mandatory
        DESCRIPTION
                "The index to a outlet entry."
        ::= { pduDevMonOutletSlave05PortEntry 1 }

pduDevMonOutletSlave05PortName OBJECT-TYPE
        SYNTAX DisplayString (SIZE(0..31))
        ACCESS read-only
        STATUS mandatory
        DESCRIPTION
                "The name of outlet."
        ::= { pduDevMonOutletSlave05PortEntry 2 }

pduDevMonOutletSlave05PortBid OBJECT-TYPE
        SYNTAX INTEGER
        ACCESS read-only
        STATUS mandatory
        DESCRIPTION
                "The board id of outlet."
        ::= { pduDevMonOutletSlave05PortEntry 3}

pduDevMonOutletSlave05PortFwType OBJECT-TYPE
        SYNTAX INTEGER
        ACCESS read-only
        STATUS mandatory
        DESCRIPTION
                "The firmware type of outlet."
        ::= { pduDevMonOutletSlave05PortEntry 4}

pduDevMonOutletSlave05PortRlyState OBJECT-TYPE
        SYNTAX INTEGER {
                off(1),
                on(2)
                }
        ACCESS read-only
        STATUS mandatory
        DESCRIPTION
                "The relay state of outlet."
        ::= { pduDevMonOutletSlave05PortEntry 5}

pduDevMonOutletSlave05PortEvtStatus OBJECT-TYPE
        SYNTAX INTEGER {
                normal(1),
                warning(2),
                critical(3)
                }
        ACCESS read-only
        STATUS mandatory
        DESCRIPTION
                "The event status of outlet."
        ::= { pduDevMonOutletSlave05PortEntry 6}

pduDevMonOutletSlave05PortVolt OBJECT-TYPE
        SYNTAX INTEGER
        UNITS  "0.1V"
        ACCESS read-only
        STATUS mandatory
        DESCRIPTION
                "The voltage of outlet."
        ::= { pduDevMonOutletSlave05PortEntry 7}

pduDevMonOutletSlave05PortCurrent OBJECT-TYPE
        SYNTAX INTEGER
        UNITS  "0.01A"
        ACCESS read-only
        STATUS mandatory
        DESCRIPTION
                "The current of outlet."
        ::= { pduDevMonOutletSlave05PortEntry 8}

pduDevMonOutletSlave05PortPf OBJECT-TYPE
        SYNTAX INTEGER
        ACCESS read-only
        STATUS mandatory
        DESCRIPTION
                "The pf of outlet."
        ::= { pduDevMonOutletSlave05PortEntry 9}

pduDevMonOutletSlave05PortActPower OBJECT-TYPE
        SYNTAX INTEGER
        UNITS  "0.1W"
        ACCESS read-only
        STATUS mandatory
        DESCRIPTION
                "The act power of outlet."
        ::= { pduDevMonOutletSlave05PortEntry 10}

pduDevMonOutletSlave05PortAppPower OBJECT-TYPE
        SYNTAX INTEGER
        UNITS  "0.1VA"
        ACCESS read-only
        STATUS mandatory
        DESCRIPTION
                "The app power of outlet."
        ::= { pduDevMonOutletSlave05PortEntry 11}

pduDevMonOutletSlave05PortEnergy OBJECT-TYPE
        SYNTAX INTEGER
        UNITS  "KWH"
        ACCESS read-only
        STATUS mandatory
        DESCRIPTION
                "The energy of outlet."
        ::= { pduDevMonOutletSlave05PortEntry 12}

pduDevMonOutletSlave05PortEnergyTime OBJECT-TYPE
        SYNTAX DisplayString (SIZE(0..31))
        ACCESS read-only
        STATUS mandatory
        DESCRIPTION
                "The energy time of outlet."
        ::= { pduDevMonOutletSlave05PortEntry 13}


-- ===========================================================================
--
-- pduDevMonOutletSlave06
--
--  Slave06 Outlet Monoitor Group
--
-- ===========================================================================
pduDevMonOutletSlave06PortSize OBJECT-TYPE
        SYNTAX INTEGER
        ACCESS read-only
        STATUS mandatory
        DESCRIPTION
                "The port size of master."
        ::= { pduDevMonOutletSlave06 1}

-- ===========================================================================
--
-- pduDevMonOutletSlave06PortTable
--
--  Slave06 Outlet Port Monoitor Group
--
-- ===========================================================================
pduDevMonOutletSlave06PortTable OBJECT-TYPE
        SYNTAX SEQUENCE OF PduDevMonOutletSlave06PortEntry
        ACCESS not-accessible
        STATUS mandatory
        DESCRIPTION
                "Display the port information list of Slave06Port."
        ::= { pduDevMonOutletSlave06 2}

pduDevMonOutletSlave06PortEntry OBJECT-TYPE
        SYNTAX PduDevMonOutletSlave06PortEntry
        ACCESS not-accessible
        STATUS mandatory
        DESCRIPTION
                "Display the port information list of Slave06Port.."
        INDEX  { pduDevMonOutletSlave06PortIndex}
        ::= { pduDevMonOutletSlave06PortTable 1 }

PduDevMonOutletSlave06PortEntry ::=
        SEQUENCE {
                pduDevMonOutletSlave06PortIndex
                        INTEGER,
                pduDevMonOutletSlave06PortName
                        DisplayString,
                pduDevMonOutletSlave06PortBid
                        INTEGER,
                pduDevMonOutletSlave06PortFwType
                        INTEGER,
                pduDevMonOutletSlave06PortRlyState
                        INTEGER,
                pduDevMonOutletSlave06PortEvtStatus
                        INTEGER,
                pduDevMonOutletSlave06PortVolt
                        INTEGER,
                pduDevMonOutletSlave06PortCurrent
                        INTEGER,
                pduDevMonOutletSlave06PortPf
                        INTEGER,
                pduDevMonOutletSlave06PortActPower
                        INTEGER,
                pduDevMonOutletSlave06PortAppPower
                        INTEGER,
                pduDevMonOutletSlave06PortEnergy
                        INTEGER,
                pduDevMonOutletSlave06PortEnergyTime
                        DisplayString
        }

pduDevMonOutletSlave06PortIndex OBJECT-TYPE
        SYNTAX INTEGER (0..63)
        ACCESS read-only
        STATUS mandatory
        DESCRIPTION
                "The index to a outlet entry."
        ::= { pduDevMonOutletSlave06PortEntry 1 }

pduDevMonOutletSlave06PortName OBJECT-TYPE
        SYNTAX DisplayString (SIZE(0..31))
        ACCESS read-only
        STATUS mandatory
        DESCRIPTION
                "The name of outlet."
        ::= { pduDevMonOutletSlave06PortEntry 2 }

pduDevMonOutletSlave06PortBid OBJECT-TYPE
        SYNTAX INTEGER
        ACCESS read-only
        STATUS mandatory
        DESCRIPTION
                "The board id of outlet."
        ::= { pduDevMonOutletSlave06PortEntry 3}

pduDevMonOutletSlave06PortFwType OBJECT-TYPE
        SYNTAX INTEGER
        ACCESS read-only
        STATUS mandatory
        DESCRIPTION
                "The firmware type of outlet."
        ::= { pduDevMonOutletSlave06PortEntry 4}

pduDevMonOutletSlave06PortRlyState OBJECT-TYPE
        SYNTAX INTEGER {
                off(1),
                on(2)
                }
        ACCESS read-only
        STATUS mandatory
        DESCRIPTION
                "The relay state of outlet."
        ::= { pduDevMonOutletSlave06PortEntry 5}

pduDevMonOutletSlave06PortEvtStatus OBJECT-TYPE
        SYNTAX INTEGER {
                normal(1),
                warning(2),
                critical(3)
                }
        ACCESS read-only
        STATUS mandatory
        DESCRIPTION
                "The event status of outlet."
        ::= { pduDevMonOutletSlave06PortEntry 6}

pduDevMonOutletSlave06PortVolt OBJECT-TYPE
        SYNTAX INTEGER
        UNITS  "0.1V"
        ACCESS read-only
        STATUS mandatory
        DESCRIPTION
                "The voltage of outlet."
        ::= { pduDevMonOutletSlave06PortEntry 7}

pduDevMonOutletSlave06PortCurrent OBJECT-TYPE
        SYNTAX INTEGER
        UNITS  "0.01A"
        ACCESS read-only
        STATUS mandatory
        DESCRIPTION
                "The current of outlet."
        ::= { pduDevMonOutletSlave06PortEntry 8}

pduDevMonOutletSlave06PortPf OBJECT-TYPE
        SYNTAX INTEGER
        ACCESS read-only
        STATUS mandatory
        DESCRIPTION
                "The pf of outlet."
        ::= { pduDevMonOutletSlave06PortEntry 9}

pduDevMonOutletSlave06PortActPower OBJECT-TYPE
        SYNTAX INTEGER
        UNITS  "0.1W"
        ACCESS read-only
        STATUS mandatory
        DESCRIPTION
                "The act power of outlet."
        ::= { pduDevMonOutletSlave06PortEntry 10}

pduDevMonOutletSlave06PortAppPower OBJECT-TYPE
        SYNTAX INTEGER
        UNITS  "0.1VA"
        ACCESS read-only
        STATUS mandatory
        DESCRIPTION
                "The app power of outlet."
        ::= { pduDevMonOutletSlave06PortEntry 11}

pduDevMonOutletSlave06PortEnergy OBJECT-TYPE
        SYNTAX INTEGER
        UNITS  "KWH"
        ACCESS read-only
        STATUS mandatory
        DESCRIPTION
                "The energy of outlet."
        ::= { pduDevMonOutletSlave06PortEntry 12}

pduDevMonOutletSlave06PortEnergyTime OBJECT-TYPE
        SYNTAX DisplayString (SIZE(0..31))
        ACCESS read-only
        STATUS mandatory
        DESCRIPTION
                "The energy time of outlet."
        ::= { pduDevMonOutletSlave06PortEntry 13}


-- ===========================================================================
--
-- pduDevMonOutletSlave07
--
--  Slave07 Outlet Monoitor Group
--
-- ===========================================================================
pduDevMonOutletSlave07PortSize OBJECT-TYPE
        SYNTAX INTEGER
        ACCESS read-only
        STATUS mandatory
        DESCRIPTION
                "The port size of master."
        ::= { pduDevMonOutletSlave07 1}

-- ===========================================================================
--
-- pduDevMonOutletSlave07PortTable
--
--  Slave07 Outlet Port Monoitor Group
--
-- ===========================================================================
pduDevMonOutletSlave07PortTable OBJECT-TYPE
        SYNTAX SEQUENCE OF PduDevMonOutletSlave07PortEntry
        ACCESS not-accessible
        STATUS mandatory
        DESCRIPTION
                "Display the port information list of Slave07Port."
        ::= { pduDevMonOutletSlave07 2}

pduDevMonOutletSlave07PortEntry OBJECT-TYPE
        SYNTAX PduDevMonOutletSlave07PortEntry
        ACCESS not-accessible
        STATUS mandatory
        DESCRIPTION
                "Display the port information list of Slave07Port.."
        INDEX  { pduDevMonOutletSlave07PortIndex}
        ::= { pduDevMonOutletSlave07PortTable 1 }

PduDevMonOutletSlave07PortEntry ::=
        SEQUENCE {
                pduDevMonOutletSlave07PortIndex
                        INTEGER,
                pduDevMonOutletSlave07PortName
                        DisplayString,
                pduDevMonOutletSlave07PortBid
                        INTEGER,
                pduDevMonOutletSlave07PortFwType
                        INTEGER,
                pduDevMonOutletSlave07PortRlyState
                        INTEGER,
                pduDevMonOutletSlave07PortEvtStatus
                        INTEGER,
                pduDevMonOutletSlave07PortVolt
                        INTEGER,
                pduDevMonOutletSlave07PortCurrent
                        INTEGER,
                pduDevMonOutletSlave07PortPf
                        INTEGER,
                pduDevMonOutletSlave07PortActPower
                        INTEGER,
                pduDevMonOutletSlave07PortAppPower
                        INTEGER,
                pduDevMonOutletSlave07PortEnergy
                        INTEGER,
                pduDevMonOutletSlave07PortEnergyTime
                        DisplayString
        }

pduDevMonOutletSlave07PortIndex OBJECT-TYPE
        SYNTAX INTEGER (0..63)
        ACCESS read-only
        STATUS mandatory
        DESCRIPTION
                "The index to a outlet entry."
        ::= { pduDevMonOutletSlave07PortEntry 1 }

pduDevMonOutletSlave07PortName OBJECT-TYPE
        SYNTAX DisplayString (SIZE(0..31))
        ACCESS read-only
        STATUS mandatory
        DESCRIPTION
                "The name of outlet."
        ::= { pduDevMonOutletSlave07PortEntry 2 }

pduDevMonOutletSlave07PortBid OBJECT-TYPE
        SYNTAX INTEGER
        ACCESS read-only
        STATUS mandatory
        DESCRIPTION
                "The board id of outlet."
        ::= { pduDevMonOutletSlave07PortEntry 3}

pduDevMonOutletSlave07PortFwType OBJECT-TYPE
        SYNTAX INTEGER
        ACCESS read-only
        STATUS mandatory
        DESCRIPTION
                "The firmware type of outlet."
        ::= { pduDevMonOutletSlave07PortEntry 4}

pduDevMonOutletSlave07PortRlyState OBJECT-TYPE
        SYNTAX INTEGER {
                off(1),
                on(2)
                }
        ACCESS read-only
        STATUS mandatory
        DESCRIPTION
                "The relay state of outlet."
        ::= { pduDevMonOutletSlave07PortEntry 5}

pduDevMonOutletSlave07PortEvtStatus OBJECT-TYPE
        SYNTAX INTEGER {
                normal(1),
                warning(2),
                critical(3)
                }
        ACCESS read-only
        STATUS mandatory
        DESCRIPTION
                "The event status of outlet."
        ::= { pduDevMonOutletSlave07PortEntry 6}

pduDevMonOutletSlave07PortVolt OBJECT-TYPE
        SYNTAX INTEGER
        UNITS  "0.1V"
        ACCESS read-only
        STATUS mandatory
        DESCRIPTION
                "The voltage of outlet."
        ::= { pduDevMonOutletSlave07PortEntry 7}

pduDevMonOutletSlave07PortCurrent OBJECT-TYPE
        SYNTAX INTEGER
        UNITS  "0.01A"
        ACCESS read-only
        STATUS mandatory
        DESCRIPTION
                "The current of outlet."
        ::= { pduDevMonOutletSlave07PortEntry 8}

pduDevMonOutletSlave07PortPf OBJECT-TYPE
        SYNTAX INTEGER
        ACCESS read-only
        STATUS mandatory
        DESCRIPTION
                "The pf of outlet."
        ::= { pduDevMonOutletSlave07PortEntry 9}

pduDevMonOutletSlave07PortActPower OBJECT-TYPE
        SYNTAX INTEGER
        UNITS  "0.1W"
        ACCESS read-only
        STATUS mandatory
        DESCRIPTION
                "The act power of outlet."
        ::= { pduDevMonOutletSlave07PortEntry 10}

pduDevMonOutletSlave07PortAppPower OBJECT-TYPE
        SYNTAX INTEGER
        UNITS  "0.1VA"
        ACCESS read-only
        STATUS mandatory
        DESCRIPTION
                "The app power of outlet."
        ::= { pduDevMonOutletSlave07PortEntry 11}

pduDevMonOutletSlave07PortEnergy OBJECT-TYPE
        SYNTAX INTEGER
        UNITS  "KWH"
        ACCESS read-only
        STATUS mandatory
        DESCRIPTION
                "The energy of outlet."
        ::= { pduDevMonOutletSlave07PortEntry 12}

pduDevMonOutletSlave07PortEnergyTime OBJECT-TYPE
        SYNTAX DisplayString (SIZE(0..31))
        ACCESS read-only
        STATUS mandatory
        DESCRIPTION
                "The energy time of outlet."
        ::= { pduDevMonOutletSlave07PortEntry 13}


-- ===========================================================================
--
-- pduDevMonOutletSlave08
--
--  Slave08 Outlet Monoitor Group
--
-- ===========================================================================
pduDevMonOutletSlave08PortSize OBJECT-TYPE
        SYNTAX INTEGER
        ACCESS read-only
        STATUS mandatory
        DESCRIPTION
                "The port size of master."
        ::= { pduDevMonOutletSlave08 1}

-- ===========================================================================
--
-- pduDevMonOutletSlave08PortTable
--
--  Slave08 Outlet Port Monoitor Group
--
-- ===========================================================================
pduDevMonOutletSlave08PortTable OBJECT-TYPE
        SYNTAX SEQUENCE OF PduDevMonOutletSlave08PortEntry
        ACCESS not-accessible
        STATUS mandatory
        DESCRIPTION
                "Display the port information list of Slave08Port."
        ::= { pduDevMonOutletSlave08 2}

pduDevMonOutletSlave08PortEntry OBJECT-TYPE
        SYNTAX PduDevMonOutletSlave08PortEntry
        ACCESS not-accessible
        STATUS mandatory
        DESCRIPTION
                "Display the port information list of Slave08Port.."
        INDEX  { pduDevMonOutletSlave08PortIndex}
        ::= { pduDevMonOutletSlave08PortTable 1 }

PduDevMonOutletSlave08PortEntry ::=
        SEQUENCE {
                pduDevMonOutletSlave08PortIndex
                        INTEGER,
                pduDevMonOutletSlave08PortName
                        DisplayString,
                pduDevMonOutletSlave08PortBid
                        INTEGER,
                pduDevMonOutletSlave08PortFwType
                        INTEGER,
                pduDevMonOutletSlave08PortRlyState
                        INTEGER,
                pduDevMonOutletSlave08PortEvtStatus
                        INTEGER,
                pduDevMonOutletSlave08PortVolt
                        INTEGER,
                pduDevMonOutletSlave08PortCurrent
                        INTEGER,
                pduDevMonOutletSlave08PortPf
                        INTEGER,
                pduDevMonOutletSlave08PortActPower
                        INTEGER,
                pduDevMonOutletSlave08PortAppPower
                        INTEGER,
                pduDevMonOutletSlave08PortEnergy
                        INTEGER,
                pduDevMonOutletSlave08PortEnergyTime
                        DisplayString
        }

pduDevMonOutletSlave08PortIndex OBJECT-TYPE
        SYNTAX INTEGER (0..63)
        ACCESS read-only
        STATUS mandatory
        DESCRIPTION
                "The index to a outlet entry."
        ::= { pduDevMonOutletSlave08PortEntry 1 }

pduDevMonOutletSlave08PortName OBJECT-TYPE
        SYNTAX DisplayString (SIZE(0..31))
        ACCESS read-only
        STATUS mandatory
        DESCRIPTION
                "The name of outlet."
        ::= { pduDevMonOutletSlave08PortEntry 2 }

pduDevMonOutletSlave08PortBid OBJECT-TYPE
        SYNTAX INTEGER
        ACCESS read-only
        STATUS mandatory
        DESCRIPTION
                "The board id of outlet."
        ::= { pduDevMonOutletSlave08PortEntry 3}

pduDevMonOutletSlave08PortFwType OBJECT-TYPE
        SYNTAX INTEGER
        ACCESS read-only
        STATUS mandatory
        DESCRIPTION
                "The firmware type of outlet."
        ::= { pduDevMonOutletSlave08PortEntry 4}

pduDevMonOutletSlave08PortRlyState OBJECT-TYPE
        SYNTAX INTEGER {
                off(1),
                on(2)
                }
        ACCESS read-only
        STATUS mandatory
        DESCRIPTION
                "The relay state of outlet."
        ::= { pduDevMonOutletSlave08PortEntry 5}

pduDevMonOutletSlave08PortEvtStatus OBJECT-TYPE
        SYNTAX INTEGER {
                normal(1),
                warning(2),
                critical(3)
                }
        ACCESS read-only
        STATUS mandatory
        DESCRIPTION
                "The event status of outlet."
        ::= { pduDevMonOutletSlave08PortEntry 6}

pduDevMonOutletSlave08PortVolt OBJECT-TYPE
        SYNTAX INTEGER
        UNITS  "0.1V"
        ACCESS read-only
        STATUS mandatory
        DESCRIPTION
                "The voltage of outlet."
        ::= { pduDevMonOutletSlave08PortEntry 7}

pduDevMonOutletSlave08PortCurrent OBJECT-TYPE
        SYNTAX INTEGER
        UNITS  "0.01A"
        ACCESS read-only
        STATUS mandatory
        DESCRIPTION
                "The current of outlet."
        ::= { pduDevMonOutletSlave08PortEntry 8}

pduDevMonOutletSlave08PortPf OBJECT-TYPE
        SYNTAX INTEGER
        ACCESS read-only
        STATUS mandatory
        DESCRIPTION
                "The pf of outlet."
        ::= { pduDevMonOutletSlave08PortEntry 9}

pduDevMonOutletSlave08PortActPower OBJECT-TYPE
        SYNTAX INTEGER
        UNITS  "0.1W"
        ACCESS read-only
        STATUS mandatory
        DESCRIPTION
                "The act power of outlet."
        ::= { pduDevMonOutletSlave08PortEntry 10}

pduDevMonOutletSlave08PortAppPower OBJECT-TYPE
        SYNTAX INTEGER
        UNITS  "0.1VA"
        ACCESS read-only
        STATUS mandatory
        DESCRIPTION
                "The app power of outlet."
        ::= { pduDevMonOutletSlave08PortEntry 11}

pduDevMonOutletSlave08PortEnergy OBJECT-TYPE
        SYNTAX INTEGER
        UNITS  "KWH"
        ACCESS read-only
        STATUS mandatory
        DESCRIPTION
                "The energy of outlet."
        ::= { pduDevMonOutletSlave08PortEntry 12}

pduDevMonOutletSlave08PortEnergyTime OBJECT-TYPE
        SYNTAX DisplayString (SIZE(0..31))
        ACCESS read-only
        STATUS mandatory
        DESCRIPTION
                "The energy time of outlet."
        ::= { pduDevMonOutletSlave08PortEntry 13}


-- ===========================================================================
--
-- pduDevMonOutletSlave09
--
--  Slave09 Outlet Monoitor Group
--
-- ===========================================================================
pduDevMonOutletSlave09PortSize OBJECT-TYPE
        SYNTAX INTEGER
        ACCESS read-only
        STATUS mandatory
        DESCRIPTION
                "The port size of master."
        ::= { pduDevMonOutletSlave09 1}

-- ===========================================================================
--
-- pduDevMonOutletSlave09PortTable
--
--  Slave09 Outlet Port Monoitor Group
--
-- ===========================================================================
pduDevMonOutletSlave09PortTable OBJECT-TYPE
        SYNTAX SEQUENCE OF PduDevMonOutletSlave09PortEntry
        ACCESS not-accessible
        STATUS mandatory
        DESCRIPTION
                "Display the port information list of Slave09Port."
        ::= { pduDevMonOutletSlave09 2}

pduDevMonOutletSlave09PortEntry OBJECT-TYPE
        SYNTAX PduDevMonOutletSlave09PortEntry
        ACCESS not-accessible
        STATUS mandatory
        DESCRIPTION
                "Display the port information list of Slave09Port.."
        INDEX  { pduDevMonOutletSlave09PortIndex}
        ::= { pduDevMonOutletSlave09PortTable 1 }

PduDevMonOutletSlave09PortEntry ::=
        SEQUENCE {
                pduDevMonOutletSlave09PortIndex
                        INTEGER,
                pduDevMonOutletSlave09PortName
                        DisplayString,
                pduDevMonOutletSlave09PortBid
                        INTEGER,
                pduDevMonOutletSlave09PortFwType
                        INTEGER,
                pduDevMonOutletSlave09PortRlyState
                        INTEGER,
                pduDevMonOutletSlave09PortEvtStatus
                        INTEGER,
                pduDevMonOutletSlave09PortVolt
                        INTEGER,
                pduDevMonOutletSlave09PortCurrent
                        INTEGER,
                pduDevMonOutletSlave09PortPf
                        INTEGER,
                pduDevMonOutletSlave09PortActPower
                        INTEGER,
                pduDevMonOutletSlave09PortAppPower
                        INTEGER,
                pduDevMonOutletSlave09PortEnergy
                        INTEGER,
                pduDevMonOutletSlave09PortEnergyTime
                        DisplayString
        }

pduDevMonOutletSlave09PortIndex OBJECT-TYPE
        SYNTAX INTEGER (0..63)
        ACCESS read-only
        STATUS mandatory
        DESCRIPTION
                "The index to a outlet entry."
        ::= { pduDevMonOutletSlave09PortEntry 1 }

pduDevMonOutletSlave09PortName OBJECT-TYPE
        SYNTAX DisplayString (SIZE(0..31))
        ACCESS read-only
        STATUS mandatory
        DESCRIPTION
                "The name of outlet."
        ::= { pduDevMonOutletSlave09PortEntry 2 }

pduDevMonOutletSlave09PortBid OBJECT-TYPE
        SYNTAX INTEGER
        ACCESS read-only
        STATUS mandatory
        DESCRIPTION
                "The board id of outlet."
        ::= { pduDevMonOutletSlave09PortEntry 3}

pduDevMonOutletSlave09PortFwType OBJECT-TYPE
        SYNTAX INTEGER
        ACCESS read-only
        STATUS mandatory
        DESCRIPTION
                "The firmware type of outlet."
        ::= { pduDevMonOutletSlave09PortEntry 4}

pduDevMonOutletSlave09PortRlyState OBJECT-TYPE
        SYNTAX INTEGER {
                off(1),
                on(2)
                }
        ACCESS read-only
        STATUS mandatory
        DESCRIPTION
                "The relay state of outlet."
        ::= { pduDevMonOutletSlave09PortEntry 5}

pduDevMonOutletSlave09PortEvtStatus OBJECT-TYPE
        SYNTAX INTEGER {
                normal(1),
                warning(2),
                critical(3)
                }
        ACCESS read-only
        STATUS mandatory
        DESCRIPTION
                "The event status of outlet."
        ::= { pduDevMonOutletSlave09PortEntry 6}

pduDevMonOutletSlave09PortVolt OBJECT-TYPE
        SYNTAX INTEGER
        UNITS  "0.1V"
        ACCESS read-only
        STATUS mandatory
        DESCRIPTION
                "The voltage of outlet."
        ::= { pduDevMonOutletSlave09PortEntry 7}

pduDevMonOutletSlave09PortCurrent OBJECT-TYPE
        SYNTAX INTEGER
        UNITS  "0.01A"
        ACCESS read-only
        STATUS mandatory
        DESCRIPTION
                "The current of outlet."
        ::= { pduDevMonOutletSlave09PortEntry 8}

pduDevMonOutletSlave09PortPf OBJECT-TYPE
        SYNTAX INTEGER
        ACCESS read-only
        STATUS mandatory
        DESCRIPTION
                "The pf of outlet."
        ::= { pduDevMonOutletSlave09PortEntry 9}

pduDevMonOutletSlave09PortActPower OBJECT-TYPE
        SYNTAX INTEGER
        UNITS  "0.1W"
        ACCESS read-only
        STATUS mandatory
        DESCRIPTION
                "The act power of outlet."
        ::= { pduDevMonOutletSlave09PortEntry 10}

pduDevMonOutletSlave09PortAppPower OBJECT-TYPE
        SYNTAX INTEGER
        UNITS  "0.1VA"
        ACCESS read-only
        STATUS mandatory
        DESCRIPTION
                "The app power of outlet."
        ::= { pduDevMonOutletSlave09PortEntry 11}

pduDevMonOutletSlave09PortEnergy OBJECT-TYPE
        SYNTAX INTEGER
        UNITS  "KWH"
        ACCESS read-only
        STATUS mandatory
        DESCRIPTION
                "The energy of outlet."
        ::= { pduDevMonOutletSlave09PortEntry 12}

pduDevMonOutletSlave09PortEnergyTime OBJECT-TYPE
        SYNTAX DisplayString (SIZE(0..31))
        ACCESS read-only
        STATUS mandatory
        DESCRIPTION
                "The energy time of outlet."
        ::= { pduDevMonOutletSlave09PortEntry 13}


-- ===========================================================================
--
-- pduDevMonOutletSlave10
--
--  Slave10 Outlet Monoitor Group
--
-- ===========================================================================
pduDevMonOutletSlave10PortSize OBJECT-TYPE
        SYNTAX INTEGER
        ACCESS read-only
        STATUS mandatory
        DESCRIPTION
                "The port size of master."
        ::= { pduDevMonOutletSlave10 1}

-- ===========================================================================
--
-- pduDevMonOutletSlave10PortTable
--
--  Slave10 Outlet Port Monoitor Group
--
-- ===========================================================================
pduDevMonOutletSlave10PortTable OBJECT-TYPE
        SYNTAX SEQUENCE OF PduDevMonOutletSlave10PortEntry
        ACCESS not-accessible
        STATUS mandatory
        DESCRIPTION
                "Display the port information list of Slave10Port."
        ::= { pduDevMonOutletSlave10 2}

pduDevMonOutletSlave10PortEntry OBJECT-TYPE
        SYNTAX PduDevMonOutletSlave10PortEntry
        ACCESS not-accessible
        STATUS mandatory
        DESCRIPTION
                "Display the port information list of Slave10Port.."
        INDEX  { pduDevMonOutletSlave10PortIndex}
        ::= { pduDevMonOutletSlave10PortTable 1 }

PduDevMonOutletSlave10PortEntry ::=
        SEQUENCE {
                pduDevMonOutletSlave10PortIndex
                        INTEGER,
                pduDevMonOutletSlave10PortName
                        DisplayString,
                pduDevMonOutletSlave10PortBid
                        INTEGER,
                pduDevMonOutletSlave10PortFwType
                        INTEGER,
                pduDevMonOutletSlave10PortRlyState
                        INTEGER,
                pduDevMonOutletSlave10PortEvtStatus
                        INTEGER,
                pduDevMonOutletSlave10PortVolt
                        INTEGER,
                pduDevMonOutletSlave10PortCurrent
                        INTEGER,
                pduDevMonOutletSlave10PortPf
                        INTEGER,
                pduDevMonOutletSlave10PortActPower
                        INTEGER,
                pduDevMonOutletSlave10PortAppPower
                        INTEGER,
                pduDevMonOutletSlave10PortEnergy
                        INTEGER,
                pduDevMonOutletSlave10PortEnergyTime
                        DisplayString
        }

pduDevMonOutletSlave10PortIndex OBJECT-TYPE
        SYNTAX INTEGER (0..63)
        ACCESS read-only
        STATUS mandatory
        DESCRIPTION
                "The index to a outlet entry."
        ::= { pduDevMonOutletSlave10PortEntry 1 }

pduDevMonOutletSlave10PortName OBJECT-TYPE
        SYNTAX DisplayString (SIZE(0..31))
        ACCESS read-only
        STATUS mandatory
        DESCRIPTION
                "The name of outlet."
        ::= { pduDevMonOutletSlave10PortEntry 2 }

pduDevMonOutletSlave10PortBid OBJECT-TYPE
        SYNTAX INTEGER
        ACCESS read-only
        STATUS mandatory
        DESCRIPTION
                "The board id of outlet."
        ::= { pduDevMonOutletSlave10PortEntry 3}

pduDevMonOutletSlave10PortFwType OBJECT-TYPE
        SYNTAX INTEGER
        ACCESS read-only
        STATUS mandatory
        DESCRIPTION
                "The firmware type of outlet."
        ::= { pduDevMonOutletSlave10PortEntry 4}

pduDevMonOutletSlave10PortRlyState OBJECT-TYPE
        SYNTAX INTEGER {
                off(1),
                on(2)
                }
        ACCESS read-only
        STATUS mandatory
        DESCRIPTION
                "The relay state of outlet."
        ::= { pduDevMonOutletSlave10PortEntry 5}

pduDevMonOutletSlave10PortEvtStatus OBJECT-TYPE
        SYNTAX INTEGER {
                normal(1),
                warning(2),
                critical(3)
                }
        ACCESS read-only
        STATUS mandatory
        DESCRIPTION
                "The event status of outlet."
        ::= { pduDevMonOutletSlave10PortEntry 6}

pduDevMonOutletSlave10PortVolt OBJECT-TYPE
        SYNTAX INTEGER
        UNITS  "0.1V"
        ACCESS read-only
        STATUS mandatory
        DESCRIPTION
                "The voltage of outlet."
        ::= { pduDevMonOutletSlave10PortEntry 7}

pduDevMonOutletSlave10PortCurrent OBJECT-TYPE
        SYNTAX INTEGER
        UNITS  "0.01A"
        ACCESS read-only
        STATUS mandatory
        DESCRIPTION
                "The current of outlet."
        ::= { pduDevMonOutletSlave10PortEntry 8}

pduDevMonOutletSlave10PortPf OBJECT-TYPE
        SYNTAX INTEGER
        ACCESS read-only
        STATUS mandatory
        DESCRIPTION
                "The pf of outlet."
        ::= { pduDevMonOutletSlave10PortEntry 9}

pduDevMonOutletSlave10PortActPower OBJECT-TYPE
        SYNTAX INTEGER
        UNITS  "0.1W"
        ACCESS read-only
        STATUS mandatory
        DESCRIPTION
                "The act power of outlet."
        ::= { pduDevMonOutletSlave10PortEntry 10}

pduDevMonOutletSlave10PortAppPower OBJECT-TYPE
        SYNTAX INTEGER
        UNITS  "0.1VA"
        ACCESS read-only
        STATUS mandatory
        DESCRIPTION
                "The app power of outlet."
        ::= { pduDevMonOutletSlave10PortEntry 11}

pduDevMonOutletSlave10PortEnergy OBJECT-TYPE
        SYNTAX INTEGER
        UNITS  "KWH"
        ACCESS read-only
        STATUS mandatory
        DESCRIPTION
                "The energy of outlet."
        ::= { pduDevMonOutletSlave10PortEntry 12}

pduDevMonOutletSlave10PortEnergyTime OBJECT-TYPE
        SYNTAX DisplayString (SIZE(0..31))
        ACCESS read-only
        STATUS mandatory
        DESCRIPTION
                "The energy time of outlet."
        ::= { pduDevMonOutletSlave10PortEntry 13}


-- ===========================================================================
--
-- pduDevMonOutletSlave11
--
--  Slave11 Outlet Monoitor Group
--
-- ===========================================================================
pduDevMonOutletSlave11PortSize OBJECT-TYPE
        SYNTAX INTEGER
        ACCESS read-only
        STATUS mandatory
        DESCRIPTION
                "The port size of master."
        ::= { pduDevMonOutletSlave11 1}

-- ===========================================================================
--
-- pduDevMonOutletSlave11PortTable
--
--  Slave11 Outlet Port Monoitor Group
--
-- ===========================================================================
pduDevMonOutletSlave11PortTable OBJECT-TYPE
        SYNTAX SEQUENCE OF PduDevMonOutletSlave11PortEntry
        ACCESS not-accessible
        STATUS mandatory
        DESCRIPTION
                "Display the port information list of Slave11Port."
        ::= { pduDevMonOutletSlave11 2}

pduDevMonOutletSlave11PortEntry OBJECT-TYPE
        SYNTAX PduDevMonOutletSlave11PortEntry
        ACCESS not-accessible
        STATUS mandatory
        DESCRIPTION
                "Display the port information list of Slave11Port.."
        INDEX  { pduDevMonOutletSlave11PortIndex}
        ::= { pduDevMonOutletSlave11PortTable 1 }

PduDevMonOutletSlave11PortEntry ::=
        SEQUENCE {
                pduDevMonOutletSlave11PortIndex
                        INTEGER,
                pduDevMonOutletSlave11PortName
                        DisplayString,
                pduDevMonOutletSlave11PortBid
                        INTEGER,
                pduDevMonOutletSlave11PortFwType
                        INTEGER,
                pduDevMonOutletSlave11PortRlyState
                        INTEGER,
                pduDevMonOutletSlave11PortEvtStatus
                        INTEGER,
                pduDevMonOutletSlave11PortVolt
                        INTEGER,
                pduDevMonOutletSlave11PortCurrent
                        INTEGER,
                pduDevMonOutletSlave11PortPf
                        INTEGER,
                pduDevMonOutletSlave11PortActPower
                        INTEGER,
                pduDevMonOutletSlave11PortAppPower
                        INTEGER,
                pduDevMonOutletSlave11PortEnergy
                        INTEGER,
                pduDevMonOutletSlave11PortEnergyTime
                        DisplayString
        }

pduDevMonOutletSlave11PortIndex OBJECT-TYPE
        SYNTAX INTEGER (0..63)
        ACCESS read-only
        STATUS mandatory
        DESCRIPTION
                "The index to a outlet entry."
        ::= { pduDevMonOutletSlave11PortEntry 1 }

pduDevMonOutletSlave11PortName OBJECT-TYPE
        SYNTAX DisplayString (SIZE(0..31))
        ACCESS read-only
        STATUS mandatory
        DESCRIPTION
                "The name of outlet."
        ::= { pduDevMonOutletSlave11PortEntry 2 }

pduDevMonOutletSlave11PortBid OBJECT-TYPE
        SYNTAX INTEGER
        ACCESS read-only
        STATUS mandatory
        DESCRIPTION
                "The board id of outlet."
        ::= { pduDevMonOutletSlave11PortEntry 3}

pduDevMonOutletSlave11PortFwType OBJECT-TYPE
        SYNTAX INTEGER
        ACCESS read-only
        STATUS mandatory
        DESCRIPTION
                "The firmware type of outlet."
        ::= { pduDevMonOutletSlave11PortEntry 4}

pduDevMonOutletSlave11PortRlyState OBJECT-TYPE
        SYNTAX INTEGER {
                off(1),
                on(2)
                }
        ACCESS read-only
        STATUS mandatory
        DESCRIPTION
                "The relay state of outlet."
        ::= { pduDevMonOutletSlave11PortEntry 5}

pduDevMonOutletSlave11PortEvtStatus OBJECT-TYPE
        SYNTAX INTEGER {
                normal(1),
                warning(2),
                critical(3)
                }
        ACCESS read-only
        STATUS mandatory
        DESCRIPTION
                "The event status of outlet."
        ::= { pduDevMonOutletSlave11PortEntry 6}

pduDevMonOutletSlave11PortVolt OBJECT-TYPE
        SYNTAX INTEGER
        UNITS  "0.1V"
        ACCESS read-only
        STATUS mandatory
        DESCRIPTION
                "The voltage of outlet."
        ::= { pduDevMonOutletSlave11PortEntry 7}

pduDevMonOutletSlave11PortCurrent OBJECT-TYPE
        SYNTAX INTEGER
        UNITS  "0.01A"
        ACCESS read-only
        STATUS mandatory
        DESCRIPTION
                "The current of outlet."
        ::= { pduDevMonOutletSlave11PortEntry 8}

pduDevMonOutletSlave11PortPf OBJECT-TYPE
        SYNTAX INTEGER
        ACCESS read-only
        STATUS mandatory
        DESCRIPTION
                "The pf of outlet."
        ::= { pduDevMonOutletSlave11PortEntry 9}

pduDevMonOutletSlave11PortActPower OBJECT-TYPE
        SYNTAX INTEGER
        UNITS  "0.1W"
        ACCESS read-only
        STATUS mandatory
        DESCRIPTION
                "The act power of outlet."
        ::= { pduDevMonOutletSlave11PortEntry 10}

pduDevMonOutletSlave11PortAppPower OBJECT-TYPE
        SYNTAX INTEGER
        UNITS  "0.1VA"
        ACCESS read-only
        STATUS mandatory
        DESCRIPTION
                "The app power of outlet."
        ::= { pduDevMonOutletSlave11PortEntry 11}

pduDevMonOutletSlave11PortEnergy OBJECT-TYPE
        SYNTAX INTEGER
        UNITS  "KWH"
        ACCESS read-only
        STATUS mandatory
        DESCRIPTION
                "The energy of outlet."
        ::= { pduDevMonOutletSlave11PortEntry 12}

pduDevMonOutletSlave11PortEnergyTime OBJECT-TYPE
        SYNTAX DisplayString (SIZE(0..31))
        ACCESS read-only
        STATUS mandatory
        DESCRIPTION
                "The energy time of outlet."
        ::= { pduDevMonOutletSlave11PortEntry 13}


-- ===========================================================================
--
-- pduDevMonOutletSlave12
--
--  Slave12 Outlet Monoitor Group
--
-- ===========================================================================
pduDevMonOutletSlave12PortSize OBJECT-TYPE
        SYNTAX INTEGER
        ACCESS read-only
        STATUS mandatory
        DESCRIPTION
                "The port size of master."
        ::= { pduDevMonOutletSlave12 1}

-- ===========================================================================
--
-- pduDevMonOutletSlave12PortTable
--
--  Slave12 Outlet Port Monoitor Group
--
-- ===========================================================================
pduDevMonOutletSlave12PortTable OBJECT-TYPE
        SYNTAX SEQUENCE OF PduDevMonOutletSlave12PortEntry
        ACCESS not-accessible
        STATUS mandatory
        DESCRIPTION
                "Display the port information list of Slave12Port."
        ::= { pduDevMonOutletSlave12 2}

pduDevMonOutletSlave12PortEntry OBJECT-TYPE
        SYNTAX PduDevMonOutletSlave12PortEntry
        ACCESS not-accessible
        STATUS mandatory
        DESCRIPTION
                "Display the port information list of Slave12Port.."
        INDEX  { pduDevMonOutletSlave12PortIndex}
        ::= { pduDevMonOutletSlave12PortTable 1 }

PduDevMonOutletSlave12PortEntry ::=
        SEQUENCE {
                pduDevMonOutletSlave12PortIndex
                        INTEGER,
                pduDevMonOutletSlave12PortName
                        DisplayString,
                pduDevMonOutletSlave12PortBid
                        INTEGER,
                pduDevMonOutletSlave12PortFwType
                        INTEGER,
                pduDevMonOutletSlave12PortRlyState
                        INTEGER,
                pduDevMonOutletSlave12PortEvtStatus
                        INTEGER,
                pduDevMonOutletSlave12PortVolt
                        INTEGER,
                pduDevMonOutletSlave12PortCurrent
                        INTEGER,
                pduDevMonOutletSlave12PortPf
                        INTEGER,
                pduDevMonOutletSlave12PortActPower
                        INTEGER,
                pduDevMonOutletSlave12PortAppPower
                        INTEGER,
                pduDevMonOutletSlave12PortEnergy
                        INTEGER,
                pduDevMonOutletSlave12PortEnergyTime
                        DisplayString
        }

pduDevMonOutletSlave12PortIndex OBJECT-TYPE
        SYNTAX INTEGER (0..63)
        ACCESS read-only
        STATUS mandatory
        DESCRIPTION
                "The index to a outlet entry."
        ::= { pduDevMonOutletSlave12PortEntry 1 }

pduDevMonOutletSlave12PortName OBJECT-TYPE
        SYNTAX DisplayString (SIZE(0..31))
        ACCESS read-only
        STATUS mandatory
        DESCRIPTION
                "The name of outlet."
        ::= { pduDevMonOutletSlave12PortEntry 2 }

pduDevMonOutletSlave12PortBid OBJECT-TYPE
        SYNTAX INTEGER
        ACCESS read-only
        STATUS mandatory
        DESCRIPTION
                "The board id of outlet."
        ::= { pduDevMonOutletSlave12PortEntry 3}

pduDevMonOutletSlave12PortFwType OBJECT-TYPE
        SYNTAX INTEGER
        ACCESS read-only
        STATUS mandatory
        DESCRIPTION
                "The firmware type of outlet."
        ::= { pduDevMonOutletSlave12PortEntry 4}

pduDevMonOutletSlave12PortRlyState OBJECT-TYPE
        SYNTAX INTEGER {
                off(1),
                on(2)
                }
        ACCESS read-only
        STATUS mandatory
        DESCRIPTION
                "The relay state of outlet."
        ::= { pduDevMonOutletSlave12PortEntry 5}

pduDevMonOutletSlave12PortEvtStatus OBJECT-TYPE
        SYNTAX INTEGER {
                normal(1),
                warning(2),
                critical(3)
                }
        ACCESS read-only
        STATUS mandatory
        DESCRIPTION
                "The event status of outlet."
        ::= { pduDevMonOutletSlave12PortEntry 6}

pduDevMonOutletSlave12PortVolt OBJECT-TYPE
        SYNTAX INTEGER
        UNITS  "0.1V"
        ACCESS read-only
        STATUS mandatory
        DESCRIPTION
                "The voltage of outlet."
        ::= { pduDevMonOutletSlave12PortEntry 7}

pduDevMonOutletSlave12PortCurrent OBJECT-TYPE
        SYNTAX INTEGER
        UNITS  "0.01A"
        ACCESS read-only
        STATUS mandatory
        DESCRIPTION
                "The current of outlet."
        ::= { pduDevMonOutletSlave12PortEntry 8}

pduDevMonOutletSlave12PortPf OBJECT-TYPE
        SYNTAX INTEGER
        ACCESS read-only
        STATUS mandatory
        DESCRIPTION
                "The pf of outlet."
        ::= { pduDevMonOutletSlave12PortEntry 9}

pduDevMonOutletSlave12PortActPower OBJECT-TYPE
        SYNTAX INTEGER
        UNITS  "0.1W"
        ACCESS read-only
        STATUS mandatory
        DESCRIPTION
                "The act power of outlet."
        ::= { pduDevMonOutletSlave12PortEntry 10}

pduDevMonOutletSlave12PortAppPower OBJECT-TYPE
        SYNTAX INTEGER
        UNITS  "0.1VA"
        ACCESS read-only
        STATUS mandatory
        DESCRIPTION
                "The app power of outlet."
        ::= { pduDevMonOutletSlave12PortEntry 11}

pduDevMonOutletSlave12PortEnergy OBJECT-TYPE
        SYNTAX INTEGER
        UNITS  "KWH"
        ACCESS read-only
        STATUS mandatory
        DESCRIPTION
                "The energy of outlet."
        ::= { pduDevMonOutletSlave12PortEntry 12}

pduDevMonOutletSlave12PortEnergyTime OBJECT-TYPE
        SYNTAX DisplayString (SIZE(0..31))
        ACCESS read-only
        STATUS mandatory
        DESCRIPTION
                "The energy time of outlet."
        ::= { pduDevMonOutletSlave12PortEntry 13}


-- ===========================================================================
--
-- pduDevMonOutletSlave13
--
--  Slave13 Outlet Monoitor Group
--
-- ===========================================================================
pduDevMonOutletSlave13PortSize OBJECT-TYPE
        SYNTAX INTEGER
        ACCESS read-only
        STATUS mandatory
        DESCRIPTION
                "The port size of master."
        ::= { pduDevMonOutletSlave13 1}

-- ===========================================================================
--
-- pduDevMonOutletSlave13PortTable
--
--  Slave13 Outlet Port Monoitor Group
--
-- ===========================================================================
pduDevMonOutletSlave13PortTable OBJECT-TYPE
        SYNTAX SEQUENCE OF PduDevMonOutletSlave13PortEntry
        ACCESS not-accessible
        STATUS mandatory
        DESCRIPTION
                "Display the port information list of Slave13Port."
        ::= { pduDevMonOutletSlave13 2}

pduDevMonOutletSlave13PortEntry OBJECT-TYPE
        SYNTAX PduDevMonOutletSlave13PortEntry
        ACCESS not-accessible
        STATUS mandatory
        DESCRIPTION
                "Display the port information list of Slave13Port.."
        INDEX  { pduDevMonOutletSlave13PortIndex}
        ::= { pduDevMonOutletSlave13PortTable 1 }

PduDevMonOutletSlave13PortEntry ::=
        SEQUENCE {
                pduDevMonOutletSlave13PortIndex
                        INTEGER,
                pduDevMonOutletSlave13PortName
                        DisplayString,
                pduDevMonOutletSlave13PortBid
                        INTEGER,
                pduDevMonOutletSlave13PortFwType
                        INTEGER,
                pduDevMonOutletSlave13PortRlyState
                        INTEGER,
                pduDevMonOutletSlave13PortEvtStatus
                        INTEGER,
                pduDevMonOutletSlave13PortVolt
                        INTEGER,
                pduDevMonOutletSlave13PortCurrent
                        INTEGER,
                pduDevMonOutletSlave13PortPf
                        INTEGER,
                pduDevMonOutletSlave13PortActPower
                        INTEGER,
                pduDevMonOutletSlave13PortAppPower
                        INTEGER,
                pduDevMonOutletSlave13PortEnergy
                        INTEGER,
                pduDevMonOutletSlave13PortEnergyTime
                        DisplayString
        }

pduDevMonOutletSlave13PortIndex OBJECT-TYPE
        SYNTAX INTEGER (0..63)
        ACCESS read-only
        STATUS mandatory
        DESCRIPTION
                "The index to a outlet entry."
        ::= { pduDevMonOutletSlave13PortEntry 1 }

pduDevMonOutletSlave13PortName OBJECT-TYPE
        SYNTAX DisplayString (SIZE(0..31))
        ACCESS read-only
        STATUS mandatory
        DESCRIPTION
                "The name of outlet."
        ::= { pduDevMonOutletSlave13PortEntry 2 }

pduDevMonOutletSlave13PortBid OBJECT-TYPE
        SYNTAX INTEGER
        ACCESS read-only
        STATUS mandatory
        DESCRIPTION
                "The board id of outlet."
        ::= { pduDevMonOutletSlave13PortEntry 3}

pduDevMonOutletSlave13PortFwType OBJECT-TYPE
        SYNTAX INTEGER
        ACCESS read-only
        STATUS mandatory
        DESCRIPTION
                "The firmware type of outlet."
        ::= { pduDevMonOutletSlave13PortEntry 4}

pduDevMonOutletSlave13PortRlyState OBJECT-TYPE
        SYNTAX INTEGER {
                off(1),
                on(2)
                }
        ACCESS read-only
        STATUS mandatory
        DESCRIPTION
                "The relay state of outlet."
        ::= { pduDevMonOutletSlave13PortEntry 5}

pduDevMonOutletSlave13PortEvtStatus OBJECT-TYPE
        SYNTAX INTEGER {
                normal(1),
                warning(2),
                critical(3)
                }
        ACCESS read-only
        STATUS mandatory
        DESCRIPTION
                "The event status of outlet."
        ::= { pduDevMonOutletSlave13PortEntry 6}

pduDevMonOutletSlave13PortVolt OBJECT-TYPE
        SYNTAX INTEGER
        UNITS  "0.1V"
        ACCESS read-only
        STATUS mandatory
        DESCRIPTION
                "The voltage of outlet."
        ::= { pduDevMonOutletSlave13PortEntry 7}

pduDevMonOutletSlave13PortCurrent OBJECT-TYPE
        SYNTAX INTEGER
        UNITS  "0.01A"
        ACCESS read-only
        STATUS mandatory
        DESCRIPTION
                "The current of outlet."
        ::= { pduDevMonOutletSlave13PortEntry 8}

pduDevMonOutletSlave13PortPf OBJECT-TYPE
        SYNTAX INTEGER
        ACCESS read-only
        STATUS mandatory
        DESCRIPTION
                "The pf of outlet."
        ::= { pduDevMonOutletSlave13PortEntry 9}

pduDevMonOutletSlave13PortActPower OBJECT-TYPE
        SYNTAX INTEGER
        UNITS  "0.1W"
        ACCESS read-only
        STATUS mandatory
        DESCRIPTION
                "The act power of outlet."
        ::= { pduDevMonOutletSlave13PortEntry 10}

pduDevMonOutletSlave13PortAppPower OBJECT-TYPE
        SYNTAX INTEGER
        UNITS  "0.1VA"
        ACCESS read-only
        STATUS mandatory
        DESCRIPTION
                "The app power of outlet."
        ::= { pduDevMonOutletSlave13PortEntry 11}

pduDevMonOutletSlave13PortEnergy OBJECT-TYPE
        SYNTAX INTEGER
        UNITS  "KWH"
        ACCESS read-only
        STATUS mandatory
        DESCRIPTION
                "The energy of outlet."
        ::= { pduDevMonOutletSlave13PortEntry 12}

pduDevMonOutletSlave13PortEnergyTime OBJECT-TYPE
        SYNTAX DisplayString (SIZE(0..31))
        ACCESS read-only
        STATUS mandatory
        DESCRIPTION
                "The energy time of outlet."
        ::= { pduDevMonOutletSlave13PortEntry 13}


-- ===========================================================================
--
-- pduDevMonOutletSlave14
--
--  Slave14 Outlet Monoitor Group
--
-- ===========================================================================
pduDevMonOutletSlave14PortSize OBJECT-TYPE
        SYNTAX INTEGER
        ACCESS read-only
        STATUS mandatory
        DESCRIPTION
                "The port size of master."
        ::= { pduDevMonOutletSlave14 1}

-- ===========================================================================
--
-- pduDevMonOutletSlave14PortTable
--
--  Slave14 Outlet Port Monoitor Group
--
-- ===========================================================================
pduDevMonOutletSlave14PortTable OBJECT-TYPE
        SYNTAX SEQUENCE OF PduDevMonOutletSlave14PortEntry
        ACCESS not-accessible
        STATUS mandatory
        DESCRIPTION
                "Display the port information list of Slave14Port."
        ::= { pduDevMonOutletSlave14 2}

pduDevMonOutletSlave14PortEntry OBJECT-TYPE
        SYNTAX PduDevMonOutletSlave14PortEntry
        ACCESS not-accessible
        STATUS mandatory
        DESCRIPTION
                "Display the port information list of Slave14Port.."
        INDEX  { pduDevMonOutletSlave14PortIndex}
        ::= { pduDevMonOutletSlave14PortTable 1 }

PduDevMonOutletSlave14PortEntry ::=
        SEQUENCE {
                pduDevMonOutletSlave14PortIndex
                        INTEGER,
                pduDevMonOutletSlave14PortName
                        DisplayString,
                pduDevMonOutletSlave14PortBid
                        INTEGER,
                pduDevMonOutletSlave14PortFwType
                        INTEGER,
                pduDevMonOutletSlave14PortRlyState
                        INTEGER,
                pduDevMonOutletSlave14PortEvtStatus
                        INTEGER,
                pduDevMonOutletSlave14PortVolt
                        INTEGER,
                pduDevMonOutletSlave14PortCurrent
                        INTEGER,
                pduDevMonOutletSlave14PortPf
                        INTEGER,
                pduDevMonOutletSlave14PortActPower
                        INTEGER,
                pduDevMonOutletSlave14PortAppPower
                        INTEGER,
                pduDevMonOutletSlave14PortEnergy
                        INTEGER,
                pduDevMonOutletSlave14PortEnergyTime
                        DisplayString
        }

pduDevMonOutletSlave14PortIndex OBJECT-TYPE
        SYNTAX INTEGER (0..63)
        ACCESS read-only
        STATUS mandatory
        DESCRIPTION
                "The index to a outlet entry."
        ::= { pduDevMonOutletSlave14PortEntry 1 }

pduDevMonOutletSlave14PortName OBJECT-TYPE
        SYNTAX DisplayString (SIZE(0..31))
        ACCESS read-only
        STATUS mandatory
        DESCRIPTION
                "The name of outlet."
        ::= { pduDevMonOutletSlave14PortEntry 2 }

pduDevMonOutletSlave14PortBid OBJECT-TYPE
        SYNTAX INTEGER
        ACCESS read-only
        STATUS mandatory
        DESCRIPTION
                "The board id of outlet."
        ::= { pduDevMonOutletSlave14PortEntry 3}

pduDevMonOutletSlave14PortFwType OBJECT-TYPE
        SYNTAX INTEGER
        ACCESS read-only
        STATUS mandatory
        DESCRIPTION
                "The firmware type of outlet."
        ::= { pduDevMonOutletSlave14PortEntry 4}

pduDevMonOutletSlave14PortRlyState OBJECT-TYPE
        SYNTAX INTEGER {
                off(1),
                on(2)
                }
        ACCESS read-only
        STATUS mandatory
        DESCRIPTION
                "The relay state of outlet."
        ::= { pduDevMonOutletSlave14PortEntry 5}

pduDevMonOutletSlave14PortEvtStatus OBJECT-TYPE
        SYNTAX INTEGER {
                normal(1),
                warning(2),
                critical(3)
                }
        ACCESS read-only
        STATUS mandatory
        DESCRIPTION
                "The event status of outlet."
        ::= { pduDevMonOutletSlave14PortEntry 6}

pduDevMonOutletSlave14PortVolt OBJECT-TYPE
        SYNTAX INTEGER
        UNITS  "0.1V"
        ACCESS read-only
        STATUS mandatory
        DESCRIPTION
                "The voltage of outlet."
        ::= { pduDevMonOutletSlave14PortEntry 7}

pduDevMonOutletSlave14PortCurrent OBJECT-TYPE
        SYNTAX INTEGER
        UNITS  "0.01A"
        ACCESS read-only
        STATUS mandatory
        DESCRIPTION
                "The current of outlet."
        ::= { pduDevMonOutletSlave14PortEntry 8}

pduDevMonOutletSlave14PortPf OBJECT-TYPE
        SYNTAX INTEGER
        ACCESS read-only
        STATUS mandatory
        DESCRIPTION
                "The pf of outlet."
        ::= { pduDevMonOutletSlave14PortEntry 9}

pduDevMonOutletSlave14PortActPower OBJECT-TYPE
        SYNTAX INTEGER
        UNITS  "0.1W"
        ACCESS read-only
        STATUS mandatory
        DESCRIPTION
                "The act power of outlet."
        ::= { pduDevMonOutletSlave14PortEntry 10}

pduDevMonOutletSlave14PortAppPower OBJECT-TYPE
        SYNTAX INTEGER
        UNITS  "0.1VA"
        ACCESS read-only
        STATUS mandatory
        DESCRIPTION
                "The app power of outlet."
        ::= { pduDevMonOutletSlave14PortEntry 11}

pduDevMonOutletSlave14PortEnergy OBJECT-TYPE
        SYNTAX INTEGER
        UNITS  "KWH"
        ACCESS read-only
        STATUS mandatory
        DESCRIPTION
                "The energy of outlet."
        ::= { pduDevMonOutletSlave14PortEntry 12}

pduDevMonOutletSlave14PortEnergyTime OBJECT-TYPE
        SYNTAX DisplayString (SIZE(0..31))
        ACCESS read-only
        STATUS mandatory
        DESCRIPTION
                "The energy time of outlet."
        ::= { pduDevMonOutletSlave14PortEntry 13}


-- ===========================================================================
--
-- pduDevMonOutletSlave15
--
--  Slave15 Outlet Monoitor Group
--
-- ===========================================================================
pduDevMonOutletSlave15PortSize OBJECT-TYPE
        SYNTAX INTEGER
        ACCESS read-only
        STATUS mandatory
        DESCRIPTION
                "The port size of master."
        ::= { pduDevMonOutletSlave15 1}

-- ===========================================================================
--
-- pduDevMonOutletSlave15PortTable
--
--  Slave15 Outlet Port Monoitor Group
--
-- ===========================================================================
pduDevMonOutletSlave15PortTable OBJECT-TYPE
        SYNTAX SEQUENCE OF PduDevMonOutletSlave15PortEntry
        ACCESS not-accessible
        STATUS mandatory
        DESCRIPTION
                "Display the port information list of Slave15Port."
        ::= { pduDevMonOutletSlave15 2}

pduDevMonOutletSlave15PortEntry OBJECT-TYPE
        SYNTAX PduDevMonOutletSlave15PortEntry
        ACCESS not-accessible
        STATUS mandatory
        DESCRIPTION
                "Display the port information list of Slave15Port.."
        INDEX  { pduDevMonOutletSlave15PortIndex}
        ::= { pduDevMonOutletSlave15PortTable 1 }

PduDevMonOutletSlave15PortEntry ::=
        SEQUENCE {
                pduDevMonOutletSlave15PortIndex
                        INTEGER,
                pduDevMonOutletSlave15PortName
                        DisplayString,
                pduDevMonOutletSlave15PortBid
                        INTEGER,
                pduDevMonOutletSlave15PortFwType
                        INTEGER,
                pduDevMonOutletSlave15PortRlyState
                        INTEGER,
                pduDevMonOutletSlave15PortEvtStatus
                        INTEGER,
                pduDevMonOutletSlave15PortVolt
                        INTEGER,
                pduDevMonOutletSlave15PortCurrent
                        INTEGER,
                pduDevMonOutletSlave15PortPf
                        INTEGER,
                pduDevMonOutletSlave15PortActPower
                        INTEGER,
                pduDevMonOutletSlave15PortAppPower
                        INTEGER,
                pduDevMonOutletSlave15PortEnergy
                        INTEGER,
                pduDevMonOutletSlave15PortEnergyTime
                        DisplayString
        }

pduDevMonOutletSlave15PortIndex OBJECT-TYPE
        SYNTAX INTEGER (0..63)
        ACCESS read-only
        STATUS mandatory
        DESCRIPTION
                "The index to a outlet entry."
        ::= { pduDevMonOutletSlave15PortEntry 1 }

pduDevMonOutletSlave15PortName OBJECT-TYPE
        SYNTAX DisplayString (SIZE(0..31))
        ACCESS read-only
        STATUS mandatory
        DESCRIPTION
                "The name of outlet."
        ::= { pduDevMonOutletSlave15PortEntry 2 }

pduDevMonOutletSlave15PortBid OBJECT-TYPE
        SYNTAX INTEGER
        ACCESS read-only
        STATUS mandatory
        DESCRIPTION
                "The board id of outlet."
        ::= { pduDevMonOutletSlave15PortEntry 3}

pduDevMonOutletSlave15PortFwType OBJECT-TYPE
        SYNTAX INTEGER
        ACCESS read-only
        STATUS mandatory
        DESCRIPTION
                "The firmware type of outlet."
        ::= { pduDevMonOutletSlave15PortEntry 4}

pduDevMonOutletSlave15PortRlyState OBJECT-TYPE
        SYNTAX INTEGER {
                off(1),
                on(2)
                }
        ACCESS read-only
        STATUS mandatory
        DESCRIPTION
                "The relay state of outlet."
        ::= { pduDevMonOutletSlave15PortEntry 5}

pduDevMonOutletSlave15PortEvtStatus OBJECT-TYPE
        SYNTAX INTEGER {
                normal(1),
                warning(2),
                critical(3)
                }
        ACCESS read-only
        STATUS mandatory
        DESCRIPTION
                "The event status of outlet."
        ::= { pduDevMonOutletSlave15PortEntry 6}

pduDevMonOutletSlave15PortVolt OBJECT-TYPE
        SYNTAX INTEGER
        UNITS  "0.1V"
        ACCESS read-only
        STATUS mandatory
        DESCRIPTION
                "The voltage of outlet."
        ::= { pduDevMonOutletSlave15PortEntry 7}

pduDevMonOutletSlave15PortCurrent OBJECT-TYPE
        SYNTAX INTEGER
        UNITS  "0.01A"
        ACCESS read-only
        STATUS mandatory
        DESCRIPTION
                "The current of outlet."
        ::= { pduDevMonOutletSlave15PortEntry 8}

pduDevMonOutletSlave15PortPf OBJECT-TYPE
        SYNTAX INTEGER
        ACCESS read-only
        STATUS mandatory
        DESCRIPTION
                "The pf of outlet."
        ::= { pduDevMonOutletSlave15PortEntry 9}

pduDevMonOutletSlave15PortActPower OBJECT-TYPE
        SYNTAX INTEGER
        UNITS  "0.1W"
        ACCESS read-only
        STATUS mandatory
        DESCRIPTION
                "The act power of outlet."
        ::= { pduDevMonOutletSlave15PortEntry 10}

pduDevMonOutletSlave15PortAppPower OBJECT-TYPE
        SYNTAX INTEGER
        UNITS  "0.1VA"
        ACCESS read-only
        STATUS mandatory
        DESCRIPTION
                "The app power of outlet."
        ::= { pduDevMonOutletSlave15PortEntry 11}

pduDevMonOutletSlave15PortEnergy OBJECT-TYPE
        SYNTAX INTEGER
        UNITS  "KWH"
        ACCESS read-only
        STATUS mandatory
        DESCRIPTION
                "The energy of outlet."
        ::= { pduDevMonOutletSlave15PortEntry 12}

pduDevMonOutletSlave15PortEnergyTime OBJECT-TYPE
        SYNTAX DisplayString (SIZE(0..31))
        ACCESS read-only
        STATUS mandatory
        DESCRIPTION
                "The energy time of outlet."
        ::= { pduDevMonOutletSlave15PortEntry 13}


-- ===========================================================================
--
-- pduDevMonEmd
--
--  Emd Device Monoitor Group
--
-- ===========================================================================
pduDevMonEmdMaster      OBJECT IDENTIFIER ::= { pduDevMonEmd 1 }
pduDevMonEmdSlave01     OBJECT IDENTIFIER ::= { pduDevMonEmd 2 }
pduDevMonEmdSlave02     OBJECT IDENTIFIER ::= { pduDevMonEmd 3 }
pduDevMonEmdSlave03     OBJECT IDENTIFIER ::= { pduDevMonEmd 4 }
pduDevMonEmdSlave04     OBJECT IDENTIFIER ::= { pduDevMonEmd 5 }
pduDevMonEmdSlave05     OBJECT IDENTIFIER ::= { pduDevMonEmd 6 }
pduDevMonEmdSlave06     OBJECT IDENTIFIER ::= { pduDevMonEmd 7 }
pduDevMonEmdSlave07     OBJECT IDENTIFIER ::= { pduDevMonEmd 8 }
pduDevMonEmdSlave08     OBJECT IDENTIFIER ::= { pduDevMonEmd 9 }
pduDevMonEmdSlave09     OBJECT IDENTIFIER ::= { pduDevMonEmd 10 }
pduDevMonEmdSlave10     OBJECT IDENTIFIER ::= { pduDevMonEmd 11 }
pduDevMonEmdSlave11     OBJECT IDENTIFIER ::= { pduDevMonEmd 12 }
pduDevMonEmdSlave12     OBJECT IDENTIFIER ::= { pduDevMonEmd 13 }
pduDevMonEmdSlave13     OBJECT IDENTIFIER ::= { pduDevMonEmd 14 }
pduDevMonEmdSlave14     OBJECT IDENTIFIER ::= { pduDevMonEmd 15 }
pduDevMonEmdSlave15     OBJECT IDENTIFIER ::= { pduDevMonEmd 16 }


-- ===========================================================================
--
-- pduDevMonEmdMaster
--
--  Master Emd Monoitor Group
--
-- ===========================================================================
pduDevMonEmdMasterTable OBJECT-TYPE
        SYNTAX SEQUENCE OF PduDevMonEmdMasterEntry
        ACCESS not-accessible
        STATUS mandatory
        DESCRIPTION
                "Display a list of the emd information of master."
        ::= { pduDevMonEmdMaster 1}

pduDevMonEmdMasterEntry OBJECT-TYPE
        SYNTAX PduDevMonEmdMasterEntry
        ACCESS not-accessible
        STATUS mandatory
        DESCRIPTION
                "Display a list of the emd information of master."
        INDEX  { pduDevMonEmdMasterIndex}
        ::= { pduDevMonEmdMasterTable 1 }

PduDevMonEmdMasterEntry ::=
        SEQUENCE {
                pduDevMonEmdMasterIndex
                        INTEGER,
                pduDevMonEmdMasterValid
                        INTEGER,
                pduDevMonEmdMasterType
                        INTEGER,
                pduDevMonEmdMasterName
                        DisplayString,
                pduDevMonEmdMasterTempName
                        DisplayString,
                pduDevMonEmdMasterHumiName
                        DisplayString,
                pduDevMonEmdMasterAlarm1Name
                        DisplayString,
                pduDevMonEmdMasterAlarm2Name
                        DisplayString,
                pduDevMonEmdMasterTemp
                        INTEGER,
                pduDevMonEmdMasterHumi
                        INTEGER,
                pduDevMonEmdMasterTempSt
                        INTEGER,
                pduDevMonEmdMasterHumiSt
                        INTEGER,
                pduDevMonEmdMasterAlarm1
                        INTEGER,
                pduDevMonEmdMasterAlarm2
                        INTEGER
        }

pduDevMonEmdMasterIndex OBJECT-TYPE
        SYNTAX INTEGER (0..7)
        ACCESS read-only
        STATUS mandatory
        DESCRIPTION
                "The index to a emd entry."
        ::= { pduDevMonEmdMasterEntry 1 }

pduDevMonEmdMasterValid OBJECT-TYPE
        SYNTAX INTEGER {
                offline(1),
                online(2)
                }
        ACCESS read-only
        STATUS mandatory
        DESCRIPTION
                "The online status of emd."
        ::= { pduDevMonEmdMasterEntry 2}


pduDevMonEmdMasterType OBJECT-TYPE
        SYNTAX INTEGER
        ACCESS read-only
        STATUS mandatory
        DESCRIPTION
                "The type of emd."
        ::= { pduDevMonEmdMasterEntry 3}

pduDevMonEmdMasterName OBJECT-TYPE
        SYNTAX DisplayString (SIZE(0..31))
        ACCESS read-only
        STATUS mandatory
        DESCRIPTION
                "The name of emd."
        ::= { pduDevMonEmdMasterEntry 4}

pduDevMonEmdMasterTempName OBJECT-TYPE
        SYNTAX DisplayString (SIZE(0..31))
        ACCESS read-only
        STATUS mandatory
        DESCRIPTION
                "The name of emd temperature."
        ::= { pduDevMonEmdMasterEntry 5}

pduDevMonEmdMasterHumiName OBJECT-TYPE
        SYNTAX DisplayString (SIZE(0..31))
        ACCESS read-only
        STATUS mandatory
        DESCRIPTION
                "The name of emd humidity."
        ::= { pduDevMonEmdMasterEntry 6}

pduDevMonEmdMasterAlarm1Name OBJECT-TYPE
        SYNTAX DisplayString (SIZE(0..31))
        ACCESS read-only
        STATUS mandatory
        DESCRIPTION
                "The name of emd alarm-1."
        ::= { pduDevMonEmdMasterEntry 7}

pduDevMonEmdMasterAlarm2Name OBJECT-TYPE
        SYNTAX DisplayString (SIZE(0..31))
        ACCESS read-only
        STATUS mandatory
        DESCRIPTION
                "The name of emd alarm-2."
        ::= { pduDevMonEmdMasterEntry 8}

pduDevMonEmdMasterTemp OBJECT-TYPE
        SYNTAX INTEGER
        UNITS  "0.1degC"
        ACCESS read-only
        STATUS mandatory
        DESCRIPTION
                "The temperature of emd."
        ::= { pduDevMonEmdMasterEntry 9}

pduDevMonEmdMasterHumi OBJECT-TYPE
        SYNTAX INTEGER
        UNITS  "0.1%"
        ACCESS read-only
        STATUS mandatory
        DESCRIPTION
                "The humidity of emd."
        ::= { pduDevMonEmdMasterEntry 10}

pduDevMonEmdMasterTempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdMasterEntry 11}

pduDevMonEmdMasterHumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdMasterEntry 12}

pduDevMonEmdMasterAlarm1 OBJECT-TYPE
        SYNTAX INTEGER {
                normal(1),
                alarm(2)
                }
        ACCESS read-only
        STATUS mandatory
        DESCRIPTION
                "The alarm-1 of emd."
        ::= { pduDevMonEmdMasterEntry 13}

pduDevMonEmdMasterAlarm2 OBJECT-TYPE
        SYNTAX INTEGER {
                normal(1),
                alarm(2)
                }
        ACCESS read-only
        STATUS mandatory
        DESCRIPTION
                "The alarm-2 of emd."
        ::= { pduDevMonEmdMasterEntry 14}


-- ===========================================================================
--
-- pduDevMonEmdSlave02
--
--  Slave01 Emd Monoitor Group
--
-- ===========================================================================
pduDevMonEmdSlave01Table OBJECT-TYPE
        SYNTAX SEQUENCE OF PduDevMonEmdSlave01Entry
        ACCESS not-accessible
        STATUS mandatory
        DESCRIPTION
                "Display a list of the emd information of Slave01."
        ::= { pduDevMonEmdSlave01 1}

pduDevMonEmdSlave01Entry OBJECT-TYPE
        SYNTAX PduDevMonEmdSlave01Entry
        ACCESS not-accessible
        STATUS mandatory
        DESCRIPTION
                "Display a list of the emd information of Slave01."
        INDEX  { pduDevMonEmdSlave01Index}
        ::= { pduDevMonEmdSlave01Table 1 }

PduDevMonEmdSlave01Entry ::=
        SEQUENCE {
                pduDevMonEmdSlave01Index
                        INTEGER,
                pduDevMonEmdSlave01Valid
                        INTEGER,
                pduDevMonEmdSlave01Type
                        INTEGER,
                pduDevMonEmdSlave01Name
                        DisplayString,
                pduDevMonEmdSlave01TempName
                        DisplayString,
                pduDevMonEmdSlave01HumiName
                        DisplayString,
                pduDevMonEmdSlave01Alarm1Name
                        DisplayString,
                pduDevMonEmdSlave01Alarm2Name
                        DisplayString,
                pduDevMonEmdSlave01Temp
                        INTEGER,
                pduDevMonEmdSlave01Humi
                        INTEGER,
                pduDevMonEmdSlave01TempSt
                        INTEGER,
                pduDevMonEmdSlave01HumiSt
                        INTEGER,
                pduDevMonEmdSlave01Alarm1
                        INTEGER,
                pduDevMonEmdSlave01Alarm2
                        INTEGER
        }

pduDevMonEmdSlave01Index OBJECT-TYPE
        SYNTAX INTEGER (0..7)
        ACCESS read-only
        STATUS mandatory
        DESCRIPTION
                "The index to a emd entry."
        ::= { pduDevMonEmdSlave01Entry 1 }

pduDevMonEmdSlave01Valid OBJECT-TYPE
        SYNTAX INTEGER {
                offline(1),
                online(2)
                }
        ACCESS read-only
        STATUS mandatory
        DESCRIPTION
                "The online status of emd."
        ::= { pduDevMonEmdSlave01Entry 2}


pduDevMonEmdSlave01Type OBJECT-TYPE
        SYNTAX INTEGER
        ACCESS read-only
        STATUS mandatory
        DESCRIPTION
                "The type of emd."
        ::= { pduDevMonEmdSlave01Entry 3}

pduDevMonEmdSlave01Name OBJECT-TYPE
        SYNTAX DisplayString (SIZE(0..31))
        ACCESS read-only
        STATUS mandatory
        DESCRIPTION
                "The name of emd."
        ::= { pduDevMonEmdSlave01Entry 4}

pduDevMonEmdSlave01TempName OBJECT-TYPE
        SYNTAX DisplayString (SIZE(0..31))
        ACCESS read-only
        STATUS mandatory
        DESCRIPTION
                "The name of emd temperature."
        ::= { pduDevMonEmdSlave01Entry 5}

pduDevMonEmdSlave01HumiName OBJECT-TYPE
        SYNTAX DisplayString (SIZE(0..31))
        ACCESS read-only
        STATUS mandatory
        DESCRIPTION
                "The name of emd humidity."
        ::= { pduDevMonEmdSlave01Entry 6}

pduDevMonEmdSlave01Alarm1Name OBJECT-TYPE
        SYNTAX DisplayString (SIZE(0..31))
        ACCESS read-only
        STATUS mandatory
        DESCRIPTION
                "The name of emd alarm-1."
        ::= { pduDevMonEmdSlave01Entry 7}

pduDevMonEmdSlave01Alarm2Name OBJECT-TYPE
        SYNTAX DisplayString (SIZE(0..31))
        ACCESS read-only
        STATUS mandatory
        DESCRIPTION
                "The name of emd alarm-2."
        ::= { pduDevMonEmdSlave01Entry 8}

pduDevMonEmdSlave01Temp OBJECT-TYPE
        SYNTAX INTEGER
        UNITS  "0.1degC"
        ACCESS read-only
        STATUS mandatory
        DESCRIPTION
                "The temperature of emd."
        ::= { pduDevMonEmdSlave01Entry 9}

pduDevMonEmdSlave01Humi OBJECT-TYPE
        SYNTAX INTEGER
        UNITS  "0.1%"
        ACCESS read-only
        STATUS mandatory
        DESCRIPTION
                "The humidity of emd."
        ::= { pduDevMonEmdSlave01Entry 10}

pduDevMonEmdSlave01TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave01Entry 11}

pduDevMonEmdSlave01HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave01Entry 12}

pduDevMonEmdSlave01Alarm1 OBJECT-TYPE
        SYNTAX INTEGER {
                normal(1),
                alarm(2)
                }
        ACCESS read-only
        STATUS mandatory
        DESCRIPTION
                "The alarm-1 of emd."
        ::= { pduDevMonEmdSlave01Entry 13}

pduDevMonEmdSlave01Alarm2 OBJECT-TYPE
        SYNTAX INTEGER {
                normal(1),
                alarm(2)
                }
        ACCESS read-only
        STATUS mandatory
        DESCRIPTION
                "The alarm-2 of emd."
        ::= { pduDevMonEmdSlave01Entry 14}


-- ===========================================================================
--
-- pduDevMonEmdSlave02
--
--  Slave02 Emd Monoitor Group
--
-- ===========================================================================
pduDevMonEmdSlave02Table OBJECT-TYPE
        SYNTAX SEQUENCE OF PduDevMonEmdSlave02Entry
        ACCESS not-accessible
        STATUS mandatory
        DESCRIPTION
                "Display a list of the emd information of Slave02."
        ::= { pduDevMonEmdSlave02 1}

pduDevMonEmdSlave02Entry OBJECT-TYPE
        SYNTAX PduDevMonEmdSlave02Entry
        ACCESS not-accessible
        STATUS mandatory
        DESCRIPTION
                "Display a list of the emd information of Slave02."
        INDEX  { pduDevMonEmdSlave02Index}
        ::= { pduDevMonEmdSlave02Table 1 }

PduDevMonEmdSlave02Entry ::=
        SEQUENCE {
                pduDevMonEmdSlave02Index
                        INTEGER,
                pduDevMonEmdSlave02Valid
                        INTEGER,
                pduDevMonEmdSlave02Type
                        INTEGER,
                pduDevMonEmdSlave02Name
                        DisplayString,
                pduDevMonEmdSlave02TempName
                        DisplayString,
                pduDevMonEmdSlave02HumiName
                        DisplayString,
                pduDevMonEmdSlave02Alarm1Name
                        DisplayString,
                pduDevMonEmdSlave02Alarm2Name
                        DisplayString,
                pduDevMonEmdSlave02Temp
                        INTEGER,
                pduDevMonEmdSlave02Humi
                        INTEGER,
                pduDevMonEmdSlave02TempSt
                        INTEGER,
                pduDevMonEmdSlave02HumiSt
                        INTEGER,
                pduDevMonEmdSlave02Alarm1
                        INTEGER,
                pduDevMonEmdSlave02Alarm2
                        INTEGER
        }

pduDevMonEmdSlave02Index OBJECT-TYPE
        SYNTAX INTEGER (0..7)
        ACCESS read-only
        STATUS mandatory
        DESCRIPTION
                "The index to a emd entry."
        ::= { pduDevMonEmdSlave02Entry 1 }

pduDevMonEmdSlave02Valid OBJECT-TYPE
        SYNTAX INTEGER {
                offline(1),
                online(2)
                }
        ACCESS read-only
        STATUS mandatory
        DESCRIPTION
                "The online status of emd."
        ::= { pduDevMonEmdSlave02Entry 2}


pduDevMonEmdSlave02Type OBJECT-TYPE
        SYNTAX INTEGER
        ACCESS read-only
        STATUS mandatory
        DESCRIPTION
                "The type of emd."
        ::= { pduDevMonEmdSlave02Entry 3}

pduDevMonEmdSlave02Name OBJECT-TYPE
        SYNTAX DisplayString (SIZE(0..31))
        ACCESS read-only
        STATUS mandatory
        DESCRIPTION
                "The name of emd."
        ::= { pduDevMonEmdSlave02Entry 4}

pduDevMonEmdSlave02TempName OBJECT-TYPE
        SYNTAX DisplayString (SIZE(0..31))
        ACCESS read-only
        STATUS mandatory
        DESCRIPTION
                "The name of emd temperature."
        ::= { pduDevMonEmdSlave02Entry 5}

pduDevMonEmdSlave02HumiName OBJECT-TYPE
        SYNTAX DisplayString (SIZE(0..31))
        ACCESS read-only
        STATUS mandatory
        DESCRIPTION
                "The name of emd humidity."
        ::= { pduDevMonEmdSlave02Entry 6}

pduDevMonEmdSlave02Alarm1Name OBJECT-TYPE
        SYNTAX DisplayString (SIZE(0..31))
        ACCESS read-only
        STATUS mandatory
        DESCRIPTION
                "The name of emd alarm-1."
        ::= { pduDevMonEmdSlave02Entry 7}

pduDevMonEmdSlave02Alarm2Name OBJECT-TYPE
        SYNTAX DisplayString (SIZE(0..31))
        ACCESS read-only
        STATUS mandatory
        DESCRIPTION
                "The name of emd alarm-2."
        ::= { pduDevMonEmdSlave02Entry 8}

pduDevMonEmdSlave02Temp OBJECT-TYPE
        SYNTAX INTEGER
        UNITS  "0.1degC"
        ACCESS read-only
        STATUS mandatory
        DESCRIPTION
                "The temperature of emd."
        ::= { pduDevMonEmdSlave02Entry 9}

pduDevMonEmdSlave02Humi OBJECT-TYPE
        SYNTAX INTEGER
        UNITS  "0.1%"
        ACCESS read-only
        STATUS mandatory
        DESCRIPTION
                "The humidity of emd."
        ::= { pduDevMonEmdSlave02Entry 10}

pduDevMonEmdSlave02TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave02Entry 11}

pduDevMonEmdSlave02HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave02Entry 12}

pduDevMonEmdSlave02Alarm1 OBJECT-TYPE
        SYNTAX INTEGER {
                normal(1),
                alarm(2)
                }
        ACCESS read-only
        STATUS mandatory
        DESCRIPTION
                "The alarm-1 of emd."
        ::= { pduDevMonEmdSlave02Entry 13}

pduDevMonEmdSlave02Alarm2 OBJECT-TYPE
        SYNTAX INTEGER {
                normal(1),
                alarm(2)
                }
        ACCESS read-only
        STATUS mandatory
        DESCRIPTION
                "The alarm-2 of emd."
        ::= { pduDevMonEmdSlave02Entry 14}


-- ===========================================================================
--
-- pduDevMonEmdSlave03
--
--  Slave03 Emd Monoitor Group
--
-- ===========================================================================
pduDevMonEmdSlave03Table OBJECT-TYPE
        SYNTAX SEQUENCE OF PduDevMonEmdSlave03Entry
        ACCESS not-accessible
        STATUS mandatory
        DESCRIPTION
                "Display a list of the emd information of Slave03."
        ::= { pduDevMonEmdSlave03 1}

pduDevMonEmdSlave03Entry OBJECT-TYPE
        SYNTAX PduDevMonEmdSlave03Entry
        ACCESS not-accessible
        STATUS mandatory
        DESCRIPTION
                "Display a list of the emd information of Slave03."
        INDEX  { pduDevMonEmdSlave03Index}
        ::= { pduDevMonEmdSlave03Table 1 }

PduDevMonEmdSlave03Entry ::=
        SEQUENCE {
                pduDevMonEmdSlave03Index
                        INTEGER,
                pduDevMonEmdSlave03Valid
                        INTEGER,
                pduDevMonEmdSlave03Type
                        INTEGER,
                pduDevMonEmdSlave03Name
                        DisplayString,
                pduDevMonEmdSlave03TempName
                        DisplayString,
                pduDevMonEmdSlave03HumiName
                        DisplayString,
                pduDevMonEmdSlave03Alarm1Name
                        DisplayString,
                pduDevMonEmdSlave03Alarm2Name
                        DisplayString,
                pduDevMonEmdSlave03Temp
                        INTEGER,
                pduDevMonEmdSlave03Humi
                        INTEGER,
                pduDevMonEmdSlave03TempSt
                        INTEGER,
                pduDevMonEmdSlave03HumiSt
                        INTEGER,
                pduDevMonEmdSlave03Alarm1
                        INTEGER,
                pduDevMonEmdSlave03Alarm2
                        INTEGER
        }

pduDevMonEmdSlave03Index OBJECT-TYPE
        SYNTAX INTEGER (0..7)
        ACCESS read-only
        STATUS mandatory
        DESCRIPTION
                "The index to a emd entry."
        ::= { pduDevMonEmdSlave03Entry 1 }

pduDevMonEmdSlave03Valid OBJECT-TYPE
        SYNTAX INTEGER {
                offline(1),
                online(2)
                }
        ACCESS read-only
        STATUS mandatory
        DESCRIPTION
                "The online status of emd."
        ::= { pduDevMonEmdSlave03Entry 2}


pduDevMonEmdSlave03Type OBJECT-TYPE
        SYNTAX INTEGER
        ACCESS read-only
        STATUS mandatory
        DESCRIPTION
                "The type of emd."
        ::= { pduDevMonEmdSlave03Entry 3}

pduDevMonEmdSlave03Name OBJECT-TYPE
        SYNTAX DisplayString (SIZE(0..31))
        ACCESS read-only
        STATUS mandatory
        DESCRIPTION
                "The name of emd."
        ::= { pduDevMonEmdSlave03Entry 4}

pduDevMonEmdSlave03TempName OBJECT-TYPE
        SYNTAX DisplayString (SIZE(0..31))
        ACCESS read-only
        STATUS mandatory
        DESCRIPTION
                "The name of emd temperature."
        ::= { pduDevMonEmdSlave03Entry 5}

pduDevMonEmdSlave03HumiName OBJECT-TYPE
        SYNTAX DisplayString (SIZE(0..31))
        ACCESS read-only
        STATUS mandatory
        DESCRIPTION
                "The name of emd humidity."
        ::= { pduDevMonEmdSlave03Entry 6}

pduDevMonEmdSlave03Alarm1Name OBJECT-TYPE
        SYNTAX DisplayString (SIZE(0..31))
        ACCESS read-only
        STATUS mandatory
        DESCRIPTION
                "The name of emd alarm-1."
        ::= { pduDevMonEmdSlave03Entry 7}

pduDevMonEmdSlave03Alarm2Name OBJECT-TYPE
        SYNTAX DisplayString (SIZE(0..31))
        ACCESS read-only
        STATUS mandatory
        DESCRIPTION
                "The name of emd alarm-2."
        ::= { pduDevMonEmdSlave03Entry 8}

pduDevMonEmdSlave03Temp OBJECT-TYPE
        SYNTAX INTEGER
        UNITS  "0.1degC"
        ACCESS read-only
        STATUS mandatory
        DESCRIPTION
                "The temperature of emd."
        ::= { pduDevMonEmdSlave03Entry 9}

pduDevMonEmdSlave03Humi OBJECT-TYPE
        SYNTAX INTEGER
        UNITS  "0.1%"
        ACCESS read-only
        STATUS mandatory
        DESCRIPTION
                "The humidity of emd."
        ::= { pduDevMonEmdSlave03Entry 10}

pduDevMonEmdSlave03TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave03Entry 11}

pduDevMonEmdSlave03HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave03Entry 12}

pduDevMonEmdSlave03Alarm1 OBJECT-TYPE
        SYNTAX INTEGER {
                normal(1),
                alarm(2)
                }
        ACCESS read-only
        STATUS mandatory
        DESCRIPTION
                "The alarm-1 of emd."
        ::= { pduDevMonEmdSlave03Entry 13}

pduDevMonEmdSlave03Alarm2 OBJECT-TYPE
        SYNTAX INTEGER {
                normal(1),
                alarm(2)
                }
        ACCESS read-only
        STATUS mandatory
        DESCRIPTION
                "The alarm-2 of emd."
        ::= { pduDevMonEmdSlave03Entry 14}


-- ===========================================================================
--
-- pduDevMonEmdSlave04
--
--  Slave04 Emd Monoitor Group
--
-- ===========================================================================
pduDevMonEmdSlave04Table OBJECT-TYPE
        SYNTAX SEQUENCE OF PduDevMonEmdSlave04Entry
        ACCESS not-accessible
        STATUS mandatory
        DESCRIPTION
                "Display a list of the emd information of Slave04."
        ::= { pduDevMonEmdSlave04 1}

pduDevMonEmdSlave04Entry OBJECT-TYPE
        SYNTAX PduDevMonEmdSlave04Entry
        ACCESS not-accessible
        STATUS mandatory
        DESCRIPTION
                "Display a list of the emd information of Slave04."
        INDEX  { pduDevMonEmdSlave04Index}
        ::= { pduDevMonEmdSlave04Table 1 }

PduDevMonEmdSlave04Entry ::=
        SEQUENCE {
                pduDevMonEmdSlave04Index
                        INTEGER,
                pduDevMonEmdSlave04Valid
                        INTEGER,
                pduDevMonEmdSlave04Type
                        INTEGER,
                pduDevMonEmdSlave04Name
                        DisplayString,
                pduDevMonEmdSlave04TempName
                        DisplayString,
                pduDevMonEmdSlave04HumiName
                        DisplayString,
                pduDevMonEmdSlave04Alarm1Name
                        DisplayString,
                pduDevMonEmdSlave04Alarm2Name
                        DisplayString,
                pduDevMonEmdSlave04Temp
                        INTEGER,
                pduDevMonEmdSlave04Humi
                        INTEGER,
                pduDevMonEmdSlave04TempSt
                        INTEGER,
                pduDevMonEmdSlave04HumiSt
                        INTEGER,
                pduDevMonEmdSlave04Alarm1
                        INTEGER,
                pduDevMonEmdSlave04Alarm2
                        INTEGER
        }

pduDevMonEmdSlave04Index OBJECT-TYPE
        SYNTAX INTEGER (0..7)
        ACCESS read-only
        STATUS mandatory
        DESCRIPTION
                "The index to a emd entry."
        ::= { pduDevMonEmdSlave04Entry 1 }

pduDevMonEmdSlave04Valid OBJECT-TYPE
        SYNTAX INTEGER {
                offline(1),
                online(2)
                }
        ACCESS read-only
        STATUS mandatory
        DESCRIPTION
                "The online status of emd."
        ::= { pduDevMonEmdSlave04Entry 2}


pduDevMonEmdSlave04Type OBJECT-TYPE
        SYNTAX INTEGER
        ACCESS read-only
        STATUS mandatory
        DESCRIPTION
                "The type of emd."
        ::= { pduDevMonEmdSlave04Entry 3}

pduDevMonEmdSlave04Name OBJECT-TYPE
        SYNTAX DisplayString (SIZE(0..31))
        ACCESS read-only
        STATUS mandatory
        DESCRIPTION
                "The name of emd."
        ::= { pduDevMonEmdSlave04Entry 4}

pduDevMonEmdSlave04TempName OBJECT-TYPE
        SYNTAX DisplayString (SIZE(0..31))
        ACCESS read-only
        STATUS mandatory
        DESCRIPTION
                "The name of emd temperature."
        ::= { pduDevMonEmdSlave04Entry 5}

pduDevMonEmdSlave04HumiName OBJECT-TYPE
        SYNTAX DisplayString (SIZE(0..31))
        ACCESS read-only
        STATUS mandatory
        DESCRIPTION
                "The name of emd humidity."
        ::= { pduDevMonEmdSlave04Entry 6}

pduDevMonEmdSlave04Alarm1Name OBJECT-TYPE
        SYNTAX DisplayString (SIZE(0..31))
        ACCESS read-only
        STATUS mandatory
        DESCRIPTION
                "The name of emd alarm-1."
        ::= { pduDevMonEmdSlave04Entry 7}

pduDevMonEmdSlave04Alarm2Name OBJECT-TYPE
        SYNTAX DisplayString (SIZE(0..31))
        ACCESS read-only
        STATUS mandatory
        DESCRIPTION
                "The name of emd alarm-2."
        ::= { pduDevMonEmdSlave04Entry 8}

pduDevMonEmdSlave04Temp OBJECT-TYPE
        SYNTAX INTEGER
        UNITS  "0.1degC"
        ACCESS read-only
        STATUS mandatory
        DESCRIPTION
                "The temperature of emd."
        ::= { pduDevMonEmdSlave04Entry 9}

pduDevMonEmdSlave04Humi OBJECT-TYPE
        SYNTAX INTEGER
        UNITS  "0.1%"
        ACCESS read-only
        STATUS mandatory
        DESCRIPTION
                "The humidity of emd."
        ::= { pduDevMonEmdSlave04Entry 10}

pduDevMonEmdSlave04TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave04Entry 11}

pduDevMonEmdSlave04HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave04Entry 12}

pduDevMonEmdSlave04Alarm1 OBJECT-TYPE
        SYNTAX INTEGER {
                normal(1),
                alarm(2)
                }
        ACCESS read-only
        STATUS mandatory
        DESCRIPTION
                "The alarm-1 of emd."
        ::= { pduDevMonEmdSlave04Entry 13}

pduDevMonEmdSlave04Alarm2 OBJECT-TYPE
        SYNTAX INTEGER {
                normal(1),
                alarm(2)
                }
        ACCESS read-only
        STATUS mandatory
        DESCRIPTION
                "The alarm-2 of emd."
        ::= { pduDevMonEmdSlave04Entry 14}


-- ===========================================================================
--
-- pduDevMonEmdSlave05
--
--  Slave05 Emd Monoitor Group
--
-- ===========================================================================
pduDevMonEmdSlave05Table OBJECT-TYPE
        SYNTAX SEQUENCE OF PduDevMonEmdSlave05Entry
        ACCESS not-accessible
        STATUS mandatory
        DESCRIPTION
                "Display a list of the emd information of Slave05."
        ::= { pduDevMonEmdSlave05 1}

pduDevMonEmdSlave05Entry OBJECT-TYPE
        SYNTAX PduDevMonEmdSlave05Entry
        ACCESS not-accessible
        STATUS mandatory
        DESCRIPTION
                "Display a list of the emd information of Slave05."
        INDEX  { pduDevMonEmdSlave05Index}
        ::= { pduDevMonEmdSlave05Table 1 }

PduDevMonEmdSlave05Entry ::=
        SEQUENCE {
                pduDevMonEmdSlave05Index
                        INTEGER,
                pduDevMonEmdSlave05Valid
                        INTEGER,
                pduDevMonEmdSlave05Type
                        INTEGER,
                pduDevMonEmdSlave05Name
                        DisplayString,
                pduDevMonEmdSlave05TempName
                        DisplayString,
                pduDevMonEmdSlave05HumiName
                        DisplayString,
                pduDevMonEmdSlave05Alarm1Name
                        DisplayString,
                pduDevMonEmdSlave05Alarm2Name
                        DisplayString,
                pduDevMonEmdSlave05Temp
                        INTEGER,
                pduDevMonEmdSlave05Humi
                        INTEGER,
                pduDevMonEmdSlave05TempSt
                        INTEGER,
                pduDevMonEmdSlave05HumiSt
                        INTEGER,
                pduDevMonEmdSlave05Alarm1
                        INTEGER,
                pduDevMonEmdSlave05Alarm2
                        INTEGER
        }

pduDevMonEmdSlave05Index OBJECT-TYPE
        SYNTAX INTEGER (0..7)
        ACCESS read-only
        STATUS mandatory
        DESCRIPTION
                "The index to a emd entry."
        ::= { pduDevMonEmdSlave05Entry 1 }

pduDevMonEmdSlave05Valid OBJECT-TYPE
        SYNTAX INTEGER {
                offline(1),
                online(2)
                }
        ACCESS read-only
        STATUS mandatory
        DESCRIPTION
                "The online status of emd."
        ::= { pduDevMonEmdSlave05Entry 2}


pduDevMonEmdSlave05Type OBJECT-TYPE
        SYNTAX INTEGER
        ACCESS read-only
        STATUS mandatory
        DESCRIPTION
                "The type of emd."
        ::= { pduDevMonEmdSlave05Entry 3}

pduDevMonEmdSlave05Name OBJECT-TYPE
        SYNTAX DisplayString (SIZE(0..31))
        ACCESS read-only
        STATUS mandatory
        DESCRIPTION
                "The name of emd."
        ::= { pduDevMonEmdSlave05Entry 4}

pduDevMonEmdSlave05TempName OBJECT-TYPE
        SYNTAX DisplayString (SIZE(0..31))
        ACCESS read-only
        STATUS mandatory
        DESCRIPTION
                "The name of emd temperature."
        ::= { pduDevMonEmdSlave05Entry 5}

pduDevMonEmdSlave05HumiName OBJECT-TYPE
        SYNTAX DisplayString (SIZE(0..31))
        ACCESS read-only
        STATUS mandatory
        DESCRIPTION
                "The name of emd humidity."
        ::= { pduDevMonEmdSlave05Entry 6}

pduDevMonEmdSlave05Alarm1Name OBJECT-TYPE
        SYNTAX DisplayString (SIZE(0..31))
        ACCESS read-only
        STATUS mandatory
        DESCRIPTION
                "The name of emd alarm-1."
        ::= { pduDevMonEmdSlave05Entry 7}

pduDevMonEmdSlave05Alarm2Name OBJECT-TYPE
        SYNTAX DisplayString (SIZE(0..31))
        ACCESS read-only
        STATUS mandatory
        DESCRIPTION
                "The name of emd alarm-2."
        ::= { pduDevMonEmdSlave05Entry 8}

pduDevMonEmdSlave05Temp OBJECT-TYPE
        SYNTAX INTEGER
        UNITS  "0.1degC"
        ACCESS read-only
        STATUS mandatory
        DESCRIPTION
                "The temperature of emd."
        ::= { pduDevMonEmdSlave05Entry 9}

pduDevMonEmdSlave05Humi OBJECT-TYPE
        SYNTAX INTEGER
        UNITS  "0.1%"
        ACCESS read-only
        STATUS mandatory
        DESCRIPTION
                "The humidity of emd."
        ::= { pduDevMonEmdSlave05Entry 10}

pduDevMonEmdSlave05TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave05Entry 11}

pduDevMonEmdSlave05HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave05Entry 12}

pduDevMonEmdSlave05Alarm1 OBJECT-TYPE
        SYNTAX INTEGER {
                normal(1),
                alarm(2)
                }
        ACCESS read-only
        STATUS mandatory
        DESCRIPTION
                "The alarm-1 of emd."
        ::= { pduDevMonEmdSlave05Entry 13}

pduDevMonEmdSlave05Alarm2 OBJECT-TYPE
        SYNTAX INTEGER {
                normal(1),
                alarm(2)
                }
        ACCESS read-only
        STATUS mandatory
        DESCRIPTION
                "The alarm-2 of emd."
        ::= { pduDevMonEmdSlave05Entry 14}


-- ===========================================================================
--
-- pduDevMonEmdSlave06
--
--  Slave06 Emd Monoitor Group
--
-- ===========================================================================
pduDevMonEmdSlave06Table OBJECT-TYPE
        SYNTAX SEQUENCE OF PduDevMonEmdSlave06Entry
        ACCESS not-accessible
        STATUS mandatory
        DESCRIPTION
                "Display a list of the emd information of Slave06."
        ::= { pduDevMonEmdSlave06 1}

pduDevMonEmdSlave06Entry OBJECT-TYPE
        SYNTAX PduDevMonEmdSlave06Entry
        ACCESS not-accessible
        STATUS mandatory
        DESCRIPTION
                "Display a list of the emd information of Slave06."
        INDEX  { pduDevMonEmdSlave06Index}
        ::= { pduDevMonEmdSlave06Table 1 }

PduDevMonEmdSlave06Entry ::=
        SEQUENCE {
                pduDevMonEmdSlave06Index
                        INTEGER,
                pduDevMonEmdSlave06Valid
                        INTEGER,
                pduDevMonEmdSlave06Type
                        INTEGER,
                pduDevMonEmdSlave06Name
                        DisplayString,
                pduDevMonEmdSlave06TempName
                        DisplayString,
                pduDevMonEmdSlave06HumiName
                        DisplayString,
                pduDevMonEmdSlave06Alarm1Name
                        DisplayString,
                pduDevMonEmdSlave06Alarm2Name
                        DisplayString,
                pduDevMonEmdSlave06Temp
                        INTEGER,
                pduDevMonEmdSlave06Humi
                        INTEGER,
                pduDevMonEmdSlave06TempSt
                        INTEGER,
                pduDevMonEmdSlave06HumiSt
                        INTEGER,
                pduDevMonEmdSlave06Alarm1
                        INTEGER,
                pduDevMonEmdSlave06Alarm2
                        INTEGER
        }

pduDevMonEmdSlave06Index OBJECT-TYPE
        SYNTAX INTEGER (0..7)
        ACCESS read-only
        STATUS mandatory
        DESCRIPTION
                "The index to a emd entry."
        ::= { pduDevMonEmdSlave06Entry 1 }

pduDevMonEmdSlave06Valid OBJECT-TYPE
        SYNTAX INTEGER {
                offline(1),
                online(2)
                }
        ACCESS read-only
        STATUS mandatory
        DESCRIPTION
                "The online status of emd."
        ::= { pduDevMonEmdSlave06Entry 2}


pduDevMonEmdSlave06Type OBJECT-TYPE
        SYNTAX INTEGER
        ACCESS read-only
        STATUS mandatory
        DESCRIPTION
                "The type of emd."
        ::= { pduDevMonEmdSlave06Entry 3}

pduDevMonEmdSlave06Name OBJECT-TYPE
        SYNTAX DisplayString (SIZE(0..31))
        ACCESS read-only
        STATUS mandatory
        DESCRIPTION
                "The name of emd."
        ::= { pduDevMonEmdSlave06Entry 4}

pduDevMonEmdSlave06TempName OBJECT-TYPE
        SYNTAX DisplayString (SIZE(0..31))
        ACCESS read-only
        STATUS mandatory
        DESCRIPTION
                "The name of emd temperature."
        ::= { pduDevMonEmdSlave06Entry 5}

pduDevMonEmdSlave06HumiName OBJECT-TYPE
        SYNTAX DisplayString (SIZE(0..31))
        ACCESS read-only
        STATUS mandatory
        DESCRIPTION
                "The name of emd humidity."
        ::= { pduDevMonEmdSlave06Entry 6}

pduDevMonEmdSlave06Alarm1Name OBJECT-TYPE
        SYNTAX DisplayString (SIZE(0..31))
        ACCESS read-only
        STATUS mandatory
        DESCRIPTION
                "The name of emd alarm-1."
        ::= { pduDevMonEmdSlave06Entry 7}

pduDevMonEmdSlave06Alarm2Name OBJECT-TYPE
        SYNTAX DisplayString (SIZE(0..31))
        ACCESS read-only
        STATUS mandatory
        DESCRIPTION
                "The name of emd alarm-2."
        ::= { pduDevMonEmdSlave06Entry 8}

pduDevMonEmdSlave06Temp OBJECT-TYPE
        SYNTAX INTEGER
        UNITS  "0.1degC"
        ACCESS read-only
        STATUS mandatory
        DESCRIPTION
                "The temperature of emd."
        ::= { pduDevMonEmdSlave06Entry 9}

pduDevMonEmdSlave06Humi OBJECT-TYPE
        SYNTAX INTEGER
        UNITS  "0.1%"
        ACCESS read-only
        STATUS mandatory
        DESCRIPTION
                "The humidity of emd."
        ::= { pduDevMonEmdSlave06Entry 10}

pduDevMonEmdSlave06TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave06Entry 11}

pduDevMonEmdSlave06HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave06Entry 12}

pduDevMonEmdSlave06Alarm1 OBJECT-TYPE
        SYNTAX INTEGER {
                normal(1),
                alarm(2)
                }
        ACCESS read-only
        STATUS mandatory
        DESCRIPTION
                "The alarm-1 of emd."
        ::= { pduDevMonEmdSlave06Entry 13}

pduDevMonEmdSlave06Alarm2 OBJECT-TYPE
        SYNTAX INTEGER {
                normal(1),
                alarm(2)
                }
        ACCESS read-only
        STATUS mandatory
        DESCRIPTION
                "The alarm-2 of emd."
        ::= { pduDevMonEmdSlave06Entry 14}


-- ===========================================================================
--
-- pduDevMonEmdSlave07
--
--  Slave07 Emd Monoitor Group
--
-- ===========================================================================
pduDevMonEmdSlave07Table OBJECT-TYPE
        SYNTAX SEQUENCE OF PduDevMonEmdSlave07Entry
        ACCESS not-accessible
        STATUS mandatory
        DESCRIPTION
                "Display a list of the emd information of Slave07."
        ::= { pduDevMonEmdSlave07 1}

pduDevMonEmdSlave07Entry OBJECT-TYPE
        SYNTAX PduDevMonEmdSlave07Entry
        ACCESS not-accessible
        STATUS mandatory
        DESCRIPTION
                "Display a list of the emd information of Slave07."
        INDEX  { pduDevMonEmdSlave07Index}
        ::= { pduDevMonEmdSlave07Table 1 }

PduDevMonEmdSlave07Entry ::=
        SEQUENCE {
                pduDevMonEmdSlave07Index
                        INTEGER,
                pduDevMonEmdSlave07Valid
                        INTEGER,
                pduDevMonEmdSlave07Type
                        INTEGER,
                pduDevMonEmdSlave07Name
                        DisplayString,
                pduDevMonEmdSlave07TempName
                        DisplayString,
                pduDevMonEmdSlave07HumiName
                        DisplayString,
                pduDevMonEmdSlave07Alarm1Name
                        DisplayString,
                pduDevMonEmdSlave07Alarm2Name
                        DisplayString,
                pduDevMonEmdSlave07Temp
                        INTEGER,
                pduDevMonEmdSlave07Humi
                        INTEGER,
                pduDevMonEmdSlave07TempSt
                        INTEGER,
                pduDevMonEmdSlave07HumiSt
                        INTEGER,
                pduDevMonEmdSlave07Alarm1
                        INTEGER,
                pduDevMonEmdSlave07Alarm2
                        INTEGER
        }

pduDevMonEmdSlave07Index OBJECT-TYPE
        SYNTAX INTEGER (0..7)
        ACCESS read-only
        STATUS mandatory
        DESCRIPTION
                "The index to a emd entry."
        ::= { pduDevMonEmdSlave07Entry 1 }

pduDevMonEmdSlave07Valid OBJECT-TYPE
        SYNTAX INTEGER {
                offline(1),
                online(2)
                }
        ACCESS read-only
        STATUS mandatory
        DESCRIPTION
                "The online status of emd."
        ::= { pduDevMonEmdSlave07Entry 2}


pduDevMonEmdSlave07Type OBJECT-TYPE
        SYNTAX INTEGER
        ACCESS read-only
        STATUS mandatory
        DESCRIPTION
                "The type of emd."
        ::= { pduDevMonEmdSlave07Entry 3}

pduDevMonEmdSlave07Name OBJECT-TYPE
        SYNTAX DisplayString (SIZE(0..31))
        ACCESS read-only
        STATUS mandatory
        DESCRIPTION
                "The name of emd."
        ::= { pduDevMonEmdSlave07Entry 4}

pduDevMonEmdSlave07TempName OBJECT-TYPE
        SYNTAX DisplayString (SIZE(0..31))
        ACCESS read-only
        STATUS mandatory
        DESCRIPTION
                "The name of emd temperature."
        ::= { pduDevMonEmdSlave07Entry 5}

pduDevMonEmdSlave07HumiName OBJECT-TYPE
        SYNTAX DisplayString (SIZE(0..31))
        ACCESS read-only
        STATUS mandatory
        DESCRIPTION
                "The name of emd humidity."
        ::= { pduDevMonEmdSlave07Entry 6}

pduDevMonEmdSlave07Alarm1Name OBJECT-TYPE
        SYNTAX DisplayString (SIZE(0..31))
        ACCESS read-only
        STATUS mandatory
        DESCRIPTION
                "The name of emd alarm-1."
        ::= { pduDevMonEmdSlave07Entry 7}

pduDevMonEmdSlave07Alarm2Name OBJECT-TYPE
        SYNTAX DisplayString (SIZE(0..31))
        ACCESS read-only
        STATUS mandatory
        DESCRIPTION
                "The name of emd alarm-2."
        ::= { pduDevMonEmdSlave07Entry 8}

pduDevMonEmdSlave07Temp OBJECT-TYPE
        SYNTAX INTEGER
        UNITS  "0.1degC"
        ACCESS read-only
        STATUS mandatory
        DESCRIPTION
                "The temperature of emd."
        ::= { pduDevMonEmdSlave07Entry 9}

pduDevMonEmdSlave07Humi OBJECT-TYPE
        SYNTAX INTEGER
        UNITS  "0.1%"
        ACCESS read-only
        STATUS mandatory
        DESCRIPTION
                "The humidity of emd."
        ::= { pduDevMonEmdSlave07Entry 10}

pduDevMonEmdSlave07TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave07Entry 11}

pduDevMonEmdSlave07HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave07Entry 12}

pduDevMonEmdSlave07Alarm1 OBJECT-TYPE
        SYNTAX INTEGER {
                normal(1),
                alarm(2)
                }
        ACCESS read-only
        STATUS mandatory
        DESCRIPTION
                "The alarm-1 of emd."
        ::= { pduDevMonEmdSlave07Entry 13}

pduDevMonEmdSlave07Alarm2 OBJECT-TYPE
        SYNTAX INTEGER {
                normal(1),
                alarm(2)
                }
        ACCESS read-only
        STATUS mandatory
        DESCRIPTION
                "The alarm-2 of emd."
        ::= { pduDevMonEmdSlave07Entry 14}


-- ===========================================================================
--
-- pduDevMonEmdSlave08
--
--  Slave08 Emd Monoitor Group
--
-- ===========================================================================
pduDevMonEmdSlave08Table OBJECT-TYPE
        SYNTAX SEQUENCE OF PduDevMonEmdSlave08Entry
        ACCESS not-accessible
        STATUS mandatory
        DESCRIPTION
                "Display a list of the emd information of Slave08."
        ::= { pduDevMonEmdSlave08 1}

pduDevMonEmdSlave08Entry OBJECT-TYPE
        SYNTAX PduDevMonEmdSlave08Entry
        ACCESS not-accessible
        STATUS mandatory
        DESCRIPTION
                "Display a list of the emd information of Slave08."
        INDEX  { pduDevMonEmdSlave08Index}
        ::= { pduDevMonEmdSlave08Table 1 }

PduDevMonEmdSlave08Entry ::=
        SEQUENCE {
                pduDevMonEmdSlave08Index
                        INTEGER,
                pduDevMonEmdSlave08Valid
                        INTEGER,
                pduDevMonEmdSlave08Type
                        INTEGER,
                pduDevMonEmdSlave08Name
                        DisplayString,
                pduDevMonEmdSlave08TempName
                        DisplayString,
                pduDevMonEmdSlave08HumiName
                        DisplayString,
                pduDevMonEmdSlave08Alarm1Name
                        DisplayString,
                pduDevMonEmdSlave08Alarm2Name
                        DisplayString,
                pduDevMonEmdSlave08Temp
                        INTEGER,
                pduDevMonEmdSlave08Humi
                        INTEGER,
                pduDevMonEmdSlave08TempSt
                        INTEGER,
                pduDevMonEmdSlave08HumiSt
                        INTEGER,
                pduDevMonEmdSlave08Alarm1
                        INTEGER,
                pduDevMonEmdSlave08Alarm2
                        INTEGER
        }

pduDevMonEmdSlave08Index OBJECT-TYPE
        SYNTAX INTEGER (0..7)
        ACCESS read-only
        STATUS mandatory
        DESCRIPTION
                "The index to a emd entry."
        ::= { pduDevMonEmdSlave08Entry 1 }

pduDevMonEmdSlave08Valid OBJECT-TYPE
        SYNTAX INTEGER {
                offline(1),
                online(2)
                }
        ACCESS read-only
        STATUS mandatory
        DESCRIPTION
                "The online status of emd."
        ::= { pduDevMonEmdSlave08Entry 2}


pduDevMonEmdSlave08Type OBJECT-TYPE
        SYNTAX INTEGER
        ACCESS read-only
        STATUS mandatory
        DESCRIPTION
                "The type of emd."
        ::= { pduDevMonEmdSlave08Entry 3}

pduDevMonEmdSlave08Name OBJECT-TYPE
        SYNTAX DisplayString (SIZE(0..31))
        ACCESS read-only
        STATUS mandatory
        DESCRIPTION
                "The name of emd."
        ::= { pduDevMonEmdSlave08Entry 4}

pduDevMonEmdSlave08TempName OBJECT-TYPE
        SYNTAX DisplayString (SIZE(0..31))
        ACCESS read-only
        STATUS mandatory
        DESCRIPTION
                "The name of emd temperature."
        ::= { pduDevMonEmdSlave08Entry 5}

pduDevMonEmdSlave08HumiName OBJECT-TYPE
        SYNTAX DisplayString (SIZE(0..31))
        ACCESS read-only
        STATUS mandatory
        DESCRIPTION
                "The name of emd humidity."
        ::= { pduDevMonEmdSlave08Entry 6}

pduDevMonEmdSlave08Alarm1Name OBJECT-TYPE
        SYNTAX DisplayString (SIZE(0..31))
        ACCESS read-only
        STATUS mandatory
        DESCRIPTION
                "The name of emd alarm-1."
        ::= { pduDevMonEmdSlave08Entry 7}

pduDevMonEmdSlave08Alarm2Name OBJECT-TYPE
        SYNTAX DisplayString (SIZE(0..31))
        ACCESS read-only
        STATUS mandatory
        DESCRIPTION
                "The name of emd alarm-2."
        ::= { pduDevMonEmdSlave08Entry 8}

pduDevMonEmdSlave08Temp OBJECT-TYPE
        SYNTAX INTEGER
        UNITS  "0.1degC"
        ACCESS read-only
        STATUS mandatory
        DESCRIPTION
                "The temperature of emd."
        ::= { pduDevMonEmdSlave08Entry 9}

pduDevMonEmdSlave08Humi OBJECT-TYPE
        SYNTAX INTEGER
        UNITS  "0.1%"
        ACCESS read-only
        STATUS mandatory
        DESCRIPTION
                "The humidity of emd."
        ::= { pduDevMonEmdSlave08Entry 10}

pduDevMonEmdSlave08TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave08Entry 11}

pduDevMonEmdSlave08HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave08Entry 12}

pduDevMonEmdSlave08Alarm1 OBJECT-TYPE
        SYNTAX INTEGER {
                normal(1),
                alarm(2)
                }
        ACCESS read-only
        STATUS mandatory
        DESCRIPTION
                "The alarm-1 of emd."
        ::= { pduDevMonEmdSlave08Entry 13}

pduDevMonEmdSlave08Alarm2 OBJECT-TYPE
        SYNTAX INTEGER {
                normal(1),
                alarm(2)
                }
        ACCESS read-only
        STATUS mandatory
        DESCRIPTION
                "The alarm-2 of emd."
        ::= { pduDevMonEmdSlave08Entry 14}


-- ===========================================================================
--
-- pduDevMonEmdSlave09
--
--  Slave09 Emd Monoitor Group
--
-- ===========================================================================
pduDevMonEmdSlave09Table OBJECT-TYPE
        SYNTAX SEQUENCE OF PduDevMonEmdSlave09Entry
        ACCESS not-accessible
        STATUS mandatory
        DESCRIPTION
                "Display a list of the emd information of Slave09."
        ::= { pduDevMonEmdSlave09 1}

pduDevMonEmdSlave09Entry OBJECT-TYPE
        SYNTAX PduDevMonEmdSlave09Entry
        ACCESS not-accessible
        STATUS mandatory
        DESCRIPTION
                "Display a list of the emd information of Slave09."
        INDEX  { pduDevMonEmdSlave09Index}
        ::= { pduDevMonEmdSlave09Table 1 }

PduDevMonEmdSlave09Entry ::=
        SEQUENCE {
                pduDevMonEmdSlave09Index
                        INTEGER,
                pduDevMonEmdSlave09Valid
                        INTEGER,
                pduDevMonEmdSlave09Type
                        INTEGER,
                pduDevMonEmdSlave09Name
                        DisplayString,
                pduDevMonEmdSlave09TempName
                        DisplayString,
                pduDevMonEmdSlave09HumiName
                        DisplayString,
                pduDevMonEmdSlave09Alarm1Name
                        DisplayString,
                pduDevMonEmdSlave09Alarm2Name
                        DisplayString,
                pduDevMonEmdSlave09Temp
                        INTEGER,
                pduDevMonEmdSlave09Humi
                        INTEGER,
                pduDevMonEmdSlave09TempSt
                        INTEGER,
                pduDevMonEmdSlave09HumiSt
                        INTEGER,
                pduDevMonEmdSlave09Alarm1
                        INTEGER,
                pduDevMonEmdSlave09Alarm2
                        INTEGER
        }

pduDevMonEmdSlave09Index OBJECT-TYPE
        SYNTAX INTEGER (0..7)
        ACCESS read-only
        STATUS mandatory
        DESCRIPTION
                "The index to a emd entry."
        ::= { pduDevMonEmdSlave09Entry 1 }

pduDevMonEmdSlave09Valid OBJECT-TYPE
        SYNTAX INTEGER {
                offline(1),
                online(2)
                }
        ACCESS read-only
        STATUS mandatory
        DESCRIPTION
                "The online status of emd."
        ::= { pduDevMonEmdSlave09Entry 2}


pduDevMonEmdSlave09Type OBJECT-TYPE
        SYNTAX INTEGER
        ACCESS read-only
        STATUS mandatory
        DESCRIPTION
                "The type of emd."
        ::= { pduDevMonEmdSlave09Entry 3}

pduDevMonEmdSlave09Name OBJECT-TYPE
        SYNTAX DisplayString (SIZE(0..31))
        ACCESS read-only
        STATUS mandatory
        DESCRIPTION
                "The name of emd."
        ::= { pduDevMonEmdSlave09Entry 4}

pduDevMonEmdSlave09TempName OBJECT-TYPE
        SYNTAX DisplayString (SIZE(0..31))
        ACCESS read-only
        STATUS mandatory
        DESCRIPTION
                "The name of emd temperature."
        ::= { pduDevMonEmdSlave09Entry 5}

pduDevMonEmdSlave09HumiName OBJECT-TYPE
        SYNTAX DisplayString (SIZE(0..31))
        ACCESS read-only
        STATUS mandatory
        DESCRIPTION
                "The name of emd humidity."
        ::= { pduDevMonEmdSlave09Entry 6}

pduDevMonEmdSlave09Alarm1Name OBJECT-TYPE
        SYNTAX DisplayString (SIZE(0..31))
        ACCESS read-only
        STATUS mandatory
        DESCRIPTION
                "The name of emd alarm-1."
        ::= { pduDevMonEmdSlave09Entry 7}

pduDevMonEmdSlave09Alarm2Name OBJECT-TYPE
        SYNTAX DisplayString (SIZE(0..31))
        ACCESS read-only
        STATUS mandatory
        DESCRIPTION
                "The name of emd alarm-2."
        ::= { pduDevMonEmdSlave09Entry 8}

pduDevMonEmdSlave09Temp OBJECT-TYPE
        SYNTAX INTEGER
        UNITS  "0.1degC"
        ACCESS read-only
        STATUS mandatory
        DESCRIPTION
                "The temperature of emd."
        ::= { pduDevMonEmdSlave09Entry 9}

pduDevMonEmdSlave09Humi OBJECT-TYPE
        SYNTAX INTEGER
        UNITS  "0.1%"
        ACCESS read-only
        STATUS mandatory
        DESCRIPTION
                "The humidity of emd."
        ::= { pduDevMonEmdSlave09Entry 10}

pduDevMonEmdSlave09TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave09Entry 11}

pduDevMonEmdSlave09HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave09Entry 12}

pduDevMonEmdSlave09Alarm1 OBJECT-TYPE
        SYNTAX INTEGER {
                normal(1),
                alarm(2)
                }
        ACCESS read-only
        STATUS mandatory
        DESCRIPTION
                "The alarm-1 of emd."
        ::= { pduDevMonEmdSlave09Entry 13}

pduDevMonEmdSlave09Alarm2 OBJECT-TYPE
        SYNTAX INTEGER {
                normal(1),
                alarm(2)
                }
        ACCESS read-only
        STATUS mandatory
        DESCRIPTION
                "The alarm-2 of emd."
        ::= { pduDevMonEmdSlave09Entry 14}


-- ===========================================================================
--
-- pduDevMonEmdSlave10
--
--  Slave10 Emd Monoitor Group
--
-- ===========================================================================
pduDevMonEmdSlave10Table OBJECT-TYPE
        SYNTAX SEQUENCE OF PduDevMonEmdSlave10Entry
        ACCESS not-accessible
        STATUS mandatory
        DESCRIPTION
                "Display a list of the emd information of Slave10."
        ::= { pduDevMonEmdSlave10 1}

pduDevMonEmdSlave10Entry OBJECT-TYPE
        SYNTAX PduDevMonEmdSlave10Entry
        ACCESS not-accessible
        STATUS mandatory
        DESCRIPTION
                "Display a list of the emd information of Slave10."
        INDEX  { pduDevMonEmdSlave10Index}
        ::= { pduDevMonEmdSlave10Table 1 }

PduDevMonEmdSlave10Entry ::=
        SEQUENCE {
                pduDevMonEmdSlave10Index
                        INTEGER,
                pduDevMonEmdSlave10Valid
                        INTEGER,
                pduDevMonEmdSlave10Type
                        INTEGER,
                pduDevMonEmdSlave10Name
                        DisplayString,
                pduDevMonEmdSlave10TempName
                        DisplayString,
                pduDevMonEmdSlave10HumiName
                        DisplayString,
                pduDevMonEmdSlave10Alarm1Name
                        DisplayString,
                pduDevMonEmdSlave10Alarm2Name
                        DisplayString,
                pduDevMonEmdSlave10Temp
                        INTEGER,
                pduDevMonEmdSlave10Humi
                        INTEGER,
                pduDevMonEmdSlave10TempSt
                        INTEGER,
                pduDevMonEmdSlave10HumiSt
                        INTEGER,
                pduDevMonEmdSlave10Alarm1
                        INTEGER,
                pduDevMonEmdSlave10Alarm2
                        INTEGER
        }

pduDevMonEmdSlave10Index OBJECT-TYPE
        SYNTAX INTEGER (0..7)
        ACCESS read-only
        STATUS mandatory
        DESCRIPTION
                "The index to a emd entry."
        ::= { pduDevMonEmdSlave10Entry 1 }

pduDevMonEmdSlave10Valid OBJECT-TYPE
        SYNTAX INTEGER {
                offline(1),
                online(2)
                }
        ACCESS read-only
        STATUS mandatory
        DESCRIPTION
                "The online status of emd."
        ::= { pduDevMonEmdSlave10Entry 2}


pduDevMonEmdSlave10Type OBJECT-TYPE
        SYNTAX INTEGER
        ACCESS read-only
        STATUS mandatory
        DESCRIPTION
                "The type of emd."
        ::= { pduDevMonEmdSlave10Entry 3}

pduDevMonEmdSlave10Name OBJECT-TYPE
        SYNTAX DisplayString (SIZE(0..31))
        ACCESS read-only
        STATUS mandatory
        DESCRIPTION
                "The name of emd."
        ::= { pduDevMonEmdSlave10Entry 4}

pduDevMonEmdSlave10TempName OBJECT-TYPE
        SYNTAX DisplayString (SIZE(0..31))
        ACCESS read-only
        STATUS mandatory
        DESCRIPTION
                "The name of emd temperature."
        ::= { pduDevMonEmdSlave10Entry 5}

pduDevMonEmdSlave10HumiName OBJECT-TYPE
        SYNTAX DisplayString (SIZE(0..31))
        ACCESS read-only
        STATUS mandatory
        DESCRIPTION
                "The name of emd humidity."
        ::= { pduDevMonEmdSlave10Entry 6}

pduDevMonEmdSlave10Alarm1Name OBJECT-TYPE
        SYNTAX DisplayString (SIZE(0..31))
        ACCESS read-only
        STATUS mandatory
        DESCRIPTION
                "The name of emd alarm-1."
        ::= { pduDevMonEmdSlave10Entry 7}

pduDevMonEmdSlave10Alarm2Name OBJECT-TYPE
        SYNTAX DisplayString (SIZE(0..31))
        ACCESS read-only
        STATUS mandatory
        DESCRIPTION
                "The name of emd alarm-2."
        ::= { pduDevMonEmdSlave10Entry 8}

pduDevMonEmdSlave10Temp OBJECT-TYPE
        SYNTAX INTEGER
        UNITS  "0.1degC"
        ACCESS read-only
        STATUS mandatory
        DESCRIPTION
                "The temperature of emd."
        ::= { pduDevMonEmdSlave10Entry 9}

pduDevMonEmdSlave10Humi OBJECT-TYPE
        SYNTAX INTEGER
        UNITS  "0.1%"
        ACCESS read-only
        STATUS mandatory
        DESCRIPTION
                "The humidity of emd."
        ::= { pduDevMonEmdSlave10Entry 10}

pduDevMonEmdSlave10TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave10Entry 11}

pduDevMonEmdSlave10HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave10Entry 12}

pduDevMonEmdSlave10Alarm1 OBJECT-TYPE
        SYNTAX INTEGER {
                normal(1),
                alarm(2)
                }
        ACCESS read-only
        STATUS mandatory
        DESCRIPTION
                "The alarm-1 of emd."
        ::= { pduDevMonEmdSlave10Entry 13}

pduDevMonEmdSlave10Alarm2 OBJECT-TYPE
        SYNTAX INTEGER {
                normal(1),
                alarm(2)
                }
        ACCESS read-only
        STATUS mandatory
        DESCRIPTION
                "The alarm-2 of emd."
        ::= { pduDevMonEmdSlave10Entry 14}


-- ===========================================================================
--
-- pduDevMonEmdSlave11
--
--  Slave11 Emd Monoitor Group
--
-- ===========================================================================
pduDevMonEmdSlave11Table OBJECT-TYPE
        SYNTAX SEQUENCE OF PduDevMonEmdSlave11Entry
        ACCESS not-accessible
        STATUS mandatory
        DESCRIPTION
                "Display a list of the emd information of Slave11."
        ::= { pduDevMonEmdSlave11 1}

pduDevMonEmdSlave11Entry OBJECT-TYPE
        SYNTAX PduDevMonEmdSlave11Entry
        ACCESS not-accessible
        STATUS mandatory
        DESCRIPTION
                "Display a list of the emd information of Slave11."
        INDEX  { pduDevMonEmdSlave11Index}
        ::= { pduDevMonEmdSlave11Table 1 }

PduDevMonEmdSlave11Entry ::=
        SEQUENCE {
                pduDevMonEmdSlave11Index
                        INTEGER,
                pduDevMonEmdSlave11Valid
                        INTEGER,
                pduDevMonEmdSlave11Type
                        INTEGER,
                pduDevMonEmdSlave11Name
                        DisplayString,
                pduDevMonEmdSlave11TempName
                        DisplayString,
                pduDevMonEmdSlave11HumiName
                        DisplayString,
                pduDevMonEmdSlave11Alarm1Name
                        DisplayString,
                pduDevMonEmdSlave11Alarm2Name
                        DisplayString,
                pduDevMonEmdSlave11Temp
                        INTEGER,
                pduDevMonEmdSlave11Humi
                        INTEGER,
                pduDevMonEmdSlave11TempSt
                        INTEGER,
                pduDevMonEmdSlave11HumiSt
                        INTEGER,
                pduDevMonEmdSlave11Alarm1
                        INTEGER,
                pduDevMonEmdSlave11Alarm2
                        INTEGER
        }

pduDevMonEmdSlave11Index OBJECT-TYPE
        SYNTAX INTEGER (0..7)
        ACCESS read-only
        STATUS mandatory
        DESCRIPTION
                "The index to a emd entry."
        ::= { pduDevMonEmdSlave11Entry 1 }

pduDevMonEmdSlave11Valid OBJECT-TYPE
        SYNTAX INTEGER {
                offline(1),
                online(2)
                }
        ACCESS read-only
        STATUS mandatory
        DESCRIPTION
                "The online status of emd."
        ::= { pduDevMonEmdSlave11Entry 2}


pduDevMonEmdSlave11Type OBJECT-TYPE
        SYNTAX INTEGER
        ACCESS read-only
        STATUS mandatory
        DESCRIPTION
                "The type of emd."
        ::= { pduDevMonEmdSlave11Entry 3}

pduDevMonEmdSlave11Name OBJECT-TYPE
        SYNTAX DisplayString (SIZE(0..31))
        ACCESS read-only
        STATUS mandatory
        DESCRIPTION
                "The name of emd."
        ::= { pduDevMonEmdSlave11Entry 4}

pduDevMonEmdSlave11TempName OBJECT-TYPE
        SYNTAX DisplayString (SIZE(0..31))
        ACCESS read-only
        STATUS mandatory
        DESCRIPTION
                "The name of emd temperature."
        ::= { pduDevMonEmdSlave11Entry 5}

pduDevMonEmdSlave11HumiName OBJECT-TYPE
        SYNTAX DisplayString (SIZE(0..31))
        ACCESS read-only
        STATUS mandatory
        DESCRIPTION
                "The name of emd humidity."
        ::= { pduDevMonEmdSlave11Entry 6}

pduDevMonEmdSlave11Alarm1Name OBJECT-TYPE
        SYNTAX DisplayString (SIZE(0..31))
        ACCESS read-only
        STATUS mandatory
        DESCRIPTION
                "The name of emd alarm-1."
        ::= { pduDevMonEmdSlave11Entry 7}

pduDevMonEmdSlave11Alarm2Name OBJECT-TYPE
        SYNTAX DisplayString (SIZE(0..31))
        ACCESS read-only
        STATUS mandatory
        DESCRIPTION
                "The name of emd alarm-2."
        ::= { pduDevMonEmdSlave11Entry 8}

pduDevMonEmdSlave11Temp OBJECT-TYPE
        SYNTAX INTEGER
        UNITS  "0.1degC"
        ACCESS read-only
        STATUS mandatory
        DESCRIPTION
                "The temperature of emd."
        ::= { pduDevMonEmdSlave11Entry 9}

pduDevMonEmdSlave11Humi OBJECT-TYPE
        SYNTAX INTEGER
        UNITS  "0.1%"
        ACCESS read-only
        STATUS mandatory
        DESCRIPTION
                "The humidity of emd."
        ::= { pduDevMonEmdSlave11Entry 10}

pduDevMonEmdSlave11TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave11Entry 11}

pduDevMonEmdSlave11HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave11Entry 12}

pduDevMonEmdSlave11Alarm1 OBJECT-TYPE
        SYNTAX INTEGER {
                normal(1),
                alarm(2)
                }
        ACCESS read-only
        STATUS mandatory
        DESCRIPTION
                "The alarm-1 of emd."
        ::= { pduDevMonEmdSlave11Entry 13}

pduDevMonEmdSlave11Alarm2 OBJECT-TYPE
        SYNTAX INTEGER {
                normal(1),
                alarm(2)
                }
        ACCESS read-only
        STATUS mandatory
        DESCRIPTION
                "The alarm-2 of emd."
        ::= { pduDevMonEmdSlave11Entry 14}


-- ===========================================================================
--
-- pduDevMonEmdSlave12
--
--  Slave12 Emd Monoitor Group
--
-- ===========================================================================
pduDevMonEmdSlave12Table OBJECT-TYPE
        SYNTAX SEQUENCE OF PduDevMonEmdSlave12Entry
        ACCESS not-accessible
        STATUS mandatory
        DESCRIPTION
                "Display a list of the emd information of Slave12."
        ::= { pduDevMonEmdSlave12 1}

pduDevMonEmdSlave12Entry OBJECT-TYPE
        SYNTAX PduDevMonEmdSlave12Entry
        ACCESS not-accessible
        STATUS mandatory
        DESCRIPTION
                "Display a list of the emd information of Slave12."
        INDEX  { pduDevMonEmdSlave12Index}
        ::= { pduDevMonEmdSlave12Table 1 }

PduDevMonEmdSlave12Entry ::=
        SEQUENCE {
                pduDevMonEmdSlave12Index
                        INTEGER,
                pduDevMonEmdSlave12Valid
                        INTEGER,
                pduDevMonEmdSlave12Type
                        INTEGER,
                pduDevMonEmdSlave12Name
                        DisplayString,
                pduDevMonEmdSlave12TempName
                        DisplayString,
                pduDevMonEmdSlave12HumiName
                        DisplayString,
                pduDevMonEmdSlave12Alarm1Name
                        DisplayString,
                pduDevMonEmdSlave12Alarm2Name
                        DisplayString,
                pduDevMonEmdSlave12Temp
                        INTEGER,
                pduDevMonEmdSlave12Humi
                        INTEGER,
                pduDevMonEmdSlave12TempSt
                        INTEGER,
                pduDevMonEmdSlave12HumiSt
                        INTEGER,
                pduDevMonEmdSlave12Alarm1
                        INTEGER,
                pduDevMonEmdSlave12Alarm2
                        INTEGER
        }

pduDevMonEmdSlave12Index OBJECT-TYPE
        SYNTAX INTEGER (0..7)
        ACCESS read-only
        STATUS mandatory
        DESCRIPTION
                "The index to a emd entry."
        ::= { pduDevMonEmdSlave12Entry 1 }

pduDevMonEmdSlave12Valid OBJECT-TYPE
        SYNTAX INTEGER {
                offline(1),
                online(2)
                }
        ACCESS read-only
        STATUS mandatory
        DESCRIPTION
                "The online status of emd."
        ::= { pduDevMonEmdSlave12Entry 2}


pduDevMonEmdSlave12Type OBJECT-TYPE
        SYNTAX INTEGER
        ACCESS read-only
        STATUS mandatory
        DESCRIPTION
                "The type of emd."
        ::= { pduDevMonEmdSlave12Entry 3}

pduDevMonEmdSlave12Name OBJECT-TYPE
        SYNTAX DisplayString (SIZE(0..31))
        ACCESS read-only
        STATUS mandatory
        DESCRIPTION
                "The name of emd."
        ::= { pduDevMonEmdSlave12Entry 4}

pduDevMonEmdSlave12TempName OBJECT-TYPE
        SYNTAX DisplayString (SIZE(0..31))
        ACCESS read-only
        STATUS mandatory
        DESCRIPTION
                "The name of emd temperature."
        ::= { pduDevMonEmdSlave12Entry 5}

pduDevMonEmdSlave12HumiName OBJECT-TYPE
        SYNTAX DisplayString (SIZE(0..31))
        ACCESS read-only
        STATUS mandatory
        DESCRIPTION
                "The name of emd humidity."
        ::= { pduDevMonEmdSlave12Entry 6}

pduDevMonEmdSlave12Alarm1Name OBJECT-TYPE
        SYNTAX DisplayString (SIZE(0..31))
        ACCESS read-only
        STATUS mandatory
        DESCRIPTION
                "The name of emd alarm-1."
        ::= { pduDevMonEmdSlave12Entry 7}

pduDevMonEmdSlave12Alarm2Name OBJECT-TYPE
        SYNTAX DisplayString (SIZE(0..31))
        ACCESS read-only
        STATUS mandatory
        DESCRIPTION
                "The name of emd alarm-2."
        ::= { pduDevMonEmdSlave12Entry 8}

pduDevMonEmdSlave12Temp OBJECT-TYPE
        SYNTAX INTEGER
        UNITS  "0.1degC"
        ACCESS read-only
        STATUS mandatory
        DESCRIPTION
                "The temperature of emd."
        ::= { pduDevMonEmdSlave12Entry 9}

pduDevMonEmdSlave12Humi OBJECT-TYPE
        SYNTAX INTEGER
        UNITS  "0.1%"
        ACCESS read-only
        STATUS mandatory
        DESCRIPTION
                "The humidity of emd."
        ::= { pduDevMonEmdSlave12Entry 10}

pduDevMonEmdSlave12TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave12Entry 11}

pduDevMonEmdSlave12HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave12Entry 12}

pduDevMonEmdSlave12Alarm1 OBJECT-TYPE
        SYNTAX INTEGER {
                normal(1),
                alarm(2)
                }
        ACCESS read-only
        STATUS mandatory
        DESCRIPTION
                "The alarm-1 of emd."
        ::= { pduDevMonEmdSlave12Entry 13}

pduDevMonEmdSlave12Alarm2 OBJECT-TYPE
        SYNTAX INTEGER {
                normal(1),
                alarm(2)
                }
        ACCESS read-only
        STATUS mandatory
        DESCRIPTION
                "The alarm-2 of emd."
        ::= { pduDevMonEmdSlave12Entry 14}


-- ===========================================================================
--
-- pduDevMonEmdSlave13
--
--  Slave13 Emd Monoitor Group
--
-- ===========================================================================
pduDevMonEmdSlave13Table OBJECT-TYPE
        SYNTAX SEQUENCE OF PduDevMonEmdSlave13Entry
        ACCESS not-accessible
        STATUS mandatory
        DESCRIPTION
                "Display a list of the emd information of Slave13."
        ::= { pduDevMonEmdSlave13 1}

pduDevMonEmdSlave13Entry OBJECT-TYPE
        SYNTAX PduDevMonEmdSlave13Entry
        ACCESS not-accessible
        STATUS mandatory
        DESCRIPTION
                "Display a list of the emd information of Slave13."
        INDEX  { pduDevMonEmdSlave13Index}
        ::= { pduDevMonEmdSlave13Table 1 }

PduDevMonEmdSlave13Entry ::=
        SEQUENCE {
                pduDevMonEmdSlave13Index
                        INTEGER,
                pduDevMonEmdSlave13Valid
                        INTEGER,
                pduDevMonEmdSlave13Type
                        INTEGER,
                pduDevMonEmdSlave13Name
                        DisplayString,
                pduDevMonEmdSlave13TempName
                        DisplayString,
                pduDevMonEmdSlave13HumiName
                        DisplayString,
                pduDevMonEmdSlave13Alarm1Name
                        DisplayString,
                pduDevMonEmdSlave13Alarm2Name
                        DisplayString,
                pduDevMonEmdSlave13Temp
                        INTEGER,
                pduDevMonEmdSlave13Humi
                        INTEGER,
                pduDevMonEmdSlave13TempSt
                        INTEGER,
                pduDevMonEmdSlave13HumiSt
                        INTEGER,
                pduDevMonEmdSlave13Alarm1
                        INTEGER,
                pduDevMonEmdSlave13Alarm2
                        INTEGER
        }

pduDevMonEmdSlave13Index OBJECT-TYPE
        SYNTAX INTEGER (0..7)
        ACCESS read-only
        STATUS mandatory
        DESCRIPTION
                "The index to a emd entry."
        ::= { pduDevMonEmdSlave13Entry 1 }

pduDevMonEmdSlave13Valid OBJECT-TYPE
        SYNTAX INTEGER {
                offline(1),
                online(2)
                }
        ACCESS read-only
        STATUS mandatory
        DESCRIPTION
                "The online status of emd."
        ::= { pduDevMonEmdSlave13Entry 2}


pduDevMonEmdSlave13Type OBJECT-TYPE
        SYNTAX INTEGER
        ACCESS read-only
        STATUS mandatory
        DESCRIPTION
                "The type of emd."
        ::= { pduDevMonEmdSlave13Entry 3}

pduDevMonEmdSlave13Name OBJECT-TYPE
        SYNTAX DisplayString (SIZE(0..31))
        ACCESS read-only
        STATUS mandatory
        DESCRIPTION
                "The name of emd."
        ::= { pduDevMonEmdSlave13Entry 4}

pduDevMonEmdSlave13TempName OBJECT-TYPE
        SYNTAX DisplayString (SIZE(0..31))
        ACCESS read-only
        STATUS mandatory
        DESCRIPTION
                "The name of emd temperature."
        ::= { pduDevMonEmdSlave13Entry 5}

pduDevMonEmdSlave13HumiName OBJECT-TYPE
        SYNTAX DisplayString (SIZE(0..31))
        ACCESS read-only
        STATUS mandatory
        DESCRIPTION
                "The name of emd humidity."
        ::= { pduDevMonEmdSlave13Entry 6}

pduDevMonEmdSlave13Alarm1Name OBJECT-TYPE
        SYNTAX DisplayString (SIZE(0..31))
        ACCESS read-only
        STATUS mandatory
        DESCRIPTION
                "The name of emd alarm-1."
        ::= { pduDevMonEmdSlave13Entry 7}

pduDevMonEmdSlave13Alarm2Name OBJECT-TYPE
        SYNTAX DisplayString (SIZE(0..31))
        ACCESS read-only
        STATUS mandatory
        DESCRIPTION
                "The name of emd alarm-2."
        ::= { pduDevMonEmdSlave13Entry 8}

pduDevMonEmdSlave13Temp OBJECT-TYPE
        SYNTAX INTEGER
        UNITS  "0.1degC"
        ACCESS read-only
        STATUS mandatory
        DESCRIPTION
                "The temperature of emd."
        ::= { pduDevMonEmdSlave13Entry 9}

pduDevMonEmdSlave13Humi OBJECT-TYPE
        SYNTAX INTEGER
        UNITS  "0.1%"
        ACCESS read-only
        STATUS mandatory
        DESCRIPTION
                "The humidity of emd."
        ::= { pduDevMonEmdSlave13Entry 10}

pduDevMonEmdSlave13TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave13Entry 11}

pduDevMonEmdSlave13HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave13Entry 12}

pduDevMonEmdSlave13Alarm1 OBJECT-TYPE
        SYNTAX INTEGER {
                normal(1),
                alarm(2)
                }
        ACCESS read-only
        STATUS mandatory
        DESCRIPTION
                "The alarm-1 of emd."
        ::= { pduDevMonEmdSlave13Entry 13}

pduDevMonEmdSlave13Alarm2 OBJECT-TYPE
        SYNTAX INTEGER {
                normal(1),
                alarm(2)
                }
        ACCESS read-only
        STATUS mandatory
        DESCRIPTION
                "The alarm-2 of emd."
        ::= { pduDevMonEmdSlave13Entry 14}


-- ===========================================================================
--
-- pduDevMonEmdSlave14
--
--  Slave14 Emd Monoitor Group
--
-- ===========================================================================
pduDevMonEmdSlave14Table OBJECT-TYPE
        SYNTAX SEQUENCE OF PduDevMonEmdSlave14Entry
        ACCESS not-accessible
        STATUS mandatory
        DESCRIPTION
                "Display a list of the emd information of Slave14."
        ::= { pduDevMonEmdSlave14 1}

pduDevMonEmdSlave14Entry OBJECT-TYPE
        SYNTAX PduDevMonEmdSlave14Entry
        ACCESS not-accessible
        STATUS mandatory
        DESCRIPTION
                "Display a list of the emd information of Slave14."
        INDEX  { pduDevMonEmdSlave14Index}
        ::= { pduDevMonEmdSlave14Table 1 }

PduDevMonEmdSlave14Entry ::=
        SEQUENCE {
                pduDevMonEmdSlave14Index
                        INTEGER,
                pduDevMonEmdSlave14Valid
                        INTEGER,
                pduDevMonEmdSlave14Type
                        INTEGER,
                pduDevMonEmdSlave14Name
                        DisplayString,
                pduDevMonEmdSlave14TempName
                        DisplayString,
                pduDevMonEmdSlave14HumiName
                        DisplayString,
                pduDevMonEmdSlave14Alarm1Name
                        DisplayString,
                pduDevMonEmdSlave14Alarm2Name
                        DisplayString,
                pduDevMonEmdSlave14Temp
                        INTEGER,
                pduDevMonEmdSlave14Humi
                        INTEGER,
                pduDevMonEmdSlave14TempSt
                        INTEGER,
                pduDevMonEmdSlave14HumiSt
                        INTEGER,
                pduDevMonEmdSlave14Alarm1
                        INTEGER,
                pduDevMonEmdSlave14Alarm2
                        INTEGER
        }

pduDevMonEmdSlave14Index OBJECT-TYPE
        SYNTAX INTEGER (0..7)
        ACCESS read-only
        STATUS mandatory
        DESCRIPTION
                "The index to a emd entry."
        ::= { pduDevMonEmdSlave14Entry 1 }

pduDevMonEmdSlave14Valid OBJECT-TYPE
        SYNTAX INTEGER {
                offline(1),
                online(2)
                }
        ACCESS read-only
        STATUS mandatory
        DESCRIPTION
                "The online status of emd."
        ::= { pduDevMonEmdSlave14Entry 2}


pduDevMonEmdSlave14Type OBJECT-TYPE
        SYNTAX INTEGER
        ACCESS read-only
        STATUS mandatory
        DESCRIPTION
                "The type of emd."
        ::= { pduDevMonEmdSlave14Entry 3}

pduDevMonEmdSlave14Name OBJECT-TYPE
        SYNTAX DisplayString (SIZE(0..31))
        ACCESS read-only
        STATUS mandatory
        DESCRIPTION
                "The name of emd."
        ::= { pduDevMonEmdSlave14Entry 4}

pduDevMonEmdSlave14TempName OBJECT-TYPE
        SYNTAX DisplayString (SIZE(0..31))
        ACCESS read-only
        STATUS mandatory
        DESCRIPTION
                "The name of emd temperature."
        ::= { pduDevMonEmdSlave14Entry 5}

pduDevMonEmdSlave14HumiName OBJECT-TYPE
        SYNTAX DisplayString (SIZE(0..31))
        ACCESS read-only
        STATUS mandatory
        DESCRIPTION
                "The name of emd humidity."
        ::= { pduDevMonEmdSlave14Entry 6}

pduDevMonEmdSlave14Alarm1Name OBJECT-TYPE
        SYNTAX DisplayString (SIZE(0..31))
        ACCESS read-only
        STATUS mandatory
        DESCRIPTION
                "The name of emd alarm-1."
        ::= { pduDevMonEmdSlave14Entry 7}

pduDevMonEmdSlave14Alarm2Name OBJECT-TYPE
        SYNTAX DisplayString (SIZE(0..31))
        ACCESS read-only
        STATUS mandatory
        DESCRIPTION
                "The name of emd alarm-2."
        ::= { pduDevMonEmdSlave14Entry 8}

pduDevMonEmdSlave14Temp OBJECT-TYPE
        SYNTAX INTEGER
        UNITS  "0.1degC"
        ACCESS read-only
        STATUS mandatory
        DESCRIPTION
                "The temperature of emd."
        ::= { pduDevMonEmdSlave14Entry 9}

pduDevMonEmdSlave14Humi OBJECT-TYPE
        SYNTAX INTEGER
        UNITS  "0.1%"
        ACCESS read-only
        STATUS mandatory
        DESCRIPTION
                "The humidity of emd."
        ::= { pduDevMonEmdSlave14Entry 10}

pduDevMonEmdSlave14TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave14Entry 11}

pduDevMonEmdSlave14HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave14Entry 12}

pduDevMonEmdSlave14Alarm1 OBJECT-TYPE
        SYNTAX INTEGER {
                normal(1),
                alarm(2)
                }
        ACCESS read-only
        STATUS mandatory
        DESCRIPTION
                "The alarm-1 of emd."
        ::= { pduDevMonEmdSlave14Entry 13}

pduDevMonEmdSlave14Alarm2 OBJECT-TYPE
        SYNTAX INTEGER {
                normal(1),
                alarm(2)
                }
        ACCESS read-only
        STATUS mandatory
        DESCRIPTION
                "The alarm-2 of emd."
        ::= { pduDevMonEmdSlave14Entry 14}


-- ===========================================================================
--
-- pduDevMonEmdSlave15
--
--  Slave15 Emd Monoitor Group
--
-- ===========================================================================
pduDevMonEmdSlave15Table OBJECT-TYPE
        SYNTAX SEQUENCE OF PduDevMonEmdSlave15Entry
        ACCESS not-accessible
        STATUS mandatory
        DESCRIPTION
                "Display a list of the emd information of Slave15."
        ::= { pduDevMonEmdSlave15 1}

pduDevMonEmdSlave15Entry OBJECT-TYPE
        SYNTAX PduDevMonEmdSlave15Entry
        ACCESS not-accessible
        STATUS mandatory
        DESCRIPTION
                "Display a list of the emd information of Slave15."
        INDEX  { pduDevMonEmdSlave15Index}
        ::= { pduDevMonEmdSlave15Table 1 }

PduDevMonEmdSlave15Entry ::=
        SEQUENCE {
                pduDevMonEmdSlave15Index
                        INTEGER,
                pduDevMonEmdSlave15Valid
                        INTEGER,
                pduDevMonEmdSlave15Type
                        INTEGER,
                pduDevMonEmdSlave15Name
                        DisplayString,
                pduDevMonEmdSlave15TempName
                        DisplayString,
                pduDevMonEmdSlave15HumiName
                        DisplayString,
                pduDevMonEmdSlave15Alarm1Name
                        DisplayString,
                pduDevMonEmdSlave15Alarm2Name
                        DisplayString,
                pduDevMonEmdSlave15Temp
                        INTEGER,
                pduDevMonEmdSlave15Humi
                        INTEGER,
                pduDevMonEmdSlave15TempSt
                        INTEGER,
                pduDevMonEmdSlave15HumiSt
                        INTEGER,
                pduDevMonEmdSlave15Alarm1
                        INTEGER,
                pduDevMonEmdSlave15Alarm2
                        INTEGER
        }

pduDevMonEmdSlave15Index OBJECT-TYPE
        SYNTAX INTEGER (0..7)
        ACCESS read-only
        STATUS mandatory
        DESCRIPTION
                "The index to a emd entry."
        ::= { pduDevMonEmdSlave15Entry 1 }

pduDevMonEmdSlave15Valid OBJECT-TYPE
        SYNTAX INTEGER {
                offline(1),
                online(2)
                }
        ACCESS read-only
        STATUS mandatory
        DESCRIPTION
                "The online status of emd."
        ::= { pduDevMonEmdSlave15Entry 2}


pduDevMonEmdSlave15Type OBJECT-TYPE
        SYNTAX INTEGER
        ACCESS read-only
        STATUS mandatory
        DESCRIPTION
                "The type of emd."
        ::= { pduDevMonEmdSlave15Entry 3}

pduDevMonEmdSlave15Name OBJECT-TYPE
        SYNTAX DisplayString (SIZE(0..31))
        ACCESS read-only
        STATUS mandatory
        DESCRIPTION
                "The name of emd."
        ::= { pduDevMonEmdSlave15Entry 4}

pduDevMonEmdSlave15TempName OBJECT-TYPE
        SYNTAX DisplayString (SIZE(0..31))
        ACCESS read-only
        STATUS mandatory
        DESCRIPTION
                "The name of emd temperature."
        ::= { pduDevMonEmdSlave15Entry 5}

pduDevMonEmdSlave15HumiName OBJECT-TYPE
        SYNTAX DisplayString (SIZE(0..31))
        ACCESS read-only
        STATUS mandatory
        DESCRIPTION
                "The name of emd humidity."
        ::= { pduDevMonEmdSlave15Entry 6}

pduDevMonEmdSlave15Alarm1Name OBJECT-TYPE
        SYNTAX DisplayString (SIZE(0..31))
        ACCESS read-only
        STATUS mandatory
        DESCRIPTION
                "The name of emd alarm-1."
        ::= { pduDevMonEmdSlave15Entry 7}

pduDevMonEmdSlave15Alarm2Name OBJECT-TYPE
        SYNTAX DisplayString (SIZE(0..31))
        ACCESS read-only
        STATUS mandatory
        DESCRIPTION
                "The name of emd alarm-2."
        ::= { pduDevMonEmdSlave15Entry 8}

pduDevMonEmdSlave15Temp OBJECT-TYPE
        SYNTAX INTEGER
        UNITS  "0.1degC"
        ACCESS read-only
        STATUS mandatory
        DESCRIPTION
                "The temperature of emd."
        ::= { pduDevMonEmdSlave15Entry 9}

pduDevMonEmdSlave15Humi OBJECT-TYPE
        SYNTAX INTEGER
        UNITS  "0.1%"
        ACCESS read-only
        STATUS mandatory
        DESCRIPTION
                "The humidity of emd."
        ::= { pduDevMonEmdSlave15Entry 10}

pduDevMonEmdSlave15TempSt OBJECT-TYPE
        SYNTAX INTEGER {
                normal(1),
                highWran(2),
                lowWran(3),
                highCrit(4),
                lowCrit(5)
                }
        ACCESS read-only
        STATUS mandatory
        DESCRIPTION
                "The temp status of emd."
        ::= { pduDevMonEmdSlave15Entry 11}

pduDevMonEmdSlave15HumiSt OBJECT-TYPE
        SYNTAX INTEGER {
                normal(1),
                highWran(2),
                lowWran(3),
                highCrit(4),
                lowCrit(5)
                }
        ACCESS read-only
        STATUS mandatory
        DESCRIPTION
                "The humi status of emd."
        ::= { pduDevMonEmdSlave15Entry 12}

pduDevMonEmdSlave15Alarm1 OBJECT-TYPE
        SYNTAX INTEGER {
                normal(1),
                alarm(2)
                }
        ACCESS read-only
        STATUS mandatory
        DESCRIPTION
                "The alarm-1 of emd."
        ::= { pduDevMonEmdSlave15Entry 13}

pduDevMonEmdSlave15Alarm2 OBJECT-TYPE
        SYNTAX INTEGER {
                normal(1),
                alarm(2)
                }
        ACCESS read-only
        STATUS mandatory
        DESCRIPTION
                "The alarm-2 of emd."
        ::= { pduDevMonEmdSlave15Entry 14}

-- ===========================================================================
--
-- pduDevMgmt
--
--  pdu Device Management Group
--
-- ===========================================================================
pduDevMgmtInlet      OBJECT IDENTIFIER ::= { pduDevMgmt 1 }
pduDevMgmtOutlet     OBJECT IDENTIFIER ::= { pduDevMgmt 2 }
pduDevMgmtEmd        OBJECT IDENTIFIER ::= { pduDevMgmt 3 }

-- ===========================================================================
--
-- pduDevMgmtInlet
--
--  Inlet Device Management Group
--
-- ===========================================================================
pduDevMgmtInletTable OBJECT-TYPE
        SYNTAX SEQUENCE OF PduDevMgmtInletEntry
        ACCESS not-accessible
        STATUS mandatory
        DESCRIPTION
                "A list to display setting of inlet of master."
        ::= { pduDevMgmtInlet 1}

pduDevMgmtInletEntry OBJECT-TYPE
        SYNTAX PduDevMgmtInletEntry
        ACCESS not-accessible
        STATUS mandatory
        DESCRIPTION
                "A list to display setting of inlet of master."
        INDEX  { pduDevMgmtInletIndex }
        ::= { pduDevMgmtInletTable 1 }

PduDevMgmtInletEntry ::=
        SEQUENCE {
                pduDevMgmtInletIndex
                        INTEGER,
                pduDevMgmtInletName
                        DisplayString,
                pduDevMgmtInletEnergyClr
                        INTEGER,
                pduDevMgmtInletOverLoadWarn
                        INTEGER,
                pduDevMgmtInletOverLoadCrit
                        INTEGER,
                pduDevMgmtInletLoadBalanceWarn
                        INTEGER,
                pduDevMgmtInletLoadBalanceCrit
                        INTEGER,
                pduDevMgmtInletOverVoltWarnPh1
                        INTEGER,
                pduDevMgmtInletOverVoltWarnPh2
                        INTEGER,
                pduDevMgmtInletOverVoltWarnPh3
                        INTEGER,
                pduDevMgmtInletOverVoltCritPh1
                        INTEGER,
                pduDevMgmtInletOverVoltCritPh2
                        INTEGER,
                pduDevMgmtInletOverVoltCritPh3
                        INTEGER,
                pduDevMgmtInletOverCurrTotalWarnPh1
                        INTEGER,
                pduDevMgmtInletOverCurrTotalWarnPh2
                        INTEGER,
                pduDevMgmtInletOverCurrTotalWarnPh3
                        INTEGER,
                pduDevMgmtInletOverCurrTotalCritPh1
                        INTEGER,
                pduDevMgmtInletOverCurrTotalCritPh2
                        INTEGER,
                pduDevMgmtInletOverCurrTotalCritPh3
                        INTEGER,
                pduDevMgmtInletOverCurrB1WarnPh1
                        INTEGER,
                pduDevMgmtInletOverCurrB1WarnPh2
                        INTEGER,
                pduDevMgmtInletOverCurrB1WarnPh3
                        INTEGER,
                pduDevMgmtInletOverCurrB1CritPh1
                        INTEGER,
                pduDevMgmtInletOverCurrB1CritPh2
                        INTEGER,
                pduDevMgmtInletOverCurrB1CritPh3
                        INTEGER,
                pduDevMgmtInletOverCurrB2WarnPh1
                        INTEGER,
                pduDevMgmtInletOverCurrB2WarnPh2
                        INTEGER,
                pduDevMgmtInletOverCurrB2WarnPh3
                        INTEGER,
                pduDevMgmtInletOverCurrB2CritPh1
                        INTEGER,
                pduDevMgmtInletOverCurrB2CritPh2
                        INTEGER,
                pduDevMgmtInletOverCurrB2CritPh3
                        INTEGER,
                pduDevMgmtInletRcmThld
                        INTEGER,
                pduDevMgmtInletOverPfB1WarnPh1
                        INTEGER,
                pduDevMgmtInletOverPfB1WarnPh2
                        INTEGER,
                pduDevMgmtInletOverPfB1WarnPh3
                        INTEGER,
                pduDevMgmtInletOverPfB1CritPh1
                        INTEGER,
                pduDevMgmtInletOverPfB1CritPh2
                        INTEGER,
                pduDevMgmtInletOverPfB1CritPh3
                        INTEGER,
                pduDevMgmtInletOverPfB2WarnPh1
                        INTEGER,
                pduDevMgmtInletOverPfB2WarnPh2
                        INTEGER,
                pduDevMgmtInletOverPfB2WarnPh3
                        INTEGER,
                pduDevMgmtInletOverPfB2CritPh1
                        INTEGER,
                pduDevMgmtInletOverPfB2CritPh2
                        INTEGER,
                pduDevMgmtInletOverPfB2CritPh3
                        INTEGER
        }

pduDevMgmtInletIndex OBJECT-TYPE
        SYNTAX INTEGER (0..15)
        ACCESS read-only
        STATUS mandatory
        DESCRIPTION
                "The index to a inlet entry."
        ::= { pduDevMgmtInletEntry 1 }

pduDevMgmtInletName OBJECT-TYPE
        SYNTAX DisplayString (SIZE(0..31))
        ACCESS read-write
        STATUS mandatory
        DESCRIPTION
                "The name of inlet."
        ::= { pduDevMgmtInletEntry 2 }

pduDevMgmtInletEnergyClr OBJECT-TYPE
        SYNTAX INTEGER {
                nothing(1),
                clearTotalEnergy(2),
                clearPhase1Energy(3),
                clearPhase2Energy(4),
                clearPhase3Energy(5)
                }
        ACCESS read-write
        STATUS mandatory
        DESCRIPTION
                "Clear energy of inlet."
        ::= { pduDevMgmtInletEntry 3}

pduDevMgmtInletOverLoadWarn OBJECT-TYPE
    SYNTAX INTEGER
    UNITS  "W"
    ACCESS read-write
    STATUS mandatory
    DESCRIPTION
            "The warning threshold of inlet load."
    ::= { pduDevMgmtInletEntry 4}

pduDevMgmtInletOverLoadCrit OBJECT-TYPE
    SYNTAX INTEGER
    UNITS  "W"
    ACCESS read-write
    STATUS mandatory
    DESCRIPTION
            "The critical threshold of inlet load."
    ::= { pduDevMgmtInletEntry 5}


pduDevMgmtInletLoadBalanceWarn OBJECT-TYPE
    SYNTAX INTEGER
    ACCESS read-write
    STATUS mandatory
    DESCRIPTION
            "The warning threshold of inlet load balance."
    ::= { pduDevMgmtInletEntry 6}

pduDevMgmtInletLoadBalanceCrit OBJECT-TYPE
    SYNTAX INTEGER
    ACCESS read-write
    STATUS mandatory
    DESCRIPTION
            "The critical threshold of inlet load balance."
    ::= { pduDevMgmtInletEntry 7}

pduDevMgmtInletOverVoltWarnPh1 OBJECT-TYPE
    SYNTAX INTEGER (0..3500)
    UNITS  "0.1V"
    ACCESS read-write
    STATUS mandatory
    DESCRIPTION
            "The warning threshold of pahse1 of inlet voltage."
    ::= { pduDevMgmtInletEntry 8}

pduDevMgmtInletOverVoltWarnPh2 OBJECT-TYPE
    SYNTAX INTEGER (0..3500)
    UNITS  "0.1V"
    ACCESS read-write
    STATUS mandatory
    DESCRIPTION
            "The warning threshold of pahse2 of inlet voltage."
    ::= { pduDevMgmtInletEntry 9}

pduDevMgmtInletOverVoltWarnPh3 OBJECT-TYPE
    SYNTAX INTEGER (0..3500)
    UNITS  "0.1V"
    ACCESS read-write
    STATUS mandatory
    DESCRIPTION
            "The warning threshold of pahse3 of inlet voltage."
    ::= { pduDevMgmtInletEntry 10}

pduDevMgmtInletOverVoltCritPh1 OBJECT-TYPE
    SYNTAX INTEGER (0..3500)
    UNITS  "0.1V"
    ACCESS read-write
    STATUS mandatory
    DESCRIPTION
            "The critical threshold of pahse1 of inlet voltage."
    ::= { pduDevMgmtInletEntry 11}

pduDevMgmtInletOverVoltCritPh2 OBJECT-TYPE
    SYNTAX INTEGER (0..3500)
    UNITS  "0.1V"
    ACCESS read-write
    STATUS mandatory
    DESCRIPTION
            "The critical threshold of pahse2 of inlet voltage."
    ::= { pduDevMgmtInletEntry 12}

pduDevMgmtInletOverVoltCritPh3 OBJECT-TYPE
    SYNTAX INTEGER (0..3500)
    UNITS  "0.1V"
    ACCESS read-write
    STATUS mandatory
    DESCRIPTION
            "The critical threshold of pahse3 of inlet voltage."
    ::= { pduDevMgmtInletEntry 13}

pduDevMgmtInletOverCurrTotalWarnPh1 OBJECT-TYPE
    SYNTAX INTEGER (0..3200)
    UNITS  "0.01A"
    ACCESS read-write
    STATUS mandatory
    DESCRIPTION
            "The warning threshold of pahse1 of inlet total current."
    ::= { pduDevMgmtInletEntry 14}

pduDevMgmtInletOverCurrTotalWarnPh2 OBJECT-TYPE
    SYNTAX INTEGER (0..3200)
    UNITS  "0.01A"
    ACCESS read-write
    STATUS mandatory
    DESCRIPTION
            "The warning threshold of pahse2 of inlet total current."
    ::= { pduDevMgmtInletEntry 15}

pduDevMgmtInletOverCurrTotalWarnPh3 OBJECT-TYPE
    SYNTAX INTEGER (0..3200)
    UNITS  "0.01A"
    ACCESS read-write
    STATUS mandatory
    DESCRIPTION
            "The warning threshold of pahse3 of inlet total current."
    ::= { pduDevMgmtInletEntry 16}

pduDevMgmtInletOverCurrTotalCritPh1 OBJECT-TYPE
    SYNTAX INTEGER (0..3200)
    UNITS  "0.01A"
    ACCESS read-write
    STATUS mandatory
    DESCRIPTION
            "The critical threshold of pahse1 of inlet total current."
    ::= { pduDevMgmtInletEntry 17}

pduDevMgmtInletOverCurrTotalCritPh2 OBJECT-TYPE
    SYNTAX INTEGER (0..3200)
    UNITS  "0.01A"
    ACCESS read-write
    STATUS mandatory
    DESCRIPTION
            "The critical threshold of pahse2 of inlet total current."
    ::= { pduDevMgmtInletEntry 18}

pduDevMgmtInletOverCurrTotalCritPh3 OBJECT-TYPE
    SYNTAX INTEGER (0..3200)
    UNITS  "0.01A"
    ACCESS read-write
    STATUS mandatory
    DESCRIPTION
            "The critical threshold of pahse3 of inlet total current."
    ::= { pduDevMgmtInletEntry 19}

pduDevMgmtInletOverCurrB1WarnPh1 OBJECT-TYPE
    SYNTAX INTEGER (0..1600)
    UNITS  "0.01A"
    ACCESS read-write
    STATUS mandatory
    DESCRIPTION
            "The warning threshold of pahse1b1 of inlet current."
    ::= { pduDevMgmtInletEntry 20}

pduDevMgmtInletOverCurrB1WarnPh2 OBJECT-TYPE
    SYNTAX INTEGER (0..1600)
    UNITS  "0.01A"
    ACCESS read-write
    STATUS mandatory
    DESCRIPTION
            "The warning threshold of pahse2b1 of inlet current."
    ::= { pduDevMgmtInletEntry 21}

pduDevMgmtInletOverCurrB1WarnPh3 OBJECT-TYPE
    SYNTAX INTEGER (0..1600)
    UNITS  "0.01A"
    ACCESS read-write
    STATUS mandatory
    DESCRIPTION
            "The warning threshold of pahse2b1 of inlet current."
    ::= { pduDevMgmtInletEntry 22}

pduDevMgmtInletOverCurrB1CritPh1 OBJECT-TYPE
    SYNTAX INTEGER (0..1600)
    UNITS  "0.01A"
    ACCESS read-write
    STATUS mandatory
    DESCRIPTION
            "The critical threshold of pahse1b1 of inlet current."
    ::= { pduDevMgmtInletEntry 23}

pduDevMgmtInletOverCurrB1CritPh2 OBJECT-TYPE
    SYNTAX INTEGER (0..1600)
    UNITS  "0.01A"
    ACCESS read-write
    STATUS mandatory
    DESCRIPTION
            "The critical threshold of pahse2b1 of inlet current."
    ::= { pduDevMgmtInletEntry 24}

pduDevMgmtInletOverCurrB1CritPh3 OBJECT-TYPE
    SYNTAX INTEGER (0..1600)
    UNITS  "0.01A"
    ACCESS read-write
    STATUS mandatory
    DESCRIPTION
            "The critical threshold of pahse3b1 of inlet current."
    ::= { pduDevMgmtInletEntry 25}

pduDevMgmtInletOverCurrB2WarnPh1 OBJECT-TYPE
    SYNTAX INTEGER (0..1600)
    UNITS  "0.01A"
    ACCESS read-write
    STATUS mandatory
    DESCRIPTION
            "The warning threshold of pahse1b2 of inlet current."
    ::= { pduDevMgmtInletEntry 26}

pduDevMgmtInletOverCurrB2WarnPh2 OBJECT-TYPE
    SYNTAX INTEGER (0..1600)
    UNITS  "0.01A"
    ACCESS read-write
    STATUS mandatory
    DESCRIPTION
            "The warning threshold of pahse2b2 of inlet current."
    ::= { pduDevMgmtInletEntry 27}

pduDevMgmtInletOverCurrB2WarnPh3 OBJECT-TYPE
    SYNTAX INTEGER (0..1600)
    UNITS  "0.01A"
    ACCESS read-write
    STATUS mandatory
    DESCRIPTION
            "The warning threshold of pahse3b2 of inlet current."
    ::= { pduDevMgmtInletEntry 28}

pduDevMgmtInletOverCurrB2CritPh1 OBJECT-TYPE
    SYNTAX INTEGER (0..1600)
    UNITS  "0.01A"
    ACCESS read-write
    STATUS mandatory
    DESCRIPTION
            "The critical threshold of pahse1b2 of inlet current."
    ::= { pduDevMgmtInletEntry 29}

pduDevMgmtInletOverCurrB2CritPh2 OBJECT-TYPE
    SYNTAX INTEGER (0..1600)
    UNITS  "0.01A"
    ACCESS read-write
    STATUS mandatory
    DESCRIPTION
            "The critical threshold of pahse2b2 of inlet current."
    ::= { pduDevMgmtInletEntry 30}

pduDevMgmtInletOverCurrB2CritPh3 OBJECT-TYPE
    SYNTAX INTEGER (0..1600)
    UNITS  "0.01A"
    ACCESS read-write
    STATUS mandatory
    DESCRIPTION
            "The critical threshold of pahse3b2 of inlet current."
    ::= { pduDevMgmtInletEntry 31}

pduDevMgmtInletRcmThld OBJECT-TYPE
    SYNTAX INTEGER (3..50)
    UNITS  "1mA"
    ACCESS read-write
    STATUS mandatory
    DESCRIPTION
            "Leakage current alarm threshold."
    ::= { pduDevMgmtInletEntry 32}

pduDevMgmtInletOverPfB1WarnPh1 OBJECT-TYPE
    SYNTAX INTEGER (0..1000)
    UNITS  "0.1%"
    ACCESS read-write
    STATUS mandatory
    DESCRIPTION
            "The warning threshold of pahse1b1 of inlet pf."
    ::= { pduDevMgmtInletEntry 33}

pduDevMgmtInletOverPfB1WarnPh2 OBJECT-TYPE
    SYNTAX INTEGER (0..1000)
    UNITS  "0.1%"
    ACCESS read-write
    STATUS mandatory
    DESCRIPTION
            "The warning threshold of pahse2b1 of inlet pf."
    ::= { pduDevMgmtInletEntry 34}

pduDevMgmtInletOverPfB1WarnPh3 OBJECT-TYPE
    SYNTAX INTEGER (0..1000)
    UNITS  "0.1%"
    ACCESS read-write
    STATUS mandatory
    DESCRIPTION
            "The warning threshold of pahse2b1 of inlet pf."
    ::= { pduDevMgmtInletEntry 35}

pduDevMgmtInletOverPfB1CritPh1 OBJECT-TYPE
    SYNTAX INTEGER (0..1000)
    UNITS  "0.1%"
    ACCESS read-write
    STATUS mandatory
    DESCRIPTION
            "The critical threshold of pahse1b1 of inlet pf."
    ::= { pduDevMgmtInletEntry 36}

pduDevMgmtInletOverPfB1CritPh2 OBJECT-TYPE
    SYNTAX INTEGER (0..1000)
    UNITS  "0.1%"
    ACCESS read-write
    STATUS mandatory
    DESCRIPTION
            "The critical threshold of pahse2b1 of inlet pf."
    ::= { pduDevMgmtInletEntry 37}

pduDevMgmtInletOverPfB1CritPh3 OBJECT-TYPE
    SYNTAX INTEGER (0..1000)
    UNITS  "0.1%"
    ACCESS read-write
    STATUS mandatory
    DESCRIPTION
            "The critical threshold of pahse3b1 of inlet pf."
    ::= { pduDevMgmtInletEntry 38}

pduDevMgmtInletOverPfB2WarnPh1 OBJECT-TYPE
    SYNTAX INTEGER (0..1000)
    UNITS  "0.1%"
    ACCESS read-write
    STATUS mandatory
    DESCRIPTION
            "The warning threshold of pahse1b2 of inlet pf."
    ::= { pduDevMgmtInletEntry 39}

pduDevMgmtInletOverPfB2WarnPh2 OBJECT-TYPE
    SYNTAX INTEGER (0..1000)
    UNITS  "0.1%"
    ACCESS read-write
    STATUS mandatory
    DESCRIPTION
            "The warning threshold of pahse2b2 of inlet pf."
    ::= { pduDevMgmtInletEntry 40}

pduDevMgmtInletOverPfB2WarnPh3 OBJECT-TYPE
    SYNTAX INTEGER (0..1000)
    UNITS  "0.1%"
    ACCESS read-write
    STATUS mandatory
    DESCRIPTION
            "The warning threshold of pahse3b2 of inlet pf."
    ::= { pduDevMgmtInletEntry 41}

pduDevMgmtInletOverPfB2CritPh1 OBJECT-TYPE
    SYNTAX INTEGER (0..1000)
    UNITS  "0.1%"
    ACCESS read-write
    STATUS mandatory
    DESCRIPTION
            "The critical threshold of pahse1b2 of inlet pf."
    ::= { pduDevMgmtInletEntry 42}

pduDevMgmtInletOverPfB2CritPh2 OBJECT-TYPE
    SYNTAX INTEGER (0..1000)
    UNITS  "0.1%"
    ACCESS read-write
    STATUS mandatory
    DESCRIPTION
            "The critical threshold of pahse2b2 of inlet pf."
    ::= { pduDevMgmtInletEntry 43}

pduDevMgmtInletOverPfB2CritPh3 OBJECT-TYPE
    SYNTAX INTEGER (0..1000)
    UNITS  "0.1%"
    ACCESS read-write
    STATUS mandatory
    DESCRIPTION
            "The critical threshold of pahse3b2 of inlet pf."
    ::= { pduDevMgmtInletEntry 44}

-- ===========================================================================
--
-- pduDevMgmtOutlet
--
--  Outlet Device Management Group
--
-- ===========================================================================
pduDevMgmtOutletMaster      OBJECT IDENTIFIER ::= { pduDevMgmtOutlet 1 }
pduDevMgmtOutletSlave01     OBJECT IDENTIFIER ::= { pduDevMgmtOutlet 2 }
pduDevMgmtOutletSlave02     OBJECT IDENTIFIER ::= { pduDevMgmtOutlet 3 }
pduDevMgmtOutletSlave03     OBJECT IDENTIFIER ::= { pduDevMgmtOutlet 4 }
pduDevMgmtOutletSlave04     OBJECT IDENTIFIER ::= { pduDevMgmtOutlet 5 }
pduDevMgmtOutletSlave05     OBJECT IDENTIFIER ::= { pduDevMgmtOutlet 6 }
pduDevMgmtOutletSlave06     OBJECT IDENTIFIER ::= { pduDevMgmtOutlet 7 }
pduDevMgmtOutletSlave07     OBJECT IDENTIFIER ::= { pduDevMgmtOutlet 8 }
pduDevMgmtOutletSlave08     OBJECT IDENTIFIER ::= { pduDevMgmtOutlet 9 }
pduDevMgmtOutletSlave09     OBJECT IDENTIFIER ::= { pduDevMgmtOutlet 10 }
pduDevMgmtOutletSlave10     OBJECT IDENTIFIER ::= { pduDevMgmtOutlet 11 }
pduDevMgmtOutletSlave11     OBJECT IDENTIFIER ::= { pduDevMgmtOutlet 12 }
pduDevMgmtOutletSlave12     OBJECT IDENTIFIER ::= { pduDevMgmtOutlet 13 }
pduDevMgmtOutletSlave13     OBJECT IDENTIFIER ::= { pduDevMgmtOutlet 14 }
pduDevMgmtOutletSlave14     OBJECT IDENTIFIER ::= { pduDevMgmtOutlet 15 }
pduDevMgmtOutletSlave15     OBJECT IDENTIFIER ::= { pduDevMgmtOutlet 16 }

-- ===========================================================================
--
-- pduDevMgmtOutletMaster
--
--  Master Outlet Mgmtoitor Group
--
-- ===========================================================================
pduDevMgmtOutletMasterPortSize OBJECT-TYPE
        SYNTAX INTEGER
        ACCESS read-only
        STATUS mandatory
        DESCRIPTION
                "The port size of master."
        ::= { pduDevMgmtOutletMaster 1}

-- ===========================================================================
--
-- pduDevMgmtOutletMasterPort
--
--  Master Outlet Port Mgmtoitor Group
--
-- ===========================================================================
pduDevMgmtOutletMasterPortTable OBJECT-TYPE
        SYNTAX SEQUENCE OF PduDevMgmtOutletMasterPortEntry
        ACCESS not-accessible
        STATUS mandatory
        DESCRIPTION
                "Display the port information list of MasterPort."
        ::= { pduDevMgmtOutletMaster 2}

pduDevMgmtOutletMasterPortEntry OBJECT-TYPE
        SYNTAX PduDevMgmtOutletMasterPortEntry
        ACCESS not-accessible
        STATUS mandatory
        DESCRIPTION
                "Display the port information list of MasterPort.."
        INDEX  { pduDevMgmtOutletMasterPortIndex}
        ::= { pduDevMgmtOutletMasterPortTable 1 }

PduDevMgmtOutletMasterPortEntry ::=
        SEQUENCE {
                pduDevMgmtOutletMasterPortIndex
                        INTEGER,
                pduDevMgmtOutletMasterPortValid
                        INTEGER,
                pduDevMgmtOutletMasterPortEnergyClr
                        INTEGER,
                pduDevMgmtOutletMasterPortName
                        DisplayString,
                pduDevMgmtOutletMasterPortOnDelayTime
                        INTEGER,
                pduDevMgmtOutletMasterPortOnDelayStatus
                        INTEGER,
                pduDevMgmtOutletMasterPortOffDelayTime
                        INTEGER,
                pduDevMgmtOutletMasterPortOffDelayStatus
                        INTEGER,
                pduDevMgmtOutletMasterPortRebootTime
                        INTEGER,
                pduDevMgmtOutletMasterPortOverCurrWarn
                        INTEGER,
                pduDevMgmtOutletMasterPortOverCurrCrit
                        INTEGER,
                pduDevMgmtOutletMasterPortOverPowerWarn
                        INTEGER,
                pduDevMgmtOutletMasterPortOverPowerCrit
                        INTEGER,
                pduDevMgmtOutletMasterPortRly
                        INTEGER
        }

pduDevMgmtOutletMasterPortIndex OBJECT-TYPE
        SYNTAX INTEGER (0..63)
        ACCESS read-only
        STATUS mandatory
        DESCRIPTION
                "The index to a outlet entry."
        ::= { pduDevMgmtOutletMasterPortEntry 1 }

pduDevMgmtOutletMasterPortValid OBJECT-TYPE
        SYNTAX INTEGER {
                offline(1),
                online(2)
                }
        ACCESS read-only
        STATUS mandatory
        DESCRIPTION
                "The online status of outlet."
        ::= { pduDevMgmtOutletMasterPortEntry 2 }

pduDevMgmtOutletMasterPortEnergyClr OBJECT-TYPE
        SYNTAX INTEGER {
                nothing(1),
                clearEnergy(2)
                }
        ACCESS read-write
        STATUS mandatory
        DESCRIPTION
                "Clear energy of outlet."
        ::= { pduDevMgmtOutletMasterPortEntry 3 }

pduDevMgmtOutletMasterPortName OBJECT-TYPE
        SYNTAX DisplayString (SIZE(0..31))
        ACCESS read-write
        STATUS mandatory
        DESCRIPTION
                "The name of outlet."
        ::= { pduDevMgmtOutletMasterPortEntry 4 }

pduDevMgmtOutletMasterPortOnDelayTime OBJECT-TYPE
        SYNTAX INTEGER (1..7200)
        ACCESS read-write
        STATUS mandatory
        DESCRIPTION
                "The on delay of outlet."
        ::= { pduDevMgmtOutletMasterPortEntry 5}

pduDevMgmtOutletMasterPortOnDelayStatus OBJECT-TYPE
        SYNTAX  INTEGER {
                nodelay(1),
                delay(2)
                }
        ACCESS read-write
        STATUS mandatory
        DESCRIPTION
                "The delay on status of outlet."
        ::= { pduDevMgmtOutletMasterPortEntry 6}

pduDevMgmtOutletMasterPortOffDelayTime OBJECT-TYPE
        SYNTAX INTEGER (1..7200)
        ACCESS read-write
        STATUS mandatory
        DESCRIPTION
                "The off delay of outlet."
        ::= { pduDevMgmtOutletMasterPortEntry 7}

pduDevMgmtOutletMasterPortOffDelayStatus OBJECT-TYPE
        SYNTAX  INTEGER {
                nodelay(1),
                delay(2)
                }
        ACCESS read-write
        STATUS mandatory
        DESCRIPTION
                "The delay off status of outlet."
        ::= { pduDevMgmtOutletMasterPortEntry 8}

pduDevMgmtOutletMasterPortRebootTime OBJECT-TYPE
        SYNTAX INTEGER (5..60)
        ACCESS read-write
        STATUS mandatory
        DESCRIPTION
                "The reboot time of outlet."
        ::= { pduDevMgmtOutletMasterPortEntry 9}

pduDevMgmtOutletMasterPortOverCurrWarn OBJECT-TYPE
        SYNTAX INTEGER (0..1600)
        UNITS  "0.01A"
        ACCESS read-write
        STATUS mandatory
        DESCRIPTION
                "The warning threshold of outlet current."
        ::= { pduDevMgmtOutletMasterPortEntry 10}

pduDevMgmtOutletMasterPortOverCurrCrit OBJECT-TYPE
        SYNTAX INTEGER (0..1600)
        UNITS  "0.01A"
        ACCESS read-write
        STATUS mandatory
        DESCRIPTION
                "The critical threshold of outlet current."
        ::= { pduDevMgmtOutletMasterPortEntry 11}

pduDevMgmtOutletMasterPortOverPowerWarn OBJECT-TYPE
        SYNTAX INTEGER (0..27500)
        ACCESS read-write
        STATUS mandatory
        DESCRIPTION
                "The warning threshold of outlet power."
        ::= { pduDevMgmtOutletMasterPortEntry 12}

pduDevMgmtOutletMasterPortOverPowerCrit OBJECT-TYPE
        SYNTAX INTEGER (0..27500)
        ACCESS read-write
        STATUS mandatory
        DESCRIPTION
                "The critical threshold of outlet power."
        ::= { pduDevMgmtOutletMasterPortEntry 13}

pduDevMgmtOutletMasterPortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletMasterPortEntry 14 }

-- ===========================================================================
--
-- pduDevMgmtOutletSlave01
--
--  Slave01 Outlet Mgmtoitor Group
--
-- ===========================================================================
pduDevMgmtOutletSlave01PortSize OBJECT-TYPE
        SYNTAX INTEGER
        ACCESS read-only
        STATUS mandatory
        DESCRIPTION
                "The port size of master."
        ::= { pduDevMgmtOutletSlave01 1}

-- ===========================================================================
--
-- pduDevMgmtOutletSlave01Port
--
--  Slave01 Outlet Port Mgmtoitor Group
--
-- ===========================================================================
pduDevMgmtOutletSlave01PortTable OBJECT-TYPE
        SYNTAX SEQUENCE OF PduDevMgmtOutletSlave01PortEntry
        ACCESS not-accessible
        STATUS mandatory
        DESCRIPTION
                "Display the port information list of Slave01Port."
        ::= { pduDevMgmtOutletSlave01 2}

pduDevMgmtOutletSlave01PortEntry OBJECT-TYPE
        SYNTAX PduDevMgmtOutletSlave01PortEntry
        ACCESS not-accessible
        STATUS mandatory
        DESCRIPTION
                "Display the port information list of Slave01Port.."
        INDEX  { pduDevMgmtOutletSlave01PortIndex}
        ::= { pduDevMgmtOutletSlave01PortTable 1 }

PduDevMgmtOutletSlave01PortEntry ::=
        SEQUENCE {
                pduDevMgmtOutletSlave01PortIndex
                        INTEGER,
                pduDevMgmtOutletSlave01PortValid
                        INTEGER,
                pduDevMgmtOutletSlave01PortEnergyClr
                        INTEGER,
                pduDevMgmtOutletSlave01PortName
                        DisplayString,
                pduDevMgmtOutletSlave01PortOnDelayTime
                        INTEGER,
                pduDevMgmtOutletSlave01PortOnDelayStatus
                        INTEGER,
                pduDevMgmtOutletSlave01PortOffDelayTime
                        INTEGER,
                pduDevMgmtOutletSlave01PortOffDelayStatus
                        INTEGER,
                pduDevMgmtOutletSlave01PortRebootTime
                        INTEGER,
                pduDevMgmtOutletSlave01PortOverCurrWarn
                        INTEGER,
                pduDevMgmtOutletSlave01PortOverCurrCrit
                        INTEGER,
                pduDevMgmtOutletSlave01PortOverPowerWarn
                        INTEGER,
                pduDevMgmtOutletSlave01PortOverPowerCrit
                        INTEGER,
                pduDevMgmtOutletSlave01PortRly
                        INTEGER
        }

pduDevMgmtOutletSlave01PortIndex OBJECT-TYPE
        SYNTAX INTEGER (0..63)
        ACCESS read-only
        STATUS mandatory
        DESCRIPTION
                "The index to a outlet entry."
        ::= { pduDevMgmtOutletSlave01PortEntry 1 }

pduDevMgmtOutletSlave01PortValid OBJECT-TYPE
        SYNTAX INTEGER {
                offline(1),
                online(2)
                }
        ACCESS read-only
        STATUS mandatory
        DESCRIPTION
                "The online status of outlet."
        ::= { pduDevMgmtOutletSlave01PortEntry 2 }

pduDevMgmtOutletSlave01PortEnergyClr OBJECT-TYPE
        SYNTAX INTEGER {
                nothing(1),
                clearEnergy(2)
                }
        ACCESS read-write
        STATUS mandatory
        DESCRIPTION
                "Clear energy of outlet."
        ::= { pduDevMgmtOutletSlave01PortEntry 3 }

pduDevMgmtOutletSlave01PortName OBJECT-TYPE
        SYNTAX DisplayString (SIZE(0..31))
        ACCESS read-write
        STATUS mandatory
        DESCRIPTION
                "The name of outlet."
        ::= { pduDevMgmtOutletSlave01PortEntry 4 }

pduDevMgmtOutletSlave01PortOnDelayTime OBJECT-TYPE
        SYNTAX INTEGER (1..7200)
        ACCESS read-write
        STATUS mandatory
        DESCRIPTION
                "The on delay of outlet."
        ::= { pduDevMgmtOutletSlave01PortEntry 5}

pduDevMgmtOutletSlave01PortOnDelayStatus OBJECT-TYPE
        SYNTAX  INTEGER {
                nodelay(1),
                delay(2)
                }
        ACCESS read-write
        STATUS mandatory
        DESCRIPTION
                "The delay on status of outlet."
        ::= { pduDevMgmtOutletSlave01PortEntry 6}

pduDevMgmtOutletSlave01PortOffDelayTime OBJECT-TYPE
        SYNTAX INTEGER (1..7200)
        ACCESS read-write
        STATUS mandatory
        DESCRIPTION
                "The off delay of outlet."
        ::= { pduDevMgmtOutletSlave01PortEntry 7}

pduDevMgmtOutletSlave01PortOffDelayStatus OBJECT-TYPE
        SYNTAX  INTEGER {
                nodelay(1),
                delay(2)
                }
        ACCESS read-write
        STATUS mandatory
        DESCRIPTION
                "The delay off status of outlet."
        ::= { pduDevMgmtOutletSlave01PortEntry 8}

pduDevMgmtOutletSlave01PortRebootTime OBJECT-TYPE
        SYNTAX INTEGER (5..60)
        ACCESS read-write
        STATUS mandatory
        DESCRIPTION
                "The reboot time of outlet."
        ::= { pduDevMgmtOutletSlave01PortEntry 9}

pduDevMgmtOutletSlave01PortOverCurrWarn OBJECT-TYPE
        SYNTAX INTEGER (0..1600)
        UNITS  "0.01A"
        ACCESS read-write
        STATUS mandatory
        DESCRIPTION
                "The warning threshold of outlet current."
        ::= { pduDevMgmtOutletSlave01PortEntry 10}

pduDevMgmtOutletSlave01PortOverCurrCrit OBJECT-TYPE
        SYNTAX INTEGER (0..1600)
        UNITS  "0.01A"
        ACCESS read-write
        STATUS mandatory
        DESCRIPTION
                "The critical threshold of outlet current."
        ::= { pduDevMgmtOutletSlave01PortEntry 11}

pduDevMgmtOutletSlave01PortOverPowerWarn OBJECT-TYPE
        SYNTAX INTEGER (0..27500)
        ACCESS read-write
        STATUS mandatory
        DESCRIPTION
                "The warning threshold of outlet power."
        ::= { pduDevMgmtOutletSlave01PortEntry 12}

pduDevMgmtOutletSlave01PortOverPowerCrit OBJECT-TYPE
        SYNTAX INTEGER (0..27500)
        ACCESS read-write
        STATUS mandatory
        DESCRIPTION
                "The critical threshold of outlet power."
        ::= { pduDevMgmtOutletSlave01PortEntry 13}

pduDevMgmtOutletSlave01PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave01PortEntry 14 }

-- ===========================================================================
--
-- pduDevMgmtOutletSlave02
--
--  Slave02 Outlet Mgmtoitor Group
--
-- ===========================================================================
pduDevMgmtOutletSlave02PortSize OBJECT-TYPE
        SYNTAX INTEGER
        ACCESS read-only
        STATUS mandatory
        DESCRIPTION
                "The port size of master."
        ::= { pduDevMgmtOutletSlave02 1}

-- ===========================================================================
--
-- pduDevMgmtOutletSlave02Port
--
--  Slave02 Outlet Port Mgmtoitor Group
--
-- ===========================================================================
pduDevMgmtOutletSlave02PortTable OBJECT-TYPE
        SYNTAX SEQUENCE OF PduDevMgmtOutletSlave02PortEntry
        ACCESS not-accessible
        STATUS mandatory
        DESCRIPTION
                "Display the port information list of Slave02Port."
        ::= { pduDevMgmtOutletSlave02 2}

pduDevMgmtOutletSlave02PortEntry OBJECT-TYPE
        SYNTAX PduDevMgmtOutletSlave02PortEntry
        ACCESS not-accessible
        STATUS mandatory
        DESCRIPTION
                "Display the port information list of Slave02Port.."
        INDEX  { pduDevMgmtOutletSlave02PortIndex}
        ::= { pduDevMgmtOutletSlave02PortTable 1 }

PduDevMgmtOutletSlave02PortEntry ::=
        SEQUENCE {
                pduDevMgmtOutletSlave02PortIndex
                        INTEGER,
                pduDevMgmtOutletSlave02PortValid
                        INTEGER,
                pduDevMgmtOutletSlave02PortEnergyClr
                        INTEGER,
                pduDevMgmtOutletSlave02PortName
                        DisplayString,
                pduDevMgmtOutletSlave02PortOnDelayTime
                        INTEGER,
                pduDevMgmtOutletSlave02PortOnDelayStatus
                        INTEGER,
                pduDevMgmtOutletSlave02PortOffDelayTime
                        INTEGER,
                pduDevMgmtOutletSlave02PortOffDelayStatus
                        INTEGER,
                pduDevMgmtOutletSlave02PortRebootTime
                        INTEGER,
                pduDevMgmtOutletSlave02PortOverCurrWarn
                        INTEGER,
                pduDevMgmtOutletSlave02PortOverCurrCrit
                        INTEGER,
                pduDevMgmtOutletSlave02PortOverPowerWarn
                        INTEGER,
                pduDevMgmtOutletSlave02PortOverPowerCrit
                        INTEGER,
                pduDevMgmtOutletSlave02PortRly
                        INTEGER
        }

pduDevMgmtOutletSlave02PortIndex OBJECT-TYPE
        SYNTAX INTEGER (0..63)
        ACCESS read-only
        STATUS mandatory
        DESCRIPTION
                "The index to a outlet entry."
        ::= { pduDevMgmtOutletSlave02PortEntry 1 }

pduDevMgmtOutletSlave02PortValid OBJECT-TYPE
        SYNTAX INTEGER {
                offline(1),
                online(2)
                }
        ACCESS read-only
        STATUS mandatory
        DESCRIPTION
                "The online status of outlet."
        ::= { pduDevMgmtOutletSlave02PortEntry 2 }

pduDevMgmtOutletSlave02PortEnergyClr OBJECT-TYPE
        SYNTAX INTEGER {
                nothing(1),
                clearEnergy(2)
                }
        ACCESS read-write
        STATUS mandatory
        DESCRIPTION
                "Clear energy of outlet."
        ::= { pduDevMgmtOutletSlave02PortEntry 3 }

pduDevMgmtOutletSlave02PortName OBJECT-TYPE
        SYNTAX DisplayString (SIZE(0..31))
        ACCESS read-write
        STATUS mandatory
        DESCRIPTION
                "The name of outlet."
        ::= { pduDevMgmtOutletSlave02PortEntry 4 }

pduDevMgmtOutletSlave02PortOnDelayTime OBJECT-TYPE
        SYNTAX INTEGER (1..7200)
        ACCESS read-write
        STATUS mandatory
        DESCRIPTION
                "The on delay of outlet."
        ::= { pduDevMgmtOutletSlave02PortEntry 5}

pduDevMgmtOutletSlave02PortOnDelayStatus OBJECT-TYPE
        SYNTAX  INTEGER {
                nodelay(1),
                delay(2)
                }
        ACCESS read-write
        STATUS mandatory
        DESCRIPTION
                "The delay on status of outlet."
        ::= { pduDevMgmtOutletSlave02PortEntry 6}

pduDevMgmtOutletSlave02PortOffDelayTime OBJECT-TYPE
        SYNTAX INTEGER (1..7200)
        ACCESS read-write
        STATUS mandatory
        DESCRIPTION
                "The off delay of outlet."
        ::= { pduDevMgmtOutletSlave02PortEntry 7}

pduDevMgmtOutletSlave02PortOffDelayStatus OBJECT-TYPE
        SYNTAX  INTEGER {
                nodelay(1),
                delay(2)
                }
        ACCESS read-write
        STATUS mandatory
        DESCRIPTION
                "The delay off status of outlet."
        ::= { pduDevMgmtOutletSlave02PortEntry 8}

pduDevMgmtOutletSlave02PortRebootTime OBJECT-TYPE
        SYNTAX INTEGER (5..60)
        ACCESS read-write
        STATUS mandatory
        DESCRIPTION
                "The reboot time of outlet."
        ::= { pduDevMgmtOutletSlave02PortEntry 9}

pduDevMgmtOutletSlave02PortOverCurrWarn OBJECT-TYPE
        SYNTAX INTEGER (0..1600)
        UNITS  "0.01A"
        ACCESS read-write
        STATUS mandatory
        DESCRIPTION
                "The warning threshold of outlet current."
        ::= { pduDevMgmtOutletSlave02PortEntry 10}

pduDevMgmtOutletSlave02PortOverCurrCrit OBJECT-TYPE
        SYNTAX INTEGER (0..1600)
        UNITS  "0.01A"
        ACCESS read-write
        STATUS mandatory
        DESCRIPTION
                "The critical threshold of outlet current."
        ::= { pduDevMgmtOutletSlave02PortEntry 11}

pduDevMgmtOutletSlave02PortOverPowerWarn OBJECT-TYPE
        SYNTAX INTEGER (0..27500)
        ACCESS read-write
        STATUS mandatory
        DESCRIPTION
                "The warning threshold of outlet power."
        ::= { pduDevMgmtOutletSlave02PortEntry 12}

pduDevMgmtOutletSlave02PortOverPowerCrit OBJECT-TYPE
        SYNTAX INTEGER (0..27500)
        ACCESS read-write
        STATUS mandatory
        DESCRIPTION
                "The critical threshold of outlet power."
        ::= { pduDevMgmtOutletSlave02PortEntry 13}

pduDevMgmtOutletSlave02PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave02PortEntry 14 }

-- ===========================================================================
--
-- pduDevMgmtOutletSlave03
--
--  Slave03 Outlet Mgmtoitor Group
--
-- ===========================================================================
pduDevMgmtOutletSlave03PortSize OBJECT-TYPE
        SYNTAX INTEGER
        ACCESS read-only
        STATUS mandatory
        DESCRIPTION
                "The port size of master."
        ::= { pduDevMgmtOutletSlave03 1}

-- ===========================================================================
--
-- pduDevMgmtOutletSlave03Port
--
--  Slave03 Outlet Port Mgmtoitor Group
--
-- ===========================================================================
pduDevMgmtOutletSlave03PortTable OBJECT-TYPE
        SYNTAX SEQUENCE OF PduDevMgmtOutletSlave03PortEntry
        ACCESS not-accessible
        STATUS mandatory
        DESCRIPTION
                "Display the port information list of Slave03Port."
        ::= { pduDevMgmtOutletSlave03 2}

pduDevMgmtOutletSlave03PortEntry OBJECT-TYPE
        SYNTAX PduDevMgmtOutletSlave03PortEntry
        ACCESS not-accessible
        STATUS mandatory
        DESCRIPTION
                "Display the port information list of Slave03Port.."
        INDEX  { pduDevMgmtOutletSlave03PortIndex}
        ::= { pduDevMgmtOutletSlave03PortTable 1 }

PduDevMgmtOutletSlave03PortEntry ::=
        SEQUENCE {
                pduDevMgmtOutletSlave03PortIndex
                        INTEGER,
                pduDevMgmtOutletSlave03PortValid
                        INTEGER,
                pduDevMgmtOutletSlave03PortEnergyClr
                        INTEGER,
                pduDevMgmtOutletSlave03PortName
                        DisplayString,
                pduDevMgmtOutletSlave03PortOnDelayTime
                        INTEGER,
                pduDevMgmtOutletSlave03PortOnDelayStatus
                        INTEGER,
                pduDevMgmtOutletSlave03PortOffDelayTime
                        INTEGER,
                pduDevMgmtOutletSlave03PortOffDelayStatus
                        INTEGER,
                pduDevMgmtOutletSlave03PortRebootTime
                        INTEGER,
                pduDevMgmtOutletSlave03PortOverCurrWarn
                        INTEGER,
                pduDevMgmtOutletSlave03PortOverCurrCrit
                        INTEGER,
                pduDevMgmtOutletSlave03PortOverPowerWarn
                        INTEGER,
                pduDevMgmtOutletSlave03PortOverPowerCrit
                        INTEGER,
                pduDevMgmtOutletSlave03PortRly
                        INTEGER
        }

pduDevMgmtOutletSlave03PortIndex OBJECT-TYPE
        SYNTAX INTEGER (0..63)
        ACCESS read-only
        STATUS mandatory
        DESCRIPTION
                "The index to a outlet entry."
        ::= { pduDevMgmtOutletSlave03PortEntry 1 }

pduDevMgmtOutletSlave03PortValid OBJECT-TYPE
        SYNTAX INTEGER {
                offline(1),
                online(2)
                }
        ACCESS read-only
        STATUS mandatory
        DESCRIPTION
                "The online status of outlet."
        ::= { pduDevMgmtOutletSlave03PortEntry 2 }

pduDevMgmtOutletSlave03PortEnergyClr OBJECT-TYPE
        SYNTAX INTEGER {
                nothing(1),
                clearEnergy(2)
                }
        ACCESS read-write
        STATUS mandatory
        DESCRIPTION
                "Clear energy of outlet."
        ::= { pduDevMgmtOutletSlave03PortEntry 3 }

pduDevMgmtOutletSlave03PortName OBJECT-TYPE
        SYNTAX DisplayString (SIZE(0..31))
        ACCESS read-write
        STATUS mandatory
        DESCRIPTION
                "The name of outlet."
        ::= { pduDevMgmtOutletSlave03PortEntry 4 }

pduDevMgmtOutletSlave03PortOnDelayTime OBJECT-TYPE
        SYNTAX INTEGER (1..7200)
        ACCESS read-write
        STATUS mandatory
        DESCRIPTION
                "The on delay of outlet."
        ::= { pduDevMgmtOutletSlave03PortEntry 5}

pduDevMgmtOutletSlave03PortOnDelayStatus OBJECT-TYPE
        SYNTAX  INTEGER {
                nodelay(1),
                delay(2)
                }
        ACCESS read-write
        STATUS mandatory
        DESCRIPTION
                "The delay on status of outlet."
        ::= { pduDevMgmtOutletSlave03PortEntry 6}

pduDevMgmtOutletSlave03PortOffDelayTime OBJECT-TYPE
        SYNTAX INTEGER (1..7200)
        ACCESS read-write
        STATUS mandatory
        DESCRIPTION
                "The off delay of outlet."
        ::= { pduDevMgmtOutletSlave03PortEntry 7}

pduDevMgmtOutletSlave03PortOffDelayStatus OBJECT-TYPE
        SYNTAX  INTEGER {
                nodelay(1),
                delay(2)
                }
        ACCESS read-write
        STATUS mandatory
        DESCRIPTION
                "The delay off status of outlet."
        ::= { pduDevMgmtOutletSlave03PortEntry 8}

pduDevMgmtOutletSlave03PortRebootTime OBJECT-TYPE
        SYNTAX INTEGER (5..60)
        ACCESS read-write
        STATUS mandatory
        DESCRIPTION
                "The reboot time of outlet."
        ::= { pduDevMgmtOutletSlave03PortEntry 9}

pduDevMgmtOutletSlave03PortOverCurrWarn OBJECT-TYPE
        SYNTAX INTEGER (0..1600)
        UNITS  "0.01A"
        ACCESS read-write
        STATUS mandatory
        DESCRIPTION
                "The warning threshold of outlet current."
        ::= { pduDevMgmtOutletSlave03PortEntry 10}

pduDevMgmtOutletSlave03PortOverCurrCrit OBJECT-TYPE
        SYNTAX INTEGER (0..1600)
        UNITS  "0.01A"
        ACCESS read-write
        STATUS mandatory
        DESCRIPTION
                "The critical threshold of outlet current."
        ::= { pduDevMgmtOutletSlave03PortEntry 11}

pduDevMgmtOutletSlave03PortOverPowerWarn OBJECT-TYPE
        SYNTAX INTEGER (0..27500)
        ACCESS read-write
        STATUS mandatory
        DESCRIPTION
                "The warning threshold of outlet power."
        ::= { pduDevMgmtOutletSlave03PortEntry 12}

pduDevMgmtOutletSlave03PortOverPowerCrit OBJECT-TYPE
        SYNTAX INTEGER (0..27500)
        ACCESS read-write
        STATUS mandatory
        DESCRIPTION
                "The critical threshold of outlet power."
        ::= { pduDevMgmtOutletSlave03PortEntry 13}

pduDevMgmtOutletSlave03PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave03PortEntry 14 }

-- ===========================================================================
--
-- pduDevMgmtOutletSlave04
--
--  Slave04 Outlet Mgmtoitor Group
--
-- ===========================================================================
pduDevMgmtOutletSlave04PortSize OBJECT-TYPE
        SYNTAX INTEGER
        ACCESS read-only
        STATUS mandatory
        DESCRIPTION
                "The port size of master."
        ::= { pduDevMgmtOutletSlave04 1}

-- ===========================================================================
--
-- pduDevMgmtOutletSlave04Port
--
--  Slave04 Outlet Port Mgmtoitor Group
--
-- ===========================================================================
pduDevMgmtOutletSlave04PortTable OBJECT-TYPE
        SYNTAX SEQUENCE OF PduDevMgmtOutletSlave04PortEntry
        ACCESS not-accessible
        STATUS mandatory
        DESCRIPTION
                "Display the port information list of Slave04Port."
        ::= { pduDevMgmtOutletSlave04 2}

pduDevMgmtOutletSlave04PortEntry OBJECT-TYPE
        SYNTAX PduDevMgmtOutletSlave04PortEntry
        ACCESS not-accessible
        STATUS mandatory
        DESCRIPTION
                "Display the port information list of Slave04Port.."
        INDEX  { pduDevMgmtOutletSlave04PortIndex}
        ::= { pduDevMgmtOutletSlave04PortTable 1 }

PduDevMgmtOutletSlave04PortEntry ::=
        SEQUENCE {
                pduDevMgmtOutletSlave04PortIndex
                        INTEGER,
                pduDevMgmtOutletSlave04PortValid
                        INTEGER,
                pduDevMgmtOutletSlave04PortEnergyClr
                        INTEGER,
                pduDevMgmtOutletSlave04PortName
                        DisplayString,
                pduDevMgmtOutletSlave04PortOnDelayTime
                        INTEGER,
                pduDevMgmtOutletSlave04PortOnDelayStatus
                        INTEGER,
                pduDevMgmtOutletSlave04PortOffDelayTime
                        INTEGER,
                pduDevMgmtOutletSlave04PortOffDelayStatus
                        INTEGER,
                pduDevMgmtOutletSlave04PortRebootTime
                        INTEGER,
                pduDevMgmtOutletSlave04PortOverCurrWarn
                        INTEGER,
                pduDevMgmtOutletSlave04PortOverCurrCrit
                        INTEGER,
                pduDevMgmtOutletSlave04PortOverPowerWarn
                        INTEGER,
                pduDevMgmtOutletSlave04PortOverPowerCrit
                        INTEGER,
                pduDevMgmtOutletSlave04PortRly
                        INTEGER
        }

pduDevMgmtOutletSlave04PortIndex OBJECT-TYPE
        SYNTAX INTEGER (0..63)
        ACCESS read-only
        STATUS mandatory
        DESCRIPTION
                "The index to a outlet entry."
        ::= { pduDevMgmtOutletSlave04PortEntry 1 }

pduDevMgmtOutletSlave04PortValid OBJECT-TYPE
        SYNTAX INTEGER {
                offline(1),
                online(2)
                }
        ACCESS read-only
        STATUS mandatory
        DESCRIPTION
                "The online status of outlet."
        ::= { pduDevMgmtOutletSlave04PortEntry 2 }

pduDevMgmtOutletSlave04PortEnergyClr OBJECT-TYPE
        SYNTAX INTEGER {
                nothing(1),
                clearEnergy(2)
                }
        ACCESS read-write
        STATUS mandatory
        DESCRIPTION
                "Clear energy of outlet."
        ::= { pduDevMgmtOutletSlave04PortEntry 3 }

pduDevMgmtOutletSlave04PortName OBJECT-TYPE
        SYNTAX DisplayString (SIZE(0..31))
        ACCESS read-write
        STATUS mandatory
        DESCRIPTION
                "The name of outlet."
        ::= { pduDevMgmtOutletSlave04PortEntry 4 }

pduDevMgmtOutletSlave04PortOnDelayTime OBJECT-TYPE
        SYNTAX INTEGER (1..7200)
        ACCESS read-write
        STATUS mandatory
        DESCRIPTION
                "The on delay of outlet."
        ::= { pduDevMgmtOutletSlave04PortEntry 5}

pduDevMgmtOutletSlave04PortOnDelayStatus OBJECT-TYPE
        SYNTAX  INTEGER {
                nodelay(1),
                delay(2)
                }
        ACCESS read-write
        STATUS mandatory
        DESCRIPTION
                "The delay on status of outlet."
        ::= { pduDevMgmtOutletSlave04PortEntry 6}

pduDevMgmtOutletSlave04PortOffDelayTime OBJECT-TYPE
        SYNTAX INTEGER (1..7200)
        ACCESS read-write
        STATUS mandatory
        DESCRIPTION
                "The off delay of outlet."
        ::= { pduDevMgmtOutletSlave04PortEntry 7}

pduDevMgmtOutletSlave04PortOffDelayStatus OBJECT-TYPE
        SYNTAX  INTEGER {
                nodelay(1),
                delay(2)
                }
        ACCESS read-write
        STATUS mandatory
        DESCRIPTION
                "The delay off status of outlet."
        ::= { pduDevMgmtOutletSlave04PortEntry 8}

pduDevMgmtOutletSlave04PortRebootTime OBJECT-TYPE
        SYNTAX INTEGER (5..60)
        ACCESS read-write
        STATUS mandatory
        DESCRIPTION
                "The reboot time of outlet."
        ::= { pduDevMgmtOutletSlave04PortEntry 9}

pduDevMgmtOutletSlave04PortOverCurrWarn OBJECT-TYPE
        SYNTAX INTEGER (0..1600)
        UNITS  "0.01A"
        ACCESS read-write
        STATUS mandatory
        DESCRIPTION
                "The warning threshold of outlet current."
        ::= { pduDevMgmtOutletSlave04PortEntry 10}

pduDevMgmtOutletSlave04PortOverCurrCrit OBJECT-TYPE
        SYNTAX INTEGER (0..1600)
        UNITS  "0.01A"
        ACCESS read-write
        STATUS mandatory
        DESCRIPTION
                "The critical threshold of outlet current."
        ::= { pduDevMgmtOutletSlave04PortEntry 11}

pduDevMgmtOutletSlave04PortOverPowerWarn OBJECT-TYPE
        SYNTAX INTEGER (0..27500)
        ACCESS read-write
        STATUS mandatory
        DESCRIPTION
                "The warning threshold of outlet power."
        ::= { pduDevMgmtOutletSlave04PortEntry 12}

pduDevMgmtOutletSlave04PortOverPowerCrit OBJECT-TYPE
        SYNTAX INTEGER (0..27500)
        ACCESS read-write
        STATUS mandatory
        DESCRIPTION
                "The critical threshold of outlet power."
        ::= { pduDevMgmtOutletSlave04PortEntry 13}

pduDevMgmtOutletSlave04PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave04PortEntry 14 }

-- ===========================================================================
--
-- pduDevMgmtOutletSlave05
--
--  Slave05 Outlet Mgmtoitor Group
--
-- ===========================================================================
pduDevMgmtOutletSlave05PortSize OBJECT-TYPE
        SYNTAX INTEGER
        ACCESS read-only
        STATUS mandatory
        DESCRIPTION
                "The port size of master."
        ::= { pduDevMgmtOutletSlave05 1}

-- ===========================================================================
--
-- pduDevMgmtOutletSlave05Port
--
--  Slave05 Outlet Port Mgmtoitor Group
--
-- ===========================================================================
pduDevMgmtOutletSlave05PortTable OBJECT-TYPE
        SYNTAX SEQUENCE OF PduDevMgmtOutletSlave05PortEntry
        ACCESS not-accessible
        STATUS mandatory
        DESCRIPTION
                "Display the port information list of Slave05Port."
        ::= { pduDevMgmtOutletSlave05 2}

pduDevMgmtOutletSlave05PortEntry OBJECT-TYPE
        SYNTAX PduDevMgmtOutletSlave05PortEntry
        ACCESS not-accessible
        STATUS mandatory
        DESCRIPTION
                "Display the port information list of Slave05Port.."
        INDEX  { pduDevMgmtOutletSlave05PortIndex}
        ::= { pduDevMgmtOutletSlave05PortTable 1 }

PduDevMgmtOutletSlave05PortEntry ::=
        SEQUENCE {
                pduDevMgmtOutletSlave05PortIndex
                        INTEGER,
                pduDevMgmtOutletSlave05PortValid
                        INTEGER,
                pduDevMgmtOutletSlave05PortEnergyClr
                        INTEGER,
                pduDevMgmtOutletSlave05PortName
                        DisplayString,
                pduDevMgmtOutletSlave05PortOnDelayTime
                        INTEGER,
                pduDevMgmtOutletSlave05PortOnDelayStatus
                        INTEGER,
                pduDevMgmtOutletSlave05PortOffDelayTime
                        INTEGER,
                pduDevMgmtOutletSlave05PortOffDelayStatus
                        INTEGER,
                pduDevMgmtOutletSlave05PortRebootTime
                        INTEGER,
                pduDevMgmtOutletSlave05PortOverCurrWarn
                        INTEGER,
                pduDevMgmtOutletSlave05PortOverCurrCrit
                        INTEGER,
                pduDevMgmtOutletSlave05PortOverPowerWarn
                        INTEGER,
                pduDevMgmtOutletSlave05PortOverPowerCrit
                        INTEGER,
                pduDevMgmtOutletSlave05PortRly
                        INTEGER
        }

pduDevMgmtOutletSlave05PortIndex OBJECT-TYPE
        SYNTAX INTEGER (0..63)
        ACCESS read-only
        STATUS mandatory
        DESCRIPTION
                "The index to a outlet entry."
        ::= { pduDevMgmtOutletSlave05PortEntry 1 }

pduDevMgmtOutletSlave05PortValid OBJECT-TYPE
        SYNTAX INTEGER {
                offline(1),
                online(2)
                }
        ACCESS read-only
        STATUS mandatory
        DESCRIPTION
                "The online status of outlet."
        ::= { pduDevMgmtOutletSlave05PortEntry 2 }

pduDevMgmtOutletSlave05PortEnergyClr OBJECT-TYPE
        SYNTAX INTEGER {
                nothing(1),
                clearEnergy(2)
                }
        ACCESS read-write
        STATUS mandatory
        DESCRIPTION
                "Clear energy of outlet."
        ::= { pduDevMgmtOutletSlave05PortEntry 3 }

pduDevMgmtOutletSlave05PortName OBJECT-TYPE
        SYNTAX DisplayString (SIZE(0..31))
        ACCESS read-write
        STATUS mandatory
        DESCRIPTION
                "The name of outlet."
        ::= { pduDevMgmtOutletSlave05PortEntry 4 }

pduDevMgmtOutletSlave05PortOnDelayTime OBJECT-TYPE
        SYNTAX INTEGER (1..7200)
        ACCESS read-write
        STATUS mandatory
        DESCRIPTION
                "The on delay of outlet."
        ::= { pduDevMgmtOutletSlave05PortEntry 5}

pduDevMgmtOutletSlave05PortOnDelayStatus OBJECT-TYPE
        SYNTAX  INTEGER {
                nodelay(1),
                delay(2)
                }
        ACCESS read-write
        STATUS mandatory
        DESCRIPTION
                "The delay on status of outlet."
        ::= { pduDevMgmtOutletSlave05PortEntry 6}

pduDevMgmtOutletSlave05PortOffDelayTime OBJECT-TYPE
        SYNTAX INTEGER (1..7200)
        ACCESS read-write
        STATUS mandatory
        DESCRIPTION
                "The off delay of outlet."
        ::= { pduDevMgmtOutletSlave05PortEntry 7}

pduDevMgmtOutletSlave05PortOffDelayStatus OBJECT-TYPE
        SYNTAX  INTEGER {
                nodelay(1),
                delay(2)
                }
        ACCESS read-write
        STATUS mandatory
        DESCRIPTION
                "The delay off status of outlet."
        ::= { pduDevMgmtOutletSlave05PortEntry 8}

pduDevMgmtOutletSlave05PortRebootTime OBJECT-TYPE
        SYNTAX INTEGER (5..60)
        ACCESS read-write
        STATUS mandatory
        DESCRIPTION
                "The reboot time of outlet."
        ::= { pduDevMgmtOutletSlave05PortEntry 9}

pduDevMgmtOutletSlave05PortOverCurrWarn OBJECT-TYPE
        SYNTAX INTEGER (0..1600)
        UNITS  "0.01A"
        ACCESS read-write
        STATUS mandatory
        DESCRIPTION
                "The warning threshold of outlet current."
        ::= { pduDevMgmtOutletSlave05PortEntry 10}

pduDevMgmtOutletSlave05PortOverCurrCrit OBJECT-TYPE
        SYNTAX INTEGER (0..1600)
        UNITS  "0.01A"
        ACCESS read-write
        STATUS mandatory
        DESCRIPTION
                "The critical threshold of outlet current."
        ::= { pduDevMgmtOutletSlave05PortEntry 11}

pduDevMgmtOutletSlave05PortOverPowerWarn OBJECT-TYPE
        SYNTAX INTEGER (0..27500)
        ACCESS read-write
        STATUS mandatory
        DESCRIPTION
                "The warning threshold of outlet power."
        ::= { pduDevMgmtOutletSlave05PortEntry 12}

pduDevMgmtOutletSlave05PortOverPowerCrit OBJECT-TYPE
        SYNTAX INTEGER (0..27500)
        ACCESS read-write
        STATUS mandatory
        DESCRIPTION
                "The critical threshold of outlet power."
        ::= { pduDevMgmtOutletSlave05PortEntry 13}

pduDevMgmtOutletSlave05PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave05PortEntry 14 }

-- ===========================================================================
--
-- pduDevMgmtOutletSlave06
--
--  Slave06 Outlet Mgmtoitor Group
--
-- ===========================================================================
pduDevMgmtOutletSlave06PortSize OBJECT-TYPE
        SYNTAX INTEGER
        ACCESS read-only
        STATUS mandatory
        DESCRIPTION
                "The port size of master."
        ::= { pduDevMgmtOutletSlave06 1}

-- ===========================================================================
--
-- pduDevMgmtOutletSlave06Port
--
--  Slave06 Outlet Port Mgmtoitor Group
--
-- ===========================================================================
pduDevMgmtOutletSlave06PortTable OBJECT-TYPE
        SYNTAX SEQUENCE OF PduDevMgmtOutletSlave06PortEntry
        ACCESS not-accessible
        STATUS mandatory
        DESCRIPTION
                "Display the port information list of Slave06Port."
        ::= { pduDevMgmtOutletSlave06 2}

pduDevMgmtOutletSlave06PortEntry OBJECT-TYPE
        SYNTAX PduDevMgmtOutletSlave06PortEntry
        ACCESS not-accessible
        STATUS mandatory
        DESCRIPTION
                "Display the port information list of Slave06Port.."
        INDEX  { pduDevMgmtOutletSlave06PortIndex}
        ::= { pduDevMgmtOutletSlave06PortTable 1 }

PduDevMgmtOutletSlave06PortEntry ::=
        SEQUENCE {
                pduDevMgmtOutletSlave06PortIndex
                        INTEGER,
                pduDevMgmtOutletSlave06PortValid
                        INTEGER,
                pduDevMgmtOutletSlave06PortEnergyClr
                        INTEGER,
                pduDevMgmtOutletSlave06PortName
                        DisplayString,
                pduDevMgmtOutletSlave06PortOnDelayTime
                        INTEGER,
                pduDevMgmtOutletSlave06PortOnDelayStatus
                        INTEGER,
                pduDevMgmtOutletSlave06PortOffDelayTime
                        INTEGER,
                pduDevMgmtOutletSlave06PortOffDelayStatus
                        INTEGER,
                pduDevMgmtOutletSlave06PortRebootTime
                        INTEGER,
                pduDevMgmtOutletSlave06PortOverCurrWarn
                        INTEGER,
                pduDevMgmtOutletSlave06PortOverCurrCrit
                        INTEGER,
                pduDevMgmtOutletSlave06PortOverPowerWarn
                        INTEGER,
                pduDevMgmtOutletSlave06PortOverPowerCrit
                        INTEGER,
                pduDevMgmtOutletSlave06PortRly
                        INTEGER
        }

pduDevMgmtOutletSlave06PortIndex OBJECT-TYPE
        SYNTAX INTEGER (0..63)
        ACCESS read-only
        STATUS mandatory
        DESCRIPTION
                "The index to a outlet entry."
        ::= { pduDevMgmtOutletSlave06PortEntry 1 }

pduDevMgmtOutletSlave06PortValid OBJECT-TYPE
        SYNTAX INTEGER {
                offline(1),
                online(2)
                }
        ACCESS read-only
        STATUS mandatory
        DESCRIPTION
                "The online status of outlet."
        ::= { pduDevMgmtOutletSlave06PortEntry 2 }

pduDevMgmtOutletSlave06PortEnergyClr OBJECT-TYPE
        SYNTAX INTEGER {
                nothing(1),
                clearEnergy(2)
                }
        ACCESS read-write
        STATUS mandatory
        DESCRIPTION
                "Clear energy of outlet."
        ::= { pduDevMgmtOutletSlave06PortEntry 3 }

pduDevMgmtOutletSlave06PortName OBJECT-TYPE
        SYNTAX DisplayString (SIZE(0..31))
        ACCESS read-write
        STATUS mandatory
        DESCRIPTION
                "The name of outlet."
        ::= { pduDevMgmtOutletSlave06PortEntry 4 }

pduDevMgmtOutletSlave06PortOnDelayTime OBJECT-TYPE
        SYNTAX INTEGER (1..7200)
        ACCESS read-write
        STATUS mandatory
        DESCRIPTION
                "The on delay of outlet."
        ::= { pduDevMgmtOutletSlave06PortEntry 5}

pduDevMgmtOutletSlave06PortOnDelayStatus OBJECT-TYPE
        SYNTAX  INTEGER {
                nodelay(1),
                delay(2)
                }
        ACCESS read-write
        STATUS mandatory
        DESCRIPTION
                "The delay on status of outlet."
        ::= { pduDevMgmtOutletSlave06PortEntry 6}

pduDevMgmtOutletSlave06PortOffDelayTime OBJECT-TYPE
        SYNTAX INTEGER (1..7200)
        ACCESS read-write
        STATUS mandatory
        DESCRIPTION
                "The off delay of outlet."
        ::= { pduDevMgmtOutletSlave06PortEntry 7}

pduDevMgmtOutletSlave06PortOffDelayStatus OBJECT-TYPE
        SYNTAX  INTEGER {
                nodelay(1),
                delay(2)
                }
        ACCESS read-write
        STATUS mandatory
        DESCRIPTION
                "The delay off status of outlet."
        ::= { pduDevMgmtOutletSlave06PortEntry 8}

pduDevMgmtOutletSlave06PortRebootTime OBJECT-TYPE
        SYNTAX INTEGER (5..60)
        ACCESS read-write
        STATUS mandatory
        DESCRIPTION
                "The reboot time of outlet."
        ::= { pduDevMgmtOutletSlave06PortEntry 9}

pduDevMgmtOutletSlave06PortOverCurrWarn OBJECT-TYPE
        SYNTAX INTEGER (0..1600)
        UNITS  "0.01A"
        ACCESS read-write
        STATUS mandatory
        DESCRIPTION
                "The warning threshold of outlet current."
        ::= { pduDevMgmtOutletSlave06PortEntry 10}

pduDevMgmtOutletSlave06PortOverCurrCrit OBJECT-TYPE
        SYNTAX INTEGER (0..1600)
        UNITS  "0.01A"
        ACCESS read-write
        STATUS mandatory
        DESCRIPTION
                "The critical threshold of outlet current."
        ::= { pduDevMgmtOutletSlave06PortEntry 11}

pduDevMgmtOutletSlave06PortOverPowerWarn OBJECT-TYPE
        SYNTAX INTEGER (0..27500)
        ACCESS read-write
        STATUS mandatory
        DESCRIPTION
                "The warning threshold of outlet power."
        ::= { pduDevMgmtOutletSlave06PortEntry 12}

pduDevMgmtOutletSlave06PortOverPowerCrit OBJECT-TYPE
        SYNTAX INTEGER (0..27500)
        ACCESS read-write
        STATUS mandatory
        DESCRIPTION
                "The critical threshold of outlet power."
        ::= { pduDevMgmtOutletSlave06PortEntry 13}

pduDevMgmtOutletSlave06PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave06PortEntry 14 }

-- ===========================================================================
--
-- pduDevMgmtOutletSlave07
--
--  Slave07 Outlet Mgmtoitor Group
--
-- ===========================================================================
pduDevMgmtOutletSlave07PortSize OBJECT-TYPE
        SYNTAX INTEGER
        ACCESS read-only
        STATUS mandatory
        DESCRIPTION
                "The port size of master."
        ::= { pduDevMgmtOutletSlave07 1}

-- ===========================================================================
--
-- pduDevMgmtOutletSlave07Port
--
--  Slave07 Outlet Port Mgmtoitor Group
--
-- ===========================================================================
pduDevMgmtOutletSlave07PortTable OBJECT-TYPE
        SYNTAX SEQUENCE OF PduDevMgmtOutletSlave07PortEntry
        ACCESS not-accessible
        STATUS mandatory
        DESCRIPTION
                "Display the port information list of Slave07Port."
        ::= { pduDevMgmtOutletSlave07 2}

pduDevMgmtOutletSlave07PortEntry OBJECT-TYPE
        SYNTAX PduDevMgmtOutletSlave07PortEntry
        ACCESS not-accessible
        STATUS mandatory
        DESCRIPTION
                "Display the port information list of Slave07Port.."
        INDEX  { pduDevMgmtOutletSlave07PortIndex}
        ::= { pduDevMgmtOutletSlave07PortTable 1 }

PduDevMgmtOutletSlave07PortEntry ::=
        SEQUENCE {
                pduDevMgmtOutletSlave07PortIndex
                        INTEGER,
                pduDevMgmtOutletSlave07PortValid
                        INTEGER,
                pduDevMgmtOutletSlave07PortEnergyClr
                        INTEGER,
                pduDevMgmtOutletSlave07PortName
                        DisplayString,
                pduDevMgmtOutletSlave07PortOnDelayTime
                        INTEGER,
                pduDevMgmtOutletSlave07PortOnDelayStatus
                        INTEGER,
                pduDevMgmtOutletSlave07PortOffDelayTime
                        INTEGER,
                pduDevMgmtOutletSlave07PortOffDelayStatus
                        INTEGER,
                pduDevMgmtOutletSlave07PortRebootTime
                        INTEGER,
                pduDevMgmtOutletSlave07PortOverCurrWarn
                        INTEGER,
                pduDevMgmtOutletSlave07PortOverCurrCrit
                        INTEGER,
                pduDevMgmtOutletSlave07PortOverPowerWarn
                        INTEGER,
                pduDevMgmtOutletSlave07PortOverPowerCrit
                        INTEGER,
                pduDevMgmtOutletSlave07PortRly
                        INTEGER
        }

pduDevMgmtOutletSlave07PortIndex OBJECT-TYPE
        SYNTAX INTEGER (0..63)
        ACCESS read-only
        STATUS mandatory
        DESCRIPTION
                "The index to a outlet entry."
        ::= { pduDevMgmtOutletSlave07PortEntry 1 }

pduDevMgmtOutletSlave07PortValid OBJECT-TYPE
        SYNTAX INTEGER {
                offline(1),
                online(2)
                }
        ACCESS read-only
        STATUS mandatory
        DESCRIPTION
                "The online status of outlet."
        ::= { pduDevMgmtOutletSlave07PortEntry 2 }

pduDevMgmtOutletSlave07PortEnergyClr OBJECT-TYPE
        SYNTAX INTEGER {
                nothing(1),
                clearEnergy(2)
                }
        ACCESS read-write
        STATUS mandatory
        DESCRIPTION
                "Clear energy of outlet."
        ::= { pduDevMgmtOutletSlave07PortEntry 3 }

pduDevMgmtOutletSlave07PortName OBJECT-TYPE
        SYNTAX DisplayString (SIZE(0..31))
        ACCESS read-write
        STATUS mandatory
        DESCRIPTION
                "The name of outlet."
        ::= { pduDevMgmtOutletSlave07PortEntry 4 }

pduDevMgmtOutletSlave07PortOnDelayTime OBJECT-TYPE
        SYNTAX INTEGER (1..7200)
        ACCESS read-write
        STATUS mandatory
        DESCRIPTION
                "The on delay of outlet."
        ::= { pduDevMgmtOutletSlave07PortEntry 5}

pduDevMgmtOutletSlave07PortOnDelayStatus OBJECT-TYPE
        SYNTAX  INTEGER {
                nodelay(1),
                delay(2)
                }
        ACCESS read-write
        STATUS mandatory
        DESCRIPTION
                "The delay on status of outlet."
        ::= { pduDevMgmtOutletSlave07PortEntry 6}

pduDevMgmtOutletSlave07PortOffDelayTime OBJECT-TYPE
        SYNTAX INTEGER (1..7200)
        ACCESS read-write
        STATUS mandatory
        DESCRIPTION
                "The off delay of outlet."
        ::= { pduDevMgmtOutletSlave07PortEntry 7}

pduDevMgmtOutletSlave07PortOffDelayStatus OBJECT-TYPE
        SYNTAX  INTEGER {
                nodelay(1),
                delay(2)
                }
        ACCESS read-write
        STATUS mandatory
        DESCRIPTION
                "The delay off status of outlet."
        ::= { pduDevMgmtOutletSlave07PortEntry 8}

pduDevMgmtOutletSlave07PortRebootTime OBJECT-TYPE
        SYNTAX INTEGER (5..60)
        ACCESS read-write
        STATUS mandatory
        DESCRIPTION
                "The reboot time of outlet."
        ::= { pduDevMgmtOutletSlave07PortEntry 9}

pduDevMgmtOutletSlave07PortOverCurrWarn OBJECT-TYPE
        SYNTAX INTEGER (0..1600)
        UNITS  "0.01A"
        ACCESS read-write
        STATUS mandatory
        DESCRIPTION
                "The warning threshold of outlet current."
        ::= { pduDevMgmtOutletSlave07PortEntry 10}

pduDevMgmtOutletSlave07PortOverCurrCrit OBJECT-TYPE
        SYNTAX INTEGER (0..1600)
        UNITS  "0.01A"
        ACCESS read-write
        STATUS mandatory
        DESCRIPTION
                "The critical threshold of outlet current."
        ::= { pduDevMgmtOutletSlave07PortEntry 11}

pduDevMgmtOutletSlave07PortOverPowerWarn OBJECT-TYPE
        SYNTAX INTEGER (0..27500)
        ACCESS read-write
        STATUS mandatory
        DESCRIPTION
                "The warning threshold of outlet power."
        ::= { pduDevMgmtOutletSlave07PortEntry 12}

pduDevMgmtOutletSlave07PortOverPowerCrit OBJECT-TYPE
        SYNTAX INTEGER (0..27500)
        ACCESS read-write
        STATUS mandatory
        DESCRIPTION
                "The critical threshold of outlet power."
        ::= { pduDevMgmtOutletSlave07PortEntry 13}

pduDevMgmtOutletSlave07PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave07PortEntry 14 }

-- ===========================================================================
--
-- pduDevMgmtOutletSlave08
--
--  Slave08 Outlet Mgmtoitor Group
--
-- ===========================================================================
pduDevMgmtOutletSlave08PortSize OBJECT-TYPE
        SYNTAX INTEGER
        ACCESS read-only
        STATUS mandatory
        DESCRIPTION
                "The port size of master."
        ::= { pduDevMgmtOutletSlave08 1}

-- ===========================================================================
--
-- pduDevMgmtOutletSlave08Port
--
--  Slave08 Outlet Port Mgmtoitor Group
--
-- ===========================================================================
pduDevMgmtOutletSlave08PortTable OBJECT-TYPE
        SYNTAX SEQUENCE OF PduDevMgmtOutletSlave08PortEntry
        ACCESS not-accessible
        STATUS mandatory
        DESCRIPTION
                "Display the port information list of Slave08Port."
        ::= { pduDevMgmtOutletSlave08 2}

pduDevMgmtOutletSlave08PortEntry OBJECT-TYPE
        SYNTAX PduDevMgmtOutletSlave08PortEntry
        ACCESS not-accessible
        STATUS mandatory
        DESCRIPTION
                "Display the port information list of Slave08Port.."
        INDEX  { pduDevMgmtOutletSlave08PortIndex}
        ::= { pduDevMgmtOutletSlave08PortTable 1 }

PduDevMgmtOutletSlave08PortEntry ::=
        SEQUENCE {
                pduDevMgmtOutletSlave08PortIndex
                        INTEGER,
                pduDevMgmtOutletSlave08PortValid
                        INTEGER,
                pduDevMgmtOutletSlave08PortEnergyClr
                        INTEGER,
                pduDevMgmtOutletSlave08PortName
                        DisplayString,
                pduDevMgmtOutletSlave08PortOnDelayTime
                        INTEGER,
                pduDevMgmtOutletSlave08PortOnDelayStatus
                        INTEGER,
                pduDevMgmtOutletSlave08PortOffDelayTime
                        INTEGER,
                pduDevMgmtOutletSlave08PortOffDelayStatus
                        INTEGER,
                pduDevMgmtOutletSlave08PortRebootTime
                        INTEGER,
                pduDevMgmtOutletSlave08PortOverCurrWarn
                        INTEGER,
                pduDevMgmtOutletSlave08PortOverCurrCrit
                        INTEGER,
                pduDevMgmtOutletSlave08PortOverPowerWarn
                        INTEGER,
                pduDevMgmtOutletSlave08PortOverPowerCrit
                        INTEGER,
                pduDevMgmtOutletSlave08PortRly
                        INTEGER
        }

pduDevMgmtOutletSlave08PortIndex OBJECT-TYPE
        SYNTAX INTEGER (0..63)
        ACCESS read-only
        STATUS mandatory
        DESCRIPTION
                "The index to a outlet entry."
        ::= { pduDevMgmtOutletSlave08PortEntry 1 }

pduDevMgmtOutletSlave08PortValid OBJECT-TYPE
        SYNTAX INTEGER {
                offline(1),
                online(2)
                }
        ACCESS read-only
        STATUS mandatory
        DESCRIPTION
                "The online status of outlet."
        ::= { pduDevMgmtOutletSlave08PortEntry 2 }

pduDevMgmtOutletSlave08PortEnergyClr OBJECT-TYPE
        SYNTAX INTEGER {
                nothing(1),
                clearEnergy(2)
                }
        ACCESS read-write
        STATUS mandatory
        DESCRIPTION
                "Clear energy of outlet."
        ::= { pduDevMgmtOutletSlave08PortEntry 3 }

pduDevMgmtOutletSlave08PortName OBJECT-TYPE
        SYNTAX DisplayString (SIZE(0..31))
        ACCESS read-write
        STATUS mandatory
        DESCRIPTION
                "The name of outlet."
        ::= { pduDevMgmtOutletSlave08PortEntry 4 }

pduDevMgmtOutletSlave08PortOnDelayTime OBJECT-TYPE
        SYNTAX INTEGER (1..7200)
        ACCESS read-write
        STATUS mandatory
        DESCRIPTION
                "The on delay of outlet."
        ::= { pduDevMgmtOutletSlave08PortEntry 5}

pduDevMgmtOutletSlave08PortOnDelayStatus OBJECT-TYPE
        SYNTAX  INTEGER {
                nodelay(1),
                delay(2)
                }
        ACCESS read-write
        STATUS mandatory
        DESCRIPTION
                "The delay on status of outlet."
        ::= { pduDevMgmtOutletSlave08PortEntry 6}

pduDevMgmtOutletSlave08PortOffDelayTime OBJECT-TYPE
        SYNTAX INTEGER (1..7200)
        ACCESS read-write
        STATUS mandatory
        DESCRIPTION
                "The off delay of outlet."
        ::= { pduDevMgmtOutletSlave08PortEntry 7}

pduDevMgmtOutletSlave08PortOffDelayStatus OBJECT-TYPE
        SYNTAX  INTEGER {
                nodelay(1),
                delay(2)
                }
        ACCESS read-write
        STATUS mandatory
        DESCRIPTION
                "The delay off status of outlet."
        ::= { pduDevMgmtOutletSlave08PortEntry 8}

pduDevMgmtOutletSlave08PortRebootTime OBJECT-TYPE
        SYNTAX INTEGER (5..60)
        ACCESS read-write
        STATUS mandatory
        DESCRIPTION
                "The reboot time of outlet."
        ::= { pduDevMgmtOutletSlave08PortEntry 9}

pduDevMgmtOutletSlave08PortOverCurrWarn OBJECT-TYPE
        SYNTAX INTEGER (0..1600)
        UNITS  "0.01A"
        ACCESS read-write
        STATUS mandatory
        DESCRIPTION
                "The warning threshold of outlet current."
        ::= { pduDevMgmtOutletSlave08PortEntry 10}

pduDevMgmtOutletSlave08PortOverCurrCrit OBJECT-TYPE
        SYNTAX INTEGER (0..1600)
        UNITS  "0.01A"
        ACCESS read-write
        STATUS mandatory
        DESCRIPTION
                "The critical threshold of outlet current."
        ::= { pduDevMgmtOutletSlave08PortEntry 11}

pduDevMgmtOutletSlave08PortOverPowerWarn OBJECT-TYPE
        SYNTAX INTEGER (0..27500)
        ACCESS read-write
        STATUS mandatory
        DESCRIPTION
                "The warning threshold of outlet power."
        ::= { pduDevMgmtOutletSlave08PortEntry 12}

pduDevMgmtOutletSlave08PortOverPowerCrit OBJECT-TYPE
        SYNTAX INTEGER (0..27500)
        ACCESS read-write
        STATUS mandatory
        DESCRIPTION
                "The critical threshold of outlet power."
        ::= { pduDevMgmtOutletSlave08PortEntry 13}

pduDevMgmtOutletSlave08PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave08PortEntry 14 }

-- ===========================================================================
--
-- pduDevMgmtOutletSlave09
--
--  Slave09 Outlet Mgmtoitor Group
--
-- ===========================================================================
pduDevMgmtOutletSlave09PortSize OBJECT-TYPE
        SYNTAX INTEGER
        ACCESS read-only
        STATUS mandatory
        DESCRIPTION
                "The port size of master."
        ::= { pduDevMgmtOutletSlave09 1}

-- ===========================================================================
--
-- pduDevMgmtOutletSlave09Port
--
--  Slave09 Outlet Port Mgmtoitor Group
--
-- ===========================================================================
pduDevMgmtOutletSlave09PortTable OBJECT-TYPE
        SYNTAX SEQUENCE OF PduDevMgmtOutletSlave09PortEntry
        ACCESS not-accessible
        STATUS mandatory
        DESCRIPTION
                "Display the port information list of Slave09Port."
        ::= { pduDevMgmtOutletSlave09 2}

pduDevMgmtOutletSlave09PortEntry OBJECT-TYPE
        SYNTAX PduDevMgmtOutletSlave09PortEntry
        ACCESS not-accessible
        STATUS mandatory
        DESCRIPTION
                "Display the port information list of Slave09Port.."
        INDEX  { pduDevMgmtOutletSlave09PortIndex}
        ::= { pduDevMgmtOutletSlave09PortTable 1 }

PduDevMgmtOutletSlave09PortEntry ::=
        SEQUENCE {
                pduDevMgmtOutletSlave09PortIndex
                        INTEGER,
                pduDevMgmtOutletSlave09PortValid
                        INTEGER,
                pduDevMgmtOutletSlave09PortEnergyClr
                        INTEGER,
                pduDevMgmtOutletSlave09PortName
                        DisplayString,
                pduDevMgmtOutletSlave09PortOnDelayTime
                        INTEGER,
                pduDevMgmtOutletSlave09PortOnDelayStatus
                        INTEGER,
                pduDevMgmtOutletSlave09PortOffDelayTime
                        INTEGER,
                pduDevMgmtOutletSlave09PortOffDelayStatus
                        INTEGER,
                pduDevMgmtOutletSlave09PortRebootTime
                        INTEGER,
                pduDevMgmtOutletSlave09PortOverCurrWarn
                        INTEGER,
                pduDevMgmtOutletSlave09PortOverCurrCrit
                        INTEGER,
                pduDevMgmtOutletSlave09PortOverPowerWarn
                        INTEGER,
                pduDevMgmtOutletSlave09PortOverPowerCrit
                        INTEGER,
                pduDevMgmtOutletSlave09PortRly
                        INTEGER
        }

pduDevMgmtOutletSlave09PortIndex OBJECT-TYPE
        SYNTAX INTEGER (0..63)
        ACCESS read-only
        STATUS mandatory
        DESCRIPTION
                "The index to a outlet entry."
        ::= { pduDevMgmtOutletSlave09PortEntry 1 }

pduDevMgmtOutletSlave09PortValid OBJECT-TYPE
        SYNTAX INTEGER {
                offline(1),
                online(2)
                }
        ACCESS read-only
        STATUS mandatory
        DESCRIPTION
                "The online status of outlet."
        ::= { pduDevMgmtOutletSlave09PortEntry 2 }

pduDevMgmtOutletSlave09PortEnergyClr OBJECT-TYPE
        SYNTAX INTEGER {
                nothing(1),
                clearEnergy(2)
                }
        ACCESS read-write
        STATUS mandatory
        DESCRIPTION
                "Clear energy of outlet."
        ::= { pduDevMgmtOutletSlave09PortEntry 3 }

pduDevMgmtOutletSlave09PortName OBJECT-TYPE
        SYNTAX DisplayString (SIZE(0..31))
        ACCESS read-write
        STATUS mandatory
        DESCRIPTION
                "The name of outlet."
        ::= { pduDevMgmtOutletSlave09PortEntry 4 }

pduDevMgmtOutletSlave09PortOnDelayTime OBJECT-TYPE
        SYNTAX INTEGER (1..7200)
        ACCESS read-write
        STATUS mandatory
        DESCRIPTION
                "The on delay of outlet."
        ::= { pduDevMgmtOutletSlave09PortEntry 5}

pduDevMgmtOutletSlave09PortOnDelayStatus OBJECT-TYPE
        SYNTAX  INTEGER {
                nodelay(1),
                delay(2)
                }
        ACCESS read-write
        STATUS mandatory
        DESCRIPTION
                "The delay on status of outlet."
        ::= { pduDevMgmtOutletSlave09PortEntry 6}

pduDevMgmtOutletSlave09PortOffDelayTime OBJECT-TYPE
        SYNTAX INTEGER (1..7200)
        ACCESS read-write
        STATUS mandatory
        DESCRIPTION
                "The off delay of outlet."
        ::= { pduDevMgmtOutletSlave09PortEntry 7}

pduDevMgmtOutletSlave09PortOffDelayStatus OBJECT-TYPE
        SYNTAX  INTEGER {
                nodelay(1),
                delay(2)
                }
        ACCESS read-write
        STATUS mandatory
        DESCRIPTION
                "The delay off status of outlet."
        ::= { pduDevMgmtOutletSlave09PortEntry 8}

pduDevMgmtOutletSlave09PortRebootTime OBJECT-TYPE
        SYNTAX INTEGER (5..60)
        ACCESS read-write
        STATUS mandatory
        DESCRIPTION
                "The reboot time of outlet."
        ::= { pduDevMgmtOutletSlave09PortEntry 9}

pduDevMgmtOutletSlave09PortOverCurrWarn OBJECT-TYPE
        SYNTAX INTEGER (0..1600)
        UNITS  "0.01A"
        ACCESS read-write
        STATUS mandatory
        DESCRIPTION
                "The warning threshold of outlet current."
        ::= { pduDevMgmtOutletSlave09PortEntry 10}

pduDevMgmtOutletSlave09PortOverCurrCrit OBJECT-TYPE
        SYNTAX INTEGER (0..1600)
        UNITS  "0.01A"
        ACCESS read-write
        STATUS mandatory
        DESCRIPTION
                "The critical threshold of outlet current."
        ::= { pduDevMgmtOutletSlave09PortEntry 11}

pduDevMgmtOutletSlave09PortOverPowerWarn OBJECT-TYPE
        SYNTAX INTEGER (0..27500)
        ACCESS read-write
        STATUS mandatory
        DESCRIPTION
                "The warning threshold of outlet power."
        ::= { pduDevMgmtOutletSlave09PortEntry 12}

pduDevMgmtOutletSlave09PortOverPowerCrit OBJECT-TYPE
        SYNTAX INTEGER (0..27500)
        ACCESS read-write
        STATUS mandatory
        DESCRIPTION
                "The critical threshold of outlet power."
        ::= { pduDevMgmtOutletSlave09PortEntry 13}

pduDevMgmtOutletSlave09PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave09PortEntry 14 }

-- ===========================================================================
--
-- pduDevMgmtOutletSlave10
--
--  Slave10 Outlet Mgmtoitor Group
--
-- ===========================================================================
pduDevMgmtOutletSlave10PortSize OBJECT-TYPE
        SYNTAX INTEGER
        ACCESS read-only
        STATUS mandatory
        DESCRIPTION
                "The port size of master."
        ::= { pduDevMgmtOutletSlave10 1}

-- ===========================================================================
--
-- pduDevMgmtOutletSlave10Port
--
--  Slave10 Outlet Port Mgmtoitor Group
--
-- ===========================================================================
pduDevMgmtOutletSlave10PortTable OBJECT-TYPE
        SYNTAX SEQUENCE OF PduDevMgmtOutletSlave10PortEntry
        ACCESS not-accessible
        STATUS mandatory
        DESCRIPTION
                "Display the port information list of Slave10Port."
        ::= { pduDevMgmtOutletSlave10 2}

pduDevMgmtOutletSlave10PortEntry OBJECT-TYPE
        SYNTAX PduDevMgmtOutletSlave10PortEntry
        ACCESS not-accessible
        STATUS mandatory
        DESCRIPTION
                "Display the port information list of Slave10Port.."
        INDEX  { pduDevMgmtOutletSlave10PortIndex}
        ::= { pduDevMgmtOutletSlave10PortTable 1 }

PduDevMgmtOutletSlave10PortEntry ::=
        SEQUENCE {
                pduDevMgmtOutletSlave10PortIndex
                        INTEGER,
                pduDevMgmtOutletSlave10PortValid
                        INTEGER,
                pduDevMgmtOutletSlave10PortEnergyClr
                        INTEGER,
                pduDevMgmtOutletSlave10PortName
                        DisplayString,
                pduDevMgmtOutletSlave10PortOnDelayTime
                        INTEGER,
                pduDevMgmtOutletSlave10PortOnDelayStatus
                        INTEGER,
                pduDevMgmtOutletSlave10PortOffDelayTime
                        INTEGER,
                pduDevMgmtOutletSlave10PortOffDelayStatus
                        INTEGER,
                pduDevMgmtOutletSlave10PortRebootTime
                        INTEGER,
                pduDevMgmtOutletSlave10PortOverCurrWarn
                        INTEGER,
                pduDevMgmtOutletSlave10PortOverCurrCrit
                        INTEGER,
                pduDevMgmtOutletSlave10PortOverPowerWarn
                        INTEGER,
                pduDevMgmtOutletSlave10PortOverPowerCrit
                        INTEGER,
                pduDevMgmtOutletSlave10PortRly
                        INTEGER
        }

pduDevMgmtOutletSlave10PortIndex OBJECT-TYPE
        SYNTAX INTEGER (0..63)
        ACCESS read-only
        STATUS mandatory
        DESCRIPTION
                "The index to a outlet entry."
        ::= { pduDevMgmtOutletSlave10PortEntry 1 }

pduDevMgmtOutletSlave10PortValid OBJECT-TYPE
        SYNTAX INTEGER {
                offline(1),
                online(2)
                }
        ACCESS read-only
        STATUS mandatory
        DESCRIPTION
                "The online status of outlet."
        ::= { pduDevMgmtOutletSlave10PortEntry 2 }

pduDevMgmtOutletSlave10PortEnergyClr OBJECT-TYPE
        SYNTAX INTEGER {
                nothing(1),
                clearEnergy(2)
                }
        ACCESS read-write
        STATUS mandatory
        DESCRIPTION
                "Clear energy of outlet."
        ::= { pduDevMgmtOutletSlave10PortEntry 3 }

pduDevMgmtOutletSlave10PortName OBJECT-TYPE
        SYNTAX DisplayString (SIZE(0..31))
        ACCESS read-write
        STATUS mandatory
        DESCRIPTION
                "The name of outlet."
        ::= { pduDevMgmtOutletSlave10PortEntry 4 }

pduDevMgmtOutletSlave10PortOnDelayTime OBJECT-TYPE
        SYNTAX INTEGER (1..7200)
        ACCESS read-write
        STATUS mandatory
        DESCRIPTION
                "The on delay of outlet."
        ::= { pduDevMgmtOutletSlave10PortEntry 5}

pduDevMgmtOutletSlave10PortOnDelayStatus OBJECT-TYPE
        SYNTAX  INTEGER {
                nodelay(1),
                delay(2)
                }
        ACCESS read-write
        STATUS mandatory
        DESCRIPTION
                "The delay on status of outlet."
        ::= { pduDevMgmtOutletSlave10PortEntry 6}

pduDevMgmtOutletSlave10PortOffDelayTime OBJECT-TYPE
        SYNTAX INTEGER (1..7200)
        ACCESS read-write
        STATUS mandatory
        DESCRIPTION
                "The off delay of outlet."
        ::= { pduDevMgmtOutletSlave10PortEntry 7}

pduDevMgmtOutletSlave10PortOffDelayStatus OBJECT-TYPE
        SYNTAX  INTEGER {
                nodelay(1),
                delay(2)
                }
        ACCESS read-write
        STATUS mandatory
        DESCRIPTION
                "The delay off status of outlet."
        ::= { pduDevMgmtOutletSlave10PortEntry 8}

pduDevMgmtOutletSlave10PortRebootTime OBJECT-TYPE
        SYNTAX INTEGER (5..60)
        ACCESS read-write
        STATUS mandatory
        DESCRIPTION
                "The reboot time of outlet."
        ::= { pduDevMgmtOutletSlave10PortEntry 9}

pduDevMgmtOutletSlave10PortOverCurrWarn OBJECT-TYPE
        SYNTAX INTEGER (0..1600)
        UNITS  "0.01A"
        ACCESS read-write
        STATUS mandatory
        DESCRIPTION
                "The warning threshold of outlet current."
        ::= { pduDevMgmtOutletSlave10PortEntry 10}

pduDevMgmtOutletSlave10PortOverCurrCrit OBJECT-TYPE
        SYNTAX INTEGER (0..1600)
        UNITS  "0.01A"
        ACCESS read-write
        STATUS mandatory
        DESCRIPTION
                "The critical threshold of outlet current."
        ::= { pduDevMgmtOutletSlave10PortEntry 11}

pduDevMgmtOutletSlave10PortOverPowerWarn OBJECT-TYPE
        SYNTAX INTEGER (0..27500)
        ACCESS read-write
        STATUS mandatory
        DESCRIPTION
                "The warning threshold of outlet power."
        ::= { pduDevMgmtOutletSlave10PortEntry 12}

pduDevMgmtOutletSlave10PortOverPowerCrit OBJECT-TYPE
        SYNTAX INTEGER (0..27500)
        ACCESS read-write
        STATUS mandatory
        DESCRIPTION
                "The critical threshold of outlet power."
        ::= { pduDevMgmtOutletSlave10PortEntry 13}

pduDevMgmtOutletSlave10PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave10PortEntry 14 }

-- ===========================================================================
--
-- pduDevMgmtOutletSlave11
--
--  Slave11 Outlet Mgmtoitor Group
--
-- ===========================================================================
pduDevMgmtOutletSlave11PortSize OBJECT-TYPE
        SYNTAX INTEGER
        ACCESS read-only
        STATUS mandatory
        DESCRIPTION
                "The port size of master."
        ::= { pduDevMgmtOutletSlave11 1}

-- ===========================================================================
--
-- pduDevMgmtOutletSlave11Port
--
--  Slave11 Outlet Port Mgmtoitor Group
--
-- ===========================================================================
pduDevMgmtOutletSlave11PortTable OBJECT-TYPE
        SYNTAX SEQUENCE OF PduDevMgmtOutletSlave11PortEntry
        ACCESS not-accessible
        STATUS mandatory
        DESCRIPTION
                "Display the port information list of Slave11Port."
        ::= { pduDevMgmtOutletSlave11 2}

pduDevMgmtOutletSlave11PortEntry OBJECT-TYPE
        SYNTAX PduDevMgmtOutletSlave11PortEntry
        ACCESS not-accessible
        STATUS mandatory
        DESCRIPTION
                "Display the port information list of Slave11Port.."
        INDEX  { pduDevMgmtOutletSlave11PortIndex}
        ::= { pduDevMgmtOutletSlave11PortTable 1 }

PduDevMgmtOutletSlave11PortEntry ::=
        SEQUENCE {
                pduDevMgmtOutletSlave11PortIndex
                        INTEGER,
                pduDevMgmtOutletSlave11PortValid
                        INTEGER,
                pduDevMgmtOutletSlave11PortEnergyClr
                        INTEGER,
                pduDevMgmtOutletSlave11PortName
                        DisplayString,
                pduDevMgmtOutletSlave11PortOnDelayTime
                        INTEGER,
                pduDevMgmtOutletSlave11PortOnDelayStatus
                        INTEGER,
                pduDevMgmtOutletSlave11PortOffDelayTime
                        INTEGER,
                pduDevMgmtOutletSlave11PortOffDelayStatus
                        INTEGER,
                pduDevMgmtOutletSlave11PortRebootTime
                        INTEGER,
                pduDevMgmtOutletSlave11PortOverCurrWarn
                        INTEGER,
                pduDevMgmtOutletSlave11PortOverCurrCrit
                        INTEGER,
                pduDevMgmtOutletSlave11PortOverPowerWarn
                        INTEGER,
                pduDevMgmtOutletSlave11PortOverPowerCrit
                        INTEGER,
                pduDevMgmtOutletSlave11PortRly
                        INTEGER
        }

pduDevMgmtOutletSlave11PortIndex OBJECT-TYPE
        SYNTAX INTEGER (0..63)
        ACCESS read-only
        STATUS mandatory
        DESCRIPTION
                "The index to a outlet entry."
        ::= { pduDevMgmtOutletSlave11PortEntry 1 }

pduDevMgmtOutletSlave11PortValid OBJECT-TYPE
        SYNTAX INTEGER {
                offline(1),
                online(2)
                }
        ACCESS read-only
        STATUS mandatory
        DESCRIPTION
                "The online status of outlet."
        ::= { pduDevMgmtOutletSlave11PortEntry 2 }

pduDevMgmtOutletSlave11PortEnergyClr OBJECT-TYPE
        SYNTAX INTEGER {
                nothing(1),
                clearEnergy(2)
                }
        ACCESS read-write
        STATUS mandatory
        DESCRIPTION
                "Clear energy of outlet."
        ::= { pduDevMgmtOutletSlave11PortEntry 3 }

pduDevMgmtOutletSlave11PortName OBJECT-TYPE
        SYNTAX DisplayString (SIZE(0..31))
        ACCESS read-write
        STATUS mandatory
        DESCRIPTION
                "The name of outlet."
        ::= { pduDevMgmtOutletSlave11PortEntry 4 }

pduDevMgmtOutletSlave11PortOnDelayTime OBJECT-TYPE
        SYNTAX INTEGER (1..7200)
        ACCESS read-write
        STATUS mandatory
        DESCRIPTION
                "The on delay of outlet."
        ::= { pduDevMgmtOutletSlave11PortEntry 5}

pduDevMgmtOutletSlave11PortOnDelayStatus OBJECT-TYPE
        SYNTAX  INTEGER {
                nodelay(1),
                delay(2)
                }
        ACCESS read-write
        STATUS mandatory
        DESCRIPTION
                "The delay on status of outlet."
        ::= { pduDevMgmtOutletSlave11PortEntry 6}

pduDevMgmtOutletSlave11PortOffDelayTime OBJECT-TYPE
        SYNTAX INTEGER (1..7200)
        ACCESS read-write
        STATUS mandatory
        DESCRIPTION
                "The off delay of outlet."
        ::= { pduDevMgmtOutletSlave11PortEntry 7}

pduDevMgmtOutletSlave11PortOffDelayStatus OBJECT-TYPE
        SYNTAX  INTEGER {
                nodelay(1),
                delay(2)
                }
        ACCESS read-write
        STATUS mandatory
        DESCRIPTION
                "The delay off status of outlet."
        ::= { pduDevMgmtOutletSlave11PortEntry 8}

pduDevMgmtOutletSlave11PortRebootTime OBJECT-TYPE
        SYNTAX INTEGER (5..60)
        ACCESS read-write
        STATUS mandatory
        DESCRIPTION
                "The reboot time of outlet."
        ::= { pduDevMgmtOutletSlave11PortEntry 9}

pduDevMgmtOutletSlave11PortOverCurrWarn OBJECT-TYPE
        SYNTAX INTEGER (0..1600)
        UNITS  "0.01A"
        ACCESS read-write
        STATUS mandatory
        DESCRIPTION
                "The warning threshold of outlet current."
        ::= { pduDevMgmtOutletSlave11PortEntry 10}

pduDevMgmtOutletSlave11PortOverCurrCrit OBJECT-TYPE
        SYNTAX INTEGER (0..1600)
        UNITS  "0.01A"
        ACCESS read-write
        STATUS mandatory
        DESCRIPTION
                "The critical threshold of outlet current."
        ::= { pduDevMgmtOutletSlave11PortEntry 11}

pduDevMgmtOutletSlave11PortOverPowerWarn OBJECT-TYPE
        SYNTAX INTEGER (0..27500)
        ACCESS read-write
        STATUS mandatory
        DESCRIPTION
                "The warning threshold of outlet power."
        ::= { pduDevMgmtOutletSlave11PortEntry 12}

pduDevMgmtOutletSlave11PortOverPowerCrit OBJECT-TYPE
        SYNTAX INTEGER (0..27500)
        ACCESS read-write
        STATUS mandatory
        DESCRIPTION
                "The critical threshold of outlet power."
        ::= { pduDevMgmtOutletSlave11PortEntry 13}

pduDevMgmtOutletSlave11PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave11PortEntry 14 }

-- ===========================================================================
--
-- pduDevMgmtOutletSlave12
--
--  Slave12 Outlet Mgmtoitor Group
--
-- ===========================================================================
pduDevMgmtOutletSlave12PortSize OBJECT-TYPE
        SYNTAX INTEGER
        ACCESS read-only
        STATUS mandatory
        DESCRIPTION
                "The port size of master."
        ::= { pduDevMgmtOutletSlave12 1}

-- ===========================================================================
--
-- pduDevMgmtOutletSlave12Port
--
--  Slave12 Outlet Port Mgmtoitor Group
--
-- ===========================================================================
pduDevMgmtOutletSlave12PortTable OBJECT-TYPE
        SYNTAX SEQUENCE OF PduDevMgmtOutletSlave12PortEntry
        ACCESS not-accessible
        STATUS mandatory
        DESCRIPTION
                "Display the port information list of Slave12Port."
        ::= { pduDevMgmtOutletSlave12 2}

pduDevMgmtOutletSlave12PortEntry OBJECT-TYPE
        SYNTAX PduDevMgmtOutletSlave12PortEntry
        ACCESS not-accessible
        STATUS mandatory
        DESCRIPTION
                "Display the port information list of Slave12Port.."
        INDEX  { pduDevMgmtOutletSlave12PortIndex}
        ::= { pduDevMgmtOutletSlave12PortTable 1 }

PduDevMgmtOutletSlave12PortEntry ::=
        SEQUENCE {
                pduDevMgmtOutletSlave12PortIndex
                        INTEGER,
                pduDevMgmtOutletSlave12PortValid
                        INTEGER,
                pduDevMgmtOutletSlave12PortEnergyClr
                        INTEGER,
                pduDevMgmtOutletSlave12PortName
                        DisplayString,
                pduDevMgmtOutletSlave12PortOnDelayTime
                        INTEGER,
                pduDevMgmtOutletSlave12PortOnDelayStatus
                        INTEGER,
                pduDevMgmtOutletSlave12PortOffDelayTime
                        INTEGER,
                pduDevMgmtOutletSlave12PortOffDelayStatus
                        INTEGER,
                pduDevMgmtOutletSlave12PortRebootTime
                        INTEGER,
                pduDevMgmtOutletSlave12PortOverCurrWarn
                        INTEGER,
                pduDevMgmtOutletSlave12PortOverCurrCrit
                        INTEGER,
                pduDevMgmtOutletSlave12PortOverPowerWarn
                        INTEGER,
                pduDevMgmtOutletSlave12PortOverPowerCrit
                        INTEGER,
                pduDevMgmtOutletSlave12PortRly
                        INTEGER
        }

pduDevMgmtOutletSlave12PortIndex OBJECT-TYPE
        SYNTAX INTEGER (0..63)
        ACCESS read-only
        STATUS mandatory
        DESCRIPTION
                "The index to a outlet entry."
        ::= { pduDevMgmtOutletSlave12PortEntry 1 }

pduDevMgmtOutletSlave12PortValid OBJECT-TYPE
        SYNTAX INTEGER {
                offline(1),
                online(2)
                }
        ACCESS read-only
        STATUS mandatory
        DESCRIPTION
                "The online status of outlet."
        ::= { pduDevMgmtOutletSlave12PortEntry 2 }

pduDevMgmtOutletSlave12PortEnergyClr OBJECT-TYPE
        SYNTAX INTEGER {
                nothing(1),
                clearEnergy(2)
                }
        ACCESS read-write
        STATUS mandatory
        DESCRIPTION
                "Clear energy of outlet."
        ::= { pduDevMgmtOutletSlave12PortEntry 3 }

pduDevMgmtOutletSlave12PortName OBJECT-TYPE
        SYNTAX DisplayString (SIZE(0..31))
        ACCESS read-write
        STATUS mandatory
        DESCRIPTION
                "The name of outlet."
        ::= { pduDevMgmtOutletSlave12PortEntry 4 }

pduDevMgmtOutletSlave12PortOnDelayTime OBJECT-TYPE
        SYNTAX INTEGER (1..7200)
        ACCESS read-write
        STATUS mandatory
        DESCRIPTION
                "The on delay of outlet."
        ::= { pduDevMgmtOutletSlave12PortEntry 5}

pduDevMgmtOutletSlave12PortOnDelayStatus OBJECT-TYPE
        SYNTAX  INTEGER {
                nodelay(1),
                delay(2)
                }
        ACCESS read-write
        STATUS mandatory
        DESCRIPTION
                "The delay on status of outlet."
        ::= { pduDevMgmtOutletSlave12PortEntry 6}

pduDevMgmtOutletSlave12PortOffDelayTime OBJECT-TYPE
        SYNTAX INTEGER (1..7200)
        ACCESS read-write
        STATUS mandatory
        DESCRIPTION
                "The off delay of outlet."
        ::= { pduDevMgmtOutletSlave12PortEntry 7}

pduDevMgmtOutletSlave12PortOffDelayStatus OBJECT-TYPE
        SYNTAX  INTEGER {
                nodelay(1),
                delay(2)
                }
        ACCESS read-write
        STATUS mandatory
        DESCRIPTION
                "The delay off status of outlet."
        ::= { pduDevMgmtOutletSlave12PortEntry 8}

pduDevMgmtOutletSlave12PortRebootTime OBJECT-TYPE
        SYNTAX INTEGER (5..60)
        ACCESS read-write
        STATUS mandatory
        DESCRIPTION
                "The reboot time of outlet."
        ::= { pduDevMgmtOutletSlave12PortEntry 9}

pduDevMgmtOutletSlave12PortOverCurrWarn OBJECT-TYPE
        SYNTAX INTEGER (0..1600)
        UNITS  "0.01A"
        ACCESS read-write
        STATUS mandatory
        DESCRIPTION
                "The warning threshold of outlet current."
        ::= { pduDevMgmtOutletSlave12PortEntry 10}

pduDevMgmtOutletSlave12PortOverCurrCrit OBJECT-TYPE
        SYNTAX INTEGER (0..1600)
        UNITS  "0.01A"
        ACCESS read-write
        STATUS mandatory
        DESCRIPTION
                "The critical threshold of outlet current."
        ::= { pduDevMgmtOutletSlave12PortEntry 11}

pduDevMgmtOutletSlave12PortOverPowerWarn OBJECT-TYPE
        SYNTAX INTEGER (0..27500)
        ACCESS read-write
        STATUS mandatory
        DESCRIPTION
                "The warning threshold of outlet power."
        ::= { pduDevMgmtOutletSlave12PortEntry 12}

pduDevMgmtOutletSlave12PortOverPowerCrit OBJECT-TYPE
        SYNTAX INTEGER (0..27500)
        ACCESS read-write
        STATUS mandatory
        DESCRIPTION
                "The critical threshold of outlet power."
        ::= { pduDevMgmtOutletSlave12PortEntry 13}

pduDevMgmtOutletSlave12PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave12PortEntry 14 }

-- ===========================================================================
--
-- pduDevMgmtOutletSlave13
--
--  Slave13 Outlet Mgmtoitor Group
--
-- ===========================================================================
pduDevMgmtOutletSlave13PortSize OBJECT-TYPE
        SYNTAX INTEGER
        ACCESS read-only
        STATUS mandatory
        DESCRIPTION
                "The port size of master."
        ::= { pduDevMgmtOutletSlave13 1}

-- ===========================================================================
--
-- pduDevMgmtOutletSlave13Port
--
--  Slave13 Outlet Port Mgmtoitor Group
--
-- ===========================================================================
pduDevMgmtOutletSlave13PortTable OBJECT-TYPE
        SYNTAX SEQUENCE OF PduDevMgmtOutletSlave13PortEntry
        ACCESS not-accessible
        STATUS mandatory
        DESCRIPTION
                "Display the port information list of Slave13Port."
        ::= { pduDevMgmtOutletSlave13 2}

pduDevMgmtOutletSlave13PortEntry OBJECT-TYPE
        SYNTAX PduDevMgmtOutletSlave13PortEntry
        ACCESS not-accessible
        STATUS mandatory
        DESCRIPTION
                "Display the port information list of Slave13Port.."
        INDEX  { pduDevMgmtOutletSlave13PortIndex}
        ::= { pduDevMgmtOutletSlave13PortTable 1 }

PduDevMgmtOutletSlave13PortEntry ::=
        SEQUENCE {
                pduDevMgmtOutletSlave13PortIndex
                        INTEGER,
                pduDevMgmtOutletSlave13PortValid
                        INTEGER,
                pduDevMgmtOutletSlave13PortEnergyClr
                        INTEGER,
                pduDevMgmtOutletSlave13PortName
                        DisplayString,
                pduDevMgmtOutletSlave13PortOnDelayTime
                        INTEGER,
                pduDevMgmtOutletSlave13PortOnDelayStatus
                        INTEGER,
                pduDevMgmtOutletSlave13PortOffDelayTime
                        INTEGER,
                pduDevMgmtOutletSlave13PortOffDelayStatus
                        INTEGER,
                pduDevMgmtOutletSlave13PortRebootTime
                        INTEGER,
                pduDevMgmtOutletSlave13PortOverCurrWarn
                        INTEGER,
                pduDevMgmtOutletSlave13PortOverCurrCrit
                        INTEGER,
                pduDevMgmtOutletSlave13PortOverPowerWarn
                        INTEGER,
                pduDevMgmtOutletSlave13PortOverPowerCrit
                        INTEGER,
                pduDevMgmtOutletSlave13PortRly
                        INTEGER
        }

pduDevMgmtOutletSlave13PortIndex OBJECT-TYPE
        SYNTAX INTEGER (0..63)
        ACCESS read-only
        STATUS mandatory
        DESCRIPTION
                "The index to a outlet entry."
        ::= { pduDevMgmtOutletSlave13PortEntry 1 }

pduDevMgmtOutletSlave13PortValid OBJECT-TYPE
        SYNTAX INTEGER {
                offline(1),
                online(2)
                }
        ACCESS read-only
        STATUS mandatory
        DESCRIPTION
                "The online status of outlet."
        ::= { pduDevMgmtOutletSlave13PortEntry 2 }

pduDevMgmtOutletSlave13PortEnergyClr OBJECT-TYPE
        SYNTAX INTEGER {
                nothing(1),
                clearEnergy(2)
                }
        ACCESS read-write
        STATUS mandatory
        DESCRIPTION
                "Clear energy of outlet."
        ::= { pduDevMgmtOutletSlave13PortEntry 3 }

pduDevMgmtOutletSlave13PortName OBJECT-TYPE
        SYNTAX DisplayString (SIZE(0..31))
        ACCESS read-write
        STATUS mandatory
        DESCRIPTION
                "The name of outlet."
        ::= { pduDevMgmtOutletSlave13PortEntry 4 }

pduDevMgmtOutletSlave13PortOnDelayTime OBJECT-TYPE
        SYNTAX INTEGER (1..7200)
        ACCESS read-write
        STATUS mandatory
        DESCRIPTION
                "The on delay of outlet."
        ::= { pduDevMgmtOutletSlave13PortEntry 5}

pduDevMgmtOutletSlave13PortOnDelayStatus OBJECT-TYPE
        SYNTAX  INTEGER {
                nodelay(1),
                delay(2)
                }
        ACCESS read-write
        STATUS mandatory
        DESCRIPTION
                "The delay on status of outlet."
        ::= { pduDevMgmtOutletSlave13PortEntry 6}

pduDevMgmtOutletSlave13PortOffDelayTime OBJECT-TYPE
        SYNTAX INTEGER (1..7200)
        ACCESS read-write
        STATUS mandatory
        DESCRIPTION
                "The off delay of outlet."
        ::= { pduDevMgmtOutletSlave13PortEntry 7}

pduDevMgmtOutletSlave13PortOffDelayStatus OBJECT-TYPE
        SYNTAX  INTEGER {
                nodelay(1),
                delay(2)
                }
        ACCESS read-write
        STATUS mandatory
        DESCRIPTION
                "The delay off status of outlet."
        ::= { pduDevMgmtOutletSlave13PortEntry 8}

pduDevMgmtOutletSlave13PortRebootTime OBJECT-TYPE
        SYNTAX INTEGER (5..60)
        ACCESS read-write
        STATUS mandatory
        DESCRIPTION
                "The reboot time of outlet."
        ::= { pduDevMgmtOutletSlave13PortEntry 9}

pduDevMgmtOutletSlave13PortOverCurrWarn OBJECT-TYPE
        SYNTAX INTEGER (0..1600)
        UNITS  "0.01A"
        ACCESS read-write
        STATUS mandatory
        DESCRIPTION
                "The warning threshold of outlet current."
        ::= { pduDevMgmtOutletSlave13PortEntry 10}

pduDevMgmtOutletSlave13PortOverCurrCrit OBJECT-TYPE
        SYNTAX INTEGER (0..1600)
        UNITS  "0.01A"
        ACCESS read-write
        STATUS mandatory
        DESCRIPTION
                "The critical threshold of outlet current."
        ::= { pduDevMgmtOutletSlave13PortEntry 11}

pduDevMgmtOutletSlave13PortOverPowerWarn OBJECT-TYPE
        SYNTAX INTEGER (0..27500)
        ACCESS read-write
        STATUS mandatory
        DESCRIPTION
                "The warning threshold of outlet power."
        ::= { pduDevMgmtOutletSlave13PortEntry 12}

pduDevMgmtOutletSlave13PortOverPowerCrit OBJECT-TYPE
        SYNTAX INTEGER (0..27500)
        ACCESS read-write
        STATUS mandatory
        DESCRIPTION
                "The critical threshold of outlet power."
        ::= { pduDevMgmtOutletSlave13PortEntry 13}

pduDevMgmtOutletSlave13PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave13PortEntry 14 }

-- ===========================================================================
--
-- pduDevMgmtOutletSlave14
--
--  Slave14 Outlet Mgmtoitor Group
--
-- ===========================================================================
pduDevMgmtOutletSlave14PortSize OBJECT-TYPE
        SYNTAX INTEGER
        ACCESS read-only
        STATUS mandatory
        DESCRIPTION
                "The port size of master."
        ::= { pduDevMgmtOutletSlave14 1}

-- ===========================================================================
--
-- pduDevMgmtOutletSlave14Port
--
--  Slave14 Outlet Port Mgmtoitor Group
--
-- ===========================================================================
pduDevMgmtOutletSlave14PortTable OBJECT-TYPE
        SYNTAX SEQUENCE OF PduDevMgmtOutletSlave14PortEntry
        ACCESS not-accessible
        STATUS mandatory
        DESCRIPTION
                "Display the port information list of Slave14Port."
        ::= { pduDevMgmtOutletSlave14 2}

pduDevMgmtOutletSlave14PortEntry OBJECT-TYPE
        SYNTAX PduDevMgmtOutletSlave14PortEntry
        ACCESS not-accessible
        STATUS mandatory
        DESCRIPTION
                "Display the port information list of Slave14Port.."
        INDEX  { pduDevMgmtOutletSlave14PortIndex}
        ::= { pduDevMgmtOutletSlave14PortTable 1 }

PduDevMgmtOutletSlave14PortEntry ::=
        SEQUENCE {
                pduDevMgmtOutletSlave14PortIndex
                        INTEGER,
                pduDevMgmtOutletSlave14PortValid
                        INTEGER,
                pduDevMgmtOutletSlave14PortEnergyClr
                        INTEGER,
                pduDevMgmtOutletSlave14PortName
                        DisplayString,
                pduDevMgmtOutletSlave14PortOnDelayTime
                        INTEGER,
                pduDevMgmtOutletSlave14PortOnDelayStatus
                        INTEGER,
                pduDevMgmtOutletSlave14PortOffDelayTime
                        INTEGER,
                pduDevMgmtOutletSlave14PortOffDelayStatus
                        INTEGER,
                pduDevMgmtOutletSlave14PortRebootTime
                        INTEGER,
                pduDevMgmtOutletSlave14PortOverCurrWarn
                        INTEGER,
                pduDevMgmtOutletSlave14PortOverCurrCrit
                        INTEGER,
                pduDevMgmtOutletSlave14PortOverPowerWarn
                        INTEGER,
                pduDevMgmtOutletSlave14PortOverPowerCrit
                        INTEGER,
                pduDevMgmtOutletSlave14PortRly
                        INTEGER
        }

pduDevMgmtOutletSlave14PortIndex OBJECT-TYPE
        SYNTAX INTEGER (0..63)
        ACCESS read-only
        STATUS mandatory
        DESCRIPTION
                "The index to a outlet entry."
        ::= { pduDevMgmtOutletSlave14PortEntry 1 }

pduDevMgmtOutletSlave14PortValid OBJECT-TYPE
        SYNTAX INTEGER {
                offline(1),
                online(2)
                }
        ACCESS read-only
        STATUS mandatory
        DESCRIPTION
                "The online status of outlet."
        ::= { pduDevMgmtOutletSlave14PortEntry 2 }

pduDevMgmtOutletSlave14PortEnergyClr OBJECT-TYPE
        SYNTAX INTEGER {
                nothing(1),
                clearEnergy(2)
                }
        ACCESS read-write
        STATUS mandatory
        DESCRIPTION
                "Clear energy of outlet."
        ::= { pduDevMgmtOutletSlave14PortEntry 3 }

pduDevMgmtOutletSlave14PortName OBJECT-TYPE
        SYNTAX DisplayString (SIZE(0..31))
        ACCESS read-write
        STATUS mandatory
        DESCRIPTION
                "The name of outlet."
        ::= { pduDevMgmtOutletSlave14PortEntry 4 }

pduDevMgmtOutletSlave14PortOnDelayTime OBJECT-TYPE
        SYNTAX INTEGER (1..7200)
        ACCESS read-write
        STATUS mandatory
        DESCRIPTION
                "The on delay of outlet."
        ::= { pduDevMgmtOutletSlave14PortEntry 5}

pduDevMgmtOutletSlave14PortOnDelayStatus OBJECT-TYPE
        SYNTAX  INTEGER {
                nodelay(1),
                delay(2)
                }
        ACCESS read-write
        STATUS mandatory
        DESCRIPTION
                "The delay on status of outlet."
        ::= { pduDevMgmtOutletSlave14PortEntry 6}

pduDevMgmtOutletSlave14PortOffDelayTime OBJECT-TYPE
        SYNTAX INTEGER (1..7200)
        ACCESS read-write
        STATUS mandatory
        DESCRIPTION
                "The off delay of outlet."
        ::= { pduDevMgmtOutletSlave14PortEntry 7}

pduDevMgmtOutletSlave14PortOffDelayStatus OBJECT-TYPE
        SYNTAX  INTEGER {
                nodelay(1),
                delay(2)
                }
        ACCESS read-write
        STATUS mandatory
        DESCRIPTION
                "The delay off status of outlet."
        ::= { pduDevMgmtOutletSlave14PortEntry 8}

pduDevMgmtOutletSlave14PortRebootTime OBJECT-TYPE
        SYNTAX INTEGER (5..60)
        ACCESS read-write
        STATUS mandatory
        DESCRIPTION
                "The reboot time of outlet."
        ::= { pduDevMgmtOutletSlave14PortEntry 9}

pduDevMgmtOutletSlave14PortOverCurrWarn OBJECT-TYPE
        SYNTAX INTEGER (0..1600)
        UNITS  "0.01A"
        ACCESS read-write
        STATUS mandatory
        DESCRIPTION
                "The warning threshold of outlet current."
        ::= { pduDevMgmtOutletSlave14PortEntry 10}

pduDevMgmtOutletSlave14PortOverCurrCrit OBJECT-TYPE
        SYNTAX INTEGER (0..1600)
        UNITS  "0.01A"
        ACCESS read-write
        STATUS mandatory
        DESCRIPTION
                "The critical threshold of outlet current."
        ::= { pduDevMgmtOutletSlave14PortEntry 11}

pduDevMgmtOutletSlave14PortOverPowerWarn OBJECT-TYPE
        SYNTAX INTEGER (0..27500)
        ACCESS read-write
        STATUS mandatory
        DESCRIPTION
                "The warning threshold of outlet power."
        ::= { pduDevMgmtOutletSlave14PortEntry 12}

pduDevMgmtOutletSlave14PortOverPowerCrit OBJECT-TYPE
        SYNTAX INTEGER (0..27500)
        ACCESS read-write
        STATUS mandatory
        DESCRIPTION
                "The critical threshold of outlet power."
        ::= { pduDevMgmtOutletSlave14PortEntry 13}

pduDevMgmtOutletSlave14PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave14PortEntry 14 }

-- ===========================================================================
--
-- pduDevMgmtOutletSlave15
--
--  Slave15 Outlet Mgmtoitor Group
--
-- ===========================================================================
pduDevMgmtOutletSlave15PortSize OBJECT-TYPE
        SYNTAX INTEGER
        ACCESS read-only
        STATUS mandatory
        DESCRIPTION
                "The port size of master."
        ::= { pduDevMgmtOutletSlave15 1}

-- ===========================================================================
--
-- pduDevMgmtOutletSlave15Port
--
--  Slave15 Outlet Port Mgmtoitor Group
--
-- ===========================================================================
pduDevMgmtOutletSlave15PortTable OBJECT-TYPE
        SYNTAX SEQUENCE OF PduDevMgmtOutletSlave15PortEntry
        ACCESS not-accessible
        STATUS mandatory
        DESCRIPTION
                "Display the port information list of Slave15Port."
        ::= { pduDevMgmtOutletSlave15 2}

pduDevMgmtOutletSlave15PortEntry OBJECT-TYPE
        SYNTAX PduDevMgmtOutletSlave15PortEntry
        ACCESS not-accessible
        STATUS mandatory
        DESCRIPTION
                "Display the port information list of Slave15Port.."
        INDEX  { pduDevMgmtOutletSlave15PortIndex}
        ::= { pduDevMgmtOutletSlave15PortTable 1 }

PduDevMgmtOutletSlave15PortEntry ::=
        SEQUENCE {
                pduDevMgmtOutletSlave15PortIndex
                        INTEGER,
                pduDevMgmtOutletSlave15PortValid
                        INTEGER,
                pduDevMgmtOutletSlave15PortEnergyClr
                        INTEGER,
                pduDevMgmtOutletSlave15PortName
                        DisplayString,
                pduDevMgmtOutletSlave15PortOnDelayTime
                        INTEGER,
                pduDevMgmtOutletSlave15PortOnDelayStatus
                        INTEGER,
                pduDevMgmtOutletSlave15PortOffDelayTime
                        INTEGER,
                pduDevMgmtOutletSlave15PortOffDelayStatus
                        INTEGER,
                pduDevMgmtOutletSlave15PortRebootTime
                        INTEGER,
                pduDevMgmtOutletSlave15PortOverCurrWarn
                        INTEGER,
                pduDevMgmtOutletSlave15PortOverCurrCrit
                        INTEGER,
                pduDevMgmtOutletSlave15PortOverPowerWarn
                        INTEGER,
                pduDevMgmtOutletSlave15PortOverPowerCrit
                        INTEGER,
                pduDevMgmtOutletSlave15PortRly
                        INTEGER
        }

pduDevMgmtOutletSlave15PortIndex OBJECT-TYPE
        SYNTAX INTEGER (0..63)
        ACCESS read-only
        STATUS mandatory
        DESCRIPTION
                "The index to a outlet entry."
        ::= { pduDevMgmtOutletSlave15PortEntry 1 }

pduDevMgmtOutletSlave15PortValid OBJECT-TYPE
        SYNTAX INTEGER {
                offline(1),
                online(2)
                }
        ACCESS read-only
        STATUS mandatory
        DESCRIPTION
                "The online status of outlet."
        ::= { pduDevMgmtOutletSlave15PortEntry 2 }

pduDevMgmtOutletSlave15PortEnergyClr OBJECT-TYPE
        SYNTAX INTEGER {
                nothing(1),
                clearEnergy(2)
                }
        ACCESS read-write
        STATUS mandatory
        DESCRIPTION
                "Clear energy of outlet."
        ::= { pduDevMgmtOutletSlave15PortEntry 3 }

pduDevMgmtOutletSlave15PortName OBJECT-TYPE
        SYNTAX DisplayString (SIZE(0..31))
        ACCESS read-write
        STATUS mandatory
        DESCRIPTION
                "The name of outlet."
        ::= { pduDevMgmtOutletSlave15PortEntry 4 }

pduDevMgmtOutletSlave15PortOnDelayTime OBJECT-TYPE
        SYNTAX INTEGER (1..7200)
        ACCESS read-write
        STATUS mandatory
        DESCRIPTION
                "The on delay of outlet."
        ::= { pduDevMgmtOutletSlave15PortEntry 5}

pduDevMgmtOutletSlave15PortOnDelayStatus OBJECT-TYPE
        SYNTAX  INTEGER {
                nodelay(1),
                delay(2)
                }
        ACCESS read-write
        STATUS mandatory
        DESCRIPTION
                "The delay on status of outlet."
        ::= { pduDevMgmtOutletSlave15PortEntry 6}

pduDevMgmtOutletSlave15PortOffDelayTime OBJECT-TYPE
        SYNTAX INTEGER (1..7200)
        ACCESS read-write
        STATUS mandatory
        DESCRIPTION
                "The off delay of outlet."
        ::= { pduDevMgmtOutletSlave15PortEntry 7}

pduDevMgmtOutletSlave15PortOffDelayStatus OBJECT-TYPE
        SYNTAX  INTEGER {
                nodelay(1),
                delay(2)
                }
        ACCESS read-write
        STATUS mandatory
        DESCRIPTION
                "The delay off status of outlet."
        ::= { pduDevMgmtOutletSlave15PortEntry 8}

pduDevMgmtOutletSlave15PortRebootTime OBJECT-TYPE
        SYNTAX INTEGER (5..60)
        ACCESS read-write
        STATUS mandatory
        DESCRIPTION
                "The reboot time of outlet."
        ::= { pduDevMgmtOutletSlave15PortEntry 9}

pduDevMgmtOutletSlave15PortOverCurrWarn OBJECT-TYPE
        SYNTAX INTEGER (0..1600)
        UNITS  "0.01A"
        ACCESS read-write
        STATUS mandatory
        DESCRIPTION
                "The warning threshold of outlet current."
        ::= { pduDevMgmtOutletSlave15PortEntry 10}

pduDevMgmtOutletSlave15PortOverCurrCrit OBJECT-TYPE
        SYNTAX INTEGER (0..1600)
        UNITS  "0.01A"
        ACCESS read-write
        STATUS mandatory
        DESCRIPTION
                "The critical threshold of outlet current."
        ::= { pduDevMgmtOutletSlave15PortEntry 11}

pduDevMgmtOutletSlave15PortOverPowerWarn OBJECT-TYPE
        SYNTAX INTEGER (0..27500)
        ACCESS read-write
        STATUS mandatory
        DESCRIPTION
                "The warning threshold of outlet power."
        ::= { pduDevMgmtOutletSlave15PortEntry 12}

pduDevMgmtOutletSlave15PortOverPowerCrit OBJECT-TYPE
        SYNTAX INTEGER (0..27500)
        ACCESS read-write
        STATUS mandatory
        DESCRIPTION
                "The critical threshold of outlet power."
        ::= { pduDevMgmtOutletSlave15PortEntry 13}

pduDevMgmtOutletSlave15PortRly OBJECT-TYPE
        SYNTAX INTEGER {
                nothing(1),
                immOn(2),
                delayOn(3),
                immOff(4),
                delayOff(5),
                cycle(6),
                delayCycle(7)
                }
        ACCESS read-write
        STATUS mandatory
        DESCRIPTION
                "Relay action of outlet."
        ::= { pduDevMgmtOutletSlave15PortEntry 14 }

-- ===========================================================================
--
-- pduDevMgmtEmd
--
--  Emd Device Management Group
--
-- ===========================================================================
pduDevMgmtEmdMaster      OBJECT IDENTIFIER ::= { pduDevMgmtEmd 1 }
pduDevMgmtEmdSlave01     OBJECT IDENTIFIER ::= { pduDevMgmtEmd 2 }
pduDevMgmtEmdSlave02     OBJECT IDENTIFIER ::= { pduDevMgmtEmd 3 }
pduDevMgmtEmdSlave03     OBJECT IDENTIFIER ::= { pduDevMgmtEmd 4 }
pduDevMgmtEmdSlave04     OBJECT IDENTIFIER ::= { pduDevMgmtEmd 5 }
pduDevMgmtEmdSlave05     OBJECT IDENTIFIER ::= { pduDevMgmtEmd 6 }
pduDevMgmtEmdSlave06     OBJECT IDENTIFIER ::= { pduDevMgmtEmd 7 }
pduDevMgmtEmdSlave07     OBJECT IDENTIFIER ::= { pduDevMgmtEmd 8 }
pduDevMgmtEmdSlave08     OBJECT IDENTIFIER ::= { pduDevMgmtEmd 9 }
pduDevMgmtEmdSlave09     OBJECT IDENTIFIER ::= { pduDevMgmtEmd 10 }
pduDevMgmtEmdSlave10     OBJECT IDENTIFIER ::= { pduDevMgmtEmd 11 }
pduDevMgmtEmdSlave11     OBJECT IDENTIFIER ::= { pduDevMgmtEmd 12 }
pduDevMgmtEmdSlave12     OBJECT IDENTIFIER ::= { pduDevMgmtEmd 13 }
pduDevMgmtEmdSlave13     OBJECT IDENTIFIER ::= { pduDevMgmtEmd 14 }
pduDevMgmtEmdSlave14     OBJECT IDENTIFIER ::= { pduDevMgmtEmd 15 }
pduDevMgmtEmdSlave15     OBJECT IDENTIFIER ::= { pduDevMgmtEmd 16 }

-- ===========================================================================
--
-- pduDevMgmtEmdMaster
--
--  Master Emd Mgmtoitor Group
--
-- ===========================================================================
pduDevMgmtEmdMasterTable OBJECT-TYPE
        SYNTAX SEQUENCE OF PduDevMgmtEmdMasterEntry
        ACCESS not-accessible
        STATUS mandatory
        DESCRIPTION
                "Display a list of the emd information of master."
        ::= { pduDevMgmtEmdMaster 1}

pduDevMgmtEmdMasterEntry OBJECT-TYPE
        SYNTAX PduDevMgmtEmdMasterEntry
        ACCESS not-accessible
        STATUS mandatory
        DESCRIPTION
                "Display a list of the emd information of master."
        INDEX  { pduDevMgmtEmdMasterIndex}
        ::= { pduDevMgmtEmdMasterTable 1 }

PduDevMgmtEmdMasterEntry ::=
        SEQUENCE {
                pduDevMgmtEmdMasterIndex
                        INTEGER,
                pduDevMgmtEmdMasterValid
                        INTEGER,
                pduDevMgmtEmdMasterType
                        INTEGER,
                pduDevMgmtEmdMasterName
                        DisplayString,
                pduDevMgmtEmdMasterTempName
                        DisplayString,
                pduDevMgmtEmdMasterHumiName
                        DisplayString,
                pduDevMgmtEmdMasterAlarm1Name
                        DisplayString,
                pduDevMgmtEmdMasterAlarm2Name
                        DisplayString,
                pduDevMgmtEmdMasterTempLowWarn
                        INTEGER,
                pduDevMgmtEmdMasterTempLowCrit
                        INTEGER,
                pduDevMgmtEmdMasterTempHighWarn
                        INTEGER,
                pduDevMgmtEmdMasterTempHighCrit
                        INTEGER,
                pduDevMgmtEmdMasterTempCali
                        INTEGER,
                pduDevMgmtEmdMasterHumiLowWarn
                        INTEGER,
                pduDevMgmtEmdMasterHumiLowCrit
                        INTEGER,
                pduDevMgmtEmdMasterHumiHighWarn
                        INTEGER,
                pduDevMgmtEmdMasterHumiHighCrit
                        INTEGER,
                pduDevMgmtEmdMasterHumiCali
                        INTEGER,
                pduDevMgmtEmdMasterAlarm1Setup
                        INTEGER,
                pduDevMgmtEmdMasterAlarm2Setup
                        INTEGER
        }

pduDevMgmtEmdMasterIndex OBJECT-TYPE
        SYNTAX INTEGER (0..7)
        ACCESS read-only
        STATUS mandatory
        DESCRIPTION
                "The index to a emd entry."
        ::= { pduDevMgmtEmdMasterEntry 1 }

pduDevMgmtEmdMasterValid OBJECT-TYPE
        SYNTAX INTEGER {
                offline(1),
                online(2)
                }
        ACCESS read-only
        STATUS mandatory
        DESCRIPTION
                "The online status of emd."
        ::= { pduDevMgmtEmdMasterEntry 2 }


pduDevMgmtEmdMasterType OBJECT-TYPE
        SYNTAX INTEGER
        ACCESS read-only
        STATUS mandatory
        DESCRIPTION
                "The type of emd."
        ::= { pduDevMgmtEmdMasterEntry 3 }

pduDevMgmtEmdMasterName OBJECT-TYPE
        SYNTAX DisplayString (SIZE(0..31))
        ACCESS read-write
        STATUS mandatory
        DESCRIPTION
                "The name of emd."
        ::= { pduDevMgmtEmdMasterEntry 4 }

pduDevMgmtEmdMasterTempName OBJECT-TYPE
        SYNTAX DisplayString (SIZE(0..31))
        ACCESS read-write
        STATUS mandatory
        DESCRIPTION
                "The name of emd temperature."
        ::= { pduDevMgmtEmdMasterEntry 5 }

pduDevMgmtEmdMasterHumiName OBJECT-TYPE
        SYNTAX DisplayString (SIZE(0..31))
        ACCESS read-write
        STATUS mandatory
        DESCRIPTION
                "The name of emd humidity."
        ::= { pduDevMgmtEmdMasterEntry 6 }

pduDevMgmtEmdMasterAlarm1Name OBJECT-TYPE
        SYNTAX DisplayString (SIZE(0..31))
        ACCESS read-write
        STATUS mandatory
        DESCRIPTION
                "The name of emd alarm-1."
        ::= { pduDevMgmtEmdMasterEntry 7 }

pduDevMgmtEmdMasterAlarm2Name OBJECT-TYPE
        SYNTAX DisplayString (SIZE(0..31))
        ACCESS read-write
        STATUS mandatory
        DESCRIPTION
                "The name of emd alarm-2."
        ::= { pduDevMgmtEmdMasterEntry 8 }

pduDevMgmtEmdMasterTempLowWarn OBJECT-TYPE
        SYNTAX INTEGER (-200..1000)
        UNITS  "0.1degC"
        ACCESS read-write
        STATUS mandatory
        DESCRIPTION
                "The low warning threshold of temperature of emd."
        ::= { pduDevMgmtEmdMasterEntry 9 }

pduDevMgmtEmdMasterTempLowCrit OBJECT-TYPE
        SYNTAX INTEGER (-200..1000)
        UNITS  "0.1degC"
        ACCESS read-write
        STATUS mandatory
        DESCRIPTION
                "The low critical threshold of temperature of emd."
        ::= { pduDevMgmtEmdMasterEntry 10 }

pduDevMgmtEmdMasterTempHighWarn OBJECT-TYPE
        SYNTAX INTEGER (-200..1000)
        UNITS  "0.1degC"
        ACCESS read-write
        STATUS mandatory
        DESCRIPTION
                "The high warning threshold of temperature of emd."
        ::= { pduDevMgmtEmdMasterEntry 11 }

pduDevMgmtEmdMasterTempHighCrit OBJECT-TYPE
        SYNTAX INTEGER (-200..1000)
        UNITS  "0.1degC"
        ACCESS read-write
        STATUS mandatory
        DESCRIPTION
                "The high critical threshold of temperature of emd."
        ::= { pduDevMgmtEmdMasterEntry 12 }

pduDevMgmtEmdMasterTempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdMasterEntry 13 }

pduDevMgmtEmdMasterHumiLowWarn OBJECT-TYPE
        SYNTAX INTEGER (0..2120)
        UNITS  "0.1%"
        ACCESS read-write
        STATUS mandatory
        DESCRIPTION
                "The low warning threshold of humidity of emd."
        ::= { pduDevMgmtEmdMasterEntry 15 }

pduDevMgmtEmdMasterHumiLowCrit OBJECT-TYPE
        SYNTAX INTEGER (0..2120)
        UNITS  "0.1%"
        ACCESS read-write
        STATUS mandatory
        DESCRIPTION
                "The low critical threshold of humidity of emd."
        ::= { pduDevMgmtEmdMasterEntry 16 }

pduDevMgmtEmdMasterHumiHighWarn OBJECT-TYPE
        SYNTAX INTEGER (0..2120)
        UNITS  "0.1%"
        ACCESS read-write
        STATUS mandatory
        DESCRIPTION
                "The high warning threshold of humidity of emd."
        ::= { pduDevMgmtEmdMasterEntry 17 }

pduDevMgmtEmdMasterHumiHighCrit OBJECT-TYPE
        SYNTAX INTEGER (0..2120)
        UNITS  "0.1%"
        ACCESS read-write
        STATUS mandatory
        DESCRIPTION
                "The high critical threshold of humidity of emd."
        ::= { pduDevMgmtEmdMasterEntry 18 }

pduDevMgmtEmdMasterHumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdMasterEntry 19 }

pduDevMgmtEmdMasterAlarm1Setup OBJECT-TYPE
        SYNTAX INTEGER {
                disabled(1),
                no(2),
				nc(3)
                }
        ACCESS read-write
        STATUS mandatory
        DESCRIPTION
                "The alarm-1 setup of emd."
        ::= { pduDevMgmtEmdMasterEntry 21 }

pduDevMgmtEmdMasterAlarm2Setup OBJECT-TYPE
        SYNTAX INTEGER {
                disabled(1),
                no(2),
				nc(3)
                }
        ACCESS read-write
        STATUS mandatory
        DESCRIPTION
                "The alarm-2 setup of emd."
        ::= { pduDevMgmtEmdMasterEntry 22 }


-- ===========================================================================
--
-- pduDevMgmtEmdSlave01
--
--  Slave01 Emd Mgmtoitor Group
--
-- ===========================================================================
pduDevMgmtEmdSlave01Table OBJECT-TYPE
        SYNTAX SEQUENCE OF PduDevMgmtEmdSlave01Entry
        ACCESS not-accessible
        STATUS mandatory
        DESCRIPTION
                "Display a list of the emd information of master."
        ::= { pduDevMgmtEmdSlave01 1}

pduDevMgmtEmdSlave01Entry OBJECT-TYPE
        SYNTAX PduDevMgmtEmdSlave01Entry
        ACCESS not-accessible
        STATUS mandatory
        DESCRIPTION
                "Display a list of the emd information of master."
        INDEX  { pduDevMgmtEmdSlave01Index}
        ::= { pduDevMgmtEmdSlave01Table 1 }

PduDevMgmtEmdSlave01Entry ::=
        SEQUENCE {
                pduDevMgmtEmdSlave01Index
                        INTEGER,
                pduDevMgmtEmdSlave01Valid
                        INTEGER,
                pduDevMgmtEmdSlave01Type
                        INTEGER,
                pduDevMgmtEmdSlave01Name
                        DisplayString,
                pduDevMgmtEmdSlave01TempName
                        DisplayString,
                pduDevMgmtEmdSlave01HumiName
                        DisplayString,
                pduDevMgmtEmdSlave01Alarm1Name
                        DisplayString,
                pduDevMgmtEmdSlave01Alarm2Name
                        DisplayString,
                pduDevMgmtEmdSlave01TempLowWarn
                        INTEGER,
                pduDevMgmtEmdSlave01TempLowCrit
                        INTEGER,
                pduDevMgmtEmdSlave01TempHighWarn
                        INTEGER,
                pduDevMgmtEmdSlave01TempHighCrit
                        INTEGER,
                pduDevMgmtEmdSlave01TempCali
                        INTEGER,
                pduDevMgmtEmdSlave01HumiLowWarn
                        INTEGER,
                pduDevMgmtEmdSlave01HumiLowCrit
                        INTEGER,
                pduDevMgmtEmdSlave01HumiHighWarn
                        INTEGER,
                pduDevMgmtEmdSlave01HumiHighCrit
                        INTEGER,
                pduDevMgmtEmdSlave01HumiCali
                        INTEGER,
                pduDevMgmtEmdSlave01Alarm1Setup
                        INTEGER,
                pduDevMgmtEmdSlave01Alarm2Setup
                        INTEGER
        }

pduDevMgmtEmdSlave01Index OBJECT-TYPE
        SYNTAX INTEGER (0..7)
        ACCESS read-only
        STATUS mandatory
        DESCRIPTION
                "The index to a emd entry."
        ::= { pduDevMgmtEmdSlave01Entry 1 }

pduDevMgmtEmdSlave01Valid OBJECT-TYPE
        SYNTAX INTEGER {
                offline(1),
                online(2)
                }
        ACCESS read-only
        STATUS mandatory
        DESCRIPTION
                "The online status of emd."
        ::= { pduDevMgmtEmdSlave01Entry 2 }


pduDevMgmtEmdSlave01Type OBJECT-TYPE
        SYNTAX INTEGER
        ACCESS read-only
        STATUS mandatory
        DESCRIPTION
                "The type of emd."
        ::= { pduDevMgmtEmdSlave01Entry 3 }

pduDevMgmtEmdSlave01Name OBJECT-TYPE
        SYNTAX DisplayString (SIZE(0..31))
        ACCESS read-write
        STATUS mandatory
        DESCRIPTION
                "The name of emd."
        ::= { pduDevMgmtEmdSlave01Entry 4 }

pduDevMgmtEmdSlave01TempName OBJECT-TYPE
        SYNTAX DisplayString (SIZE(0..31))
        ACCESS read-write
        STATUS mandatory
        DESCRIPTION
                "The name of emd temperature."
        ::= { pduDevMgmtEmdSlave01Entry 5 }

pduDevMgmtEmdSlave01HumiName OBJECT-TYPE
        SYNTAX DisplayString (SIZE(0..31))
        ACCESS read-write
        STATUS mandatory
        DESCRIPTION
                "The name of emd humidity."
        ::= { pduDevMgmtEmdSlave01Entry 6 }

pduDevMgmtEmdSlave01Alarm1Name OBJECT-TYPE
        SYNTAX DisplayString (SIZE(0..31))
        ACCESS read-write
        STATUS mandatory
        DESCRIPTION
                "The name of emd alarm-1."
        ::= { pduDevMgmtEmdSlave01Entry 7 }

pduDevMgmtEmdSlave01Alarm2Name OBJECT-TYPE
        SYNTAX DisplayString (SIZE(0..31))
        ACCESS read-write
        STATUS mandatory
        DESCRIPTION
                "The name of emd alarm-2."
        ::= { pduDevMgmtEmdSlave01Entry 8 }

pduDevMgmtEmdSlave01TempLowWarn OBJECT-TYPE
        SYNTAX INTEGER (-200..1000)
        UNITS  "0.1degC"
        ACCESS read-write
        STATUS mandatory
        DESCRIPTION
                "The low warning threshold of temperature of emd."
        ::= { pduDevMgmtEmdSlave01Entry 9 }

pduDevMgmtEmdSlave01TempLowCrit OBJECT-TYPE
        SYNTAX INTEGER (-200..1000)
        UNITS  "0.1degC"
        ACCESS read-write
        STATUS mandatory
        DESCRIPTION
                "The low critical threshold of temperature of emd."
        ::= { pduDevMgmtEmdSlave01Entry 10 }

pduDevMgmtEmdSlave01TempHighWarn OBJECT-TYPE
        SYNTAX INTEGER (-200..1000)
        UNITS  "0.1degC"
        ACCESS read-write
        STATUS mandatory
        DESCRIPTION
                "The high warning threshold of temperature of emd."
        ::= { pduDevMgmtEmdSlave01Entry 11 }

pduDevMgmtEmdSlave01TempHighCrit OBJECT-TYPE
        SYNTAX INTEGER (-200..1000)
        UNITS  "0.1degC"
        ACCESS read-write
        STATUS mandatory
        DESCRIPTION
                "The high critical threshold of temperature of emd."
        ::= { pduDevMgmtEmdSlave01Entry 12 }

pduDevMgmtEmdSlave01TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave01Entry 13 }

pduDevMgmtEmdSlave01HumiLowWarn OBJECT-TYPE
        SYNTAX INTEGER (0..2120)
        UNITS  "0.1%"
        ACCESS read-write
        STATUS mandatory
        DESCRIPTION
                "The low warning threshold of humidity of emd."
        ::= { pduDevMgmtEmdSlave01Entry 15 }

pduDevMgmtEmdSlave01HumiLowCrit OBJECT-TYPE
        SYNTAX INTEGER (0..2120)
        UNITS  "0.1%"
        ACCESS read-write
        STATUS mandatory
        DESCRIPTION
                "The low critical threshold of humidity of emd."
        ::= { pduDevMgmtEmdSlave01Entry 16 }

pduDevMgmtEmdSlave01HumiHighWarn OBJECT-TYPE
        SYNTAX INTEGER (0..2120)
        UNITS  "0.1%"
        ACCESS read-write
        STATUS mandatory
        DESCRIPTION
                "The high warning threshold of humidity of emd."
        ::= { pduDevMgmtEmdSlave01Entry 17 }

pduDevMgmtEmdSlave01HumiHighCrit OBJECT-TYPE
        SYNTAX INTEGER (0..2120)
        UNITS  "0.1%"
        ACCESS read-write
        STATUS mandatory
        DESCRIPTION
                "The high critical threshold of humidity of emd."
        ::= { pduDevMgmtEmdSlave01Entry 18 }

pduDevMgmtEmdSlave01HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave01Entry 19 }

pduDevMgmtEmdSlave01Alarm1Setup OBJECT-TYPE
        SYNTAX INTEGER {
                disabled(1),
                no(2),
				nc(3)
                }
        ACCESS read-write
        STATUS mandatory
        DESCRIPTION
                "The alarm-1 setup of emd."
        ::= { pduDevMgmtEmdSlave01Entry 21 }

pduDevMgmtEmdSlave01Alarm2Setup OBJECT-TYPE
        SYNTAX INTEGER {
                disabled(1),
                no(2),
				nc(3)
                }
        ACCESS read-write
        STATUS mandatory
        DESCRIPTION
                "The alarm-2 setup of emd."
        ::= { pduDevMgmtEmdSlave01Entry 22 }


-- ===========================================================================
--
-- pduDevMgmtEmdSlave02
--
--  Slave02 Emd Mgmtoitor Group
--
-- ===========================================================================
pduDevMgmtEmdSlave02Table OBJECT-TYPE
        SYNTAX SEQUENCE OF PduDevMgmtEmdSlave02Entry
        ACCESS not-accessible
        STATUS mandatory
        DESCRIPTION
                "Display a list of the emd information of master."
        ::= { pduDevMgmtEmdSlave02 1}

pduDevMgmtEmdSlave02Entry OBJECT-TYPE
        SYNTAX PduDevMgmtEmdSlave02Entry
        ACCESS not-accessible
        STATUS mandatory
        DESCRIPTION
                "Display a list of the emd information of master."
        INDEX  { pduDevMgmtEmdSlave02Index}
        ::= { pduDevMgmtEmdSlave02Table 1 }

PduDevMgmtEmdSlave02Entry ::=
        SEQUENCE {
                pduDevMgmtEmdSlave02Index
                        INTEGER,
                pduDevMgmtEmdSlave02Valid
                        INTEGER,
                pduDevMgmtEmdSlave02Type
                        INTEGER,
                pduDevMgmtEmdSlave02Name
                        DisplayString,
                pduDevMgmtEmdSlave02TempName
                        DisplayString,
                pduDevMgmtEmdSlave02HumiName
                        DisplayString,
                pduDevMgmtEmdSlave02Alarm1Name
                        DisplayString,
                pduDevMgmtEmdSlave02Alarm2Name
                        DisplayString,
                pduDevMgmtEmdSlave02TempLowWarn
                        INTEGER,
                pduDevMgmtEmdSlave02TempLowCrit
                        INTEGER,
                pduDevMgmtEmdSlave02TempHighWarn
                        INTEGER,
                pduDevMgmtEmdSlave02TempHighCrit
                        INTEGER,
                pduDevMgmtEmdSlave02TempCali
                        INTEGER,
                pduDevMgmtEmdSlave02HumiLowWarn
                        INTEGER,
                pduDevMgmtEmdSlave02HumiLowCrit
                        INTEGER,
                pduDevMgmtEmdSlave02HumiHighWarn
                        INTEGER,
                pduDevMgmtEmdSlave02HumiHighCrit
                        INTEGER,
                pduDevMgmtEmdSlave02HumiCali
                        INTEGER,
                pduDevMgmtEmdSlave02Alarm1Setup
                        INTEGER,
                pduDevMgmtEmdSlave02Alarm2Setup
                        INTEGER
        }

pduDevMgmtEmdSlave02Index OBJECT-TYPE
        SYNTAX INTEGER (0..7)
        ACCESS read-only
        STATUS mandatory
        DESCRIPTION
                "The index to a emd entry."
        ::= { pduDevMgmtEmdSlave02Entry 1 }

pduDevMgmtEmdSlave02Valid OBJECT-TYPE
        SYNTAX INTEGER {
                offline(1),
                online(2)
                }
        ACCESS read-only
        STATUS mandatory
        DESCRIPTION
                "The online status of emd."
        ::= { pduDevMgmtEmdSlave02Entry 2 }


pduDevMgmtEmdSlave02Type OBJECT-TYPE
        SYNTAX INTEGER
        ACCESS read-only
        STATUS mandatory
        DESCRIPTION
                "The type of emd."
        ::= { pduDevMgmtEmdSlave02Entry 3 }

pduDevMgmtEmdSlave02Name OBJECT-TYPE
        SYNTAX DisplayString (SIZE(0..31))
        ACCESS read-write
        STATUS mandatory
        DESCRIPTION
                "The name of emd."
        ::= { pduDevMgmtEmdSlave02Entry 4 }

pduDevMgmtEmdSlave02TempName OBJECT-TYPE
        SYNTAX DisplayString (SIZE(0..31))
        ACCESS read-write
        STATUS mandatory
        DESCRIPTION
                "The name of emd temperature."
        ::= { pduDevMgmtEmdSlave02Entry 5 }

pduDevMgmtEmdSlave02HumiName OBJECT-TYPE
        SYNTAX DisplayString (SIZE(0..31))
        ACCESS read-write
        STATUS mandatory
        DESCRIPTION
                "The name of emd humidity."
        ::= { pduDevMgmtEmdSlave02Entry 6 }

pduDevMgmtEmdSlave02Alarm1Name OBJECT-TYPE
        SYNTAX DisplayString (SIZE(0..31))
        ACCESS read-write
        STATUS mandatory
        DESCRIPTION
                "The name of emd alarm-1."
        ::= { pduDevMgmtEmdSlave02Entry 7 }

pduDevMgmtEmdSlave02Alarm2Name OBJECT-TYPE
        SYNTAX DisplayString (SIZE(0..31))
        ACCESS read-write
        STATUS mandatory
        DESCRIPTION
                "The name of emd alarm-2."
        ::= { pduDevMgmtEmdSlave02Entry 8 }

pduDevMgmtEmdSlave02TempLowWarn OBJECT-TYPE
        SYNTAX INTEGER (-200..1000)
        UNITS  "0.1degC"
        ACCESS read-write
        STATUS mandatory
        DESCRIPTION
                "The low warning threshold of temperature of emd."
        ::= { pduDevMgmtEmdSlave02Entry 9 }

pduDevMgmtEmdSlave02TempLowCrit OBJECT-TYPE
        SYNTAX INTEGER (-200..1000)
        UNITS  "0.1degC"
        ACCESS read-write
        STATUS mandatory
        DESCRIPTION
                "The low critical threshold of temperature of emd."
        ::= { pduDevMgmtEmdSlave02Entry 10 }

pduDevMgmtEmdSlave02TempHighWarn OBJECT-TYPE
        SYNTAX INTEGER (-200..1000)
        UNITS  "0.1degC"
        ACCESS read-write
        STATUS mandatory
        DESCRIPTION
                "The high warning threshold of temperature of emd."
        ::= { pduDevMgmtEmdSlave02Entry 11 }

pduDevMgmtEmdSlave02TempHighCrit OBJECT-TYPE
        SYNTAX INTEGER (-200..1000)
        UNITS  "0.1degC"
        ACCESS read-write
        STATUS mandatory
        DESCRIPTION
                "The high critical threshold of temperature of emd."
        ::= { pduDevMgmtEmdSlave02Entry 12 }

pduDevMgmtEmdSlave02TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave02Entry 13 }

pduDevMgmtEmdSlave02HumiLowWarn OBJECT-TYPE
        SYNTAX INTEGER (0..2120)
        UNITS  "0.1%"
        ACCESS read-write
        STATUS mandatory
        DESCRIPTION
                "The low warning threshold of humidity of emd."
        ::= { pduDevMgmtEmdSlave02Entry 15 }

pduDevMgmtEmdSlave02HumiLowCrit OBJECT-TYPE
        SYNTAX INTEGER (0..2120)
        UNITS  "0.1%"
        ACCESS read-write
        STATUS mandatory
        DESCRIPTION
                "The low critical threshold of humidity of emd."
        ::= { pduDevMgmtEmdSlave02Entry 16 }

pduDevMgmtEmdSlave02HumiHighWarn OBJECT-TYPE
        SYNTAX INTEGER (0..2120)
        UNITS  "0.1%"
        ACCESS read-write
        STATUS mandatory
        DESCRIPTION
                "The high warning threshold of humidity of emd."
        ::= { pduDevMgmtEmdSlave02Entry 17 }

pduDevMgmtEmdSlave02HumiHighCrit OBJECT-TYPE
        SYNTAX INTEGER (0..2120)
        UNITS  "0.1%"
        ACCESS read-write
        STATUS mandatory
        DESCRIPTION
                "The high critical threshold of humidity of emd."
        ::= { pduDevMgmtEmdSlave02Entry 18 }

pduDevMgmtEmdSlave02HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave02Entry 19 }

pduDevMgmtEmdSlave02Alarm1Setup OBJECT-TYPE
        SYNTAX INTEGER {
                disabled(1),
                no(2),
				nc(3)
                }
        ACCESS read-write
        STATUS mandatory
        DESCRIPTION
                "The alarm-1 setup of emd."
        ::= { pduDevMgmtEmdSlave02Entry 21 }

pduDevMgmtEmdSlave02Alarm2Setup OBJECT-TYPE
        SYNTAX INTEGER {
                disabled(1),
                no(2),
				nc(3)
                }
        ACCESS read-write
        STATUS mandatory
        DESCRIPTION
                "The alarm-2 setup of emd."
        ::= { pduDevMgmtEmdSlave02Entry 22 }


-- ===========================================================================
--
-- pduDevMgmtEmdSlave03
--
--  Slave03 Emd Mgmtoitor Group
--
-- ===========================================================================
pduDevMgmtEmdSlave03Table OBJECT-TYPE
        SYNTAX SEQUENCE OF PduDevMgmtEmdSlave03Entry
        ACCESS not-accessible
        STATUS mandatory
        DESCRIPTION
                "Display a list of the emd information of master."
        ::= { pduDevMgmtEmdSlave03 1}

pduDevMgmtEmdSlave03Entry OBJECT-TYPE
        SYNTAX PduDevMgmtEmdSlave03Entry
        ACCESS not-accessible
        STATUS mandatory
        DESCRIPTION
                "Display a list of the emd information of master."
        INDEX  { pduDevMgmtEmdSlave03Index}
        ::= { pduDevMgmtEmdSlave03Table 1 }

PduDevMgmtEmdSlave03Entry ::=
        SEQUENCE {
                pduDevMgmtEmdSlave03Index
                        INTEGER,
                pduDevMgmtEmdSlave03Valid
                        INTEGER,
                pduDevMgmtEmdSlave03Type
                        INTEGER,
                pduDevMgmtEmdSlave03Name
                        DisplayString,
                pduDevMgmtEmdSlave03TempName
                        DisplayString,
                pduDevMgmtEmdSlave03HumiName
                        DisplayString,
                pduDevMgmtEmdSlave03Alarm1Name
                        DisplayString,
                pduDevMgmtEmdSlave03Alarm2Name
                        DisplayString,
                pduDevMgmtEmdSlave03TempLowWarn
                        INTEGER,
                pduDevMgmtEmdSlave03TempLowCrit
                        INTEGER,
                pduDevMgmtEmdSlave03TempHighWarn
                        INTEGER,
                pduDevMgmtEmdSlave03TempHighCrit
                        INTEGER,
                pduDevMgmtEmdSlave03TempCali
                        INTEGER,
                pduDevMgmtEmdSlave03HumiLowWarn
                        INTEGER,
                pduDevMgmtEmdSlave03HumiLowCrit
                        INTEGER,
                pduDevMgmtEmdSlave03HumiHighWarn
                        INTEGER,
                pduDevMgmtEmdSlave03HumiHighCrit
                        INTEGER,
                pduDevMgmtEmdSlave03HumiCali
                        INTEGER,
                pduDevMgmtEmdSlave03Alarm1Setup
                        INTEGER,
                pduDevMgmtEmdSlave03Alarm2Setup
                        INTEGER
        }

pduDevMgmtEmdSlave03Index OBJECT-TYPE
        SYNTAX INTEGER (0..7)
        ACCESS read-only
        STATUS mandatory
        DESCRIPTION
                "The index to a emd entry."
        ::= { pduDevMgmtEmdSlave03Entry 1 }

pduDevMgmtEmdSlave03Valid OBJECT-TYPE
        SYNTAX INTEGER {
                offline(1),
                online(2)
                }
        ACCESS read-only
        STATUS mandatory
        DESCRIPTION
                "The online status of emd."
        ::= { pduDevMgmtEmdSlave03Entry 2 }


pduDevMgmtEmdSlave03Type OBJECT-TYPE
        SYNTAX INTEGER
        ACCESS read-only
        STATUS mandatory
        DESCRIPTION
                "The type of emd."
        ::= { pduDevMgmtEmdSlave03Entry 3 }

pduDevMgmtEmdSlave03Name OBJECT-TYPE
        SYNTAX DisplayString (SIZE(0..31))
        ACCESS read-write
        STATUS mandatory
        DESCRIPTION
                "The name of emd."
        ::= { pduDevMgmtEmdSlave03Entry 4 }

pduDevMgmtEmdSlave03TempName OBJECT-TYPE
        SYNTAX DisplayString (SIZE(0..31))
        ACCESS read-write
        STATUS mandatory
        DESCRIPTION
                "The name of emd temperature."
        ::= { pduDevMgmtEmdSlave03Entry 5 }

pduDevMgmtEmdSlave03HumiName OBJECT-TYPE
        SYNTAX DisplayString (SIZE(0..31))
        ACCESS read-write
        STATUS mandatory
        DESCRIPTION
                "The name of emd humidity."
        ::= { pduDevMgmtEmdSlave03Entry 6 }

pduDevMgmtEmdSlave03Alarm1Name OBJECT-TYPE
        SYNTAX DisplayString (SIZE(0..31))
        ACCESS read-write
        STATUS mandatory
        DESCRIPTION
                "The name of emd alarm-1."
        ::= { pduDevMgmtEmdSlave03Entry 7 }

pduDevMgmtEmdSlave03Alarm2Name OBJECT-TYPE
        SYNTAX DisplayString (SIZE(0..31))
        ACCESS read-write
        STATUS mandatory
        DESCRIPTION
                "The name of emd alarm-2."
        ::= { pduDevMgmtEmdSlave03Entry 8 }

pduDevMgmtEmdSlave03TempLowWarn OBJECT-TYPE
        SYNTAX INTEGER (-200..1000)
        UNITS  "0.1degC"
        ACCESS read-write
        STATUS mandatory
        DESCRIPTION
                "The low warning threshold of temperature of emd."
        ::= { pduDevMgmtEmdSlave03Entry 9 }

pduDevMgmtEmdSlave03TempLowCrit OBJECT-TYPE
        SYNTAX INTEGER (-200..1000)
        UNITS  "0.1degC"
        ACCESS read-write
        STATUS mandatory
        DESCRIPTION
                "The low critical threshold of temperature of emd."
        ::= { pduDevMgmtEmdSlave03Entry 10 }

pduDevMgmtEmdSlave03TempHighWarn OBJECT-TYPE
        SYNTAX INTEGER (-200..1000)
        UNITS  "0.1degC"
        ACCESS read-write
        STATUS mandatory
        DESCRIPTION
                "The high warning threshold of temperature of emd."
        ::= { pduDevMgmtEmdSlave03Entry 11 }

pduDevMgmtEmdSlave03TempHighCrit OBJECT-TYPE
        SYNTAX INTEGER (-200..1000)
        UNITS  "0.1degC"
        ACCESS read-write
        STATUS mandatory
        DESCRIPTION
                "The high critical threshold of temperature of emd."
        ::= { pduDevMgmtEmdSlave03Entry 12 }

pduDevMgmtEmdSlave03TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave03Entry 13 }

pduDevMgmtEmdSlave03HumiLowWarn OBJECT-TYPE
        SYNTAX INTEGER (0..2120)
        UNITS  "0.1%"
        ACCESS read-write
        STATUS mandatory
        DESCRIPTION
                "The low warning threshold of humidity of emd."
        ::= { pduDevMgmtEmdSlave03Entry 15 }

pduDevMgmtEmdSlave03HumiLowCrit OBJECT-TYPE
        SYNTAX INTEGER (0..2120)
        UNITS  "0.1%"
        ACCESS read-write
        STATUS mandatory
        DESCRIPTION
                "The low critical threshold of humidity of emd."
        ::= { pduDevMgmtEmdSlave03Entry 16 }

pduDevMgmtEmdSlave03HumiHighWarn OBJECT-TYPE
        SYNTAX INTEGER (0..2120)
        UNITS  "0.1%"
        ACCESS read-write
        STATUS mandatory
        DESCRIPTION
                "The high warning threshold of humidity of emd."
        ::= { pduDevMgmtEmdSlave03Entry 17 }

pduDevMgmtEmdSlave03HumiHighCrit OBJECT-TYPE
        SYNTAX INTEGER (0..2120)
        UNITS  "0.1%"
        ACCESS read-write
        STATUS mandatory
        DESCRIPTION
                "The high critical threshold of humidity of emd."
        ::= { pduDevMgmtEmdSlave03Entry 18 }

pduDevMgmtEmdSlave03HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave03Entry 19 }

pduDevMgmtEmdSlave03Alarm1Setup OBJECT-TYPE
        SYNTAX INTEGER {
                disabled(1),
                no(2),
				nc(3)
                }
        ACCESS read-write
        STATUS mandatory
        DESCRIPTION
                "The alarm-1 setup of emd."
        ::= { pduDevMgmtEmdSlave03Entry 21 }

pduDevMgmtEmdSlave03Alarm2Setup OBJECT-TYPE
        SYNTAX INTEGER {
                disabled(1),
                no(2),
				nc(3)
                }
        ACCESS read-write
        STATUS mandatory
        DESCRIPTION
                "The alarm-2 setup of emd."
        ::= { pduDevMgmtEmdSlave03Entry 22 }


-- ===========================================================================
--
-- pduDevMgmtEmdSlave04
--
--  Slave04 Emd Mgmtoitor Group
--
-- ===========================================================================
pduDevMgmtEmdSlave04Table OBJECT-TYPE
        SYNTAX SEQUENCE OF PduDevMgmtEmdSlave04Entry
        ACCESS not-accessible
        STATUS mandatory
        DESCRIPTION
                "Display a list of the emd information of master."
        ::= { pduDevMgmtEmdSlave04 1}

pduDevMgmtEmdSlave04Entry OBJECT-TYPE
        SYNTAX PduDevMgmtEmdSlave04Entry
        ACCESS not-accessible
        STATUS mandatory
        DESCRIPTION
                "Display a list of the emd information of master."
        INDEX  { pduDevMgmtEmdSlave04Index}
        ::= { pduDevMgmtEmdSlave04Table 1 }

PduDevMgmtEmdSlave04Entry ::=
        SEQUENCE {
                pduDevMgmtEmdSlave04Index
                        INTEGER,
                pduDevMgmtEmdSlave04Valid
                        INTEGER,
                pduDevMgmtEmdSlave04Type
                        INTEGER,
                pduDevMgmtEmdSlave04Name
                        DisplayString,
                pduDevMgmtEmdSlave04TempName
                        DisplayString,
                pduDevMgmtEmdSlave04HumiName
                        DisplayString,
                pduDevMgmtEmdSlave04Alarm1Name
                        DisplayString,
                pduDevMgmtEmdSlave04Alarm2Name
                        DisplayString,
                pduDevMgmtEmdSlave04TempLowWarn
                        INTEGER,
                pduDevMgmtEmdSlave04TempLowCrit
                        INTEGER,
                pduDevMgmtEmdSlave04TempHighWarn
                        INTEGER,
                pduDevMgmtEmdSlave04TempHighCrit
                        INTEGER,
                pduDevMgmtEmdSlave04TempCali
                        INTEGER,
                pduDevMgmtEmdSlave04HumiLowWarn
                        INTEGER,
                pduDevMgmtEmdSlave04HumiLowCrit
                        INTEGER,
                pduDevMgmtEmdSlave04HumiHighWarn
                        INTEGER,
                pduDevMgmtEmdSlave04HumiHighCrit
                        INTEGER,
                pduDevMgmtEmdSlave04HumiCali
                        INTEGER,
                pduDevMgmtEmdSlave04Alarm1Setup
                        INTEGER,
                pduDevMgmtEmdSlave04Alarm2Setup
                        INTEGER
        }

pduDevMgmtEmdSlave04Index OBJECT-TYPE
        SYNTAX INTEGER (0..7)
        ACCESS read-only
        STATUS mandatory
        DESCRIPTION
                "The index to a emd entry."
        ::= { pduDevMgmtEmdSlave04Entry 1 }

pduDevMgmtEmdSlave04Valid OBJECT-TYPE
        SYNTAX INTEGER {
                offline(1),
                online(2)
                }
        ACCESS read-only
        STATUS mandatory
        DESCRIPTION
                "The online status of emd."
        ::= { pduDevMgmtEmdSlave04Entry 2 }


pduDevMgmtEmdSlave04Type OBJECT-TYPE
        SYNTAX INTEGER
        ACCESS read-only
        STATUS mandatory
        DESCRIPTION
                "The type of emd."
        ::= { pduDevMgmtEmdSlave04Entry 3 }

pduDevMgmtEmdSlave04Name OBJECT-TYPE
        SYNTAX DisplayString (SIZE(0..31))
        ACCESS read-write
        STATUS mandatory
        DESCRIPTION
                "The name of emd."
        ::= { pduDevMgmtEmdSlave04Entry 4 }

pduDevMgmtEmdSlave04TempName OBJECT-TYPE
        SYNTAX DisplayString (SIZE(0..31))
        ACCESS read-write
        STATUS mandatory
        DESCRIPTION
                "The name of emd temperature."
        ::= { pduDevMgmtEmdSlave04Entry 5 }

pduDevMgmtEmdSlave04HumiName OBJECT-TYPE
        SYNTAX DisplayString (SIZE(0..31))
        ACCESS read-write
        STATUS mandatory
        DESCRIPTION
                "The name of emd humidity."
        ::= { pduDevMgmtEmdSlave04Entry 6 }

pduDevMgmtEmdSlave04Alarm1Name OBJECT-TYPE
        SYNTAX DisplayString (SIZE(0..31))
        ACCESS read-write
        STATUS mandatory
        DESCRIPTION
                "The name of emd alarm-1."
        ::= { pduDevMgmtEmdSlave04Entry 7 }

pduDevMgmtEmdSlave04Alarm2Name OBJECT-TYPE
        SYNTAX DisplayString (SIZE(0..31))
        ACCESS read-write
        STATUS mandatory
        DESCRIPTION
                "The name of emd alarm-2."
        ::= { pduDevMgmtEmdSlave04Entry 8 }

pduDevMgmtEmdSlave04TempLowWarn OBJECT-TYPE
        SYNTAX INTEGER (-200..1000)
        UNITS  "0.1degC"
        ACCESS read-write
        STATUS mandatory
        DESCRIPTION
                "The low warning threshold of temperature of emd."
        ::= { pduDevMgmtEmdSlave04Entry 9 }

pduDevMgmtEmdSlave04TempLowCrit OBJECT-TYPE
        SYNTAX INTEGER (-200..1000)
        UNITS  "0.1degC"
        ACCESS read-write
        STATUS mandatory
        DESCRIPTION
                "The low critical threshold of temperature of emd."
        ::= { pduDevMgmtEmdSlave04Entry 10 }

pduDevMgmtEmdSlave04TempHighWarn OBJECT-TYPE
        SYNTAX INTEGER (-200..1000)
        UNITS  "0.1degC"
        ACCESS read-write
        STATUS mandatory
        DESCRIPTION
                "The high warning threshold of temperature of emd."
        ::= { pduDevMgmtEmdSlave04Entry 11 }

pduDevMgmtEmdSlave04TempHighCrit OBJECT-TYPE
        SYNTAX INTEGER (-200..1000)
        UNITS  "0.1degC"
        ACCESS read-write
        STATUS mandatory
        DESCRIPTION
                "The high critical threshold of temperature of emd."
        ::= { pduDevMgmtEmdSlave04Entry 12 }

pduDevMgmtEmdSlave04TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave04Entry 13 }

pduDevMgmtEmdSlave04HumiLowWarn OBJECT-TYPE
        SYNTAX INTEGER (0..2120)
        UNITS  "0.1%"
        ACCESS read-write
        STATUS mandatory
        DESCRIPTION
                "The low warning threshold of humidity of emd."
        ::= { pduDevMgmtEmdSlave04Entry 15 }

pduDevMgmtEmdSlave04HumiLowCrit OBJECT-TYPE
        SYNTAX INTEGER (0..2120)
        UNITS  "0.1%"
        ACCESS read-write
        STATUS mandatory
        DESCRIPTION
                "The low critical threshold of humidity of emd."
        ::= { pduDevMgmtEmdSlave04Entry 16 }

pduDevMgmtEmdSlave04HumiHighWarn OBJECT-TYPE
        SYNTAX INTEGER (0..2120)
        UNITS  "0.1%"
        ACCESS read-write
        STATUS mandatory
        DESCRIPTION
                "The high warning threshold of humidity of emd."
        ::= { pduDevMgmtEmdSlave04Entry 17 }

pduDevMgmtEmdSlave04HumiHighCrit OBJECT-TYPE
        SYNTAX INTEGER (0..2120)
        UNITS  "0.1%"
        ACCESS read-write
        STATUS mandatory
        DESCRIPTION
                "The high critical threshold of humidity of emd."
        ::= { pduDevMgmtEmdSlave04Entry 18 }

pduDevMgmtEmdSlave04HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave04Entry 19 }

pduDevMgmtEmdSlave04Alarm1Setup OBJECT-TYPE
        SYNTAX INTEGER {
                disabled(1),
                no(2),
				nc(3)
                }
        ACCESS read-write
        STATUS mandatory
        DESCRIPTION
                "The alarm-1 setup of emd."
        ::= { pduDevMgmtEmdSlave04Entry 21 }

pduDevMgmtEmdSlave04Alarm2Setup OBJECT-TYPE
        SYNTAX INTEGER {
                disabled(1),
                no(2),
				nc(3)
                }
        ACCESS read-write
        STATUS mandatory
        DESCRIPTION
                "The alarm-2 setup of emd."
        ::= { pduDevMgmtEmdSlave04Entry 22 }


-- ===========================================================================
--
-- pduDevMgmtEmdSlave05
--
--  Slave05 Emd Mgmtoitor Group
--
-- ===========================================================================
pduDevMgmtEmdSlave05Table OBJECT-TYPE
        SYNTAX SEQUENCE OF PduDevMgmtEmdSlave05Entry
        ACCESS not-accessible
        STATUS mandatory
        DESCRIPTION
                "Display a list of the emd information of master."
        ::= { pduDevMgmtEmdSlave05 1}

pduDevMgmtEmdSlave05Entry OBJECT-TYPE
        SYNTAX PduDevMgmtEmdSlave05Entry
        ACCESS not-accessible
        STATUS mandatory
        DESCRIPTION
                "Display a list of the emd information of master."
        INDEX  { pduDevMgmtEmdSlave05Index}
        ::= { pduDevMgmtEmdSlave05Table 1 }

PduDevMgmtEmdSlave05Entry ::=
        SEQUENCE {
                pduDevMgmtEmdSlave05Index
                        INTEGER,
                pduDevMgmtEmdSlave05Valid
                        INTEGER,
                pduDevMgmtEmdSlave05Type
                        INTEGER,
                pduDevMgmtEmdSlave05Name
                        DisplayString,
                pduDevMgmtEmdSlave05TempName
                        DisplayString,
                pduDevMgmtEmdSlave05HumiName
                        DisplayString,
                pduDevMgmtEmdSlave05Alarm1Name
                        DisplayString,
                pduDevMgmtEmdSlave05Alarm2Name
                        DisplayString,
                pduDevMgmtEmdSlave05TempLowWarn
                        INTEGER,
                pduDevMgmtEmdSlave05TempLowCrit
                        INTEGER,
                pduDevMgmtEmdSlave05TempHighWarn
                        INTEGER,
                pduDevMgmtEmdSlave05TempHighCrit
                        INTEGER,
                pduDevMgmtEmdSlave05TempCali
                        INTEGER,
                pduDevMgmtEmdSlave05HumiLowWarn
                        INTEGER,
                pduDevMgmtEmdSlave05HumiLowCrit
                        INTEGER,
                pduDevMgmtEmdSlave05HumiHighWarn
                        INTEGER,
                pduDevMgmtEmdSlave05HumiHighCrit
                        INTEGER,
                pduDevMgmtEmdSlave05HumiCali
                        INTEGER,
                pduDevMgmtEmdSlave05Alarm1Setup
                        INTEGER,
                pduDevMgmtEmdSlave05Alarm2Setup
                        INTEGER
        }

pduDevMgmtEmdSlave05Index OBJECT-TYPE
        SYNTAX INTEGER (0..7)
        ACCESS read-only
        STATUS mandatory
        DESCRIPTION
                "The index to a emd entry."
        ::= { pduDevMgmtEmdSlave05Entry 1 }

pduDevMgmtEmdSlave05Valid OBJECT-TYPE
        SYNTAX INTEGER {
                offline(1),
                online(2)
                }
        ACCESS read-only
        STATUS mandatory
        DESCRIPTION
                "The online status of emd."
        ::= { pduDevMgmtEmdSlave05Entry 2 }


pduDevMgmtEmdSlave05Type OBJECT-TYPE
        SYNTAX INTEGER
        ACCESS read-only
        STATUS mandatory
        DESCRIPTION
                "The type of emd."
        ::= { pduDevMgmtEmdSlave05Entry 3 }

pduDevMgmtEmdSlave05Name OBJECT-TYPE
        SYNTAX DisplayString (SIZE(0..31))
        ACCESS read-write
        STATUS mandatory
        DESCRIPTION
                "The name of emd."
        ::= { pduDevMgmtEmdSlave05Entry 4 }

pduDevMgmtEmdSlave05TempName OBJECT-TYPE
        SYNTAX DisplayString (SIZE(0..31))
        ACCESS read-write
        STATUS mandatory
        DESCRIPTION
                "The name of emd temperature."
        ::= { pduDevMgmtEmdSlave05Entry 5 }

pduDevMgmtEmdSlave05HumiName OBJECT-TYPE
        SYNTAX DisplayString (SIZE(0..31))
        ACCESS read-write
        STATUS mandatory
        DESCRIPTION
                "The name of emd humidity."
        ::= { pduDevMgmtEmdSlave05Entry 6 }

pduDevMgmtEmdSlave05Alarm1Name OBJECT-TYPE
        SYNTAX DisplayString (SIZE(0..31))
        ACCESS read-write
        STATUS mandatory
        DESCRIPTION
                "The name of emd alarm-1."
        ::= { pduDevMgmtEmdSlave05Entry 7 }

pduDevMgmtEmdSlave05Alarm2Name OBJECT-TYPE
        SYNTAX DisplayString (SIZE(0..31))
        ACCESS read-write
        STATUS mandatory
        DESCRIPTION
                "The name of emd alarm-2."
        ::= { pduDevMgmtEmdSlave05Entry 8 }

pduDevMgmtEmdSlave05TempLowWarn OBJECT-TYPE
        SYNTAX INTEGER (-200..1000)
        UNITS  "0.1degC"
        ACCESS read-write
        STATUS mandatory
        DESCRIPTION
                "The low warning threshold of temperature of emd."
        ::= { pduDevMgmtEmdSlave05Entry 9 }

pduDevMgmtEmdSlave05TempLowCrit OBJECT-TYPE
        SYNTAX INTEGER (-200..1000)
        UNITS  "0.1degC"
        ACCESS read-write
        STATUS mandatory
        DESCRIPTION
                "The low critical threshold of temperature of emd."
        ::= { pduDevMgmtEmdSlave05Entry 10 }

pduDevMgmtEmdSlave05TempHighWarn OBJECT-TYPE
        SYNTAX INTEGER (-200..1000)
        UNITS  "0.1degC"
        ACCESS read-write
        STATUS mandatory
        DESCRIPTION
                "The high warning threshold of temperature of emd."
        ::= { pduDevMgmtEmdSlave05Entry 11 }

pduDevMgmtEmdSlave05TempHighCrit OBJECT-TYPE
        SYNTAX INTEGER (-200..1000)
        UNITS  "0.1degC"
        ACCESS read-write
        STATUS mandatory
        DESCRIPTION
                "The high critical threshold of temperature of emd."
        ::= { pduDevMgmtEmdSlave05Entry 12 }

pduDevMgmtEmdSlave05TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave05Entry 13 }

pduDevMgmtEmdSlave05HumiLowWarn OBJECT-TYPE
        SYNTAX INTEGER (0..2120)
        UNITS  "0.1%"
        ACCESS read-write
        STATUS mandatory
        DESCRIPTION
                "The low warning threshold of humidity of emd."
        ::= { pduDevMgmtEmdSlave05Entry 15 }

pduDevMgmtEmdSlave05HumiLowCrit OBJECT-TYPE
        SYNTAX INTEGER (0..2120)
        UNITS  "0.1%"
        ACCESS read-write
        STATUS mandatory
        DESCRIPTION
                "The low critical threshold of humidity of emd."
        ::= { pduDevMgmtEmdSlave05Entry 16 }

pduDevMgmtEmdSlave05HumiHighWarn OBJECT-TYPE
        SYNTAX INTEGER (0..2120)
        UNITS  "0.1%"
        ACCESS read-write
        STATUS mandatory
        DESCRIPTION
                "The high warning threshold of humidity of emd."
        ::= { pduDevMgmtEmdSlave05Entry 17 }

pduDevMgmtEmdSlave05HumiHighCrit OBJECT-TYPE
        SYNTAX INTEGER (0..2120)
        UNITS  "0.1%"
        ACCESS read-write
        STATUS mandatory
        DESCRIPTION
                "The high critical threshold of humidity of emd."
        ::= { pduDevMgmtEmdSlave05Entry 18 }

pduDevMgmtEmdSlave05HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave05Entry 19 }

pduDevMgmtEmdSlave05Alarm1Setup OBJECT-TYPE
        SYNTAX INTEGER {
                disabled(1),
                no(2),
				nc(3)
                }
        ACCESS read-write
        STATUS mandatory
        DESCRIPTION
                "The alarm-1 setup of emd."
        ::= { pduDevMgmtEmdSlave05Entry 21 }

pduDevMgmtEmdSlave05Alarm2Setup OBJECT-TYPE
        SYNTAX INTEGER {
                disabled(1),
                no(2),
				nc(3)
                }
        ACCESS read-write
        STATUS mandatory
        DESCRIPTION
                "The alarm-2 setup of emd."
        ::= { pduDevMgmtEmdSlave05Entry 22 }


-- ===========================================================================
--
-- pduDevMgmtEmdSlave06
--
--  Slave06 Emd Mgmtoitor Group
--
-- ===========================================================================
pduDevMgmtEmdSlave06Table OBJECT-TYPE
        SYNTAX SEQUENCE OF PduDevMgmtEmdSlave06Entry
        ACCESS not-accessible
        STATUS mandatory
        DESCRIPTION
                "Display a list of the emd information of master."
        ::= { pduDevMgmtEmdSlave06 1}

pduDevMgmtEmdSlave06Entry OBJECT-TYPE
        SYNTAX PduDevMgmtEmdSlave06Entry
        ACCESS not-accessible
        STATUS mandatory
        DESCRIPTION
                "Display a list of the emd information of master."
        INDEX  { pduDevMgmtEmdSlave06Index}
        ::= { pduDevMgmtEmdSlave06Table 1 }

PduDevMgmtEmdSlave06Entry ::=
        SEQUENCE {
                pduDevMgmtEmdSlave06Index
                        INTEGER,
                pduDevMgmtEmdSlave06Valid
                        INTEGER,
                pduDevMgmtEmdSlave06Type
                        INTEGER,
                pduDevMgmtEmdSlave06Name
                        DisplayString,
                pduDevMgmtEmdSlave06TempName
                        DisplayString,
                pduDevMgmtEmdSlave06HumiName
                        DisplayString,
                pduDevMgmtEmdSlave06Alarm1Name
                        DisplayString,
                pduDevMgmtEmdSlave06Alarm2Name
                        DisplayString,
                pduDevMgmtEmdSlave06TempLowWarn
                        INTEGER,
                pduDevMgmtEmdSlave06TempLowCrit
                        INTEGER,
                pduDevMgmtEmdSlave06TempHighWarn
                        INTEGER,
                pduDevMgmtEmdSlave06TempHighCrit
                        INTEGER,
                pduDevMgmtEmdSlave06TempCali
                        INTEGER,
                pduDevMgmtEmdSlave06HumiLowWarn
                        INTEGER,
                pduDevMgmtEmdSlave06HumiLowCrit
                        INTEGER,
                pduDevMgmtEmdSlave06HumiHighWarn
                        INTEGER,
                pduDevMgmtEmdSlave06HumiHighCrit
                        INTEGER,
                pduDevMgmtEmdSlave06HumiCali
                        INTEGER,
                pduDevMgmtEmdSlave06Alarm1Setup
                        INTEGER,
                pduDevMgmtEmdSlave06Alarm2Setup
                        INTEGER
        }

pduDevMgmtEmdSlave06Index OBJECT-TYPE
        SYNTAX INTEGER (0..7)
        ACCESS read-only
        STATUS mandatory
        DESCRIPTION
                "The index to a emd entry."
        ::= { pduDevMgmtEmdSlave06Entry 1 }

pduDevMgmtEmdSlave06Valid OBJECT-TYPE
        SYNTAX INTEGER {
                offline(1),
                online(2)
                }
        ACCESS read-only
        STATUS mandatory
        DESCRIPTION
                "The online status of emd."
        ::= { pduDevMgmtEmdSlave06Entry 2 }


pduDevMgmtEmdSlave06Type OBJECT-TYPE
        SYNTAX INTEGER
        ACCESS read-only
        STATUS mandatory
        DESCRIPTION
                "The type of emd."
        ::= { pduDevMgmtEmdSlave06Entry 3 }

pduDevMgmtEmdSlave06Name OBJECT-TYPE
        SYNTAX DisplayString (SIZE(0..31))
        ACCESS read-write
        STATUS mandatory
        DESCRIPTION
                "The name of emd."
        ::= { pduDevMgmtEmdSlave06Entry 4 }

pduDevMgmtEmdSlave06TempName OBJECT-TYPE
        SYNTAX DisplayString (SIZE(0..31))
        ACCESS read-write
        STATUS mandatory
        DESCRIPTION
                "The name of emd temperature."
        ::= { pduDevMgmtEmdSlave06Entry 5 }

pduDevMgmtEmdSlave06HumiName OBJECT-TYPE
        SYNTAX DisplayString (SIZE(0..31))
        ACCESS read-write
        STATUS mandatory
        DESCRIPTION
                "The name of emd humidity."
        ::= { pduDevMgmtEmdSlave06Entry 6 }

pduDevMgmtEmdSlave06Alarm1Name OBJECT-TYPE
        SYNTAX DisplayString (SIZE(0..31))
        ACCESS read-write
        STATUS mandatory
        DESCRIPTION
                "The name of emd alarm-1."
        ::= { pduDevMgmtEmdSlave06Entry 7 }

pduDevMgmtEmdSlave06Alarm2Name OBJECT-TYPE
        SYNTAX DisplayString (SIZE(0..31))
        ACCESS read-write
        STATUS mandatory
        DESCRIPTION
                "The name of emd alarm-2."
        ::= { pduDevMgmtEmdSlave06Entry 8 }

pduDevMgmtEmdSlave06TempLowWarn OBJECT-TYPE
        SYNTAX INTEGER (-200..1000)
        UNITS  "0.1degC"
        ACCESS read-write
        STATUS mandatory
        DESCRIPTION
                "The low warning threshold of temperature of emd."
        ::= { pduDevMgmtEmdSlave06Entry 9 }

pduDevMgmtEmdSlave06TempLowCrit OBJECT-TYPE
        SYNTAX INTEGER (-200..1000)
        UNITS  "0.1degC"
        ACCESS read-write
        STATUS mandatory
        DESCRIPTION
                "The low critical threshold of temperature of emd."
        ::= { pduDevMgmtEmdSlave06Entry 10 }

pduDevMgmtEmdSlave06TempHighWarn OBJECT-TYPE
        SYNTAX INTEGER (-200..1000)
        UNITS  "0.1degC"
        ACCESS read-write
        STATUS mandatory
        DESCRIPTION
                "The high warning threshold of temperature of emd."
        ::= { pduDevMgmtEmdSlave06Entry 11 }

pduDevMgmtEmdSlave06TempHighCrit OBJECT-TYPE
        SYNTAX INTEGER (-200..1000)
        UNITS  "0.1degC"
        ACCESS read-write
        STATUS mandatory
        DESCRIPTION
                "The high critical threshold of temperature of emd."
        ::= { pduDevMgmtEmdSlave06Entry 12 }

pduDevMgmtEmdSlave06TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave06Entry 13 }

pduDevMgmtEmdSlave06HumiLowWarn OBJECT-TYPE
        SYNTAX INTEGER (0..2120)
        UNITS  "0.1%"
        ACCESS read-write
        STATUS mandatory
        DESCRIPTION
                "The low warning threshold of humidity of emd."
        ::= { pduDevMgmtEmdSlave06Entry 15 }

pduDevMgmtEmdSlave06HumiLowCrit OBJECT-TYPE
        SYNTAX INTEGER (0..2120)
        UNITS  "0.1%"
        ACCESS read-write
        STATUS mandatory
        DESCRIPTION
                "The low critical threshold of humidity of emd."
        ::= { pduDevMgmtEmdSlave06Entry 16 }

pduDevMgmtEmdSlave06HumiHighWarn OBJECT-TYPE
        SYNTAX INTEGER (0..2120)
        UNITS  "0.1%"
        ACCESS read-write
        STATUS mandatory
        DESCRIPTION
                "The high warning threshold of humidity of emd."
        ::= { pduDevMgmtEmdSlave06Entry 17 }

pduDevMgmtEmdSlave06HumiHighCrit OBJECT-TYPE
        SYNTAX INTEGER (0..2120)
        UNITS  "0.1%"
        ACCESS read-write
        STATUS mandatory
        DESCRIPTION
                "The high critical threshold of humidity of emd."
        ::= { pduDevMgmtEmdSlave06Entry 18 }

pduDevMgmtEmdSlave06HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave06Entry 19 }

pduDevMgmtEmdSlave06Alarm1Setup OBJECT-TYPE
        SYNTAX INTEGER {
                disabled(1),
                no(2),
				nc(3)
                }
        ACCESS read-write
        STATUS mandatory
        DESCRIPTION
                "The alarm-1 setup of emd."
        ::= { pduDevMgmtEmdSlave06Entry 21 }

pduDevMgmtEmdSlave06Alarm2Setup OBJECT-TYPE
        SYNTAX INTEGER {
                disabled(1),
                no(2),
				nc(3)
                }
        ACCESS read-write
        STATUS mandatory
        DESCRIPTION
                "The alarm-2 setup of emd."
        ::= { pduDevMgmtEmdSlave06Entry 22 }


-- ===========================================================================
--
-- pduDevMgmtEmdSlave07
--
--  Slave07 Emd Mgmtoitor Group
--
-- ===========================================================================
pduDevMgmtEmdSlave07Table OBJECT-TYPE
        SYNTAX SEQUENCE OF PduDevMgmtEmdSlave07Entry
        ACCESS not-accessible
        STATUS mandatory
        DESCRIPTION
                "Display a list of the emd information of master."
        ::= { pduDevMgmtEmdSlave07 1}

pduDevMgmtEmdSlave07Entry OBJECT-TYPE
        SYNTAX PduDevMgmtEmdSlave07Entry
        ACCESS not-accessible
        STATUS mandatory
        DESCRIPTION
                "Display a list of the emd information of master."
        INDEX  { pduDevMgmtEmdSlave07Index}
        ::= { pduDevMgmtEmdSlave07Table 1 }

PduDevMgmtEmdSlave07Entry ::=
        SEQUENCE {
                pduDevMgmtEmdSlave07Index
                        INTEGER,
                pduDevMgmtEmdSlave07Valid
                        INTEGER,
                pduDevMgmtEmdSlave07Type
                        INTEGER,
                pduDevMgmtEmdSlave07Name
                        DisplayString,
                pduDevMgmtEmdSlave07TempName
                        DisplayString,
                pduDevMgmtEmdSlave07HumiName
                        DisplayString,
                pduDevMgmtEmdSlave07Alarm1Name
                        DisplayString,
                pduDevMgmtEmdSlave07Alarm2Name
                        DisplayString,
                pduDevMgmtEmdSlave07TempLowWarn
                        INTEGER,
                pduDevMgmtEmdSlave07TempLowCrit
                        INTEGER,
                pduDevMgmtEmdSlave07TempHighWarn
                        INTEGER,
                pduDevMgmtEmdSlave07TempHighCrit
                        INTEGER,
                pduDevMgmtEmdSlave07TempCali
                        INTEGER,
                pduDevMgmtEmdSlave07HumiLowWarn
                        INTEGER,
                pduDevMgmtEmdSlave07HumiLowCrit
                        INTEGER,
                pduDevMgmtEmdSlave07HumiHighWarn
                        INTEGER,
                pduDevMgmtEmdSlave07HumiHighCrit
                        INTEGER,
                pduDevMgmtEmdSlave07HumiCali
                        INTEGER,
                pduDevMgmtEmdSlave07Alarm1Setup
                        INTEGER,
                pduDevMgmtEmdSlave07Alarm2Setup
                        INTEGER
        }

pduDevMgmtEmdSlave07Index OBJECT-TYPE
        SYNTAX INTEGER (0..7)
        ACCESS read-only
        STATUS mandatory
        DESCRIPTION
                "The index to a emd entry."
        ::= { pduDevMgmtEmdSlave07Entry 1 }

pduDevMgmtEmdSlave07Valid OBJECT-TYPE
        SYNTAX INTEGER {
                offline(1),
                online(2)
                }
        ACCESS read-only
        STATUS mandatory
        DESCRIPTION
                "The online status of emd."
        ::= { pduDevMgmtEmdSlave07Entry 2 }


pduDevMgmtEmdSlave07Type OBJECT-TYPE
        SYNTAX INTEGER
        ACCESS read-only
        STATUS mandatory
        DESCRIPTION
                "The type of emd."
        ::= { pduDevMgmtEmdSlave07Entry 3 }

pduDevMgmtEmdSlave07Name OBJECT-TYPE
        SYNTAX DisplayString (SIZE(0..31))
        ACCESS read-write
        STATUS mandatory
        DESCRIPTION
                "The name of emd."
        ::= { pduDevMgmtEmdSlave07Entry 4 }

pduDevMgmtEmdSlave07TempName OBJECT-TYPE
        SYNTAX DisplayString (SIZE(0..31))
        ACCESS read-write
        STATUS mandatory
        DESCRIPTION
                "The name of emd temperature."
        ::= { pduDevMgmtEmdSlave07Entry 5 }

pduDevMgmtEmdSlave07HumiName OBJECT-TYPE
        SYNTAX DisplayString (SIZE(0..31))
        ACCESS read-write
        STATUS mandatory
        DESCRIPTION
                "The name of emd humidity."
        ::= { pduDevMgmtEmdSlave07Entry 6 }

pduDevMgmtEmdSlave07Alarm1Name OBJECT-TYPE
        SYNTAX DisplayString (SIZE(0..31))
        ACCESS read-write
        STATUS mandatory
        DESCRIPTION
                "The name of emd alarm-1."
        ::= { pduDevMgmtEmdSlave07Entry 7 }

pduDevMgmtEmdSlave07Alarm2Name OBJECT-TYPE
        SYNTAX DisplayString (SIZE(0..31))
        ACCESS read-write
        STATUS mandatory
        DESCRIPTION
                "The name of emd alarm-2."
        ::= { pduDevMgmtEmdSlave07Entry 8 }

pduDevMgmtEmdSlave07TempLowWarn OBJECT-TYPE
        SYNTAX INTEGER (-200..1000)
        UNITS  "0.1degC"
        ACCESS read-write
        STATUS mandatory
        DESCRIPTION
                "The low warning threshold of temperature of emd."
        ::= { pduDevMgmtEmdSlave07Entry 9 }

pduDevMgmtEmdSlave07TempLowCrit OBJECT-TYPE
        SYNTAX INTEGER (-200..1000)
        UNITS  "0.1degC"
        ACCESS read-write
        STATUS mandatory
        DESCRIPTION
                "The low critical threshold of temperature of emd."
        ::= { pduDevMgmtEmdSlave07Entry 10 }

pduDevMgmtEmdSlave07TempHighWarn OBJECT-TYPE
        SYNTAX INTEGER (-200..1000)
        UNITS  "0.1degC"
        ACCESS read-write
        STATUS mandatory
        DESCRIPTION
                "The high warning threshold of temperature of emd."
        ::= { pduDevMgmtEmdSlave07Entry 11 }

pduDevMgmtEmdSlave07TempHighCrit OBJECT-TYPE
        SYNTAX INTEGER (-200..1000)
        UNITS  "0.1degC"
        ACCESS read-write
        STATUS mandatory
        DESCRIPTION
                "The high critical threshold of temperature of emd."
        ::= { pduDevMgmtEmdSlave07Entry 12 }

pduDevMgmtEmdSlave07TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave07Entry 13 }

pduDevMgmtEmdSlave07HumiLowWarn OBJECT-TYPE
        SYNTAX INTEGER (0..2120)
        UNITS  "0.1%"
        ACCESS read-write
        STATUS mandatory
        DESCRIPTION
                "The low warning threshold of humidity of emd."
        ::= { pduDevMgmtEmdSlave07Entry 15 }

pduDevMgmtEmdSlave07HumiLowCrit OBJECT-TYPE
        SYNTAX INTEGER (0..2120)
        UNITS  "0.1%"
        ACCESS read-write
        STATUS mandatory
        DESCRIPTION
                "The low critical threshold of humidity of emd."
        ::= { pduDevMgmtEmdSlave07Entry 16 }

pduDevMgmtEmdSlave07HumiHighWarn OBJECT-TYPE
        SYNTAX INTEGER (0..2120)
        UNITS  "0.1%"
        ACCESS read-write
        STATUS mandatory
        DESCRIPTION
                "The high warning threshold of humidity of emd."
        ::= { pduDevMgmtEmdSlave07Entry 17 }

pduDevMgmtEmdSlave07HumiHighCrit OBJECT-TYPE
        SYNTAX INTEGER (0..2120)
        UNITS  "0.1%"
        ACCESS read-write
        STATUS mandatory
        DESCRIPTION
                "The high critical threshold of humidity of emd."
        ::= { pduDevMgmtEmdSlave07Entry 18 }

pduDevMgmtEmdSlave07HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave07Entry 19 }

pduDevMgmtEmdSlave07Alarm1Setup OBJECT-TYPE
        SYNTAX INTEGER {
                disabled(1),
                no(2),
				nc(3)
                }
        ACCESS read-write
        STATUS mandatory
        DESCRIPTION
                "The alarm-1 setup of emd."
        ::= { pduDevMgmtEmdSlave07Entry 21 }

pduDevMgmtEmdSlave07Alarm2Setup OBJECT-TYPE
        SYNTAX INTEGER {
                disabled(1),
                no(2),
				nc(3)
                }
        ACCESS read-write
        STATUS mandatory
        DESCRIPTION
                "The alarm-2 setup of emd."
        ::= { pduDevMgmtEmdSlave07Entry 22 }


-- ===========================================================================
--
-- pduDevMgmtEmdSlave08
--
--  Slave08 Emd Mgmtoitor Group
--
-- ===========================================================================
pduDevMgmtEmdSlave08Table OBJECT-TYPE
        SYNTAX SEQUENCE OF PduDevMgmtEmdSlave08Entry
        ACCESS not-accessible
        STATUS mandatory
        DESCRIPTION
                "Display a list of the emd information of master."
        ::= { pduDevMgmtEmdSlave08 1}

pduDevMgmtEmdSlave08Entry OBJECT-TYPE
        SYNTAX PduDevMgmtEmdSlave08Entry
        ACCESS not-accessible
        STATUS mandatory
        DESCRIPTION
                "Display a list of the emd information of master."
        INDEX  { pduDevMgmtEmdSlave08Index}
        ::= { pduDevMgmtEmdSlave08Table 1 }

PduDevMgmtEmdSlave08Entry ::=
        SEQUENCE {
                pduDevMgmtEmdSlave08Index
                        INTEGER,
                pduDevMgmtEmdSlave08Valid
                        INTEGER,
                pduDevMgmtEmdSlave08Type
                        INTEGER,
                pduDevMgmtEmdSlave08Name
                        DisplayString,
                pduDevMgmtEmdSlave08TempName
                        DisplayString,
                pduDevMgmtEmdSlave08HumiName
                        DisplayString,
                pduDevMgmtEmdSlave08Alarm1Name
                        DisplayString,
                pduDevMgmtEmdSlave08Alarm2Name
                        DisplayString,
                pduDevMgmtEmdSlave08TempLowWarn
                        INTEGER,
                pduDevMgmtEmdSlave08TempLowCrit
                        INTEGER,
                pduDevMgmtEmdSlave08TempHighWarn
                        INTEGER,
                pduDevMgmtEmdSlave08TempHighCrit
                        INTEGER,
                pduDevMgmtEmdSlave08TempCali
                        INTEGER,
                pduDevMgmtEmdSlave08HumiLowWarn
                        INTEGER,
                pduDevMgmtEmdSlave08HumiLowCrit
                        INTEGER,
                pduDevMgmtEmdSlave08HumiHighWarn
                        INTEGER,
                pduDevMgmtEmdSlave08HumiHighCrit
                        INTEGER,
                pduDevMgmtEmdSlave08HumiCali
                        INTEGER,
                pduDevMgmtEmdSlave08Alarm1Setup
                        INTEGER,
                pduDevMgmtEmdSlave08Alarm2Setup
                        INTEGER
        }

pduDevMgmtEmdSlave08Index OBJECT-TYPE
        SYNTAX INTEGER (0..7)
        ACCESS read-only
        STATUS mandatory
        DESCRIPTION
                "The index to a emd entry."
        ::= { pduDevMgmtEmdSlave08Entry 1 }

pduDevMgmtEmdSlave08Valid OBJECT-TYPE
        SYNTAX INTEGER {
                offline(1),
                online(2)
                }
        ACCESS read-only
        STATUS mandatory
        DESCRIPTION
                "The online status of emd."
        ::= { pduDevMgmtEmdSlave08Entry 2 }


pduDevMgmtEmdSlave08Type OBJECT-TYPE
        SYNTAX INTEGER
        ACCESS read-only
        STATUS mandatory
        DESCRIPTION
                "The type of emd."
        ::= { pduDevMgmtEmdSlave08Entry 3 }

pduDevMgmtEmdSlave08Name OBJECT-TYPE
        SYNTAX DisplayString (SIZE(0..31))
        ACCESS read-write
        STATUS mandatory
        DESCRIPTION
                "The name of emd."
        ::= { pduDevMgmtEmdSlave08Entry 4 }

pduDevMgmtEmdSlave08TempName OBJECT-TYPE
        SYNTAX DisplayString (SIZE(0..31))
        ACCESS read-write
        STATUS mandatory
        DESCRIPTION
                "The name of emd temperature."
        ::= { pduDevMgmtEmdSlave08Entry 5 }

pduDevMgmtEmdSlave08HumiName OBJECT-TYPE
        SYNTAX DisplayString (SIZE(0..31))
        ACCESS read-write
        STATUS mandatory
        DESCRIPTION
                "The name of emd humidity."
        ::= { pduDevMgmtEmdSlave08Entry 6 }

pduDevMgmtEmdSlave08Alarm1Name OBJECT-TYPE
        SYNTAX DisplayString (SIZE(0..31))
        ACCESS read-write
        STATUS mandatory
        DESCRIPTION
                "The name of emd alarm-1."
        ::= { pduDevMgmtEmdSlave08Entry 7 }

pduDevMgmtEmdSlave08Alarm2Name OBJECT-TYPE
        SYNTAX DisplayString (SIZE(0..31))
        ACCESS read-write
        STATUS mandatory
        DESCRIPTION
                "The name of emd alarm-2."
        ::= { pduDevMgmtEmdSlave08Entry 8 }

pduDevMgmtEmdSlave08TempLowWarn OBJECT-TYPE
        SYNTAX INTEGER (-200..1000)
        UNITS  "0.1degC"
        ACCESS read-write
        STATUS mandatory
        DESCRIPTION
                "The low warning threshold of temperature of emd."
        ::= { pduDevMgmtEmdSlave08Entry 9 }

pduDevMgmtEmdSlave08TempLowCrit OBJECT-TYPE
        SYNTAX INTEGER (-200..1000)
        UNITS  "0.1degC"
        ACCESS read-write
        STATUS mandatory
        DESCRIPTION
                "The low critical threshold of temperature of emd."
        ::= { pduDevMgmtEmdSlave08Entry 10 }

pduDevMgmtEmdSlave08TempHighWarn OBJECT-TYPE
        SYNTAX INTEGER (-200..1000)
        UNITS  "0.1degC"
        ACCESS read-write
        STATUS mandatory
        DESCRIPTION
                "The high warning threshold of temperature of emd."
        ::= { pduDevMgmtEmdSlave08Entry 11 }

pduDevMgmtEmdSlave08TempHighCrit OBJECT-TYPE
        SYNTAX INTEGER (-200..1000)
        UNITS  "0.1degC"
        ACCESS read-write
        STATUS mandatory
        DESCRIPTION
                "The high critical threshold of temperature of emd."
        ::= { pduDevMgmtEmdSlave08Entry 12 }

pduDevMgmtEmdSlave08TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave08Entry 13 }

pduDevMgmtEmdSlave08HumiLowWarn OBJECT-TYPE
        SYNTAX INTEGER (0..2120)
        UNITS  "0.1%"
        ACCESS read-write
        STATUS mandatory
        DESCRIPTION
                "The low warning threshold of humidity of emd."
        ::= { pduDevMgmtEmdSlave08Entry 15 }

pduDevMgmtEmdSlave08HumiLowCrit OBJECT-TYPE
        SYNTAX INTEGER (0..2120)
        UNITS  "0.1%"
        ACCESS read-write
        STATUS mandatory
        DESCRIPTION
                "The low critical threshold of humidity of emd."
        ::= { pduDevMgmtEmdSlave08Entry 16 }

pduDevMgmtEmdSlave08HumiHighWarn OBJECT-TYPE
        SYNTAX INTEGER (0..2120)
        UNITS  "0.1%"
        ACCESS read-write
        STATUS mandatory
        DESCRIPTION
                "The high warning threshold of humidity of emd."
        ::= { pduDevMgmtEmdSlave08Entry 17 }

pduDevMgmtEmdSlave08HumiHighCrit OBJECT-TYPE
        SYNTAX INTEGER (0..2120)
        UNITS  "0.1%"
        ACCESS read-write
        STATUS mandatory
        DESCRIPTION
                "The high critical threshold of humidity of emd."
        ::= { pduDevMgmtEmdSlave08Entry 18 }

pduDevMgmtEmdSlave08HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave08Entry 19 }

pduDevMgmtEmdSlave08Alarm1Setup OBJECT-TYPE
        SYNTAX INTEGER {
                disabled(1),
                no(2),
				nc(3)
                }
        ACCESS read-write
        STATUS mandatory
        DESCRIPTION
                "The alarm-1 setup of emd."
        ::= { pduDevMgmtEmdSlave08Entry 21 }

pduDevMgmtEmdSlave08Alarm2Setup OBJECT-TYPE
        SYNTAX INTEGER {
                disabled(1),
                no(2),
				nc(3)
                }
        ACCESS read-write
        STATUS mandatory
        DESCRIPTION
                "The alarm-2 setup of emd."
        ::= { pduDevMgmtEmdSlave08Entry 22 }


-- ===========================================================================
--
-- pduDevMgmtEmdSlave09
--
--  Slave09 Emd Mgmtoitor Group
--
-- ===========================================================================
pduDevMgmtEmdSlave09Table OBJECT-TYPE
        SYNTAX SEQUENCE OF PduDevMgmtEmdSlave09Entry
        ACCESS not-accessible
        STATUS mandatory
        DESCRIPTION
                "Display a list of the emd information of master."
        ::= { pduDevMgmtEmdSlave09 1}

pduDevMgmtEmdSlave09Entry OBJECT-TYPE
        SYNTAX PduDevMgmtEmdSlave09Entry
        ACCESS not-accessible
        STATUS mandatory
        DESCRIPTION
                "Display a list of the emd information of master."
        INDEX  { pduDevMgmtEmdSlave09Index}
        ::= { pduDevMgmtEmdSlave09Table 1 }

PduDevMgmtEmdSlave09Entry ::=
        SEQUENCE {
                pduDevMgmtEmdSlave09Index
                        INTEGER,
                pduDevMgmtEmdSlave09Valid
                        INTEGER,
                pduDevMgmtEmdSlave09Type
                        INTEGER,
                pduDevMgmtEmdSlave09Name
                        DisplayString,
                pduDevMgmtEmdSlave09TempName
                        DisplayString,
                pduDevMgmtEmdSlave09HumiName
                        DisplayString,
                pduDevMgmtEmdSlave09Alarm1Name
                        DisplayString,
                pduDevMgmtEmdSlave09Alarm2Name
                        DisplayString,
                pduDevMgmtEmdSlave09TempLowWarn
                        INTEGER,
                pduDevMgmtEmdSlave09TempLowCrit
                        INTEGER,
                pduDevMgmtEmdSlave09TempHighWarn
                        INTEGER,
                pduDevMgmtEmdSlave09TempHighCrit
                        INTEGER,
                pduDevMgmtEmdSlave09TempCali
                        INTEGER,
                pduDevMgmtEmdSlave09HumiLowWarn
                        INTEGER,
                pduDevMgmtEmdSlave09HumiLowCrit
                        INTEGER,
                pduDevMgmtEmdSlave09HumiHighWarn
                        INTEGER,
                pduDevMgmtEmdSlave09HumiHighCrit
                        INTEGER,
                pduDevMgmtEmdSlave09HumiCali
                        INTEGER,
                pduDevMgmtEmdSlave09Alarm1Setup
                        INTEGER,
                pduDevMgmtEmdSlave09Alarm2Setup
                        INTEGER
        }

pduDevMgmtEmdSlave09Index OBJECT-TYPE
        SYNTAX INTEGER (0..7)
        ACCESS read-only
        STATUS mandatory
        DESCRIPTION
                "The index to a emd entry."
        ::= { pduDevMgmtEmdSlave09Entry 1 }

pduDevMgmtEmdSlave09Valid OBJECT-TYPE
        SYNTAX INTEGER {
                offline(1),
                online(2)
                }
        ACCESS read-only
        STATUS mandatory
        DESCRIPTION
                "The online status of emd."
        ::= { pduDevMgmtEmdSlave09Entry 2 }


pduDevMgmtEmdSlave09Type OBJECT-TYPE
        SYNTAX INTEGER
        ACCESS read-only
        STATUS mandatory
        DESCRIPTION
                "The type of emd."
        ::= { pduDevMgmtEmdSlave09Entry 3 }

pduDevMgmtEmdSlave09Name OBJECT-TYPE
        SYNTAX DisplayString (SIZE(0..31))
        ACCESS read-write
        STATUS mandatory
        DESCRIPTION
                "The name of emd."
        ::= { pduDevMgmtEmdSlave09Entry 4 }

pduDevMgmtEmdSlave09TempName OBJECT-TYPE
        SYNTAX DisplayString (SIZE(0..31))
        ACCESS read-write
        STATUS mandatory
        DESCRIPTION
                "The name of emd temperature."
        ::= { pduDevMgmtEmdSlave09Entry 5 }

pduDevMgmtEmdSlave09HumiName OBJECT-TYPE
        SYNTAX DisplayString (SIZE(0..31))
        ACCESS read-write
        STATUS mandatory
        DESCRIPTION
                "The name of emd humidity."
        ::= { pduDevMgmtEmdSlave09Entry 6 }

pduDevMgmtEmdSlave09Alarm1Name OBJECT-TYPE
        SYNTAX DisplayString (SIZE(0..31))
        ACCESS read-write
        STATUS mandatory
        DESCRIPTION
                "The name of emd alarm-1."
        ::= { pduDevMgmtEmdSlave09Entry 7 }

pduDevMgmtEmdSlave09Alarm2Name OBJECT-TYPE
        SYNTAX DisplayString (SIZE(0..31))
        ACCESS read-write
        STATUS mandatory
        DESCRIPTION
                "The name of emd alarm-2."
        ::= { pduDevMgmtEmdSlave09Entry 8 }

pduDevMgmtEmdSlave09TempLowWarn OBJECT-TYPE
        SYNTAX INTEGER (-200..1000)
        UNITS  "0.1degC"
        ACCESS read-write
        STATUS mandatory
        DESCRIPTION
                "The low warning threshold of temperature of emd."
        ::= { pduDevMgmtEmdSlave09Entry 9 }

pduDevMgmtEmdSlave09TempLowCrit OBJECT-TYPE
        SYNTAX INTEGER (-200..1000)
        UNITS  "0.1degC"
        ACCESS read-write
        STATUS mandatory
        DESCRIPTION
                "The low critical threshold of temperature of emd."
        ::= { pduDevMgmtEmdSlave09Entry 10 }

pduDevMgmtEmdSlave09TempHighWarn OBJECT-TYPE
        SYNTAX INTEGER (-200..1000)
        UNITS  "0.1degC"
        ACCESS read-write
        STATUS mandatory
        DESCRIPTION
                "The high warning threshold of temperature of emd."
        ::= { pduDevMgmtEmdSlave09Entry 11 }

pduDevMgmtEmdSlave09TempHighCrit OBJECT-TYPE
        SYNTAX INTEGER (-200..1000)
        UNITS  "0.1degC"
        ACCESS read-write
        STATUS mandatory
        DESCRIPTION
                "The high critical threshold of temperature of emd."
        ::= { pduDevMgmtEmdSlave09Entry 12 }

pduDevMgmtEmdSlave09TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave09Entry 13 }

pduDevMgmtEmdSlave09HumiLowWarn OBJECT-TYPE
        SYNTAX INTEGER (0..2120)
        UNITS  "0.1%"
        ACCESS read-write
        STATUS mandatory
        DESCRIPTION
                "The low warning threshold of humidity of emd."
        ::= { pduDevMgmtEmdSlave09Entry 15 }

pduDevMgmtEmdSlave09HumiLowCrit OBJECT-TYPE
        SYNTAX INTEGER (0..2120)
        UNITS  "0.1%"
        ACCESS read-write
        STATUS mandatory
        DESCRIPTION
                "The low critical threshold of humidity of emd."
        ::= { pduDevMgmtEmdSlave09Entry 16 }

pduDevMgmtEmdSlave09HumiHighWarn OBJECT-TYPE
        SYNTAX INTEGER (0..2120)
        UNITS  "0.1%"
        ACCESS read-write
        STATUS mandatory
        DESCRIPTION
                "The high warning threshold of humidity of emd."
        ::= { pduDevMgmtEmdSlave09Entry 17 }

pduDevMgmtEmdSlave09HumiHighCrit OBJECT-TYPE
        SYNTAX INTEGER (0..2120)
        UNITS  "0.1%"
        ACCESS read-write
        STATUS mandatory
        DESCRIPTION
                "The high critical threshold of humidity of emd."
        ::= { pduDevMgmtEmdSlave09Entry 18 }

pduDevMgmtEmdSlave09HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave09Entry 19 }

pduDevMgmtEmdSlave09Alarm1Setup OBJECT-TYPE
        SYNTAX INTEGER {
                disabled(1),
                no(2),
				nc(3)
                }
        ACCESS read-write
        STATUS mandatory
        DESCRIPTION
                "The alarm-1 setup of emd."
        ::= { pduDevMgmtEmdSlave09Entry 21 }

pduDevMgmtEmdSlave09Alarm2Setup OBJECT-TYPE
        SYNTAX INTEGER {
                disabled(1),
                no(2),
				nc(3)
                }
        ACCESS read-write
        STATUS mandatory
        DESCRIPTION
                "The alarm-2 setup of emd."
        ::= { pduDevMgmtEmdSlave09Entry 22 }


-- ===========================================================================
--
-- pduDevMgmtEmdSlave10
--
--  Slave10 Emd Mgmtoitor Group
--
-- ===========================================================================
pduDevMgmtEmdSlave10Table OBJECT-TYPE
        SYNTAX SEQUENCE OF PduDevMgmtEmdSlave10Entry
        ACCESS not-accessible
        STATUS mandatory
        DESCRIPTION
                "Display a list of the emd information of master."
        ::= { pduDevMgmtEmdSlave10 1}

pduDevMgmtEmdSlave10Entry OBJECT-TYPE
        SYNTAX PduDevMgmtEmdSlave10Entry
        ACCESS not-accessible
        STATUS mandatory
        DESCRIPTION
                "Display a list of the emd information of master."
        INDEX  { pduDevMgmtEmdSlave10Index}
        ::= { pduDevMgmtEmdSlave10Table 1 }

PduDevMgmtEmdSlave10Entry ::=
        SEQUENCE {
                pduDevMgmtEmdSlave10Index
                        INTEGER,
                pduDevMgmtEmdSlave10Valid
                        INTEGER,
                pduDevMgmtEmdSlave10Type
                        INTEGER,
                pduDevMgmtEmdSlave10Name
                        DisplayString,
                pduDevMgmtEmdSlave10TempName
                        DisplayString,
                pduDevMgmtEmdSlave10HumiName
                        DisplayString,
                pduDevMgmtEmdSlave10Alarm1Name
                        DisplayString,
                pduDevMgmtEmdSlave10Alarm2Name
                        DisplayString,
                pduDevMgmtEmdSlave10TempLowWarn
                        INTEGER,
                pduDevMgmtEmdSlave10TempLowCrit
                        INTEGER,
                pduDevMgmtEmdSlave10TempHighWarn
                        INTEGER,
                pduDevMgmtEmdSlave10TempHighCrit
                        INTEGER,
                pduDevMgmtEmdSlave10TempCali
                        INTEGER,
                pduDevMgmtEmdSlave10HumiLowWarn
                        INTEGER,
                pduDevMgmtEmdSlave10HumiLowCrit
                        INTEGER,
                pduDevMgmtEmdSlave10HumiHighWarn
                        INTEGER,
                pduDevMgmtEmdSlave10HumiHighCrit
                        INTEGER,
                pduDevMgmtEmdSlave10HumiCali
                        INTEGER,
                pduDevMgmtEmdSlave10Alarm1Setup
                        INTEGER,
                pduDevMgmtEmdSlave10Alarm2Setup
                        INTEGER
        }

pduDevMgmtEmdSlave10Index OBJECT-TYPE
        SYNTAX INTEGER (0..7)
        ACCESS read-only
        STATUS mandatory
        DESCRIPTION
                "The index to a emd entry."
        ::= { pduDevMgmtEmdSlave10Entry 1 }

pduDevMgmtEmdSlave10Valid OBJECT-TYPE
        SYNTAX INTEGER {
                offline(1),
                online(2)
                }
        ACCESS read-only
        STATUS mandatory
        DESCRIPTION
                "The online status of emd."
        ::= { pduDevMgmtEmdSlave10Entry 2 }


pduDevMgmtEmdSlave10Type OBJECT-TYPE
        SYNTAX INTEGER
        ACCESS read-only
        STATUS mandatory
        DESCRIPTION
                "The type of emd."
        ::= { pduDevMgmtEmdSlave10Entry 3 }

pduDevMgmtEmdSlave10Name OBJECT-TYPE
        SYNTAX DisplayString (SIZE(0..31))
        ACCESS read-write
        STATUS mandatory
        DESCRIPTION
                "The name of emd."
        ::= { pduDevMgmtEmdSlave10Entry 4 }

pduDevMgmtEmdSlave10TempName OBJECT-TYPE
        SYNTAX DisplayString (SIZE(0..31))
        ACCESS read-write
        STATUS mandatory
        DESCRIPTION
                "The name of emd temperature."
        ::= { pduDevMgmtEmdSlave10Entry 5 }

pduDevMgmtEmdSlave10HumiName OBJECT-TYPE
        SYNTAX DisplayString (SIZE(0..31))
        ACCESS read-write
        STATUS mandatory
        DESCRIPTION
                "The name of emd humidity."
        ::= { pduDevMgmtEmdSlave10Entry 6 }

pduDevMgmtEmdSlave10Alarm1Name OBJECT-TYPE
        SYNTAX DisplayString (SIZE(0..31))
        ACCESS read-write
        STATUS mandatory
        DESCRIPTION
                "The name of emd alarm-1."
        ::= { pduDevMgmtEmdSlave10Entry 7 }

pduDevMgmtEmdSlave10Alarm2Name OBJECT-TYPE
        SYNTAX DisplayString (SIZE(0..31))
        ACCESS read-write
        STATUS mandatory
        DESCRIPTION
                "The name of emd alarm-2."
        ::= { pduDevMgmtEmdSlave10Entry 8 }

pduDevMgmtEmdSlave10TempLowWarn OBJECT-TYPE
        SYNTAX INTEGER (-200..1000)
        UNITS  "0.1degC"
        ACCESS read-write
        STATUS mandatory
        DESCRIPTION
                "The low warning threshold of temperature of emd."
        ::= { pduDevMgmtEmdSlave10Entry 9 }

pduDevMgmtEmdSlave10TempLowCrit OBJECT-TYPE
        SYNTAX INTEGER (-200..1000)
        UNITS  "0.1degC"
        ACCESS read-write
        STATUS mandatory
        DESCRIPTION
                "The low critical threshold of temperature of emd."
        ::= { pduDevMgmtEmdSlave10Entry 10 }

pduDevMgmtEmdSlave10TempHighWarn OBJECT-TYPE
        SYNTAX INTEGER (-200..1000)
        UNITS  "0.1degC"
        ACCESS read-write
        STATUS mandatory
        DESCRIPTION
                "The high warning threshold of temperature of emd."
        ::= { pduDevMgmtEmdSlave10Entry 11 }

pduDevMgmtEmdSlave10TempHighCrit OBJECT-TYPE
        SYNTAX INTEGER (-200..1000)
        UNITS  "0.1degC"
        ACCESS read-write
        STATUS mandatory
        DESCRIPTION
                "The high critical threshold of temperature of emd."
        ::= { pduDevMgmtEmdSlave10Entry 12 }

pduDevMgmtEmdSlave10TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave10Entry 13 }

pduDevMgmtEmdSlave10HumiLowWarn OBJECT-TYPE
        SYNTAX INTEGER (0..2120)
        UNITS  "0.1%"
        ACCESS read-write
        STATUS mandatory
        DESCRIPTION
                "The low warning threshold of humidity of emd."
        ::= { pduDevMgmtEmdSlave10Entry 15 }

pduDevMgmtEmdSlave10HumiLowCrit OBJECT-TYPE
        SYNTAX INTEGER (0..2120)
        UNITS  "0.1%"
        ACCESS read-write
        STATUS mandatory
        DESCRIPTION
                "The low critical threshold of humidity of emd."
        ::= { pduDevMgmtEmdSlave10Entry 16 }

pduDevMgmtEmdSlave10HumiHighWarn OBJECT-TYPE
        SYNTAX INTEGER (0..2120)
        UNITS  "0.1%"
        ACCESS read-write
        STATUS mandatory
        DESCRIPTION
                "The high warning threshold of humidity of emd."
        ::= { pduDevMgmtEmdSlave10Entry 17 }

pduDevMgmtEmdSlave10HumiHighCrit OBJECT-TYPE
        SYNTAX INTEGER (0..2120)
        UNITS  "0.1%"
        ACCESS read-write
        STATUS mandatory
        DESCRIPTION
                "The high critical threshold of humidity of emd."
        ::= { pduDevMgmtEmdSlave10Entry 18 }

pduDevMgmtEmdSlave10HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave10Entry 19 }

pduDevMgmtEmdSlave10Alarm1Setup OBJECT-TYPE
        SYNTAX INTEGER {
                disabled(1),
                no(2),
				nc(3)
                }
        ACCESS read-write
        STATUS mandatory
        DESCRIPTION
                "The alarm-1 setup of emd."
        ::= { pduDevMgmtEmdSlave10Entry 21 }

pduDevMgmtEmdSlave10Alarm2Setup OBJECT-TYPE
        SYNTAX INTEGER {
                disabled(1),
                no(2),
				nc(3)
                }
        ACCESS read-write
        STATUS mandatory
        DESCRIPTION
                "The alarm-2 setup of emd."
        ::= { pduDevMgmtEmdSlave10Entry 22 }


-- ===========================================================================
--
-- pduDevMgmtEmdSlave11
--
--  Slave11 Emd Mgmtoitor Group
--
-- ===========================================================================
pduDevMgmtEmdSlave11Table OBJECT-TYPE
        SYNTAX SEQUENCE OF PduDevMgmtEmdSlave11Entry
        ACCESS not-accessible
        STATUS mandatory
        DESCRIPTION
                "Display a list of the emd information of master."
        ::= { pduDevMgmtEmdSlave11 1}

pduDevMgmtEmdSlave11Entry OBJECT-TYPE
        SYNTAX PduDevMgmtEmdSlave11Entry
        ACCESS not-accessible
        STATUS mandatory
        DESCRIPTION
                "Display a list of the emd information of master."
        INDEX  { pduDevMgmtEmdSlave11Index}
        ::= { pduDevMgmtEmdSlave11Table 1 }

PduDevMgmtEmdSlave11Entry ::=
        SEQUENCE {
                pduDevMgmtEmdSlave11Index
                        INTEGER,
                pduDevMgmtEmdSlave11Valid
                        INTEGER,
                pduDevMgmtEmdSlave11Type
                        INTEGER,
                pduDevMgmtEmdSlave11Name
                        DisplayString,
                pduDevMgmtEmdSlave11TempName
                        DisplayString,
                pduDevMgmtEmdSlave11HumiName
                        DisplayString,
                pduDevMgmtEmdSlave11Alarm1Name
                        DisplayString,
                pduDevMgmtEmdSlave11Alarm2Name
                        DisplayString,
                pduDevMgmtEmdSlave11TempLowWarn
                        INTEGER,
                pduDevMgmtEmdSlave11TempLowCrit
                        INTEGER,
                pduDevMgmtEmdSlave11TempHighWarn
                        INTEGER,
                pduDevMgmtEmdSlave11TempHighCrit
                        INTEGER,
                pduDevMgmtEmdSlave11TempCali
                        INTEGER,
                pduDevMgmtEmdSlave11HumiLowWarn
                        INTEGER,
                pduDevMgmtEmdSlave11HumiLowCrit
                        INTEGER,
                pduDevMgmtEmdSlave11HumiHighWarn
                        INTEGER,
                pduDevMgmtEmdSlave11HumiHighCrit
                        INTEGER,
                pduDevMgmtEmdSlave11HumiCali
                        INTEGER,
                pduDevMgmtEmdSlave11Alarm1Setup
                        INTEGER,
                pduDevMgmtEmdSlave11Alarm2Setup
                        INTEGER
        }

pduDevMgmtEmdSlave11Index OBJECT-TYPE
        SYNTAX INTEGER (0..7)
        ACCESS read-only
        STATUS mandatory
        DESCRIPTION
                "The index to a emd entry."
        ::= { pduDevMgmtEmdSlave11Entry 1 }

pduDevMgmtEmdSlave11Valid OBJECT-TYPE
        SYNTAX INTEGER {
                offline(1),
                online(2)
                }
        ACCESS read-only
        STATUS mandatory
        DESCRIPTION
                "The online status of emd."
        ::= { pduDevMgmtEmdSlave11Entry 2 }


pduDevMgmtEmdSlave11Type OBJECT-TYPE
        SYNTAX INTEGER
        ACCESS read-only
        STATUS mandatory
        DESCRIPTION
                "The type of emd."
        ::= { pduDevMgmtEmdSlave11Entry 3 }

pduDevMgmtEmdSlave11Name OBJECT-TYPE
        SYNTAX DisplayString (SIZE(0..31))
        ACCESS read-write
        STATUS mandatory
        DESCRIPTION
                "The name of emd."
        ::= { pduDevMgmtEmdSlave11Entry 4 }

pduDevMgmtEmdSlave11TempName OBJECT-TYPE
        SYNTAX DisplayString (SIZE(0..31))
        ACCESS read-write
        STATUS mandatory
        DESCRIPTION
                "The name of emd temperature."
        ::= { pduDevMgmtEmdSlave11Entry 5 }

pduDevMgmtEmdSlave11HumiName OBJECT-TYPE
        SYNTAX DisplayString (SIZE(0..31))
        ACCESS read-write
        STATUS mandatory
        DESCRIPTION
                "The name of emd humidity."
        ::= { pduDevMgmtEmdSlave11Entry 6 }

pduDevMgmtEmdSlave11Alarm1Name OBJECT-TYPE
        SYNTAX DisplayString (SIZE(0..31))
        ACCESS read-write
        STATUS mandatory
        DESCRIPTION
                "The name of emd alarm-1."
        ::= { pduDevMgmtEmdSlave11Entry 7 }

pduDevMgmtEmdSlave11Alarm2Name OBJECT-TYPE
        SYNTAX DisplayString (SIZE(0..31))
        ACCESS read-write
        STATUS mandatory
        DESCRIPTION
                "The name of emd alarm-2."
        ::= { pduDevMgmtEmdSlave11Entry 8 }

pduDevMgmtEmdSlave11TempLowWarn OBJECT-TYPE
        SYNTAX INTEGER (-200..1000)
        UNITS  "0.1degC"
        ACCESS read-write
        STATUS mandatory
        DESCRIPTION
                "The low warning threshold of temperature of emd."
        ::= { pduDevMgmtEmdSlave11Entry 9 }

pduDevMgmtEmdSlave11TempLowCrit OBJECT-TYPE
        SYNTAX INTEGER (-200..1000)
        UNITS  "0.1degC"
        ACCESS read-write
        STATUS mandatory
        DESCRIPTION
                "The low critical threshold of temperature of emd."
        ::= { pduDevMgmtEmdSlave11Entry 10 }

pduDevMgmtEmdSlave11TempHighWarn OBJECT-TYPE
        SYNTAX INTEGER (-200..1000)
        UNITS  "0.1degC"
        ACCESS read-write
        STATUS mandatory
        DESCRIPTION
                "The high warning threshold of temperature of emd."
        ::= { pduDevMgmtEmdSlave11Entry 11 }

pduDevMgmtEmdSlave11TempHighCrit OBJECT-TYPE
        SYNTAX INTEGER (-200..1000)
        UNITS  "0.1degC"
        ACCESS read-write
        STATUS mandatory
        DESCRIPTION
                "The high critical threshold of temperature of emd."
        ::= { pduDevMgmtEmdSlave11Entry 12 }

pduDevMgmtEmdSlave11TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave11Entry 13 }

pduDevMgmtEmdSlave11HumiLowWarn OBJECT-TYPE
        SYNTAX INTEGER (0..2120)
        UNITS  "0.1%"
        ACCESS read-write
        STATUS mandatory
        DESCRIPTION
                "The low warning threshold of humidity of emd."
        ::= { pduDevMgmtEmdSlave11Entry 15 }

pduDevMgmtEmdSlave11HumiLowCrit OBJECT-TYPE
        SYNTAX INTEGER (0..2120)
        UNITS  "0.1%"
        ACCESS read-write
        STATUS mandatory
        DESCRIPTION
                "The low critical threshold of humidity of emd."
        ::= { pduDevMgmtEmdSlave11Entry 16 }

pduDevMgmtEmdSlave11HumiHighWarn OBJECT-TYPE
        SYNTAX INTEGER (0..2120)
        UNITS  "0.1%"
        ACCESS read-write
        STATUS mandatory
        DESCRIPTION
                "The high warning threshold of humidity of emd."
        ::= { pduDevMgmtEmdSlave11Entry 17 }

pduDevMgmtEmdSlave11HumiHighCrit OBJECT-TYPE
        SYNTAX INTEGER (0..2120)
        UNITS  "0.1%"
        ACCESS read-write
        STATUS mandatory
        DESCRIPTION
                "The high critical threshold of humidity of emd."
        ::= { pduDevMgmtEmdSlave11Entry 18 }

pduDevMgmtEmdSlave11HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave11Entry 19 }

pduDevMgmtEmdSlave11Alarm1Setup OBJECT-TYPE
        SYNTAX INTEGER {
                disabled(1),
                no(2),
				nc(3)
                }
        ACCESS read-write
        STATUS mandatory
        DESCRIPTION
                "The alarm-1 setup of emd."
        ::= { pduDevMgmtEmdSlave11Entry 21 }

pduDevMgmtEmdSlave11Alarm2Setup OBJECT-TYPE
        SYNTAX INTEGER {
                disabled(1),
                no(2),
				nc(3)
                }
        ACCESS read-write
        STATUS mandatory
        DESCRIPTION
                "The alarm-2 setup of emd."
        ::= { pduDevMgmtEmdSlave11Entry 22 }


-- ===========================================================================
--
-- pduDevMgmtEmdSlave12
--
--  Slave12 Emd Mgmtoitor Group
--
-- ===========================================================================
pduDevMgmtEmdSlave12Table OBJECT-TYPE
        SYNTAX SEQUENCE OF PduDevMgmtEmdSlave12Entry
        ACCESS not-accessible
        STATUS mandatory
        DESCRIPTION
                "Display a list of the emd information of master."
        ::= { pduDevMgmtEmdSlave12 1}

pduDevMgmtEmdSlave12Entry OBJECT-TYPE
        SYNTAX PduDevMgmtEmdSlave12Entry
        ACCESS not-accessible
        STATUS mandatory
        DESCRIPTION
                "Display a list of the emd information of master."
        INDEX  { pduDevMgmtEmdSlave12Index}
        ::= { pduDevMgmtEmdSlave12Table 1 }

PduDevMgmtEmdSlave12Entry ::=
        SEQUENCE {
                pduDevMgmtEmdSlave12Index
                        INTEGER,
                pduDevMgmtEmdSlave12Valid
                        INTEGER,
                pduDevMgmtEmdSlave12Type
                        INTEGER,
                pduDevMgmtEmdSlave12Name
                        DisplayString,
                pduDevMgmtEmdSlave12TempName
                        DisplayString,
                pduDevMgmtEmdSlave12HumiName
                        DisplayString,
                pduDevMgmtEmdSlave12Alarm1Name
                        DisplayString,
                pduDevMgmtEmdSlave12Alarm2Name
                        DisplayString,
                pduDevMgmtEmdSlave12TempLowWarn
                        INTEGER,
                pduDevMgmtEmdSlave12TempLowCrit
                        INTEGER,
                pduDevMgmtEmdSlave12TempHighWarn
                        INTEGER,
                pduDevMgmtEmdSlave12TempHighCrit
                        INTEGER,
                pduDevMgmtEmdSlave12TempCali
                        INTEGER,
                pduDevMgmtEmdSlave12HumiLowWarn
                        INTEGER,
                pduDevMgmtEmdSlave12HumiLowCrit
                        INTEGER,
                pduDevMgmtEmdSlave12HumiHighWarn
                        INTEGER,
                pduDevMgmtEmdSlave12HumiHighCrit
                        INTEGER,
                pduDevMgmtEmdSlave12HumiCali
                        INTEGER,
                pduDevMgmtEmdSlave12Alarm1Setup
                        INTEGER,
                pduDevMgmtEmdSlave12Alarm2Setup
                        INTEGER
        }

pduDevMgmtEmdSlave12Index OBJECT-TYPE
        SYNTAX INTEGER (0..7)
        ACCESS read-only
        STATUS mandatory
        DESCRIPTION
                "The index to a emd entry."
        ::= { pduDevMgmtEmdSlave12Entry 1 }

pduDevMgmtEmdSlave12Valid OBJECT-TYPE
        SYNTAX INTEGER {
                offline(1),
                online(2)
                }
        ACCESS read-only
        STATUS mandatory
        DESCRIPTION
                "The online status of emd."
        ::= { pduDevMgmtEmdSlave12Entry 2 }


pduDevMgmtEmdSlave12Type OBJECT-TYPE
        SYNTAX INTEGER
        ACCESS read-only
        STATUS mandatory
        DESCRIPTION
                "The type of emd."
        ::= { pduDevMgmtEmdSlave12Entry 3 }

pduDevMgmtEmdSlave12Name OBJECT-TYPE
        SYNTAX DisplayString (SIZE(0..31))
        ACCESS read-write
        STATUS mandatory
        DESCRIPTION
                "The name of emd."
        ::= { pduDevMgmtEmdSlave12Entry 4 }

pduDevMgmtEmdSlave12TempName OBJECT-TYPE
        SYNTAX DisplayString (SIZE(0..31))
        ACCESS read-write
        STATUS mandatory
        DESCRIPTION
                "The name of emd temperature."
        ::= { pduDevMgmtEmdSlave12Entry 5 }

pduDevMgmtEmdSlave12HumiName OBJECT-TYPE
        SYNTAX DisplayString (SIZE(0..31))
        ACCESS read-write
        STATUS mandatory
        DESCRIPTION
                "The name of emd humidity."
        ::= { pduDevMgmtEmdSlave12Entry 6 }

pduDevMgmtEmdSlave12Alarm1Name OBJECT-TYPE
        SYNTAX DisplayString (SIZE(0..31))
        ACCESS read-write
        STATUS mandatory
        DESCRIPTION
                "The name of emd alarm-1."
        ::= { pduDevMgmtEmdSlave12Entry 7 }

pduDevMgmtEmdSlave12Alarm2Name OBJECT-TYPE
        SYNTAX DisplayString (SIZE(0..31))
        ACCESS read-write
        STATUS mandatory
        DESCRIPTION
                "The name of emd alarm-2."
        ::= { pduDevMgmtEmdSlave12Entry 8 }

pduDevMgmtEmdSlave12TempLowWarn OBJECT-TYPE
        SYNTAX INTEGER (-200..1000)
        UNITS  "0.1degC"
        ACCESS read-write
        STATUS mandatory
        DESCRIPTION
                "The low warning threshold of temperature of emd."
        ::= { pduDevMgmtEmdSlave12Entry 9 }

pduDevMgmtEmdSlave12TempLowCrit OBJECT-TYPE
        SYNTAX INTEGER (-200..1000)
        UNITS  "0.1degC"
        ACCESS read-write
        STATUS mandatory
        DESCRIPTION
                "The low critical threshold of temperature of emd."
        ::= { pduDevMgmtEmdSlave12Entry 10 }

pduDevMgmtEmdSlave12TempHighWarn OBJECT-TYPE
        SYNTAX INTEGER (-200..1000)
        UNITS  "0.1degC"
        ACCESS read-write
        STATUS mandatory
        DESCRIPTION
                "The high warning threshold of temperature of emd."
        ::= { pduDevMgmtEmdSlave12Entry 11 }

pduDevMgmtEmdSlave12TempHighCrit OBJECT-TYPE
        SYNTAX INTEGER (-200..1000)
        UNITS  "0.1degC"
        ACCESS read-write
        STATUS mandatory
        DESCRIPTION
                "The high critical threshold of temperature of emd."
        ::= { pduDevMgmtEmdSlave12Entry 12 }

pduDevMgmtEmdSlave12TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave12Entry 13 }

pduDevMgmtEmdSlave12HumiLowWarn OBJECT-TYPE
        SYNTAX INTEGER (0..2120)
        UNITS  "0.1%"
        ACCESS read-write
        STATUS mandatory
        DESCRIPTION
                "The low warning threshold of humidity of emd."
        ::= { pduDevMgmtEmdSlave12Entry 15 }

pduDevMgmtEmdSlave12HumiLowCrit OBJECT-TYPE
        SYNTAX INTEGER (0..2120)
        UNITS  "0.1%"
        ACCESS read-write
        STATUS mandatory
        DESCRIPTION
                "The low critical threshold of humidity of emd."
        ::= { pduDevMgmtEmdSlave12Entry 16 }

pduDevMgmtEmdSlave12HumiHighWarn OBJECT-TYPE
        SYNTAX INTEGER (0..2120)
        UNITS  "0.1%"
        ACCESS read-write
        STATUS mandatory
        DESCRIPTION
                "The high warning threshold of humidity of emd."
        ::= { pduDevMgmtEmdSlave12Entry 17 }

pduDevMgmtEmdSlave12HumiHighCrit OBJECT-TYPE
        SYNTAX INTEGER (0..2120)
        UNITS  "0.1%"
        ACCESS read-write
        STATUS mandatory
        DESCRIPTION
                "The high critical threshold of humidity of emd."
        ::= { pduDevMgmtEmdSlave12Entry 18 }

pduDevMgmtEmdSlave12HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave12Entry 19 }

pduDevMgmtEmdSlave12Alarm1Setup OBJECT-TYPE
        SYNTAX INTEGER {
                disabled(1),
                no(2),
				nc(3)
                }
        ACCESS read-write
        STATUS mandatory
        DESCRIPTION
                "The alarm-1 setup of emd."
        ::= { pduDevMgmtEmdSlave12Entry 21 }

pduDevMgmtEmdSlave12Alarm2Setup OBJECT-TYPE
        SYNTAX INTEGER {
                disabled(1),
                no(2),
				nc(3)
                }
        ACCESS read-write
        STATUS mandatory
        DESCRIPTION
                "The alarm-2 setup of emd."
        ::= { pduDevMgmtEmdSlave12Entry 22 }


-- ===========================================================================
--
-- pduDevMgmtEmdSlave13
--
--  Slave13 Emd Mgmtoitor Group
--
-- ===========================================================================
pduDevMgmtEmdSlave13Table OBJECT-TYPE
        SYNTAX SEQUENCE OF PduDevMgmtEmdSlave13Entry
        ACCESS not-accessible
        STATUS mandatory
        DESCRIPTION
                "Display a list of the emd information of master."
        ::= { pduDevMgmtEmdSlave13 1}

pduDevMgmtEmdSlave13Entry OBJECT-TYPE
        SYNTAX PduDevMgmtEmdSlave13Entry
        ACCESS not-accessible
        STATUS mandatory
        DESCRIPTION
                "Display a list of the emd information of master."
        INDEX  { pduDevMgmtEmdSlave13Index}
        ::= { pduDevMgmtEmdSlave13Table 1 }

PduDevMgmtEmdSlave13Entry ::=
        SEQUENCE {
                pduDevMgmtEmdSlave13Index
                        INTEGER,
                pduDevMgmtEmdSlave13Valid
                        INTEGER,
                pduDevMgmtEmdSlave13Type
                        INTEGER,
                pduDevMgmtEmdSlave13Name
                        DisplayString,
                pduDevMgmtEmdSlave13TempName
                        DisplayString,
                pduDevMgmtEmdSlave13HumiName
                        DisplayString,
                pduDevMgmtEmdSlave13Alarm1Name
                        DisplayString,
                pduDevMgmtEmdSlave13Alarm2Name
                        DisplayString,
                pduDevMgmtEmdSlave13TempLowWarn
                        INTEGER,
                pduDevMgmtEmdSlave13TempLowCrit
                        INTEGER,
                pduDevMgmtEmdSlave13TempHighWarn
                        INTEGER,
                pduDevMgmtEmdSlave13TempHighCrit
                        INTEGER,
                pduDevMgmtEmdSlave13TempCali
                        INTEGER,
                pduDevMgmtEmdSlave13HumiLowWarn
                        INTEGER,
                pduDevMgmtEmdSlave13HumiLowCrit
                        INTEGER,
                pduDevMgmtEmdSlave13HumiHighWarn
                        INTEGER,
                pduDevMgmtEmdSlave13HumiHighCrit
                        INTEGER,
                pduDevMgmtEmdSlave13HumiCali
                        INTEGER,
                pduDevMgmtEmdSlave13Alarm1Setup
                        INTEGER,
                pduDevMgmtEmdSlave13Alarm2Setup
                        INTEGER
        }

pduDevMgmtEmdSlave13Index OBJECT-TYPE
        SYNTAX INTEGER (0..7)
        ACCESS read-only
        STATUS mandatory
        DESCRIPTION
                "The index to a emd entry."
        ::= { pduDevMgmtEmdSlave13Entry 1 }

pduDevMgmtEmdSlave13Valid OBJECT-TYPE
        SYNTAX INTEGER {
                offline(1),
                online(2)
                }
        ACCESS read-only
        STATUS mandatory
        DESCRIPTION
                "The online status of emd."
        ::= { pduDevMgmtEmdSlave13Entry 2 }


pduDevMgmtEmdSlave13Type OBJECT-TYPE
        SYNTAX INTEGER
        ACCESS read-only
        STATUS mandatory
        DESCRIPTION
                "The type of emd."
        ::= { pduDevMgmtEmdSlave13Entry 3 }

pduDevMgmtEmdSlave13Name OBJECT-TYPE
        SYNTAX DisplayString (SIZE(0..31))
        ACCESS read-write
        STATUS mandatory
        DESCRIPTION
                "The name of emd."
        ::= { pduDevMgmtEmdSlave13Entry 4 }

pduDevMgmtEmdSlave13TempName OBJECT-TYPE
        SYNTAX DisplayString (SIZE(0..31))
        ACCESS read-write
        STATUS mandatory
        DESCRIPTION
                "The name of emd temperature."
        ::= { pduDevMgmtEmdSlave13Entry 5 }

pduDevMgmtEmdSlave13HumiName OBJECT-TYPE
        SYNTAX DisplayString (SIZE(0..31))
        ACCESS read-write
        STATUS mandatory
        DESCRIPTION
                "The name of emd humidity."
        ::= { pduDevMgmtEmdSlave13Entry 6 }

pduDevMgmtEmdSlave13Alarm1Name OBJECT-TYPE
        SYNTAX DisplayString (SIZE(0..31))
        ACCESS read-write
        STATUS mandatory
        DESCRIPTION
                "The name of emd alarm-1."
        ::= { pduDevMgmtEmdSlave13Entry 7 }

pduDevMgmtEmdSlave13Alarm2Name OBJECT-TYPE
        SYNTAX DisplayString (SIZE(0..31))
        ACCESS read-write
        STATUS mandatory
        DESCRIPTION
                "The name of emd alarm-2."
        ::= { pduDevMgmtEmdSlave13Entry 8 }

pduDevMgmtEmdSlave13TempLowWarn OBJECT-TYPE
        SYNTAX INTEGER (-200..1000)
        UNITS  "0.1degC"
        ACCESS read-write
        STATUS mandatory
        DESCRIPTION
                "The low warning threshold of temperature of emd."
        ::= { pduDevMgmtEmdSlave13Entry 9 }

pduDevMgmtEmdSlave13TempLowCrit OBJECT-TYPE
        SYNTAX INTEGER (-200..1000)
        UNITS  "0.1degC"
        ACCESS read-write
        STATUS mandatory
        DESCRIPTION
                "The low critical threshold of temperature of emd."
        ::= { pduDevMgmtEmdSlave13Entry 10 }

pduDevMgmtEmdSlave13TempHighWarn OBJECT-TYPE
        SYNTAX INTEGER (-200..1000)
        UNITS  "0.1degC"
        ACCESS read-write
        STATUS mandatory
        DESCRIPTION
                "The high warning threshold of temperature of emd."
        ::= { pduDevMgmtEmdSlave13Entry 11 }

pduDevMgmtEmdSlave13TempHighCrit OBJECT-TYPE
        SYNTAX INTEGER (-200..1000)
        UNITS  "0.1degC"
        ACCESS read-write
        STATUS mandatory
        DESCRIPTION
                "The high critical threshold of temperature of emd."
        ::= { pduDevMgmtEmdSlave13Entry 12 }

pduDevMgmtEmdSlave13TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave13Entry 13 }

pduDevMgmtEmdSlave13HumiLowWarn OBJECT-TYPE
        SYNTAX INTEGER (0..2120)
        UNITS  "0.1%"
        ACCESS read-write
        STATUS mandatory
        DESCRIPTION
                "The low warning threshold of humidity of emd."
        ::= { pduDevMgmtEmdSlave13Entry 15 }

pduDevMgmtEmdSlave13HumiLowCrit OBJECT-TYPE
        SYNTAX INTEGER (0..2120)
        UNITS  "0.1%"
        ACCESS read-write
        STATUS mandatory
        DESCRIPTION
                "The low critical threshold of humidity of emd."
        ::= { pduDevMgmtEmdSlave13Entry 16 }

pduDevMgmtEmdSlave13HumiHighWarn OBJECT-TYPE
        SYNTAX INTEGER (0..2120)
        UNITS  "0.1%"
        ACCESS read-write
        STATUS mandatory
        DESCRIPTION
                "The high warning threshold of humidity of emd."
        ::= { pduDevMgmtEmdSlave13Entry 17 }

pduDevMgmtEmdSlave13HumiHighCrit OBJECT-TYPE
        SYNTAX INTEGER (0..2120)
        UNITS  "0.1%"
        ACCESS read-write
        STATUS mandatory
        DESCRIPTION
                "The high critical threshold of humidity of emd."
        ::= { pduDevMgmtEmdSlave13Entry 18 }

pduDevMgmtEmdSlave13HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave13Entry 19 }

pduDevMgmtEmdSlave13Alarm1Setup OBJECT-TYPE
        SYNTAX INTEGER {
                disabled(1),
                no(2),
				nc(3)
                }
        ACCESS read-write
        STATUS mandatory
        DESCRIPTION
                "The alarm-1 setup of emd."
        ::= { pduDevMgmtEmdSlave13Entry 21 }

pduDevMgmtEmdSlave13Alarm2Setup OBJECT-TYPE
        SYNTAX INTEGER {
                disabled(1),
                no(2),
				nc(3)
                }
        ACCESS read-write
        STATUS mandatory
        DESCRIPTION
                "The alarm-2 setup of emd."
        ::= { pduDevMgmtEmdSlave13Entry 22 }


-- ===========================================================================
--
-- pduDevMgmtEmdSlave14
--
--  Slave14 Emd Mgmtoitor Group
--
-- ===========================================================================
pduDevMgmtEmdSlave14Table OBJECT-TYPE
        SYNTAX SEQUENCE OF PduDevMgmtEmdSlave14Entry
        ACCESS not-accessible
        STATUS mandatory
        DESCRIPTION
                "Display a list of the emd information of master."
        ::= { pduDevMgmtEmdSlave14 1}

pduDevMgmtEmdSlave14Entry OBJECT-TYPE
        SYNTAX PduDevMgmtEmdSlave14Entry
        ACCESS not-accessible
        STATUS mandatory
        DESCRIPTION
                "Display a list of the emd information of master."
        INDEX  { pduDevMgmtEmdSlave14Index}
        ::= { pduDevMgmtEmdSlave14Table 1 }

PduDevMgmtEmdSlave14Entry ::=
        SEQUENCE {
                pduDevMgmtEmdSlave14Index
                        INTEGER,
                pduDevMgmtEmdSlave14Valid
                        INTEGER,
                pduDevMgmtEmdSlave14Type
                        INTEGER,
                pduDevMgmtEmdSlave14Name
                        DisplayString,
                pduDevMgmtEmdSlave14TempName
                        DisplayString,
                pduDevMgmtEmdSlave14HumiName
                        DisplayString,
                pduDevMgmtEmdSlave14Alarm1Name
                        DisplayString,
                pduDevMgmtEmdSlave14Alarm2Name
                        DisplayString,
                pduDevMgmtEmdSlave14TempLowWarn
                        INTEGER,
                pduDevMgmtEmdSlave14TempLowCrit
                        INTEGER,
                pduDevMgmtEmdSlave14TempHighWarn
                        INTEGER,
                pduDevMgmtEmdSlave14TempHighCrit
                        INTEGER,
                pduDevMgmtEmdSlave14TempCali
                        INTEGER,
                pduDevMgmtEmdSlave14HumiLowWarn
                        INTEGER,
                pduDevMgmtEmdSlave14HumiLowCrit
                        INTEGER,
                pduDevMgmtEmdSlave14HumiHighWarn
                        INTEGER,
                pduDevMgmtEmdSlave14HumiHighCrit
                        INTEGER,
                pduDevMgmtEmdSlave14HumiCali
                        INTEGER,
                pduDevMgmtEmdSlave14Alarm1Setup
                        INTEGER,
                pduDevMgmtEmdSlave14Alarm2Setup
                        INTEGER
        }

pduDevMgmtEmdSlave14Index OBJECT-TYPE
        SYNTAX INTEGER (0..7)
        ACCESS read-only
        STATUS mandatory
        DESCRIPTION
                "The index to a emd entry."
        ::= { pduDevMgmtEmdSlave14Entry 1 }

pduDevMgmtEmdSlave14Valid OBJECT-TYPE
        SYNTAX INTEGER {
                offline(1),
                online(2)
                }
        ACCESS read-only
        STATUS mandatory
        DESCRIPTION
                "The online status of emd."
        ::= { pduDevMgmtEmdSlave14Entry 2 }


pduDevMgmtEmdSlave14Type OBJECT-TYPE
        SYNTAX INTEGER
        ACCESS read-only
        STATUS mandatory
        DESCRIPTION
                "The type of emd."
        ::= { pduDevMgmtEmdSlave14Entry 3 }

pduDevMgmtEmdSlave14Name OBJECT-TYPE
        SYNTAX DisplayString (SIZE(0..31))
        ACCESS read-write
        STATUS mandatory
        DESCRIPTION
                "The name of emd."
        ::= { pduDevMgmtEmdSlave14Entry 4 }

pduDevMgmtEmdSlave14TempName OBJECT-TYPE
        SYNTAX DisplayString (SIZE(0..31))
        ACCESS read-write
        STATUS mandatory
        DESCRIPTION
                "The name of emd temperature."
        ::= { pduDevMgmtEmdSlave14Entry 5 }

pduDevMgmtEmdSlave14HumiName OBJECT-TYPE
        SYNTAX DisplayString (SIZE(0..31))
        ACCESS read-write
        STATUS mandatory
        DESCRIPTION
                "The name of emd humidity."
        ::= { pduDevMgmtEmdSlave14Entry 6 }

pduDevMgmtEmdSlave14Alarm1Name OBJECT-TYPE
        SYNTAX DisplayString (SIZE(0..31))
        ACCESS read-write
        STATUS mandatory
        DESCRIPTION
                "The name of emd alarm-1."
        ::= { pduDevMgmtEmdSlave14Entry 7 }

pduDevMgmtEmdSlave14Alarm2Name OBJECT-TYPE
        SYNTAX DisplayString (SIZE(0..31))
        ACCESS read-write
        STATUS mandatory
        DESCRIPTION
                "The name of emd alarm-2."
        ::= { pduDevMgmtEmdSlave14Entry 8 }

pduDevMgmtEmdSlave14TempLowWarn OBJECT-TYPE
        SYNTAX INTEGER (-200..1000)
        UNITS  "0.1degC"
        ACCESS read-write
        STATUS mandatory
        DESCRIPTION
                "The low warning threshold of temperature of emd."
        ::= { pduDevMgmtEmdSlave14Entry 9 }

pduDevMgmtEmdSlave14TempLowCrit OBJECT-TYPE
        SYNTAX INTEGER (-200..1000)
        UNITS  "0.1degC"
        ACCESS read-write
        STATUS mandatory
        DESCRIPTION
                "The low critical threshold of temperature of emd."
        ::= { pduDevMgmtEmdSlave14Entry 10 }

pduDevMgmtEmdSlave14TempHighWarn OBJECT-TYPE
        SYNTAX INTEGER (-200..1000)
        UNITS  "0.1degC"
        ACCESS read-write
        STATUS mandatory
        DESCRIPTION
                "The high warning threshold of temperature of emd."
        ::= { pduDevMgmtEmdSlave14Entry 11 }

pduDevMgmtEmdSlave14TempHighCrit OBJECT-TYPE
        SYNTAX INTEGER (-200..1000)
        UNITS  "0.1degC"
        ACCESS read-write
        STATUS mandatory
        DESCRIPTION
                "The high critical threshold of temperature of emd."
        ::= { pduDevMgmtEmdSlave14Entry 12 }

pduDevMgmtEmdSlave14TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave14Entry 13 }

pduDevMgmtEmdSlave14HumiLowWarn OBJECT-TYPE
        SYNTAX INTEGER (0..2120)
        UNITS  "0.1%"
        ACCESS read-write
        STATUS mandatory
        DESCRIPTION
                "The low warning threshold of humidity of emd."
        ::= { pduDevMgmtEmdSlave14Entry 15 }

pduDevMgmtEmdSlave14HumiLowCrit OBJECT-TYPE
        SYNTAX INTEGER (0..2120)
        UNITS  "0.1%"
        ACCESS read-write
        STATUS mandatory
        DESCRIPTION
                "The low critical threshold of humidity of emd."
        ::= { pduDevMgmtEmdSlave14Entry 16 }

pduDevMgmtEmdSlave14HumiHighWarn OBJECT-TYPE
        SYNTAX INTEGER (0..2120)
        UNITS  "0.1%"
        ACCESS read-write
        STATUS mandatory
        DESCRIPTION
                "The high warning threshold of humidity of emd."
        ::= { pduDevMgmtEmdSlave14Entry 17 }

pduDevMgmtEmdSlave14HumiHighCrit OBJECT-TYPE
        SYNTAX INTEGER (0..2120)
        UNITS  "0.1%"
        ACCESS read-write
        STATUS mandatory
        DESCRIPTION
                "The high critical threshold of humidity of emd."
        ::= { pduDevMgmtEmdSlave14Entry 18 }

pduDevMgmtEmdSlave14HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave14Entry 19 }

pduDevMgmtEmdSlave14Alarm1Setup OBJECT-TYPE
        SYNTAX INTEGER {
                disabled(1),
                no(2),
				nc(3)
                }
        ACCESS read-write
        STATUS mandatory
        DESCRIPTION
                "The alarm-1 setup of emd."
        ::= { pduDevMgmtEmdSlave14Entry 21 }

pduDevMgmtEmdSlave14Alarm2Setup OBJECT-TYPE
        SYNTAX INTEGER {
                disabled(1),
                no(2),
				nc(3)
                }
        ACCESS read-write
        STATUS mandatory
        DESCRIPTION
                "The alarm-2 setup of emd."
        ::= { pduDevMgmtEmdSlave14Entry 22 }


-- ===========================================================================
--
-- pduDevMgmtEmdSlave15
--
--  Slave15 Emd Mgmtoitor Group
--
-- ===========================================================================
pduDevMgmtEmdSlave15Table OBJECT-TYPE
        SYNTAX SEQUENCE OF PduDevMgmtEmdSlave15Entry
        ACCESS not-accessible
        STATUS mandatory
        DESCRIPTION
                "Display a list of the emd information of master."
        ::= { pduDevMgmtEmdSlave15 1}

pduDevMgmtEmdSlave15Entry OBJECT-TYPE
        SYNTAX PduDevMgmtEmdSlave15Entry
        ACCESS not-accessible
        STATUS mandatory
        DESCRIPTION
                "Display a list of the emd information of master."
        INDEX  { pduDevMgmtEmdSlave15Index}
        ::= { pduDevMgmtEmdSlave15Table 1 }

PduDevMgmtEmdSlave15Entry ::=
        SEQUENCE {
                pduDevMgmtEmdSlave15Index
                        INTEGER,
                pduDevMgmtEmdSlave15Valid
                        INTEGER,
                pduDevMgmtEmdSlave15Type
                        INTEGER,
                pduDevMgmtEmdSlave15Name
                        DisplayString,
                pduDevMgmtEmdSlave15TempName
                        DisplayString,
                pduDevMgmtEmdSlave15HumiName
                        DisplayString,
                pduDevMgmtEmdSlave15Alarm1Name
                        DisplayString,
                pduDevMgmtEmdSlave15Alarm2Name
                        DisplayString,
                pduDevMgmtEmdSlave15TempLowWarn
                        INTEGER,
                pduDevMgmtEmdSlave15TempLowCrit
                        INTEGER,
                pduDevMgmtEmdSlave15TempHighWarn
                        INTEGER,
                pduDevMgmtEmdSlave15TempHighCrit
                        INTEGER,
                pduDevMgmtEmdSlave15TempCali
                        INTEGER,
                pduDevMgmtEmdSlave15HumiLowWarn
                        INTEGER,
                pduDevMgmtEmdSlave15HumiLowCrit
                        INTEGER,
                pduDevMgmtEmdSlave15HumiHighWarn
                        INTEGER,
                pduDevMgmtEmdSlave15HumiHighCrit
                        INTEGER,
                pduDevMgmtEmdSlave15HumiCali
                        INTEGER,
                pduDevMgmtEmdSlave15Alarm1Setup
                        INTEGER,
                pduDevMgmtEmdSlave15Alarm2Setup
                        INTEGER
        }

pduDevMgmtEmdSlave15Index OBJECT-TYPE
        SYNTAX INTEGER (0..7)
        ACCESS read-only
        STATUS mandatory
        DESCRIPTION
                "The index to a emd entry."
        ::= { pduDevMgmtEmdSlave15Entry 1 }

pduDevMgmtEmdSlave15Valid OBJECT-TYPE
        SYNTAX INTEGER {
                offline(1),
                online(2)
                }
        ACCESS read-only
        STATUS mandatory
        DESCRIPTION
                "The online status of emd."
        ::= { pduDevMgmtEmdSlave15Entry 2 }


pduDevMgmtEmdSlave15Type OBJECT-TYPE
        SYNTAX INTEGER
        ACCESS read-only
        STATUS mandatory
        DESCRIPTION
                "The type of emd."
        ::= { pduDevMgmtEmdSlave15Entry 3 }

pduDevMgmtEmdSlave15Name OBJECT-TYPE
        SYNTAX DisplayString (SIZE(0..31))
        ACCESS read-write
        STATUS mandatory
        DESCRIPTION
                "The name of emd."
        ::= { pduDevMgmtEmdSlave15Entry 4 }

pduDevMgmtEmdSlave15TempName OBJECT-TYPE
        SYNTAX DisplayString (SIZE(0..31))
        ACCESS read-write
        STATUS mandatory
        DESCRIPTION
                "The name of emd temperature."
        ::= { pduDevMgmtEmdSlave15Entry 5 }

pduDevMgmtEmdSlave15HumiName OBJECT-TYPE
        SYNTAX DisplayString (SIZE(0..31))
        ACCESS read-write
        STATUS mandatory
        DESCRIPTION
                "The name of emd humidity."
        ::= { pduDevMgmtEmdSlave15Entry 6 }

pduDevMgmtEmdSlave15Alarm1Name OBJECT-TYPE
        SYNTAX DisplayString (SIZE(0..31))
        ACCESS read-write
        STATUS mandatory
        DESCRIPTION
                "The name of emd alarm-1."
        ::= { pduDevMgmtEmdSlave15Entry 7 }

pduDevMgmtEmdSlave15Alarm2Name OBJECT-TYPE
        SYNTAX DisplayString (SIZE(0..31))
        ACCESS read-write
        STATUS mandatory
        DESCRIPTION
                "The name of emd alarm-2."
        ::= { pduDevMgmtEmdSlave15Entry 8 }

pduDevMgmtEmdSlave15TempLowWarn OBJECT-TYPE
        SYNTAX INTEGER (-200..1000)
        UNITS  "0.1degC"
        ACCESS read-write
        STATUS mandatory
        DESCRIPTION
                "The low warning threshold of temperature of emd."
        ::= { pduDevMgmtEmdSlave15Entry 9 }

pduDevMgmtEmdSlave15TempLowCrit OBJECT-TYPE
        SYNTAX INTEGER (-200..1000)
        UNITS  "0.1degC"
        ACCESS read-write
        STATUS mandatory
        DESCRIPTION
                "The low critical threshold of temperature of emd."
        ::= { pduDevMgmtEmdSlave15Entry 10 }

pduDevMgmtEmdSlave15TempHighWarn OBJECT-TYPE
        SYNTAX INTEGER (-200..1000)
        UNITS  "0.1degC"
        ACCESS read-write
        STATUS mandatory
        DESCRIPTION
                "The high warning threshold of temperature of emd."
        ::= { pduDevMgmtEmdSlave15Entry 11 }

pduDevMgmtEmdSlave15TempHighCrit OBJECT-TYPE
        SYNTAX INTEGER (-200..1000)
        UNITS  "0.1degC"
        ACCESS read-write
        STATUS mandatory
        DESCRIPTION
                "The high critical threshold of temperature of emd."
        ::= { pduDevMgmtEmdSlave15Entry 12 }

pduDevMgmtEmdSlave15TempCali OBJECT-TYPE
        SYNTAX  INTEGER {
                pos5C4(1),
                pos4C5(2),
                pos3C6(3),
                pos2C7(4),
                pos1C8(5),
                pos0C9(6),
                pos0C(7),
                neg0C9(8),
                neg1C8(9),
                neg2C7(10),
                neg3C6(11),
                neg4C5(12),
                neg5C4(13)
                }
        UNITS  "degC"
        ACCESS read-write
        STATUS mandatory
        DESCRIPTION
                "The ofset of temperature of emd."
        ::= { pduDevMgmtEmdSlave15Entry 13 }

pduDevMgmtEmdSlave15HumiLowWarn OBJECT-TYPE
        SYNTAX INTEGER (0..2120)
        UNITS  "0.1%"
        ACCESS read-write
        STATUS mandatory
        DESCRIPTION
                "The low warning threshold of humidity of emd."
        ::= { pduDevMgmtEmdSlave15Entry 15 }

pduDevMgmtEmdSlave15HumiLowCrit OBJECT-TYPE
        SYNTAX INTEGER (0..2120)
        UNITS  "0.1%"
        ACCESS read-write
        STATUS mandatory
        DESCRIPTION
                "The low critical threshold of humidity of emd."
        ::= { pduDevMgmtEmdSlave15Entry 16 }

pduDevMgmtEmdSlave15HumiHighWarn OBJECT-TYPE
        SYNTAX INTEGER (0..2120)
        UNITS  "0.1%"
        ACCESS read-write
        STATUS mandatory
        DESCRIPTION
                "The high warning threshold of humidity of emd."
        ::= { pduDevMgmtEmdSlave15Entry 17 }

pduDevMgmtEmdSlave15HumiHighCrit OBJECT-TYPE
        SYNTAX INTEGER (0..2120)
        UNITS  "0.1%"
        ACCESS read-write
        STATUS mandatory
        DESCRIPTION
                "The high critical threshold of humidity of emd."
        ::= { pduDevMgmtEmdSlave15Entry 18 }

pduDevMgmtEmdSlave15HumiCali OBJECT-TYPE
        SYNTAX  INTEGER {
                pos6(1),
                pos5(2),
                pos4(3),
                pos3(4),
                pos2(5),
                pos1(6),
				none(7),
                neg1(8),
                neg2(9),
                neg3(10),
                neg4(11),
                neg5(12),
                neg6(13)
                }
        UNITS  "0.1%"
        ACCESS read-write
        STATUS mandatory
        DESCRIPTION
                "The ofset of humidity of emd."
        ::= { pduDevMgmtEmdSlave15Entry 19 }

pduDevMgmtEmdSlave15Alarm1Setup OBJECT-TYPE
        SYNTAX INTEGER {
                disabled(1),
                no(2),
				nc(3)
                }
        ACCESS read-write
        STATUS mandatory
        DESCRIPTION
                "The alarm-1 setup of emd."
        ::= { pduDevMgmtEmdSlave15Entry 21 }

pduDevMgmtEmdSlave15Alarm2Setup OBJECT-TYPE
        SYNTAX INTEGER {
                disabled(1),
                no(2),
				nc(3)
                }
        ACCESS read-write
        STATUS mandatory
        DESCRIPTION
                "The alarm-2 setup of emd."
        ::= { pduDevMgmtEmdSlave15Entry 22 }


-- ===========================================================================
--
-- pduNetwork
--
--  PDU Network Group
--
-- ===========================================================================
pduNetworkTcp           OBJECT IDENTIFIER ::= { pduNetwork 1 }
pduNetworkDualEth       OBJECT IDENTIFIER ::= { pduNetwork 2 }
pduNetworkAccessIp      OBJECT IDENTIFIER ::= { pduNetwork 3 }
pduNetworkSecurity      OBJECT IDENTIFIER ::= { pduNetwork 4 }
pduNetworkService       OBJECT IDENTIFIER ::= { pduNetwork 5 }
pduNetworkSnmpSetting   OBJECT IDENTIFIER ::= { pduNetwork 6 }
pduNetworkSnmpTrap      OBJECT IDENTIFIER ::= { pduNetwork 7 }

-- ===========================================================================
--
-- pduNetworkTcp
--
--  Network IPv4 Group
--
-- ===========================================================================
pduNetworkTcpIpv4DhcpEn OBJECT-TYPE
        SYNTAX INTEGER {
                disabled(1),
                enabled(2)
                }
        ACCESS read-write
        STATUS mandatory
        DESCRIPTION
                "Enable/disable DHCP protocol."
        ::= { pduNetworkTcp 1 }

pduNetworkTcpIpv4Address OBJECT-TYPE
        SYNTAX IpAddress
        ACCESS read-write
        STATUS mandatory
        DESCRIPTION
                "The ip address that NMS can identify the managed device."
        ::= { pduNetworkTcp 2 }

pduNetworkTcpIpv4Gateway OBJECT-TYPE
        SYNTAX IpAddress
        ACCESS read-write
        STATUS mandatory
        DESCRIPTION
                "The default gateway that allow device managed through routers."
        ::= { pduNetworkTcp 3 }

pduNetworkTcpIpv4Mask OBJECT-TYPE
        SYNTAX IpAddress
        ACCESS read-write
        STATUS mandatory
        DESCRIPTION
                "Internet address subnet mask."
        ::= { pduNetworkTcp 4 }

pduNetworkTcpIpv4Dns1 OBJECT-TYPE
        SYNTAX IpAddress
        ACCESS read-write
        STATUS mandatory
        DESCRIPTION
                "Internet address of Primary DNS Server."
        ::= { pduNetworkTcp 5 }

pduNetworkTcpIpv4Dns2 OBJECT-TYPE
        SYNTAX IpAddress
        ACCESS read-write
        STATUS mandatory
        DESCRIPTION
                "Internet address of Secondary DNS."
        ::= { pduNetworkTcp 6 }

pduNetworkTcpIpv6En OBJECT-TYPE
        SYNTAX INTEGER {
                disabled(1),
                enabled(2)
                }
        ACCESS read-write
        STATUS mandatory
        DESCRIPTION
                "Enable/disable IPv6 protocol."
        ::= { pduNetworkTcp 7 }

pduNetworkTcpIpv6AutoConfig OBJECT-TYPE
        SYNTAX INTEGER {
                automatic(1),
                dhcpv6(2),
				manual(3),
				disableIpv6(4)
                }
        ACCESS read-write
        STATUS mandatory
        DESCRIPTION
                "IPv6 Auto-config or Maual setting."
        ::= { pduNetworkTcp 8 }

pduNetworkTcpIpv6Address OBJECT-TYPE
        SYNTAX DisplayString (SIZE (0..63))
        ACCESS read-write
        STATUS mandatory
        DESCRIPTION
                "The ipv6 address that NMS can identify the managed device."
        ::= { pduNetworkTcp 9 }

pduNetworkTcpIpv6Prefix OBJECT-TYPE
        SYNTAX INTEGER
        ACCESS read-write
        STATUS mandatory
        DESCRIPTION
                "The prefix length for ipv6 address."
        ::= { pduNetworkTcp 10 }

pduNetworkTcpIpv6Router OBJECT-TYPE
        SYNTAX DisplayString (SIZE (0..63))
        ACCESS read-write
        STATUS mandatory
        DESCRIPTION
                "The default gateway that allow device managed through routers."
        ::= { pduNetworkTcp 11 }

pduNetworkTcpIpv6PrimaryDNS OBJECT-TYPE
        SYNTAX DisplayString (SIZE (0..63))
        ACCESS read-write
        STATUS mandatory
        DESCRIPTION
                "Internet address of Primary DNS Server"
        ::= { pduNetworkTcp 12 }

pduNetworkTcpIpv6SecondaryDNS OBJECT-TYPE
        SYNTAX DisplayString (SIZE (0..63))
        ACCESS read-write
        STATUS mandatory
        DESCRIPTION
                "Internet address of Secondary DNS"
        ::= { pduNetworkTcp 13 }

-- ===========================================================================
--
-- pduNetworkDualEth
--
--  Network Dual Ethernet Group
--
-- ===========================================================================
pduNetworkDualEthMode OBJECT-TYPE
        SYNTAX INTEGER {
                activeBackup(1),
                ieee8023ad(2),
                balanceAlb(3),
                bridge(4)
                }
        ACCESS read-write
        STATUS mandatory
        DESCRIPTION
                "Dual ethernet mode."
        ::= { pduNetworkDualEth 1 }

pduNetworkDualEthDownDelay OBJECT-TYPE
        SYNTAX INTEGER (1..100)
        ACCESS read-write
        STATUS mandatory
        DESCRIPTION
                "The down delay of ethernet mode."
        ::= { pduNetworkDualEth 2 }

pduNetworkDualEthUpDelay OBJECT-TYPE
        SYNTAX INTEGER (1..100)
        ACCESS read-write
        STATUS mandatory
        DESCRIPTION
                "The down delay of ethernet mode."
        ::= { pduNetworkDualEth 3 }

pduNetworkDualEthMiimon OBJECT-TYPE
        SYNTAX INTEGER (1..100)
        ACCESS read-write
        STATUS mandatory
        DESCRIPTION
                "The MII monitoring of ethernet mode."
        ::= { pduNetworkDualEth 4 }

pduNetworkDualEthPrimary OBJECT-TYPE
        SYNTAX INTEGER {
                eth1(1),
                eth2(2)
                }
        ACCESS read-write
        STATUS mandatory
        DESCRIPTION
                "The primary ethernet port, Only valid active-backup."
        ::= { pduNetworkDualEth 5 }


-- ===========================================================================
--
-- pduNetworkAccessIp
--
--  Accessible IP Group
--
-- ===========================================================================
pduNetworkAccessIpEn OBJECT-TYPE
        SYNTAX INTEGER {
                disabled(1),
                enabled(2)
                }
        ACCESS read-write
        STATUS mandatory
        DESCRIPTION
                "Enable/disable access ip table."
        ::= { pduNetworkAccessIp 1 }

pduNetworkAccessIpTable OBJECT-TYPE
        SYNTAX SEQUENCE OF PduNetworkAccessIpTblEntry
        ACCESS not-accessible
        STATUS mandatory
        DESCRIPTION
                "Display a list of access ip table of master."
        ::= { pduNetworkAccessIp 2}

pduNetworkAccessIpTblEntry OBJECT-TYPE
        SYNTAX PduNetworkAccessIpTblEntry
        ACCESS not-accessible
        STATUS mandatory
        DESCRIPTION
                "Display a list of access ip tablen of master."
        INDEX  { pduNetworkAccessIpTblIndex}
        ::= { pduNetworkAccessIpTable 1 }

PduNetworkAccessIpTblEntry ::=
        SEQUENCE {
                pduNetworkAccessIpTblIndex
                        INTEGER,
                pduNetworkAccessIpTblAddr
                        DisplayString,
                pduNetworkAccessIpTblPrefix
                        INTEGER,
                pduNetworkAccessIpTblAction
                        INTEGER
        }

pduNetworkAccessIpTblIndex OBJECT-TYPE
        SYNTAX INTEGER (0..15)
        ACCESS read-only
        STATUS mandatory
        DESCRIPTION
                "The index to a access ip entry."
        ::= { pduNetworkAccessIpTblEntry 1 }

pduNetworkAccessIpTblAddr OBJECT-TYPE
        SYNTAX DisplayString (SIZE (0..63))
        ACCESS read-write
        STATUS mandatory
        DESCRIPTION
                "The ip address of access ip."
        ::= { pduNetworkAccessIpTblEntry 2 }

pduNetworkAccessIpTblPrefix OBJECT-TYPE
        SYNTAX INTEGER
        ACCESS read-write
        STATUS mandatory
        DESCRIPTION
                "The prefix length of access ip."
        ::= { pduNetworkAccessIpTblEntry 3 }

pduNetworkAccessIpTblAction OBJECT-TYPE
        SYNTAX INTEGER {
                deny(1),
                allow(2)
                }
        ACCESS read-write
        STATUS mandatory
        DESCRIPTION
                "The action of access ip."
        ::= { pduNetworkAccessIpTblEntry 4 }

-- ===========================================================================
--
-- pduNetworkSecurity
--
--  Network Security Group
--
-- ===========================================================================
pduNetworkSecurityAccessProtectEn OBJECT-TYPE
        SYNTAX INTEGER {
               disable(1),
               enable(2)
               }
        ACCESS read-write
        STATUS mandatory
        DESCRIPTION
                "Enable/disable access protect function."
        ::= { pduNetworkSecurity 1 }

pduNetworkSecuritySshEn OBJECT-TYPE
        SYNTAX INTEGER {
               disable(1),
               enable(2)
               }
        ACCESS read-write
        STATUS mandatory
        DESCRIPTION
                "Enable/disable protect SSH function."
        ::= { pduNetworkSecurity 2 }

pduNetworkSecuritySshInterval OBJECT-TYPE
        SYNTAX INTEGER {
               value1Min(1),
               value5Min(2),
               value10Min(3),
               value30Min(4)
               }
        ACCESS read-write
        STATUS mandatory
        DESCRIPTION
                "The interval of protect SSH."
        ::= { pduNetworkSecurity 3 }

pduNetworkSecuritySshTime OBJECT-TYPE
        SYNTAX INTEGER {
               value5(1),
               value10(2),
               value20(3),
               value30(4),
               value100(5)
               }
        ACCESS read-write
        STATUS mandatory
        DESCRIPTION
                "The time of protect SSH."
        ::= { pduNetworkSecurity 4 }

pduNetworkSecuritySshBlock OBJECT-TYPE
        SYNTAX INTEGER {
               value1Min(1),
               value30Min(2),
               value1Hour(3),
               value1Day(4)
               }
        ACCESS read-write
        STATUS mandatory
        DESCRIPTION
                "The block time of protect SSH."
        ::= { pduNetworkSecurity 5 }

pduNetworkSecuritySnmpEn OBJECT-TYPE
        SYNTAX INTEGER {
               disable(1),
               enable(2)
               }
        ACCESS read-write
        STATUS mandatory
        DESCRIPTION
                "Enable/disable protect SNMP function."
        ::= { pduNetworkSecurity 6 }

pduNetworkSecuritySnmpInterval OBJECT-TYPE
        SYNTAX INTEGER {
               value1Min(1),
               value5Min(2),
               value10Min(3),
               value30Min(4)
               }
        ACCESS read-write
        STATUS mandatory
        DESCRIPTION
                "The interval of protect SNMP."
        ::= { pduNetworkSecurity 7 }

pduNetworkSecuritySnmpTime OBJECT-TYPE
        SYNTAX INTEGER {
               value5(1),
               value10(2),
               value20(3),
               value30(4),
               value100(5)
               }
        ACCESS read-write
        STATUS mandatory
        DESCRIPTION
                "The time of protect SNMP."
        ::= { pduNetworkSecurity 8 }

pduNetworkSecuritySnmpBlock OBJECT-TYPE
        SYNTAX INTEGER {
               value1Min(1),
               value30Min(2),
               value1Hour(3),
               value1Day(4)
               }
        ACCESS read-write
        STATUS mandatory
        DESCRIPTION
                "The block time of protect SNMP."
        ::= { pduNetworkSecurity 9 }

pduNetworkSecurityHttpEn OBJECT-TYPE
        SYNTAX INTEGER {
               disable(1),
               enable(2)
               }
        ACCESS read-write
        STATUS mandatory
        DESCRIPTION
                "Enable/disable protect HTTP(s) function."
        ::= { pduNetworkSecurity 10 }

pduNetworkSecurityHttpInterval OBJECT-TYPE
        SYNTAX INTEGER {
               value1Min(1),
               value5Min(2),
               value10Min(3),
               value30Min(4)
               }
        ACCESS read-write
        STATUS mandatory
        DESCRIPTION
                "The interval of protect HTTP(s)."
        ::= { pduNetworkSecurity 11 }

pduNetworkSecurityHttpTime OBJECT-TYPE
        SYNTAX INTEGER {
               value5(1),
               value10(2),
               value20(3),
               value30(4),
               value100(5)
               }
        ACCESS read-write
        STATUS mandatory
        DESCRIPTION
                "The time of protect HTTP(s)."
        ::= { pduNetworkSecurity 12 }

pduNetworkSecurityHttpBlock OBJECT-TYPE
        SYNTAX INTEGER {
               value1Min(1),
               value30Min(2),
               value1Hour(3),
               value1Day(4)
               }
        ACCESS read-write
        STATUS mandatory
        DESCRIPTION
                "The block time of protect HTTP(s)."
        ::= { pduNetworkSecurity 13 }


-- ===========================================================================
--
-- pduNetworkService
--
--  Network Service Group
--
-- ===========================================================================
pduNetworkServiceSsh        OBJECT IDENTIFIER ::= { pduNetworkService 1 }
pduNetworkServiceHttps      OBJECT IDENTIFIER ::= { pduNetworkService 2 }
pduNetworkServicePing       OBJECT IDENTIFIER ::= { pduNetworkService 3 }
pduNetworkServiceModbus     OBJECT IDENTIFIER ::= { pduNetworkService 4 }
pduNetworkServiceRadius     OBJECT IDENTIFIER ::= { pduNetworkService 5 }
pduNetworkServiceLdap       OBJECT IDENTIFIER ::= { pduNetworkService 6 }
pduNetworkServiceTacacs     OBJECT IDENTIFIER ::= { pduNetworkService 7 }


-- ===========================================================================
--
-- pduNetworkServiceSsh
--
--  Network SSH Service Group
--
-- ===========================================================================
pduNetworkServiceSshEn OBJECT-TYPE
        SYNTAX INTEGER {
               disable(1),
               enable(2)
               }
        ACCESS read-write
        STATUS mandatory
        DESCRIPTION
                "Enable/disable SSH Server Service."
        ::= { pduNetworkServiceSsh 1 }

pduNetworkServiceSshPort OBJECT-TYPE
        SYNTAX INTEGER (0..65535)
        ACCESS read-write
        STATUS mandatory
        DESCRIPTION
                "The Port Number of SSH Server Service."
        ::= { pduNetworkServiceSsh 2 }


-- ===========================================================================
--
-- pduNetworkServiceHttps
--
--  Network HTTPs Service Group
--
-- ===========================================================================
pduNetworkServiceHttpsEn OBJECT-TYPE
        SYNTAX INTEGER {
               disable(1),
               enable(2)
               }
        ACCESS read-write
        STATUS mandatory
        DESCRIPTION
                "Enable/disable HTTPs Server Service."
        ::= { pduNetworkServiceHttps 1 }

pduNetworkServiceHttpsPort OBJECT-TYPE
        SYNTAX INTEGER (0..65535)
        ACCESS read-write
        STATUS mandatory
        DESCRIPTION
                "The Port Number of HTTPs Server Service."
        ::= { pduNetworkServiceHttps 2 }

pduNetworkServiceHttpsForce OBJECT-TYPE
        SYNTAX INTEGER {
               disable(1),
               enable(2)
               }
        ACCESS read-write
        STATUS mandatory
        DESCRIPTION
                "Force use HTTPs Server Service only."
        ::= { pduNetworkServiceHttps 3 }


-- ===========================================================================
--
-- pduNetworkServicePing
--
--  Network Ping Service Group
--
-- ===========================================================================
pduNetworkServicePingEn OBJECT-TYPE
        SYNTAX INTEGER {
               disable(1),
               enable(2)
               }
        ACCESS read-write
        STATUS mandatory
        DESCRIPTION
                "Enable/disable to response to PING request."
        ::= { pduNetworkServicePing 1 }


-- ===========================================================================
--
-- pduNetworkServiceModbus
--
--  Network Modbus Service Group
--
-- ===========================================================================
pduNetworkServiceModbusEn OBJECT-TYPE
        SYNTAX INTEGER {
               disable(1),
               enable(2)
               }
        ACCESS read-write
        STATUS mandatory
        DESCRIPTION
                "Enable/disable Modbus Server Service."
        ::= { pduNetworkServiceModbus 1 }

pduNetworkServiceModbusPort OBJECT-TYPE
        SYNTAX INTEGER (0..65535)
        ACCESS read-write
        STATUS mandatory
        DESCRIPTION
                "The Port Number of Modbus Server Service."
        ::= { pduNetworkServiceModbus 2 }


-- ===========================================================================
--
-- pduNetworkServiceRadius
--
--  Network RADIUS Client Group
--
-- ===========================================================================
pduNetworkServiceRadiusEn OBJECT-TYPE
        SYNTAX INTEGER {
               disable(1),
               enable(2)
               }
        ACCESS read-write
        STATUS mandatory
        DESCRIPTION
                "Enable/disable RADIUS Client Service."
        ::= { pduNetworkServiceRadius 1 }

pduNetworkServiceRadiusIp OBJECT-TYPE
        SYNTAX DisplayString (SIZE (0..63))
        ACCESS read-write
        STATUS mandatory
        DESCRIPTION
                "The IP Address of RADIUS Client Service."
        ::= { pduNetworkServiceRadius 2 }

pduNetworkServiceRadiusPort OBJECT-TYPE
        SYNTAX INTEGER
        ACCESS read-write
        STATUS mandatory
        DESCRIPTION
                "The Port Number of RADIUS Client Service."
        ::= { pduNetworkServiceRadius 3 }

pduNetworkServiceRadiusSecKey OBJECT-TYPE
        SYNTAX DisplayString (SIZE (0..63))
        ACCESS read-write
        STATUS mandatory
        DESCRIPTION
                "The Secret Key of RADIUS Client Service."
        ::= { pduNetworkServiceRadius 4 }

pduNetworkServiceRadiusTimeout OBJECT-TYPE
        SYNTAX INTEGER
        ACCESS read-write
        STATUS mandatory
        DESCRIPTION
                "The Timeout Interval of RADIUS Client Service in seconds."
        ::= { pduNetworkServiceRadius 5 }

pduNetworkServiceRadiusRetry OBJECT-TYPE
        SYNTAX INTEGER
        ACCESS read-write
        STATUS mandatory
        DESCRIPTION
                "The Retry Times of RADIUS Client Service."
        ::= { pduNetworkServiceRadius 6 }

-- ===========================================================================
--
-- pduNetworkServiceLdap
--
--  Network LDAP Client Group
--
-- ===========================================================================
pduNetworkServiceLdapEn OBJECT-TYPE
        SYNTAX INTEGER {
               disable(1),
               enable(2)
               }
        ACCESS read-write
        STATUS mandatory
        DESCRIPTION
                "Enable/disable LDAP Client Service."
        ::= { pduNetworkServiceLdap 1 }

pduNetworkServiceLdapIp OBJECT-TYPE
        SYNTAX DisplayString (SIZE (0..63))
        ACCESS read-write
        STATUS mandatory
        DESCRIPTION
                "The IP Address of LDAP Client Service."
        ::= { pduNetworkServiceLdap 2 }

pduNetworkServiceLdapPort OBJECT-TYPE
        SYNTAX INTEGER
        ACCESS read-write
        STATUS mandatory
        DESCRIPTION
                "The Port Number of LDAP Client Service."
        ::= { pduNetworkServiceLdap 3 }

pduNetworkServiceLdapTls OBJECT-TYPE
        SYNTAX INTEGER {
               disable(1),
               enable(2)
               }
        ACCESS read-write
        STATUS mandatory
        DESCRIPTION
                "Enable/disable LDAP TLS connection."
        ::= { pduNetworkServiceLdap 4 }

pduNetworkServiceLdapBaseDn OBJECT-TYPE
        SYNTAX DisplayString (SIZE (0..127))
        ACCESS read-write
        STATUS mandatory
        DESCRIPTION
                "The Base DN of LDAP Client Service."
        ::= { pduNetworkServiceLdap 5 }


-- ===========================================================================
--
-- pduNetworkServiceTacacs
--
--  Network TACACS+ Client Group
--
-- ===========================================================================
pduNetworkServiceTacacsEn OBJECT-TYPE
        SYNTAX INTEGER {
               disable(1),
               enable(2)
               }
        ACCESS read-write
        STATUS mandatory
        DESCRIPTION
                "Enable/disable TACACS+ Client Service."
        ::= { pduNetworkServiceTacacs 1 }

pduNetworkServiceTacacsIp OBJECT-TYPE
        SYNTAX DisplayString (SIZE (0..63))
        ACCESS read-write
        STATUS mandatory
        DESCRIPTION
                "The IP Address of TACACS+ Client Service."
        ::= { pduNetworkServiceTacacs 2 }

pduNetworkServiceTacacsPort OBJECT-TYPE
        SYNTAX INTEGER
        ACCESS read-write
        STATUS mandatory
        DESCRIPTION
                "The Port Number of TACACS+ Client Service."
        ::= { pduNetworkServiceTacacs 3 }

pduNetworkServiceTacacsSecKey OBJECT-TYPE
        SYNTAX DisplayString (SIZE (0..31))
        ACCESS read-write
        STATUS mandatory
        DESCRIPTION
                "The Secret Key of TACACS+ Client Service."
        ::= { pduNetworkServiceTacacs 4 }

pduNetworkServiceTacacsTimeout OBJECT-TYPE
        SYNTAX INTEGER
        ACCESS read-write
        STATUS mandatory
        DESCRIPTION
                "The Timeout Interval of TACACS+ Client Service in seconds."
        ::= { pduNetworkServiceTacacs 5 }

pduNetworkServiceTacacsRetry OBJECT-TYPE
        SYNTAX INTEGER
        ACCESS read-write
        STATUS mandatory
        DESCRIPTION
                "The Retry Times of TACACS+ Client Service."
        ::= { pduNetworkServiceTacacs 6 }

pduNetworkServiceTacacsAuthMode OBJECT-TYPE
        SYNTAX INTEGER {
               ascii(1),
               pap(2),
			   chap(3)
               }
        ACCESS read-write
        STATUS mandatory
        DESCRIPTION
                "The Authentication Mode of TACACS+ Client Service."
        ::= { pduNetworkServiceTacacs 7 }

-- ===========================================================================
--
-- pduNetworkSnmpSetting
--
--  SNMP Setting Group
--
-- ===========================================================================
pduNetworkSnmpSettingEn OBJECT-TYPE
        SYNTAX INTEGER {
               disable(1),
               enable(2)
               }
        ACCESS read-write
        STATUS mandatory
        DESCRIPTION
                "Enable/disable SNMP Server Service."
        ::= { pduNetworkSnmpSetting 1 }

pduNetworkSnmpSettingPort OBJECT-TYPE
        SYNTAX INTEGER
        ACCESS read-write
        STATUS mandatory
        DESCRIPTION
                "The Port Number of SNMP Server Service."
        ::= { pduNetworkSnmpSetting 2 }

-- ===========================================================================
--
-- pduNetworkSnmpTrap
--
--  SNMP Trap Group
--
-- ===========================================================================
pduNetworkSnmpTrapTable OBJECT-TYPE
        SYNTAX SEQUENCE OF PduNetworkSnmpTrapEntry
        ACCESS not-accessible
        STATUS mandatory
        DESCRIPTION
                "Display a list of the emd information of master."
        ::= { pduNetworkSnmpTrap 1}

pduNetworkSnmpTrapEntry OBJECT-TYPE
        SYNTAX PduNetworkSnmpTrapEntry
        ACCESS not-accessible
        STATUS mandatory
        DESCRIPTION
                "Display a list of the emd information of master."
        INDEX  { pduNetworkSnmpTrapIndex}
        ::= { pduNetworkSnmpTrapTable 1 }

PduNetworkSnmpTrapEntry ::=
        SEQUENCE {
                pduNetworkSnmpTrapIndex
                        INTEGER,
                pduNetworkSnmpTrapIp
                        DisplayString,
                pduNetworkSnmpTrapEvtLev
                        INTEGER,
                pduNetworkSnmpTrapVer
                        INTEGER,
                pduNetworkSnmpTrapDesc
                        DisplayString
        }

pduNetworkSnmpTrapIndex OBJECT-TYPE
        SYNTAX INTEGER (0..15)
        ACCESS read-only
        STATUS mandatory
        DESCRIPTION
                "The index to a trap receiver entry."
        ::= { pduNetworkSnmpTrapEntry 1 }

pduNetworkSnmpTrapIp OBJECT-TYPE
        SYNTAX DisplayString (SIZE(0..63))
        ACCESS read-write
        STATUS mandatory
        DESCRIPTION
                "The IP address of the manager to send a trap to."
        ::= { pduNetworkSnmpTrapEntry 2 }

pduNetworkSnmpTrapEvtLev OBJECT-TYPE
        SYNTAX INTEGER {
                critical(1),
                warning(2),
                informational(3)
                }
        ACCESS read-write
        STATUS mandatory
        DESCRIPTION
                "The severity level of traps to be received by this manager."
        ::= { pduNetworkSnmpTrapEntry 3 }

pduNetworkSnmpTrapVer OBJECT-TYPE
        SYNTAX INTEGER {
                v1(1),
                v2(2),
                v3(3)
                }
        ACCESS read-write
        STATUS mandatory
        DESCRIPTION
                "The SNMP Trap version of trap receivers."
        ::= { pduNetworkSnmpTrapEntry 4 }

pduNetworkSnmpTrapDesc OBJECT-TYPE
        SYNTAX DisplayString (SIZE(0..31))
        ACCESS read-write
        STATUS mandatory
        DESCRIPTION
                "Description of trap receivers."
        ::= { pduNetworkSnmpTrapEntry 5 }

-- ===========================================================================
--
-- pduSetting
--
--  PDU Setting Group
--
-- ===========================================================================
pduSettingSys           OBJECT IDENTIFIER ::= { pduSetting 1 }
pduSettingTime          OBJECT IDENTIFIER ::= { pduSetting 2 }
pduSettingNtp           OBJECT IDENTIFIER ::= { pduSetting 3 }
pduSettingAuth          OBJECT IDENTIFIER ::= { pduSetting 4 }
pduSettingiEC           OBJECT IDENTIFIER ::= { pduSetting 5 }
pduSettingMaint         OBJECT IDENTIFIER ::= { pduSetting 6 }
pduSettingSmtp          OBJECT IDENTIFIER ::= { pduSetting 7 }
pduSettingMailNotify    OBJECT IDENTIFIER ::= { pduSetting 8 }


-- ===========================================================================
--
-- pduSettingSys
--
--  PDU System Setting Group
--
-- ===========================================================================
pduSettingSysName OBJECT-TYPE
        SYNTAX DisplayString (SIZE(0..31))
        ACCESS read-write
        STATUS mandatory
        DESCRIPTION
                "The name of system."
        ::= { pduSettingSys 1 }

pduSettingSysContact OBJECT-TYPE
        SYNTAX DisplayString (SIZE(0..31))
        ACCESS read-write
        STATUS mandatory
        DESCRIPTION
                "The contact of system."
        ::= { pduSettingSys 2 }

pduSettingSysLocation OBJECT-TYPE
        SYNTAX DisplayString (SIZE(0..31))
        ACCESS read-write
        STATUS mandatory
        DESCRIPTION
                "The location of system."
        ::= { pduSettingSys 3 }

pduSettingLogInterval OBJECT-TYPE
        SYNTAX INTEGER (5..28800)
        ACCESS read-write
        STATUS mandatory
        DESCRIPTION
                "The Log Interval of system."
        ::= { pduSettingSys 4 }

pduSettingWebRefresh OBJECT-TYPE
        SYNTAX INTEGER (3..60)
        ACCESS read-write
        STATUS mandatory
        DESCRIPTION
                "The Web Refresh Interval of system."
        ::= { pduSettingSys 5 }


-- ===========================================================================
--
-- pduSettingTime
--
--  PDU Time Setting Group
--
-- ===========================================================================
pduSettingNowTime OBJECT-TYPE
        SYNTAX DisplayString
        ACCESS read-only
        STATUS mandatory
        DESCRIPTION
                "The date/time in agent"
        ::= { pduSettingTime 1 }

pduSettingTimeZone OBJECT-TYPE
        SYNTAX INTEGER {
                    gMT-1200InternationalDateLineWest(1),
                    gMT-1200Eniwetok-Kwajalein(2),
                    gMT-1100MidwayIsland-Samoa(3),
                    gMT-1000Hawaii(4),
                    gMT-0900Alaska(5),
                    gMT-0800PacificTime-Tijuana(6),
                    gMT-0700Arizona-MountainTime(7),
                    gMT-0700Chihuahua-LaPaz-Mazatlan(8),
                    gMT-0700MountainTime(9),
                    gMT-0600CentralAmerica(10),
                    gMT-0600CentralTime(11),
                    gMT-0600Guadalajara-MexicoCity-Monterrey(12),
                    gMT-0600Saskatchewan(13),
                    gMT-0500Bogota-Lima-Quito(14),
                    gMT-0500EasternTime(15),
                    gMT-0500Indiana(16),
                    gMT-0400AtlanticTime(17),
                    gMT-0400Caracas-LaPaz(18),
                    gMT-0400Santiago(19),
                    gMT-0330Newfoundland(20),
                    gMT-0300Brasilia(21),
                    gMT-0300BuenosAires-Georgetown(22),
                    gMT-0300Greenland(23),
                    gMT-0200Mid-Atlantic(24),
                    gMT-0100Azores(25),
                    gMT-0100CapeVerdeIs(26),
                    gMT-0000Casablanca-Monrovia(27),
                    gMT-0000GreenwichMeanTime-Dublin-Edinburgh-Lisbon-London(28),
                    gMT0100Amsterdam-Berlin-Bern-Rome-Stockholm-Vienna(29),
                    gMT0100Belgrade-Bratislava-Budapest-Ljubljana-Prague(30),
                    gMT0100Brussels-Copenhagen-Madrid-Paris(31),
                    gMT0100Sarajevo-Skopje-Warsaw-Zagreb(32),
                    gMT0100WestCentralAfrica(33),
                    gMT0200Athens-Istanbul-Minsk(34),
                    gMT0200Bucharest(35),
                    gMT0200Cairo(36),
                    gMT0200Harare-Pretoria(37),
                    gMT0200Helsinki-Kyiv-Riga-Sofia-Tallinn-Vilnius(38),
                    gMT0200Jerusalem(39),
                    gMT0300Baghdad(40),
                    gMT0300Kuwait-Riyadh(41),
                    gMT0300Moscow-StPetersburg-Volgograd(42),
                    gMT0300Nairobi(43),
                    gMT0330Tehran(44),
                    gMT0400AbuDhabi-Muscat(45),
                    gMT0400Baku-Tbilisi-Yerevan(46),
                    gMT0430Kabul(47),
                    gMT0500Ekaterinburg(48),
                    gMT0500Islamabad-Karachi-Tashkent(49),
                    gMT0530Bombay-Calcutta(50),
                    gMT0530Chennai-Kolkata-Mumbai-NewDelhi(51),
                    gMT0545Kathmandu(52),
                    gMT0600Almaty-Novosibirsk(53),
                    gMT0600Astana-Dhaka(54),
                    gMT0600SriJayawardenepura(55),
                    gMT0630Rangoon(56),
                    gMT0700Bangkok-Hanoi-Jakarta(57),
                    gMT0700Krasnoyarsk(58),
                    gMT0800Beijing-Chongqing-HongKong-Urumqi(59),
                    gMT0800Irkutsk-UlaanBataar(60),
                    gMT0800KualaLumpur-Singapore(61),
                    gMT0800Perth(62),
                    gMT0800Taipei(63),
                    gMT0900Osaka-Sapporo-Tokyo(64),
                    gMT0900Seoul(65),
                    gMT0900Yakutsk(66),
                    gMT0930Adelaide(67),
                    gMT0930Darwin(68),
                    gMT1000Brisbane(69),
                    gMT1000Canberra-Melbourne-Sydney(70),
                    gMT1000Guam-PortMoresby(71),
                    gMT1000Hobart(72),
                    gMT1000Vladivostok(73),
                    gMT1100Magadan-SolomonIs-NewCaledonia(74),
                    gMT1200Auckland-Wellington(75),
                    gMT1200Fiji-Kamchatka-MarshallIs(76),
                    gMT1300NukuAlofa(77)
                }
        ACCESS read-write
        STATUS mandatory
        DESCRIPTION
                "Time Zone to use when synchronize with NTP server."
        ::= { pduSettingTime 2 }

pduSettingTimeFormat OBJECT-TYPE
        SYNTAX INTEGER {
                ddmmyyyy(1),
                mmddyyyy(2),
                yyyymmdd(3)
                }
        ACCESS read-write
        STATUS mandatory
        DESCRIPTION
                "Date Format"
        ::= { pduSettingTime 3 }

pduSettingTimeManualDate OBJECT-TYPE
        SYNTAX DisplayString (SIZE (10..10))
        ACCESS read-write
        STATUS mandatory
        DESCRIPTION
                "The date in agent, format is (dd/mm/yyyy)"
        ::= { pduSettingTime 5 }

pduSettingTimeManualTime OBJECT-TYPE
        SYNTAX DisplayString (SIZE (8..8))
        ACCESS read-write
        STATUS mandatory
        DESCRIPTION
                "The time in agent, format is (hh:mm:ss)"
        ::= { pduSettingTime 6 }

pduSettingTimeDayLightSaving OBJECT-TYPE
        SYNTAX INTEGER {
                disabled(1),
                enabled(2)
                }
        ACCESS read-write
        STATUS mandatory
        DESCRIPTION
                "Enable/disable the Day Light Saving when synchronize with NTP server."
        ::= { pduSettingTime 7 }


-- ===========================================================================
--
-- pduSettingNtp
--
--  PDU NTP Client Setting Group
--
-- ===========================================================================
pduSettingNtpEn OBJECT-TYPE
        SYNTAX INTEGER {
                disabled(1),
                enabled(2)
                }
        ACCESS read-write
        STATUS mandatory
        DESCRIPTION
                "Enable or disable the agent to synchronize date/time with NTP server."
        ::= { pduSettingNtp 1 }

pduSettingNtpServer OBJECT-TYPE
       SYNTAX DisplayString (SIZE (0..63))
       ACCESS read-write
       STATUS mandatory
       DESCRIPTION
               "The ip address of NTP server."
       ::= { pduSettingNtp 2 }

pduSettingNtpSyncInterval OBJECT-TYPE
       SYNTAX INTEGER (1..99)
       ACCESS read-write
       STATUS mandatory
       DESCRIPTION
               "The Sync Interval with NTP server."
       ::= { pduSettingNtp 3 }

pduSettingNtpSyncUnit OBJECT-TYPE
        SYNTAX INTEGER {
                day(1),
                month(2)
                }
        ACCESS read-write
        STATUS mandatory
        DESCRIPTION
                "The Unit of Sync Interval"
        ::= { pduSettingNtp 4 }


-- ===========================================================================
--
-- pduSettingAuth
--
--  PDU Authentication Confuguration Group
--
-- ===========================================================================
pduSettingAuthAdminName OBJECT-TYPE
       SYNTAX DisplayString (SIZE (0..31))
       ACCESS read-write
       STATUS mandatory
       DESCRIPTION
               "The admin name of system."
       ::= { pduSettingAuth 1 }

pduSettingAuthAdminPasswd OBJECT-TYPE
       SYNTAX DisplayString (SIZE (0..31))
       ACCESS read-write
       STATUS mandatory
       DESCRIPTION
               "The admin password of system."
       ::= { pduSettingAuth 2 }

-- ===========================================================================
--
-- pduSettingiEC
--
--  PDU iEC Setting Group
--
-- ===========================================================================
pduSettingiECEn OBJECT-TYPE
        SYNTAX INTEGER {
                disabled(1),
                enabled(2)
                }
        ACCESS read-write
        STATUS mandatory
        DESCRIPTION
                "Enable/disable iEC function."
        ::= { pduSettingiEC 1 }

pduSettingiECServer OBJECT-TYPE
       SYNTAX DisplayString (SIZE (0..63))
       ACCESS read-write
       STATUS mandatory
       DESCRIPTION
               "The ip address of iEC server."
       ::= { pduSettingiEC 2 }

pduSettingiECPort OBJECT-TYPE
       SYNTAX INTEGER
       ACCESS read-write
       STATUS mandatory
       DESCRIPTION
               "The port number of iEC server."
       ::= { pduSettingiEC 3 }

pduSettingiECPasswd OBJECT-TYPE
       SYNTAX DisplayString (SIZE (0..63))
       ACCESS read-write
       STATUS mandatory
       DESCRIPTION
               "The password of iEC server."
       ::= { pduSettingiEC 4 }


-- ===========================================================================
--
-- pduSettingMaint
--
--  PDU System Maintenance Group
--
-- ===========================================================================
pduSettingMaintResetToDefault OBJECT-TYPE
        SYNTAX INTEGER {
                nothing(1),
                resetToDefaultWithoutIp(2),
                reboot(3)
                }
        ACCESS read-write
        STATUS mandatory
        DESCRIPTION
                "Reset the parameter of PDU to default."
        ::= { pduSettingMaint 1 }

-- ===========================================================================
--
-- pduSettingSmtp
--
--  PDU Smtp Setting Group
--
-- ===========================================================================
pduSettingSmtpIp OBJECT-TYPE
       SYNTAX DisplayString (SIZE (0..63))
       ACCESS read-write
       STATUS mandatory
       DESCRIPTION
               "The address of Email server."
       ::= { pduSettingSmtp 1 }

pduSettingSmtpPort OBJECT-TYPE
       SYNTAX INTEGER
       ACCESS read-write
       STATUS mandatory
       DESCRIPTION
               "The UDP port for Email Server."
       ::= { pduSettingSmtp 2 }

pduSettingSmtpSender OBJECT-TYPE
       SYNTAX DisplayString (SIZE (0..63))
       ACCESS read-write
       STATUS mandatory
       DESCRIPTION
               "The sender's Email address."
       ::= { pduSettingSmtp 3 }

pduSettingSmtpSubject OBJECT-TYPE
       SYNTAX DisplayString (SIZE (0..63))
       ACCESS read-write
       STATUS mandatory
       DESCRIPTION
               "The prefix string of mail subject"
       ::= { pduSettingSmtp 4 }

pduSettingSmtpAuthEn OBJECT-TYPE
        SYNTAX INTEGER {
                disabled(1),
                enabled(2)
                }
        ACCESS read-write
        STATUS mandatory
        DESCRIPTION
                "Enable/disable SMTP Authentication."
        ::= { pduSettingSmtp 5 }

pduSettingSmtpAuthUser OBJECT-TYPE
       SYNTAX DisplayString (SIZE (0..63))
       ACCESS read-write
       STATUS mandatory
       DESCRIPTION
               "The user name of SMTP Authentication."
       ::= { pduSettingSmtp 6 }

pduSettingSmtpAuthPasswd OBJECT-TYPE
       SYNTAX DisplayString (SIZE (0..63))
       ACCESS read-write
       STATUS mandatory
       DESCRIPTION
               "The password of SMTP Authentication."
       ::= { pduSettingSmtp 7 }


-- ===========================================================================
--
-- pduSettingMailNotify
--
--  PDU Mail Notify Setting Group
--
-- ===========================================================================

pduSettingMailNotifyTable OBJECT-TYPE
        SYNTAX SEQUENCE OF PduSettingMailNotifyEntry
        ACCESS not-accessible
        STATUS mandatory
        DESCRIPTION
                "A list of managers to send email notification to."
        ::= { pduSettingMailNotify 1}

pduSettingMailNotifyEntry OBJECT-TYPE
        SYNTAX PduSettingMailNotifyEntry
        ACCESS not-accessible
        STATUS mandatory
        DESCRIPTION
                "The managers to send email notification to."
        INDEX  { pduSettingMailNotifyIndex}
        ::= { pduSettingMailNotifyTable 1 }

PduSettingMailNotifyEntry ::=
        SEQUENCE {
                pduSettingMailNotifyIndex
                        INTEGER,
                pduSettingMailNotifyRecvAddr
                        DisplayString,
                pduSettingMailNotifyType
                        INTEGER,
                pduSettingMailNotifyEvtLev
                        INTEGER,
                pduSettingMailNotifyDesc
                        DisplayString
        }

pduSettingMailNotifyIndex OBJECT-TYPE
        SYNTAX INTEGER (0..15)
        ACCESS read-only
        STATUS mandatory
        DESCRIPTION
                "The index to a email notification receiver entry."
        ::= { pduSettingMailNotifyEntry 1 }

pduSettingMailNotifyRecvAddr OBJECT-TYPE
        SYNTAX DisplayString (SIZE(0..63))
        ACCESS read-write
        STATUS mandatory
        DESCRIPTION
                "The Email address of the manager to send a email notification to."
        ::= { pduSettingMailNotifyEntry 2 }

pduSettingMailNotifyType OBJECT-TYPE
        SYNTAX INTEGER {
                none(1),
                events(2),
                status(3)
                }
        ACCESS read-write
        STATUS mandatory
        DESCRIPTION
                "The Email Type of email notification receivers."
        ::= { pduSettingMailNotifyEntry 3 }

pduSettingMailNotifyEvtLev OBJECT-TYPE
        SYNTAX INTEGER {
                critical(1),
                warning(2),
                informational(3)
                }
        ACCESS read-write
        STATUS mandatory
        DESCRIPTION
                "The severity level of email notification to be received by this manager."
        ::= { pduSettingMailNotifyEntry 4 }

pduSettingMailNotifyDesc OBJECT-TYPE
        SYNTAX DisplayString (SIZE(0..63))
        ACCESS read-write
        STATUS mandatory
        DESCRIPTION
                "Description of email notification receivers."
        ::= { pduSettingMailNotifyEntry 5 }


-- ===========================================================================
--
-- pduLog
--
--  PDU Log Group
--
-- ===========================================================================
pduLogSyslogEvtEn OBJECT-TYPE
        SYNTAX INTEGER {
                disabled(1),
                enabled(2)
                }
       ACCESS read-write
       STATUS mandatory
       DESCRIPTION
               "Enable/disable the transmission event log of the syslog server."
       ::= { pduLog 1 }

pduLogSyslogEvtIp OBJECT-TYPE
       SYNTAX DisplayString (SIZE (0..63))
       ACCESS read-write
       STATUS mandatory
       DESCRIPTION
               "The address of event log of syslog server."
       ::= { pduLog 2 }

pduLogSyslogEvtPort OBJECT-TYPE
       SYNTAX INTEGER
       ACCESS read-write
       STATUS mandatory
       DESCRIPTION
               "The port number of event log of syslog Server."
       ::= { pduLog 3 }

pduLogSyslogHisEn OBJECT-TYPE
        SYNTAX INTEGER {
                disabled(1),
                enabled(2)
                }
       ACCESS read-write
       STATUS mandatory
       DESCRIPTION
               "Enable/disable the transmission history log of the syslog server."
       ::= { pduLog 4 }

pduLogSyslogHisIp OBJECT-TYPE
       SYNTAX DisplayString (SIZE (0..63))
       ACCESS read-write
       STATUS mandatory
       DESCRIPTION
               "The address of history log of syslog server."
       ::= { pduLog 5 }

pduLogSyslogHisPort OBJECT-TYPE
       SYNTAX INTEGER
       ACCESS read-write
       STATUS mandatory
       DESCRIPTION
               "The port number of history log of syslog Server."
       ::= { pduLog 6 }

-- ===========================================================================
--
-- pduAdvanced
--
--  PDU Advanced Group
--
-- ===========================================================================
pduAdvWifi           OBJECT IDENTIFIER ::= { pduAdvanced 1 }
pduAdvWiSms          OBJECT IDENTIFIER ::= { pduAdvanced 2 }

-- ===========================================================================
--
-- pduAdvWifi
--
--  Wifi Group
--
-- ===========================================================================
pduAdvWifiCtrl OBJECT-TYPE
       SYNTAX INTEGER {
                disabled(1),
                enabled(2)
                }
       ACCESS read-write
       STATUS mandatory
       DESCRIPTION
               "Enable/disable the Wifi function."
       ::= { pduAdvWifi 1 }

pduAdvWifiSsid OBJECT-TYPE
       SYNTAX DisplayString (SIZE (0..127))
       ACCESS read-write
       STATUS mandatory
       DESCRIPTION
               "The ssid name of wifi, using base64(aes-cbc-256) encryption."
       ::= { pduAdvWifi 2 }

pduAdvWifiPasswd OBJECT-TYPE
       SYNTAX DisplayString (SIZE (0..64))
       ACCESS read-write
       STATUS mandatory
       DESCRIPTION
               "The password of wifi."
       ::= { pduAdvWifi 3 }

pduAdvWifiEncryption OBJECT-TYPE
       SYNTAX INTEGER {
                none(1),
                wep(2),
                wpaPsk(3),
                wpa2Psk(4)
                }
       ACCESS read-write
       STATUS mandatory
       DESCRIPTION
               "The encryption of wifi."
       ::= { pduAdvWifi 4 }

pduAdvWifiSecurity OBJECT-TYPE
       SYNTAX INTEGER {
                none(1),
                tkip(2),
                aes(3),
                tkipAes(4)
                }
       ACCESS read-write
       STATUS mandatory
       DESCRIPTION
               "The security of wifi."
       ::= { pduAdvWifi 5 }

pduAdvWifiSet OBJECT-TYPE
       SYNTAX INTEGER {
                none(1),
                write(2)
                }
       ACCESS read-write
       STATUS mandatory
       DESCRIPTION
               "Set the config to Wifi."
       ::= { pduAdvWifi 6 }

pduAdvWifiConnSt OBJECT-TYPE
       SYNTAX INTEGER {
                disconnection(1),
				associated(2),
                connection(3)
                }
       ACCESS read-only
       STATUS mandatory
       DESCRIPTION
               "The connect status of wifi."
       ::= { pduAdvWifi 7 }

pduAdvWifiIpAddr OBJECT-TYPE
       SYNTAX IpAddress
       ACCESS read-only
       STATUS mandatory
       DESCRIPTION
               "The ip address of wifi."
       ::= { pduAdvWifi 8 }

pduAdvWifiNetMask OBJECT-TYPE
       SYNTAX IpAddress
       ACCESS read-only
       STATUS mandatory
       DESCRIPTION
               "The network mask of wifi."
       ::= { pduAdvWifi 9 }

pduAdvWifiGwAddr OBJECT-TYPE
       SYNTAX IpAddress
       ACCESS read-only
       STATUS mandatory
       DESCRIPTION
               "The ssid name of wifi."
       ::= { pduAdvWifi 10 }

pduAdvWifiMacAddr OBJECT-TYPE
       SYNTAX DisplayString (SIZE (0..31))
       ACCESS read-only
       STATUS mandatory
       DESCRIPTION
               "The mac address of wifi."
       ::= { pduAdvWifi 11 }

pduAdvWifiReconnect OBJECT-TYPE
       SYNTAX INTEGER {
                none(1),
                reconnect(2)
                }
       ACCESS read-write
       STATUS mandatory
       DESCRIPTION
               "Reconnect wifi."
       ::= { pduAdvWifi 12 }

-- ===========================================================================
--
-- pduAdvWiSms
--
--  SMS Group
--
-- ===========================================================================
pduAdvSmsCtrl OBJECT-TYPE
       SYNTAX INTEGER {
                disabled(1),
                enabled(2)
                }
       ACCESS read-write
       STATUS mandatory
       DESCRIPTION
               "Enable/disable the SMS function."
       ::= { pduAdvWiSms 1 }

pduAdvSmsAuth OBJECT-TYPE
       SYNTAX INTEGER {
                disabled(1),
                enabled(2)
                }
       ACCESS read-write
       STATUS mandatory
       DESCRIPTION
               "Enable/disable the Authentication of SMS."
       ::= { pduAdvWiSms 2 }

pduAdvSmsPinCode OBJECT-TYPE
       SYNTAX DisplayString (SIZE (0..15))
       ACCESS read-write
       STATUS mandatory
       DESCRIPTION
               "The pin code of SMS, using base64(aes-cbc-256) encryption."
       ::= { pduAdvWiSms 3 }

pduAdvSmsTable OBJECT-TYPE
        SYNTAX SEQUENCE OF PduAdvSmsTblEntry
        ACCESS not-accessible
        STATUS mandatory
        DESCRIPTION
                "A list of managers to send sms notification to."
        ::= { pduAdvWiSms 4 }

pduAdvSmsTblEntry OBJECT-TYPE
        SYNTAX PduAdvSmsTblEntry
        ACCESS not-accessible
        STATUS mandatory
        DESCRIPTION
                "The managers to send sms notification to."
        INDEX  { pduAdvSmsTblIndex }
        ::= { pduAdvSmsTable 1 }

PduAdvSmsTblEntry ::=
        SEQUENCE {
                pduAdvSmsTblIndex
                        INTEGER,
                pduAdvSmsTblPhone
                        DisplayString,
                pduAdvSmsTblSeverity
                        INTEGER,
                pduAdvSmsTblBody
                        DisplayString
        }

pduAdvSmsTblIndex OBJECT-TYPE
        SYNTAX INTEGER
        ACCESS read-only
        STATUS mandatory
        DESCRIPTION
                "The index to a sms notification receiver entry."
        ::= { pduAdvSmsTblEntry 1 }

pduAdvSmsTblPhone OBJECT-TYPE
        SYNTAX DisplayString (SIZE (0..31))
        ACCESS read-write
        STATUS mandatory
        DESCRIPTION
                "The phone number of SMS list."
        ::= { pduAdvSmsTblEntry 2 }

pduAdvSmsTblSeverity OBJECT-TYPE
        SYNTAX INTEGER {
                information(1),
                warning(2),
                critical(3)
                }
        ACCESS read-write
        STATUS mandatory
        DESCRIPTION
                "The severity level of SMS list."
        ::= { pduAdvSmsTblEntry 3 }

pduAdvSmsTblBody OBJECT-TYPE
        SYNTAX DisplayString (SIZE (0..254))
        ACCESS read-write
        STATUS mandatory
        DESCRIPTION
                "The prefix body of SMS list."
        ::= { pduAdvSmsTblEntry 4 }

-- ===========================================================================
--
-- PduExtLink
--
--  PDU External Link Group
--
-- ===========================================================================


-- ===========================================================================
-- pduTraps
--
-- iPoManIII Trap group
-- ===========================================================================
pduSystemColdBoot TRAP-TYPE
        ENTERPRISE pduTraps
        DESCRIPTION
                "Informational: Cold boot."
        ::= 1

pduSystemWarmBoot TRAP-TYPE
        ENTERPRISE pduTraps
        DESCRIPTION
                "Informational: Warm boot."
        ::= 2

pduSystemRestart TRAP-TYPE
        ENTERPRISE pduTraps
        DESCRIPTION
                "Informational: System restart."
        ::= 3

pduResetToDefault TRAP-TYPE
        ENTERPRISE pduTraps
        DESCRIPTION
                "Informational: Parameters reset to default."
        ::= 4

pduSystemLogClear TRAP-TYPE
        ENTERPRISE pduTraps
        DESCRIPTION
                "Informational: System log cleared."
        ::= 6

pduEventlogClear TRAP-TYPE
        ENTERPRISE pduTraps
        DESCRIPTION
                "Informational: Event log cleared."
        ::= 7

pduInletHistoryClear TRAP-TYPE
        ENTERPRISE pduTraps
        DESCRIPTION
                "Informational: Inlet history log cleared."
        ::= 8

pduOutletHistoryClear TRAP-TYPE
        ENTERPRISE pduTraps
        DESCRIPTION
                "Informational: Outlet history log cleared."
        ::= 9

pduEmdHistoryLogClear TRAP-TYPE
        ENTERPRISE pduTraps
        DESCRIPTION
                "Informational: EMD history log cleared."
        ::= 10

pduSystemTimeChangeUser TRAP-TYPE
        ENTERPRISE pduTraps
        DESCRIPTION
                "Informational: Time changed by user."
        ::= 11

pduSystemTimeChangeNtp TRAP-TYPE
        ENTERPRISE pduTraps
        DESCRIPTION
                "Informational: Time synced with NTP server."
        ::= 12

pduSystemTimeChangeRtc TRAP-TYPE
        ENTERPRISE pduTraps
        DESCRIPTION
                "Informational: Time changed by RTC."
        ::= 13

pduMailTestPass TRAP-TYPE
        ENTERPRISE pduTraps
        DESCRIPTION
                "Informational: Test mail pass."
        ::= 14

pduMailTestFail TRAP-TYPE
        ENTERPRISE pduTraps
        DESCRIPTION
                "Informational: Test mail failed."
        ::= 15

pduMailSentPass TRAP-TYPE
        ENTERPRISE pduTraps
        DESCRIPTION
                "Informational: Mail sent successfully."
        ::= 16

pduMailSentFail TRAP-TYPE
        ENTERPRISE pduTraps
        DESCRIPTION
                "Informational: Mail sent failed."
        ::= 17

pduSystemParamImport TRAP-TYPE
        ENTERPRISE pduTraps
        DESCRIPTION
                "Informational: Import XML configuration."
        ::= 19

pduAccountResetDefault TRAP-TYPE
        ENTERPRISE pduTraps
        DESCRIPTION
                "Informational: The default accounts had been reset to default value."
        ::= 20

pduGroupOutletChanged TRAP-TYPE
        ENTERPRISE pduTraps
        DESCRIPTION
                "Informational: The Administrator has changed the authority of Outlet Manager, the Grouping setting will be cleared synchronously."
        ::= 21

pduScheduleOutletChanged TRAP-TYPE
        ENTERPRISE pduTraps
        DESCRIPTION
                "Informational: The Administrator has changed the authority of Outlet Manager, the Schedule setting will be cleared synchronously."
        ::= 22

pduGroupChanged TRAP-TYPE
        ENTERPRISE pduTraps
        DESCRIPTION
                "Informational: The Outlet Manger has changed the setting of Outlet Grouping, the Schedule will be cleared synchronously."
        ::= 23

pduSetUser TRAP-TYPE
        ENTERPRISE pduTraps
        DESCRIPTION
                "Informational: Assign outlet to user."
        ::= 24

pduDeletUser TRAP-TYPE
        ENTERPRISE pduTraps
        DESCRIPTION
                "Informational: Delete user."
        ::= 25

pduInletCommLost TRAP-TYPE
        ENTERPRISE pduTraps
        DESCRIPTION
                "Informational: PDU communication lost."
        ::= 26

pduInletCommRestore TRAP-TYPE
        ENTERPRISE pduTraps
        DESCRIPTION
                "Informational: PDU communication restore."
        ::= 27

pduUpgradeDevSuccess TRAP-TYPE
        ENTERPRISE pduTraps
        DESCRIPTION
                "Informational: Device upgrade successfully."
        ::= 28

pduUpgradeDevFail TRAP-TYPE
        ENTERPRISE pduTraps
        DESCRIPTION
                "Informational: Device upgrade fail."
        ::= 29

pduEmdComSuccess TRAP-TYPE
        ENTERPRISE pduTraps
        DESCRIPTION
                "Informational: EMD communication succeeded."
        ::= 30

pduEmdComLost TRAP-TYPE
        ENTERPRISE pduTraps
        DESCRIPTION
                "Informational: EMD communication lost."
        ::= 31

pduEmdUpdateSuccess TRAP-TYPE
        ENTERPRISE pduTraps
        DESCRIPTION
                "Informational: EMD Firmware update success."
        ::= 32

pduEmdUpdateFail TRAP-TYPE
        ENTERPRISE pduTraps
        DESCRIPTION
                "Informational: EMD Firmware update fail."
        ::= 33

pduSendTestTrap TRAP-TYPE
        ENTERPRISE pduTraps
        DESCRIPTION
                "Informational: Send test trap."
        ::= 34

pduDaisyCommLost TRAP-TYPE
        ENTERPRISE pduTraps
        DESCRIPTION
                "Warning:Daisy chain communication lost."
        ::= 54

pduDaisyCommRestore TRAP-TYPE
        ENTERPRISE pduTraps
        DESCRIPTION
                "Informational:Daisy chain communication restore."
        ::= 55

pduInletLoadCritToWarn TRAP-TYPE
        ENTERPRISE pduTraps
        DESCRIPTION
                "Informational: Inlet load had returned from critical to warning."
        ::= 130

pduInletLoadCritical TRAP-TYPE
        ENTERPRISE pduTraps
        DESCRIPTION
                "Critical: Inlet load was higher than critical set point."
        ::= 131

pduInletLoadWarnToNormal TRAP-TYPE
        ENTERPRISE pduTraps
        DESCRIPTION
                "Informational: Inlet load had returned from warning to normal."
        ::= 132

pduInletLoadWarn TRAP-TYPE
        ENTERPRISE pduTraps
        DESCRIPTION
                "Warning: Inlet load was higher than warning set point."
        ::= 133

pduInletCurrPhase1CritToWarn TRAP-TYPE
        ENTERPRISE pduTraps
        DESCRIPTION
                "Informational: Inlet phase1 current had returned from critical to warning."
        ::= 134

pduInletCurrPhase1Critical TRAP-TYPE
        ENTERPRISE pduTraps
        DESCRIPTION
                "Critical: Inlet phase1 current was higher than critical set point."
        ::= 135

pduInletCurrPhase1WarnToNormal TRAP-TYPE
        ENTERPRISE pduTraps
        DESCRIPTION
                "Informational: Inlet phase1 current had returned from warning to normal."
        ::= 136

pduInletCurrPhase1Warn TRAP-TYPE
        ENTERPRISE pduTraps
        DESCRIPTION
                "Warning: Inlet phase1 current was higher than warning set point."
        ::= 137

pduInletCurrPhase2CritToWarn TRAP-TYPE
        ENTERPRISE pduTraps
        DESCRIPTION
                "Informational: Inlet phase2 current had returned from critical to warning."
        ::= 138

pduInletCurrPhase2Critical TRAP-TYPE
        ENTERPRISE pduTraps
        DESCRIPTION
                "Critical: Inlet phase2 current was higher than critical set point."
        ::= 139

pduInletCurrPhase2WarnToNormal TRAP-TYPE
        ENTERPRISE pduTraps
        DESCRIPTION
                "Informational: Inlet phase2 current had returned from warning to normal."
        ::= 140

pduInletCurrPhase2Warn TRAP-TYPE
        ENTERPRISE pduTraps
        DESCRIPTION
                "Warning: Inlet phase2 current was higher than warning set point."
        ::= 141

pduInletCurrPhase3CritToWarn TRAP-TYPE
        ENTERPRISE pduTraps
        DESCRIPTION
                "Informational: Inlet phase3 current had returned from critical to warning."
        ::= 142

pduInletCurrPhase3Critical TRAP-TYPE
        ENTERPRISE pduTraps
        DESCRIPTION
                "Critical: Inlet phase3 current was higher than critical set point."
        ::= 143

pduInletCurrPhase3WarnToNprmal TRAP-TYPE
        ENTERPRISE pduTraps
        DESCRIPTION
                "Informational: Inlet phase3 current had returned from warning to normal."
        ::= 144

pduInletCurrPhase3Warn TRAP-TYPE
        ENTERPRISE pduTraps
        DESCRIPTION
                "Warning: Inlet phase3 current had returned from critical to warning."
        ::= 145

pduInletCurrPhase1CritToWarnB1 TRAP-TYPE
        ENTERPRISE pduTraps
        DESCRIPTION
                "Informational: Inlet phase1 current branch1 had returned from critical to warning."
        ::= 146

pduInletCurrPhase1CriticalB1 TRAP-TYPE
        ENTERPRISE pduTraps
        DESCRIPTION
                "Critical: Inlet phase1 current branch1 was higher than critical set point."
        ::= 147

pduInletCurrPhase1WarnToNormalB1 TRAP-TYPE
        ENTERPRISE pduTraps
        DESCRIPTION
                "Informational: Inlet phase1 current branch1 had returned from warning to normal."
        ::= 148

pduInletCurrPhase1WarnB1 TRAP-TYPE
        ENTERPRISE pduTraps
        DESCRIPTION
                "Warning: Inlet phase1 current branch1 was higher than warning set point."
        ::= 149

pduInletCurrPhase2CritToWarnB1 TRAP-TYPE
        ENTERPRISE pduTraps
        DESCRIPTION
                "Informational: Inlet phase2 current branch1 had returned from critical to warning."
        ::= 150

pduInletCurrPhase2CriticalB1 TRAP-TYPE
        ENTERPRISE pduTraps
        DESCRIPTION
                "Critical: Inlet phase2 current branch1 was higher than critical set point."
        ::= 151

pduInletCurrPhase2WarnToNormalB1 TRAP-TYPE
        ENTERPRISE pduTraps
        DESCRIPTION
                "Informational: Inlet phase2 current branch1 had returned from warning to normal."
        ::= 152

pduInletCurrPhase2WarnB1 TRAP-TYPE
        ENTERPRISE pduTraps
        DESCRIPTION
                "Warning: Inlet phase2 current branch1 was higher than warning set point."
        ::= 153

pduInletCurrPhase3CritToWarnB1 TRAP-TYPE
        ENTERPRISE pduTraps
        DESCRIPTION
                "Informational: Inlet phase3 current branch1 had returned from critical to warning."
        ::= 154

pduInletCurrPhase3CriticalB1 TRAP-TYPE
        ENTERPRISE pduTraps
        DESCRIPTION
                "Critical: Inlet phase3 current branch1 was higher than critical set point."
        ::= 155

pduInletCurrPhase3WarnToNprmalB1 TRAP-TYPE
        ENTERPRISE pduTraps
        DESCRIPTION
                "Informational: Inlet phase3 current branch1 had returned from warning to normal."
        ::= 156

pduInletCurrPhase3WarnB1 TRAP-TYPE
        ENTERPRISE pduTraps
        DESCRIPTION
                "Warning: Inlet phase3 current branch1 had returned from critical to warning."
        ::= 157

pduInletCurrPhase1CritToWarnB2 TRAP-TYPE
        ENTERPRISE pduTraps
        DESCRIPTION
                "Informational: Inlet phase1 current branch2 had returned from critical to warning."
        ::= 158

pduInletCurrPhase1CriticalB2 TRAP-TYPE
        ENTERPRISE pduTraps
        DESCRIPTION
                "Critical: Inlet phase1 current branch2 was higher than critical set point."
        ::= 159

pduInletCurrPhase1WarnToNormalB2 TRAP-TYPE
        ENTERPRISE pduTraps
        DESCRIPTION
                "Informational: Inlet phase1 current branch2 had returned from warning to normal."
        ::= 160

pduInletCurrPhase1WarnB2 TRAP-TYPE
        ENTERPRISE pduTraps
        DESCRIPTION
                "Warning: Inlet phase1 current branch2 was higher than warning set point."
        ::= 161

pduInletCurrPhase2CritToWarnB2 TRAP-TYPE
        ENTERPRISE pduTraps
        DESCRIPTION
                "Informational: Inlet phase2 current branch2 had returned from critical to warning."
        ::= 162

pduInletCurrPhase2CriticalB2 TRAP-TYPE
        ENTERPRISE pduTraps
        DESCRIPTION
                "Critical: Inlet phase2 current branch2 was higher than critical set point."
        ::= 163

pduInletCurrPhase2WarnToNormalB2 TRAP-TYPE
        ENTERPRISE pduTraps
        DESCRIPTION
                "Informational: Inlet phase2 current branch2 had returned from warning to normal."
        ::= 164

pduInletCurrPhase2WarnB2 TRAP-TYPE
        ENTERPRISE pduTraps
        DESCRIPTION
                "Warning: Inlet phase2 current branch2 was higher than warning set point."
        ::= 165

pduInletCurrPhase3CritToWarnB2 TRAP-TYPE
        ENTERPRISE pduTraps
        DESCRIPTION
                "Informational: Inlet phase3 current branch2 had returned from critical to warning."
        ::= 166

pduInletCurrPhase3CriticalB2 TRAP-TYPE
        ENTERPRISE pduTraps
        DESCRIPTION
                "Critical: Inlet phase3 current branch2 was higher than critical set point."
        ::= 167

pduInletCurrPhase3WarnToNprmalB2 TRAP-TYPE
        ENTERPRISE pduTraps
        DESCRIPTION
                "Informational: Inlet phase3 current branch2 had returned from warning to normal."
        ::= 168

pduInletCurrPhase3WarnB2 TRAP-TYPE
        ENTERPRISE pduTraps
        DESCRIPTION
                "Warning: Inlet phase3 current branch2 had returned from critical to warning."
        ::= 169

pduInletCurrPhase1CritToWarnTotal TRAP-TYPE
        ENTERPRISE pduTraps
        DESCRIPTION
                "Informational: Inlet phase1 current total had returned from critical to warning."
        ::= 170

pduInletCurrPhase1CriticalTotal TRAP-TYPE
        ENTERPRISE pduTraps
        DESCRIPTION
                "Critical: Inlet phase1 current total was higher than critical set point."
        ::= 171

pduInletCurrPhase1WarnToNormalTotal TRAP-TYPE
        ENTERPRISE pduTraps
        DESCRIPTION
                "Informational: Inlet phase1 current total had returned from warning to normal."
        ::= 172

pduInletCurrPhase1WarnTotal TRAP-TYPE
        ENTERPRISE pduTraps
        DESCRIPTION
                "Warning: Inlet phase1 current total was higher than warning set point."
        ::= 173

pduInletCurrPhase2CritToWarnTotal TRAP-TYPE
        ENTERPRISE pduTraps
        DESCRIPTION
                "Informational: Inlet phase2 current total had returned from critical to warning."
        ::= 174

pduInletCurrPhase2CriticalTotal TRAP-TYPE
        ENTERPRISE pduTraps
        DESCRIPTION
                "Critical: Inlet phase2 current total was higher than critical set point."
        ::= 175

pduInletCurrPhase2WarnToNormalTotal TRAP-TYPE
        ENTERPRISE pduTraps
        DESCRIPTION
                "Informational: Inlet phase2 current total had returned from warning to normal."
        ::= 176

pduInletCurrPhase2WarnTotal TRAP-TYPE
        ENTERPRISE pduTraps
        DESCRIPTION
                "Warning: Inlet phase2 current total was higher than warning set point."
        ::= 177

pduInletCurrPhase3CritToWarnTotal TRAP-TYPE
        ENTERPRISE pduTraps
        DESCRIPTION
                "Informational: Inlet phase3 current total had returned from critical to warning."
        ::= 178

pduInletCurrPhase3CriticalTotal TRAP-TYPE
        ENTERPRISE pduTraps
        DESCRIPTION
                "Critical: Inlet phase3 current total was higher than critical set point."
        ::= 179

pduInletCurrPhase3WarnToNprmalTotal TRAP-TYPE
        ENTERPRISE pduTraps
        DESCRIPTION
                "Informational: Inlet phase3 current total had returned from warning to normal."
        ::= 180

pduInletCurrPhase3WarnTotal TRAP-TYPE
        ENTERPRISE pduTraps
        DESCRIPTION
                "Warning: Inlet phase3 current total had returned from critical to warning."
        ::= 181

pduInletVoltPhase1CritToWarn TRAP-TYPE
        ENTERPRISE pduTraps
        DESCRIPTION
                "Informational: Inlet phase1 voltage had returned from critical to warning."
        ::= 182

pduInletVoltPhase1Critical TRAP-TYPE
        ENTERPRISE pduTraps
        DESCRIPTION
                "Critical: Inlet phase1 voltage was higher than critical set point."
        ::= 183

pduInletVoltPhase1WarnToNormal TRAP-TYPE
        ENTERPRISE pduTraps
        DESCRIPTION
                "Informational: Inlet phase1 voltage had returned from warning to normal."
        ::= 184

pduInletVoltPhase1Warn TRAP-TYPE
        ENTERPRISE pduTraps
        DESCRIPTION
                "Warning: Inlet phase1 voltage was higher than warning set point."
        ::= 185

pduInletVoltPhase2CritToWarn TRAP-TYPE
        ENTERPRISE pduTraps
        DESCRIPTION
                "Informational: Inlet phase2 voltage had returned from critical to warning."
        ::= 186

pduInletVoltPhase2Critical TRAP-TYPE
        ENTERPRISE pduTraps
        DESCRIPTION
                "Critical: Inlet phase2 voltage was higher than critical set point."
        ::= 187

pduInletVoltPhase2WarnToNormal TRAP-TYPE
        ENTERPRISE pduTraps
        DESCRIPTION
                "Informational: Inlet phase2 voltage had returned from warning to normal."
        ::= 188

pduInletVoltPhase2Warn TRAP-TYPE
        ENTERPRISE pduTraps
        DESCRIPTION
                "Warning: Inlet phase2 voltage was higher than warning set point."
        ::= 189

pduInletVoltPhase3CritToWarn TRAP-TYPE
        ENTERPRISE pduTraps
        DESCRIPTION
                "Informational: Inlet phase3 voltage had returned from critical to warning."
        ::= 190

pduInletVoltPhase3Critical TRAP-TYPE
        ENTERPRISE pduTraps
        DESCRIPTION
                "Critical: Inlet phase3 voltage was higher than critical set point."
        ::= 191

pduInletVoltPhase3WarnToNormal TRAP-TYPE
        ENTERPRISE pduTraps
        DESCRIPTION
                "Informational: Inlet phase3 voltage had returned from warning to normal."
        ::= 192

pduInletVoltPhase3Warn TRAP-TYPE
        ENTERPRISE pduTraps
        DESCRIPTION
                "Warning: Inlet phase3 voltage was higher than warning set point."
        ::= 193

pduInletLoadBalanceCritToWarn TRAP-TYPE
        ENTERPRISE pduTraps
        DESCRIPTION
                "Informational: Inlet load balance had returned from critical to warning."
        ::= 194

pduInletLoadBalanceCritical TRAP-TYPE
        ENTERPRISE pduTraps
        DESCRIPTION
                "Critical: Inlet load balance was higher than critical set point."
        ::= 195

pduInletLoadBalanceWarnToNormal TRAP-TYPE
        ENTERPRISE pduTraps
        DESCRIPTION
                "Informational: Inlet load balance had returned from warning to normal."
        ::= 196

pduInletLoadBalanceWarn TRAP-TYPE
        ENTERPRISE pduTraps
        DESCRIPTION
                "Warning: Inlet load balance was higher than warning set point."
        ::= 197

pduOutletCurrCritToWarn TRAP-TYPE
        ENTERPRISE pduTraps
        DESCRIPTION
                "Informational: Outlet current had returned from critical to warning."
        ::= 198

pduOutletCurrCritical TRAP-TYPE
        ENTERPRISE pduTraps
        DESCRIPTION
                "Critical: Outlet current was higher than critical set point."
        ::= 199

pduOutletCurrWarnToNormal TRAP-TYPE
        ENTERPRISE pduTraps
        DESCRIPTION
                "Informational: Outlet current had returned from warning to normal."
        ::= 200

pduOutletCurrWarn TRAP-TYPE
        ENTERPRISE pduTraps
        DESCRIPTION
                "Warning: Outlet current was higher than warning set point."
        ::= 201

pduOutletPwrCritTOWarn TRAP-TYPE
        ENTERPRISE pduTraps
        DESCRIPTION
                "Informational: Outlet power had returned from critical to warning."
        ::= 202

pduOutletPwrCritical TRAP-TYPE
        ENTERPRISE pduTraps
        DESCRIPTION
                "Critical: Outlet power was higher than critical set point."
        ::= 203

pduOutletPwrWarnToNormal TRAP-TYPE
        ENTERPRISE pduTraps
        DESCRIPTION
                "Informational: Outlet power had returned from warning to normal."
        ::= 204

pduOutletPwrWarn TRAP-TYPE
        ENTERPRISE pduTraps
        DESCRIPTION
                "Warning: Outlet power was higher than warning set point."
        ::= 205

pduOutletOnUser TRAP-TYPE
        ENTERPRISE pduTraps
        DESCRIPTION
                "Informational: Outlet turned on by user."
        ::= 206

pduOutletOnSchedule TRAP-TYPE
        ENTERPRISE pduTraps
        DESCRIPTION
                "Informational: Outlet turned on by schedule."
        ::= 207

pduOutletOffUser TRAP-TYPE
        ENTERPRISE pduTraps
        DESCRIPTION
                "Informational: Outlet turned off by user."
        ::= 208

pduOutletOffSchedule TRAP-TYPE
        ENTERPRISE pduTraps
        DESCRIPTION
                "Informational: Outlet turned off by schedule."
        ::= 209

pduOutletRebootUser TRAP-TYPE
        ENTERPRISE pduTraps
        DESCRIPTION
                "Informational: Outlet reboot by user."
        ::= 210

pduOutletRebootSchedule TRAP-TYPE
        ENTERPRISE pduTraps
        DESCRIPTION
                "Informational: Outlet reboot by schedule."
        ::= 211

pduEmdTempHighWarnToNormal TRAP-TYPE
        ENTERPRISE pduTraps
        DESCRIPTION
                "Informational: Temperature had returned from high warning to normal."
        ::= 212

pduEmdTempHighWarn TRAP-TYPE
        ENTERPRISE pduTraps
        DESCRIPTION
                "Warning: Temperature was higher than high warning set point."
        ::= 213

pduEmdTempLowWarnToNormal TRAP-TYPE
        ENTERPRISE pduTraps
        DESCRIPTION
                "Informational: Temperature had returned from low warning to normal."
        ::= 214

pduEmdTempLowWarn TRAP-TYPE
        ENTERPRISE pduTraps
        DESCRIPTION
                "Warning: Temperature was lower than low warning set point."
        ::= 215

pduEmdTempHighCritToWarn TRAP-TYPE
        ENTERPRISE pduTraps
        DESCRIPTION
                "Informational: Temperature had returned from high critical to high warning."
        ::= 216

pduEmdTempHighCritical TRAP-TYPE
        ENTERPRISE pduTraps
        DESCRIPTION
                "Critical: Temperature was higher than high critical set point."
        ::= 217

pduEmdTempLowCritToWarn TRAP-TYPE
        ENTERPRISE pduTraps
        DESCRIPTION
                "Informational: Temperature had returned from low critical to low warning."
        ::= 218

pduEmdTempLowCritical TRAP-TYPE
        ENTERPRISE pduTraps
        DESCRIPTION
                "Critical: Temperature was lower than low critical set point."
        ::= 219

pduEmdHumiHighWarnToNormal TRAP-TYPE
        ENTERPRISE pduTraps
        DESCRIPTION
                "Informational: Humidity had returned from high warning to normal."
        ::= 220

pduEmdHumiHighWarn TRAP-TYPE
        ENTERPRISE pduTraps
        DESCRIPTION
                "Warning: Humidity was higher than high warning set point."
        ::= 221

pduEmdHumiLowWarnToNormal TRAP-TYPE
        ENTERPRISE pduTraps
        DESCRIPTION
                "Informational: Humidity had returned from low warning to normal."
        ::= 222

pduEmdHumiLowWarn TRAP-TYPE
        ENTERPRISE pduTraps
        DESCRIPTION
                "Warning: Humidity was lower than low warning set point."
        ::= 223

pduEmdHumiHighCritToWarn TRAP-TYPE
        ENTERPRISE pduTraps
        DESCRIPTION
                "Informational: Humidity had returned from high critical to high warning."
        ::= 224

pduEmdHumiHighCritical TRAP-TYPE
        ENTERPRISE pduTraps
        DESCRIPTION
                "Critical: Humidity was higher than high critical set point."
        ::= 225

pduEmdHumiLowCritToWarn TRAP-TYPE
        ENTERPRISE pduTraps
        DESCRIPTION
                "Informational: Humidity had returned from low critical to low warning."
        ::= 226

pduEmdHumiLowCritical TRAP-TYPE
        ENTERPRISE pduTraps
        DESCRIPTION
                "Critical: Humidity was lower than low critical set point."
        ::= 227

pduEmdAlarm1NotActive TRAP-TYPE
        ENTERPRISE pduTraps
        DESCRIPTION
                "Informational: Alarm-1 became inactive."
        ::= 228

pduEmdAlarm1Active TRAP-TYPE
        ENTERPRISE pduTraps
        DESCRIPTION
                "Warning: Alarm-1 became active."
        ::= 229

pduEmdAlarm2NotActive TRAP-TYPE
        ENTERPRISE pduTraps
        DESCRIPTION
                "Informational: Alarm-2 became inactive."
        ::= 230

pduEmdAlarm2Active TRAP-TYPE
        ENTERPRISE pduTraps
        DESCRIPTION
                "Warning: Alarm-2 became active."
        ::= 231

pduInletEnergyReset TRAP-TYPE
        ENTERPRISE pduTraps
        DESCRIPTION
                "Informational: Inlet energy reset."
        ::= 232

pduInletEnergyResetPhase1 TRAP-TYPE
        ENTERPRISE pduTraps
        DESCRIPTION
                "Informational: Inlet phase1 energy reset."
        ::= 233

pduInletEnergyResetPhase2 TRAP-TYPE
        ENTERPRISE pduTraps
        DESCRIPTION
                "Informational: Inlet phase2 energy reset."
        ::= 234

pduInletEnergyResetPhase3 TRAP-TYPE
        ENTERPRISE pduTraps
        DESCRIPTION
                "Informational: Inlet phase3 energy reset."
        ::= 235

pduOutletEnergyReset TRAP-TYPE
        ENTERPRISE pduTraps
        DESCRIPTION
                "Informational: Outlet energy reset."
        ::= 236

pduIntetResidualCurrect1Occured TRAP-TYPE
        ENTERPRISE pduTraps
        DESCRIPTION
                "Critical: Inlet Residual current occurred."
        ::= 237

pduIntetResidualCurrect1Remove TRAP-TYPE
        ENTERPRISE pduTraps
        DESCRIPTION
                "Informational: Inlet Residual current removed."
        ::= 238

pduInletPfPhase1CritToWarnB1 TRAP-TYPE
        ENTERPRISE pduTraps
        DESCRIPTION
                "Informational: Inlet phase1 pf branch1 had returned from critical to warning."
        ::= 239

pduInletPfPhase1CriticalB1 TRAP-TYPE
        ENTERPRISE pduTraps
        DESCRIPTION
                "Critical: Inlet phase1 pf branch1 was lower than critical set point."
        ::= 240

pduInletPfPhase1WarnToNormalB1 TRAP-TYPE
        ENTERPRISE pduTraps
        DESCRIPTION
                "Informational: Inlet phase1 pf branch1 had returned from warning to normal."
        ::= 241

pduInletPfPhase1WarnB1 TRAP-TYPE
        ENTERPRISE pduTraps
        DESCRIPTION
                "Warning: Inlet phase1 pf branch1 was lower than warning set point."
        ::= 242

pduInletPfPhase2CritToWarnB1 TRAP-TYPE
        ENTERPRISE pduTraps
        DESCRIPTION
                "Informational: Inlet phase2 pf branch1 had returned from critical to warning."
        ::= 243

pduInletPfPhase2CriticalB1 TRAP-TYPE
        ENTERPRISE pduTraps
        DESCRIPTION
                "Critical: Inlet phase2 pf branch1 was lower than critical set point."
        ::= 244

pduInletPfPhase2WarnToNormalB1 TRAP-TYPE
        ENTERPRISE pduTraps
        DESCRIPTION
                "Informational: Inlet phase2 pf branch1 had returned from warning to normal."
        ::= 245

pduInletPfPhase2WarnB1 TRAP-TYPE
        ENTERPRISE pduTraps
        DESCRIPTION
                "Warning: Inlet phase2 pf branch1 was lower than warning set point."
        ::= 246

pduInletPfPhase3CritToWarnB1 TRAP-TYPE
        ENTERPRISE pduTraps
        DESCRIPTION
                "Informational: Inlet phase3 pf branch1 had returned from critical to warning."
        ::= 247

pduInletPfPhase3CriticalB1 TRAP-TYPE
        ENTERPRISE pduTraps
        DESCRIPTION
                "Critical: Inlet phase3 pf branch1 was lower than critical set point."
        ::= 248

pduInletPfPhase3WarnToNprmalB1 TRAP-TYPE
        ENTERPRISE pduTraps
        DESCRIPTION
                "Informational: Inlet phase3 pf branch1 had returned from warning to normal."
        ::= 249

pduInletPfPhase3WarnB1 TRAP-TYPE
        ENTERPRISE pduTraps
        DESCRIPTION
                "Warning: Inlet phase3 pf branch1 had returned from critical to warning."
        ::= 250

pduInletPfPhase1CritToWarnB2 TRAP-TYPE
        ENTERPRISE pduTraps
        DESCRIPTION
                "Informational: Inlet phase1 pf branch2 had returned from critical to warning."
        ::= 251

pduInletPfPhase1CriticalB2 TRAP-TYPE
        ENTERPRISE pduTraps
        DESCRIPTION
                "Critical: Inlet phase1 pf branch2 was lower than critical set point."
        ::= 252

pduInletPfPhase1WarnToNormalB2 TRAP-TYPE
        ENTERPRISE pduTraps
        DESCRIPTION
                "Informational: Inlet phase1 pf branch2 had returned from warning to normal."
        ::= 253

pduInletPfPhase1WarnB2 TRAP-TYPE
        ENTERPRISE pduTraps
        DESCRIPTION
                "Warning: Inlet phase1 pf branch2 was lower than warning set point."
        ::= 254

pduInletPfPhase2CritToWarnB2 TRAP-TYPE
        ENTERPRISE pduTraps
        DESCRIPTION
                "Informational: Inlet phase2 pf branch2 had returned from critical to warning."
        ::= 255

pduInletPfPhase2CriticalB2 TRAP-TYPE
        ENTERPRISE pduTraps
        DESCRIPTION
                "Critical: Inlet phase2 pf branch2 was lower than critical set point."
        ::= 256

pduInletPfPhase2WarnToNormalB2 TRAP-TYPE
        ENTERPRISE pduTraps
        DESCRIPTION
                "Informational: Inlet phase2 pf branch2 had returned from warning to normal."
        ::= 257

pduInletPfPhase2WarnB2 TRAP-TYPE
        ENTERPRISE pduTraps
        DESCRIPTION
                "Warning: Inlet phase2 pf branch2 was lower than warning set point."
        ::= 258

pduInletPfPhase3CritToWarnB2 TRAP-TYPE
        ENTERPRISE pduTraps
        DESCRIPTION
                "Informational: Inlet phase3 pf branch2 had returned from critical to warning."
        ::= 259

pduInletPfPhase3CriticalB2 TRAP-TYPE
        ENTERPRISE pduTraps
        DESCRIPTION
                "Critical: Inlet phase3 pf branch2 was lower than critical set point."
        ::= 260

pduInletPfPhase3WarnToNprmalB2 TRAP-TYPE
        ENTERPRISE pduTraps
        DESCRIPTION
                "Informational: Inlet phase3 pf branch2 had returned from warning to normal."
        ::= 261

pduInletPfPhase3WarnB2 TRAP-TYPE
        ENTERPRISE pduTraps
        DESCRIPTION
                "Warning: Inlet phase3 pf branch2 had returned from critical to warning."
        ::= 262

pduInletPowerShareMainLose TRAP-TYPE
        ENTERPRISE pduTraps
        DESCRIPTION
                "Warning: Active/Main Power change to Active/Backup Power."
        ::= 263

pduInletPowerShareMainResotre TRAP-TYPE
        ENTERPRISE pduTraps
        DESCRIPTION
                "Informational: Active/Backup Power change to Active/Main Power."
        ::= 264

pduInletPowerShareBackupLose TRAP-TYPE
        ENTERPRISE pduTraps
        DESCRIPTION
                "Warning: Active/Main Power change to Inactive."
        ::= 265

pduInletPowerShareBackupResotre TRAP-TYPE
        ENTERPRISE pduTraps
        DESCRIPTION
                "Informational:  Inactive change to Active/Main Power Alarmstring."
        ::= 266
END
