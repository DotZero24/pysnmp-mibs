MBG-SNMP-RSC-MDU-MIB DEFINITIONS ::= BEGIN

IMPORTS
    MODULE-IDENTITY, OBJECT-TYPE, Integer32, Unsigned32, IpAddress, NOTIFICATION-TYPE FROM SNMPv2-SMI
    MODULE-COMPLIANCE, OBJECT-GROUP, NOTIFICATION-GROUP FROM SNMPv2-CONF
    DisplayString, TEXTUAL-CONVENTION                         FROM SNMPv2-TC
	mbgSnmpRoot FROM MBG-SNMP-ROOT-MIB;


mbgRSC180 MODULE-IDENTITY
    LAST-UPDATED "201703280000Z"
    ORGANIZATION "www.meinberg.de"
    CONTACT-INFO
	 "postal:   Meinberg Funkuhren
                    Lange Wand 9
                    31812 Bad Pyrmont
	            Germany

          email:    info@meinberg.de"
    DESCRIPTION
	"Top-level infrastructure of the MBG-SNMP project enterprise MIB tree"
    REVISION     "201703280000Z"
    DESCRIPTION
       "Update to new format referencing MBG-SNMP-ROOT-MIB"
    REVISION     "200601200000Z"
    DESCRIPTION
       "Covering RSC-MDU modules from Meinberg"
    ::= { mbgSnmpRoot 80 }

MeinbergRefClockTyp ::= TEXTUAL-CONVENTION
        STATUS current
        DESCRIPTION
            "indicates different Ref and MDU types"
        SYNTAX INTEGER {
		notAvailable(0),
		gps166(1),
		gps167(2),
		gps167SV(3),
		gps167PC(4),
		gps167PCI(5),
		gps163(6),
		gps168PCI(7),
		gps161(8),
		gps169PCI(9),
		tcr167PCI(10),
		gps164(11),
		gps170PCI(12),
		pzf511(13),
		gps170(14),
		tcr511(15),
		am511(16),
		msf511(17),
		grc170(18),
		gps170PEX(19),
		gps162(20),
		ptp270PEX(21),
		frc511PEX(22),
		gen170(23),
		tcr170PEX(24),
		wwvb511(25),
		mbg170(26),
		jjy511(27),
		pzf600(28),
		tcr600(29),
		gps180(30),
		gln170(31),
		gps180PEX(32),
		tcr180PEX(33),
		pzf180PEX(34),
		mbg180(35),
		msf600(36),
		wwvb600(37),
		jjy600(38),
		gps180HS(39),
		gps180AMC(40),
		esi180(41),
		cpe180(42),
		lno180(43),
		grc180(44),
		liu(45),
		dcf600HS(46),
		dcf600RS(47),
		mri(48),
		bpe(49),
		gln180pex(50),
		n2x(51),
		rsc180(52),
		lne_gb(53),
		Ppg180(54),
		scg(55),
		mdu300(56),
		sdi(57),
		fdm180(58),
		spt(59),
		pzf180(60),
		rel1000(61),
		hps100(62),
		vsg180(63),
		msf180(64),
		wwvb180(65),
		cpc180(66),
		ctc100(67),
		tcr180(68),
		lue180(69),
		cpc_01(70),
		tsu_01(71),
		cmc_01(72),
		scu_01(73),
		fcu_01(74),
		csm100(75),
		lne180sfp(76),
		gts180(77),
		gps180csm(78),
		grc181(79),
		n2x180(80),
		grc181PEX(81),
		mdu180(82),
		mdu312(83),
		gps165(84),
		gns181_uc(85),
		psx_4ge(86),
		rsc180rdu(87)
	}


--
--  MBG-SNMP enterprise-specific management objects
--
--
-- Copy everything from here into your MBG-SNMP-MIB.txt file, if you are using several different SNMP-supporting Meinberg systems
--

mbgRefClock				    OBJECT IDENTIFIER ::= {mbgRSC180 0}
mbgMDU			    		OBJECT IDENTIFIER ::= {mbgRSC180 1}
mbgTrapRoot         		OBJECT IDENTIFIER ::= {mbgRSC180 2}



-- physical interface table/configuration

mbgRefClockStatus        OBJECT IDENTIFIER ::= { mbgRefClock 0 }

mbgRefClockTable OBJECT-TYPE
    SYNTAX SEQUENCE OF MbgRefClockTableEntry
    MAX-ACCESS not-accessible
    STATUS current
    DESCRIPTION
         "A table of content for individual clocks."
    ::= { mbgRefClockStatus 1 }

mbgRefClockTableEntry OBJECT-TYPE
    SYNTAX MbgRefClockTableEntry
    MAX-ACCESS not-accessible
    STATUS current
    DESCRIPTION
         "A list of objects for individual clocks."
    INDEX { mbgClkTableIndex }
    ::= { mbgRefClockTable 1 }

MbgRefClockTableEntry ::=
    SEQUENCE {
		mbgClkTableIndex 		Unsigned32,
	    mbgClkType 				INTEGER,
		mbgClkSerialNo			DisplayString,
		mbgClkFirmwareRev		DisplayString,
	    mbgClkMode 				INTEGER,
	    mbgGpsState 			INTEGER,
		mbgGpsPosition 			DisplayString,
		mbgGpsSatellitesGood 	Integer32,
		mbgGpsSatellitesInView 	Integer32,
		mbgGPSNavSolved			INTEGER,
		mbgLeapSecond			DisplayString
	}

-- GPS RefClock states
--  (For MDURSC180 systems this is RefClock 1)
--
mbgClkTableIndex OBJECT-TYPE
    SYNTAX Unsigned32
    MAX-ACCESS not-accessible
    STATUS current
    DESCRIPTION
       "Specifies index for a RefClock Table."
    ::= { mbgRefClockTableEntry 1 }

mbgClkType OBJECT-TYPE
    SYNTAX MeinbergRefClockTyp
	MAX-ACCESS  read-only
    STATUS	current
    DESCRIPTION
        "Type of the Refclock."
    DEFVAL { 0 }
    ::= { mbgRefClockTableEntry 2 }


mbgClkSerialNo	OBJECT-TYPE
	SYNTAX DisplayString
    MAX-ACCESS read-only
    STATUS current
    DESCRIPTION
       "Serial Number of the Refclock."
    ::= { mbgRefClockTableEntry 3 }


mbgClkFirmwareRev	OBJECT-TYPE
	SYNTAX DisplayString
    MAX-ACCESS read-only
    STATUS current
    DESCRIPTION
       "Firmware Version of the Refclock."
    ::= { mbgRefClockTableEntry 4 }



mbgGpsState OBJECT-TYPE
    SYNTAX INTEGER {
		notAvailable(0),
		synchronized(1),
		notSynchronized(2)
	}
	MAX-ACCESS  read-only
    STATUS	current
    DESCRIPTION
        "Current state of GPS refclock as value
			0: not available
			1: synchronized
			2: not synchronized"
    DEFVAL { 0 }
    ::= { mbgRefClockTableEntry 5 }





-- GPS Switchcard states
-- (for MDU)


-- this object has SYNTAX MeinbergRefClockTyp

mbgMDUType OBJECT-TYPE
    SYNTAX      MeinbergRefClockTyp
    MAX-ACCESS  read-only
    STATUS	current
    DESCRIPTION
        "Type of clock"
    ::= { mbgMDU 1 }

mbgMDUSerialNo OBJECT-TYPE
    SYNTAX      DisplayString
    MAX-ACCESS  read-only
    STATUS	current
    DESCRIPTION
        "MDU serial number"
    ::= { mbgMDU 2 }

mbgMDUFirmwareRev OBJECT-TYPE
    SYNTAX      DisplayString
    MAX-ACCESS  read-only
    STATUS	current
    DESCRIPTION
        "MDU firmware version"
    ::= { mbgMDU 3 }

mbgMDUMasterVal OBJECT-TYPE
    SYNTAX		INTEGER {
		noMaster(0),
		clk1isMaster(1),
		clk2isMaster(2)
	}
    MAX-ACCESS  read-write
    STATUS	current
    DESCRIPTION
        "Current selected masterclock of switchcard as value
		0: no master selected (outputs disabled)
		1: GPS clock 1 is master
		2: GPS clock 2 is master"
    DEFVAL { 0 }
    ::= { mbgMDU 4 }

mbgMDULocalRemote OBJECT-TYPE
    SYNTAX 		INTEGER {
	local(0),
	remote(1)
	}
    MAX-ACCESS  read-write
    STATUS	current
    DESCRIPTION
        "Current masterselect mode of GPS switchcard as value
		0: local masterselect
		1: remote masterselect"
	DEFVAL{0}
    ::= { mbgMDU 5 }

mbgTrapIPAddress OBJECT-TYPE
    SYNTAX 		IpAddress
    MAX-ACCESS  read-write
    STATUS	current
    DESCRIPTION
        "Trap receiver IP address."
	DEFVAL{"0.0.0.0"}
    ::= { mbgMDU 6 }

mbgMDUSyncStatusClk1 OBJECT-TYPE
    SYNTAX      INTEGER {
	notSync(0),
	sync(1)
	}
    MAX-ACCESS  read-only
    STATUS	current
    DESCRIPTION
        "Current time sync status of clk 1
		0: not synchronized
		1: synchronized"
	DEFVAL{0}
    ::= { mbgMDU 7 }

mbgMDUSyncStatusClk2 OBJECT-TYPE
    SYNTAX      INTEGER {
	notSync(0),
	sync(1)
	}
    MAX-ACCESS  read-only
    STATUS	current
    DESCRIPTION
        "Current time sync status of clk 2
		0: not synchronized
		1: synchronized"
	DEFVAL{0}
    ::= { mbgMDU 8 }

mbgMDUOutputStatus OBJECT-TYPE
    SYNTAX		INTEGER {
	outputsDisabled(0),
	outputsEnabled(1)
	}
    MAX-ACCESS  read-only
    STATUS	current
    DESCRIPTION
        "Current state of outputs (0=outputs disabled, 1=outputs enabled)"
    ::= { mbgMDU 9 }


mbgMDUACOMode OBJECT-TYPE
    SYNTAX      INTEGER {
	acoModeOFF(0),
	acoModeON (1)
	}
    MAX-ACCESS  read-only
    STATUS	current
    DESCRIPTION
        "Current state of ACO (access control override)
		0: ACO mode off (no firmware updates, password protection and encryption on)
		1: ACO mode on (firmware updates possible, password set to empty string (=just press enter)"
    ::= { mbgMDU 10 }

mbgMDUPowerSupply1 OBJECT-TYPE
    SYNTAX      INTEGER{
	notOK (0),
	ok (1)
	}
    MAX-ACCESS  read-only
    STATUS	current
    DESCRIPTION
        "Current status of power supply  1
		0: notOK
		1: OK"
    ::= { mbgMDU 11 }


mbgMDUPowerSupply2 OBJECT-TYPE
    SYNTAX      INTEGER{
	notOK(0),
	ok (1)
	}
    MAX-ACCESS  read-only
    STATUS	current
    DESCRIPTION
        "Current status of power supply  2
		0: notOK
		1: OK"
    ::= { mbgMDU 12 }

mbgMDUPowerSupply3 OBJECT-TYPE
    SYNTAX      INTEGER{
	notOK (0),
	ok (1)
	}
    MAX-ACCESS  read-only
    STATUS	current
    DESCRIPTION
        "Current status of power supply  3
		0: notOK
		1: OK"
    ::= { mbgMDU 13 }

mbgMDUPowerSupply4 OBJECT-TYPE
    SYNTAX      INTEGER{
	notOK (0),
	ok (1)
	}
    MAX-ACCESS  read-only
    STATUS	current
    DESCRIPTION
        "Current status of power supply  4
		0: notOK
		1: OK"
    ::= { mbgMDU 14 }

mbgMDUTemp OBJECT-TYPE
    SYNTAX      DisplayString
    MAX-ACCESS  read-only
    STATUS	current
    DESCRIPTION
        "MDU temperature"
    ::= { mbgMDU 15 }

mbgMDUSlot1 OBJECT-TYPE
    SYNTAX      DisplayString
    MAX-ACCESS  read-only
    STATUS	current
    DESCRIPTION
        "IO Module"
    ::= { mbgMDU 16 }

mbgMDUSlot2 OBJECT-TYPE
    SYNTAX      DisplayString
    MAX-ACCESS  read-only
    STATUS	current
    DESCRIPTION
        "IO Module"
    ::= { mbgMDU 17 }

mbgMDUSlot3 OBJECT-TYPE
    SYNTAX      DisplayString
    MAX-ACCESS  read-only
    STATUS	current
    DESCRIPTION
        "IO Module"
    ::= { mbgMDU 18 }

mbgMDUSlot4 OBJECT-TYPE
    SYNTAX      DisplayString
    MAX-ACCESS  read-only
    STATUS	current
    DESCRIPTION
        "IO Module"
    ::= { mbgMDU 19 }

mbgMDUSlot5 OBJECT-TYPE
    SYNTAX      DisplayString
    MAX-ACCESS  read-only
    STATUS	current
    DESCRIPTION
        "IO Module"
    ::= { mbgMDU 20 }

mbgMDUSlot6 OBJECT-TYPE
    SYNTAX      DisplayString
    MAX-ACCESS  read-only
    STATUS	current
    DESCRIPTION
        "IO Module"
    ::= { mbgMDU 21 }

mbgMDUSlot7 OBJECT-TYPE
    SYNTAX      DisplayString
    MAX-ACCESS  read-only
    STATUS	current
    DESCRIPTION
        "IO Module"
    ::= { mbgMDU 22 }

mbgMDUSlot8 OBJECT-TYPE
    SYNTAX      DisplayString
    MAX-ACCESS  read-only
    STATUS	current
    DESCRIPTION
        "IO Module"
    ::= { mbgMDU 23 }

mbgMDUSlot9 OBJECT-TYPE
    SYNTAX      DisplayString
    MAX-ACCESS  read-only
    STATUS	current
    DESCRIPTION
        "IO Module"
    ::= { mbgMDU 24 }

mbgMDUSlot10 OBJECT-TYPE
    SYNTAX      DisplayString
    MAX-ACCESS  read-only
    STATUS	current
    DESCRIPTION
        "IO Module"
    ::= { mbgMDU 25 }

mbgMDUSlot11 OBJECT-TYPE
    SYNTAX      DisplayString
    MAX-ACCESS  read-only
    STATUS	current
    DESCRIPTION
        "IO Module"
    ::= { mbgMDU 26 }

mbgMDUSlot12 OBJECT-TYPE
    SYNTAX      DisplayString
    MAX-ACCESS  read-only
    STATUS	current
    DESCRIPTION
        "IO Module"
    ::= { mbgMDU 27 }

mbgMDUSlot13 OBJECT-TYPE
    SYNTAX      DisplayString
    MAX-ACCESS  read-only
    STATUS	current
    DESCRIPTION
        "IO Module"
    ::= { mbgMDU 28 }

mbgMDUSlot14 OBJECT-TYPE
    SYNTAX      DisplayString
    MAX-ACCESS  read-only
    STATUS	current
    DESCRIPTION
        "IO Module"
    ::= { mbgMDU 29 }

mbgMDUClk1 OBJECT-TYPE
    SYNTAX      DisplayString
    MAX-ACCESS  read-only
    STATUS	current
    DESCRIPTION
        "Clk Module"
    ::= { mbgMDU 30 }

mbgMDUClk2 OBJECT-TYPE
    SYNTAX      DisplayString
    MAX-ACCESS  read-only
    STATUS	current
    DESCRIPTION
        "Clk Module"
    ::= { mbgMDU 31 }

--
-- here come SNMP trap definitions according to SNMPv2
--

mbgTraps OBJECT IDENTIFIER 	::={mbgTrapRoot 0}

mbgColdBootTrap NOTIFICATION-TYPE
	STATUS current
    DESCRIPTION
        "The trap is sent when a Refclock is in the Cold Boot mode."
    ::= {mbgTraps 1}

mbgWarmBootTrap NOTIFICATION-TYPE
     STATUS	current
    DESCRIPTION
        "The trap is sent when a Refclock is in the Warm Boot mode."
    ::= {mbgTraps 2}

mbgGPSNavSolvedTrap NOTIFICATION-TYPE
    STATUS      current
    DESCRIPTION
        "The trap is sent when a Refclock calculated its actual position."
    ::= { mbgTraps 3 }

mbgGPSReceiverNotRespondingTrap NOTIFICATION-TYPE
    STATUS	current
    DESCRIPTION
        "The trap is sent when a GPS receiver is not responding."
    ::= {mbgTraps 4}

mbgGPSReceiverNotSyncTrap NOTIFICATION-TYPE
    STATUS	current
    DESCRIPTION
        "The trap is sent when a GPS receiver is not synchronised."
    ::= {mbgTraps 5}

mbgGPSAntennaFaultyTrap NOTIFICATION-TYPE
    STATUS	current
    DESCRIPTION
        "The trap is sent when a connection to an antenna is lost."
    ::= {mbgTraps 6}

mbgGPSAntennaReconnectTrap NOTIFICATION-TYPE
    STATUS	current
    DESCRIPTION
        "The trap is sent when an antenna has been reconnected."
    ::= {mbgTraps 7}

mbgSCUBootTrap NOTIFICATION-TYPE
    STATUS	current
    DESCRIPTION
        "The trap is sent when SCU has been rebooted."
    ::= {mbgTraps 8}

mbgLeapSecondAnnouncedTrap NOTIFICATION-TYPE
    STATUS	current
    DESCRIPTION
        "The trap is sent when a leap second has been announced."
    ::= {mbgTraps 9}

mbgMasterclockSwitchoverTrap NOTIFICATION-TYPE
     STATUS	current
     DESCRIPTION
        "The trap is sent when a masterclock changes."
    ::= {mbgTraps 10}

mbgPowerSupplyFailureTrap NOTIFICATION-TYPE
    STATUS	current
    DESCRIPTION
        "The trap is sent when a power supply unit fails."
    ::= {mbgTraps 11}

mbgPowerSupplyOKTrap NOTIFICATION-TYPE
    STATUS	current
    DESCRIPTION
        "The trap is sent when a power supply unit restores its operation."
    ::= {mbgTraps 12}

mbgHighTempTrap NOTIFICATION-TYPE
	STATUS	current
    DESCRIPTION
        "The trap is sent when the SCU temperature is over 85 degrees Celsius."
    ::= {mbgTraps 13}

mbgTestNotificationTrap NOTIFICATION-TYPE
    STATUS	current
    DESCRIPTION
        "The trap is sent when a test notification has been requested. "
    ::= {mbgTraps 99}


--
-- Conformance Statements
--


mbgRSC180Conformance		OBJECT IDENTIFIER ::= { mbgRSC180 90 }
mbgRSC180Compliances		OBJECT IDENTIFIER ::= { mbgRSC180Conformance 1 }
mbgRSC180Groups				OBJECT IDENTIFIER ::= { mbgRSC180Conformance 2 }

mbgRSC180Compliance MODULE-COMPLIANCE
    STATUS  current
    DESCRIPTION
	"The compliance statement for SNMP entities which implement version 2 of the RSC180 MIB"
    MODULE -- this module
    MANDATORY-GROUPS
	{
		mbgRSC180ObjectsGroup,
		mbgRSC180TrapsGroup
    }
    ::= { mbgRSC180Compliances 1 }


mbgRSC180ObjectsGroup	OBJECT-GROUP
    OBJECTS {
	mbgClkType,
	mbgClkSerialNo,
	mbgClkFirmwareRev,
	mbgClkMode,
	mbgGpsState,
	mbgGpsPosition,
	mbgGpsSatellitesGood,
	mbgGpsSatellitesInView,
	mbgGPSNavSolved,
	mbgLeapSecond,
	mbgSCUType,
	mbgSCUSerialNo,
	mbgSCUFirmwareRev,
	mbgSCUMasterVal,
	mbgSCULocalRemote,
	mbgTrapIPAddress,
	mbgSCUSyncStatusClk1,
	mbgSCUSyncStatusClk2,
	mbgSCUOutputStatus,
	mbgSCUACOMode,
	mbgSCUPowerSupply1,
	mbgSCUPowerSupply2,
	mbgSCUTemp
    }
    STATUS	current
    DESCRIPTION
	"The collection of objects for the RSC180 MIB"

    ::= { mbgRSC180Groups 1 }

	mbgRSC180TrapsGroup 	NOTIFICATION-GROUP
	NOTIFICATIONS {
	mbgColdBootTrap,
	mbgWarmBootTrap,
	mbgGPSNavSolvedTrap,
	mbgGPSReceiverNotRespondingTrap,
	mbgGPSReceiverNotSyncTrap,
	mbgGPSAntennaFaultyTrap,
	mbgGPSAntennaReconnectTrap,
	mbgSCUBootTrap,
	mbgLeapSecondAnnouncedTrap,
	mbgMasterclockSwitchoverTrap,
	mbgPowerSupplyFailureTrap,
	mbgPowerSupplyOKTrap,
	mbgHighTempTrap,
	mbgTestNotificationTrap
	}
	STATUS	current
	DESCRIPTION
	"The collection of traps for the MBG RSC180 MIB"
	::= { mbgRSC180Groups 2 }

END
