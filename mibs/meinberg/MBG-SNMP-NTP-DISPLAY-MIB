MBG-SNMP-NTP-DISPLAY-MIB DEFINITIONS ::= BEGIN

IMPORTS
    OBJECT-TYPE FROM RFC-1212
    TRAP-TYPE FROM RFC-1215
    DisplayString FROM RFC1213-MIB

   mbgSnmpRoot FROM MBG-SNMP-ROOT-MIB;

mbgNtpDisp OBJECT IDENTIFIER ::= { mbgSnmpRoot 20 }
    --LAST-UPDATED "201211080621Z"
    --ORGANIZATION "www.meinberg.de"
    --CONTACT-INFO
	-- "postal:   Meinberg Funkuhren
    --            Auf der Landwehr 22
    --            31812 Bad Pyrmont
	--            Germany

    --      email:    info@meinberg.de"
    --DESCRIPTION
	--"Initial revision"
    --REVISION     "201211080621Z"
    --DESCRIPTION
    --   "Covering NTP display from Meinberg"

mbgNtpDispInfo		    OBJECT IDENTIFIER ::= {mbgNtpDisp 2}
mbgNtpDispTraps		    OBJECT IDENTIFIER ::= {mbgNtpDisp 3}

-- Display info

mbgNtpDispClockType OBJECT-TYPE
    SYNTAX      DisplayString
    ACCESS      read-only
    STATUS      mandatory
    DESCRIPTION
        "Type of clock"
    ::= { mbgNtpDispInfo 1 }

mbgNtpDispClockTypeVal OBJECT-TYPE
    SYNTAX      Integer32
    ACCESS      read-only
    STATUS      mandatory
    DESCRIPTION
        "Type of clock as integer"
    ::= { mbgNtpDispInfo 2 }

mbgNtpDispMode OBJECT-TYPE
    SYNTAX      DisplayString
    ACCESS      read-only
    STATUS      mandatory
    DESCRIPTION
        "Display mode"
    ::= { mbgNtpDispInfo 3 }


mbgNtpDispModeVal OBJECT-TYPE
    SYNTAX      Integer32
    ACCESS      read-only
    STATUS      mandatory
    DESCRIPTION
        "Display mode as integer"
    ::= { mbgNtpDispInfo 4 }

mbgNtpDispState OBJECT-TYPE
    SYNTAX      DisplayString
    ACCESS      read-only
    STATUS      mandatory
    DESCRIPTION
        "Display's state"
    ::= { mbgNtpDispInfo 5 }

-- Traps

mbgNtpDispTrapBoot TRAP-TYPE
    ENTERPRISE  mbgNtpDispTraps
    DESCRIPTION
        "Trap to be sent when display reboots"
    ::= 1

mbgNtpDispTrapSync TRAP-TYPE
    ENTERPRISE  mbgNtpDispTraps
    DESCRIPTION
        "Trap to be sent when display is synchronized"
    ::= 2

mbgNtpDispTrapNotSync TRAP-TYPE
    ENTERPRISE  mbgNtpDispTraps
    DESCRIPTION
        "Trap to be sent when display is not synchronized"
    ::= 3

mbgNtpDispTrapTestNotification TRAP-TYPE
    ENTERPRISE  mbgNtpDispTraps
    DESCRIPTION
        "Testing notification"
    ::= 4

END
