--          *****************************
--          *							*
--          *         ONEOS MIB			*
--          *							*
--          *****************************
--
--          ONEOS_MIB_STD_V05.1.R005_E001
--
--          Creation date : 07/08/2010

	ONEACCESS-SNMP-CONFIG-MIB DEFINITIONS ::= BEGIN

		IMPORTS
			OBJECT-GROUP
				FROM SNMPv2-CONF
			IpAddress, Integer32, Counter32, Counter64, OBJECT-TYPE,
			MODULE-IDENTITY
				FROM SNMPv2-SMI
			DisplayString, RowStatus, PhysAddress, TruthValue
				FROM SNMPv2-TC
			oacExpIMIpAcl, oacMIBModules, oacExpIMManagement
		        FROM ONEACCESS-GLOBAL-REG;

	oacSnmpConfigMIB MODULE-IDENTITY

	LAST-UPDATED    "201107290000Z"
        ORGANIZATION    " OneAccess "
        CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

	DESCRIPTION
			"fixed compilation issues"
	REVISION	"201107290000Z"

	DESCRIPTION
			"Fixed the issues related to octet string range"
	REVISION	"201107260000Z"

	DESCRIPTION
                        "Contact updated"
	REVISION        "201106150000Z"

	DESCRIPTION
		"Updated with review comments."
	REVISION	"201007080001Z"

	DESCRIPTION
        "OneOS can be managed via snmp. The snmp agent on the device
		supports all the three formats v1, v2, and v3.

		The current mib is an requirement to create snmpv3 users on the device
		using snmp protocol. Hence this snmp configuration mib will provide
		tables and scalars requried to configure an v3 user on ONE OS.

		The snmpv3 user creation is dependent on the views and the snmp groups.
		Hence the mib should support creating views and groups.

		The user of this mib can configure  the following using this mib
				Configuring SNMP Views
				Configuring Snmp Group
				Snmpv3 User Table
				EningeId "
		::= { oacMIBModules 2002 }

--
-- Node definitions
--

	-- 1.3.6.1.4.1.13191.1.10.3.4.20
	oacSnmpConfig OBJECT IDENTIFIER ::= { oacExpIMManagement 20 }

	-- 1.3.6.1.4.1.13191.1.10.3.4.20.1
	oacSnmpConfigObjects      OBJECT IDENTIFIER ::= { oacSnmpConfig 1  }

	-- 1.3.6.1.4.1.13191.1.10.3.4.20.2
	oacSnmpConfigConformance  OBJECT IDENTIFIER ::= { oacSnmpConfig 2  }

--
-- Snmp Configuration
--

		-- 1.3.6.1.4.1.13191.1.10.3.4.20.1.1
		oacSnmpSource OBJECT-TYPE
			SYNTAX 		OCTET STRING (SIZE(1..255))
			MAX-ACCESS 	read-write
			STATUS 		current
			DESCRIPTION
				"snmp source { <interface> | any }"
			DEFVAL { "any" }
			::= { oacSnmpConfigObjects 1 }


		-- 1.3.6.1.4.1.13191.1.10.3.4.20.1.2
		oacSnmpTrapSource OBJECT-TYPE
			SYNTAX 		OCTET STRING (SIZE(1..255))
			MAX-ACCESS 	read-write
			STATUS 		current
			DESCRIPTION
				"snmp trap-source { <interface> | any }"
			DEFVAL { "any" }
			::= { oacSnmpConfigObjects 2 }


		-- 1.3.6.1.4.1.13191.1.10.3.4.20.1.3
		oacSnmpMibIfDescrShort OBJECT-TYPE
			SYNTAX 		TruthValue
			MAX-ACCESS 	read-write
			STATUS 		current
			DESCRIPTION
				"will display the interface name
				 with out spaces between the interface
				 and unit"
			DEFVAL { false }
			::= { oacSnmpConfigObjects 3 }


		-- 1.3.6.1.4.1.13191.1.10.3.4.20.1.4
		oacSnmpChassisId OBJECT-TYPE
			SYNTAX 		OCTET STRING (SIZE(0..255))
			MAX-ACCESS 	read-write
			STATUS 		current
			DESCRIPTION
				"Chassis Id of this device."
			::= { oacSnmpConfigObjects 4 }

		-- 1.3.6.1.4.1.13191.1.10.3.4.20.1.5
		oacSnmpMaxMsgSize OBJECT-TYPE
			SYNTAX 		INTEGER
			MAX-ACCESS 	read-write
			STATUS 		current
			DESCRIPTION
				"maximum size of the snmp message"
			DEFVAL { 8192 }
			::= { oacSnmpConfigObjects 5 }


--
-- Snmp v2 Community
--

		-- 1.3.6.1.4.1.13191.1.10.3.4.20.1.6
		oacSnmpCommunityConfigTable OBJECT-TYPE
			SYNTAX SEQUENCE OF OacSnmpCommunityConfigEntry
			MAX-ACCESS 	not-accessible
			STATUS 		current
			DESCRIPTION
				"This table will hold the configuration required to
				apply the SNMP view on a read/write V2C community."
			::= { oacSnmpConfigObjects 6 }

		-- 1.3.6.1.4.1.13191.1.10.3.4.20.1.6.1
		oacSnmpCommunityConfigEntry OBJECT-TYPE
			SYNTAX 		OacSnmpCommunityConfigEntry
			MAX-ACCESS 	not-accessible
			STATUS 		current
			DESCRIPTION
				"A Entry will hold the view applied for a community."
			INDEX { oacSnmpCommunityString, oacSnmpCommunityAccessType }
			::= { oacSnmpCommunityConfigTable 1 }

		OacSnmpCommunityConfigEntry ::=
			SEQUENCE {
				oacSnmpCommunityString
					OCTET STRING,
				oacSnmpCommunityAccessType
					INTEGER,
				oacSnmpCommunityAclType
					INTEGER,
				oacSnmpCommunityAclName
					OCTET STRING,
				oacSnmpCommunityV2GroupName
					OCTET STRING,
				oacSnmpCommunityisEncrypted
					TruthValue,
				oacSnmpCommunityRowStatus
					RowStatus
			}

		-- 1.3.6.1.4.1.13191.1.10.3.4.20.1.6.1.1
		oacSnmpCommunityString	OBJECT-TYPE
			SYNTAX      OCTET STRING (SIZE(1..255))
			MAX-ACCESS 	not-accessible
			STATUS 		current
			DESCRIPTION
				"The community string"
			::= { oacSnmpCommunityConfigEntry 1 }

		-- 1.3.6.1.4.1.13191.1.10.3.4.20.1.6.1.2
		oacSnmpCommunityAccessType	OBJECT-TYPE
			SYNTAX		INTEGER
				{
				set-read-community(1),
				set-write-community(2)
				}
			MAX-ACCESS  not-accessible
			STATUS 		current
			DESCRIPTION
				"This object identifies the type of
				community for which this community
				string is attached."
			::= { oacSnmpCommunityConfigEntry 2 }

		-- 1.3.6.1.4.1.13191.1.10.3.4.20.1.6.1.3
		oacSnmpCommunityAclType	OBJECT-TYPE
			SYNTAX INTEGER
				{
				ipv4(1),
				ipv6(2)
				}
			MAX-ACCESS 	read-create
			STATUS 		current
			DESCRIPTION
				"Ipv4 or Ipv6 Acl attached to this
				snmp community string"
			::= { oacSnmpCommunityConfigEntry 3 }


		-- 1.3.6.1.4.1.13191.1.10.3.4.20.1.6.1.4
		oacSnmpCommunityAclName	OBJECT-TYPE
			SYNTAX		OCTET STRING (SIZE(0..255))
			MAX-ACCESS 	read-create
			STATUS 		current
			DESCRIPTION
				"Ipv4 Acl attached to this snmp community string"
			::= { oacSnmpCommunityConfigEntry 4 }

		-- 1.3.6.1.4.1.13191.1.10.3.4.20.1.6.1.5
		oacSnmpCommunityV2GroupName	OBJECT-TYPE
			SYNTAX		OCTET STRING (SIZE(0..255))
			MAX-ACCESS 	read-create
			STATUS 		current
			DESCRIPTION
				"Snmp group attached to this community string"
			::= { oacSnmpCommunityConfigEntry 5 }

		-- 1.3.6.1.4.1.13191.1.10.3.4.20.1.6.1.6
		oacSnmpCommunityisEncrypted	OBJECT-TYPE
			SYNTAX		TruthValue
			MAX-ACCESS 	read-create
			STATUS 		current
			DESCRIPTION
				"if true the string should be encrypted.
				If false it will be a plain text string."
			::= { oacSnmpCommunityConfigEntry 6 }

		-- 1.3.6.1.4.1.13191.1.10.3.4.20.1.6.1.7
		oacSnmpCommunityRowStatus	OBJECT-TYPE
			SYNTAX		RowStatus
			MAX-ACCESS 	read-create
			STATUS 		current
			DESCRIPTION
				"The row status for this entry"
			::= { oacSnmpCommunityConfigEntry 7 }

		-- 1.3.6.1.4.1.13191.1.10.3.4.20.1.7
		oacSnmpEngineId OBJECT-TYPE
			SYNTAX		OCTET STRING (SIZE(1..255))
			MAX-ACCESS 	read-write
			STATUS		current
			DESCRIPTION
				"By default on OneOS the engineId is created by
				using the mac address of FastEthernet Interface."
			::= { oacSnmpConfigObjects 7 }

--
-- SNMP V3 INFORMS
--

		-- 1.3.6.1.4.1.13191.1.10.3.4.20.1.8
		oacSnmpRemoteAgentIpAddr OBJECT-TYPE
			SYNTAX		IpAddress
			MAX-ACCESS 	read-write
			STATUS		current
			DESCRIPTION
				"From the ip address provided remote agent's
				 engine id is discovered."
			DEFVAL { '00000000'H }
			::= { oacSnmpConfigObjects 8 }


		-- 1.3.6.1.4.1.13191.1.10.3.4.20.1.9
		oacSnmpRemoteEngineIdConfigTable OBJECT-TYPE
			SYNTAX SEQUENCE OF OacSnmpRemoteEngineIdConfigEntry
			MAX-ACCESS 	not-accessible
			STATUS 		current
			DESCRIPTION
				"This table will hold the configuration for snmp traps."
			::= { oacSnmpConfigObjects 9 }

		-- 1.3.6.1.4.1.13191.1.10.3.4.20.1.9.1
		oacSnmpRemoteEngineIdConfigEntry OBJECT-TYPE
			SYNTAX 		OacSnmpRemoteEngineIdConfigEntry
			MAX-ACCESS 	not-accessible
			STATUS 		current
			DESCRIPTION
				"A Entry will hold if a trap is enabled or disabled."
			INDEX { oacSnmpRemoteEngineId }
			::= { oacSnmpRemoteEngineIdConfigTable 1 }

		OacSnmpRemoteEngineIdConfigEntry ::=
			SEQUENCE {
				oacSnmpRemoteEngineId
					OCTET STRING,
				oacSnmpRemoteEngineIpAddr
					IpAddress,
				oacSnmpRemoteEngineMaxMsgSize
					INTEGER,
				oacSnmpRemoteEngineRowstatus
					RowStatus
			}

		-- 1.3.6.1.4.1.13191.1.10.3.4.20.1.9.1.1
		oacSnmpRemoteEngineId	OBJECT-TYPE
			SYNTAX		OCTET STRING (SIZE(1..255))
			MAX-ACCESS  not-accessible
			STATUS 		current
			DESCRIPTION
				"Engine Id of the remote."
			::= { oacSnmpRemoteEngineIdConfigEntry 1 }


		-- 1.3.6.1.4.1.13191.1.10.3.4.20.1.9.1.2
		oacSnmpRemoteEngineIpAddr	OBJECT-TYPE
			SYNTAX		IpAddress
			MAX-ACCESS 	read-create
			STATUS 		current
			DESCRIPTION
				"if true the string should be encrypted.
				If false it will be a plain text string."
			::= { oacSnmpRemoteEngineIdConfigEntry 2 }


		-- 1.3.6.1.4.1.13191.1.10.3.4.20.1.9.1.3
		oacSnmpRemoteEngineMaxMsgSize	OBJECT-TYPE
			SYNTAX		INTEGER (484..8192)
			MAX-ACCESS 	read-create
			STATUS 		current
			DESCRIPTION
				"if true the string should be encrypted. if false it will
				be a plain text string."
			DEFVAL { 8192 }
			::= { oacSnmpRemoteEngineIdConfigEntry 3 }


		-- 1.3.6.1.4.1.13191.1.10.3.4.20.1.9.1.4
		oacSnmpRemoteEngineRowstatus	OBJECT-TYPE
			SYNTAX		RowStatus
			MAX-ACCESS 	read-create
			STATUS 		current
			DESCRIPTION
				"The row status for this entry"
			::= { oacSnmpRemoteEngineIdConfigEntry 4 }

--
-- SNMP Trap Configuration Table
--

		-- 1.3.6.1.4.1.13191.1.10.3.4.20.1.10
		oacSnmpTrapConfigTable OBJECT-TYPE
			SYNTAX SEQUENCE OF OacSnmpTrapConfigEntry
			MAX-ACCESS 	not-accessible
			STATUS 		current
			DESCRIPTION
				"This table will hold the configuration for snmp traps."
			::= { oacSnmpConfigObjects 10 }

		-- 1.3.6.1.4.1.13191.1.10.3.4.20.1.10.1
		oacSnmpTrapConfigEntry OBJECT-TYPE
			SYNTAX 		OacSnmpTrapConfigEntry
			MAX-ACCESS 	not-accessible
			STATUS 		current
			DESCRIPTION
				"A Entry will hold if a trap is enabled or disabled."
			INDEX { oacSnmpTrapConfigType }
			::= { oacSnmpTrapConfigTable 1 }

		OacSnmpTrapConfigEntry ::=
			SEQUENCE {
				oacSnmpTrapConfigType
					INTEGER,
				oacSnmpTrapConfigisEnabled
					TruthValue,
				oacSnmpTrapConfigRowStatus
					RowStatus
			}

		-- 1.3.6.1.4.1.13191.1.10.3.4.20.1.10.1.1
		oacSnmpTrapConfigType OBJECT-TYPE
			SYNTAX 		INTEGER
				{
				standard(1),
				acl(2),
				bgp(3),
				ipsec(4),
				isakmp(5),
				isdn(6),
				nat(7),
				pstn(8),
				vrrp(9)
				}
			MAX-ACCESS 	not-accessible
			STATUS 		current
			DESCRIPTION
				"The user can enable or disable the following traps:
					1. standard, 2. acl, 3. bgp,
					4. ipsec, 5. isakmp, 6. isdn,
					7. nat,	8. pstn, 9. vrrp"
			::= { oacSnmpTrapConfigEntry 1 }

		-- 1.3.6.1.4.1.13191.1.10.3.4.20.1.10.1.2
		oacSnmpTrapConfigisEnabled	OBJECT-TYPE
			SYNTAX		TruthValue
			MAX-ACCESS 	read-create
			STATUS 		current
			DESCRIPTION
				"if true the string should be encrypted.
				if false it will be a plain text string."
			::= { oacSnmpTrapConfigEntry 2 }

		-- 1.3.6.1.4.1.13191.1.10.3.4.20.1.10.1.3
		oacSnmpTrapConfigRowStatus	OBJECT-TYPE
			SYNTAX		RowStatus
			MAX-ACCESS 	read-create
			STATUS 		current
			DESCRIPTION
				"The row status for this entry"
			::= { oacSnmpTrapConfigEntry 3 }


		-- 1.3.6.1.4.1.13191.1.10.3.4.20.2.1
		oacSnmpConfigGroups OBJECT IDENTIFIER ::= { oacSnmpConfigConformance 1 }

		-- 1.3.6.1.4.1.13191.1.10.3.4.20.2.1.1
		oacSnmpConfigGroup OBJECT-GROUP
			OBJECTS { oacSnmpTrapConfigisEnabled }
			STATUS current
			DESCRIPTION
				"Group of SNMP objects"
			::= { oacSnmpConfigGroups 1 }

		-- 1.3.6.1.4.1.13191.1.10.3.4.20.2.2
		oacSnmpCompls OBJECT IDENTIFIER ::= { oacSnmpConfigConformance 2 }

	END

--
-- END OF ONE ACCESS SNMPV3 CONFIG MIB
--
