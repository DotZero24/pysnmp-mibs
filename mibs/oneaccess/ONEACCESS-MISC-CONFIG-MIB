--          *****************************
--          *                           *
--          *         ONEOS MIB         *
--          *                           *
--          *****************************
--
--          ONEOS_MIB_STD_V05.1.R005_E001
--
--          Creation date : 07/08/2010

	ONEACCESS-MISC-CONFIG-MIB DEFINITIONS ::= BEGIN

		IMPORTS
			OBJECT-GROUP
				FROM SNMPv2-CONF
			IpAddress, Integer32, Counter32, Counter64, Unsigned32,
			OBJECT-TYPE, MODULE-IDENTITY
				FROM SNMPv2-SMI
			DisplayString, RowStatus, PhysAddress, TruthValue,
			DateAndTime
				FROM SNMPv2-TC
			InterfaceIndex, InterfaceIndexOrZero
				FROM IF-MIB
			oacExpIMIpAcl, oacMIBModules, oacExpIMManagement
		        FROM ONEACCESS-GLOBAL-REG;

	oacMiscConfigMIB MODULE-IDENTITY

	LAST-UPDATED    "201107260000Z"
        ORGANIZATION    " OneAccess "
        CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

       	DESCRIPTION
			"Fixed the issues related to octet string range"
	REVISION	"201107260000Z"

        DESCRIPTION
                        "Contact updated"
        REVISION        "201106150000Z"

       	DESCRIPTION
		        "change syntax for date and time objects"
        REVISION	"201012170001Z"

	DESCRIPTION
        "This module contains objects to configure
			1) telnet server
			2) Syslog server
			3) Sntp client
			4) Banner
			5) Date and time."

		::= { oacMIBModules 2003 }

--
-- Node definitions
--

	-- 1.3.6.1.4.1.13191.1.10.3.4.21
	oacMiscConfig OBJECT IDENTIFIER ::= { oacExpIMManagement 21 }

	-- 1.3.6.1.4.1.13191.1.10.3.4.21.1
	oacTelnetServerConfigObjects      OBJECT IDENTIFIER ::= { oacMiscConfig 1  }

	-- 1.3.6.1.4.1.13191.1.10.3.4.21.2
	oacSyslogServerConfigObjects      OBJECT IDENTIFIER ::= { oacMiscConfig 2 }

	-- 1.3.6.1.4.1.13191.1.10.3.4.21.3
	oacSntpClientConfigObjects  OBJECT IDENTIFIER ::= { oacMiscConfig 3 }

	-- 1.3.6.1.4.1.13191.1.10.3.4.21.4
	oacBannerConfigObjects  OBJECT IDENTIFIER ::= { oacMiscConfig 4 }

	-- 1.3.6.1.4.1.13191.1.10.3.4.21.5
	oacDateAndTimeConfigObjects  OBJECT IDENTIFIER ::= { oacMiscConfig 5 }

	-- 1.3.6.1.4.1.13191.1.10.3.4.21.6
	oacMiscConfigConformance  OBJECT IDENTIFIER ::= { oacMiscConfig 6  }


--
-- Telnet Server Configuration
--


		-- 1.3.6.1.4.1.13191.1.10.3.4.21.1.1
		oacTelnetServerBindInterfaceTable OBJECT-TYPE
			SYNTAX SEQUENCE OF OacTelnetServerBindInterfaceEntry
			MAX-ACCESS 	not-accessible
			STATUS 		current
			DESCRIPTION
				"This is for displaying all the users
				who are logged into device."
			::= { oacTelnetServerConfigObjects 1 }

		-- 1.3.6.1.4.1.13191.1.10.3.4.21.1.1.1
		oacTelnetServerBindInterfaceEntry OBJECT-TYPE
			SYNTAX  OacTelnetServerBindInterfaceEntry
			MAX-ACCESS 	not-accessible
			STATUS 		current
			DESCRIPTION
				"Each entry in the table is identified by the
				unique session id."
			INDEX { oacTelnetServerBindInterfaceIndex }
			::= { oacTelnetServerBindInterfaceTable 1 }


		OacTelnetServerBindInterfaceEntry ::=
			SEQUENCE {
				oacTelnetServerBindInterfaceIndex
					InterfaceIndex,
				oacTelnetServerBindInterfaceName
					OCTET STRING,
				oacTelnetServerBindInterfaceRowStatus
					RowStatus
			}


		-- 1.3.6.1.4.1.13191.1.10.3.4.21.1.1.1.1
		oacTelnetServerBindInterfaceIndex  OBJECT-TYPE
			SYNTAX InterfaceIndex
			MAX-ACCESS read-create
			STATUS current
			DESCRIPTION
				"The interface index to which the Telnet server will bind."
			::= { oacTelnetServerBindInterfaceEntry 1 }


		-- 1.3.6.1.4.1.13191.1.10.3.4.21.1.1.1.2
		oacTelnetServerBindInterfaceName  OBJECT-TYPE
			SYNTAX OCTET STRING (SIZE(1..255))
			MAX-ACCESS read-create
			STATUS current
			DESCRIPTION
				"The name of the interface to which the telnet server will bind."
			::= { oacTelnetServerBindInterfaceEntry 2 }


		-- 1.3.6.1.4.1.13191.1.10.3.4.21.1.1.1.3
		oacTelnetServerBindInterfaceRowStatus  OBJECT-TYPE
			SYNTAX RowStatus
			MAX-ACCESS read-create
			STATUS current
			DESCRIPTION
				"Row status for this entry"
			::= { oacTelnetServerBindInterfaceEntry 3 }


		-- 1.3.6.1.4.1.13191.1.10.3.4.21.1.2
		oacTelnetServerBindAcl   OBJECT-TYPE
		SYNTAX        OCTET STRING (SIZE(0..255))
		MAX-ACCESS    read-write
		STATUS        current
		DESCRIPTION
			"It is possible to restrict access to telnet clients
			by using a list of addresses standing for the list
			of permitted source IP addresses."
		::= { oacTelnetServerConfigObjects 2 }


		-- 1.3.6.1.4.1.13191.1.10.3.4.21.1.3
		oacTelnetServerIdleTimeout OBJECT-TYPE
			SYNTAX 		Unsigned32
			UNITS       "seconds"
			MAX-ACCESS 	read-write
			STATUS 		current
			DESCRIPTION
				"If a connected telnet client is inactive during a certain time,
				it is disconnected. By default, any inactive telnet client is
				disconnected after 10 minutes."
			DEFVAL { 600 }
			::= { oacTelnetServerConfigObjects 3 }


		-- 1.3.6.1.4.1.13191.1.10.3.4.21.1.4
		oacTelnetServerLogEnable OBJECT-TYPE
			SYNTAX 		TruthValue
			MAX-ACCESS 	read-write
			STATUS 		current
			DESCRIPTION
				"Remote connections to the telnet server
				can be logged by enabling log enable."
			DEFVAL { true }
			::= { oacTelnetServerConfigObjects 4 }


		-- 1.3.6.1.4.1.13191.1.10.3.4.21.1.5
		oacTelnetServerLogFileSize OBJECT-TYPE
			SYNTAX 		INTEGER (82..8200)
			UNITS		"bytes"
			MAX-ACCESS 	read-write
			STATUS 		current
			DESCRIPTION
				"By default, the log file size is 8200 bytes."
			DEFVAL { 8200 }
			::= { oacTelnetServerConfigObjects 5 }


--
-- Syslog configuration
--

		-- 1.3.6.1.4.1.13191.1.10.3.4.21.2.1
		oacSyslogServerTable OBJECT-TYPE
			SYNTAX SEQUENCE OF OacSyslogServerEntry
			MAX-ACCESS 	not-accessible
			STATUS 		current
			DESCRIPTION
				"Table to configure remote syslog servers."
			::= { oacSyslogServerConfigObjects 1 }

		-- 1.3.6.1.4.1.13191.1.10.3.4.21.2.1.1
		oacSyslogServerEntry OBJECT-TYPE
			SYNTAX OacSyslogServerEntry
			MAX-ACCESS 	not-accessible
			STATUS 		current
			DESCRIPTION
				"An entry for a syslog server."
			INDEX { oacSyslogServerAddress }
			::= { oacSyslogServerTable 1 }

		OacSyslogServerEntry ::=
			SEQUENCE {
				oacSyslogServerAddress
					OCTET STRING,
				oacSyslogServerFacilityNum
					INTEGER,
				oacSyslogServerInterface
					InterfaceIndex,
				oacSyslogServerRowStatus
					RowStatus
			}

		-- 1.3.6.1.4.1.13191.1.10.3.4.21.2.1.1.1
		oacSyslogServerAddress  OBJECT-TYPE
			SYNTAX OCTET STRING (SIZE(1..255))
			MAX-ACCESS read-create
			STATUS current
			DESCRIPTION
				"The remote syslog server IP address, or
				hostname."
			::= { oacSyslogServerEntry 1 }

		-- 1.3.6.1.4.1.13191.1.10.3.4.21.2.1.1.2
		oacSyslogServerFacilityNum  OBJECT-TYPE
			SYNTAX INTEGER (0..23)
			MAX-ACCESS read-create
			STATUS current
			DESCRIPTION
				"facility number, ranging from 0 up to 23.
				Must be set according to the server configuration"
			DEFVAL { 0 }
			::= { oacSyslogServerEntry 2 }

		-- 1.3.6.1.4.1.13191.1.10.3.4.21.2.1.1.3
		oacSyslogServerInterface  OBJECT-TYPE
			SYNTAX InterfaceIndex
			MAX-ACCESS read-create
			STATUS current
			DESCRIPTION
				"The interface which this syslog client
				should used to send log messages to the
				configured remote syslog server."
			::= { oacSyslogServerEntry 3 }

		-- 1.3.6.1.4.1.13191.1.10.3.4.21.2.1.1.4
		oacSyslogServerRowStatus  OBJECT-TYPE
			SYNTAX RowStatus
			MAX-ACCESS read-create
			STATUS current
			DESCRIPTION
				"Row status for this entry"
			::= { oacSyslogServerEntry 4 }

		-- 1.3.6.1.4.1.13191.1.10.3.4.21.2.2
		oacSyslogMaxServers	OBJECT-TYPE
			SYNTAX		INTEGER (1..20)
			MAX-ACCESS 	read-write
			STATUS		current
			DESCRIPTION
				"maximum number of syslog servers that can be configured."
			::= { oacSyslogServerConfigObjects 2 }


--
-- SNTP Client configuration
--


		-- 1.3.6.1.4.1.13191.1.10.3.4.21.3.1
		oacSntpClientBroadcastEnable OBJECT-TYPE
			SYNTAX		TruthValue
			MAX-ACCESS 	read-write
			STATUS		current
			DESCRIPTION
				"To configure the SNTP client in
				broadcast mode to accept NTP packets
				from any NTP broadcast server."
			::= { oacSntpClientConfigObjects 1 }


		-- 1.3.6.1.4.1.13191.1.10.3.4.21.3.2
		oacSntpRemoteServerTable OBJECT-TYPE
			SYNTAX SEQUENCE OF OacSntpRemoteServerEntry
			MAX-ACCESS 	not-accessible
			STATUS 		current
			DESCRIPTION
				"Table to configure the SNTP client to request
				NTP packets from a specified NTP server"
			::= { oacSntpClientConfigObjects 2 }


		-- 1.3.6.1.4.1.13191.1.10.3.4.21.3.2.1
		oacSntpRemoteServerEntry OBJECT-TYPE
			SYNTAX OacSntpRemoteServerEntry
			MAX-ACCESS 	not-accessible
			STATUS 		current
			DESCRIPTION
				"Entry for the remote sntp server."
			INDEX { oacSntpRemoteServerAddress }
			::= { oacSntpRemoteServerTable 1 }


		OacSntpRemoteServerEntry ::=
			SEQUENCE {
				oacSntpRemoteServerAddress
					OCTET STRING,
				oacSntpRemoteServerInterface
					InterfaceIndex,
				oacSntpRemoteServerRowStatus
					RowStatus
			}


		-- 1.3.6.1.4.1.13191.1.10.3.4.21.3.1.1.1
		oacSntpRemoteServerAddress  OBJECT-TYPE
			SYNTAX OCTET STRING (SIZE(1..255))
			MAX-ACCESS read-create
			STATUS current
			DESCRIPTION
				"The sntp remote server info."
			::= { oacSntpRemoteServerEntry 1 }


		-- 1.3.6.1.4.1.13191.1.10.3.4.21.3.1.1.2
		oacSntpRemoteServerInterface  OBJECT-TYPE
			SYNTAX InterfaceIndex
			MAX-ACCESS read-create
			STATUS current
			DESCRIPTION
				"Interface thru which the client requests the
				ntp servers."
			::= { oacSntpRemoteServerEntry 2 }


		-- 1.3.6.1.4.1.13191.1.10.3.4.21.3.1.1.3
		oacSntpRemoteServerRowStatus  OBJECT-TYPE
			SYNTAX RowStatus
			MAX-ACCESS read-create
			STATUS current
			DESCRIPTION
				"Row status for this entry"
			::= { oacSntpRemoteServerEntry 3 }


		-- 1.3.6.1.4.1.13191.1.10.3.4.21.3.3
		oacSntpClientPollInterval OBJECT-TYPE
			SYNTAX		Unsigned32
			UNITS		"seconds"
			MAX-ACCESS 	read-write
			STATUS		current
			DESCRIPTION
				"The duration between two requests
				sent to the NTP server when synchronized."
			DEFVAL { 64 }
			::= { oacSntpClientConfigObjects 3 }


--
-- Banner Table
--


		-- 1.3.6.1.4.1.13191.1.10.3.4.21.4.1
		oacConfigBannerSeqTable 	OBJECT-TYPE
			SYNTAX		SEQUENCE OF OacConfigBannerSeqEntry
			MAX-ACCESS 	not-accessible
			STATUS		current
			DESCRIPTION
				"This table holds upto 40 banner messages."
				::= { oacBannerConfigObjects 1 }

		-- 1.3.6.1.4.1.13191.1.10.3.4.21.4.1.1
		oacConfigBannerSeqEntry 	OBJECT-TYPE
			SYNTAX OacConfigBannerSeqEntry
			MAX-ACCESS 	not-accessible
			STATUS 		current
			DESCRIPTION
				"Each entry will hold one banner string"
			INDEX { oacConfigBannerSequence }
			::= { oacConfigBannerSeqTable 1 }

		OacConfigBannerSeqEntry ::=
			SEQUENCE {
				oacConfigBannerType
					INTEGER,
				oacConfigBannerSequence
					INTEGER,
				oacConfigBannerString
					OCTET STRING,
				oacConfigBannerSeqRowStatus
					RowStatus
		}

		-- 1.3.6.1.4.1.13191.1.10.3.4.21.4.1.1.1
		oacConfigBannerType OBJECT-TYPE
			SYNTAX	INTEGER
					{
					motd(1),
					exec(2)
					}
			MAX-ACCESS 	read-create
			STATUS 		current
			DESCRIPTION
				"motd is for the text displayed when attempting
				to log in, whereas exec is for the text displayed
				when logged in. "
			::= { oacConfigBannerSeqEntry 1 }

		-- 1.3.6.1.4.1.13191.1.10.3.4.21.4.1.1.2
		oacConfigBannerSequence OBJECT-TYPE
			SYNTAX		INTEGER (1..40)
			MAX-ACCESS 	read-create
			STATUS 		current
			DESCRIPTION
				"The maximum number of strings that can be stored are 40."
			::= { oacConfigBannerSeqEntry 2 }

		-- 1.3.6.1.4.1.13191.1.10.3.4.21.4.1.1.3
		oacConfigBannerString OBJECT-TYPE
			SYNTAX		OCTET STRING (SIZE(1..255))
			MAX-ACCESS 	read-create
			STATUS 		current
			DESCRIPTION
				"banner test is a set of string maximum upto 255 characters."
			::= { oacConfigBannerSeqEntry 3 }

		-- 1.3.6.1.4.1.13191.1.10.3.4.21.4.1.1.4
		oacConfigBannerSeqRowStatus OBJECT-TYPE
			SYNTAX		RowStatus
			MAX-ACCESS 	read-create
			STATUS 		current
			DESCRIPTION
				"The row status of this entry"
			::= { oacConfigBannerSeqEntry 4 }

		-- 1.3.6.1.4.1.13191.1.10.3.4.21.4.2
		oacConfigMotdBanner OBJECT-TYPE
			SYNTAX		OCTET STRING (SIZE(0..230))
			MAX-ACCESS 	read-write
			STATUS 		current
			DESCRIPTION
				"banner text without a sequence number displayed when attempting
				to login."
			::= { oacBannerConfigObjects 2 }

		-- 1.3.6.1.4.1.13191.1.10.3.4.21.4.3
		oacConfigExecBanner OBJECT-TYPE
			SYNTAX		OCTET STRING (SIZE(0..230))
			MAX-ACCESS 	read-write
			STATUS 		current
			DESCRIPTION
				"banner text without a sequence number displayed when logged in."
			::= { oacBannerConfigObjects 3 }

--
-- DATE AND TIME
--


		-- 1.3.6.1.4.1.13191.1.10.3.4.21.5.1
		oacMiscConfigDateAndTime OBJECT-TYPE
			SYNTAX	DateAndTime
			MAX-ACCESS	read-write
			STATUS		current
			DESCRIPTION
				"Current date and time"
			::= { oacDateAndTimeConfigObjects 1 }

		-- 1.3.6.1.4.1.13191.1.10.3.4.21.5.2
		oacConfigClockDstTable 	OBJECT-TYPE
			SYNTAX		SEQUENCE OF OacConfigClockDstEntry
			MAX-ACCESS 	not-accessible
			STATUS		current
			DESCRIPTION
				"Entry for day light saving this table"
				::= { oacDateAndTimeConfigObjects 2 }

		-- 1.3.6.1.4.1.13191.1.10.3.4.21.5.2.1
		oacConfigClockDstEntry 	OBJECT-TYPE
			SYNTAX OacConfigClockDstEntry
			MAX-ACCESS 	not-accessible
			STATUS 		current
			DESCRIPTION
				"Entry for this table."
			INDEX { oacClockDstName }
			::= { oacConfigClockDstTable 1 }

		OacConfigClockDstEntry ::=
			SEQUENCE {
				oacClockDstName
					OCTET STRING,
				oacClockDstSummerStartWeek
					OCTET STRING,
				oacClockDstSummerStartDate
					OCTET STRING,
				oacClockDstWinterStartWeek
					OCTET STRING,
				oacClockDstWinterStartDate
					OCTET STRING,
				oacClockDstRowStatus
					RowStatus
			}

		-- 1.3.6.1.4.1.13191.1.10.3.4.21.5.2.1.1
		oacClockDstName OBJECT-TYPE
			SYNTAX		OCTET STRING (SIZE(1..255))
			MAX-ACCESS	read-create
			STATUS		current
			DESCRIPTION
				"oacClockDstName is an arbitrary string
				that can ease readability."
			::= { oacConfigClockDstEntry 1 }


		-- 1.3.6.1.4.1.13191.1.10.3.4.21.5.2.1.2
		oacClockDstSummerStartWeek OBJECT-TYPE
			SYNTAX		OCTET STRING (SIZE(1..255))
			MAX-ACCESS	read-create
			STATUS		current
			DESCRIPTION
				"designates the week when the summer time starts"
			::= { oacConfigClockDstEntry 2 }


		-- 1.3.6.1.4.1.13191.1.10.3.4.21.5.2.1.3
		oacClockDstSummerStartDate OBJECT-TYPE
			SYNTAX		OCTET STRING (SIZE(1..255))
			MAX-ACCESS	read-create
			STATUS		current
			DESCRIPTION
				"Summer day light saving start date"
			::= { oacConfigClockDstEntry 3 }


		-- 1.3.6.1.4.1.13191.1.10.3.4.21.5.2.1.4
		oacClockDstWinterStartWeek OBJECT-TYPE
			SYNTAX		OCTET STRING (SIZE(1..255))
			MAX-ACCESS	read-create
			STATUS		current
			DESCRIPTION
				"designates the week when the winter time starts"
			::= { oacConfigClockDstEntry 4 }


		-- 1.3.6.1.4.1.13191.1.10.3.4.21.5.2.1.5
		oacClockDstWinterStartDate OBJECT-TYPE
			SYNTAX		OCTET STRING (SIZE(1..255))
			MAX-ACCESS	read-create
			STATUS		current
			DESCRIPTION
				"Winter day light saving start time."
			::= { oacConfigClockDstEntry 5 }


		-- 1.3.6.1.4.1.13191.1.10.3.4.21.5.2.1.6
		oacClockDstRowStatus OBJECT-TYPE
			SYNTAX		RowStatus
			MAX-ACCESS	read-create
			STATUS		current
			DESCRIPTION
				"RowStatus for this entry."
			::= { oacConfigClockDstEntry 6 }


		-- 1.3.6.1.4.1.13191.1.10.3.4.21.6.1
		oacMiscConfigGroups OBJECT IDENTIFIER ::= { oacMiscConfigConformance 1 }


		-- 1.3.6.1.4.1.13191.1.10.3.4.21.6.1.1
		oacMiscConfigGroup OBJECT-GROUP
			OBJECTS { oacConfigBannerString }
			STATUS current
			DESCRIPTION
				"Group of Misc Configuration objects."
			::= { oacMiscConfigGroups 1 }


		-- 1.3.6.1.4.1.13191.1.10.3.4.21.6.2
		oacMiscCompls OBJECT IDENTIFIER ::= { oacMiscConfigConformance 2 }


	END

--
-- END OF ONE ACCESS MISC CONFIG MIB
--
