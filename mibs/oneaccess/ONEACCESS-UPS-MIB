--          *****************************
--          *             *
--          *         ONEOS MIB     *
--          *             *
--          *****************************
--
--          ONEOS_MIB_STD_V05.2.R001_E001
--
--          Creation date : 05/23/2014


ONEACCESS-UPS-MIB DEFINITIONS ::= BEGIN

   IMPORTS
       MODULE-IDENTITY, OBJECT-TYPE, NOTIFICATION-TYPE,
       OBJECT-IDENTITY, Counter32, Gauge32, Integer32
           FROM SNMPv2-SMI
       DisplayString, TimeStamp, TimeInterval, TestAndIncr,
         AutonomousType
           FROM SNMPv2-TC
       MODULE-COMPLIANCE, OBJECT-GROUP
           FROM SNMPv2-CONF
		oacExpIMManagement
			FROM ONEACCESS-GLOBAL-REG;

   oacUpsMIB MODULE-IDENTITY
       LAST-UPDATED "9402230000Z"
       ORGANIZATION "IETF UPS MIB Working Group"
       CONTACT-INFO
              "        Pascal KESTELOOT

                Postal: ONE ACCESS
                        92140 Clamart, France
                        FRANCE

                   Tel: (+33) 01 41 87 70 54
                   Fax: (+33) 01 41 87 74 39

                E-mail: pascal.kesteloot@oneaccess-net.com"
       DESCRIPTION
               "The MIB module to describe Uninterruptible Power
               Supplies."
       ::= { oacExpIMManagement 1225 }



oacUpsMIBObjects OBJECT IDENTIFIER ::= { oacUpsMIB 1 }
oacUpsBattery OBJECT IDENTIFIER ::= { oacUpsMIBObjects 1 }

-- ------------------------------------------------------------------ --
-- OAC UPS MIB Battery Objects
-- ------------------------------------------------------------------ --

oacUpsBatteryStatus OBJECT-TYPE
       SYNTAX     INTEGER {
           unknown(1),
           batteryNormal(2),
           batteryLow(3),
           batteryDepleted(4)
       }
       MAX-ACCESS read-only
       STATUS     current
       DESCRIPTION
               "The indication of the capacity remaining in the UPS
               system's batteries.   A value of batteryNormal
               indicates that the remaining run-time is greater than
               upsConfigLowBattTime.  A value of batteryLow indicates
               that the remaining battery run-time is less than or
               equal to upsConfigLowBattTime.  A value of
               batteryDepleted indicates that the UPS will be unable
               to sustain the present load when and if the utility
               power is lost (including the possibility that the
               utility power is currently absent and the UPS is
               unable to sustain the output)."
       ::= { oacUpsBattery 1 }

-- ------------------------------------------------------------------ --
-- OAC UPS MIB Alarm Objects
-- ------------------------------------------------------------------ --


oacUpsAlarm OBJECT IDENTIFIER ::= { oacUpsMIBObjects 2 }


oacUpsAlarmsPresent OBJECT-TYPE
       SYNTAX     Gauge32
       MAX-ACCESS read-only
	   STATUS     current
       DESCRIPTION
               "The present number of active alarm conditions."
       ::= { oacUpsAlarm 1 }

oacUpsAlarmDescr OBJECT-TYPE
       SYNTAX     AutonomousType
       MAX-ACCESS read-only
       STATUS     current
       DESCRIPTION
               "A reference to an alarm description object.  The
               object referenced should not be accessible, but rather
               be used to provide a unique description of the alarm
               condition."
       ::= { oacUpsAlarm 2 }

oacUpsAlarmTime OBJECT-TYPE
       SYNTAX     TimeStamp
       MAX-ACCESS read-only
       STATUS     current
       DESCRIPTION
               "The value of sysUpTime when the alarm condition was
               detected.  If the alarm condition was detected at the
               time of agent startup and presumably existed before
               agent startup, the value of upsAlarmTime shall equal
               0."
       ::= { oacUpsAlarm 3 }

-- ------------------------------------------------------------------ --
-- OAC UPS MIB Traps
-- ------------------------------------------------------------------ --


oacUpsTraps OBJECT IDENTIFIER ::= { oacUpsMIB 2 }


oacUpsTrapAlarmEntryAdded NOTIFICATION-TYPE
       OBJECTS {oacUpsAlarmDescr}
       STATUS  current
       DESCRIPTION
               "This trap is sent each time an alarm is inserted into
               to the alarm table.  It is sent on the insertion of
               all alarms except for upsAlarmOnBattery and
               upsAlarmTestInProgress."
     ::= { oacUpsTraps 0 }

oacUpsTrapAlarmEntryRemoved NOTIFICATION-TYPE
       OBJECTS {oacUpsAlarmDescr}
       STATUS  current
       DESCRIPTION
               "This trap is sent each time an alarm is removed from
               the alarm table.  It is sent on the removal of all
               alarms except for upsAlarmTestInProgress."
     ::= { oacUpsTraps 1 }
END
