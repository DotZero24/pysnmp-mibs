--------------------------------------------------------------------
--          *****************************
--          *                           *
--          *         ONEOS MIB         *
--          *                           *
--          *****************************
--
--          ONEOS_MIB_STD_V05.2.R001_E001
--
--          Creation date : 2007-03-08
--
--------------------------------------------------------------------

    ONEACCESS-CONFIGMGMT-MIB DEFINITIONS ::= BEGIN

--------------------------------------------------------------------
-- Imports
--------------------------------------------------------------------

    IMPORTS
        MODULE-IDENTITY, OBJECT-TYPE, Integer32, IpAddress, NOTIFICATION-TYPE
            FROM SNMPv2-SMI
    --
        DateAndTime, TEXTUAL-CONVENTION
            FROM SNMPv2-TC
    --
		MODULE-COMPLIANCE, OBJECT-GROUP
			FROM SNMPv2-CONF
    --
        DisplayString
			FROM RFC1213-MIB
    --
        oacMIBModules, oacExpIMManagement, oacRequirements
            FROM ONEACCESS-GLOBAL-REG;
	--
--------------------------------------------------------------------
-- Module Entity
--------------------------------------------------------------------

    oacConfigMgmtMIBModule MODULE-IDENTITY
        LAST-UPDATED "201110270000Z"
        ORGANIZATION    " OneAccess "
        CONTACT-INFO
            "Pascal KESTELOOT
             Postal: ONE ACCESS
                    381 Avenue du Général de Gaulle
                    92140 Clamart, France
             FRANCE

            Tel: (+33) 01 41 87 70 00
            Fax: (+33) 01 41 87 74 00

             E-mail: pascal.kesteloot@oneaccess-net.com"

		DESCRIPTION
                    	"Contact updated"
    	REVISION        "201110270000Z"

		DESCRIPTION
			"Added MODULE-COMPLIANCE AND OBJECT GROUP,
			fixed some minor corrections."
		REVISION	"201007081000Z"

        DESCRIPTION
            "This MIB module describes a MIB for keeping track of changes
            on equipment's configuration."
        ::= { oacMIBModules 2001 }

--------------------------------------------------------------------
-- Textual Conventions
--------------------------------------------------------------------

--

--------------------------------------------------------------------
-- Objects Definitions
--------------------------------------------------------------------

    oacExpIMConfigMgmt OBJECT IDENTIFIER ::= { oacExpIMManagement 6 }
    oacConfigMgmtObjects OBJECT IDENTIFIER ::= { oacExpIMConfigMgmt 1 }
    oacCMHistory OBJECT IDENTIFIER ::= { oacConfigMgmtObjects 1 }
    oacCMCopy OBJECT IDENTIFIER ::= { oacConfigMgmtObjects 2 }
	oacConfigMgmtNotifications OBJECT IDENTIFIER ::= { oacConfigMgmtObjects 3 }

    --------------------------------------------------------------------
    -- Configuration Management Objects Definition
    --------------------------------------------------------------------

		-- Configuration History

		oacCMHistoryRunningLastChanged OBJECT-TYPE
			SYNTAX 			DateAndTime
			MAX-ACCESS 	read-only
			STATUS 			current
			DESCRIPTION	"The time when the running configuration
									was last changed."
			::= { oacCMHistory 1 }

		oacCMHistoryRunningLastSaved OBJECT-TYPE
			SYNTAX 			DateAndTime
			MAX-ACCESS 	read-only
			STATUS 			current
			DESCRIPTION	"The time when the running configuration
									was last saved (written)."
			::= { oacCMHistory 2 }

		oacCMHistoryStartupLastChanged OBJECT-TYPE
			SYNTAX 			DateAndTime
			MAX-ACCESS 	read-only
			STATUS 			current
			DESCRIPTION	"The time when the startup configuration
									was last written to."
			::= { oacCMHistory 3 }

		oacCMCopyIndex OBJECT-TYPE
			SYNTAX 			IpAddress
			MAX-ACCESS  not-accessible
			STATUS 			current
			DESCRIPTION	"IP address used for configuration copy."
			::= { oacCMCopy 1 }

    oacCMCopyTftpRunTable OBJECT-TYPE
        SYNTAX SEQUENCE OF OacCMCopyTftpRunEntry
        MAX-ACCESS         not-accessible
        STATUS             current
        DESCRIPTION        "Config Table for TFTP copy of running config."
        ::= { oacCMCopy 2 }

    oacCMCopyTftpRunEntry OBJECT-TYPE
        SYNTAX         OacCMCopyTftpRunEntry
        MAX-ACCESS     not-accessible
        STATUS         current
        DESCRIPTION    "List of objects defining a conceptual copy tftp entry."
  			INDEX 			{ oacCMCopyIndex }
        ::= { oacCMCopyTftpRunTable 1 }

    OacCMCopyTftpRunEntry ::= SEQUENCE {
        oacCMCopyTftpRun             DisplayString
    }

		oacCMCopyTftpRun OBJECT-TYPE
			SYNTAX 			DisplayString
			MAX-ACCESS  read-write
			STATUS 			current
			DESCRIPTION	"Name of the file on the server where the configuration script is located.
			            This variable is in effect a write-only variable.
									Attempts to read this variable will result in a no-such-object response."
			::= { oacCMCopyTftpRunEntry 1 }

    oacCMCopyRunTftpTable OBJECT-TYPE
        SYNTAX SEQUENCE OF OacCMCopyRunTftpEntry
        MAX-ACCESS         not-accessible
        STATUS             current
        DESCRIPTION        "Config Table for copy of running config to tftp."
        ::= { oacCMCopy 3 }

    oacCMCopyRunTftpEntry OBJECT-TYPE
        SYNTAX         OacCMCopyRunTftpEntry
        MAX-ACCESS     not-accessible
        STATUS         current
        DESCRIPTION    "List of objects defining a conceptual copy tftp entry."
  			INDEX 			{ oacCMCopyIndex }
        ::= { oacCMCopyRunTftpTable 1 }

    OacCMCopyRunTftpEntry ::= SEQUENCE {
        oacCMCopyRunTftp             DisplayString
    }
		oacCMCopyRunTftp OBJECT-TYPE
			SYNTAX 			DisplayString
			MAX-ACCESS  read-write
			STATUS 			current
			DESCRIPTION	"Name of the file on the server where the configuration script will be stored.
									This variable is in effect a write-only variable.
									Attempts to read this variable will result in a no-such-object response."
			::= { oacCMCopyRunTftpEntry 1 }

	oacCMRunningConfigSaved NOTIFICATION-TYPE
     STATUS       current
     DESCRIPTION
         "The running configuration has been saved."
     ::= { oacConfigMgmtNotifications 1 }
--------------------------------------------------------------------
-- Conformance Definitions
--------------------------------------------------------------------

    oacCMConformance OBJECT IDENTIFIER ::= { oacRequirements 2001 }
    oacCMGroups      OBJECT IDENTIFIER ::= { oacCMConformance 1 }
    oacCMCompliances OBJECT IDENTIFIER ::= { oacCMConformance 2 }

    oacCMCompliance MODULE-COMPLIANCE
        STATUS  current
        DESCRIPTION
            "The compliance statement for agents that support the
             ONEACCESS-CONFIGMGMT-MIB."
        MODULE -- this module
        MANDATORY-GROUPS { oacCMGeneralGroup }
	    ::= { oacCMCompliances 1 }

    oacCMGeneralGroup OBJECT-GROUP
	    OBJECTS {
            oacCMHistoryRunningLastChanged,
            oacCMHistoryRunningLastSaved,
            oacCMHistoryStartupLastChanged
        }
        STATUS  current
        DESCRIPTION
            "This group is mandatory for Configuration Management entity."
        ::= { oacCMGroups 1 }

END
