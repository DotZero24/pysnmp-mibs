--          *****************************
--          *                           *
--          *         ONEOS MIB         *
--          *                           *
--          *****************************
--
--          ONEOS_MIB_STD_V05.1.R002_E004
--
--          Creation date : 07/08/2010

ONEACCESS-BRIDGE-MIB DEFINITIONS ::= BEGIN

IMPORTS
        MODULE-IDENTITY,
        OBJECT-TYPE,
        Integer32, Unsigned32
                FROM SNMPv2-SMI

        MODULE-COMPLIANCE,
        OBJECT-GROUP
                FROM SNMPv2-CONF

        TEXTUAL-CONVENTION,
        DisplayString,
        TruthValue,
        RowStatus
                FROM SNMPv2-TC

	    ifIndex, InterfaceIndex
                FROM IF-MIB
        oacExpIMIp, oacMIBModules
		        FROM ONEACCESS-GLOBAL-REG;


oacBridgeMIB MODULE-IDENTITY

	LAST-UPDATED    "201106150000Z"
        ORGANIZATION    " OneAccess "
        CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

    DESCRIPTION
                    "Contact updated"
    REVISION        "201106150000Z"

	DESCRIPTION
		"Removed the Deprecated group. fixed some minor
		corrections."
	REVISION	"201007081000Z"

	DESCRIPTION
        "This MIB defines configuration capabilities relating to
        Bridge Group on interfaces."

	::= { oacMIBModules 682 }

--
-- Node definitions
--

		oacBridgeObjects OBJECT IDENTIFIER ::= { 	oacExpIMIp 7  }

		oacBridgeConfigObjects      OBJECT IDENTIFIER ::= { oacBridgeObjects 1  }
		oacBridgeConformance        OBJECT IDENTIFIER ::= { oacBridgeObjects 10  }


-- Bridge-group

oacBridgeGroupTable OBJECT-TYPE
    SYNTAX      SEQUENCE OF OacBridgeGroupEntry
    MAX-ACCESS  not-accessible
    STATUS      current
    DESCRIPTION
        "This table contains the  bridge group configuration
        on interfaces."

        ::= { oacBridgeConfigObjects 1  }

oacBridgeGroupEntry OBJECT-TYPE
    SYNTAX      OacBridgeGroupEntry
    MAX-ACCESS  not-accessible
    STATUS      current
    DESCRIPTION
        "An entry in this table defines a Bridged interface."
    INDEX    { oacBridgeGroupValue }
    ::= { oacBridgeGroupTable 1 }

OacBridgeGroupEntry ::= SEQUENCE {
    oacBridgeGroupValue        Unsigned32,
    oacBridgeTransparency      TruthValue,
    oacBridgeGroupRowStatus    RowStatus
}

oacBridgeGroupValue OBJECT-TYPE
    SYNTAX      Unsigned32 (1..255)
    MAX-ACCESS  read-create
    STATUS      current
    DESCRIPTION
        "The Value of a bridge group to assign to an interface"

    ::= { oacBridgeGroupEntry 1 }

oacBridgeTransparency OBJECT-TYPE
    SYNTAX      TruthValue
    MAX-ACCESS  read-create
    STATUS      current
    DESCRIPTION
        "Activation of the transparency of a bridge group"
    DEFVAL     { false }
    ::= { oacBridgeGroupEntry 2 }

oacBridgeGroupRowStatus OBJECT-TYPE
    SYNTAX      RowStatus
    MAX-ACCESS  read-create
    STATUS      current
    DESCRIPTION
        "This object allows the creation, modification, or deletion of the row"
    ::= { oacBridgeGroupEntry 3 }


-- Interface : Brigde Group configuration per interface
--

oacBridgeGroupInterfaceTable OBJECT-TYPE
    SYNTAX SEQUENCE OF OacBridgeGroupInterfaceEntry
    MAX-ACCESS not-accessible
    STATUS current
    DESCRIPTION
        "Table for configuration of Bridge Group per Interface"
    ::= { oacBridgeConfigObjects 2 }

oacBridgeGroupInterfaceEntry OBJECT-TYPE
    SYNTAX OacBridgeGroupInterfaceEntry
    MAX-ACCESS not-accessible
    STATUS current
    DESCRIPTION
        "An entry in Bridge Group table."
    INDEX { ifIndex }
    ::= { oacBridgeGroupInterfaceTable 1 }

OacBridgeGroupInterfaceEntry ::= SEQUENCE {
    oacInBridgeGroupValue    Unsigned32,
    oacBridgeGroupInterfaceName    DisplayString,
    oacBridgeGroupInterfaceRowStatus    RowStatus
}

oacInBridgeGroupValue OBJECT-TYPE
    SYNTAX      Unsigned32 (1..255)
    MAX-ACCESS  read-create
    STATUS      current
    DESCRIPTION
        "The Value of a bridge group to assign to an interface"

    ::= { oacBridgeGroupInterfaceEntry 1 }

oacBridgeGroupInterfaceName OBJECT-TYPE
    SYNTAX DisplayString
    MAX-ACCESS read-create
    STATUS current
    DESCRIPTION
        "The name of the interface to which the bridge group is applied.
	 This is read-only "
    ::= { oacBridgeGroupInterfaceEntry 2 }

oacBridgeGroupInterfaceRowStatus OBJECT-TYPE
    SYNTAX RowStatus
    MAX-ACCESS read-create
    STATUS current
    DESCRIPTION
        "The row status for this entry."
    ::= { oacBridgeGroupInterfaceEntry 3}


oacBridgeGroupConfigGroups OBJECT IDENTIFIER ::= { oacBridgeConformance 1 }

		oacBridgeGroupConfigGroup OBJECT-GROUP
			OBJECTS { oacBridgeGroupValue, oacBridgeGroupInterfaceName }
			STATUS current
			DESCRIPTION
				"Group of Bridge Group objects"
			::= { oacBridgeGroupConfigGroups 1 }

		oacBridgeGroupCompls OBJECT IDENTIFIER ::= { oacBridgeConformance 2 }


END
