--          *****************************
--          *                           *
--          *         ONEOS MIB         *
--          *                           *
--          *****************************
--
--          ONEOS_MIB_STD_V05.1.R005_E001
--
--          Creation date : 07/08/2010

	ONEACCESS-SSH-CONFIG-MIB DEFINITIONS ::= BEGIN

		IMPORTS
			OBJECT-GROUP
				FROM SNMPv2-CONF
			IpAddress, Integer32, Counter32, Counter64, Unsigned32,
			OBJECT-TYPE, MODULE-IDENTITY
				FROM SNMPv2-SMI
			DisplayString, RowStatus, PhysAddress, TruthValue
				FROM SNMPv2-TC
			oacExpIMIpAcl, oacMIBModules, oacExpIMManagement
		        FROM ONEACCESS-GLOBAL-REG;

	oacSshConfigMIB MODULE-IDENTITY

        LAST-UPDATED    "201107260000Z"
        ORGANIZATION    " OneAccess "
        CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

	DESCRIPTION
			"Fixed the issues related to octet string range"
	REVISION	"201107260000Z"

	DESCRIPTION
        		"Contact updated"
	REVISION        "201106150000Z"

	DESCRIPTION
        "MIB for displaying and configuring
		Secure Shell (SSH) related features."
		::= { oacMIBModules 2004 }

--
-- Node definitions
--

	-- 1.3.6.1.4.1.13191.1.10.3.4.22
	oacSshConfig OBJECT IDENTIFIER ::= { oacExpIMManagement 22 }


	-- 1.3.6.1.4.1.13191.1.10.3.4.22.1
	oacSshConfigObjects      OBJECT IDENTIFIER ::= { oacSshConfig 1  }


	-- 1.3.6.1.4.1.13191.1.10.3.4.22.2
	oacSshConfigConformance  OBJECT IDENTIFIER ::= { oacSshConfig 2  }


--
-- Ssh Configuration
--

		-- 1.3.6.1.4.1.13191.1.10.3.4.22.1.1
		oacSshDsaKey OBJECT-TYPE
			SYNTAX	INTEGER
					{
					keysize-0bits(0),
					keysize-256bits(256),
					keysize-512bits(512),
					keysize-1024bits(1024),
					keysize-2048bits(2048)
					}
			MAX-ACCESS 	read-write
			STATUS 		current
			DESCRIPTION
				"To generate a public key."
			::= { oacSshConfigObjects 1 }


		-- 1.3.6.1.4.1.13191.1.10.3.4.22.1.2
		oacSshEnabled   OBJECT-TYPE
			SYNTAX        TruthValue
			MAX-ACCESS    read-write
			STATUS        current
			DESCRIPTION
				"Controls the operation of the Secure Shell server task
				on the oneos. When enabled, the SSH server will accept
				connection requests and create a secure transport layer
				on which to transmit system configuration data."
			DEFVAL { false }
			::= { oacSshConfigObjects 2 }


		-- 1.3.6.1.4.1.13191.1.10.3.4.22.1.3
		oacSshIdleTimeout OBJECT-TYPE
			SYNTAX 		Unsigned32 (120..4294967295)
			UNITS       "seconds"
			MAX-ACCESS 	read-write
			STATUS 		current
			DESCRIPTION
				"If a connected SSH client is inactive during a certain time,
				it is disconnected. By default, any inactive SSH client is
				disconnected after 10 minutes."
			DEFVAL { 600 }
			::= { oacSshConfigObjects 3 }


		-- 1.3.6.1.4.1.13191.1.10.3.4.22.1.4
		oacSshAuthTimeout OBJECT-TYPE
			SYNTAX 		INTEGER (5..120)
			UNITS       "seconds"
			MAX-ACCESS 	read-write
			STATUS 		current
			DESCRIPTION
				"If an SSH client is in the authentication phase and it is
				inactive during a certain time it is disconnected. By default,
				any inactive SSH client doing an authentication is disconnected
				after 2 minutes."
			DEFVAL { 120 }
			::= { oacSshConfigObjects 4 }


		-- 1.3.6.1.4.1.13191.1.10.3.4.22.1.5
		oacSshAuthRetries OBJECT-TYPE
			SYNTAX 		INTEGER
			MAX-ACCESS 	read-write
			STATUS 		current
			DESCRIPTION
				"By default, the authentication retries number is 3."
			DEFVAL { 3 }
			::= { oacSshConfigObjects 5 }


		-- 1.3.6.1.4.1.13191.1.10.3.4.22.1.6
		oacSshBindInterface OBJECT-TYPE
			SYNTAX 		OCTET STRING (SIZE(1..255))
			MAX-ACCESS 	read-write
			STATUS 		current
			DESCRIPTION
				"To permit SSH access from an interface,
				default configuration is any."
			DEFVAL { "any" }
			::= { oacSshConfigObjects 6 }


		-- 1.3.6.1.4.1.13191.1.10.3.4.22.1.7
		oacSshBindAcl OBJECT-TYPE
			SYNTAX 		OCTET STRING (SIZE(0..255))
			MAX-ACCESS 	read-write
			STATUS 		current
			DESCRIPTION
				"To restrict access to SSH clients by using a
				list of addresses standing for the list of
				permitted source IP addresses."
			::= { oacSshConfigObjects 7 }


		-- 1.3.6.1.4.1.13191.1.10.3.4.22.1.8
		oacSshMaxSessions OBJECT-TYPE
			SYNTAX 		INTEGER (1..5)
			MAX-ACCESS 	read-write
			STATUS 		current
			DESCRIPTION
				"By default, the maximum number of channels
				per session is 5 and the maximum number of
				local port forwarding sessions is 5."
			DEFVAL { 5 }
			::= { oacSshConfigObjects 8 }


		-- 1.3.6.1.4.1.13191.1.10.3.4.22.1.9
		oacSshMaxSessionChannels OBJECT-TYPE
			SYNTAX 		INTEGER (1..10)
			MAX-ACCESS 	read-write
			STATUS 		current
			DESCRIPTION
				"Maximum number of channels that a SSH session can use."
			DEFVAL { 10 }
			::= { oacSshConfigObjects 9 }


		-- 1.3.6.1.4.1.13191.1.10.3.4.22.2.1
		oacSshConfigGroups OBJECT IDENTIFIER ::= { oacSshConfigConformance 1 }


		-- 1.3.6.1.4.1.13191.1.10.3.4.22.2.1.1
		oacSshConfigGroup OBJECT-GROUP
			OBJECTS { oacSshEnabled }
			STATUS current
			DESCRIPTION
				"Group of SSH objects"
			::= { oacSshConfigGroups 1 }


		-- 1.3.6.1.4.1.13191.1.10.3.4.22.2.2
		oacSshCompls OBJECT IDENTIFIER ::= { oacSshConfigConformance 2 }

	END

--
-- END OF ONE ACCESS SSH CONFIG MIB
--
