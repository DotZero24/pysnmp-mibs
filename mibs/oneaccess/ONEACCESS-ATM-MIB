--          *****************************
--          *                           *
--          *         ONEOS MIB         *
--          *                           *
--          *****************************
--
--          ONEOS_MIB_STD_V05.1.R005_E001
--
--          Creation date : 22/01/2003
--
--          Compatibility with ONEOS_V31
--
--          Compatibility with ONEOS_V32
--



     ONEACCESS-ATM-MIB DEFINITIONS ::= BEGIN

     IMPORTS
        MODULE-IDENTITY, OBJECT-TYPE,Counter32,Integer32
			FROM SNMPv2-SMI
		MODULE-COMPLIANCE, OBJECT-GROUP
			FROM SNMPv2-CONF
		AtmVcIdentifier, AtmVpIdentifier
			FROM ATM-TC-MIB
        InterfaceIndex, ifIndex
			FROM IF-MIB
 	    oacExpIMAtmStatistics,oacMIBModules
			FROM ONEACCESS-GLOBAL-REG;

     oacAtmMIBModule MODULE-IDENTITY
			LAST-UPDATED "201110270000Z"
			ORGANIZATION " OneAccess "
         CONTACT-INFO
           "Pascal KESTELOOT
            Postal: ONE ACCESS
                    381 Avenue du Général de Gaulle
                    92140 Clamart, France
		    FRANCE

            Tel: (+33) 01 41 87 70 00
            Fax: (+33) 01 41 87 74 00
            E-mail: pascal.kesteloot@oneaccess-net.com"

         DESCRIPTION
         		           	"Contact updated"
	    	REVISION        "201110270000Z"

			DESCRIPTION
				"Fixed some minor corrections."
			REVISION	"201007080001Z"
			DESCRIPTION
              "This MIB module describes ATM Management objects."

	::= { oacMIBModules 667 }

oacAtmStatObjects OBJECT IDENTIFIER ::= { oacExpIMAtmStatistics 1 }
oacAtmStatNotifications OBJECT IDENTIFIER ::= { oacExpIMAtmStatistics 2 }
oacAtmStatConformance OBJECT IDENTIFIER ::= { oacExpIMAtmStatistics 3 }

oacAtmChannelTable OBJECT-TYPE
		SYNTAX SEQUENCE OF OacAtmChannelEntry
		MAX-ACCESS not-accessible
		STATUS current
		DESCRIPTION
			"The table representing the oacAtmChannel"
	 ::= { oacAtmStatObjects 1 }

oacAtmChannelEntry OBJECT-TYPE
		SYNTAX OacAtmChannelEntry
		MAX-ACCESS not-accessible
		STATUS current
		DESCRIPTION
			"An index into the table oacAtmChannelTable"
		INDEX {ifIndex,oacAtmChanVpi,oacAtmChanVci }
::= { oacAtmChannelTable 1 }

OacAtmChannelEntry ::= SEQUENCE {
		oacAtmChanVpi AtmVpIdentifier,
		oacAtmChanVci AtmVcIdentifier,
		oacAtmChanTxBytes   Counter32,
		oacAtmChanTxCells Counter32,
		oacAtmChanRxBytes Counter32,
		oacAtmChanRxCells  Counter32,
		oacAtmChanRxErrors Counter32,
		oacAtmChanTxOverflows Counter32
	}

oacAtmChanVpi OBJECT-TYPE
		SYNTAX AtmVpIdentifier
		MAX-ACCESS not-accessible
		STATUS current
		DESCRIPTION
			"  Virtual Path Id for the connexion"
	 ::= { oacAtmChannelEntry 1 }

oacAtmChanVci OBJECT-TYPE
		SYNTAX AtmVcIdentifier
		MAX-ACCESS not-accessible
		STATUS current
		DESCRIPTION
			"   Virtual Channel Id for the connexion"
	 ::= { oacAtmChannelEntry 2 }

oacAtmChanTxBytes OBJECT-TYPE
		SYNTAX Counter32
		MAX-ACCESS read-only
		STATUS current
		DESCRIPTION
			"  Total transmitted UINT8s counter"
	 ::= { oacAtmChannelEntry 3 }

oacAtmChanTxCells OBJECT-TYPE
		SYNTAX Counter32
		MAX-ACCESS read-only
		STATUS current
		DESCRIPTION
			"  Total transmitted cells counter"
	 ::= { oacAtmChannelEntry 4 }

oacAtmChanRxBytes OBJECT-TYPE
		SYNTAX Counter32
		MAX-ACCESS read-only
		STATUS current
		DESCRIPTION
			"  Total received UINT8s counter"
	 ::= { oacAtmChannelEntry 5 }

oacAtmChanRxCells OBJECT-TYPE
		SYNTAX Counter32
		MAX-ACCESS read-only
		STATUS current
		DESCRIPTION
			"  Total received cells counter"
	 ::= { oacAtmChannelEntry 6 }

oacAtmChanRxErrors OBJECT-TYPE
		SYNTAX Counter32
		MAX-ACCESS read-only
		STATUS current
		DESCRIPTION
			      " Total receive errors counter.
				For AAL0: counts number of CRC10 errors.
				For AAL1: counts number of SN errors.
				For AA5: counts frames with errors"
	 ::= { oacAtmChannelEntry 7 }

oacAtmChanTxOverflows OBJECT-TYPE
		SYNTAX Counter32
		MAX-ACCESS read-only
		STATUS current
		DESCRIPTION
			" Transmit overflow counter. It counts the number of frames discarded
			due to transmit queue overflow or transmit BD overflow for AAL5 and
			AAL1 channels and the number of cells discarded due to the same
			reasons for AAL0 channels"

	 ::= { oacAtmChannelEntry 8 }


oacAtmAal0ChannelGlobalStatTable OBJECT-TYPE
		SYNTAX SEQUENCE OF OacAtmAal0ChannelGlobalStatEntry
		MAX-ACCESS not-accessible
		STATUS current
		DESCRIPTION
			" The table representing oacAtmAal0ChannelGlobalStats"
	 ::= { oacAtmStatObjects 2 }

oacAtmAal0ChannelGlobalStatEntry OBJECT-TYPE
		SYNTAX OacAtmAal0ChannelGlobalStatEntry
		MAX-ACCESS not-accessible
		STATUS current
		DESCRIPTION
			"An index into the table oacAtmAal0ChannelGlobalStatTable"
		INDEX { ifIndex,oacAtmChanVpi,oacAtmChanVci }
::= { oacAtmAal0ChannelGlobalStatTable 1 }

OacAtmAal0ChannelGlobalStatEntry ::= SEQUENCE {
		oacAtmAal0ChanRxCellsDiscarded Counter32
	}

oacAtmAal0ChanRxCellsDiscarded OBJECT-TYPE
		SYNTAX Counter32
		MAX-ACCESS read-only
		STATUS current
		DESCRIPTION
			"Cells discarded due to busy condition counter"
	 ::= { oacAtmAal0ChannelGlobalStatEntry 1 }


oacAtmAal1ChannelGlobalStatTable OBJECT-TYPE
		SYNTAX SEQUENCE OF OacAtmAal1ChannelGlobalStatEntry
		MAX-ACCESS not-accessible
		STATUS current
		DESCRIPTION
			"An index into the table oacAtmAal1ChannelGlobalStatTable"
	 ::= { oacAtmStatObjects 3 }

oacAtmAal1ChannelGlobalStatEntry OBJECT-TYPE
		SYNTAX OacAtmAal1ChannelGlobalStatEntry
		MAX-ACCESS not-accessible
		STATUS current
		DESCRIPTION
			"An index into the table oacAtmAal1ChannelGlobalStatTable"
		INDEX { ifIndex,oacAtmChanVpi,oacAtmChanVci }
::= { oacAtmAal1ChannelGlobalStatTable 1 }

OacAtmAal1ChannelGlobalStatEntry ::= SEQUENCE {
		oacAtmAal1ChanTxUnderflows Counter32,
		oacAtmAal1ChanRxOverflows Counter32
	}

oacAtmAal1ChanTxUnderflows OBJECT-TYPE
		SYNTAX Counter32
		MAX-ACCESS read-only
		STATUS current
		DESCRIPTION
			"Transmit buffer underflows counter"
	 ::= { oacAtmAal1ChannelGlobalStatEntry 1 }

oacAtmAal1ChanRxOverflows OBJECT-TYPE
		SYNTAX Counter32
		MAX-ACCESS read-only
		STATUS current
		DESCRIPTION
			"Receive buffer overflows counter"
	 ::= { oacAtmAal1ChannelGlobalStatEntry 2 }

oacAtmAal5ChannelGlobalStatTable OBJECT-TYPE
		SYNTAX SEQUENCE OF OacAtmAal5ChannelGlobalStatEntry
		MAX-ACCESS not-accessible
		STATUS current
		DESCRIPTION
			"An index into the table oacAtmAal5ChannelGlobalStatEntry"
	 ::= { oacAtmStatObjects 4 }

oacAtmAal5ChannelGlobalStatEntry OBJECT-TYPE
		SYNTAX OacAtmAal5ChannelGlobalStatEntry
		MAX-ACCESS not-accessible
		STATUS current
		DESCRIPTION
			"An index into the table oacAtmAal5ChannelGlobalStatEntry"
		INDEX { ifIndex,oacAtmChanVpi,oacAtmChanVci }
::= { oacAtmAal5ChannelGlobalStatTable 1 }

OacAtmAal5ChannelGlobalStatEntry ::= SEQUENCE {
		oacAtmAal5ChanTxFrames Counter32,
		oacAtmAal5ChanRxFrames Counter32,
		oacAtmAal5ChanRxFramesDiscarded Counter32,
		oacAtmAal5ChanCrc32Errors Counter32,
		oacAtmAal5ChanLengthErrors Counter32,
		oacAtmAal5ChanReassemblyTimeouts Counter32
	}

oacAtmAal5ChanTxFrames OBJECT-TYPE
		SYNTAX Counter32
		MAX-ACCESS read-only
		STATUS current
		DESCRIPTION
			"Total AAL5 transmitted frames counter"
	 ::= { oacAtmAal5ChannelGlobalStatEntry 1 }

oacAtmAal5ChanRxFrames OBJECT-TYPE
		SYNTAX Counter32
		MAX-ACCESS read-only
		STATUS current
		DESCRIPTION
			"Total AAL5 received frames counter"
	 ::= { oacAtmAal5ChannelGlobalStatEntry 2 }

oacAtmAal5ChanRxFramesDiscarded OBJECT-TYPE
		SYNTAX Counter32
		MAX-ACCESS read-only
		STATUS current
		DESCRIPTION
			"Total AAL5 receive frames discarded counter"
	 ::= { oacAtmAal5ChannelGlobalStatEntry 3 }

oacAtmAal5ChanCrc32Errors OBJECT-TYPE
		SYNTAX Counter32
		MAX-ACCESS read-only
		STATUS current
		DESCRIPTION
			"AAL5 frames with CRC32 error counter"
	 ::= { oacAtmAal5ChannelGlobalStatEntry 4 }

oacAtmAal5ChanLengthErrors OBJECT-TYPE
		SYNTAX Counter32
		MAX-ACCESS read-only
		STATUS current
		DESCRIPTION
			"AAL5 frames with length error counter"
	 ::= { oacAtmAal5ChannelGlobalStatEntry 5 }

oacAtmAal5ChanReassemblyTimeouts OBJECT-TYPE
		SYNTAX Counter32
		MAX-ACCESS read-only
		STATUS current
		DESCRIPTION
			"AAL5 reassembling timeouts counter"
	 ::= { oacAtmAal5ChannelGlobalStatEntry 6 }

oacAtmPortStatTable OBJECT-TYPE
		SYNTAX SEQUENCE OF OacAtmPortStatEntry
		MAX-ACCESS not-accessible
		STATUS current
		DESCRIPTION
			"An entry into the table oacAtmPortStatEntry"
	 ::= { oacAtmStatObjects 5 }

oacAtmPortStatEntry OBJECT-TYPE
		SYNTAX OacAtmPortStatEntry
		MAX-ACCESS not-accessible
		STATUS current
		DESCRIPTION
			"An entry into the table oacAtmPortStatEntry"
		INDEX { ifIndex}
::= { oacAtmPortStatTable 1 }

OacAtmPortStatEntry ::= SEQUENCE {
		oacAtmPortTxCells Counter32,
		oacAtmPortRxCells Counter32,
		oacAtmPortRxCellsDiscarded Counter32,
		oacAtmPortHecErrors Counter32
	}

oacAtmPortTxCells OBJECT-TYPE
		SYNTAX Counter32
		MAX-ACCESS read-only
		STATUS current
		DESCRIPTION
			"Total transmitted cells for ATM port counter"
	 ::= { oacAtmPortStatEntry  1 }

oacAtmPortRxCells OBJECT-TYPE
		SYNTAX Counter32
		MAX-ACCESS read-only
		STATUS current
		DESCRIPTION
			"Total received cells for ATM port counter"
	 ::= { oacAtmPortStatEntry  2 }

oacAtmPortRxCellsDiscarded OBJECT-TYPE
		SYNTAX Counter32
		MAX-ACCESS read-only
		STATUS current
		DESCRIPTION
			"Receive cells discarded counter.
			Cells discarded due to: UTOPIA errors,
			header validation (mis-insertion),
			CRC10 error for AAL5-ABR channels"
	 ::= { oacAtmPortStatEntry  3 }

oacAtmPortHecErrors OBJECT-TYPE
		SYNTAX Counter32
		MAX-ACCESS read-only
		STATUS current
		DESCRIPTION
			"Cells received with HEC error counter"
	 ::= { oacAtmPortStatEntry  4 }


oacAtmAal5PortStatTable OBJECT-TYPE
		SYNTAX SEQUENCE OF OacAtmAal5PortStatEntry
		MAX-ACCESS not-accessible
		STATUS current
		DESCRIPTION
			"An entry into the table oacAtmAal5PortStatTable"
	 ::= { oacAtmStatObjects 6 }

oacAtmAal5PortStatEntry OBJECT-TYPE
		SYNTAX OacAtmAal5PortStatEntry
		MAX-ACCESS not-accessible
		STATUS current
		DESCRIPTION
			"An entry into the table oacAtmAal5PortStatTable"
		INDEX { ifIndex}
::= { oacAtmAal5PortStatTable 1 }

OacAtmAal5PortStatEntry ::= SEQUENCE {
		oacAtmAal5PortTxBytes Counter32,
		oacAtmAal5PortTxFrames Counter32,
		oacAtmAal5PortTxFramesDiscarded Counter32,
		oacAtmAal5PortRxBytes Counter32,
		oacAtmAal5PortRxFrames Counter32,
		oacAtmAal5PortRxErrors Counter32,
		oacAtmAal5PortRxFramesDiscarded Counter32
	}

oacAtmAal5PortTxBytes OBJECT-TYPE
		SYNTAX Counter32
		MAX-ACCESS read-only
		STATUS current
		DESCRIPTION
			"Total transmitted bytes counter"
	 ::= { oacAtmAal5PortStatEntry  1 }

oacAtmAal5PortTxFrames OBJECT-TYPE
		SYNTAX Counter32
		MAX-ACCESS read-only
		STATUS current
		DESCRIPTION
			"Total transmitted frames counter"
	 ::= { oacAtmAal5PortStatEntry  2 }

oacAtmAal5PortTxFramesDiscarded OBJECT-TYPE
		SYNTAX Counter32
		MAX-ACCESS read-only
		STATUS current
		DESCRIPTION
			"Transmit frames discarded counter
			(due to transmit queue overflow)"
	 ::= { oacAtmAal5PortStatEntry  3 }

oacAtmAal5PortRxBytes OBJECT-TYPE
		SYNTAX Counter32
		MAX-ACCESS read-only
		STATUS current
		DESCRIPTION
			"Total received bytes counter"
	 ::= { oacAtmAal5PortStatEntry  4 }

oacAtmAal5PortRxFrames OBJECT-TYPE
		SYNTAX Counter32
		MAX-ACCESS read-only
		STATUS current
		DESCRIPTION
			"Total received frames counter"
	 ::= { oacAtmAal5PortStatEntry  5 }

oacAtmAal5PortRxErrors OBJECT-TYPE
		SYNTAX Counter32
		MAX-ACCESS read-only
		STATUS current
		DESCRIPTION
			"Total receive errors counter
			(CRC32 errors, length errors, RAS timeouts)"
	 ::= { oacAtmAal5PortStatEntry  6 }

oacAtmAal5PortRxFramesDiscarded OBJECT-TYPE
		SYNTAX Counter32
		MAX-ACCESS read-only
		STATUS current
		DESCRIPTION
			"Total receive frames discarded counter"
	 ::= { oacAtmAal5PortStatEntry  7 }


oacAtmStatGroups OBJECT IDENTIFIER ::= { oacAtmStatConformance 1}

oacAtmStatCompliances OBJECT IDENTIFIER ::= { oacAtmStatConformance 2}

oacAtmStatCompliance MODULE-COMPLIANCE
      STATUS  current
      DESCRIPTION
          "The compliance statement for agents that support the
          OA-ATM-MIB."
      MODULE -- this module
          MANDATORY-GROUPS { oacAtmStatGeneralGroup
                }
--          GROUP atmStatGeneralGroup
--
--         DESCRIPTION
--             "This group optional, when declared here."
	::= { oacAtmStatCompliances 1}

oacAtmStatGeneralGroup OBJECT-GROUP
	OBJECTS {
		oacAtmChanTxBytes,
		oacAtmChanTxCells,
		oacAtmChanRxBytes,
		oacAtmChanRxCells,
		oacAtmChanRxErrors,
		oacAtmChanTxOverflows,
		oacAtmAal0ChanRxCellsDiscarded,
		oacAtmAal1ChanTxUnderflows,
		oacAtmAal1ChanRxOverflows,
		oacAtmAal5ChanTxFrames,
		oacAtmAal5ChanRxFrames,
		oacAtmAal5ChanRxFramesDiscarded,
		oacAtmAal5ChanCrc32Errors,
		oacAtmAal5ChanLengthErrors,
		oacAtmAal5ChanReassemblyTimeouts,
		oacAtmPortTxCells,
		oacAtmPortRxCells,
		oacAtmPortRxCellsDiscarded,
		oacAtmPortHecErrors,
		oacAtmAal5PortTxBytes,
		oacAtmAal5PortTxFrames,
		oacAtmAal5PortTxFramesDiscarded,
		oacAtmAal5PortRxBytes,
		oacAtmAal5PortRxFrames,
		oacAtmAal5PortRxErrors,
		oacAtmAal5PortRxFramesDiscarded
}

STATUS  current
      DESCRIPTION
          "This group is mandatory for all  ATM entities."
      ::= { oacAtmStatGroups 1 }


END
--
