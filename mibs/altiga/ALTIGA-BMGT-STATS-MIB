-- *------------------------------------------------------------------
-- * ALTIGA-BMGT-STATS-MIB.my:  Altiga Bandwidth Limiting/Guarantee and Policy Statistics MIB.
-- *
-- * Altiga Networks was acquired by Cisco Systems on March 29, 2000
-- *
-- * Copyright (c) 2002 by Cisco Systems, Inc.
-- * All rights reserved.
-- *
-- *------------------------------------------------------------------

ALTIGA-BMGT-STATS-MIB DEFINITIONS ::= BEGIN

   IMPORTS
      MODULE-IDENTITY, OBJECT-TYPE, Counter32, Unsigned32
         FROM SNMPv2-SMI
      RowStatus
         FROM SNMPv2-TC
      OBJECT-GROUP, MODULE-COMPLIANCE
         FROM SNMPv2-CONF
      alBwMgmtGroup, alStatsBwMgmt
         FROM ALTIGA-MIB
      alBwMgmtMibModule
         FROM ALTIGA-GLOBAL-REG;

   altigaBwMgmMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga Bandwidth Limiting/Guarantee and Policy Statistics MIB
          models counters and objects that are of management interest for bandwidth
          management.

          Acronyms
          The following acronyms are used in this document:

            BW:         Bandwidth

            MIB:        Management Information Base

         "

        REVISION "200209051300Z"
        DESCRIPTION
                "Added module compliance."

        REVISION "200207100000Z"
        DESCRIPTION
                "Updated with new header"

      ::= { alBwMgmtMibModule 2 }

-- +++++++++++++++++++++++++++++++++++++++++++++++++++++++
-- MIB Objects
-- +++++++++++++++++++++++++++++++++++++++++++++++++++++++

alBwMgmtStatsGlobal OBJECT IDENTIFIER ::= { alStatsBwMgmt 1 }

-- Any global stuff here...

alBwMgmtStatTable OBJECT-TYPE
   SYNTAX     SEQUENCE OF AlBwMgmtStatEntry
   MAX-ACCESS not-accessible
   STATUS     current
   DESCRIPTION
      "A table of BW Management status entries."
   ::= { alStatsBwMgmt 2 }

alBwMgmtStatEntry OBJECT-TYPE
   SYNTAX     AlBwMgmtStatEntry
   MAX-ACCESS not-accessible
   STATUS     current
   DESCRIPTION
      "A collection of bandwidth mgmt status objects on this
       interface."
   INDEX      { alBwMgmtStatIntfId }
   ::= { alBwMgmtStatTable 1 }

AlBwMgmtStatEntry ::=
SEQUENCE {
   alBwMgmtStatRowStatus               RowStatus,
   alBwMgmtStatIntfId                  INTEGER,
   alBwMgmtStatGrpId                   INTEGER,
   alBwMgmtStatInConformedRate         Unsigned32,
   alBwMgmtStatInDroppedRate           Unsigned32,
   alBwMgmtStatInConformedBytes        Counter32,
   alBwMgmtStatInDroppedBytes          Counter32,
   alBwMgmtStatOutConformedRate        Unsigned32,
   alBwMgmtStatOutDroppedRate          Unsigned32,
   alBwMgmtStatOutConformedBytes       Counter32,
   alBwMgmtStatOutDroppedBytes         Counter32
}

alBwMgmtStatRowStatus OBJECT-TYPE
   SYNTAX     RowStatus
   MAX-ACCESS read-only
   STATUS     current
   DESCRIPTION
      "The status of this row."
   ::= { alBwMgmtStatEntry 1 }

alBwMgmtStatIntfId OBJECT-TYPE
   SYNTAX     INTEGER (1..3)
   MAX-ACCESS read-only
   STATUS     current
   DESCRIPTION
      "BwPolicy identifier used as the index of this row."
   ::= { alBwMgmtStatEntry 2 }

alBwMgmtStatGrpId OBJECT-TYPE
   SYNTAX     INTEGER (0..100000)
   MAX-ACCESS read-only
   STATUS     current
   DESCRIPTION
      "BwPolicy identifier used as the index of this row."
   ::= { alBwMgmtStatEntry 3 }

alBwMgmtStatInConformedRate OBJECT-TYPE
   SYNTAX     Unsigned32
   UNITS      "kbytes"
   MAX-ACCESS read-only
   STATUS     current
   DESCRIPTION
      "The counter of packets permitted by this rate limit."
   ::= { alBwMgmtStatEntry 4 }

alBwMgmtStatInDroppedRate OBJECT-TYPE
   SYNTAX     Unsigned32
   UNITS      "kbytes"
   MAX-ACCESS read-only
   STATUS     current
   DESCRIPTION
      "The counter of packets which exceeded this rate limit."
   ::= { alBwMgmtStatEntry 5 }

alBwMgmtStatInConformedBytes OBJECT-TYPE
   SYNTAX     Counter32
   UNITS      "bytes"
   MAX-ACCESS read-only
   STATUS     current
   DESCRIPTION
      "The counter of bytes which exceeded this rate limit."
   ::= { alBwMgmtStatEntry 6 }

alBwMgmtStatInDroppedBytes OBJECT-TYPE
   SYNTAX     Counter32
   UNITS      "bytes"
   MAX-ACCESS read-only
   STATUS     current
   DESCRIPTION
      "The counter of bytes which exceeded this rate limit."
   ::= { alBwMgmtStatEntry 7 }


alBwMgmtStatOutConformedRate OBJECT-TYPE
   SYNTAX     Unsigned32
   UNITS      "kbytes"
   MAX-ACCESS read-only
   STATUS     current
   DESCRIPTION
      "The counter of packets permitted by this rate limit."
   ::= { alBwMgmtStatEntry 8 }

alBwMgmtStatOutDroppedRate OBJECT-TYPE
   SYNTAX     Unsigned32
   UNITS      "kbytes"
   MAX-ACCESS read-only
   STATUS     current
   DESCRIPTION
      "The counter of packets which exceeded this rate limit."
   ::= { alBwMgmtStatEntry 9 }

alBwMgmtStatOutConformedBytes OBJECT-TYPE
   SYNTAX     Counter32
   UNITS      "bytes"
   MAX-ACCESS read-only
   STATUS     current
   DESCRIPTION
      "The counter of bytes which exceeded this rate limit."
   ::= { alBwMgmtStatEntry 10 }

alBwMgmtStatOutDroppedBytes OBJECT-TYPE
   SYNTAX     Counter32
   UNITS      "bytes"
   MAX-ACCESS read-only
   STATUS     current
   DESCRIPTION
      "The counter of bytes which exceeded this rate limit."
   ::= { alBwMgmtStatEntry 11 }

altigaBwMgmMibConformance OBJECT IDENTIFIER ::= { altigaBwMgmMibModule 1 }
altigaBwMgmMibCompliances OBJECT IDENTIFIER ::= { altigaBwMgmMibConformance 1 }

altigaBwMgmMibCompliance MODULE-COMPLIANCE
   STATUS         current
   DESCRIPTION
      "The compliance statement for agents which
       implement the Bandwidth Limiting/Guarantee and Policy Statistics MIB."
   MODULE
   MANDATORY-GROUPS {
      alBwMgmtStatsGroup
   }
   ::= { altigaBwMgmMibCompliances 1 }

alBwMgmtStatsGroup OBJECT-GROUP
   OBJECTS {
      alBwMgmtStatRowStatus,
      alBwMgmtStatIntfId,
      alBwMgmtStatGrpId,
      alBwMgmtStatInConformedRate,
      alBwMgmtStatInDroppedRate,
      alBwMgmtStatInConformedBytes,
      alBwMgmtStatInDroppedBytes,
      alBwMgmtStatOutConformedRate,
      alBwMgmtStatOutDroppedRate,
      alBwMgmtStatOutConformedBytes,
      alBwMgmtStatOutDroppedBytes
   }
   STATUS     current
   DESCRIPTION
      "A collection of objects providing BW Management monitoring."
   ::= { alBwMgmtGroup 2 }

END
