-- Dell Networking OS DCB Proprietary MIB Definition

-- This document explains the proprietary MIB implemented
-- for the DCB Features.

-- Data Center Bridging is a flexible framework that defines the
-- capabilities required for switches and end points to be part of a
-- data center network.

-- DCB contains the following capabilities:

--  1. Priority-based flow control (PFC; IEEE 802.1Qbb)
--     The Priority-based Flow Control (PFC) feature is used for a
--     link level flow control mechanism that can be independently
--     controlled for each priority.
--  2. Enhanced transmission selection (ETS; IEEE 802.1Qaz)
--     The Enhanced Transmission Selection (ETS) feature provides a
--     common management framework for assignment of bandwidth to
--     traffic classes
--  3. DCBX is a discovery and capability exchange protocol that is used
--     by devices enabled for Data Center Bridging to exchange
--     configuration information. "

DF10-DCB-MIB DEFINITIONS ::= BEGIN

--  This MIB contains tables used to configure a Dell Networking OS switch
--  for the DCB functionality
--
--  This module will be extended, as needed.

IMPORTS
    	Unsigned32,
	MODULE-IDENTITY,
	OBJECT-TYPE,
	NOTIFICATION-TYPE,
	Counter32,
	Integer32
		FROM SNMPv2-SMI
       InterfaceIndex
              FROM IF-MIB
	TEXTUAL-CONVENTION,
	TruthValue,
	MacAddress
		FROM SNMPv2-TC
       MODULE-COMPLIANCE,
       OBJECT-GROUP,
       NOTIFICATION-GROUP
              FROM SNMPv2-CONF
       f10Mgmt
		FROM FORCE10-SMI;

 dF10Dcb MODULE-IDENTITY
        LAST-UPDATED "201204160000Z"  -- Apr 16, 2012
        ORGANIZATION "Dell Inc."
        CONTACT-INFO
            "http://www.force10networks.com/support"


  	  DESCRIPTION
         "The proprietary extension MIB module for Dell Networking OS DCB and DCBX."

         REVISION   "201204160000Z"  -- Apr 16, 2012
         DESCRIPTION
                    "1.Modified Access permission of following objects to read-only
                       dF10ETSAdminMode,dF10PFCAdminMode,dF10DCBXAdminStatus,
                       dF10DcbPfcMinThreshold,dF10DcbPfcMaxThreshold,
                       dF10DcbETSAdminStatus,dF10DcbPFCAdminStatus,
                       dF10ETSSystemControl,dF10ETSModuleStatus,
                       dF10PFCSystemControl,dF10PFCModuleStatus,
                       dF10ETSGlobalEnableTrap,dF10PFCGlobalEnableTrap,
                       as enabling DCB on interface has been changed to policy based options.
                     2.Removed 'auto' from DcbAdminMode as ets/pfc mode supported are on/off.
                     3.Removed dF10DcbRowStatus,dF10ETSRowStatus,dF10PFCRowStatus objects."

         REVISION   "201111240000Z" -- Nov 24, 2011
         DESCRIPTION
                    "Added interoperablity support - Modified MIB to reflect
                    Configuration Exchange and Auto detection of version.
                    1. Modified DcbState Textual Convention to include internally
                    propagated information from Config Source.
                    2. Modified DcbStateMachineType - for legacy DCBX versions
                    like CIN, CEE we only have a feature state machine.
                    3. Added textual convention DcbxPortRole for various port
                    roles supported for Configuration Exchange.
                    4. Added textual convention DcbxVersion for the different
                    versions of DCBX - CIN/ CEE /IEEEv2.4.
                    5. Added a new table dF10DCBXPortStatusTable for the
                    statistics and configuration exchange and version specific
                    details.
                    6. Added Compliance and Conformance information."
         REVISION   "201009250000Z" -- Aug 25 2010
         DESCRIPTION "Initial version of DCBX mib."
    ::=  { f10Mgmt 15}

 EnabledStatus ::= TEXTUAL-CONVENTION
    STATUS      current
    DESCRIPTION
        "A simple status value for the object."
    SYNTAX      INTEGER { enabled(1), disabled(2) }

 DcbAdminMode ::= TEXTUAL-CONVENTION
    STATUS      current
    DESCRIPTION

         "'on(1)', In this mode, the configurations,
         either from this system or the remote system will take
         effect based on DCBX negotiations.

         'off(2)', In this mode, all the operational(local) parameters
	 for the feature will be same as Admin Configuration Parameters.
	 But Operational(local) parameters do not have any impact in the system."

    SYNTAX      INTEGER { on(1), off(2)}

 DcbState ::= TEXTUAL-CONVENTION
    STATUS      current
    DESCRIPTION
 	"The state of the DCBX state machine.

	 off '(0)', In this state all Operational(local) parameters
	 for the feature will be same as Admin Configuration parameters
	 but will not be operational in the system(hardware).

        init '(1)', In this state all Operational(local) parameters
	 for the feature will be same as Admin Configuration Parameters.

        rxrecommended '(2)', In this state all the Operational(local)
	 parameters for the feature will be same as particular
	 feature Remote Parameters.

	 internallypropagated '(3)', In this state all the Operational(local)
	 parameters for the feature will be same as the internal propagated
	 information from the config source."
    SYNTAX      INTEGER { off(0), init(1), rxrecommended(2), internallypropagated(3) }

 DcbStateMachineType ::= TEXTUAL-CONVENTION
    STATUS      current
    DESCRIPTION
        "asymmetric'(1)',By using this state machine the operational parameters
                        for the DCB feature can be same as peer or not.
         symmetric '(2)',By using this state machine the operational parameters
                        for the DCB feature will be same as peer.
	  feature '(3)' Feature State machine as used by legacy DCBX - CIN/CEE
			versions."
    SYNTAX      INTEGER { asymmetric(1), symmetric(2), feature(3) }

 DcbxPortRole ::= TEXTUAL-CONVENTION
    STATUS     current
    DESCRIPTION
            "."
    SYNTAX      INTEGER  {
            manual(1),
            autoup(2),
            autodown(3),
            configSource(4)
    }

 DcbxVersion ::= TEXTUAL-CONVENTION
    STATUS     current
    DESCRIPTION
            "."
    SYNTAX      INTEGER  {
            auto(1),
            ieee(2),
            cin(3),
            cee(4)
    }

-- ****************************************************************************
--                           Groups in the MIB
-- ****************************************************************************

dF10DcbSystem   		OBJECT IDENTIFIER ::= { dF10Dcb 1 }
dF10DcbObjects  		OBJECT IDENTIFIER ::= { dF10Dcb 2 }
dF10DcbApplicationObjects   OBJECT IDENTIFIER ::= { dF10Dcb 3 }
dF10DcbNotificationObjects  OBJECT IDENTIFIER ::= { dF10Dcb 4 }

dF10DCBXObjects 	OBJECT IDENTIFIER ::= { dF10DcbApplicationObjects 1 }
dF10ETSObjects	OBJECT IDENTIFIER ::= { dF10DcbApplicationObjects 2 }
dF10PFCObjects	OBJECT IDENTIFIER ::= { dF10DcbApplicationObjects 3 }

dF10DCBXScalars	OBJECT IDENTIFIER ::= { dF10DCBXObjects 1 }
dF10ETSScalars	OBJECT IDENTIFIER ::= { dF10ETSObjects 1 }
dF10PFCScalars	OBJECT IDENTIFIER ::= { dF10PFCObjects 1 }


-- ****************************************************************************
-- DCB Scalar  MIB Objects
-- ****************************************************************************

 dF10DcbPfcMinThreshold    OBJECT-TYPE
    SYNTAX        Unsigned32 ( 1..65535 )
    MAX-ACCESS    read-only
    STATUS        current
    DESCRIPTION
        "The minimum PFC(Priority Based Flow Control) threshold for the switch.
         This Object indicates the minimum Receive queue buffer count.
         The minimum and maximum values for this object may vary based on the
         underlying hardware's capacity."
    ::= { dF10DcbSystem 1 }

 dF10DcbPfcMaxThreshold    OBJECT-TYPE
    SYNTAX        Unsigned32 ( 1..65535 )
    MAX-ACCESS    read-only
    STATUS        current
    DESCRIPTION
        "The maximum PFC(Priority Based Flow Control)threshold for the switch.
         This Object indicates the maximum Receive queue buffer count.
         The minimum and maximum values for this object may vary based
         on the underlying hardware's capacity. "
    ::= { dF10DcbSystem 2 }

 dF10DcbMaxPfcProfiles    OBJECT-TYPE
    SYNTAX        Unsigned32 (1..256)
    MAX-ACCESS    read-only
    STATUS        current
    DESCRIPTION
        "The maximum number of PFC(Priority Based Flow Control)profiles supported
         by the device.

         A PFC profile is a bitmap, containing the status of PFC for all the
         priorities.

         If Bit 0 is set, then it means PFC is enabled for priority 0, otherwise
         PFC is disabled for priority 0.

         If Bit 1 is set, then it means PFC is enabled for priority 1, otherwise
         PFC is disabled for priority 1, and so on.

         If this object value is zero, it means all the bits are set to zero and
         PFC is disabled for all priorities.

         If this object's value is 3, it means the bits 0 and 1 are set and
         PFC is enabled for priorities 0 and 1 and disabled for all other priorities.

         Device supporting 256 PFC profiles, means all possible combination of
         PFC status on 8 priorities are supported. "

    DEFVAL { 256 }
    ::= { dF10DcbSystem 3}

-- ****************************************************************************
-- DCB Port Configuration MIB Objects
-- ****************************************************************************

 dF10DcbPortTable    OBJECT-TYPE
    SYNTAX      SEQUENCE OF DF10DcbPortEntry
    MAX-ACCESS  not-accessible
    STATUS      obsolete
    DESCRIPTION
        "Port table contains the DCB features
         (Enhanced Transmission Selection/Priortiy Based Flow Control)
         status (enabled or disabled)."
    ::= { dF10DcbObjects 1 }

 dF10DcbPortEntry    OBJECT-TYPE
    SYNTAX      DF10DcbPortEntry
    MAX-ACCESS  not-accessible
    STATUS      obsolete
    DESCRIPTION
        "An entry containing DCB control parameters for a particular port."
    INDEX  {dF10DcbPortNumber}
    ::= { dF10DcbPortTable 1 }

 DF10DcbPortEntry ::=
 SEQUENCE {
    dF10DcbPortNumber	  InterfaceIndex,
    dF10DcbETSAdminStatus     EnabledStatus,
    dF10DcbPFCAdminStatus     EnabledStatus
    }

 dF10DcbPortNumber OBJECT-TYPE
    SYNTAX       InterfaceIndex
    MAX-ACCESS   not-accessible
    STATUS       obsolete
    DESCRIPTION
       "This indicates the interface identifier for which the Dcb
        configuration is applied."
    ::= { dF10DcbPortEntry 1 }

 dF10DcbETSAdminStatus    OBJECT-TYPE
    SYNTAX      EnabledStatus
    MAX-ACCESS  read-only
    STATUS      obsolete
    DESCRIPTION
        "This object is used to display if ETS feature is
         enabled or disabled on the given port."

    DEFVAL { enabled }
    ::= { dF10DcbPortEntry 2 }

 dF10DcbPFCAdminStatus    OBJECT-TYPE
    SYNTAX      EnabledStatus
    MAX-ACCESS  read-only
    STATUS      obsolete
    DESCRIPTION
        "This object is used to display if PFC feature is
         enabled or disabled on the given port."

    DEFVAL { enabled }
    ::= { dF10DcbPortEntry 3 }

-- ****************************************************************************
-- DCBX Scalar Objects
-- ****************************************************************************

 dF10DcbxGlobalTraceLevel    OBJECT-TYPE
    SYNTAX        Integer32
    MAX-ACCESS    read-write
    STATUS        current
    DESCRIPTION
        "This object is used to enable Trace Statements in DCBX Module.

         A FOUR BYTE integer is used for enabling the level of tracing.
         Each BIT in the four byte integer represents a particular
         level of Trace.

         The mapping between the bit positions & the level of trace is
         as follows:
                  1 - Management Traces
                  2 - DCBX State Machine Traces
                  3 - TLV Traces
                  4 - System Resource Traces
                  5 - Failure Traces
                  6 - Configuration Exchange Traces
                  7 - Auto Detection Traces

         The remaining bits are unused.

         The user has to enter the corresponding INTEGER VALUE for the
         trace to be set. Only one trace can be enabled at a time.
         To enable all the traces, sum of all individual
         traces must be provided."
    ::= { dF10DCBXScalars 1 }

 dF10DCBXGlobalVersion       OBJECT-TYPE
    SYNTAX        DcbxVersion
    MAX-ACCESS    read-write
    STATUS        current
    DESCRIPTION
         "CIN is Cisco Intel Nuova DCBX (version 1.0).
         CEE is converged enhanced ethernet DCBX (version 1.06).
         IEEE is 802-1 az version.
         The default value is auto.

         DCBX supports the legacy implementations v1.0 (CIN) and
         v1.06 (CEE) in addition to standard IEEE version 2.4 DCBX.

         1.DCBX starts in standard IEEE mode by sending an IEEE
         standard version 2.4 DCBX frame. If the peer responds,
         then IEEE standard version 2.4 DCBX is used,Starts means
         after a link up, a DCBX timeout (or multiple peer
         condition) or when commanded by the network operator.
         If DCBX receives a DCBX frame with an OUI indicating a
         legacy version, it immediately switches into legacy mode
         for the detected version and does not wait for the
         3x LLDP fast timeout.
         2.If no IEEE DCBX response is received within 3 times the
         LLDP fast transmit timeout period, DCBX immediately
         transmits a version 1.06 DCBX frame with the
         appropriate version number. If DCBX receives a DCBX
         frame with an OUI indicating IEEE standard support,
         it immediately switches into IEEE standard mode and
         does not wait for the timer. If DCBX receives a DCBX
         frame with an OUI indicating legacy mode and a version
         number indicating version 1.0 support, it immediately
         switches into legacy 1.0 mode and does not wait for the
         timer.
         3.If no version 1.06 response is received within 3 times
         the DCBX fast transmit timeout period, DCBX falls back
         to version 1.0 and immediately transmits a version 1.0
         frame. If no response is received within 3 times the
         DCBX fast transmit period, DCBX waits the standard LLDP
         timeout period, and then begins again with step 1. If
         DCBX receives a DCBX frame with an OUI indicating IEEE
         standard mode, it immediately switches into IEEE
         standard mode."
     DEFVAL { 1 }
     ::= { dF10DCBXScalars 2 }

-- ****************************************************************************
-- DCBX Port Configuration MIB Objects
-- ****************************************************************************

 dF10DCBXPortTable    OBJECT-TYPE
    SYNTAX      SEQUENCE OF DF10DCBXPortEntry
    MAX-ACCESS  not-accessible
    STATUS      current
    DESCRIPTION
        "Port table contains the DCBX feature status (enabled or disabled)."
    ::= { dF10DCBXObjects 2 }

 dF10DCBXPortEntry    OBJECT-TYPE
    SYNTAX      DF10DCBXPortEntry
    MAX-ACCESS  not-accessible
    STATUS      current
    DESCRIPTION
        "An entry containing DCBX control parameters for a particular port."
    INDEX  {dF10DCBXPortNumber}
    ::= { dF10DCBXPortTable 1 }

 DF10DCBXPortEntry ::=
 SEQUENCE {
    dF10DCBXPortNumber	   		InterfaceIndex,
    dF10DCBXAdminStatus     		EnabledStatus,
    dF10DCBXAutoCfgPortRole 		DcbxPortRole,
    dF10DCBXPortVersion     		DcbxVersion,
    dF10DCBXPortSupportedTLVs   	BITS,
    dF10DCBXPortConfigTLVsTxEnable 	BITS
    }

 dF10DCBXPortNumber OBJECT-TYPE
    SYNTAX       InterfaceIndex
    MAX-ACCESS   not-accessible
    STATUS       current
    DESCRIPTION
       "This indicates the interface identifier for which the DCBX
        configuration is applied."
    ::= { dF10DCBXPortEntry 1 }

 dF10DCBXAdminStatus    OBJECT-TYPE
    SYNTAX      EnabledStatus
    MAX-ACCESS  read-only
    STATUS      current
    DESCRIPTION
        "This object is used to display if DCBX feature is
         enabled(1) or disabled(2) on the given port."

    DEFVAL { enabled }
    ::= { dF10DCBXPortEntry 2 }

 dF10DCBXAutoCfgPortRole OBJECT-TYPE
    SYNTAX      DcbxPortRole
    MAX-ACCESS  read-write
    STATUS      current
    DESCRIPTION
        " Ports operating in the manual role do not have their
          configuration affected by peer devices or by internal
          propagation of configuration. These ports will advertise
          their configuration to their peer if DCBX is enabled
          on that port.

          Auto-up: Advertises a configuration, but is also willing
          to accept a configuration from the link-partner and
          propagate it internally to the auto-downstream ports
          as well as receive configuration propagated internally
          by other auto-upstream ports.

          Auto-down: Advertises a configuration but is not willing
          to accept one from the link partner. However, the port
          will accept a configuration propagated internally by the
          configuration source.

          Configuration Source:In this role, the port has been
          manually selected to be the configuration source.
          Configuration received over this port is propagated
          to the other auto-configuration ports."
    DEFVAL { 1 }
    ::= { dF10DCBXPortEntry 3 }

 dF10DCBXPortVersion OBJECT-TYPE
    SYNTAX      DcbxVersion
    MAX-ACCESS  read-write
    STATUS      current
    DESCRIPTION
          "CIN is Cisco Intel Nuova DCBX (version 1.0).
          CEE is converged enhanced ethernet DCBX (version 1.06).
          IEEE is 802-1 az version.
          The default value is auto.

          DCBX supports the legacy implementations v1.0 (CIN) and
          v1.06 (CEE) in addition to standard IEEE version 2.4 DCBX.

          1.DCBX starts in standard IEEE mode by sending an IEEE
          standard version 2.4 DCBX frame. If the peer responds,
          then IEEE standard version 2.4 DCBX is used,Starts means
          after a link up, a DCBX timeout (or multiple peer
          condition) or when commanded by the network operator.
          If DCBX receives a DCBX frame with an OUI indicating a
          legacy version, it immediately switches into legacy mode
          for the detected version and does not wait for the
          3x LLDP fast timeout.
          2.If no IEEE DCBX response is received within 3 times the
          LLDP fast transmit timeout period, DCBX immediately
          transmits a version 1.06 DCBX frame with the
          appropriate version number. If DCBX receives a DCBX
          frame with an OUI indicating IEEE standard support,
          it immediately switches into IEEE standard mode and
          does not wait for the timer. If DCBX receives a DCBX
          frame with an OUI indicating legacy mode and a version
          number indicating version 1.0 support, it immediately
          switches into legacy 1.0 mode and does not wait for the
          timer.
          3.If no version 1.06 response is received within 3 times
          the DCBX fast transmit timeout period, DCBX falls back
          to version 1.0 and immediately transmits a version 1.0
          frame. If no response is received within 3 times the
          DCBX fast transmit period, DCBX waits the standard LLDP
          timeout period, and then begins again with step 1. If
          DCBX receives a DCBX frame with an OUI indicating IEEE
          standard mode, it immediately switches into IEEE
          standard mode."
    DEFVAL { 1 }
    ::= { dF10DCBXPortEntry 4 }

 dF10DCBXPortSupportedTLVs      OBJECT-TYPE
    SYNTAX       BITS {
                    pfc(0),
                    etsConfig(1),
                    etsRecom(2),
                    applicationPriorityFCOE(3),
                    applicationPriorityISCSI(4)
    }
    MAX-ACCESS  read-only
    STATUS      current
    DESCRIPTION
        "Bitmap that includes the supported set of DCBX LLDP
        TLVs the device is capable of and whose transmission is allowed on
        the local LLDP agent by network management.

        Having the bit 'pfc(0)' set indicates that the LLDP
        transmit PFC TLV as part of DCBX TLVs.

        Having the bit 'etcConfig(1)' set indicates that the LLDP
        transmit ETS configuration TLV as part of DCBX TLVs.

        Having the bit 'etsRecom(2)' set indicates that
        transmit ETS Recommendation TLV as part of DCBX TLVs.

        Having the bit 'applicationPriorityFCOE(3)' set indicates that
        the LLDP transmit applicationPriority TLV for FCOE as part of
        DCBX TLVs.

        Having the bit 'applicationPriorityISCSI(4)' set indicates that
        the LLDP transmit applicationPriority TLV for ISCSI as part of
        DCBX TLVs."
   ::= { dF10DCBXPortEntry 5 }

 dF10DCBXPortConfigTLVsTxEnable OBJECT-TYPE
    SYNTAX       BITS {
                        pfc(0),
                        etsConfig(1),
                        etsRecom(2),
                        applicationPriorityFCOE(3),
                        applicationPriorityISCSI(4)
    }
    MAX-ACCESS  read-write
    STATUS      current
    DESCRIPTION
       "Bitmap that includes the DCBX defined set of LLDP
       TLVs whose transmission is enabled on the local LLDP agent by
       network management.

       Having the bit 'pfc(0)' set indicates that the LLDP
       transmit PFC TLV as part of DCBX TLVs.

       Having the bit 'etsConfig(1)' set indicates that the LLDP
       transmit ETS configuration TLV as part of DCBX TLVs.

       Having the bit 'etsRecom(2)' set indicates that
       transmit ETS Recommendation TLV as part of DCBX TLVs.

       Having the bit 'applicationPriorityFCOE(3)' set indicates that
       the LLDP transmit applicationPriority TLV for FCOE as part of
       DCBX TLVs.

       Having the bit 'applicationPriorityISCSI(4)' set indicates that
       the LLDP transmit applicationPriority TLV for ISCSI as part of
       DCBX TLVs."
    ::= { dF10DCBXPortEntry 6 }

-- ****************************************************************************
-- DCBX Statistics
-- ****************************************************************************

 dF10DCBXPortStatusTable OBJECT-TYPE
    SYNTAX      SEQUENCE OF DF10DCBXPortStatusEntry
    MAX-ACCESS  not-accessible
    STATUS      current
    DESCRIPTION
        "."
    ::= { dF10DCBXObjects 3 }

 dF10DCBXPortStatusEntry OBJECT-TYPE
    SYNTAX      DF10DCBXPortStatusEntry
    MAX-ACCESS  not-accessible
    STATUS      current
    DESCRIPTION
        "."
    AUGMENTS { dF10DCBXPortEntry }
    ::= { dF10DCBXPortStatusTable 1 }

 DF10DCBXPortStatusEntry::=
    SEQUENCE {
            dF10DCBXPortOperVersion
                DcbxVersion,
            dF10DCBXPortPeerMACaddress
                MacAddress,
            dF10DCBXPortCfgSource
                INTEGER,
            dF10DCBXOperStatus
                EnabledStatus,
            dF10DCBXPortMultiplePeerCount
                Counter32,
            dF10DCBXPortPeerRemovedCount
                Counter32,
            dF10DCBXPortPeerOperVersionNum
                Unsigned32,
            dF10DCBXPortPeerMaxVersion
                Unsigned32,
            dF10DCBXPortSeqNum
                Unsigned32,
            dF10DCBXPortAckNum
                Unsigned32,
            dF10DCBXPortPeerRcvdAckNum
                Unsigned32,
            dF10DCBXPortTxCount
                Counter32,
            dF10DCBXPortRxCount
                Counter32,
            dF10DCBXPortErrorFramesCount
                Counter32
         }

 dF10DCBXPortOperVersion     OBJECT-TYPE
    SYNTAX      DcbxVersion
    MAX-ACCESS  read-only
    STATUS      current
    DESCRIPTION
        "Specifies the DCBX mode in which  the interface is
         currently operating."
    DEFVAL { 1 }
    ::= { dF10DCBXPortStatusEntry 2 }

 dF10DCBXPortPeerMACaddress  OBJECT-TYPE
    SYNTAX      MacAddress
    MAX-ACCESS  read-only
    STATUS      current
    DESCRIPTION
        "MAC Address of the DCBX peer."
    ::= { dF10DCBXPortStatusEntry 3 }

 dF10DCBXPortCfgSource    OBJECT-TYPE
    SYNTAX      INTEGER {
                       false(0),
                       true(1)
    }
    MAX-ACCESS  read-only
    STATUS      current
    DESCRIPTION
        "Indicates if this port is the source of configuration
         information for auto-* ports."
    ::= { dF10DCBXPortStatusEntry 4 }

 dF10DCBXOperStatus OBJECT-TYPE
    SYNTAX         EnabledStatus
    MAX-ACCESS     read-only
    STATUS         current
    DESCRIPTION
        "This object gives information on the operational status of
         DCBX on the given port.
         Enabled(1) indicates DCBX on the port is in sync with the
         remote and is operationally up.
         Disabled(2) indicates DCBX on the port is operationally
         disabled."
    ::= { dF10DCBXPortStatusEntry 5 }

 dF10DCBXPortMultiplePeerCount  OBJECT-TYPE
    SYNTAX      Counter32
    MAX-ACCESS  read-only
    STATUS      current
    DESCRIPTION
        "Indicates number of times multiple peers were detected.
         A duplicate peer is when more than one DCBX peer is
         detected on a port."
    ::= { dF10DCBXPortStatusEntry 6 }

 dF10DCBXPortPeerRemovedCount  OBJECT-TYPE
    SYNTAX      Counter32
    MAX-ACCESS  read-only
    STATUS      current
    DESCRIPTION
         "."
    ::= { dF10DCBXPortStatusEntry 7 }

 dF10DCBXPortPeerOperVersionNum  OBJECT-TYPE
    SYNTAX      Unsigned32
    MAX-ACCESS  read-only
    STATUS      current
    DESCRIPTION
        "Specifies the operational version of the peer DCBX device.
         Valid only when peer device is a CEE/CIN DCBX device."
    ::= { dF10DCBXPortStatusEntry 8 }

 dF10DCBXPortPeerMaxVersion  OBJECT-TYPE
    SYNTAX      Unsigned32
    MAX-ACCESS  read-only
    STATUS      current
    DESCRIPTION
        "Specifies the max version of the peer DCBX device.
         Valid only when peer device is CEE/CIN DCBX device."
    ::= { dF10DCBXPortStatusEntry 9 }

 dF10DCBXPortSeqNum  OBJECT-TYPE
    SYNTAX      Unsigned32
    MAX-ACCESS  read-only
    STATUS      current
    DESCRIPTION
        "Specifies the current sequence number that is sent
         in DCBX control TLVs in CEE/CIN Mode."
    ::= { dF10DCBXPortStatusEntry 10 }

 dF10DCBXPortAckNum  OBJECT-TYPE
    SYNTAX      Unsigned32
    MAX-ACCESS  read-only
    STATUS      current
    DESCRIPTION
        "Specifies the current ACK number that is to be sent
         to peer in DCBX control TLVs in CEE/CIN Mode."
    ::= { dF10DCBXPortStatusEntry 11 }

 dF10DCBXPortPeerRcvdAckNum  OBJECT-TYPE
    SYNTAX      Unsigned32
    MAX-ACCESS  read-only
    STATUS      current
    DESCRIPTION
        "Specifies the current ACK number that is sent by peer
         in DCBX control TLV in CEE/CIN Mode."
    ::= { dF10DCBXPortStatusEntry 12 }

 dF10DCBXPortTxCount  OBJECT-TYPE
    SYNTAX      Counter32
    MAX-ACCESS  read-only
    STATUS      current
    DESCRIPTION
        "The number of DCBX frames transmitted per interface."
    ::= { dF10DCBXPortStatusEntry 13 }

 dF10DCBXPortRxCount  OBJECT-TYPE
    SYNTAX      Counter32
    MAX-ACCESS  read-only
    STATUS      current
    DESCRIPTION
        "The number of DCBX frames received per interface."
    ::= { dF10DCBXPortStatusEntry 14 }

 dF10DCBXPortErrorFramesCount  OBJECT-TYPE
    SYNTAX      Counter32
    MAX-ACCESS  read-only
    STATUS      current
    DESCRIPTION
        "The number of DCBX frames discarded due to errors in the frame."
    ::= { dF10DCBXPortStatusEntry 15 }

-- ****************************************************************************
-- ETS Scalar Objects
-- ****************************************************************************

 dF10ETSSystemControl   OBJECT-TYPE
    SYNTAX        INTEGER { running(1), shutdown(2) }
    MAX-ACCESS    read-only
    STATUS        current
    DESCRIPTION
        "The ETS(Enhanced Transmission selection) system control status
	 for the switch.

	 It indicates whether ETS Module in the system is
	 running or shutdown. When this object returns 'running',
	 resources required by ETS module are allocated and
	 the module is running. When this object returns 'shutdown',
	 all the pools used by ETS module are released to the system."
    DEFVAL { running }
    ::= { dF10ETSScalars 1 }

 dF10ETSModuleStatus   OBJECT-TYPE
    SYNTAX        EnabledStatus
    MAX-ACCESS    read-only
    STATUS        current
    DESCRIPTION
        "The ETS(Enhanced Transmission Selection) Module status for the switch.

	 If this object returns with 'disabled', then all the ports
	 have the ETS feature disabled in the system(hardware)
	 and the DCBX state machine has stopped on the ports.

	 If this object returns with 'enabled', then all the ports
	 have the ETS feature enabled in the system(hardware)
	 and the DCBX state machine is running on the ports."
    DEFVAL { enabled }
    ::= { dF10ETSScalars 2 }

 dF10ETSClearCounters   OBJECT-TYPE
    SYNTAX        TruthValue
    MAX-ACCESS    read-write
    STATUS        current
    DESCRIPTION
        "This object when set to TRUE, clears the following counters
         for the ETS Module:
	    dF10ETSConfTxTLVCounter,
	    dF10ETSConfRxTLVCounter,
	    dF10ETSConfRxTLVErrors,
	    dF10ETSRecoTxTLVCounter,
	    dF10ETSRecoRxTLVCounter,
	    dF10ETSRecoRxTLVErrors.

         Setting this object to FALSE has no effect.
         This object always returns FALSE when read."
    DEFVAL { false }
    ::= {dF10ETSScalars 3 }

 dF10ETSGlobalEnableTrap   OBJECT-TYPE
    SYNTAX        Integer32
    MAX-ACCESS    read-only
    STATUS        current
    DESCRIPTION
           "This object indicates whether the transmission of TRAP
            notification messages for ETS feature is enabled or disabled."

    DEFVAL { 0 }
    ::= { dF10ETSScalars 4 }

-- ****************************************************************************
-- ETS Port Configuration table
-- ****************************************************************************

 dF10ETSPortTable    OBJECT-TYPE
    SYNTAX      SEQUENCE OF DF10ETSPortEntry
    MAX-ACCESS  not-accessible
    STATUS      current
    DESCRIPTION
        "ETS Port table contains the ETS (Enhanced Transmission Selection) features
         information specific to this port.

	 An entry created in this table in the following tables in the standard
	 DCBX Mib for this port.
	 lldpXdot1dcbxConfigTCSupportedTable,
	 lldpXdot1dcbxConfigETSConfigurationTable,
	 lldpXdot1dcbxConfigETSRecommendationTable,
	 lldpXdot1dcbxLocTCSupportedTable,
	 lldpXdot1dcbxLocETSBasicConfigurationTable,
	 lldpXdot1dcbxLocETSConPriorityAssignmentTable,
	 lldpXdot1dcbxLocETSRecommendationTable,
	 lldpXdot1dcbxAdminTCSupportedTable,
	 lldpXdot1dcbxAdminETSBasicConfigurationTable,
	 lldpXdot1dcbxAdminETSConPriorityAssignmentTable,
	 lldpXdot1dcbxAdminETSRecommendationTable.

	 Deletion of entry in this table deletes all the entries in the above tables
	 in the standatd DCBX mib for this port."
    ::= { dF10ETSObjects 2 }

 dF10ETSPortEntry    OBJECT-TYPE
    SYNTAX      DF10ETSPortEntry
    MAX-ACCESS  not-accessible
    STATUS      current
    DESCRIPTION
        "An entry containing ETS control parameters and ETS information
	 for a particular port."
    INDEX  {dF10ETSPortNumber}
    ::= { dF10ETSPortTable 1 }

 DF10ETSPortEntry ::=
 SEQUENCE {
    dF10ETSPortNumber	  InterfaceIndex,
    dF10ETSAdminMode     	  DcbAdminMode,
    dF10ETSDcbxOperState      DcbState,
    dF10ETSDcbxStateMachine   DcbStateMachineType,
    dF10ETSOperStatus         EnabledStatus,
    dF10ETSClearTLVCounters   TruthValue,
    dF10ETSConfTxTLVCounter   Counter32,
    dF10ETSConfRxTLVCounter   Counter32,
    dF10ETSConfRxTLVErrors    Counter32,
    dF10ETSRecoTxTLVCounter   Counter32,
    dF10ETSRecoRxTLVCounter   Counter32,
    dF10ETSRecoRxTLVErrors    Counter32
    }

 dF10ETSPortNumber OBJECT-TYPE
    SYNTAX       InterfaceIndex
    MAX-ACCESS   not-accessible
    STATUS       current
    DESCRIPTION
       "This indicates the interface identifier for which the ETS
        configuration is applied."
    ::= { dF10ETSPortEntry 1 }

 dF10ETSAdminMode    OBJECT-TYPE
    SYNTAX      DcbAdminMode
    MAX-ACCESS  read-only
    STATUS      current
    DESCRIPTION
        "This object is used to display the Admin mode for ETS feature on
         the given port.

         If the mode is 'on(1)',ETS feature is enabled on this port.
         ETS configurations, either from this system or
         the remote system will take effect based on DCBX negotiations.

         If the mode is 'off(2)', ETS feature is disabled on this port.
         Operational(local) parameters is same as Admin Configuration
         Parameters. But Operational(local) parameters do not have any impact
         in the system and dF10ETSOperState is in 'Off' state.
         dF10ETSDcbxOperState becomes oper up if remote is also disabled.

         The Operational(local) parameters do not have any impact in
         the system if this object value is 'on(1)' and
         dF10ETSModuleStatus is disabled. dF10ETSDcbxOperState will
         be in 'Off' State."
    DEFVAL { on }
    ::= { dF10ETSPortEntry 2 }

 dF10ETSDcbxOperState    OBJECT-TYPE
    SYNTAX      DcbState
    MAX-ACCESS  read-only
    STATUS      current
    DESCRIPTION
        "This object is used to display the current state of the
	 DCBX state machine for the ETS feature on the given port.

         If state is Off '(0)', then ETS Operational(local) parameters
	 will be same as ETS Admin Configuration Parameters and will
	 not have any impact in the system(hardware).

         If state is init '(1)', then ETS Operational(local) parameters
	 will be same as ETS Admin Configuration Parameters.

         If state is rxrecommended '(2)', then ETS Operational(local) parameters
	 will be same as ETS Remote Parameters.

	  internallypropagated '(3)', In this state all the Operational(local)
	 parameters for the feature will be same as the internal propagated
	 information from the config source."
    ::= { dF10ETSPortEntry 3 }

 dF10ETSDcbxStateMachine    OBJECT-TYPE
    SYNTAX      DcbStateMachineType
    MAX-ACCESS  read-only
    STATUS      current
    DESCRIPTION
        "This object is used to display the DCBX state machine
	 type that is used by the ETS feature on the given port."
    ::= { dF10ETSPortEntry 4 }

 dF10ETSOperStatus      OBJECT-TYPE
    SYNTAX         EnabledStatus
    MAX-ACCESS     read-only
    STATUS         current
    DESCRIPTION
       "This object gives information on the operational status of ETS
        on the given port.
        Enabled(1) indicates ETS on the port is in sync with the remote
        and is operationally up.
        Disabled(2) indicates ETS on the port is operationally disabled."
    ::= { dF10ETSPortEntry 5 }

 dF10ETSClearTLVCounters    OBJECT-TYPE
    SYNTAX      TruthValue
    MAX-ACCESS  read-write
    STATUS      current
    DESCRIPTION
        "This object when set to TRUE, clears the following counters
         associated with a Port:
	    dF10ETSConfTxTLVCounter,
	    dF10ETSConfRxTLVCounter,
	    dF10ETSConfRxTLVErrors,
	    dF10ETSRecoTxTLVCounter,
	    dF10ETSRecoRxTLVCounter,
	    dF10ETSRecoRxTLVErrors.

         Setting this object to FALSE has no effect.
         This object always returns FALSE when read."
    DEFVAL { false }
    ::= { dF10ETSPortEntry 6 }

 dF10ETSConfTxTLVCounter    OBJECT-TYPE
    SYNTAX      Counter32
    MAX-ACCESS  read-only
    STATUS      current
    DESCRIPTION
        "This object is used to keep track of the number of ETS
	 configuration TLV that are transmitted from this port.
	 This counter will be incremented every time when there
	 is ETS Configuration TLV is generated and transmitted
	 to the LLDP."
    ::= { dF10ETSPortEntry 7 }

 dF10ETSConfRxTLVCounter    OBJECT-TYPE
    SYNTAX      Counter32
    MAX-ACCESS  read-only
    STATUS      current
    DESCRIPTION
        "This object is used to keep track of the number of ETS
	 ConfigurationTLV that are received in this port. This
	 counter will be incremented every time when there is ETS
	 Configuration TLV is received from the LLDP."
    ::= { dF10ETSPortEntry 8 }

 dF10ETSConfRxTLVErrors    OBJECT-TYPE
    SYNTAX      Counter32
    MAX-ACCESS  read-only
    STATUS      current
    DESCRIPTION
        "This object is used to keep track of number of malformed
	 ETS Conf TLVs received by ETS. This counter will be
	 incremented every time a ETS Conf TLV is dropped by ETS."
    ::= { dF10ETSPortEntry 9 }


 dF10ETSRecoTxTLVCounter    OBJECT-TYPE
    SYNTAX      Counter32
    MAX-ACCESS  read-only
    STATUS      current
    DESCRIPTION
        "This object is used to keep track of the number of ETS
	 Recommendation TLV that are transmitted from this port.
	 This counter will be incremented every time when there
	 is ETS Recommendation TLV is generated and transmitted
	 to the LLDP."
    ::= { dF10ETSPortEntry 10 }

 dF10ETSRecoRxTLVCounter    OBJECT-TYPE
    SYNTAX      Counter32
    MAX-ACCESS  read-only
    STATUS      current
    DESCRIPTION
        "This object is used to keep track of the number of ETS
	 Recommendation TLV that are received in this port. This
	 counter will be incremented every time when there is ETS
	 Recommendation TLV is received from the LLDP."
    ::= { dF10ETSPortEntry 11 }

 dF10ETSRecoRxTLVErrors    OBJECT-TYPE
    SYNTAX      Counter32
    MAX-ACCESS  read-only
    STATUS      current
    DESCRIPTION
        "This object is used to keep track of number of malformed
	 ETS Reco TLVs received by ETS. This counter will be
	 incremented every time a ETS Reco TLV is dropped by ETS."
    ::= { dF10ETSPortEntry 12 }

-- ****************************************************************************
--  PFC Scalar Objects
-- ****************************************************************************

 dF10PFCSystemControl   OBJECT-TYPE
    SYNTAX        INTEGER { running(1), shutdown(2) }
    MAX-ACCESS    read-only
    STATUS        current
    DESCRIPTION
        "The PFC(Priority Based Flow Control) system control status for the switch.

         It indicates whether PFC Module in the system is
         running or shutdown. When this object returns 'running',
         resources required by PFC module are allocated and
         the module is running. When this object returns 'shutdown',
         all the pools used by PFC module are released to the system."

    DEFVAL { running }
    ::= { dF10PFCScalars 1 }

 dF10PFCModuleStatus   OBJECT-TYPE
    SYNTAX        EnabledStatus
    MAX-ACCESS    read-only
    STATUS        current
    DESCRIPTION
        "The PFC(Priority Based Flow Control) Module status for the switch.

	 If this object returns with 'disabled', then all the ports
	 have the PFC feature disabled in the system(hardware)
	 and the DCBX state machine has stopped on the ports.

	 If this object returns with 'enabled', then all the ports
	 have the PFC feature enabled in the system(hardware)
	 and the DCBX state machine is running on the ports."
    DEFVAL { enabled }
    ::= { dF10PFCScalars 2 }

 dF10PFCClearCounters   OBJECT-TYPE
    SYNTAX        TruthValue
    MAX-ACCESS    read-write
    STATUS        current
    DESCRIPTION
        "This object when set to TRUE, clears the following counters
         for the PFC Module:
	    dF10PFCTxTLVCounter,
	    dF10PFCRxTLVCounter,
	    dF10PFCRxTLVErrors.

         Setting this object to FALSE has no effect.
         This object always returns FALSE when read."
    DEFVAL { false }
    ::= {dF10PFCScalars 3 }

 dF10PFCGlobalEnableTrap   OBJECT-TYPE
    SYNTAX        Integer32
    MAX-ACCESS    read-only
    STATUS        current
    DESCRIPTION
           "This object indicates whether the transmission of TRAP
            notification messages for PFC feature is enabled or disabled."

    DEFVAL { 0 }
    ::= { dF10PFCScalars 4 }

-- ****************************************************************************
--  PFC Port Configuration table
-- ****************************************************************************

 dF10PFCPortTable    OBJECT-TYPE
    SYNTAX      SEQUENCE OF DF10PFCPortEntry
    MAX-ACCESS  not-accessible
    STATUS      current
    DESCRIPTION
        "PFC Port table contains the PFC (Priortiy Based Flow Control) features
         information specific to this port.

	 An entry created in the port table populates the entry in this table and
	 in the following tables in the standard DCBX Mib for this port.
	 lldpXdot1dcbxConfigPFCTable,
	 lldpXdot1dcbxLocPFCBasicTable,
	 lldpXdot1dcbxLocPFCEnableTable,
	 lldpXdot1dcbxAdminPFCBasicTable,
 	 lldpXdot1dcbxAdminPFCEnableTable.

	 Deletion of entry in the port table deletes the entry in this table and
	 all the entries in the above tables in the standatd DCBX mib for this port."
    ::= { dF10PFCObjects 2 }

 dF10PFCPortEntry    OBJECT-TYPE
    SYNTAX      DF10PFCPortEntry
    MAX-ACCESS  not-accessible
    STATUS      current
    DESCRIPTION
        "An entry containing PFC control parameters and PFC information
	 for a particular port."
    INDEX  {dF10PFCPortNumber}
    ::= { dF10PFCPortTable 1 }

 DF10PFCPortEntry ::=
 SEQUENCE {
    dF10PFCPortNumber	    InterfaceIndex,
    dF10PFCAdminMode     	    DcbAdminMode,
    dF10PFCDcbxOperState      DcbState,
    dF10PFCDcbxStateMachine   DcbStateMachineType,
    dF10PFCOperStatus         EnabledStatus,
    dF10PFCClearTLVCounters   TruthValue,
    dF10PFCTxTLVCounter	    Counter32,
    dF10PFCRxTLVCounter	    Counter32,
    dF10PFCRxTLVErrors	    Counter32
    }

 dF10PFCPortNumber OBJECT-TYPE
    SYNTAX       InterfaceIndex
    MAX-ACCESS   not-accessible
    STATUS       current
    DESCRIPTION
       "This indicates the interface identifier for which the PFC
        configuration is applied."
    ::= { dF10PFCPortEntry 1 }

 dF10PFCAdminMode    OBJECT-TYPE
    SYNTAX      DcbAdminMode
    MAX-ACCESS  read-only
    STATUS      current
    DESCRIPTION
        "This object is used to display Admin mode for PFC feature on
         the given port.

         If mode is 'on(1)',PFC feature is enabled on this port.
         PFC configurations, either from this system or
         the remote system will take effect based on DCBX negotiations.

         If mode is 'off(2)',PFC feature is disabled on this port.
         Operational(local) parameters is same as Admin Configuration
         Parameters. But Operational(local) parameters do not have any impact
         in the system.dF10PFCDcbxOperState becomes up if remote is also disabled

         The Operational(local) parameters do not have any impact in
         the system if this object value is 'on(1)'
         and dF10PFCModuleStatus is disabled. dF10PFCDcbxOperState
         will be in 'Off' State."
    DEFVAL { on }
    ::= { dF10PFCPortEntry 2 }

 dF10PFCDcbxOperState    OBJECT-TYPE
    SYNTAX      DcbState
    MAX-ACCESS  read-only
    STATUS      current
    DESCRIPTION
        "This object is used to display the current state of the
	 DCBX state machine for the PFC feature on the given port.

         If state is Off '(0)', then PFC Operational(local) parameters
	 will be same as PFC Admin Configuration Parameters and will
	 not have any impact in the system(hardware).

         If state is init '(1)', then PFC Operational(local) parameters
	 will be same as PFC Admin Configuration Parameters.

         If state is rxrecommended '(2)',then PFC Operational(local) parameters
	 will be same as PFC Remote Parameters.

	  internallypropagated '(3)', In this state all the Operational(local)
	 parameters for the feature will be same as the internal propagated
	 information from the config source."
    ::= { dF10PFCPortEntry 3 }

 dF10PFCDcbxStateMachine    OBJECT-TYPE
    SYNTAX      DcbStateMachineType
    MAX-ACCESS  read-only
    STATUS      current
    DESCRIPTION
        "This object is used to display the DCBX state machine
	 type that is used by the PFC feature on the given port."
    ::= { dF10PFCPortEntry 4 }

 dF10PFCOperStatus      OBJECT-TYPE
    SYNTAX         EnabledStatus
    MAX-ACCESS     read-only
    STATUS         current
    DESCRIPTION
       "This object gives information on the operational status of PFC
        on the given port.
        Enabled(1) indicates PFC on the port is in sync with the remote
        and is operationally up.
        Disabled(2) indicates PFC on the port is operationally disabled."
    ::= { dF10PFCPortEntry 5 }

 dF10PFCClearTLVCounters    OBJECT-TYPE
    SYNTAX      TruthValue
    MAX-ACCESS  read-write
    STATUS      current
    DESCRIPTION
        "This object when set to TRUE, clears the following counters
         associated with a Port:
	    dF10PFCTxTLVCounter,
	    dF10PFCRxTLVCounter,
	    dF10PFCRxTLVErrors.

         Setting this object to FALSE has no effect.
         This object always returns FALSE when read."
    DEFVAL { false }
    ::= { dF10PFCPortEntry 6 }

 dF10PFCTxTLVCounter    OBJECT-TYPE
    SYNTAX      Counter32
    MAX-ACCESS  read-only
    STATUS      current
    DESCRIPTION
        "This object is used to keep track of the number of PFC TLV
	 that are transmitted from this port. This counter will be
	 incremented every time when there is PFC TLV is generated
	 and transmitted to the LLDP."
    ::= { dF10PFCPortEntry 7 }

 dF10PFCRxTLVCounter    OBJECT-TYPE
    SYNTAX      Counter32
    MAX-ACCESS  read-only
    STATUS      current
    DESCRIPTION
        "This object is used to keep track of the number of PFC TLV
	 that are received in this port. This counter will be
	 incremented every time when there is PFC TLV is received
	 from the LLDP."
    ::= { dF10PFCPortEntry 8 }

 dF10PFCRxTLVErrors    OBJECT-TYPE
    SYNTAX      Counter32
    MAX-ACCESS  read-only
    STATUS      current
    DESCRIPTION
        "This object is used to keep track of number of malformed TLVs received by PFC.
         This counter will be incremented every time a PFC-TLV is dropped by PFC."
    ::= { dF10PFCPortEntry 9 }

-- ****************************************************************************
--  dF10DCbNotification subtree contains the objects related to notifications.
-- ****************************************************************************
 dF10DCBTraps OBJECT IDENTIFIER ::= { dF10DcbNotificationObjects 0 }
 dF10DCBTrapObjects OBJECT IDENTIFIER ::= { dF10DcbNotificationObjects 1 }

    dF10DcbTrapPortNumber OBJECT-TYPE
    SYNTAX      TruthValue
    MAX-ACCESS  accessible-for-notify
    STATUS      current
    DESCRIPTION
        "This object refers to the Port number for which the DCBX feature
	 is enabled. And will be used in sending the feature port specific Traps."
    ::= { dF10DCBTrapObjects 1 }

 dF10DcbPeerUpStatus OBJECT-TYPE
    SYNTAX      TruthValue
    MAX-ACCESS  accessible-for-notify
    STATUS      current
    DESCRIPTION
        "This object refers to the DCBX Peer Up or Peer down status
	 on the port.
	 If the value is 'true', then the DCBX Peer will be present
	 and UP.
	 If the value is 'false', then the DCBX Peer will be absent
	 and DOWN."
    ::= { dF10DCBTrapObjects 2 }

 dF10ETSModuleStatusTrap NOTIFICATION-TYPE
    OBJECTS  {
        dF10ETSModuleStatus
    }
    STATUS   current
    DESCRIPTION
        "This trap is generated when there is a change in the ETS Module
        status. This trap is generated only if dF10ETSGlobalEnableTrap
        is enabled to send the trap."
    ::= { dF10DCBTraps 1 }

 dF10ETSPortAdminStatusTrap NOTIFICATION-TYPE
    OBJECTS  {
            dF10DcbTrapPortNumber,
            dF10ETSAdminMode
    }
    STATUS   current
    DESCRIPTION
        "This trap is generated in the following conditions.
        Whenever there is a change in the ETS Admin status and the
        dF10ETSGlobalEnableTrap is enabled to send the trap
        for ETS Admin mode change. "
    ::= {dF10DCBTraps 2 }

 dF10ETSPortPeerStatusTrap NOTIFICATION-TYPE
    OBJECTS  {
            dF10DcbTrapPortNumber,
	     dF10DcbPeerUpStatus
    }
    STATUS   current
    DESCRIPTION
        "This trap is generated in the following conditions.
        Whenever there is a change in the DCBX Peer Status and the
        dF10ETSGlobalEnableTrap is enabled
        to send the trap for Peer Up or Peer Down."
    ::= {dF10DCBTraps 3 }

 dF10ETSPortDcbxOperStateTrap NOTIFICATION-TYPE
     OBJECTS  {
             dF10DcbTrapPortNumber,
             dF10ETSDcbxOperState
     }
     STATUS   current
     DESCRIPTION
         "This trap is generated in the following conditions.
         Whenever there is a change in the ETS Operational State and the
         dF10ETSGlobalEnableTrap is enabled
         to send the trap for ETS state machine state change."
     ::= {dF10DCBTraps 4 }

 dF10PFCModuleStatusTrap NOTIFICATION-TYPE
    OBJECTS  {
            dF10PFCModuleStatus
    }
    STATUS   current
    DESCRIPTION
        "This trap is generated when there is a change in the PFC Module
        status is enabled. This trap is generated only if
        dF10PFCGlobalEnableTrap is enabled to send the trap."
    ::= { dF10DCBTraps 5 }

 dF10PFCPortAdminStatusTrap NOTIFICATION-TYPE
    OBJECTS  {
            dF10DcbTrapPortNumber,
	     dF10PFCAdminMode
    }
    STATUS   current
    DESCRIPTION
        "This trap is generated in the following conditions.
        Whenever there is a change in the PFC Admin Status and the
        dF10PFCGlobalEnableTrap is enabled
        to send the trap for PFC Admin Status change."
    ::= {dF10DCBTraps 6 }

 dF10PFCPortPeerStatusTrap NOTIFICATION-TYPE
    OBJECTS  {
            dF10DcbTrapPortNumber,
            dF10DcbPeerUpStatus
    }
    STATUS   current
    DESCRIPTION
        "This trap is generated in the following conditions.
        Whenever there is a change in the DCBX Peer Status and the
        dF10PFCGlobalEnableTrap is enabled
        to send the trap for Peer Up or Peer Down."
    ::= {dF10DCBTraps 7 }

 dF10PFCPortDcbxOperStateTrap NOTIFICATION-TYPE
    OBJECTS  {
            dF10DcbTrapPortNumber,
            dF10PFCDcbxOperState
    }
    STATUS   current
    DESCRIPTION
        "This trap is generated in the following conditions.
        Whenever there is a change in the PFC Operational State and the
        dF10PFCGlobalEnableTrap is enabled
        to send the trap for PFC state machine state change."
    ::= {dF10DCBTraps 8 }

-- ############################################################################
-- Conformance information
-- ############################################################################

  dF10DCBMibConformance     OBJECT IDENTIFIER
        ::=    { dF10Dcb 5 }

  dF10DCBMibCompliances     OBJECT IDENTIFIER
        ::=    { dF10DCBMibConformance 1 }

  dF10DCBMibGroups     OBJECT IDENTIFIER
        ::=    { dF10DCBMibConformance 2 }

-- ############################################################################
-- Compliance Statements
-- ############################################################################

dF10DCBMibComplianceRev1       MODULE-COMPLIANCE
  STATUS                       current
  DESCRIPTION
      "The compliance statement for Dell Networking OS product which implement the
      Dell Networking OS dcbx MIB. "
  MODULE
  MANDATORY-GROUPS {
      dF10DcbSystemObjectGroup,
      dF10DcbxScalarsGroup,
      dF10DCBXPortTableGroup,
      dF10ETSScalarsGroup,
      dF10ETSPortTableGroup,
      dF10PFCScalarsGroup,
      dF10PFCPortTableGroup,
      dF10DCBNotificationObjectsGroup,
      dF10DCBNotificationsGroup
  }
  ::= { dF10DCBMibCompliances 1 }

dF10DCBMibCompliance      MODULE-COMPLIANCE
  STATUS                  obsolete
  DESCRIPTION
    "The compliance statement for Dell Networking OS product which implement the
    Dell Networking OS dcb MIB. This module consists of the obsolete MIB objects."
  MODULE
  MANDATORY-GROUPS {
      dF10DcbObjectGroup
  }
  ::= { dF10DCBMibCompliances 2 }

-- ##########################################################################
-- Units of conformance
-- ##########################################################################

dF10DcbSystemObjectGroup OBJECT-GROUP
   OBJECTS {
           dF10DcbPfcMinThreshold,
           dF10DcbPfcMaxThreshold,
           dF10DcbMaxPfcProfiles
   }
   STATUS            current
   DESCRIPTION
       "This group represents a collection of objects providing the
       DCB system information."
   ::= { dF10DCBMibGroups 1 }

 dF10DcbObjectGroup      OBJECT-GROUP
    OBJECTS {
          dF10DcbETSAdminStatus,
          dF10DcbPFCAdminStatus
    }
    STATUS             obsolete
    DESCRIPTION
        "This group represents a collection of objects providing the
        information on the DCB control parameters for a particular port."
    ::= { dF10DCBMibGroups 2 }

 dF10DcbxScalarsGroup    OBJECT-GROUP
    OBJECTS {
          dF10DcbxGlobalTraceLevel,
          dF10DCBXGlobalVersion
    }
    STATUS             current
    DESCRIPTION
        "This group represents the DCBX scalars in the DF10 DCB mib. "
    ::= { dF10DCBMibGroups 3 }

 dF10DCBXPortTableGroup     OBJECT-GROUP
    OBJECTS  {
          dF10DCBXAdminStatus,
          dF10DCBXAutoCfgPortRole,
          dF10DCBXPortVersion,
          dF10DCBXPortSupportedTLVs,
          dF10DCBXPortConfigTLVsTxEnable,
          dF10DCBXPortOperVersion,
          dF10DCBXPortPeerMACaddress,
          dF10DCBXPortCfgSource,
          dF10DCBXOperStatus,
          dF10DCBXPortMultiplePeerCount,
          dF10DCBXPortPeerRemovedCount,
          dF10DCBXPortPeerOperVersionNum,
          dF10DCBXPortPeerMaxVersion,
          dF10DCBXPortSeqNum,
          dF10DCBXPortAckNum,
          dF10DCBXPortPeerRcvdAckNum,
          dF10DCBXPortTxCount,
          dF10DCBXPortRxCount,
          dF10DCBXPortErrorFramesCount
    }
    STATUS             current
    DESCRIPTION
        "This group contains the collection of objects describing the
        DCBX specific information on the particular port. "
    ::= { dF10DCBMibGroups 4 }

 dF10ETSScalarsGroup  OBJECT-GROUP
    OBJECTS {
          dF10ETSSystemControl,
          dF10ETSModuleStatus,
          dF10ETSClearCounters,
          dF10ETSGlobalEnableTrap
    }
    STATUS            current
    DESCRIPTION
        "This object represents the collection of objects providing the ETS
        Information on the system."
    ::= { dF10DCBMibGroups 5 }

 dF10ETSPortTableGroup    OBJECT-GROUP
    OBJECTS  {
          dF10ETSAdminMode,
          dF10ETSDcbxOperState,
          dF10ETSDcbxStateMachine,
          dF10ETSOperStatus,
          dF10ETSClearTLVCounters,
          dF10ETSConfTxTLVCounter,
          dF10ETSConfRxTLVCounter,
          dF10ETSConfRxTLVErrors,
          dF10ETSRecoTxTLVCounter,
          dF10ETSRecoRxTLVCounter,
          dF10ETSRecoRxTLVErrors
    }
    STATUS            current
    DESCRIPTION
        "This object group represents the collection of objects providing
        ETS specific status information on a specific port."
    ::= { dF10DCBMibGroups 6 }

 dF10PFCScalarsGroup     OBJECT-GROUP
    OBJECTS   {
         dF10PFCSystemControl,
         dF10PFCModuleStatus,
         dF10PFCClearCounters,
         dF10PFCGlobalEnableTrap
    }
    STATUS            current
    DESCRIPTION
        "This group represents a collection of objects providing the system
        information related to PFC."
    ::= { dF10DCBMibGroups 7 }

 dF10PFCPortTableGroup   OBJECT-GROUP
    OBJECTS {
         dF10PFCAdminMode,
         dF10PFCDcbxOperState,
         dF10PFCDcbxStateMachine,
         dF10PFCOperStatus,
         dF10PFCClearTLVCounters,
         dF10PFCTxTLVCounter,
         dF10PFCRxTLVCounter,
         dF10PFCRxTLVErrors
    }
    STATUS            current
    DESCRIPTION
        "This group represents a collection of objects providing the
        PFC specific status information per port. "
    ::= { dF10DCBMibGroups 8 }

 dF10DCBNotificationObjectsGroup    OBJECT-GROUP
    OBJECTS {
         dF10DcbTrapPortNumber,
         dF10DcbPeerUpStatus
    }
    STATUS            current
    DESCRIPTION
        "This object group represents the collection of objects used by the
        notification group dF10DCBNotificationsGroup."
    ::= { dF10DCBMibGroups 9 }

 dF10DCBNotificationsGroup  NOTIFICATION-GROUP
    NOTIFICATIONS {
         dF10ETSModuleStatusTrap,
         dF10ETSPortAdminStatusTrap,
         dF10ETSPortPeerStatusTrap,
         dF10ETSPortDcbxOperStateTrap,
         dF10PFCModuleStatusTrap,
         dF10PFCPortAdminStatusTrap,
         dF10PFCPortPeerStatusTrap,
         dF10PFCPortDcbxOperStateTrap
    }
    STATUS               current
    DESCRIPTION
        "A collection on notification objects in the DF10-DCB mib"
    ::= { dF10DCBMibGroups 10 }


END
