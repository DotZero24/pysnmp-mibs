-- *****************************************************************
-- CISCO-CALL-TRACKER-TCP-MIB.my: Progress and Status Tracking
--                                MIB for Call associated TCP
--                                connections
--
--
-- Copyright (c) 1996-2005 by cisco Systems, Inc.
-- All rights reserved.
-- *****************************************************************

CISCO-CALL-TRACKER-TCP-MIB DEFINITIONS ::= BEGIN

IMPORTS
        MODULE-IDENTITY,
        OBJECT-TYPE,
        Counter32,
        IpAddress
                FROM SNMPv2-SMI
        MODULE-COMPLIANCE,
        OBJECT-GROUP
                FROM SNMPv2-CONF
        CiscoPort
               FROM CISCO-TC
        ciscoMgmt
                FROM CISCO-SMI
        cctActiveCallId,
        cctHistoryIndex
                FROM CISCO-CALL-TRACKER-MIB;


ciscoCallTrackerTCPMIB MODULE-IDENTITY
        LAST-UPDATED    "200512060000Z"
        ORGANIZATION    "Cisco Systems, Inc."
        CONTACT-INFO
                "       Cisco Systems
                        Customer Service

                Postal: 170 W. Tasman Drive
                        San Jose, CA  95134
                        USA

                Tel: +1 800 553-NETS

                E-mail: cs-dial@cisco.com"
        DESCRIPTION
                "This MIB module provides TCP service connection
                 related data for tracking the progress and status of
                 a call.

                 This module extends tables defined in the MIB module
                 ciscoCallTrackerMIB in CISCO-CALL-TRACKER-MIB.
                "
        REVISION  "200512060000Z"
        DESCRIPTION
            "Removed Unsigned32 from the imports since it is not used."
        REVISION  "200006070000Z"
        DESCRIPTION
                "Initial version of this mib."
       ::= { ciscoMgmt 164 }




-- Call Tracker TCP MIB objects definitions

ccttMIBObjects OBJECT IDENTIFIER ::= { ciscoCallTrackerTCPMIB 1 }


-- The Call Tracker TCP MIB consists of the following groups
-- [1] Call Tracker Active Group  (ccttActive)
-- [2] Call Tracker History Group (ccttHistory)

ccttActive         OBJECT IDENTIFIER ::= { ccttMIBObjects 1 }
ccttHistory        OBJECT IDENTIFIER ::= { ccttMIBObjects 2 }



-- *****************************************************************
-- Call Tracker Active Group
-- *****************************************************************
--
--


--
-- Call Active Table
--


ccttActiveTable OBJECT-TYPE
        SYNTAX      SEQUENCE OF CcttActiveEntry
        MAX-ACCESS  not-accessible
        STATUS      current
        DESCRIPTION
            "This table contains entries for active calls in the
             system which utilize TCP connections, as reported by
             cctActiveServiceType.

             This table extends the cctActiveTable, using the same
             index, cctActiveCallId.
            "
        ::= { ccttActive 1 }


ccttActiveEntry OBJECT-TYPE
        SYNTAX      CcttActiveEntry
        MAX-ACCESS  not-accessible
        STATUS      current
        DESCRIPTION
            "The information related to TCP connection for a single
             call.

             Entries are created if the call requests TCP connection
             based service. Entries are deleted when the call
             terminates.
            "
        INDEX   { cctActiveCallId }
        ::= { ccttActiveTable 1 }


CcttActiveEntry ::=
        SEQUENCE {
            ccttActiveLocalIpAddress           IpAddress,
            ccttActiveLocalTcpPort             CiscoPort,
            ccttActiveRemoteIpAddress          IpAddress,
            ccttActiveRemoteTcpPort            CiscoPort,
            ccttActiveDestinationFailures      Counter32
        }

ccttActiveLocalIpAddress OBJECT-TYPE
        SYNTAX     IpAddress
        MAX-ACCESS read-only
        STATUS     current
        DESCRIPTION
            "The IP address for local endpoint of the call's TCP
             connection.

             This object has the same value as tcpConnLocalAddress
             from TCP-MIB.
            "
        REFERENCE  "RFC 2012 TCP-MIB"
        ::= { ccttActiveEntry 1 }

ccttActiveLocalTcpPort OBJECT-TYPE
        SYNTAX     CiscoPort
        MAX-ACCESS read-only
        STATUS     current
        DESCRIPTION
            "TCP port number for local endpoint of the call's TCP
             connection.

             This object has the same value as tcpConnLocalPort
             from TCP-MIB.
            "
        REFERENCE  "RFC 2012 TCP-MIB"
        ::= { ccttActiveEntry 2 }

ccttActiveRemoteIpAddress OBJECT-TYPE
        SYNTAX     IpAddress
        MAX-ACCESS read-only
        STATUS     current
        DESCRIPTION
            "The IP address for remote endpoint of the call's TCP
             connection.

             This object has the same value as tcpConnRemAddress
             from TCP-MIB.
            "
        REFERENCE  "RFC 2012 TCP-MIB"
        ::= { ccttActiveEntry 3 }

ccttActiveRemoteTcpPort OBJECT-TYPE
        SYNTAX     CiscoPort
        MAX-ACCESS read-only
        STATUS     current
        DESCRIPTION
            "TCP port number for remote endpoint of the call's TCP
             connection.

             This object has the same value as tcpConnRemPort
             from TCP-MIB.
            "
        REFERENCE  "RFC 2012 TCP-MIB"
        ::= { ccttActiveEntry 4 }

ccttActiveDestinationFailures OBJECT-TYPE
        SYNTAX     Counter32
        MAX-ACCESS read-only
        STATUS     current
        DESCRIPTION
            "The number of requests from the call processing
             software to the Telnet/TCP to setup a connection for
             which Telnet/TCP was unable to establish the requested
             connection.
            "
        ::= { ccttActiveEntry 5 }


-- *****************************************************************
-- Call Tracker History Group
-- *****************************************************************

--
-- Call Tracker History Table
--

ccttHistoryTable OBJECT-TYPE
        SYNTAX      SEQUENCE OF CcttHistoryEntry
        MAX-ACCESS  not-accessible
        STATUS      current
        DESCRIPTION
            "This table provides information on terminated calls
             with associated TCP connections, as reported by
             cctHistoryServiceType.

             This table extends the cctHistoryTable, using the same
             index, cctHistoryIndex.
            "
        ::= { ccttHistory 1 }


ccttHistoryEntry OBJECT-TYPE
        SYNTAX      CcttHistoryEntry
        MAX-ACCESS  not-accessible
        STATUS      current
        DESCRIPTION
            "The information regarding a single terminated call with
             TCP connections.

             Entries are created and deleted in sync with the entries
             in cctHistoryTable, when there is a TCP connection
             service requested for the call.
            "
        INDEX   { cctHistoryIndex }
        ::= { ccttHistoryTable 1 }


CcttHistoryEntry ::=
        SEQUENCE {
            ccttHistoryLocalIpAddress          IpAddress,
            ccttHistoryLocalTcpPort            CiscoPort,
            ccttHistoryRemoteIpAddress         IpAddress,
            ccttHistoryRemoteTcpPort           CiscoPort,
            ccttHistoryDestinationFailures     Counter32
        }

ccttHistoryLocalIpAddress OBJECT-TYPE
        SYNTAX     IpAddress
        MAX-ACCESS read-only
        STATUS     current
        DESCRIPTION
            "The IP address for local endpoint of the call's TCP
             connection.
            "
        ::= { ccttHistoryEntry 1 }

ccttHistoryLocalTcpPort OBJECT-TYPE
        SYNTAX     CiscoPort
        MAX-ACCESS read-only
        STATUS     current
        DESCRIPTION
            "TCP port number for local endpoint of the call's TCP
             connection.
            "
        ::= { ccttHistoryEntry 2 }

ccttHistoryRemoteIpAddress OBJECT-TYPE
        SYNTAX     IpAddress
        MAX-ACCESS read-only
        STATUS     current
        DESCRIPTION
            "The IP address for remote endpoint of the call's TCP
             connection.

             If no TCP connection was established, this object
             reports the first destination attempted.
            "
        ::= { ccttHistoryEntry 3 }

ccttHistoryRemoteTcpPort OBJECT-TYPE
        SYNTAX     CiscoPort
        MAX-ACCESS read-only
        STATUS     current
        DESCRIPTION
            "TCP port number for remote endpoint of the call's TCP
             connection.

             If no TCP connection was established, this object reports
             the TCP port of the first destination attempted.
            "
        ::= { ccttHistoryEntry 4 }

ccttHistoryDestinationFailures OBJECT-TYPE
        SYNTAX     Counter32
        MAX-ACCESS read-only
        STATUS     current
        DESCRIPTION
            "The number of requests from the call processing
             software to the Telnet/TCP to setup a connection for
             which Telnet/TCP was unable to establish the requested
             connection.
            "
        ::= { ccttHistoryEntry 5 }


-- *****************************************************************
-- Notifications
-- *****************************************************************
ccttMIBNotificationPrefix OBJECT IDENTIFIER ::=
                                { ciscoCallTrackerTCPMIB 2 }
ccttMIBNotifications      OBJECT IDENTIFIER ::=
                                { ccttMIBNotificationPrefix 0 }


-- *****************************************************************
-- Conformance and Compliances
-- *****************************************************************

ccttMIBConformance OBJECT IDENTIFIER ::=
                                { ciscoCallTrackerTCPMIB 3 }
ccttMIBCompliances OBJECT IDENTIFIER ::=
                                { ccttMIBConformance 1 }
ccttMIBGroups      OBJECT IDENTIFIER ::=
                                { ccttMIBConformance 2 }

-- compliance statements

ccttMIBCompliance MODULE-COMPLIANCE
        STATUS      current
        DESCRIPTION
            "The compliance statement for entities which
             implement the CISCO CALL TRACKER TCP MIB
            "
        MODULE      -- this module
        MANDATORY-GROUPS
            { ccttActiveGroup,
              ccttHistoryGroup }
        ::= { ccttMIBCompliances 1 }



-- units of conformance


ccttActiveGroup OBJECT-GROUP
        OBJECTS {
            ccttActiveLocalIpAddress,
            ccttActiveLocalTcpPort,
            ccttActiveRemoteIpAddress,
            ccttActiveRemoteTcpPort,
            ccttActiveDestinationFailures
        }
        STATUS      current
        DESCRIPTION
            "A collection of objects providing the
             active call information.
            "
        ::= { ccttMIBGroups 2 }

ccttHistoryGroup OBJECT-GROUP
        OBJECTS {
            ccttHistoryLocalIpAddress,
            ccttHistoryLocalTcpPort,
            ccttHistoryRemoteIpAddress,
            ccttHistoryRemoteTcpPort,
            ccttHistoryDestinationFailures
        }
        STATUS      current
        DESCRIPTION
            "A collection of objects providing the
             historical call information.
            "
        ::= { ccttMIBGroups 3 }

END
