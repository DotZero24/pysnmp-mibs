--*****************************************************************
-- CISCO_DMN_DSG_Fault.mib: Mib file for Fault control and status.
--
-- August 2010, TEL MIB Team
--
-- Copyright (c) 1999-2010 Cisco Systems, Inc. All rights reserved.
--*****************************************************************

CISCO-DMN-DSG-FAULT-MIB

DEFINITIONS ::= BEGIN

IMPORTS
    MODULE-IDENTITY,
    OBJECT-TYPE, Integer32, Counter32
        FROM SNMPv2-SMI
    DisplayString
        FROM SNMPv2-TC
    OBJECT-GROUP, MODULE-COMPLIANCE
        FROM SNMPv2-CONF
    ciscoDSGUtilities
        FROM CISCO-DMN-DSG-ROOT-MIB;

ciscoDSGFault  MODULE-IDENTITY
    LAST-UPDATED  "201008301100Z" -- August 30 2010 11:00:00 GMT
    ORGANIZATION  "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco DSG Fault Information MIB."

    REVISION      "201008301100Z"
    DESCRIPTION   "V01.00.05 2010-08-30
                   Updated for adherence to SNMPv2 format."

                   REVISION      "201003220500Z"
    DESCRIPTION   "V01.00.04 2010-03-22
                   The Syntax of Unsigned32 MIB objects whose range
                   is within the range of Integer32, is updated to
                   Integer32."

    REVISION      "201002121200Z"
    DESCRIPTION   "V01.00.03 2010-02-12
                   The Syntax of read-only objects is updated
                   to DisplayString."

    REVISION      "201001081200Z"
    DESCRIPTION   "V01.00.02 2010-01-08
                   Updated FaultStatus and FaultSetting Table."

    REVISION      "200912201200Z"
    DESCRIPTION   "V01.00.01 2009-12-20
                   Removed logHistoryTable."

    REVISION      "200912071200Z"
    DESCRIPTION   "V01.00.00 2009-12-07
                   Initial Version."

    ::= { ciscoDSGUtilities 17 }

faultSummary             OBJECT IDENTIFIER ::= { ciscoDSGFault 1 }
faultAWTable             OBJECT IDENTIFIER ::= { ciscoDSGFault 2 }


-- *************************************
-- Fault Summary Branch
-- *************************************

faultSummaryNumActiveAlarms OBJECT-TYPE
     SYNTAX  DisplayString (SIZE(0..32))
     MAX-ACCESS  read-only
     STATUS  current
     DESCRIPTION
         "Number of system alarms currently in a set state.
         The range is from 0 to 4294967295."
     ::= {faultSummary 1 }

faultSummaryNumActiveWarnings OBJECT-TYPE
     SYNTAX DisplayString (SIZE(0..32))
     MAX-ACCESS  read-only
     STATUS  current
     DESCRIPTION
         "Number of system Warnings currently in a set state.
          THe range is from 0 to 4294967295."
     ::= { faultSummary 2 }

faultSummaryClearAlarms OBJECT-TYPE
      SYNTAX  INTEGER {
             writeonly(1),
             yes(2)
         }
     MAX-ACCESS  read-write
     STATUS  current
     DESCRIPTION
         "Set this object to yes( 2 ) to clear the system Alarms."
     ::= { faultSummary 3 }

faultSummaryClearWarnings OBJECT-TYPE
      SYNTAX  INTEGER {
             writeOnly(1),
             yes(2)
         }
     MAX-ACCESS  read-write
     STATUS  current
     DESCRIPTION
         "Set this object to yes( 2 ) to clear the system Warnings."
     ::= { faultSummary 4 }

faultSummaryClearHistory OBJECT-TYPE
      SYNTAX  INTEGER {
             writeOnly(1),
             yes(2)
         }
     MAX-ACCESS  read-write
     STATUS  current
     DESCRIPTION
         "Set this object to yes( 2 ) to clear the system History."
     ::= { faultSummary 5 }


-- *************************************
-- faultAWTable Branch
-- *************************************

-- *************************************
-- awFaultActiveListTable Branch
-- *************************************

awFaultActiveListTable OBJECT-TYPE
     SYNTAX  SEQUENCE OF AWFaultActiveListEntry
     MAX-ACCESS  not-accessible
     STATUS  current
     DESCRIPTION
         "Alarms and warnings fault active list table."
     ::= { faultAWTable 1 }

awFaultActiveListEntry OBJECT-TYPE
     SYNTAX  AWFaultActiveListEntry
     MAX-ACCESS  not-accessible
     STATUS  current
     DESCRIPTION
         "Entry for alarms and warnings fault active list."
     INDEX   { awFaultActiveListPriority }
     ::= { awFaultActiveListTable 1 }

AWFaultActiveListEntry ::=  SEQUENCE
{
  awFaultActiveListPriority      Integer32,
  awFaultActiveListTextID        DisplayString,
  awFaultActiveListName          DisplayString,
  awFaultActiveListType          INTEGER,
  awFaultActiveListSetDateTime   DisplayString,
  awFaultActiveListDetails       DisplayString
}

awFaultActiveListPriority OBJECT-TYPE
     SYNTAX  Integer32 (1..2147483647)
     MAX-ACCESS  not-accessible
     STATUS  current
     DESCRIPTION
         "Priority of fault.Higher priority faults are displayed first."
     ::= { awFaultActiveListEntry 1 }

awFaultActiveListTextID OBJECT-TYPE
     SYNTAX  DisplayString (SIZE(0..32))
     MAX-ACCESS  read-only
     STATUS  current
     DESCRIPTION
         "Fault ID."
     ::= { awFaultActiveListEntry 2 }

awFaultActiveListName OBJECT-TYPE
     SYNTAX  DisplayString (SIZE(0..32))
     MAX-ACCESS  read-only
     STATUS  current
     DESCRIPTION
         "Faults displayed text."
     ::= { awFaultActiveListEntry 3 }

awFaultActiveListType OBJECT-TYPE
     SYNTAX  INTEGER {
             alarm(1),
             warning(2)
         }
     MAX-ACCESS  read-only
     STATUS  current
     DESCRIPTION
         "Active list type."
     ::= { awFaultActiveListEntry 4 }

awFaultActiveListSetDateTime OBJECT-TYPE
     SYNTAX  DisplayString (SIZE(0..32))
     MAX-ACCESS  read-only
     STATUS  current
     DESCRIPTION
         "Date and time of fault condition occurred."
     ::= { awFaultActiveListEntry 5 }

awFaultActiveListDetails OBJECT-TYPE
     SYNTAX  DisplayString (SIZE(0..63))
     MAX-ACCESS  read-only
     STATUS  current
     DESCRIPTION
         "Fault description."
     ::= { awFaultActiveListEntry 6 }


-- *************************************
-- awFaultStatusTable Branch
-- *************************************

awFaultStatusTable OBJECT-TYPE
     SYNTAX  SEQUENCE OF AWFaultStatusEntry
     MAX-ACCESS  not-accessible
     STATUS  current
     DESCRIPTION
         "Alarms and warnings fault status."
     ::= { faultAWTable 2 }

awFaultStatusEntry OBJECT-TYPE
     SYNTAX  AWFaultStatusEntry
     MAX-ACCESS  not-accessible
     STATUS  current
     DESCRIPTION
         "Entry for Alarms and warnings fault status."
     INDEX   { awFaultStatusPriority }
     ::= { awFaultStatusTable 1 }

AWFaultStatusEntry ::=  SEQUENCE
{
  awFaultStatusPriority       Integer32,
  awFaultStatusTextId         DisplayString,
  awFaultStatusFaultNum       DisplayString,
  awFaultStatusName           DisplayString,
  awFaultStatusType           INTEGER,
  awFaultStatusSeverity       INTEGER,
  awFaultStatusLastDateTime   DisplayString,
  awFaultStatusTrapState      INTEGER,
  awFaultStatusDetails        DisplayString,
  awFaultStatusRelay          DisplayString
}

awFaultStatusPriority OBJECT-TYPE
     SYNTAX  Integer32(1..2147483647)
     MAX-ACCESS  not-accessible
     STATUS  current
     DESCRIPTION
         "Fault status Priority value."
     ::= { awFaultStatusEntry 1 }

awFaultStatusTextId OBJECT-TYPE
     SYNTAX  DisplayString (SIZE(0..32))
     MAX-ACCESS  read-only
     STATUS  current
     DESCRIPTION
         "Fault Status Text ID."
     ::= { awFaultStatusEntry 2 }

awFaultStatusFaultNum OBJECT-TYPE
     SYNTAX  DisplayString (SIZE(0..32))
     MAX-ACCESS  read-only
     STATUS  current
     DESCRIPTION
         "Fault Status number.The range is from 0 to 4294967295."
     ::= { awFaultStatusEntry 3 }

awFaultStatusName OBJECT-TYPE
     SYNTAX  DisplayString (SIZE(0..32))
     MAX-ACCESS  read-only
     STATUS  current
     DESCRIPTION
         "Fault displayed text."
     ::= { awFaultStatusEntry 4 }

awFaultStatusType OBJECT-TYPE
     SYNTAX  INTEGER {
             alarm(1),
             warning(2)
         }
     MAX-ACCESS  read-only
     STATUS  current
     DESCRIPTION
         "Fault Status type."
     ::= { awFaultStatusEntry 5 }

awFaultStatusSeverity OBJECT-TYPE
     SYNTAX  INTEGER {
             major(1),
             minor(2),
             warning(3),
             information(4)
         }
     MAX-ACCESS  read-only
     STATUS  current
     DESCRIPTION
         "Fault severity."
     ::= { awFaultStatusEntry 6 }

awFaultStatusLastDateTime OBJECT-TYPE
     SYNTAX  DisplayString (SIZE(0..32))
     MAX-ACCESS  read-only
     STATUS  current
     DESCRIPTION
         "Date&time of faults last state change."
     ::= { awFaultStatusEntry 7 }

awFaultStatusTrapState OBJECT-TYPE
     SYNTAX  INTEGER {
             clear(1),
             set(2)
         }
     MAX-ACCESS  read-only
     STATUS  current
     DESCRIPTION
         "Trap state."
     ::= { awFaultStatusEntry 8 }

awFaultStatusDetails OBJECT-TYPE
     SYNTAX  DisplayString (SIZE(0..64))
     MAX-ACCESS  read-only
     STATUS  current
     DESCRIPTION
         "Faults descriptive reason."
     ::= { awFaultStatusEntry 9 }

awFaultStatusRelay OBJECT-TYPE
     SYNTAX DisplayString(SIZE(0..32))
     MAX-ACCESS  read-only
     STATUS  current
     DESCRIPTION
         "Fault Relay control status.The range is from 0 to 8.
          Indicates which relay output this fault is hardcoded to
          control. Not used."
     ::= { awFaultStatusEntry 10 }

-- *************************************
-- awFaultSettingTable Branch
-- *************************************

awFaultSettingTable OBJECT-TYPE
     SYNTAX  SEQUENCE OF AWFaultSettingEntry
     MAX-ACCESS  not-accessible
     STATUS  current
     DESCRIPTION
         "Faults settings Table."
     ::= { faultAWTable 3 }

awFaultSettingEntry OBJECT-TYPE
     SYNTAX  AWFaultSettingEntry
     MAX-ACCESS  not-accessible
     STATUS  current
     DESCRIPTION
         "Entry for Faults settings Table."
     INDEX   { awFaultSettingPriority }
     ::= { awFaultSettingTable 1 }

AWFaultSettingEntry ::=  SEQUENCE
{
  awFaultSettingPriority    Integer32,
  awFaultSettingTextId      DisplayString,
  awFaultSettingType        INTEGER,
  awFaultSettingSeverity    INTEGER,
  awFaultSettingName        DisplayString,
  awFaultSettingEnable      INTEGER,
  awFaultSettingRelay       INTEGER,
  awFaultSettingTrap        INTEGER
}

awFaultSettingPriority OBJECT-TYPE
     SYNTAX  Integer32(1..2147483647)
     MAX-ACCESS  not-accessible
     STATUS  current
     DESCRIPTION
         "Fault Setting Index (Fault Priority value)."
     ::= { awFaultSettingEntry 1 }

awFaultSettingTextId OBJECT-TYPE
     SYNTAX  DisplayString(SIZE(0..32))
     MAX-ACCESS  read-only
     STATUS  current
     DESCRIPTION
         "Fault Setting Text ID."
     ::= { awFaultSettingEntry 2 }

awFaultSettingType OBJECT-TYPE
     SYNTAX  INTEGER {
             alarm(1),
             warning(2)
         }
     MAX-ACCESS  read-only
     STATUS  current
     DESCRIPTION
         "Fault type."
     ::= { awFaultSettingEntry 3 }

awFaultSettingSeverity OBJECT-TYPE
     SYNTAX  INTEGER {
             major(1),
             minor(2),
             warning(3),
             information(4)
         }
     MAX-ACCESS  read-only
     STATUS  current
     DESCRIPTION
         "Fault severity."
     ::= { awFaultSettingEntry 4 }

awFaultSettingName OBJECT-TYPE
     SYNTAX  DisplayString (SIZE(0..32))
     MAX-ACCESS  read-only
     STATUS  current
     DESCRIPTION
         "Fault displayed text."
     ::= { awFaultSettingEntry 5 }

awFaultSettingEnable OBJECT-TYPE
     SYNTAX  INTEGER {
             no(1),
             yes(2),
             disabled(3)
         }
     MAX-ACCESS  read-write
     STATUS  current
     DESCRIPTION
         "Controls overall enabling of this Fault.Affects LEDs, Relays,
         and Traps. disabled(3) is a read-only value."
     ::= { awFaultSettingEntry 6 }

awFaultSettingRelay OBJECT-TYPE
     SYNTAX  INTEGER {
             no(1),
             yes(2),
             disabled(3)
         }
     MAX-ACCESS  read-write
     STATUS  current
     DESCRIPTION
         "Controls whether Relays are enabled for the Fault.
          disabled(3) is a read-only value."
     ::= { awFaultSettingEntry 7 }

awFaultSettingTrap OBJECT-TYPE
     SYNTAX  INTEGER {
             no(1),
             yes(2),
             disabled(3)
         }
     MAX-ACCESS  read-write
     STATUS  current
     DESCRIPTION
         "Controls whether Traps are enabled for the Fault.
          disabled(3) is a read-only value."
     ::= { awFaultSettingEntry 8 }


-- *************************************
-- awFaultHistoryTable Branch
-- *************************************

awFaultHistoryTable OBJECT-TYPE
     SYNTAX  SEQUENCE OF AWFaultHistoryEntry
     MAX-ACCESS  not-accessible
     STATUS  current
     DESCRIPTION
         "Fault History table."
     ::= { faultAWTable 5 }

awFaultHistoryEntry OBJECT-TYPE
     SYNTAX  AWFaultHistoryEntry
     MAX-ACCESS  not-accessible
     STATUS  current
     DESCRIPTION
         "Entry for Fault History table."
     INDEX   { awFaultHistorySequence }
     ::= { awFaultHistoryTable 1 }

AWFaultHistoryEntry ::=  SEQUENCE
{
    awFaultHistorySequence          Counter32,
    awFaultHistoryName              DisplayString,
    awFaultHistoryType              INTEGER,
    awFaultHistorySetDateTime       DisplayString,
    awFaultHistoryResetDateTime     DisplayString,
    awFaultHistoryState             INTEGER,
    awFaultHistoryDetails           DisplayString
}

awFaultHistorySequence OBJECT-TYPE
     SYNTAX  Counter32
     MAX-ACCESS  not-accessible
     STATUS  current
     DESCRIPTION
         "Fault History sequence number."
     ::= { awFaultHistoryEntry 1 }

awFaultHistoryName OBJECT-TYPE
     SYNTAX  DisplayString (SIZE(0..32))
     MAX-ACCESS  read-only
     STATUS  current
     DESCRIPTION
         "Fault displayed text."
     ::= { awFaultHistoryEntry 2 }

awFaultHistoryType OBJECT-TYPE
     SYNTAX  INTEGER {
             alarm(1),
             warning(2)
         }
     MAX-ACCESS  read-only
     STATUS  current
     DESCRIPTION
         "Fault History list Type."
     ::= { awFaultHistoryEntry 3 }

awFaultHistorySetDateTime OBJECT-TYPE
     SYNTAX  DisplayString (SIZE(0..32))
     MAX-ACCESS  read-only
     STATUS  current
     DESCRIPTION
         "Faults set date and time."
     ::= { awFaultHistoryEntry 4 }

awFaultHistoryResetDateTime OBJECT-TYPE
     SYNTAX  DisplayString (SIZE(0..32))
     MAX-ACCESS  read-only
     STATUS  current
     DESCRIPTION
         "Faults reset date and time.
          If cleared by reset, contains the power-up time."
     ::= { awFaultHistoryEntry 5 }

awFaultHistoryState OBJECT-TYPE
     SYNTAX  INTEGER {
             clear(1),
             set(2),
             clearByReset(3)
         }
     MAX-ACCESS  read-only
     STATUS  current
     DESCRIPTION
         "Fault History list state."
     ::= { awFaultHistoryEntry 6 }

awFaultHistoryDetails OBJECT-TYPE
     SYNTAX  DisplayString (SIZE(0..63))
     MAX-ACCESS  read-only
     STATUS  current
     DESCRIPTION
         "Fault descriptive Reason."
     ::= { awFaultHistoryEntry 7 }

END
