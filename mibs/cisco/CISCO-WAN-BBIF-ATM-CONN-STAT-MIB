-- *****************************************************************
-- CISCO-WAN-BBIF-ATM-CONN-STAT-MIB
--  Broadband Interface Connection Statistics MIB for MGX82xx
--  products.
--
-- October 2002, Subra Hegde
--
-- Copyright (c) 2002 by cisco Systems, Inc.
-- All rights reserved.
-- *****************************************************************

CISCO-WAN-BBIF-ATM-CONN-STAT-MIB DEFINITIONS ::= BEGIN
IMPORTS
        MODULE-IDENTITY,
        OBJECT-TYPE,
        Integer32,
        Counter32       FROM    SNMPv2-SMI
        MODULE-COMPLIANCE,
        OBJECT-GROUP    FROM    SNMPv2-CONF
        bbChanCntGrp    FROM    BASIS-MIB
        ciscoWan        FROM    CISCOWAN-SMI;

ciscoWanBbifAtmConnStatMIB MODULE-IDENTITY
        LAST-UPDATED    "200210180000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "This MIB module contains ATM Connection related
        real time statistical counter objects. The ATM
        connections are applicable to PXM1 service module.
        in MGX82xx products.

        Logical Channel refers to ATM Connection(or connection
        end point).

        Terminologies used:
            broadband interface - Logical port on PXM1.
            SCR  - Sustained Cell Rate
            BT   - Burst Tolerance
            PCR  - Peak Cell Rate
            CDVT - Cell Delay Transfer Variance Tolerance
	    GCRA - The Generic Cell Rate Algorithm(GCRA) is used to
	           define comformance with repect to the traffic
	           contract. For each cell arrival, the GCRA determines
		   whether the cell conforms to the traffic contract
		   of the connection.

            GCRA1 - GCRA  Bucket 1. For CBR and UBR connections, only
                    GCRA-1 is needed to check for PCR, CDVT Conformance.

            GCRA2 - GCRA  Bucket 2. For VBR and ABR Connections, GCRA-1
                    is needed to check for PCR, CDVT conformance and
                    GCRA-2 for SCR, BT Conformance.

            EFCI - Explicit Forward Congestion Indication.
            QE    - Queue Engine(QE).
                    This ASIC Provides the traffic management functions
                    related to VC queues, QoS queues and interface
                    queues. This management function is performed
                    for both directions of traffic(ingress, egress).
            ingress - ingress traffic is defined as data flowing
                      toward the switch fabric. Ingress data can come
                      from either the Service Modules through the
                      backplane or the PXM1 Uplink back card.
            egress  - Egress traffic is defined as data flowing
                      away from the switch fabric."

       -- REFERENCE
       --    "ATM Forum Traffic Management 4.0 af-tm-0056.000"

    REVISION    "200210180000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= { ciscoWan 36 }


-- *********************************************************************
--
--
--      BROADBAND CHANNEL  COUNT Group
--
--
-- *********************************************************************


bbChanCntGrpTable OBJECT-TYPE
    SYNTAX     SEQUENCE OF BbChanCntGrpEntry
    MAX-ACCESS not-accessible
    STATUS     current
    DESCRIPTION
        "This is the broadband channel statistics table."
    ::= { bbChanCntGrp 1 }

bbChanCntGrpEntry OBJECT-TYPE
    SYNTAX     BbChanCntGrpEntry
    MAX-ACCESS not-accessible
    STATUS     current
    DESCRIPTION
        "An entry for statistics on logical channel.
        Each entry contains statistics for an ATM connection
        on broadband interface."
    INDEX   { bbChanCntNum }
    ::= { bbChanCntGrpTable  1 }

BbChanCntGrpEntry ::=
    SEQUENCE {
        bbChanCntNum                           Integer32,
        bbChanRcvClp0Cells                     Counter32,
        bbChanRcvClp1Cells                     Counter32,
        bbChanNonConformCellsAtGcra1Policer    Counter32,
        bbChanNonConformCellsAtGcra2Policer    Counter32,
--
-- additional 4 ingress counts are from QE
--
        bbChanRcvEOFCells                      Counter32,
        bbChanDscdClp0Cells                    Counter32,
        bbChanDscdClp1Cells                    Counter32,
        bbChanRcvCellsSent                     Counter32,

--
-- 4 egress counts are from QE
--
--
        bbChanXmtClp0Cells                     Counter32,
	bbChanXmtClp1Cells                     Counter32,
        bbChanDscdClpZeroCellsToPort           Counter32,
        bbChanDscdClpOneCellsToPort            Counter32,
        bbChanCntClrButton                     INTEGER
    }

bbChanCntNum OBJECT-TYPE
	SYNTAX     Integer32 (16..4111)
	MAX-ACCESS read-only
	STATUS     current
	DESCRIPTION
	    "This object identifies the logical channel number.
            The value for this object must be same as the value
            of 'bbChanCnfNum' from bbChanCnfGrpTable."
        REFERENCE
            "bbChanCnfNum is defined in CISCO-WAN-BBIF-ATM-CONN-MIB."
	::= { bbChanCntGrpEntry 1 }

bbChanRcvClp0Cells OBJECT-TYPE
	SYNTAX     Counter32
	MAX-ACCESS read-only
	STATUS     current
	DESCRIPTION
	    "CLP_0 Cells Received from broadband interface."
	::= { bbChanCntGrpEntry 2 }

bbChanRcvClp1Cells OBJECT-TYPE
	SYNTAX     Counter32
	MAX-ACCESS read-only
	STATUS     current
	DESCRIPTION
            "CLP_1 Cells Received from broadband interface."
	::= { bbChanCntGrpEntry 3 }

bbChanNonConformCellsAtGcra1Policer OBJECT-TYPE
	SYNTAX     Counter32
	MAX-ACCESS read-only
	STATUS     current
	DESCRIPTION
	    "This object provides a count of the
            nonconforming cells that are received at the
            first policing point(GCRA1 policer)."
	::= { bbChanCntGrpEntry 4 }

bbChanNonConformCellsAtGcra2Policer OBJECT-TYPE
	SYNTAX     Counter32
	MAX-ACCESS read-only
	STATUS     current
	DESCRIPTION
	    "This object provides a count of the
            nonconforming cells that are received at the
            second policing point(GCRA2 policer)."
	::= { bbChanCntGrpEntry 5 }

bbChanRcvEOFCells OBJECT-TYPE
	SYNTAX     Counter32
	MAX-ACCESS read-only
	STATUS     current
	DESCRIPTION
	    "This object provides count of End Of Frame(EOF)
            cells that are received."
	::= { bbChanCntGrpEntry 6 }

bbChanDscdClp0Cells OBJECT-TYPE
	SYNTAX     Counter32
	MAX-ACCESS read-only
	STATUS     current
        DESCRIPTION
	    "This object provides a count of the CLP equal to
            0 that are received and then discarded."
	::= { bbChanCntGrpEntry 7 }

bbChanDscdClp1Cells OBJECT-TYPE
	SYNTAX     Counter32
	MAX-ACCESS read-only
	STATUS     current
	DESCRIPTION
	    "This object provides a count of the CLP equal to
            1 that are received and then discarded."
	::= { bbChanCntGrpEntry 8 }

bbChanRcvCellsSent OBJECT-TYPE
	 SYNTAX     Counter32
	 MAX-ACCESS read-only
	 STATUS     current
	 DESCRIPTION
	     "Number of cells received from broadband interface
             and sent out of the Queue Engine(QE device)."
	::= { bbChanCntGrpEntry 9 }

bbChanXmtClp0Cells OBJECT-TYPE
	SYNTAX     Counter32
	MAX-ACCESS read-only
	STATUS     current
	DESCRIPTION
            "This object provides count of Number of cells
            with EFCI=0 that are transmitted."
	::= { bbChanCntGrpEntry 10 }

bbChanXmtClp1Cells OBJECT-TYPE
	SYNTAX     Counter32
	MAX-ACCESS read-only
	STATUS     current
	DESCRIPTION
            "This object provides count of Number of cells
            with EFCI set that are transmitted."
	::= { bbChanCntGrpEntry 11 }

bbChanDscdClpZeroCellsToPort OBJECT-TYPE
	SYNTAX     Counter32
	MAX-ACCESS read-only
	STATUS     current
	DESCRIPTION
	    "Number of CLP = 0 cells discarded before
            transmitted to broadband interface."
	::= { bbChanCntGrpEntry 12 }

bbChanDscdClpOneCellsToPort OBJECT-TYPE
	SYNTAX     Counter32
	MAX-ACCESS read-only
	STATUS     current
	DESCRIPTION
	    "Number of CLP = 1 cells discarded before
            transmitted to broadband interface."
	::= { bbChanCntGrpEntry 13 }

bbChanCntClrButton OBJECT-TYPE
    SYNTAX  INTEGER {
        noAction      (1),
        resetCounters (2)
    }
    MAX-ACCESS  read-write
    STATUS      current
    DESCRIPTION
        "Writing a value of 2 resets all the counters."
	::= { bbChanCntGrpEntry 14 }


-- conformance information

cwbAtmConnStatMIBConformance OBJECT IDENTIFIER ::=
                                    { ciscoWanBbifAtmConnStatMIB 2 }

cwbAtmConnStatMIBGroups      OBJECT IDENTIFIER ::=
                                    { cwbAtmConnStatMIBConformance 1 }

cwbAtmConnStatMIBCompliances OBJECT IDENTIFIER ::=
                                    { cwbAtmConnStatMIBConformance 2 }


-- compliance statements

cwbAtmConnStatCompliance MODULE-COMPLIANCE
    STATUS  current
    DESCRIPTION
            "The compliance statement for broadband
            interface Connection Statstics MIB."
    MODULE  -- this module
        MANDATORY-GROUPS {
            cwbAtmConnStatsGroup
        }
    ::= { cwbAtmConnStatMIBCompliances 1 }

cwbAtmConnStatsGroup OBJECT-GROUP
   OBJECTS {
        bbChanCntNum,
        bbChanRcvClp0Cells,
        bbChanRcvClp1Cells,
        bbChanNonConformCellsAtGcra1Policer,
        bbChanNonConformCellsAtGcra2Policer,
        bbChanRcvEOFCells,
        bbChanDscdClp0Cells,
        bbChanDscdClp1Cells,
        bbChanRcvCellsSent,
        bbChanXmtClp0Cells,
	bbChanXmtClp1Cells,
        bbChanDscdClpZeroCellsToPort,
        bbChanDscdClpOneCellsToPort,
        bbChanCntClrButton
   }
   STATUS current
   DESCRIPTION
       "The objects related to broadband interface
       connection statistics."
    ::= { cwbAtmConnStatMIBGroups 1 }

END
