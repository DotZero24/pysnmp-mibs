-- $ID$
-- ********************************************************************
-- CISCO-GTP-DIRECTOR-MIB.my: MIB file for GTP Director Module
--
-- September 2001, Jeyachitra Alagar
--
-- Copyright (c) 2001 by cisco Systems, Inc.
-- All rights reserved.
-- ********************************************************************
-- $Endlog$

CISCO-GTP-DIRECTOR-MIB DEFINITIONS ::= BEGIN

IMPORTS
        MODULE-IDENTITY,
        OBJECT-TYPE,
        NOTIFICATION-TYPE,
        Gauge32,
        Counter32,
        Unsigned32
                FROM SNMPv2-SMI
        TruthValue
                FROM SNMPv2-TC
        MODULE-COMPLIANCE,
        OBJECT-GROUP,
        NOTIFICATION-GROUP
                FROM SNMPv2-CONF
        ciscoMgmt
                FROM CISCO-SMI;

ciscoGtpDirectorMIB MODULE-IDENTITY
        LAST-UPDATED        "200109131400Z"
        ORGANIZATION        "Cisco Systems, Inc."
        CONTACT-INFO
                "       Cisco Systems
                        Customer Service

                Postal: 170 W Tasman Drive
                        San Jose, CA  95134
                        USA

                   Tel: +1 800 553-NETS

                E-mail: cs-gprs@cisco.com"
        DESCRIPTION
                "This MIB module defines objects that are used to
                 manage GTP Director Module.

                 In the GPRS network, the APN is the identifier that
                 specifies where the user is connecting. The APN
                 identifies whether the network is a corporate network
                 or a service provider network.  The APN comprises of
                 two parts, the network id and the operator id.

                 The Single Access point feature enables the
                 service provider to add new access-points to the GGSN
                 without having to provision the HLR. The requests are
                 sent by the SGSN to the same virtual APN. A virtual
                 APN is not associated with any actual physical
                 network.  The GGSN processes the request and forwards
                 the packet to the appropriate access-point that is
                 specified in the PCO. The Single APN feature is
                 supported only in Cisco GGSNs.

                 The purpose of the GTP-Director is to provide a
                 mechanism for service providers using non-Cisco GGSN
                 to use the Single APN feature. This would enable the
                 service providers to add access-point to the network
                 without having to provision the HLR. This will be
                 transparent to the SGSN. The mobile user initiates
                 a connection request to the SGSN. The access-point
                 name specified in the request is the virtual APN.
                 The GTP-Director would resolve the access-point name
                 and forward the request to the appropriate
                 GGSN (real GGSN).

                +==+  +===+  +====+   ====   +===+  +====+     +===+
                |MS|--|BSS|--|SGSN|--|PLMN|--|GDM|--|GGSN|--Gi-|PDN|
                +==+  +===+  +====+   ====   +===+  +====+     +===+
                                              | |
                                              | |   +====+
                                              | |___|GGSN|------Gi
                                              |     +====+       |
                                              |                  |
                                              |     +====+     +===+
                                              |_____|GGSN|--Gi-|PDN|
                                                    +====+     +===+

                 The GTP-Director also provides load balancing across
                 GGSNs. The GTP-Director uses the round-robin
                 mechanism for providing load balancing.  The
                 Cisco GGSNs may use the GTP-Director, but is not
                 necessary as they can use IOS-SLB ( Server Load
                 Balancing ).

                Acronyms and terms:
                 APN    Access Point Name
                 BSS    Base Staion Subsystem
                 GDM    GTP Director Module
                 GGSN   Gateway GPRS Support Node
                 Gi     Reference point between GPRS and an external
                        packet data network
                 GPRS   General Packet Radio Service
                 HLR    Home Location Register
                 NMS    Network Management System
                 PCO    Protocol Configuration Options
                 PDN    Packet Data Network
                 PDP    Packet Data Protocol
                 PLMN   Public Land Mobile Network
                 MS     Mobile Station
                 SGSN   Serving GPRS Support Node
                 TID    Tunnel Identifier
                 "

        REVISION        "200109131400Z"
        DESCRIPTION
                "Initial version of this MIB Module."
        ::= { ciscoMgmt 245 }

ciscoGtpDirectorMIBObjects     OBJECT IDENTIFIER
                   ::=  { ciscoGtpDirectorMIB 1 }

cgdConfigurations OBJECT IDENTIFIER
                   ::=  { ciscoGtpDirectorMIBObjects 1 }

cgdStatus         OBJECT IDENTIFIER
                   ::= { ciscoGtpDirectorMIBObjects 2 }

cgdStatistics     OBJECT IDENTIFIER
                   ::= { ciscoGtpDirectorMIBObjects 3 }

cgdNotifMgmt      OBJECT IDENTIFIER
                   ::= { ciscoGtpDirectorMIBObjects 4 }


--
-- Configuration
--
cgdCreatePdpRequestInfoSaveTimer OBJECT-TYPE
    SYNTAX      Unsigned32(1..65535)
    UNITS       "seconds"
    MAX-ACCESS  read-write
    STATUS      current
    DESCRIPTION
        "When a GDM receives a request to create PDP, it processes
        and forwards the request to the GGSN and saves the information
        related to the request.  This object defines the time during
        which the information is maintained by the GDM. Any subsequent
        retries by the SGSN within this time period will be forwarded
        to the same GGSN, but the timer will not be reset if a retry
        occurs before it has expired.
        "
    DEFVAL { 30 }
    ::= { cgdConfigurations 1 }


--
-- Status
--

cgdPendingPdps OBJECT-TYPE
    SYNTAX      Gauge32
    MAX-ACCESS  read-only
    STATUS      current
    DESCRIPTION
        "This object gives the number of create PDP requests whose
        connection retry timer has not expired.
        "
    ::= { cgdStatus 1 }

--
-- Statistics
--

cgdCreatePdpRequestFwded OBJECT-TYPE
    SYNTAX      Counter32
    MAX-ACCESS  read-only
    STATUS      current
    DESCRIPTION
        "This object gives the number of unique create PDP requests
        forwarded by the GDM to GGSN.  This does not include
        the retransmissions.
        "
    ::= { cgdStatistics 1 }

cgdTotalCreatePdpRequestFwded OBJECT-TYPE
    SYNTAX      Counter32
    MAX-ACCESS  read-only
    STATUS      current
    DESCRIPTION
        "This object gives the total number of create PDP requests
        forwarded by the GDM to GGSN.  This includes retransmissions
        too.
        "
    ::= { cgdStatistics 2 }

cgdCreateRequestRejected OBJECT-TYPE
    SYNTAX      Counter32
    MAX-ACCESS  read-only
    STATUS      current
    DESCRIPTION
        "This object gives the total number of create PDP requests
        rejected by the GGSN.
        "
    ::= { cgdStatistics 3 }

cgdTotalUnsupportedMessages OBJECT-TYPE
    SYNTAX      Counter32
    MAX-ACCESS  read-only
    STATUS      current
    DESCRIPTION
        "GDM does not support any signalling message other than
        create PDP request.  If the GDM receives any unsupported
        signalling message, it will not be forwarded to GGSN
        and will be dropped.  This object gives the total number
        of unsupported signalling messages received by the GDM.
        "
    ::= { cgdStatistics 4 }

cgdPdpRequestDropped OBJECT-TYPE
    SYNTAX      Counter32
    MAX-ACCESS  read-only
    STATUS      current
    DESCRIPTION
        "This object gives the total number of PDP requests dropped
        by the GDM due to routing failures, which occur, if the GTP is
        unable to pass the packet to IP.
        "
    ::= { cgdStatistics 5 }

--
-- Notifications and Alarms
--

cgdNotifEnable OBJECT-TYPE
    SYNTAX      TruthValue
    MAX-ACCESS  read-write
    STATUS      current
    DESCRIPTION
       "Indicates whether ciscoGtpDirectorNotifications notification will
        be sent when it is generated by the device.
          - 'true',  will enable the device to send the notification.
          - 'false', will prevent the device from sending out the
                     notification.
       "
    DEFVAL { false }
    ::= { cgdNotifMgmt 1 }

cgdNotifType OBJECT-TYPE
    SYNTAX      INTEGER {
                gdmServiceUp(1),  --GDM service Enabled
                gdmServiceDown(2) --GDM service Disabled
                }
    MAX-ACCESS  accessible-for-notify
    STATUS      current
    DESCRIPTION
        "This object indicates the type of notification.
        "
    ::= { cgdNotifMgmt 2 }

--
--  Notification Definitions
--

ciscoGtpDirectorNotifPrefix OBJECT IDENTIFIER
                           ::= { ciscoGtpDirectorMIB 2 }
ciscoGtpDirectorNotifications OBJECT IDENTIFIER
                           ::= { ciscoGtpDirectorNotifPrefix 0 }

--
-- Notifications
--

ciscoGtpDirectorNotification NOTIFICATION-TYPE
    OBJECTS     {
                  cgdNotifType
                }
    STATUS      current
    DESCRIPTION
        "This notification indicates the occurrence of a GDM
        related alarm.
        "
    ::= { ciscoGtpDirectorNotifications 1 }

--
-- Conformances definitions
--

ciscoGtpDirectorMIBConformance OBJECT IDENTIFIER
                           ::= { ciscoGtpDirectorMIB 3 }
ciscoGtpDirectorMIBCompliances OBJECT IDENTIFIER
                           ::= { ciscoGtpDirectorMIBConformance 1 }
ciscoGtpDirectorMIBGroups      OBJECT IDENTIFIER
                           ::= { ciscoGtpDirectorMIBConformance 2 }


-- Conformance

ciscoGtpDirectorMIBCompliance MODULE-COMPLIANCE
    STATUS           current
    DESCRIPTION
        "The compliance statements for entities which implement
        CISCO-GDM-MIB.
        "
    MODULE            -- this module
    MANDATORY-GROUPS  {
                        ciscoGtpDirectorConfigurationsGroup,
                        ciscoGtpDirectorStatusGroup,
                        ciscoGtpDirectorStatisticsGroup,
                        ciscoGtpDirectorNotifMgmtGroup,
                        ciscoGtpDirectorNotifGroup
                      }
        ::= { ciscoGtpDirectorMIBCompliances 1 }

-- Units of Conformance

ciscoGtpDirectorConfigurationsGroup OBJECT-GROUP
    OBJECTS      {
                   cgdCreatePdpRequestInfoSaveTimer
                 }
    STATUS       current
    DESCRIPTION
        "A collection of GDM configuration objects.
        "
        ::= { ciscoGtpDirectorMIBGroups 1 }

ciscoGtpDirectorStatusGroup OBJECT-GROUP
    OBJECTS      {
                   cgdPendingPdps
                 }
    STATUS       current
    DESCRIPTION
        "A collection of GDM status.
        "
        ::= { ciscoGtpDirectorMIBGroups 2 }

ciscoGtpDirectorStatisticsGroup OBJECT-GROUP
    OBJECTS      { cgdCreatePdpRequestFwded,
                   cgdTotalCreatePdpRequestFwded,
                   cgdCreateRequestRejected,
                   cgdTotalUnsupportedMessages,
                   cgdPdpRequestDropped
                 }
    STATUS       current
    DESCRIPTION
        "A collection of GDM Statistics.
        "
        ::= { ciscoGtpDirectorMIBGroups 3 }

ciscoGtpDirectorNotifMgmtGroup OBJECT-GROUP
    OBJECTS     {
                  cgdNotifEnable,
                  cgdNotifType
                }
    STATUS      current
    DESCRIPTION
        " A collection of objects related with notification
        management on GDM."
    ::= { ciscoGtpDirectorMIBGroups 4 }

ciscoGtpDirectorNotifGroup NOTIFICATION-GROUP
    NOTIFICATIONS  {
                      ciscoGtpDirectorNotification
                   }
    STATUS         current
    DESCRIPTION
        "A collection of notifications.
        "
    ::= { ciscoGtpDirectorMIBGroups 5 }
END
