-- *****************************************************************
-- CISCO-ITP-DSMR-MIB: Distributed Short Message Routing
--
-- September 2004, John Linton, Shekhar Acharya
--
-- Copyright (c) 2004-2005 by Cisco Systems, Inc.
-- All rights reserved.
-- *****************************************************************
CISCO-ITP-DSMR-MIB DEFINITIONS ::= BEGIN
IMPORTS
        CgsccpGttGlobalTitleInd,
        CgsccpGttTransType
                FROM CISCO-ITP-GSCCP-MIB

        cgspCLLICode,
        cgspEventSequenceNumber,
        cgspInstNetwork
                FROM CISCO-ITP-GSP-MIB

        CItpTcGtaLongDisplay,
        CItpTcNAI,
        CItpTcNetworkName,
        CItpTcNumberingPlan,
        CItpTcPointCode,
        CItpTcSubSystemNumber,
        CItpTcTableLoadStatus,
        CItpTcURL
                FROM CISCO-ITP-TC-MIB

        CmlrAddressDigits,
        CmlrAddressType,
        CmlrId,
        CmlrName,
        CmlrRuleProtocol,
        CmlrRuleSetName
                FROM CISCO-ITP-MLR-MIB

        ciscoMgmt
                FROM CISCO-SMI

        InetAddressType,
        InetAddress,
        InetPortNumber
             FROM INET-ADDRESS-MIB

        MODULE-COMPLIANCE,
        NOTIFICATION-GROUP,
        OBJECT-GROUP
                FROM SNMPv2-CONF

        Counter32,
        Integer32 ,
        MODULE-IDENTITY,
        NOTIFICATION-TYPE,
        OBJECT-TYPE,
        Unsigned32
                FROM SNMPv2-SMI

        DateAndTime,
        RowStatus,
        TEXTUAL-CONVENTION,
        TimeStamp,
        TruthValue
                FROM SNMPv2-TC;

ciscoItpDsmrMIB MODULE-IDENTITY
        LAST-UPDATED    "200505170000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"

        DESCRIPTION
           "The MIB for providing information about Distributed Short
            Message Routing for Short Message Service Center.  This
            MIB will provide information used to control and measure
            SS7 messages signalling units in a SS7 Network. Message
            Signalling Units are routed based on information found
            in the SCCP, TCAP, MAP, and MAP-user layers.  It uses
            information from these layers to make customizable
            routing decision based on the following criteria.

            - message A-address (origination SME)
            - message B-address (destination SME)
            - protocol identifier
            - operation code
            - called party address
            - calling party address

            The Cisco IP Transfer Point (ITP) is a hardware
            and software solution that transports SS7 traffic
            using IP.  Each ITP node provides function similar
            to SS7 signalling point.

            The Distributed Short Message Routing will be developed in
            compliance to the following standards.

            - GSM MAP v1, v2 and v3  MO SMS formats
            - GSM MAP SMS user information for MO messages
            - IS-41 MAP Mobile Originated SMS formats for
              Revisions A thru D.


            Acronyms and Terms
            A-address  The originating SME of the short message.

            AO         Application Originated (synonymous with FO).
                       This term is used to refer to an SMS
                       message that is being sent from an
                       application to the SMSC, typically over
                       SMPP.  Traffic alerts, stock quotes,
                       sports updates are typically AO.

            ANSI-41    ANSI standard for defining cellular radio
                       telecommunications inter-system operation.

            AT         Application Terminated (synonymous with FT).
                       This term is used to refer to an SMS message
                       that is being sent to an application from
                       the SMSC, typically over SMPP.  Voting
                       traffic is typically AT.

            B-address  The destination SME of the short message.

            BCH        Binary Coded Hexadecimal

            CdPA       The SCCP Called Party Address field.

            CgPA       The SCCP Calling Party Address field.

            ESME       External Short Message Entity.

            DSMR       Distributed Short Message Routing

            FO         Fixed Originated (synonymous with AO)

            FT         Fixed Terminated (synonymous with AT)

            GSM        ITU standard for defining the Global
                       System for Mobile communications.

            GTT        Global Title Translation.  A function
                       normally performed in an STP, GTT is the
                       procedure by which the destination
                       signalling point and subsystem number(SSN)
                       is determined from GTA digits (i.e., the
                       global title) present in the signalling
                       message.

            IMEI       International Mobile Equipment Identity

            IMSI       International Mobile Station Identity or
                       International Mobile Subscriber Identity
                       A mobile station identifier typically
                       used in GSM networks, but is also defined
                       for use in IS-41 networks via IS-751.

            IS-41      ANSI standard for defining cellular radio
                       telecommunications inter-system operation.
                       Unless otherwise stated, this refers to
                       the IS-41-D specification.

            MAP        SS7 Mobile Application Part.  This layer
                       provides mobility procedures to SS7
                       network applications.  MAP is generically
                       used to refer to both GSM-MAP, and the
                       IS-41-D MAP Protocol.

            MC         Message Center.  Network element responsible
                       for relaying and store-and-forwarding of
                       short messages in ANSI-41 networks.

            MDN        Mobile Directory Number.  A 10-digit North
                       American Numbering Plan number assigned to
                       mobile users in IS-41 networks.  It may be
                       different from the MIN.

            MIN        Mobile Identification Number.  The 10-digit
                       North American Numbering Plan number
                       assigned to mobile users in IS-41 networks.
                       It may be different from the MDN.

            MLR        Multi-layer Routing

            MO         Mobile Originated.  This term is used to
                       refer to an SMS message that is being
                       sent from an MS to the SMSC.

            MS         Mobile Subscriber.

            MS         mobile station

            MSU        Message Signal Unit

            MT         Mobile Terminated.  This term is used to
                       refer to an SMS message that is being
                       sent from an SMSC to an MS.

            MTP        Message Transfer Part
                       MTP1   Layers 1 (physical)
                       MTP2   Layer  2 (data) and
                       MTP3   Layer  3 (network)


            M2PA       SS7 MTP2-User Peer-to-Peer Adaptation
                       Layer specified by the IETF SIGTRAN
                       working group, which provides SCTP/IP
                       based links for MTP3.

            M3UA       SS7 MTP3 User Adaptation Layer specified
                       by RFC 3332 for MTP3 users like ISUP.

            RR         Round Robin.  A balancing algorithm that
                       evenly distributes traffic among
                       available servers.

            SCCP       Signalling Connection Control Part.  As
                       part of the SS7 signalling protocol, it
                       provides connectionless and
                       connection-oriented network services
                       above MTP Level 3.


            SCP        Service Control Point. An element of
                       an SS7-based Intelligent Network which
                       performs various service functions, such
                       as number translation, call setup
                       and tear down, etc.

            SCTP       Stream Control Transmission Protocol.
                       A protocol designed by the SigTran
                       working group of the IETF to transport
                       messages reliably over IP networks(RFC
                       2960).
                       It has been specifically designed with
                       PSTN signalling in mind, but is meant to
                       be a general IP transport protocol.

            SG         Signalling Gateway.
            SIM        Subscriber Identity Module

            SME        Short Message Entity.  An entity that may
                       send or receive short messages, and may
                       be fixed or mobile.

            SM         Short Message

            SMPP       Short Message Peer-to-Peer (protocol)
            SMD-PP     Short Message Delivery Point to Point.

            SMS        Short Message Service, as defined in
                       GSM and IS-41-D.

            SMS-MO     Short Message Service Mobile Originated.

            SMS-MT     Short Message Service Mobile Terminated.

            SMSC       Short Message Service Center.  Network
                       element responsible for relaying and
                       store-and-forwarding of short messages.

            SRI        Send Routing Information or Send Routing
                       Information for Short Messages.  Refers
                       to the procedure by which an SMSC
                       requests the HLR to send current routing
                       information for a particular mobile user.

            SRI-SM     Send Routing Information Short Message

            SSP        Service Switching Point.  An element of
                       an SS7-based Intelligent Network that
                       performs call origination, termination,
                       or tandem switching.

            STP        Signal Transfer Point.  An element of
                       an SS7-based Intelligent Network that
                       performs routing of the SS7 signalling.

            SUA        SS7 SCCP User Adaptation Layer specified
                       by IETF SIGTRAN for SCCP users, like
                       GSM MAP, UMTS RANAP, CDMA IS-41,
                       CDMA IS-634, IN INAP, CAMEL CAP.

            TCAP       Transaction Capability Application Part.
                       The application layer of the SS7
                       signalling protocol.

            UCP        Universal Computer Protocol.

            WRR        Weighted Round Robin.  A variation of
                       the round robin algorithm that uses
                       server weights to allow uneven
                       distribution of traffic among a set
                       of available servers.

           All objects defined as Counter32 apply from the time the
           statement is activated until it is deleted.

            ********************************************"
        REVISION        "200505170000Z"
        DESCRIPTION
                "Initial version of this MIB module."
        ::= { ciscoMgmt 1300 }


-- Top-level structure of the MIB
ciscoItpDsmrMIBNotifs  OBJECT IDENTIFIER ::= { ciscoItpDsmrMIB    0 }
ciscoItpDsmrMIBObjects OBJECT IDENTIFIER ::= { ciscoItpDsmrMIB    1 }
ciscoItpDsmrMIBConform OBJECT IDENTIFIER ::= { ciscoItpDsmrMIB    2 }

--  ********************************************************************
--  *                                                                  *
--  * Textual Conventions                                              *
--  *                                                                  *
--  ********************************************************************
CdsmrMaximumDigits ::= TEXTUAL-CONVENTION
        STATUS          current
        DESCRIPTION
           "Maximum number of digits that global title
            address can contain and match rule.  The maximum
            number of digits must be greater than or equal to
            the length of the specified address.  Also, the
            maximum number of digits must be greater than or
            equal to minimum number of digits. A value of zero
            indicates the ranges is not be applied."
        SYNTAX  Unsigned32 (0..20)

CdsmrMinimumDigits ::= TEXTUAL-CONVENTION
        STATUS          current
        DESCRIPTION
           "Minimum number of digits that global title
            address can contain and match rule.  The minimum
            number of digits must be greater than or equal to
            the length of the specified address. A value of zero
            indicates the ranges is not be applied.
            does not apply when the global title address length
            is set to zero."
        SYNTAX  Unsigned32 (0..20)

CdsmrResultDestinationType ::= TEXTUAL-CONVENTION
    STATUS          current
    DESCRIPTION
       "List of possible destination types as follows.
        'none'    : Result not specified.
        'gt'      : The global title address formatted as
                    CItpTcGtaLongDisplay
        'smpp'    : Short Message Peer-to-Peer protocol destination.
        'ucp'     : Universal Computer Protocol destination.
        'pc'      : Point-code  destination.
        'pcSsn'   : Point-code and subsystem number destination."
    SYNTAX                       INTEGER {
                                    none(1),
                                    gt(2),
                                    smpp(3),
                                    ucp(4),
                                    pc(5),
                                    pcSsn(6)
                                 }

CdsmrResultOctet ::= TEXTUAL-CONVENTION
        STATUS          current
        DESCRIPTION
          "An octet string that contains various types of output
           from a rule. The information in this textual convention
           is formatted as follows:

           CdsmrResultType:
              None      : Octet string with length of zero.
              pc        : Not applicable
              pcSsn     : Not applicable.
              gt        : The global title address formatted as
                          CItpTcGtaLongDisplay
              group     : Result group formatted as CmlrName.
              smpp      : Result group formatted as CmlrName
              ucp       : Result group formatted as CmlrName
              block     : Not applicable.
              ruleNext  : Not applicable.
              ruleNumber: Not applicable.
              deliveryMt: Not applicable.
              origImsi  : Not Applicable
              origImsiNext: Not Applicable

           When the result octet is not used as a parameter,
           not applicable, the length will be set to zero.

           An octet string specified by an administrator that
           must be in human-readable form.  The names must
           conform to the allowed characters that can be
           specified via Command Line Interface(CLI).  The
           names cannot contain control character and should
           not contain leading or trailing white space."
        SYNTAX OCTET STRING ( SIZE (0..64) )

CdsmrResultParameters ::= TEXTUAL-CONVENTION
    STATUS          current
    DESCRIPTION
       "In order to specify the results of DSMR
        statements different values in the packet can be
        modified. These values are determined by a combination
        of variant and operation type. This object indicates
        which objects will be used to form a result action
        as follows.

        This textual convention defines the result actions of DSMR
        which are determined by a combination of variant and
        operation type. The possible result actions of DSMR are
        as follows:

        'network'   : specifies network
        'octet'     : specifies octet string
        'tranType'  : specifies translation type
        'gti'       : specifies global title indicator
        'np'        : specifies numbering plan
        'nai'       : specifies nature of address
        'pc'        : specifies point-code
        'ssn'       : specifies subsystem number
        'ruleNumber': specifies next rule to execute"
    SYNTAX                       BITS {
                                    network(0),
                                    octet(1),
                                    tranType(2),
                                    gti(3),
                                    np(4),
                                    nai(5),
                                    pc(6),
                                    ssn(7),
                                    ruleNumber(8)
                                  }
CdsmrResultType ::= TEXTUAL-CONVENTION
    STATUS          current
    DESCRIPTION
       "This textual convention defines the result type of DSMR.
        The possible result types are as follows:
        'none'    : Result not specified.
        'block'   : Message will be discarded.
        'pc'      : Message will be routed using the specified
                    destination point code.
        'pcSsn'   : Message will be routed using the specified
                    destination point code and subsystem number.
                    destination M3UA or SUA Application Server(AS).
        'gt'      : Message will be routed using SCCP global title.
        'group'   : Message will be routed using information
                    specified in result group.
        'smpp'    : Delivery via Short Message Peer-to-Peer
        'ucp'     : Delivery via Universal Computer Protocol
        'ruleNext'
                  : When address matches entry in table processing
                    will continue with next rule.
        'ruleNumber'
                  : When address matches entry in table processing
                    will continue with specified rule.
        'deliverMt': Indicates that a delivery attempt should be
                    attempted to the destination SME as a mobile
                    device.
        'origImsi': Attempt to obtain the original IMSI address and
                    us it to delivery packet.  When the IMSI address
                    is unavailable fail packet.
        'origImsiNext': Attempt to obtain the original IMSI address
                    and us it to delivery packet.  When the IMSI
                    address is unavailable continue processing with
                    next rule.
       "
    SYNTAX                       INTEGER {
                                    none(0),
                                    pc(1),
                                    pcSsn(2),
                                    gt(3),
                                    group(4),
                                    smpp(5),
                                    ucp(6),
                                    block(7),
                                    ruleNext(8),
                                    ruleNumber(9),
                                    deliverMt(10),
                                    origImsi(11),
                                    origImsiNext(12)
                                 }

--  *************************************************************
--  *                                                           *
--  * Scalars                                                   *
--  *                                                           *
--  *************************************************************
cdsmrScalars   OBJECT IDENTIFIER ::= { ciscoItpDsmrMIBObjects 1 }

cdsmrTableLoadNotifEnabled       OBJECT-TYPE
     SYNTAX                      TruthValue
     MAX-ACCESS                  read-write
     STATUS                      current
     DESCRIPTION
        "This object controls the generation of
        ciscoDsmrTableLoad as follows:
        'true(1)'  - the generation of ciscoDsmrTableLoad
                     notifications is enabled.
        'false(2)' - the generation of ciscoDsmrTableLoad
                     notifications is disabled."
     DEFVAL { false }
    ::= { cdsmrScalars 1 }

--  *************************************************************
--  *                                                           *
--  * Instance Table                                            *
--  *                                                           *
--  *************************************************************
cdsmrInstTable              OBJECT-TYPE
    SYNTAX                  SEQUENCE OF CdsmrInstTableEntry
    MAX-ACCESS              not-accessible
    STATUS                  current
    DESCRIPTION
       "A table that is used to provide information and measurements
        related to Distributed Short Message Routing per signalling
        point. Entries are added to this table via
        cdsmrInstRowStatus in accordance with the RowStatus
        convention."
    ::= { ciscoItpDsmrMIBObjects 2 }

cdsmrInstTableEntry               OBJECT-TYPE
    SYNTAX                        CdsmrInstTableEntry
    MAX-ACCESS                    not-accessible
    STATUS                        current
    DESCRIPTION
       "Each entry in this table provides information on each
        signalling point supported by this device."
    INDEX   { cgspInstNetwork
    }
    ::= { cdsmrInstTable  1 }

CdsmrInstTableEntry ::= SEQUENCE {
    cdsmrInstLastChanged             TimeStamp,
    cdsmrInstLastLoadTime            TimeStamp,
    cdsmrInstLoadStatus              CItpTcTableLoadStatus,
    cdsmrInstLastURL                 CItpTcURL,
    cdsmrInstDeliveredSmppCounts     Counter32,
    cdsmrInstDeliveredUcpCounts      Counter32,
    cdsmrInstDeliveredGsmCounts      Counter32,
    cdsmrInstDeferredGsmCounts       Counter32,
    cdsmrInstGsmStatusReports        Counter32,
    cdsmrInstUcpNotifications        Counter32,
    cdsmrInstSmppDeliveryReceipts    Counter32,
    cdsmrInstRoutingFailures         Counter32,
    cdsmrInstResultFailures          Counter32,
    cdsmrInstInternalErrors          Counter32,
    cdsmrInstParseErrors             Counter32,
    cdsmrInstResourceErrors          Counter32,
    cdsmrInstProvisioningErrors      Counter32,
    cdsmrInstDestUnreachableErrors   Counter32,
    cdsmrInstDestSignalErrors        Counter32,
    cdsmrInstTimeOuts                Counter32,
    cdsmrInstBlockedPackets          Counter32,
    cdsmrInstRoutingRequestsRcvdGsm  Counter32,
    cdsmrInstRoutingRequestsRcvdIs41 Counter32,
    cdsmrInstRoutingRequestsRcvdUcp  Counter32,
    cdsmrInstRoutingRequestsRcvdSmpp Counter32,
    cdsmrInstRowStatus               RowStatus
}


cdsmrInstLastChanged              OBJECT-TYPE
    SYNTAX                        TimeStamp
    MAX-ACCESS                    read-only
    STATUS                        current
    DESCRIPTION
       "The value of sysUpTime at the time of the last
        creation or deletion of an entry in the Multi-Layer
        configurations defined for this signalling point.
        If the local network management subsystem is
        re-initialized, then this object contains the
        sysUpTime at the time when this occurred.  This value
        can be used to prevent unnecessary walks of the
        various tables supporting Distributed Short
        Message Routing."
    ::= {  cdsmrInstTableEntry  1 }

cdsmrInstLastLoadTime             OBJECT-TYPE
    SYNTAX                        TimeStamp
    MAX-ACCESS                    read-only
    STATUS                        current
    DESCRIPTION
       "The value of sysUpTime at the time of the last load of
        a file supporting Distributed Short Message Routing
        for this signalling point."
    ::= {  cdsmrInstTableEntry 2 }

cdsmrInstLoadStatus               OBJECT-TYPE
    SYNTAX                        CItpTcTableLoadStatus
    MAX-ACCESS                    read-only
    STATUS                        current
    DESCRIPTION
       "The status of the current load or status from
        the prior load operation.  This object will have
        a value of loadInProgress while the load operation
        is in progress.  The cdsmrInstLastLoadTime contains
        a timestamp indicating when the load operation is
        completed."
    ::= { cdsmrInstTableEntry  3 }

cdsmrInstLastURL                  OBJECT-TYPE
    SYNTAX                        CItpTcURL
    MAX-ACCESS                    read-only
    STATUS                        current
    DESCRIPTION
       "The last URL used to load a file used to configure
        Distributed Short Message Routing."
    ::= { cdsmrInstTableEntry  4 }

cdsmrInstDeliveredSmppCounts     OBJECT-TYPE
    SYNTAX                       Counter32
    UNITS                        "packets"
    MAX-ACCESS                   read-only
    STATUS                       current
    DESCRIPTION
       "Count of the number of times a packet was routed
        using Short Message Peer-to-Peer protocol."
    ::= { cdsmrInstTableEntry   5 }

cdsmrInstDeliveredUcpCounts      OBJECT-TYPE
    SYNTAX                       Counter32
    UNITS                        "packets"
    MAX-ACCESS                   read-only
    STATUS                       current
    DESCRIPTION
       "Count of the number of times a packet was routed
        using Universal Computer Protocol(UCP)."
    ::= { cdsmrInstTableEntry   6 }

cdsmrInstDeliveredGsmCounts      OBJECT-TYPE
    SYNTAX                       Counter32
    UNITS                        "packets"
    MAX-ACCESS                   read-only
    STATUS                       current
    DESCRIPTION
       "Count of the number of times a GSM packet was
        delivered."
    ::= { cdsmrInstTableEntry   7 }

cdsmrInstDeferredGsmCounts        OBJECT-TYPE
    SYNTAX                       Counter32
    UNITS                        "packets"
    MAX-ACCESS                   read-only
    STATUS                       current
    DESCRIPTION
       "Count of the number of times a GSM packet was
        deferred."
    ::= { cdsmrInstTableEntry   8 }

cdsmrInstGsmStatusReports        OBJECT-TYPE
    SYNTAX                       Counter32
    UNITS                        "packets"
    MAX-ACCESS                   read-only
    STATUS                       current
    DESCRIPTION
       "Count of the number GSM status reports issued by device."
    ::= { cdsmrInstTableEntry   9 }

cdsmrInstUcpNotifications        OBJECT-TYPE
    SYNTAX                       Counter32
    UNITS                        "packets"
    MAX-ACCESS                   read-only
    STATUS                       current
    DESCRIPTION
       "Count of the number UCP notifications issued by device."
    ::= { cdsmrInstTableEntry  10 }

cdsmrInstSmppDeliveryReceipts    OBJECT-TYPE
    SYNTAX                       Counter32
    UNITS                        "packets"
    MAX-ACCESS                   read-only
    STATUS                       current
    DESCRIPTION
       "Count of the number SMPP delivery receipts issued by
        device."
    ::= { cdsmrInstTableEntry  11 }

cdsmrInstRoutingFailures         OBJECT-TYPE
    SYNTAX                       Counter32
    UNITS                        "packets"
    MAX-ACCESS                   read-only
    STATUS                       current
    DESCRIPTION
       "Count of the number of times a packet could not be delivered
        because route was not configured."
    ::= { cdsmrInstTableEntry  12 }

cdsmrInstResultFailures          OBJECT-TYPE
    SYNTAX                       Counter32
    UNITS                        "packets"
    MAX-ACCESS                   read-only
    STATUS                       current
    DESCRIPTION
       "Count of the number of times processing of packet did not
        produce valid result."
    ::= { cdsmrInstTableEntry  13 }

cdsmrInstInternalErrors          OBJECT-TYPE
    SYNTAX                       Counter32
    UNITS                        "packets"
    MAX-ACCESS                   read-only
    STATUS                       current
    DESCRIPTION
       "Count of the number of times processing of packet was
        not completed due to internal error."
    ::= { cdsmrInstTableEntry  14 }

cdsmrInstParseErrors             OBJECT-TYPE
    SYNTAX                       Counter32
    UNITS                        "packets"
    MAX-ACCESS                   read-only
    STATUS                       current
    DESCRIPTION
       "Count of the number of times processing of packet was
        not completed due to parsing error."
    ::= { cdsmrInstTableEntry  15 }

cdsmrInstResourceErrors          OBJECT-TYPE
    SYNTAX                       Counter32
    UNITS                        "packets"
    MAX-ACCESS                   read-only
    STATUS                       current
    DESCRIPTION
       "Count of the number of times processing of packet was
        not completed due to unavailable resources on device."
    ::= { cdsmrInstTableEntry  16 }

cdsmrInstProvisioningErrors      OBJECT-TYPE
    SYNTAX                       Counter32
    UNITS                        "packets"
    MAX-ACCESS                   read-only
    STATUS                       current
    DESCRIPTION
       "Count of the number of times processing of packet was
        not completed due to provisioning errors on device."
    ::= { cdsmrInstTableEntry  17 }

cdsmrInstDestUnreachableErrors   OBJECT-TYPE
    SYNTAX                       Counter32
    UNITS                        "packets"
    MAX-ACCESS                   read-only
    STATUS                       current
    DESCRIPTION
       "Count of the number of times packet was not routed
        because destination was unreachable."
    ::= { cdsmrInstTableEntry  18 }

cdsmrInstDestSignalErrors        OBJECT-TYPE
    SYNTAX                       Counter32
    UNITS                        "packets"
    MAX-ACCESS                   read-only
    STATUS                       current
    DESCRIPTION
       "Count of the number of times packet was not routed
        because destination had signal error."
    ::= { cdsmrInstTableEntry  19 }

cdsmrInstTimeOuts                OBJECT-TYPE
    SYNTAX                       Counter32
    UNITS                        "packets"
    MAX-ACCESS                   read-only
    STATUS                       current
    DESCRIPTION
       "Count of the number of times packet was not delivered
        due to timeout."
    ::= { cdsmrInstTableEntry  20 }

cdsmrInstBlockedPackets          OBJECT-TYPE
    SYNTAX                       Counter32
    UNITS                        "packets"
    MAX-ACCESS                   read-only
    STATUS                       current
    DESCRIPTION
       "Count of the number of times packets were blocked
        by processing."
    ::= { cdsmrInstTableEntry  21 }

cdsmrInstRoutingRequestsRcvdGsm  OBJECT-TYPE
    SYNTAX                       Counter32
    UNITS                        "packets"
    MAX-ACCESS                   read-only
    STATUS                       current
    DESCRIPTION
       "Count of the number of routing requests received
        were traffic was GSM based."
    ::= { cdsmrInstTableEntry  22 }

cdsmrInstRoutingRequestsRcvdIs41  OBJECT-TYPE
    SYNTAX                       Counter32
    UNITS                        "packets"
    MAX-ACCESS                   read-only
    STATUS                       current
    DESCRIPTION
       "Count of the number of routing requests received
        were traffic was IS-41 based."
    ::= { cdsmrInstTableEntry  23 }

cdsmrInstRoutingRequestsRcvdUcp  OBJECT-TYPE
    SYNTAX                       Counter32
    UNITS                        "packets"
    MAX-ACCESS                   read-only
    STATUS                       current
    DESCRIPTION
       "Count of the number of routing requests received
        were traffic was UCP based."
    ::= { cdsmrInstTableEntry  24 }

cdsmrInstRoutingRequestsRcvdSmpp OBJECT-TYPE
    SYNTAX                       Counter32
    UNITS                        "packets"
    MAX-ACCESS                   read-only
    STATUS                       current
    DESCRIPTION
       "Count of the number of routing requests received
        were traffic was SMPP based."
    ::= { cdsmrInstTableEntry  25 }

cdsmrInstRowStatus               OBJECT-TYPE
    SYNTAX                       RowStatus
    MAX-ACCESS                   read-create
    STATUS                       current
    DESCRIPTION
       "The object is used by a management station to
        create or delete the row entry in cdsmrInstTable
        following the RowStatus textual convention."
    ::= { cdsmrInstTableEntry 26}

--  *************************************************************
--  *                                                           *
--  * Result Group Table                                        *
--  *                                                           *
--  *************************************************************
cdsmrResultGroupTable       OBJECT-TYPE
    SYNTAX                  SEQUENCE OF CdsmrResultGroupTableEntry
    MAX-ACCESS              not-accessible
    STATUS                  current
    DESCRIPTION
       "A table used to identify a group of results and define
        parameter that apply to all result within the group.
        Entries are added to this table via
        cdsmrResultGroupRowStatus  in accordance with the RowStatus
        convention."

    ::= { ciscoItpDsmrMIBObjects 3 }

cdsmrResultGroupTableEntry        OBJECT-TYPE
    SYNTAX                        CdsmrResultGroupTableEntry
    MAX-ACCESS                    not-accessible
    STATUS                        current
    DESCRIPTION
      "This table is used to define a collection of results."

    INDEX   { cgspInstNetwork,
              cdsmrResultGroupName
    }
    ::= { cdsmrResultGroupTable  1 }

CdsmrResultGroupTableEntry ::= SEQUENCE {
    cdsmrResultGroupName                 CmlrName,
    cdsmrResultGroupServerType           INTEGER,
    cdsmrResultGroupCdrConsolidation     OCTET STRING,
    cdsmrResultGroupIdentifier           Unsigned32,
    cdsmrResultGroupQueueLimit           Unsigned32,
    cdsmrResultGroupQueueTimeLimit       Unsigned32,
    cdsmrResultGroupMatchSmppId          OCTET STRING,
    cdsmrResultGroupMatchSmppType        OCTET STRING,
    cdsmrResultGroupMatchUcpId           OCTET STRING,
    cdsmrResultGroupRowStatus            RowStatus
    }

cdsmrResultGroupName             OBJECT-TYPE
    SYNTAX                       CmlrName
    MAX-ACCESS                   not-accessible
    STATUS                       current
    DESCRIPTION
       "A name used to define a result group."
    ::= { cdsmrResultGroupTableEntry  1 }

cdsmrResultGroupServerType       OBJECT-TYPE
    SYNTAX                       INTEGER {
                                    esme(1),
                                    smsc(2)
    }
    MAX-ACCESS                   read-create
    STATUS                       current
    DESCRIPTION
       "This object specifies the server type as follows.

        'esme' - Indicates this result group represents an external
                 short message entity (ESME).  Coding this parameter
                 will allow the user to enter ESME specific
                 parameters and enable the Distributed Short Message
                 Routing to properly characterize the routing of the
                 message.

        'smsc' - Indicates this result group represents a short
                 message service center (SMSC).  Coding this
                 parameter will allow the user to enter SMSC
                 specific parameters and enable the Distributed
                 Short Message Routing to properly characterize
                 the routing of the message."
    ::= { cdsmrResultGroupTableEntry  2 }

cdsmrResultGroupCdrConsolidation OBJECT-TYPE
    SYNTAX                       OCTET STRING( SIZE ( 0..5 ) )
    MAX-ACCESS                   read-create
    STATUS                       current
    DESCRIPTION
        "The object provides a one to five ASCII characters ESME
         (large account) consolidation string. This object only
         applies when the cdsmrResultGroupServerType object
         specifies ESME. The object returns the null string
         when not specified."
    ::= { cdsmrResultGroupTableEntry  3 }


cdsmrResultGroupIdentifier       OBJECT-TYPE
    SYNTAX                       Unsigned32 (0 | 100..9999)
    MAX-ACCESS                   read-create
    STATUS                       current
    DESCRIPTION
        "The object provides a ESME (large account) identifier.
         This object only applies when the cdsmrResultGroupServerType
         object specifies ESME. The zero value is usedt to
         indicate that the object has not been specified."
    ::= { cdsmrResultGroupTableEntry  4 }

cdsmrResultGroupQueueLimit       OBJECT-TYPE
    SYNTAX                       Unsigned32 (0..100000)
    MAX-ACCESS                   read-create
    STATUS                       current
    DESCRIPTION
        "This object defines the maximum number of elements on
         outbound queue for any destination. The value of 0
         indicates that there is no limit on the number of
         entries."
    ::= { cdsmrResultGroupTableEntry  5 }

cdsmrResultGroupQueueTimeLimit   OBJECT-TYPE
    SYNTAX                       Unsigned32
    UNITS                        "milliseconds"
    MAX-ACCESS                   read-create
    STATUS                       current
    DESCRIPTION
        "Maximum time element can exist in outbound queue."
    ::= { cdsmrResultGroupTableEntry  6 }

cdsmrResultGroupMatchSmppId      OBJECT-TYPE
    SYNTAX                       OCTET STRING( SIZE ( 0..15 ) )
    MAX-ACCESS                   read-create
    STATUS                       current
    DESCRIPTION
        "When specified this object provides 1 to 15 character
         ESME system identifier. This object only applies when
         the cdsmrResultGroupServerType object specifies ESME."
    ::= { cdsmrResultGroupTableEntry  7 }

cdsmrResultGroupMatchSmppType    OBJECT-TYPE
    SYNTAX                       OCTET STRING( SIZE ( 0..12 ) )
    MAX-ACCESS                   read-create
    STATUS                       current
    DESCRIPTION
        "When specified this object provides 1 to 12 character
         ESME system type.  This object only applies when the
         cdsmrResultGroupServerType object specifies ESME.
         When this object is not specified it will return the
         null sting."
    ::= { cdsmrResultGroupTableEntry  8 }

cdsmrResultGroupMatchUcpId       OBJECT-TYPE
    SYNTAX                       OCTET STRING( SIZE ( 0..16 ) )
    MAX-ACCESS                   read-create
    STATUS                       current
    DESCRIPTION
        "The object provides 1 to 16 character ESME
         ESME UCP address code. This object only applies when
         the cdsmrResultGroupServerType object specifies ESME."
    ::= { cdsmrResultGroupTableEntry  9 }

cdsmrResultGroupRowStatus        OBJECT-TYPE
    SYNTAX                       RowStatus
    MAX-ACCESS                   read-create
    STATUS                       current
    DESCRIPTION
       "The object is used by a management station to
        create or delete the row entry in cdsmrResultGroupTable
        following the RowStatus textual convention."
    ::= { cdsmrResultGroupTableEntry  10 }

--  *************************************************************
--  *                                                           *
--  * Result IP                                                 *
--  *                                                           *
--  *************************************************************
cdsmrResultIpTable          OBJECT-TYPE
    SYNTAX                  SEQUENCE OF CdsmrResultIpTableEntry
    MAX-ACCESS              not-accessible
    STATUS                  current
    DESCRIPTION
       "A table used to configure parameters to allow destination
        to be establish at request of partner. Entries are added
        to this table via cdsmrResultIpRowStatus in accordance
        with the RowStatus convention."

    ::= { ciscoItpDsmrMIBObjects 4 }

cdsmrResultIpTableEntry           OBJECT-TYPE
    SYNTAX                        CdsmrResultIpTableEntry
    MAX-ACCESS                    not-accessible
    STATUS                        current
    DESCRIPTION
       "This table is used to define a list of IP addresses and
        ports from which destination and establish connection."
    INDEX   { cgspInstNetwork,
              cdsmrResultGroupName,
              cdsmrResultIpNumber
    }
    ::= { cdsmrResultIpTable  1 }

CdsmrResultIpTableEntry ::= SEQUENCE {
    cdsmrResultIpNumber                CmlrId,
    cdsmrResultIpRemotePortNumber      InetPortNumber,
    cdsmrResultIpRemoteIpAddrType      InetAddressType,
    cdsmrResultIpRemoteIpAddress       InetAddress,
    cdsmrResultIpProfileName           CmlrName,
    cdsmrResultIpWeight                Integer32,
    cdsmrResultIpRowStatus             RowStatus
    }

cdsmrResultIpNumber              OBJECT-TYPE
    SYNTAX                       CmlrId
    MAX-ACCESS                   not-accessible
    STATUS                       current
    DESCRIPTION
       "This object specifies the index for a list of results
        specified per result group. "
    ::= { cdsmrResultIpTableEntry  1 }

cdsmrResultIpRemotePortNumber    OBJECT-TYPE
    SYNTAX                       InetPortNumber
    MAX-ACCESS                   read-create
    STATUS                       current
    DESCRIPTION
       "Remote port number used to establish connection.
        The value of zero indicates that any port number
        will be accepted."
    ::= { cdsmrResultIpTableEntry  2 }

cdsmrResultIpRemoteIpAddrType    OBJECT-TYPE
        SYNTAX                   InetAddressType
        MAX-ACCESS               read-create
        STATUS                   current
        DESCRIPTION
            "This object contains the type of the remote
             IP address used to create an session."
    ::= { cdsmrResultIpTableEntry  3 }

cdsmrResultIpRemoteIpAddress     OBJECT-TYPE
        SYNTAX                   InetAddress
        MAX-ACCESS               read-create
        STATUS                   current
        DESCRIPTION
            "This object contains the remote IP address allowed
             to request the session."
    ::= { cdsmrResultIpTableEntry  4 }

cdsmrResultIpProfileName         OBJECT-TYPE
    SYNTAX                       CmlrName
    MAX-ACCESS                   read-create
    STATUS                       current
    DESCRIPTION
       "The name of the profile used to specify parameter for
        session as follows.

        'smpp': cdsmrSmppProfileName
        'ucp':  cdsmrUcpProfileName

        For all other values this object is ignored."
    ::= { cdsmrResultIpTableEntry  5 }

cdsmrResultIpWeight              OBJECT-TYPE
    SYNTAX                       Integer32 (0..10)
    MAX-ACCESS                   read-create
    STATUS                       current
    DESCRIPTION
       "This object specifies the weight applied to the weighted
        round robin distribution algorithm used for multi-layer
        result group.  An integer value in the range of 0 to 10.
        A value of ten indicates the resource should be selected
        ten times more than a resource assigned a weight of one."
    ::= { cdsmrResultIpTableEntry  6 }

cdsmrResultIpRowStatus           OBJECT-TYPE
    SYNTAX                       RowStatus
    MAX-ACCESS                   read-create
    STATUS                       current
    DESCRIPTION
       "The object is used by a management station to
        create or delete the row entry in cdsmrResultIpTable
        following the RowStatus textual convention."
    ::= { cdsmrResultIpTableEntry  7 }

--  *************************************************************
--  *                                                           *
--  * Result Entries                                            *
--  *                                                           *
--  *************************************************************
cdsmrResultTable            OBJECT-TYPE
    SYNTAX                  SEQUENCE OF CdsmrResultTableEntry
    MAX-ACCESS              not-accessible
    STATUS                  current
    DESCRIPTION
       "A table used to configure parameters for destination
        resources. The result group lists the appropriate destination
        resources, and the mechanism used to select a single
        destination for a given packet.  State information is
        determined for each possible destination. Entries are
        added to this table via cdsmrResultRowStatus in accordance
        with the RowStatus convention."

    ::= { ciscoItpDsmrMIBObjects 5 }

cdsmrResultTableEntry             OBJECT-TYPE
    SYNTAX                        CdsmrResultTableEntry
    MAX-ACCESS                    not-accessible
    STATUS                        current
    DESCRIPTION
       "This table is used to define a collection of
        multi-layer routing statements."
    INDEX   { cgspInstNetwork,
              cdsmrResultGroupName,
              cdsmrResultNumber
    }
    ::= { cdsmrResultTable  1 }

CdsmrResultTableEntry ::= SEQUENCE {
    cdsmrResultNumber                  CmlrId,
    cdsmrResultDestinationType         CdsmrResultDestinationType,
    cdsmrResultParameters              CdsmrResultParameters,
    cdsmrResultDestinationName         CmlrName,
    cdsmrResultPc                      CItpTcPointCode,
    cdsmrResultSsn                     CItpTcSubSystemNumber,
    cdsmrResultGt                      CItpTcGtaLongDisplay,
    cdsmrResultTransType               CgsccpGttTransType,
    cdsmrResultGti                     CgsccpGttGlobalTitleInd,
    cdsmrResultNp                      CItpTcNumberingPlan,
    cdsmrResultNai                     CItpTcNAI,
    cdsmrResultWeight                  Integer32,
    cdsmrResultNetwork                 CItpTcNetworkName,
    cdsmrResultCounts                  Counter32,
    cdsmrResultRowStatus               RowStatus
    }

cdsmrResultNumber                OBJECT-TYPE
    SYNTAX                       CmlrId
    MAX-ACCESS                   not-accessible
    STATUS                       current
    DESCRIPTION
       "This object specifies the index for a list of results
        specified per result group. "
    ::= { cdsmrResultTableEntry  1 }

cdsmrResultDestinationType       OBJECT-TYPE
    SYNTAX                       CdsmrResultDestinationType
    MAX-ACCESS                   read-create
    STATUS                       current
    DESCRIPTION
       "Destination type."
    ::= { cdsmrResultTableEntry  2 }

cdsmrResultParameters            OBJECT-TYPE
    SYNTAX                       CdsmrResultParameters
    MAX-ACCESS                   read-create
    STATUS                       current
    DESCRIPTION
       "Many of the result parameter used creating result are
        optional.  This object is used to indicate which
        options are provided as follows.

        'tranType'  : cdsmrResultTransType
        'gti'       : cdsmrResultGti
        'np'        : cdsmrResultNp
        'nai'       : cdsmrResultNai
        'pc'        : cdsmrResultPc
        'ssn'       : cdsmrResultSsn "
    ::= { cdsmrResultTableEntry  3 }

cdsmrResultDestinationName       OBJECT-TYPE
    SYNTAX                       CmlrName
    MAX-ACCESS                   read-create
    STATUS                       current
    DESCRIPTION
       "The name of the destination as follows based on
        cdsmrResultDestinationType:
        'smpp': cdsmrSmppDestName
        'ucp':  cdsmrUcpDestName

        For all other values this object is ignored."
    ::= { cdsmrResultTableEntry  4 }

cdsmrResultPc                    OBJECT-TYPE
    SYNTAX                       CItpTcPointCode
    MAX-ACCESS                   read-create
    STATUS                       current
    DESCRIPTION
       "A destination point code that must exist in the MTP3
        routing table, and its state is extracted from MTP3
        for availability purposes.  This object only has
        applies when the cdsmrResultDestinationType object
        has the 'pc' or 'pcSsn' values.
        Otherwise, this object will return zero value."
    ::= { cdsmrResultTableEntry  5 }

cdsmrResultSsn                   OBJECT-TYPE
    SYNTAX                       CItpTcSubSystemNumber
    MAX-ACCESS                   read-create
    STATUS                       current
    DESCRIPTION
       "The subsystem number to be inserted into MSU. This
        object only has applies when the cdsmrResultDestinationType
        object  has the 'pcSsn' value.
        Otherwise, this object will return zero value."
    ::= { cdsmrResultTableEntry  6 }

cdsmrResultGt                    OBJECT-TYPE
    SYNTAX                       CItpTcGtaLongDisplay
    MAX-ACCESS                   read-create
    STATUS                       current
    DESCRIPTION
       "The global title address.

        When the length of the global title address is zero it
        specified a wildcard match and all global title will
        match GTA clause of rule.

        This object only applies when the CdsmrResultDestinationType
        is set to 'gt' value."
    ::= { cdsmrResultTableEntry  7 }

cdsmrResultTransType             OBJECT-TYPE
    SYNTAX                       CgsccpGttTransType
    MAX-ACCESS                   read-create
    STATUS                       current
    DESCRIPTION
       "The translation type specified within the address in the
        message signal unit.  This object only applies when the
        CdsmrResultDestinationType is set to 'gt' value and
        the 'tranType' bit is set in the cdsmrResultResultParameters
        object."
    ::= { cdsmrResultTableEntry  8 }

cdsmrResultGti                   OBJECT-TYPE
    SYNTAX                       CgsccpGttGlobalTitleInd
    MAX-ACCESS                   read-create
    STATUS                       current
    DESCRIPTION
       "The global title indicator value for the global tile address
        specified within the message signal unit.  This object only
        applies when the CdsmrResultDestinationType is set to
        'gt' value."
    ::= { cdsmrResultTableEntry  9 }

cdsmrResultNp                    OBJECT-TYPE
    SYNTAX                       CItpTcNumberingPlan
    MAX-ACCESS                   read-create
    STATUS                       current
    DESCRIPTION
       "The numbering plan for the global tile address specified
        within the message signal unit.  This object only applies
        when the CdsmrResultDestinationType is set to 'gt' value."
    ::= { cdsmrResultTableEntry  10 }

cdsmrResultNai                   OBJECT-TYPE
    SYNTAX                       CItpTcNAI
    MAX-ACCESS                   read-create
    STATUS                       current
    DESCRIPTION
       "The nature of specified address for the global tile
        address specified within the message signal unit.  This
        object only applies when the cdsmrResultDestinationType is
        set to 'gt' value."
    ::= { cdsmrResultTableEntry 11 }

cdsmrResultWeight                OBJECT-TYPE
    SYNTAX                       Integer32 (0..10)
    MAX-ACCESS                   read-create
    STATUS                       current
    DESCRIPTION
       "This object specifies the weight applied to the weighted
        round robin distribution algorithm used for multi-layer
        result group.  An integer value in the range of 0 to 10.
        A value of ten indicates the resource should be selected
        ten times more than a resource assigned a weight of one."
    ::= { cdsmrResultTableEntry  12}

cdsmrResultNetwork               OBJECT-TYPE
    SYNTAX                       CItpTcNetworkName
    MAX-ACCESS                   read-create
    STATUS                       current
    DESCRIPTION
       "The network name is used to indicate the network in which
        the result operation will be performed."
    ::= { cdsmrResultTableEntry  13}

cdsmrResultCounts                OBJECT-TYPE
    SYNTAX                       Counter32
    UNITS                        "matches"
    MAX-ACCESS                   read-only
    STATUS                       current
    DESCRIPTION
       "Number of times this entry was invoked."
    ::= { cdsmrResultTableEntry  14}

cdsmrResultRowStatus             OBJECT-TYPE
    SYNTAX                       RowStatus
    MAX-ACCESS                   read-create
    STATUS                       current
    DESCRIPTION
       "The object is used by a management station to
        create or delete the row entry in cdsmrResultTable
        following the RowStatus textual convention."
    ::= { cdsmrResultTableEntry  15}

--  *************************************************************
--  *                                                           *
--  * Distributed Short Message Routing Address table           *
--  *                                                           *
--  *************************************************************
cdsmrAddressTable           OBJECT-TYPE
    SYNTAX                  SEQUENCE OF CdsmrAddressTableEntry
    MAX-ACCESS              not-accessible
    STATUS                  current
    DESCRIPTION
       "A table used to create a collection of addresses that
        can be searched for exact or best matches. Entries are
        added to this table via cdsmrAddressRowStatus in accordance
        with the RowStatus convention."
    ::= { ciscoItpDsmrMIBObjects 6 }

cdsmrAddressTableEntry            OBJECT-TYPE
    SYNTAX                        CdsmrAddressTableEntry
    MAX-ACCESS                    not-accessible
    STATUS                        current
    DESCRIPTION
       "Each entry in the cdsmrAddressTable is used to search
        for matches within a messages signalling unit.
        Message signalling that match a particular rule can
        be directed to cdsmrAddressTable to allow MSU to be
        directed or modified based on address information.
        The table is searched using information specified in
        the rule in cdsmrRuleTable Table."

    INDEX   { cgspInstNetwork,
              cdsmrAddressTableName,
              cdsmrAddressType,
              cdsmrAddressDigits,
              cdsmrAddressExactMatch
    }
    ::= { cdsmrAddressTable  1 }

CdsmrAddressTableEntry ::= SEQUENCE {
    cdsmrAddressTableName                CmlrName,
    cdsmrAddressType                     CmlrAddressType,
    cdsmrAddressDigits                   CmlrAddressDigits,
    cdsmrAddressExactMatch               TruthValue,
    cdsmrAddressResultParameters         CdsmrResultParameters,
    cdsmrAddressResultNetwork            CItpTcNetworkName,
    cdsmrAddressResultType               CdsmrResultType,
    cdsmrAddressResultOctet              CdsmrResultOctet,
    cdsmrAddressResultTransType          CgsccpGttTransType,
    cdsmrAddressResultGti                CgsccpGttGlobalTitleInd,
    cdsmrAddressResultNp                 CItpTcNumberingPlan,
    cdsmrAddressResultNai                CItpTcNAI,
    cdsmrAddressResultPc                 CItpTcPointCode,
    cdsmrAddressResultSsn                CItpTcSubSystemNumber,
    cdsmrAddressResultRuleNumber         CmlrId,
    cdsmrAddressMatchCounts              Counter32,
    cdsmrAddressRowStatus                RowStatus
}

cdsmrAddressTableName            OBJECT-TYPE
    SYNTAX                       CmlrName
    MAX-ACCESS                   not-accessible
    STATUS                       current
    DESCRIPTION
       "A name used to define a collection of addresses used to
        route and modify messages signalling units."
    ::= { cdsmrAddressTableEntry  1 }

cdsmrAddressType                 OBJECT-TYPE
    SYNTAX                       CmlrAddressType
    MAX-ACCESS                   not-accessible
    STATUS                       current
    DESCRIPTION
       "The type of addresses in the address tables.
        The different types will be used to determine
        how to format and convert cdsmrAddressDigits."
    ::= { cdsmrAddressTableEntry  2 }

cdsmrAddressDigits               OBJECT-TYPE
    SYNTAX                       CmlrAddressDigits
    MAX-ACCESS                   not-accessible
    STATUS                       current
    DESCRIPTION
       "The digits of the address in following  formats as
        indicated by cdsmrAddressType object.
         'hexadecimal' - The digits are hexadecimal digits specified
                         in ASCII as follows.
                         '0123456789ABCDEF'"
    ::= { cdsmrAddressTableEntry  3 }

cdsmrAddressExactMatch           OBJECT-TYPE
    SYNTAX                       TruthValue
    MAX-ACCESS                   not-accessible
    STATUS                       current
    DESCRIPTION
       "This object indicates that the address specified by
        cdsmrAddressDigits object must exactly match value
        in message signalling unit.

        'true'  - Exact match is specified.
        'false' - Best match is specified."
    ::= { cdsmrAddressTableEntry  4 }

cdsmrAddressResultParameters     OBJECT-TYPE
    SYNTAX                       CdsmrResultParameters
    MAX-ACCESS                   read-create
    STATUS                       current
    DESCRIPTION
       "Many of the result parameter used in the processing of
        address table have default values.  These values are
        determined by a combination of variant and operation
        type. This object will be provide information which
        parameter used in setting results have been specified
        as follows.

        'network'   : cdsmrAddressSetResultNetwork
        'octet'     : cdsmrAddressSetResultOctet
        'tranType'  : cdsmrAddressResultTransType
        'gti'       : cdsmrAddressResultGti
        'np'        : cdsmrAddressResultNp
        'nai'       : cdsmrAddressResultNai
        'pc'        : cdsmrAddressResultPc
        'ssn'       : cdsmrAddressResultSsn"
    ::= { cdsmrAddressTableEntry  5 }

cdsmrAddressResultNetwork        OBJECT-TYPE
    SYNTAX                       CItpTcNetworkName
    MAX-ACCESS                   read-create
    STATUS                       current
    DESCRIPTION
       "The network name is used to indicate the network in which
        the result operation will be performed."
    ::= { cdsmrAddressTableEntry  6 }

cdsmrAddressResultType           OBJECT-TYPE
    SYNTAX                       CdsmrResultType
    MAX-ACCESS                   read-create
    STATUS                       current
    DESCRIPTION
       "Specified the type of information to be placed into the
        message signal unit or how the it will be processed."
    ::= { cdsmrAddressTableEntry  7 }

cdsmrAddressResultOctet          OBJECT-TYPE
    SYNTAX                       CdsmrResultOctet
    MAX-ACCESS                   read-create
    STATUS                       current
    DESCRIPTION
       "Information to be placed in the message signal
        unit based on the value specified by the
        cdsmrAddressResultType object.  When the
        cdsmrAddressResultType object is set to
        'group' or 'gt' this object will contain
        the string specifying output. For all other
        values the this object will not be used in the
        result processing and will have a length of
        zero.
        "
    ::= { cdsmrAddressTableEntry  8 }

cdsmrAddressResultTransType      OBJECT-TYPE
    SYNTAX                       CgsccpGttTransType
    MAX-ACCESS                   read-create
    STATUS                       current
    DESCRIPTION
       "The translation type specified within the address in the
        message signal unit.  This object only applies when the
        cdsmrAddressResultType is set to 'gt' value and
        the 'tranType' bit is set in the cdsmrAddressResultParameters
        object."
    ::= { cdsmrAddressTableEntry  9 }

cdsmrAddressResultGti            OBJECT-TYPE
    SYNTAX                       CgsccpGttGlobalTitleInd
    MAX-ACCESS                   read-create
    STATUS                       current
    DESCRIPTION
       "The global title indicator value for the global tile address
        specified within the message signal unit.  This object only
        applies when the cdsmrAddressResultType is set to
        'gt' value."
    DEFVAL      { 0 }
    ::= { cdsmrAddressTableEntry 10 }

cdsmrAddressResultNp             OBJECT-TYPE
    SYNTAX                       CItpTcNumberingPlan
    MAX-ACCESS                   read-create
    STATUS                       current
    DESCRIPTION
       "The numbering plan for the global tile address specified
        within the message signal unit.  This object only applies
        when the cdsmrAddressResultType is set to 'gt' value."
    ::= { cdsmrAddressTableEntry 11 }

cdsmrAddressResultNai            OBJECT-TYPE
    SYNTAX                       CItpTcNAI
    MAX-ACCESS                   read-create
    STATUS                       current
    DESCRIPTION
       "The nature of specified address for the global tile
        address specified within the message signal unit.  This
        object only applies when the cdsmrAddressResultType is
        set to 'gt' value."
    ::= { cdsmrAddressTableEntry 12 }

cdsmrAddressResultPc             OBJECT-TYPE
    SYNTAX                       CItpTcPointCode
    MAX-ACCESS                   read-create
    STATUS                       current
    DESCRIPTION
       "The point-code to be place in the message signal unit.  This
        object only applies when the cdsmrAddressResultType is set
        to 'pc' value."
    ::= { cdsmrAddressTableEntry 13 }

cdsmrAddressResultSsn            OBJECT-TYPE
    SYNTAX                       CItpTcSubSystemNumber
    MAX-ACCESS                   read-create
    STATUS                       current
    DESCRIPTION
       "The subsystem number to be place in the message signal unit.
        This object only applies when the cdsmrAddressResultType is set
        to 'pcSsn' value."
    ::= { cdsmrAddressTableEntry 14 }

cdsmrAddressResultRuleNumber     OBJECT-TYPE
    SYNTAX                       CmlrId
    MAX-ACCESS                   read-create
    STATUS                       current
    DESCRIPTION
       "Processing continues with rule number specified by this object.
        This object only applies when the cdsmrAddressResultType is set
        to 'ruleNumber' value."
    ::= { cdsmrAddressTableEntry 15 }

cdsmrAddressMatchCounts          OBJECT-TYPE
    SYNTAX                       Counter32
    UNITS                        "matches"
    MAX-ACCESS                   read-only
    STATUS                       current
    DESCRIPTION
       "Count of the number of times address was matched. This counter
        is only incremented when rule matches."
    ::= { cdsmrAddressTableEntry 16   }

cdsmrAddressRowStatus            OBJECT-TYPE
    SYNTAX                       RowStatus
    MAX-ACCESS                   read-create
    STATUS                       current
    DESCRIPTION
       "The object is used by a management station to
        create or delete the row entry in cdsmrAddressTable
        following the RowStatus textual convention."
    ::= { cdsmrAddressTableEntry 17  }

--  *************************************************************
--  *                                                           *
--  * DSMR - Multi-Layer Rule Set Table                         *
--  *                                                           *
--  *************************************************************
cdsmrRuleSetTable           OBJECT-TYPE
    SYNTAX                  SEQUENCE OF CdsmrRuleSetTableEntry
    MAX-ACCESS              not-accessible
    STATUS                  current
    DESCRIPTION
      "A table that is used to specify attributes of an
       application-layer message to be matched and the resulting
       behavior for handling the message. Entries are added to
       this table via cdsmrRuleSetRowStatus in accordance with
       the RowStatus convention."
    ::= { ciscoItpDsmrMIBObjects 7 }

cdsmrRuleSetTableEntry            OBJECT-TYPE
    SYNTAX                        CdsmrRuleSetTableEntry
    MAX-ACCESS                    not-accessible
    STATUS                        current
    DESCRIPTION
       "Each entry in this table represents a set of addresses
        used to perform non-standard routing of messages
        signalling units.."

    INDEX   { cgspInstNetwork,
              cdsmrRuleSetName
    }
    ::= { cdsmrRuleSetTable  1 }

CdsmrRuleSetTableEntry ::= SEQUENCE {
    cdsmrRuleSetName                     CmlrRuleSetName,
    cdsmrRuleSetProtocol                 CmlrRuleProtocol,
    cdsmrRuleSetStartDateAndTime         DateAndTime,
    cdsmrRuleSetEndDateAndTime           DateAndTime,
    cdsmrRuleSetRowStatus                RowStatus
}

cdsmrRuleSetName                 OBJECT-TYPE
    SYNTAX                       CmlrRuleSetName
    MAX-ACCESS                   not-accessible
    STATUS                       current
    DESCRIPTION
       "A name used to define a set rules used to transform
        traffic."
    ::= { cdsmrRuleSetTableEntry  1 }

cdsmrRuleSetProtocol             OBJECT-TYPE
    SYNTAX                       CmlrRuleProtocol
    MAX-ACCESS                   read-create
    STATUS                       current
    DESCRIPTION
       "The object is used to establish a default protocol
        type for all rules within the rule set.  If this
        object is set to 'none'  will default to protocol
        specified by variant."
    ::= { cdsmrRuleSetTableEntry  2 }

cdsmrRuleSetStartDateAndTime      OBJECT-TYPE
    SYNTAX                        DateAndTime
    MAX-ACCESS                    read-create
    STATUS                        current
    DESCRIPTION
       "The local date and time when this trigger and sub-triggers
        will become active.  When the value is null then the
        cdsmrInstStartDateAndTime does not apply. "
    ::= { cdsmrRuleSetTableEntry  3 }

cdsmrRuleSetEndDateAndTime        OBJECT-TYPE
    SYNTAX                        DateAndTime
    MAX-ACCESS                    read-create
    STATUS                        current
    DESCRIPTION
       "The local date and time this trigger and sub-triggers
        will become inactive.  When the value is null then the
        cdsmrInstEndDateAndTime does not apply. "
    ::= { cdsmrRuleSetTableEntry  4 }

cdsmrRuleSetRowStatus            OBJECT-TYPE
    SYNTAX                       RowStatus
    MAX-ACCESS                   read-create
    STATUS                       current
    DESCRIPTION
       "The object is used by a management station to
        create or delete the row entry in cdsmrRuleSetTable
        following the RowStatus textual convention."
    ::= { cdsmrRuleSetTableEntry  5 }

--  *************************************************************
--  *                                                           *
--  * Rule Table                                                *
--  *                                                           *
--  *************************************************************
cdsmrRuleTable              OBJECT-TYPE
    SYNTAX                  SEQUENCE OF CdsmrRuleTableEntry
    MAX-ACCESS              not-accessible
    STATUS                  current
    DESCRIPTION
       "A table that is used to specify attributes of an
        application-layer message to be matched and the resulting
        behavior for handling the message. Entries are added to
        this table via cdsmrRuleResultRowStatus in accordance
        with the RowStatus convention."
    ::= { ciscoItpDsmrMIBObjects 8 }

cdsmrRuleTableEntry               OBJECT-TYPE
    SYNTAX                        CdsmrRuleTableEntry
    MAX-ACCESS                    not-accessible
    STATUS                        current
    DESCRIPTION
    "Entries in this table are searched in the specified order
     defined by cdsmrRuleNumber object.
    "
    INDEX   { cgspInstNetwork,
              cdsmrRuleSetName,
              cdsmrRuleNumber
    }
    ::= { cdsmrRuleTable  1 }

CdsmrRuleTableEntry ::= SEQUENCE {
    cdsmrRuleNumber                   CmlrId,
    cdsmrRuleOperationType            INTEGER,
    cdsmrRuleCdrServiceQueue          INTEGER,
    cdsmrRuleInputParameters          BITS,
    cdsmrRuleDestPort                 Unsigned32,
    cdsmrRuleDestSmeGta               CItpTcGtaLongDisplay,
    cdsmrRuleDestSmeNai               CItpTcNAI,
    cdsmrRuleDestSmeNp                CItpTcNumberingPlan,
    cdsmrRuleDestSmeMinDigits         CdsmrMinimumDigits,
    cdsmrRuleDestSmeMaxDigits         CdsmrMaximumDigits,
    cdsmrRuleDestSmeTable             CmlrName,
    cdsmrRuleDestSmeTableNai          CItpTcNAI,
    cdsmrRuleDestSmeTableNp           CItpTcNumberingPlan,
    cdsmrRuleDestSmscGta              CItpTcGtaLongDisplay,
    cdsmrRuleDestSmscNai              CItpTcNAI,
    cdsmrRuleDestSmscNp               CItpTcNumberingPlan,
    cdsmrRuleDestSmscMinDigits        CdsmrMinimumDigits,
    cdsmrRuleDestSmscMaxDigits        CdsmrMaximumDigits,
    cdsmrRuleOrigImsiGta              CItpTcGtaLongDisplay,
    cdsmrRuleOrigImsiNai              CItpTcNAI,
    cdsmrRuleOrigImsiNp               CItpTcNumberingPlan,
    cdsmrRuleOrigImsiMinDigits        CdsmrMinimumDigits,
    cdsmrRuleOrigImsiMaxDigits        CdsmrMaximumDigits,
    cdsmrRuleOrigImsiTable            CmlrName,
    cdsmrRuleOrigSmeGta               CItpTcGtaLongDisplay,
    cdsmrRuleOrigSmeNai               CItpTcNAI,
    cdsmrRuleOrigSmeNp                CItpTcNumberingPlan,
    cdsmrRuleOrigSmeMinDigits         CdsmrMinimumDigits,
    cdsmrRuleOrigSmeMaxDigits         CdsmrMaximumDigits,
    cdsmrRuleOrigSmeTable             CmlrName,
    cdsmrRuleOrigSmeTableNai          CItpTcNAI,
    cdsmrRuleOrigSmeTableNp           CItpTcNumberingPlan,
    cdsmrRuleOrigSmscGta              CItpTcGtaLongDisplay,
    cdsmrRuleOrigSmscNai              CItpTcNAI,
    cdsmrRuleOrigSmscNp               CItpTcNumberingPlan,
    cdsmrRuleOrigSmscMinDigits        CdsmrMinimumDigits,
    cdsmrRuleOrigSmscMaxDigits        CdsmrMaximumDigits,
    cdsmrRuleOrigSmscTable            CmlrName,
    cdsmrRuleOrigSmscTableNai         CItpTcNAI,
    cdsmrRuleOrigSmscTableNp          CItpTcNumberingPlan,
    cdsmrRuleProtocolId               Unsigned32,
    cdsmrRuleTeleserviceId            Unsigned32,
    cdsmrRuleResultParameters         CdsmrResultParameters,
    cdsmrRuleResultNetwork            CItpTcNetworkName,
    cdsmrRuleResultType               CdsmrResultType,
    cdsmrRuleResultOctet              CdsmrResultOctet,
    cdsmrRuleResultTransType          CgsccpGttTransType,
    cdsmrRuleResultGti                CgsccpGttGlobalTitleInd,
    cdsmrRuleResultNp                 CItpTcNumberingPlan,
    cdsmrRuleResultNai                CItpTcNAI,
    cdsmrRuleResultPc                 CItpTcPointCode,
    cdsmrRuleResultSsn                CItpTcSubSystemNumber,
    cdsmrRuleResultRuleNumber         CmlrId,
    cdsmrRuleResultRowStatus          RowStatus
}

cdsmrRuleNumber                  OBJECT-TYPE
    SYNTAX                       CmlrId
    MAX-ACCESS                   not-accessible
    STATUS                       current
    DESCRIPTION
       "This object specifies the index for a list of secondary
        triggers specified per routing table.  The trigger will be
        processed in ascending order."
    ::= { cdsmrRuleTableEntry  1 }

cdsmrRuleOperationType           OBJECT-TYPE
    SYNTAX                       INTEGER {  all(1),
                                            smdPp(2),
                                            smsMo(3),
                                            smsMt(4),
                                            smsSri(5),
                                            smsReg(6),
                                            smsNot(7),
                                            ucpSubmit(8)
                                 }
    MAX-ACCESS                   read-create
    STATUS                       current
    DESCRIPTION
       "The list of possible operation types.
         'all'       - All operations types.
         'smdPp'     - ANSI-41 Short message service delivery point
                       to point.
         'smsMo'     - GSM-MAP Short message service mobile
                       originated request.
         'smsMt'     - GSM-MAP Short message service mobile
                       terminated request.
         'smsSri'    - GSM-MAP send routing info for short message.
         'smsReg'    - ANSI-41 Short message service request.
         'smsNot'    - ANSI-41 Short message service notification
                       request
         'ucpSubmit' - Match UCP Submit Short Message requests"
    ::= { cdsmrRuleTableEntry  2 }

cdsmrRuleCdrServiceQueue         OBJECT-TYPE
    SYNTAX                       INTEGER {
                                    none(0),
                                    available(1),
                                    congested(2),
                                    unavailable(3)
    }
    MAX-ACCESS                   read-create
    STATUS                       current
    DESCRIPTION
       "Protocol used to examine message.
        'none'       : CDR Service queue not specified.
        'available'  : Matches when CDR service queue is available.
        'congested'  : Matches when CDR service queue is congested.
        'unavailable': Matches when CDR service queue is unavailable.
       "
    ::= { cdsmrRuleTableEntry  3 }


cdsmrRuleInputParameters         OBJECT-TYPE
    SYNTAX                       BITS {
                                       cdrService(0),
                                       destPort(1),
                                       destSmeGta(2),
                                       destSmeExact(3),
                                       destSmeNai(4),
                                       destSmeNp(5),
                                       destSmeImsi(6),
                                       destSmeMin(7),
                                       destSmeMinDigits(8),
                                       destSmeMaxDigits(9),
                                       destSmeTable(10),
                                       destSmeTableLoc(11),
                                       destSmeTableImsi(12),
                                       destSmeTableMin(13),
                                       destSmeTableNai(14),
                                       destSmeTableNp(15),
                                       destSmscGta(16),
                                       destSmscExact(17),
                                       destSmscNai(18),
                                       destSmscNp(19),
                                       destSmscMinDigits(20),
                                       destSmscMaxDigits(21),
                                       origImsiGta(22),
                                       origImsiExact(23),
                                       origImsiUnknown(24),
                                       origImsiNai(25),
                                       origImsiNp(26),
                                       origImsiMinDigits(27),
                                       origImsiMaxDigits(28),
                                       origImsiTable(29),
                                       origImsiTableLoc(30),
                                       origSmeGta(31),
                                       origSmeExact(32),
                                       origSmeNai(33),
                                       origSmeNp(34),
                                       origSmeMinDigits(35),
                                       origSmeMaxDigits(36),
                                       origSmeTable(37),
                                       origSmeTableLoc(38),
                                       origSmeTableNai(39),
                                       origSmeTableNp(40),
                                       origSmscGta(41),
                                       origSmscExact(42),
                                       origSmscNai(43),
                                       origSmscNp(44),
                                       origSmscMinDigits(45),
                                       origSmscMaxDigits(46),
                                       origSmscTable(47),
                                       origSmscTableLoc(48),
                                       origSmscTableNai(49),
                                       origSmscTableNp(50),
                                       pid(51),
                                       tid(52),
                                       default(53)
                                  }
    MAX-ACCESS                    read-create
    STATUS                        current
    DESCRIPTION
       "Many of the parameter used in the processing of rules
        have default values.  These values are determined
        by a combination of variant and operation type. This
        object will be provide information which parameter has
        been specified as follows.

        'cdrService'  : Indicates that CDR service queue parameter is
                        specified in cdsmrRuleCdrServiceQueue

        'destPort'    : Indicates that the destination Port number
                        is specified in the cdsmrRuleDestPort
                        object.

        'destSmeGta'  : Indicates that a global title address is
                        specified in the cdsmrRuleDestSmeGta object.

        'destSmeExact': Indicates that the cdsmrRuleDestSmeGta
                        address must be an exact match.

        'destSmeNai'  : Indicates that the nature of specified
                        address is specified in the
                        cdsmrRuleDestSmeNai object.

        'destSmeNp'   : Indicates that the numbering plan is
                        specified in the cdsmrRuleDestSmeNp object.

        'destSmeImsi' : Indicates that the address specified in the
                        International Mobile Subscriber
                        Identification address. This indicator
                        applies to the cdsmrRuleDestSmeGta object.

        'destSmeMin'  : Indicates that the address specified in the
                        Mobile Identification Number. This indicator
                        applies to the cdsmrRuleDestSmeGta object.

        'destSmeMinDigits'
                      : Minimum number global title address digits
                        specified in the cdsmrRuleDestSmeGta object
                        using the cdsmrRuleDestSmeMinDigits object.

        'destSmeMaxDigits'
                      : Maximum number global title address digits
                        specified in the cdsmrRuleDestSmeGta object
                        using the cdsmrRuleDestSmeMaxDigits object.

        'destSmeTable'
                      : A table of destination short message entity
                        addresses.  The name of the table is
                        specified in the cdsmrRuleDestSmeTable
                        object.

        'destSmeTableLoc'
                      : Specifies the location of the address table
                        as follows.
                        'true' - The name specified in the
                                 cdsmrRuleDestSmeTable object
                                 exists in the cdsmrAddressTable
                                 table.

                        'false' - The name specified in the
                                 cdsmrRuleDestSmeTable object
                                 exists in the cmlrAddressTableEntry
                                 table from the CISCO-ITP-MLR-MIB.

        'destSmeTableImsi'
                      : Indicates that the addresses specified in the
                        cdsmrRuleDestSmeTable are International Mobile
                        Subscriber Identification addresses.

        'destSmeTableNai'
                      : Indicates that the all nature of specified
                        address is specified in the
                        cdsmrRuleDestSmeTableNai object.

        'destSmeTableNp'
                      : Indicates that the numbering plan is
                        specified in the cdsmrRuleDestSmeTableNp
                        object.

        'destSmscGta' : Indicates that a global title address is
                        specified in the cdsmrRuleDestSmscGta object.

        'destSmscExact'
                      : Indicates that the cdsmrRuleDestSmscGta
                        address must be an exact match.


        'destSmscNai' : Indicates that the nature of specified
                        address is specified in the
                        cdsmrRuleDestSmscNai object.

        'destSmscNp'  : Indicates that the numbering plan is
                        specified in the cdsmrRuleDestSmscNp object.

        'destSmscMinDigits'
                      : Minimum number global title address digits
                        specified in the cdsmrRuleDestSmscGta object
                        using the cdsmrRuleDestSmscMinDigits object.

        'destSmscMaxDigits'
                      : Maximum number global title address digits
                        specified in the cdsmrRuleDestSmscGta object
                        using the cdsmrRuleDestSmscMaxDigits object.

        'origImsiGta' : Indicates that a global title address is
                        specified in the cdsmrRuleDestSmeGta object.

        'origImsiExact'
                      : Indicates that the cdsmrRuleDestSmeGta
                        address must be an exact match.

        'origImsiUnknown'
                      : Indicates that the rule can match when
                        packets do not contain the orgination IMSI
                        address. That is,  when the address is
                        unknown or unspecified.  The IMSI address
                        is only specified in map version 3.
                        Therefore, the packets using version 1 or
                        2 when match when this parameter is
                        specified.

        'origImsiNai' : Indicates that the nature of specified
                        address is specified in the
                        cdsmrRuleDestSmeNai object.

        'origImsiNp'  : Indicates that the numbering plan is
                        specified in the cdsmrRuleDestSmeNp object.

        'origImsiMinDigits'
                      : Minimum number global title address digits
                        specified in the cdsmrRuleOrigImsiGta
                        object using the cdsmrRuleOrigImsiMinDigits
                        object.

        'origImsiMaxDigits'
                      : Maximum number global title address digits
                        specified in the cdsmrRuleOrigImsiGta object
                        using the cdsmrRuleOrigImsiMaxDigits object.

        'origImsiTable'
                      : A table of orgination IMSI addresses. The
                        name of the table is specified in the
                        cdsmrRuleOrigImsiTable object.

        'origImsiTableLoc'
                      : Specifies the location of the address table
                        as follows.
                        'true' - The name specified in the
                                 cdsmrRuleOrigImsiTable object
                                 exists in the cdsmrAddressTable
                                 table.

                        'false' - The name specified in the
                                 cdsmrRuleOrigImsiTable object
                                 exists in the cmlrAddressTableEntry
                                 table from the CISCO-ITP-MLR-MIB.

        'origSmeGta'  : Indicates that a global title address is
                        specified in the cdsmrRuleOrigSmeGta object.

        'origSmeExact': Indicates that the cdsmrRuleOrigSmeGta
                        address must be an exact match.

        'origSmeNai'  : Indicates that the nature of specified
                       address is specified in the
                       cdsmrRuleOrigSmeNai object.

        'origSmeNp'   : Indicates that the numbering plan is
                       specified in the cdsmrRuleOrigSmeNp object.

        'origSmeMinDigits'
                      : Minimum number global title address digits
                        specified in the cdsmrRuleOrigSmeGta object
                        using the cdsmrRuleOrigSmeMinDigits object.

        'origSmeMaxDigits'
                      : Maximum number global title address digits
                        specified in the cdsmrRuleOrigSmeGta object
                        using the cdsmrRuleOrigSmeMaxDigits object.

        'origSmeTable': A table of origination short message entity
                        addresses.  The name of the table is
                        specified in the cdsmrRuleOrigSmeTable
                        object.

        'origSmeTableLoc':
                      : Specifies the location of the address table
                        as follows.
                        'true' - The name specified in the
                                 cdsmrRuleOrigSmeTable object
                                 exists in the cdsmrAddressTable
                                 table.

                        'false' - The name specified in the
                                 cdsmrRuleOrigSmeTable object
                                 exists in the cmlrAddressTableEntry
                                 table from the CISCO-ITP-MLR-MIB.

        'origSmeTableNai'
                      : Indicates that the all nature of specified
                        address is specified in the
                        cdsmrRuleOrigSmeTableNai object.

        'origSmeTableNp'
                      : Indicates that the numbering plan is
                        specified in the cdsmrRuleOrigSmeTableNp
                        object.

        'origSmscGta' : Indicates that a global title address is
                       specified in the cdsmrRuleOrigSmscGta object.

        'origSmscExact':Indicates that the cdsmrRuleOrigSmeGta
                       address must be an exact match.

        'origSmscNai' : Indicates that the nature of specified
                       address is specified in the
                       cdsmrRuleOrigSmscNai object.

        'origSmscNp'  : Indicates that the numbering plan is
                       specified in the cdsmrRuleOrigSmscNp object.

        'origSmscMinDigits'
                      : Minimum number global title address digits
                        specified in the cdsmrRuleOrigSmscGta object
                        using the cdsmrRuleOrigSmscMinDigits object.

        'origSmscMaxDigits'
                      : Maximum number global title address digits
                        specified in the cdsmrRuleOrigSmscGta object
                        using the cdsmrRuleOrigSmscMaxDigits object.

        'origSmscTable'
                      : A table of Short Message Service Center
                        addresses.  The name of the table is
                        specified in the cdsmrRuleOrigSmscTable
                        object.

        'origSmscTableLoc'
                      : Specifies the location of the address table
                        as follows.
                        'true' - The name specified in the
                                 cdsmrRuleOrigSmscTable object
                                 exists in the cdsmrAddressTable
                                 table.

                        'false' - The name specified in the
                                 cdsmrRuleOrigSmscTable object
                                 exists in the cmlrAddressTableEntry
                                 table from the CISCO-ITP-MLR-MIB.

        'origSmscTableNai'
                      : Indicates that the all nature of specified
                        address is specified in the
                        cdsmrRuleOrigSmscTableNai object.

        'origSmscTableNp'
                      : Indicates that the numbering plan is
                        specified in the cdsmrRuleOrigSmscTableNp
                        object.


        'pid'         : Indicates that the Protocol Identifier has
                       been specified in the cdsmrRuleProtocolId
                       object.

        'tid'         : Indicates that the Teleservice Identifier
                       has been specified in the
                       cdsmrRuleTeleserviceId object.
        "
   ::= { cdsmrRuleTableEntry  4 }

cdsmrRuleDestPort                OBJECT-TYPE
    SYNTAX                       Unsigned32 (0..65535)
    MAX-ACCESS                   read-create
    STATUS                       current
    DESCRIPTION
       "A destination application port number.   The value of the
        port number maps to the values specified in the User
        Data Header (UDH) of the SMS message.

        This object only applies when the 'destPort' bit is
        set in the cdsmrRuleInputParameters object."
    ::= { cdsmrRuleTableEntry  5 }

cdsmrRuleDestSmeGta              OBJECT-TYPE
    SYNTAX                       CItpTcGtaLongDisplay
    MAX-ACCESS                   read-create
    STATUS                       current
    DESCRIPTION
       "The destination short message entity global title address.

        When the length of the global title address is zero it
        specified a wildcard match and all global title will
        match GTA clause of rule.

        This object only applies when the 'destSmeGta' bit is
        set in the cdsmrRuleInputParameters object."
    ::= { cdsmrRuleTableEntry  6 }

cdsmrRuleDestSmeNai              OBJECT-TYPE
    SYNTAX                       CItpTcNAI
    MAX-ACCESS                   read-create
    STATUS                       current
    DESCRIPTION
       "The nature of specified address for the destination short
        message entity global title address specified within the
        message signal unit.

        This object only applies when the 'destSmeNai' bit is
        set in the cdsmrRuleInputParameters object."
    ::= { cdsmrRuleTableEntry  7 }

cdsmrRuleDestSmeNp               OBJECT-TYPE
    SYNTAX                       CItpTcNumberingPlan
    MAX-ACCESS                   read-create
    STATUS                       current
    DESCRIPTION
       "The numbering plan for the destination short message
        entity global title address specified within the message
        signal unit.

        This object only applies when the 'destSmeNp' bit is
        set in the cdsmrRuleInputParameters object."
    ::= { cdsmrRuleTableEntry  8 }

cdsmrRuleDestSmeMinDigits        OBJECT-TYPE
    SYNTAX                       CdsmrMinimumDigits
    MAX-ACCESS                   read-create
    STATUS                       current
    DESCRIPTION
       "Specifies the minimum number of digits that the global
        title address specified by the cdsmrRuleDestSmeGta object
        can contain for rule to match.

        This object only applies when the 'destSmeMinDigits' bit is
        set in the cdsmrRuleInputParameters object."
    ::= { cdsmrRuleTableEntry   9 }

cdsmrRuleDestSmeMaxDigits        OBJECT-TYPE
    SYNTAX                       CdsmrMaximumDigits
    MAX-ACCESS                   read-create
    STATUS                       current
    DESCRIPTION
       "Specifies the maximum number of digits that the global
        title address specified by the cdsmrRuleDestSmeGta object
        can contain for rule to match.

        This object only applies when the 'destSmeMaxDigits' bit is
        set in the cdsmrRuleInputParameters object."
    ::= { cdsmrRuleTableEntry  10 }

cdsmrRuleDestSmeTable            OBJECT-TYPE
    SYNTAX                       CmlrName
    MAX-ACCESS                   read-create
    STATUS                       current
    DESCRIPTION
       "The name of the entry in the cdsmrAddressTable that will be
        searched for matches. The table will be search for the
        following types of addresses based on values set in the
        cdsmrRuleInputParameters object.

        This object only applies when the 'destSmeTable' bit is
        set in the cdsmrRuleInputParameters object."
    ::= { cdsmrRuleTableEntry  11 }

cdsmrRuleDestSmeTableNai         OBJECT-TYPE
    SYNTAX                       CItpTcNAI
    MAX-ACCESS                   read-create
    STATUS                       current
    DESCRIPTION
       "The nature of specified address for the global tile
        address specified within the message signal unit.  This
        object only applies when the 'destSmeTableNai' bit is
        set in the cdsmrRuleInputParameters object."
    ::= { cdsmrRuleTableEntry  12 }

cdsmrRuleDestSmeTableNp          OBJECT-TYPE
    SYNTAX                       CItpTcNumberingPlan
    MAX-ACCESS                   read-create
    STATUS                       current
    DESCRIPTION
       "The numbering plan for the destination short message
        service center global title address specified within the
        message signal unit.

        This object only applies when the 'destSmeTableNp' bit is
        set in the cdsmrRuleInputParameters object."
    ::= { cdsmrRuleTableEntry  13 }

cdsmrRuleDestSmscGta             OBJECT-TYPE
    SYNTAX                       CItpTcGtaLongDisplay
    MAX-ACCESS                   read-create
    STATUS                       current
    DESCRIPTION
       "The destination short message service center global title
        address.

        When the length of the global title address is zero it
        specified a wildcard match and all global title will
        match GTA clause of rule.

        This object only applies when the 'destSmscGta' bit is
        set in the cdsmrRuleInputParameters object."
    ::= { cdsmrRuleTableEntry  14 }

cdsmrRuleDestSmscNai             OBJECT-TYPE
    SYNTAX                       CItpTcNAI
    MAX-ACCESS                   read-create
    STATUS                       current
    DESCRIPTION
       "The nature of specified address for the destination short
        message service center global title address specified
        within the message signal unit.

        This object only applies when the 'destSmscNai' bit is
        set in the cdsmrRuleInputParameters object."
    ::= { cdsmrRuleTableEntry  15 }

cdsmrRuleDestSmscNp              OBJECT-TYPE
    SYNTAX                       CItpTcNumberingPlan
    MAX-ACCESS                   read-create
    STATUS                       current
    DESCRIPTION
       "The numbering plan for the destination short message
        service center  global title address specified within the
        message signal unit.

        This object only applies when the 'destSmscNp' bit is
        set in the cdsmrRuleInputParameters object."
    ::= { cdsmrRuleTableEntry  16 }

cdsmrRuleDestSmscMinDigits       OBJECT-TYPE
    SYNTAX                       CdsmrMinimumDigits
    MAX-ACCESS                   read-create
    STATUS                       current
    DESCRIPTION
       "Specifies the minimum number of digits that the global
        title address specified by the cdsmrRuleDestSmscGta object
        can contain for rule to match.

        This object only applies when the 'destSmscMinDigits' bit is
        set in the cdsmrRuleInputParameters object."
    ::= { cdsmrRuleTableEntry  17 }

cdsmrRuleDestSmscMaxDigits       OBJECT-TYPE
    SYNTAX                       CdsmrMaximumDigits
    MAX-ACCESS                   read-create
    STATUS                       current
    DESCRIPTION
       "Specifies the maximum number of digits that the global
        title address specified by the cdsmrRuleDestSmscGta object
        can contain for rule to match.

        This object only applies when the 'destSmscMaxDigits' bit is
        set in the cdsmrRuleInputParameters object."
    ::= { cdsmrRuleTableEntry  18 }

cdsmrRuleOrigImsiGta             OBJECT-TYPE
    SYNTAX                       CItpTcGtaLongDisplay
    MAX-ACCESS                   read-create
    STATUS                       current
    DESCRIPTION
       "The origination short message entity global title address.

        When the length of the global title address is zero it
        specified a wildcard match and all global title will
        match GTA clause of rule.

        This object only applies when the 'origImsiGta' bit is
        set in the cdsmrRuleInputParameters object."
    ::= { cdsmrRuleTableEntry  19 }

cdsmrRuleOrigImsiNai             OBJECT-TYPE
    SYNTAX                       CItpTcNAI
    MAX-ACCESS                   read-create
    STATUS                       current
    DESCRIPTION
       "The nature of specified address for the origination short
        message entity global title address specified within the
        message signal unit.

        This object only applies when the 'origImsiNai' bit is
        set in the cdsmrRuleInputParameters object."
    ::= { cdsmrRuleTableEntry  20 }

cdsmrRuleOrigImsiNp              OBJECT-TYPE
    SYNTAX                       CItpTcNumberingPlan
    MAX-ACCESS                   read-create
    STATUS                       current
    DESCRIPTION
       "The numbering plan for the origination short message
        entity global title address specified within the message
        signal unit.

        This object only applies when the 'origImsiNp' bit is
        set in the cdsmrRuleInputParameters object."
    ::= { cdsmrRuleTableEntry  21 }

cdsmrRuleOrigImsiMinDigits       OBJECT-TYPE
    SYNTAX                       CdsmrMinimumDigits
    MAX-ACCESS                   read-create
    STATUS                       current
    DESCRIPTION
       "Specifies the minimum number of digits that the global
        title address specified by the cdsmrRuleOrigImsiGta object
        can contain for rule to match.

        This object only applies when the 'origImsiMinDigits' bit is
        set in the cdsmrRuleInputParameters object."
    ::= { cdsmrRuleTableEntry  22 }

cdsmrRuleOrigImsiMaxDigits       OBJECT-TYPE
    SYNTAX                       CdsmrMaximumDigits
    MAX-ACCESS                   read-create
    STATUS                       current
    DESCRIPTION
       "Specifies the maximum number of digits that the global
        title address specified by the cdsmrRuleOrigImsiGta object
        can contain for rule to match.

        This object only applies when the 'origImsiMaxDigits' bit is
        set in the cdsmrRuleInputParameters object."
    ::= { cdsmrRuleTableEntry  23 }

cdsmrRuleOrigImsiTable           OBJECT-TYPE
    SYNTAX                       CmlrName
    MAX-ACCESS                   read-create
    STATUS                       current
    DESCRIPTION
       "The name of the entry in the cdsmrAddressTable that will be
        searched for matches.  The table will be search for the
        following types of addresses based on values set in the
        cdsmrRuleInputParameters object.

        This object only applies when the 'origImsiTable' bit is
        set in the cdsmrRuleInputParameters object."
    ::= { cdsmrRuleTableEntry  24 }

cdsmrRuleOrigSmeGta              OBJECT-TYPE
    SYNTAX                       CItpTcGtaLongDisplay
    MAX-ACCESS                   read-create
    STATUS                       current
    DESCRIPTION
       "The origination short message entity global title address.

        When the length of the global title address is zero it
        specified a wildcard match and all global title will
        match GTA clause of rule.

        This object only applies when the 'origSmeGta' bit is
        set in the cdsmrRuleInputParameters object."
    ::= { cdsmrRuleTableEntry  25 }

cdsmrRuleOrigSmeNai              OBJECT-TYPE
    SYNTAX                       CItpTcNAI
    MAX-ACCESS                   read-create
    STATUS                       current
    DESCRIPTION
       "The nature of specified address for the origination short
        message entity global title address specified within the
        message signal unit.

        This object only applies when the 'origSmeNai' bit is
        set in the cdsmrRuleInputParameters object."
    ::= { cdsmrRuleTableEntry  26 }

cdsmrRuleOrigSmeNp               OBJECT-TYPE
    SYNTAX                       CItpTcNumberingPlan
    MAX-ACCESS                   read-create
    STATUS                       current
    DESCRIPTION
       "The numbering plan for the origination short message
        entity global title address specified within the message
        signal unit.

        This object only applies when the 'origSmeNp' bit is
        set in the cdsmrRuleInputParameters object."
    ::= { cdsmrRuleTableEntry  27 }

cdsmrRuleOrigSmeMinDigits        OBJECT-TYPE
    SYNTAX                       CdsmrMinimumDigits
    MAX-ACCESS                   read-create
    STATUS                       current
    DESCRIPTION
       "Specifies the minimum number of digits that the global
        title address specified by the cdsmrRuleOrigSmeGta object
        can contain for rule to match.

        This object only applies when the 'origSmeMinDigits' bit is
        set in the cdsmrRuleInputParameters object."
    ::= { cdsmrRuleTableEntry  28 }

cdsmrRuleOrigSmeMaxDigits        OBJECT-TYPE
    SYNTAX                       CdsmrMaximumDigits
    MAX-ACCESS                   read-create
    STATUS                       current
    DESCRIPTION
       "Specifies the maximum number of digits that the global
        title address specified by the cdsmrRuleOrigSmeGta can
        contain for rule to match.

        This object only applies when the 'origSmeMaxDigits' bit is
        set in the cdsmrRuleInputParameters object."
    ::= { cdsmrRuleTableEntry  29 }

cdsmrRuleOrigSmeTable            OBJECT-TYPE
    SYNTAX                       CmlrName
    MAX-ACCESS                   read-create
    STATUS                       current
    DESCRIPTION
       "The name of the entry in the cdsmrAddressTable that will be
        searched for matches. The table will be search for the
        following types of addresses based on values set in the
        cdsmrRuleInputParameters object.

        This object only applies when the 'origSmeTable' bit is
        set in the cdsmrRuleInputParameters object."
    ::= { cdsmrRuleTableEntry  30 }

cdsmrRuleOrigSmeTableNai         OBJECT-TYPE
    SYNTAX                       CItpTcNAI
    MAX-ACCESS                   read-create
    STATUS                       current
    DESCRIPTION
       "The nature of specified address for the global tile
        address specified within the message signal unit.  This
        object only applies when the 'origSmeTableNai' bit is
        set in the cdsmrRuleInputParameters object."
    ::= { cdsmrRuleTableEntry  31 }

cdsmrRuleOrigSmeTableNp          OBJECT-TYPE
    SYNTAX                       CItpTcNumberingPlan
    MAX-ACCESS                   read-create
    STATUS                       current
    DESCRIPTION
       "The numbering plan for the destination short message
        service center global title address specified within the
        message signal unit.

        This object only applies when the 'origSmeTableNp' bit is
        set in the cdsmrRuleInputParameters object."
    ::= { cdsmrRuleTableEntry  32 }

cdsmrRuleOrigSmscGta             OBJECT-TYPE
    SYNTAX                       CItpTcGtaLongDisplay
    MAX-ACCESS                   read-create
    STATUS                       current
    DESCRIPTION
       "The origination short message service center global title
        address.

        When the length of the global title address is zero it
        specified a wildcard match and all global title will
        match GTA clause of rule.

        This object only applies when the 'origSmscGta' bit is
        set in the cdsmrRuleInputParameters object."
    ::= { cdsmrRuleTableEntry  33 }

cdsmrRuleOrigSmscNai             OBJECT-TYPE
    SYNTAX                       CItpTcNAI
    MAX-ACCESS                   read-create
    STATUS                       current
    DESCRIPTION
       "The nature of specified address for the origination short
        message service center global title address specified
        within the message signal unit.

        This object only applies when the 'origSmscNai' bit is
        set in the cdsmrRuleInputParameters object."
    ::= { cdsmrRuleTableEntry  34 }

cdsmrRuleOrigSmscNp              OBJECT-TYPE
    SYNTAX                       CItpTcNumberingPlan
    MAX-ACCESS                   read-create
    STATUS                       current
    DESCRIPTION
       "The numbering plan for the origination short message
        service center  global title address specified within the
        message signal unit.

        This object only applies when the 'origSmscNp' bit is
        set in the cdsmrRuleInputParameters object."
    ::= { cdsmrRuleTableEntry  35 }

cdsmrRuleOrigSmscMinDigits       OBJECT-TYPE
    SYNTAX                       CdsmrMinimumDigits
    MAX-ACCESS                   read-create
    STATUS                       current
    DESCRIPTION
       "Specifies the minimum number of digits that the global
        title address specified by the cdsmrRuleOrigSmscGta
        object can contain for rule to match.

        This object only applies when the 'origSmscMinDigits'
        bit is set in the cdsmrRuleInputParameters object."
    ::= { cdsmrRuleTableEntry  36 }

cdsmrRuleOrigSmscMaxDigits       OBJECT-TYPE
    SYNTAX                       CdsmrMaximumDigits
    MAX-ACCESS                   read-create
    STATUS                       current
    DESCRIPTION
       "Specifies the maximum number of digits that the global
        title address specified by the cdsmrRuleOrigSmscGta object
        can contain for rule to match.

        This object only applies when the 'origSmscMaxDigits' bit is
        set in the cdsmrRuleInputParameters object."
    ::= { cdsmrRuleTableEntry  37 }

cdsmrRuleOrigSmscTable           OBJECT-TYPE
    SYNTAX                       CmlrName
    MAX-ACCESS                   read-create
    STATUS                       current
    DESCRIPTION
       "The name of the entry in the cdsmrAddressTable that will be
        searched for matches. The table will be search for the
        following types of addresses based on values set in the
        cdsmrRuleInputParameters object.

        This object only applies when the 'origSmscTable' bit is
        set in the cdsmrRuleInputParameters object."
    ::= { cdsmrRuleTableEntry  38 }

cdsmrRuleOrigSmscTableNai        OBJECT-TYPE
    SYNTAX                       CItpTcNAI
    MAX-ACCESS                   read-create
    STATUS                       current
    DESCRIPTION
       "The nature of specified address for the global tile
        address specified within the message signal unit.  This
        object only applies when the 'origSmscTableNai' bit is
        set in the cdsmrRuleInputParameters object."
    ::= { cdsmrRuleTableEntry  39 }

cdsmrRuleOrigSmscTableNp         OBJECT-TYPE
    SYNTAX                       CItpTcNumberingPlan
    MAX-ACCESS                   read-create
    STATUS                       current
    DESCRIPTION
       "The numbering plan for the destination short message
        service center global title address specified within the
        message signal unit.

        This object only applies when the 'origSmscTableNp' bit is
        set in the cdsmrRuleInputParameters object."
    ::= { cdsmrRuleTableEntry  40 }

cdsmrRuleProtocolId              OBJECT-TYPE
    SYNTAX                       Unsigned32 (0..255)
    MAX-ACCESS                   read-create
    STATUS                       current
    DESCRIPTION
       "The protocol identifier value used for the 'smsMo and
        'smsMt' operations specified by the
         cdsmrRuleParmsOperationType object.

        The value of the cdsmrRuleParmsMatchPid object maps to the
        values specified  for the TP-PID SMS parameter.

        This object only applies when the 'pid' bit is
        set in the cdsmrRuleInputParameters object."
    ::= { cdsmrRuleTableEntry  41 }

cdsmrRuleTeleserviceId           OBJECT-TYPE
    SYNTAX                       Unsigned32 (0..65535)
    MAX-ACCESS                   read-create
    STATUS                       current
    DESCRIPTION
       "The Teleservice identifier value for the following types
       of operations specified by the cdsmrRuleParmsOperationType
        object.
           'smdPp'
           'smsMo'
           'smsMt'
           'smsNotify'
        The value of the cdsmrRuleParmsMatchTid object maps to the
        values  specified for the SMS_TeleserviceIdentifier
        parameter in ANSI-41.

        This object only applies when the 'tid' bit is
        set in the cdsmrRuleInputParameters object."
    ::= { cdsmrRuleTableEntry  42 }


cdsmrRuleResultParameters        OBJECT-TYPE
    SYNTAX                       CdsmrResultParameters
    MAX-ACCESS                    read-create
    STATUS                        current
    DESCRIPTION
       "Many of the parameter used in the processing of rules
        have default values.  These values are determined
        by a combination of variant and operation type. This
        object will be provide information on which parameter
        have been specified as follows.

        'network'   : cdsmrRuleSetResultNetwork
        'octet'     : cdsmrRuleSetResultOctet
        'tranType'  : cdsmrRuleResultTransType
        'gti'       : cdsmrRuleResultGti
        'np'        : cdsmrRuleResultNp
        'nai'       : cdsmrRuleResultNai
        'pc'        : cdsmrRuleResultPc
        'ssn'       : cdsmrRuleResultSsn
        'ruleNumber': cdsmrRuleResultRuleNumber"
    ::= { cdsmrRuleTableEntry  43 }

cdsmrRuleResultNetwork           OBJECT-TYPE
    SYNTAX                       CItpTcNetworkName
    MAX-ACCESS                   read-create
    STATUS                       current
    DESCRIPTION
       "The network name is used to indicate the network in which
        the result operation will be performed."
    ::= { cdsmrRuleTableEntry  44 }

cdsmrRuleResultType              OBJECT-TYPE
    SYNTAX                       CdsmrResultType
    MAX-ACCESS                   read-create
    STATUS                       current
    DESCRIPTION
       "Specified the type of information to be placed
        into the message signal unit or how the it
        will be processed."
    ::= { cdsmrRuleTableEntry  45 }

cdsmrRuleResultOctet             OBJECT-TYPE
    SYNTAX                       CdsmrResultOctet
    MAX-ACCESS                   read-create
    STATUS                       current
    DESCRIPTION
       "Information to be placed in the message signal
        unit based on the value specified by the
        cdsmrRuleSetResultType object.  When the
        cdsmrRuleSetResultType object is set to 'pc'
        or 'none' this object will not be used in the
        result processing and will have a length of
        zero."
    ::= { cdsmrRuleTableEntry  46 }

cdsmrRuleResultTransType         OBJECT-TYPE
    SYNTAX                       CgsccpGttTransType
    MAX-ACCESS                   read-create
    STATUS                       current
    DESCRIPTION
       "The translation type specified within the  address in the
        message signal unit. This object only applies when the
        cdsmrRuleSetResultType is set to 'gt' value."
    ::= { cdsmrRuleTableEntry  47 }

cdsmrRuleResultGti               OBJECT-TYPE
    SYNTAX                       CgsccpGttGlobalTitleInd
    MAX-ACCESS                   read-create
    STATUS                       current
    DESCRIPTION
       "The global title indicator value for the global tile address
        specified within the message signal unit.  This object only
        applies when the cdsmrRuleSetResultType is set to
        'gt' value."
    ::= { cdsmrRuleTableEntry  48 }

cdsmrRuleResultNp                OBJECT-TYPE
    SYNTAX                       CItpTcNumberingPlan
    MAX-ACCESS                   read-create
    STATUS                       current
    DESCRIPTION
       "The numbering plan for the global tile address specified
        within the message signal unit.  This object only applies
        when the cdsmrRuleSetResultType is set to 'gt' value."
    ::= { cdsmrRuleTableEntry  49 }

cdsmrRuleResultNai               OBJECT-TYPE
    SYNTAX                       CItpTcNAI
    MAX-ACCESS                   read-create
    STATUS                       current
    DESCRIPTION
       "The nature of specified address for the global tile
        address specified within the message signal unit.  This
        object only applies when the cdsmrRuleSetResultType is
        set to 'gt' value."
    ::= { cdsmrRuleTableEntry  50 }

cdsmrRuleResultPc                OBJECT-TYPE
    SYNTAX                       CItpTcPointCode
    MAX-ACCESS                   read-create
    STATUS                       current
    DESCRIPTION
       "The point-code to be place in the message signal unit.  This
        object only applies when the cdsmrRuleResultType is set
        to 'pc' value."
    ::= { cdsmrRuleTableEntry  51 }

cdsmrRuleResultSsn               OBJECT-TYPE
    SYNTAX                       CItpTcSubSystemNumber
    MAX-ACCESS                   read-create
    STATUS                       current
    DESCRIPTION
       "The subsystem number to be place in the message signal unit.
        This object only applies when the cdsmrRuleResultType is set
        to 'ssn' value."
    ::= { cdsmrRuleTableEntry  52 }

cdsmrRuleResultRuleNumber        OBJECT-TYPE
    SYNTAX                       CmlrId
    MAX-ACCESS                   read-create
    STATUS                       current
    DESCRIPTION
       "This object specifies the next rule to execute when
        rule matches. The specified rule number must be greater
        than current rule."
    ::= { cdsmrRuleTableEntry  53 }

cdsmrRuleResultRowStatus         OBJECT-TYPE
    SYNTAX                       RowStatus
    MAX-ACCESS                   read-create
    STATUS                       current
    DESCRIPTION
       "The object is used by a management station to
        create or delete the row entry in cdsmrRuleTable
        following the RowStatus textual convention."
    ::= { cdsmrRuleTableEntry  54 }

--  *************************************************************
--  *                                                           *
--  * Rule Statistics Table                                     *
--  *                                                           *
--  *************************************************************
cdsmrRuleStatsTable         OBJECT-TYPE
    SYNTAX                  SEQUENCE OF CdsmrRuleStatsTableEntry
    MAX-ACCESS              not-accessible
    STATUS                  current
    DESCRIPTION
       "A table that is used to specify attributes of an
        application-layer message to be matched and the resulting
        behavior for handling the message."
    ::= { ciscoItpDsmrMIBObjects 9 }

cdsmrRuleStatsTableEntry          OBJECT-TYPE
    SYNTAX                        CdsmrRuleStatsTableEntry
    MAX-ACCESS                    not-accessible
    STATUS                        current
    DESCRIPTION
    "Entries in this table provide measurements for entries in
     cdsmrRuleTable."
    INDEX   { cgspInstNetwork,
              cdsmrRuleSetName,
              cdsmrRuleNumber
    }
    ::= { cdsmrRuleStatsTable  1 }

CdsmrRuleStatsTableEntry ::= SEQUENCE {
    cdsmrRuleStatsCheckedCounts            Counter32,
    cdsmrRuleStatsMatchCounts              Counter32,
    cdsmrRuleStatsRoutedCounts             Counter32
}

cdsmrRuleStatsCheckedCounts      OBJECT-TYPE
    SYNTAX                       Counter32
    UNITS                        "checks"
    MAX-ACCESS                   read-only
    STATUS                       current
    DESCRIPTION
       "Count of the number of times this rule was checked."
    ::= { cdsmrRuleStatsTableEntry  1 }

cdsmrRuleStatsMatchCounts        OBJECT-TYPE
    SYNTAX                       Counter32
    UNITS                        "matches"
    MAX-ACCESS                   read-only
    STATUS                       current
    DESCRIPTION
       "Count of the number of times this rule was matched."
    ::= { cdsmrRuleStatsTableEntry  2 }

cdsmrRuleStatsRoutedCounts       OBJECT-TYPE
    SYNTAX                       Counter32
    UNITS                        "successes"
    MAX-ACCESS                   read-only
    STATUS                       current
    DESCRIPTION
       "Count of the number of times this rule was matched
        and packet was routed using mechanism specified by
        result."
    ::= { cdsmrRuleStatsTableEntry  3 }


-- *************************************************************
-- *                                                           *
-- * Notifications                                             *
-- *                                                           *
-- *************************************************************
ciscoItpDsmrTableLoad NOTIFICATION-TYPE
     OBJECTS {
              cgspEventSequenceNumber,
              cgspCLLICode,
              cdsmrInstLoadStatus,
              cdsmrInstLastURL
     }
     STATUS  current
     DESCRIPTION
        "This notification is generated whenever a load
         operation is started or completed."
     ::= { ciscoItpDsmrMIBNotifs 1 }

-- *************************************************************
-- *                                                           *
-- * Conformance Information                                   *
-- *                                                           *
-- *************************************************************
ciscoItpDsmrMIBCompliances OBJECT IDENTIFIER
                        ::= { ciscoItpDsmrMIBConform 1 }
ciscoItpDsmrMIBGroups      OBJECT IDENTIFIER
                        ::= { ciscoItpDsmrMIBConform 2 }

-- Compliance

ciscoItpDsmrMIBCompliance MODULE-COMPLIANCE
    STATUS current
    DESCRIPTION
            "The compliance statement for entities which implement
            the Cisco CISCO-ITP-MLR-MIB"
    MODULE
            MANDATORY-GROUPS { ciscoItpDsmrInstanceGroup,
                               ciscoItpDsmrResultGroup,
                               ciscoItpDsmrAddressGroup,
                               ciscoItpDsmrRulesGroup,
                               ciscoItpDsmrNotificationsGroup
            }

--       *** cdsmrInstTable *********************************

         OBJECT           cdsmrInstRowStatus
         MIN-ACCESS       read-only
         DESCRIPTION      "Create/Write access is not required."

--       *** cdsmrResultGroupTable *********************************

         OBJECT           cdsmrResultGroupServerType
         MIN-ACCESS       read-only
         DESCRIPTION      "Create/Write access is not required."

         OBJECT           cdsmrResultGroupCdrConsolidation
         MIN-ACCESS       read-only
         DESCRIPTION      "Create/Write access is not required."

         OBJECT           cdsmrResultGroupIdentifier
         MIN-ACCESS       read-only
         DESCRIPTION      "Create/Write access is not required."

         OBJECT           cdsmrResultGroupQueueLimit
         MIN-ACCESS       read-only
         DESCRIPTION      "Create/Write access is not required."

         OBJECT           cdsmrResultGroupQueueTimeLimit
         MIN-ACCESS       read-only
         DESCRIPTION      "Create/Write access is not required."

         OBJECT           cdsmrResultGroupMatchSmppId
         MIN-ACCESS       read-only
         DESCRIPTION      "Create/Write access is not required."

         OBJECT           cdsmrResultGroupMatchSmppType
         MIN-ACCESS       read-only
         DESCRIPTION      "Create/Write access is not required."

         OBJECT           cdsmrResultGroupMatchUcpId
         MIN-ACCESS       read-only
         DESCRIPTION      "Create/Write access is not required."

         OBJECT           cdsmrResultGroupRowStatus
         MIN-ACCESS       read-only
         DESCRIPTION      "Create/Write access is not required."

--       *** cdsmrResultIpTable *********************************

         OBJECT           cdsmrResultIpRemotePortNumber
         MIN-ACCESS       read-only
         DESCRIPTION      "Create/Write access is not required."

         OBJECT           cdsmrResultIpRemoteIpAddrType
         MIN-ACCESS       read-only
         DESCRIPTION      "Create/Write access is not required."

         OBJECT           cdsmrResultIpRemoteIpAddress
         MIN-ACCESS       read-only
         DESCRIPTION      "Create/Write access is not required."

         OBJECT           cdsmrResultIpProfileName
         MIN-ACCESS       read-only
         DESCRIPTION      "Create/Write access is not required."

         OBJECT           cdsmrResultIpWeight
         MIN-ACCESS       read-only
         DESCRIPTION      "Create/Write access is not required."

         OBJECT           cdsmrResultIpRowStatus
         MIN-ACCESS       read-only
         DESCRIPTION      "Create/Write access is not required."

--       *** cdsmrResultTable *********************************

         OBJECT           cdsmrResultDestinationType
         MIN-ACCESS       read-only
         DESCRIPTION      "Create/Write access is not required."

         OBJECT           cdsmrResultParameters
         MIN-ACCESS       read-only
         DESCRIPTION      "Create/Write access is not required."

         OBJECT           cdsmrResultDestinationName
         MIN-ACCESS       read-only
         DESCRIPTION      "Create/Write access is not required."

         OBJECT           cdsmrResultPc
         MIN-ACCESS       read-only
         DESCRIPTION      "Create/Write access is not required."

         OBJECT           cdsmrResultSsn
         MIN-ACCESS       read-only
         DESCRIPTION      "Create/Write access is not required."

         OBJECT           cdsmrResultGt
         MIN-ACCESS       read-only
         DESCRIPTION      "Create/Write access is not required."

         OBJECT           cdsmrResultTransType
         MIN-ACCESS       read-only
         DESCRIPTION      "Create/Write access is not required."

         OBJECT           cdsmrResultGti
         MIN-ACCESS       read-only
         DESCRIPTION      "Create/Write access is not required."

         OBJECT           cdsmrResultNp
         MIN-ACCESS       read-only
         DESCRIPTION      "Create/Write access is not required."

         OBJECT           cdsmrResultNai
         MIN-ACCESS       read-only
         DESCRIPTION      "Create/Write access is not required."

         OBJECT           cdsmrResultWeight
         MIN-ACCESS       read-only
         DESCRIPTION      "Create/Write access is not required."

         OBJECT           cdsmrResultNetwork
         MIN-ACCESS       read-only
         DESCRIPTION      "Create/Write access is not required."

         OBJECT           cdsmrResultRowStatus
         MIN-ACCESS       read-only
         DESCRIPTION      "Create/Write access is not required."


--       *** cdsmrAddressTable *********************************
         OBJECT           cdsmrAddressResultParameters
         MIN-ACCESS       read-only
         DESCRIPTION      "Create/Write access is not required."

         OBJECT           cdsmrAddressResultNetwork
         MIN-ACCESS       read-only
         DESCRIPTION      "Create/Write access is not required."

         OBJECT           cdsmrAddressResultType
         MIN-ACCESS       read-only
         DESCRIPTION      "Create/Write access is not required."

         OBJECT           cdsmrAddressResultOctet
         MIN-ACCESS       read-only
         DESCRIPTION      "Create/Write access is not required."

         OBJECT           cdsmrAddressResultTransType
         MIN-ACCESS       read-only
         DESCRIPTION      "Create/Write access is not required."

         OBJECT           cdsmrAddressResultGti
         MIN-ACCESS       read-only
         DESCRIPTION      "Create/Write access is not required."

         OBJECT           cdsmrAddressResultNp
         MIN-ACCESS       read-only
         DESCRIPTION      "Create/Write access is not required."

         OBJECT           cdsmrAddressResultNai
         MIN-ACCESS       read-only
         DESCRIPTION      "Create/Write access is not required."

         OBJECT           cdsmrAddressResultPc
         MIN-ACCESS       read-only
         DESCRIPTION      "Create/Write access is not required."

         OBJECT           cdsmrAddressResultSsn
         MIN-ACCESS       read-only
         DESCRIPTION      "Create/Write access is not required."

         OBJECT           cdsmrAddressResultRuleNumber
         MIN-ACCESS       read-only
         DESCRIPTION      "Create/Write access is not required."

         OBJECT           cdsmrAddressRowStatus
         MIN-ACCESS       read-only
         DESCRIPTION      "Create/Write access is not required."

--       *** cdsmrRuleSetTable *********************************

         OBJECT           cdsmrRuleSetProtocol
         MIN-ACCESS       read-only
         DESCRIPTION      "Create/Write access is not required."

         OBJECT           cdsmrRuleSetStartDateAndTime
         MIN-ACCESS       read-only
         DESCRIPTION      "Create/Write access is not required."

         OBJECT           cdsmrRuleSetEndDateAndTime
         MIN-ACCESS       read-only
         DESCRIPTION      "Create/Write access is not required."

         OBJECT           cdsmrRuleSetRowStatus
         MIN-ACCESS       read-only
         DESCRIPTION      "Create/Write access is not required."


--       *** cdsmrRuleTable *********************************
         OBJECT           cdsmrRuleOperationType
         MIN-ACCESS       read-only
         DESCRIPTION      "Create/Write access is not required."

         OBJECT           cdsmrRuleCdrServiceQueue
         MIN-ACCESS       read-only
         DESCRIPTION      "Create/Write access is not required."

         OBJECT           cdsmrRuleInputParameters
         MIN-ACCESS       read-only
         DESCRIPTION      "Create/Write access is not required."

         OBJECT           cdsmrRuleDestPort
         MIN-ACCESS       read-only
         DESCRIPTION      "Create/Write access is not required."

         OBJECT           cdsmrRuleDestSmeGta
         MIN-ACCESS       read-only
         DESCRIPTION      "Create/Write access is not required."

         OBJECT           cdsmrRuleDestSmeNai
         MIN-ACCESS       read-only
         DESCRIPTION      "Create/Write access is not required."

         OBJECT           cdsmrRuleDestSmeNp
         MIN-ACCESS       read-only
         DESCRIPTION      "Create/Write access is not required."

         OBJECT           cdsmrRuleDestSmeMinDigits
         MIN-ACCESS       read-only
         DESCRIPTION      "Create/Write access is not required."

         OBJECT           cdsmrRuleDestSmeMaxDigits
         MIN-ACCESS       read-only
         DESCRIPTION      "Create/Write access is not required."

         OBJECT           cdsmrRuleDestSmeTable
         MIN-ACCESS       read-only
         DESCRIPTION      "Create/Write access is not required."

         OBJECT           cdsmrRuleDestSmeTableNai
         MIN-ACCESS       read-only
         DESCRIPTION      "Create/Write access is not required."

         OBJECT           cdsmrRuleDestSmeTableNp
         MIN-ACCESS       read-only
         DESCRIPTION      "Create/Write access is not required."

         OBJECT           cdsmrRuleDestSmscGta
         MIN-ACCESS       read-only
         DESCRIPTION      "Create/Write access is not required."

         OBJECT           cdsmrRuleDestSmscNai
         MIN-ACCESS       read-only
         DESCRIPTION      "Create/Write access is not required."

         OBJECT           cdsmrRuleDestSmscNp
         MIN-ACCESS       read-only
         DESCRIPTION      "Create/Write access is not required."

         OBJECT           cdsmrRuleDestSmscMinDigits
         MIN-ACCESS       read-only
         DESCRIPTION      "Create/Write access is not required."

         OBJECT           cdsmrRuleDestSmscMaxDigits
         MIN-ACCESS       read-only
         DESCRIPTION      "Create/Write access is not required."

         OBJECT           cdsmrRuleOrigImsiGta
         MIN-ACCESS       read-only
         DESCRIPTION      "Create/Write access is not required."

         OBJECT           cdsmrRuleOrigImsiNai
         MIN-ACCESS       read-only
         DESCRIPTION      "Create/Write access is not required."

         OBJECT           cdsmrRuleOrigImsiNp
         MIN-ACCESS       read-only
         DESCRIPTION      "Create/Write access is not required."

         OBJECT           cdsmrRuleOrigImsiMinDigits
         MIN-ACCESS       read-only
         DESCRIPTION      "Create/Write access is not required."

         OBJECT           cdsmrRuleOrigImsiMaxDigits
         MIN-ACCESS       read-only
         DESCRIPTION      "Create/Write access is not required."

         OBJECT           cdsmrRuleOrigImsiTable
         MIN-ACCESS       read-only
         DESCRIPTION      "Create/Write access is not required."

         OBJECT           cdsmrRuleOrigSmeGta
         MIN-ACCESS       read-only
         DESCRIPTION      "Create/Write access is not required."

         OBJECT           cdsmrRuleOrigSmeNai
         MIN-ACCESS       read-only
         DESCRIPTION      "Create/Write access is not required."

         OBJECT           cdsmrRuleOrigSmeNp
         MIN-ACCESS       read-only
         DESCRIPTION      "Create/Write access is not required."

         OBJECT           cdsmrRuleOrigSmeMinDigits
         MIN-ACCESS       read-only
         DESCRIPTION      "Create/Write access is not required."

         OBJECT           cdsmrRuleOrigSmeMaxDigits
         MIN-ACCESS       read-only
         DESCRIPTION      "Create/Write access is not required."
         OBJECT           cdsmrRuleOrigSmeTable
         MIN-ACCESS       read-only
         DESCRIPTION      "Create/Write access is not required."

         OBJECT           cdsmrRuleOrigSmeTableNai
         MIN-ACCESS       read-only
         DESCRIPTION      "Create/Write access is not required."

         OBJECT           cdsmrRuleOrigSmeTableNp
         MIN-ACCESS       read-only
         DESCRIPTION      "Create/Write access is not required."

         OBJECT           cdsmrRuleOrigSmscGta
         MIN-ACCESS       read-only
         DESCRIPTION      "Create/Write access is not required."

         OBJECT           cdsmrRuleOrigSmscNai
         MIN-ACCESS       read-only
         DESCRIPTION      "Create/Write access is not required."

         OBJECT           cdsmrRuleOrigSmscNp
         MIN-ACCESS       read-only
         DESCRIPTION      "Create/Write access is not required."

         OBJECT           cdsmrRuleOrigSmscMinDigits
         MIN-ACCESS       read-only
         DESCRIPTION      "Create/Write access is not required."

         OBJECT           cdsmrRuleOrigSmscMaxDigits
         MIN-ACCESS       read-only
         DESCRIPTION      "Create/Write access is not required."

         OBJECT           cdsmrRuleOrigSmscTable
         MIN-ACCESS       read-only
         DESCRIPTION      "Create/Write access is not required."

         OBJECT           cdsmrRuleOrigSmscTableNai
         MIN-ACCESS       read-only
         DESCRIPTION      "Create/Write access is not required."

         OBJECT           cdsmrRuleOrigSmscTableNp
         MIN-ACCESS       read-only
         DESCRIPTION      "Create/Write access is not required."

         OBJECT           cdsmrRuleProtocolId
         MIN-ACCESS       read-only
         DESCRIPTION      "Create/Write access is not required."

         OBJECT           cdsmrRuleTeleserviceId
         MIN-ACCESS       read-only
         DESCRIPTION      "Create/Write access is not required."

         OBJECT           cdsmrRuleResultParameters
         MIN-ACCESS       read-only
         DESCRIPTION      "Create/Write access is not required."

         OBJECT           cdsmrRuleResultNetwork
         MIN-ACCESS       read-only
         DESCRIPTION      "Create/Write access is not required."

         OBJECT           cdsmrRuleResultType
         MIN-ACCESS       read-only
         DESCRIPTION      "Create/Write access is not required."

         OBJECT           cdsmrRuleResultOctet
         MIN-ACCESS       read-only
         DESCRIPTION      "Create/Write access is not required."

         OBJECT           cdsmrRuleResultTransType
         MIN-ACCESS       read-only
         DESCRIPTION      "Create/Write access is not required."

         OBJECT           cdsmrRuleResultGti
         MIN-ACCESS       read-only
         DESCRIPTION      "Create/Write access is not required."

         OBJECT           cdsmrRuleResultNp
         MIN-ACCESS       read-only
         DESCRIPTION      "Create/Write access is not required."

         OBJECT           cdsmrRuleResultNai
         MIN-ACCESS       read-only
         DESCRIPTION      "Create/Write access is not required."

         OBJECT           cdsmrRuleResultPc
         MIN-ACCESS       read-only
         DESCRIPTION      "Create/Write access is not required."

         OBJECT           cdsmrRuleResultSsn
         MIN-ACCESS       read-only
         DESCRIPTION      "Create/Write access is not required."

         OBJECT           cdsmrRuleResultRuleNumber
         MIN-ACCESS       read-only
         DESCRIPTION      "Create/Write access is not required."

         OBJECT           cdsmrRuleResultRowStatus
         MIN-ACCESS       read-only
         DESCRIPTION      "Create/Write access is not required."


::= { ciscoItpDsmrMIBCompliances 1 }

-- Units of Conformance

ciscoItpDsmrInstanceGroup OBJECT-GROUP
    OBJECTS { cdsmrTableLoadNotifEnabled,
              cdsmrInstLastChanged,
              cdsmrInstLastLoadTime,
              cdsmrInstLoadStatus,
              cdsmrInstLastURL,
              cdsmrInstDeliveredSmppCounts,
              cdsmrInstDeliveredUcpCounts,
              cdsmrInstDeliveredGsmCounts,
              cdsmrInstDeferredGsmCounts,
              cdsmrInstGsmStatusReports,
              cdsmrInstUcpNotifications,
              cdsmrInstSmppDeliveryReceipts,
              cdsmrInstRoutingFailures,
              cdsmrInstResultFailures,
              cdsmrInstInternalErrors,
              cdsmrInstParseErrors,
              cdsmrInstResourceErrors,
              cdsmrInstProvisioningErrors,
              cdsmrInstDestUnreachableErrors,
              cdsmrInstDestSignalErrors,
              cdsmrInstTimeOuts,
              cdsmrInstBlockedPackets,
              cdsmrInstRoutingRequestsRcvdGsm,
              cdsmrInstRoutingRequestsRcvdIs41,
              cdsmrInstRoutingRequestsRcvdUcp,
              cdsmrInstRoutingRequestsRcvdSmpp,
              cdsmrInstRowStatus
    }
    STATUS current
    DESCRIPTION
       "A collection of objects providing information on DSMR per
        instance of signalling point."
    ::= { ciscoItpDsmrMIBGroups 1 }


ciscoItpDsmrResultGroup OBJECT-GROUP
    OBJECTS { cdsmrResultGroupServerType,
              cdsmrResultGroupCdrConsolidation,
              cdsmrResultGroupIdentifier,
              cdsmrResultGroupQueueLimit,
              cdsmrResultGroupQueueTimeLimit,
              cdsmrResultGroupMatchSmppId,
              cdsmrResultGroupMatchSmppType,
              cdsmrResultGroupMatchUcpId,
              cdsmrResultGroupRowStatus,
              cdsmrResultDestinationType,
              cdsmrResultParameters,
              cdsmrResultDestinationName,
              cdsmrResultPc,
              cdsmrResultSsn,
              cdsmrResultGt,
              cdsmrResultTransType,
              cdsmrResultGti,
              cdsmrResultNp,
              cdsmrResultNai,
              cdsmrResultWeight,
              cdsmrResultCounts,
              cdsmrResultNetwork,
              cdsmrResultRowStatus,
              cdsmrResultIpRemotePortNumber,
              cdsmrResultIpRemoteIpAddrType,
              cdsmrResultIpRemoteIpAddress,
              cdsmrResultIpProfileName,
              cdsmrResultIpWeight,
              cdsmrResultIpRowStatus
            }
    STATUS current
    DESCRIPTION
       "A collection of objects providing information used to
        configure distributed short message routing result
        groups and entries."
    ::= { ciscoItpDsmrMIBGroups 2 }


ciscoItpDsmrAddressGroup OBJECT-GROUP
    OBJECTS { cdsmrAddressResultParameters,
              cdsmrAddressResultNetwork,
              cdsmrAddressResultType,
              cdsmrAddressResultOctet,
              cdsmrAddressResultTransType,
              cdsmrAddressResultGti,
              cdsmrAddressResultNp,
              cdsmrAddressResultNai,
              cdsmrAddressResultPc,
              cdsmrAddressResultSsn,
              cdsmrAddressResultRuleNumber,
              cdsmrAddressMatchCounts,
              cdsmrAddressRowStatus
            }
    STATUS current
    DESCRIPTION
       "A collection of objects providing information used to
        configure distributed short message routing address tables."
    ::= { ciscoItpDsmrMIBGroups 3 }

ciscoItpDsmrRulesGroup OBJECT-GROUP
    OBJECTS { cdsmrRuleSetProtocol,
              cdsmrRuleSetStartDateAndTime,
              cdsmrRuleSetEndDateAndTime,
              cdsmrRuleSetRowStatus,
              cdsmrRuleOperationType,
              cdsmrRuleCdrServiceQueue,
              cdsmrRuleInputParameters,
              cdsmrRuleDestPort,
              cdsmrRuleDestSmeGta,
              cdsmrRuleDestSmeNai,
              cdsmrRuleDestSmeNp,
              cdsmrRuleDestSmeMinDigits,
              cdsmrRuleDestSmeMaxDigits,
              cdsmrRuleDestSmeTable,
              cdsmrRuleDestSmeTableNai,
              cdsmrRuleDestSmeTableNp,
              cdsmrRuleDestSmscGta,
              cdsmrRuleDestSmscNai,
              cdsmrRuleDestSmscNp,
              cdsmrRuleDestSmscMinDigits,
              cdsmrRuleDestSmscMaxDigits,
              cdsmrRuleOrigImsiGta,
              cdsmrRuleOrigImsiNai,
              cdsmrRuleOrigImsiNp,
              cdsmrRuleOrigImsiMinDigits,
              cdsmrRuleOrigImsiMaxDigits,
              cdsmrRuleOrigImsiTable,
              cdsmrRuleOrigSmeGta,
              cdsmrRuleOrigSmeNai,
              cdsmrRuleOrigSmeNp,
              cdsmrRuleOrigSmeMinDigits,
              cdsmrRuleOrigSmeMaxDigits,
              cdsmrRuleOrigSmeTable,
              cdsmrRuleOrigSmeTableNai,
              cdsmrRuleOrigSmeTableNp,
              cdsmrRuleOrigSmscGta,
              cdsmrRuleOrigSmscNai,
              cdsmrRuleOrigSmscNp,
              cdsmrRuleOrigSmscMinDigits,
              cdsmrRuleOrigSmscMaxDigits,
              cdsmrRuleOrigSmscTable,
              cdsmrRuleOrigSmscTableNai,
              cdsmrRuleOrigSmscTableNp,
              cdsmrRuleProtocolId,
              cdsmrRuleTeleserviceId,
              cdsmrRuleResultParameters,
              cdsmrRuleResultNetwork,
              cdsmrRuleResultType,
              cdsmrRuleResultOctet,
              cdsmrRuleResultTransType,
              cdsmrRuleResultGti,
              cdsmrRuleResultNp,
              cdsmrRuleResultNai,
              cdsmrRuleResultPc,
              cdsmrRuleResultSsn,
              cdsmrRuleResultRuleNumber,
              cdsmrRuleResultRowStatus,
              cdsmrRuleStatsMatchCounts,
              cdsmrRuleStatsCheckedCounts,
              cdsmrRuleStatsRoutedCounts
            }
    STATUS current
    DESCRIPTION
       "A collection of objects providing information used to
        configure rules used for distributed short message routing."
    ::= { ciscoItpDsmrMIBGroups 4 }


ciscoItpDsmrNotificationsGroup NOTIFICATION-GROUP
        NOTIFICATIONS { ciscoItpDsmrTableLoad }
        STATUS current
        DESCRIPTION
           "Distributed short message routing notification
            objects."
        ::= { ciscoItpDsmrMIBGroups 6 }
END
