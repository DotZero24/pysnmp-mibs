-- *********************************************************************
-- CISCO-FIREPOWER-ETHER-MIB.my
--
-- MIB representation of the Cisco Firepower
-- ETHER management information model package
--
-- Created March 2020 by Charles Bullis
--
-- Copyright (c) 2005-2020 Cisco Systems, Inc. All rights reserved.
--
-- *********************************************************************

CISCO-FIREPOWER-ETHER-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionRemoteInvRslt,
    CfprEquipmentChassisConfigState,
    CfprEquipmentXcvrType,
    CfprEtherCIoEpIfType,
    CfprEtherCloudType,
    CfprEtherErrStatsHistThresholded,
    CfprEtherErrStatsThresholded,
    CfprEtherExternalEpAdminState,
    CfprEtherExternalEpLocale,
    CfprEtherExternalPcAdminState,
    CfprEtherExternalPcLocale,
    CfprEtherFcoeInterfaceStatsHistThresholded,
    CfprEtherFcoeInterfaceStatsThresholded,
    CfprEtherFtwOperMode,
    CfprEtherFtwPortPairFsmCurrentFsm,
    CfprEtherFtwPortPairFsmStageName,
    CfprEtherFtwPortPairFsmTaskItem,
    CfprEtherFtwPortPairMode,
    CfprEtherFtwPortPairWdtState,
    CfprEtherIntFIoEpType,
    CfprEtherInternalPcLocale,
    CfprEtherLossStatsHistThresholded,
    CfprEtherLossStatsThresholded,
    CfprEtherNiErrStatsHistThresholded,
    CfprEtherNiErrStatsThresholded,
    CfprEtherPIoEpIfType,
    CfprEtherPIoFsmCurrentFsm,
    CfprEtherPIoFsmStageName,
    CfprEtherPauseStatsHistThresholded,
    CfprEtherPauseStatsThresholded,
    CfprEtherRxStatsHistThresholded,
    CfprEtherRxStatsThresholded,
    CfprEtherSatelliteConnectionDisc,
    CfprEtherServerIntFIoAdminState,
    CfprEtherServerIntFIoFsmCurrentFsm,
    CfprEtherServerIntFIoFsmStageName,
    CfprEtherServerIntFIoFsmTaskItem,
    CfprEtherServerIntFIoIfRole,
    CfprEtherServerIntFIoLocale,
    CfprEtherServerIntFIoPcEpIfRole,
    CfprEtherServerIntFIoPcEpPortId,
    CfprEtherServerIntFIoPcIfRole,
    CfprEtherServerIntFIoPcPortId,
    CfprEtherServerIntFIoPcTransport,
    CfprEtherServerIntFIoPcType,
    CfprEtherServerIntFIoTransport,
    CfprEtherServerIntFIoType,
    CfprEtherSwitchIntFIoAck,
    CfprEtherSwitchIntFIoIfRole,
    CfprEtherSwitchIntFIoLocale,
    CfprEtherSwitchIntFIoPcEpIfRole,
    CfprEtherSwitchIntFIoPcEpPortId,
    CfprEtherSwitchIntFIoPcIfRole,
    CfprEtherSwitchIntFIoPcPortId,
    CfprEtherSwitchIntFIoPcTransport,
    CfprEtherSwitchIntFIoPcType,
    CfprEtherSwitchIntFIoTransport,
    CfprEtherSwitchIntFIoType,
    CfprEtherTxStatsHistThresholded,
    CfprEtherTxStatsThresholded,
    CfprFabricAdminState,
    CfprFabricMembershipStatus,
    CfprFsmCompletion,
    CfprFsmFlags,
    CfprFsmFsmStageStatus,
    CfprFsmLifecycle,
    CfprLicenseState,
    CfprNetworkConnectionType,
    CfprNetworkLocale,
    CfprNetworkPhysEpIfType,
    CfprNetworkPortOperState,
    CfprNetworkPortRole,
    CfprNetworkSwitchId,
    CfprNetworkTransport,
    CfprPortDuplex,
    CfprPortEncap,
    CfprPortEthSpeed,
    CfprPortMode
        FROM CISCO-FIREPOWER-TC-MIB;

cfprEtherObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        ETHER management information model package"
    ::= { ciscoFirepowerMIBObjects 21 }

cfprEtherErrStatsTable OBJECT-TYPE
    SYNTAX           SEQUENCE OF CfprEtherErrStatsEntry
    MAX-ACCESS       not-accessible
    STATUS           current
    DESCRIPTION
        "Cisco Firepower ether:ErrStats managed object table"
    ::= { cfprEtherObjects 1 }

cfprEtherErrStatsEntry OBJECT-TYPE
    SYNTAX           CfprEtherErrStatsEntry
    MAX-ACCESS       not-accessible
    STATUS           current
    DESCRIPTION
        "Entry for the cfprEtherErrStatsTable table."
    INDEX { cfprEtherErrStatsInstanceId }
    ::= { cfprEtherErrStatsTable 1 }

CfprEtherErrStatsEntry ::= SEQUENCE {
    cfprEtherErrStatsInstanceId                                      CfprManagedObjectId,
    cfprEtherErrStatsDn                                              CfprManagedObjectDn,
    cfprEtherErrStatsRn                                              SnmpAdminString,
    cfprEtherErrStatsAlign                                           Unsigned64,
    cfprEtherErrStatsAlignDelta                                      Counter64,
    cfprEtherErrStatsAlignDeltaAvg                                   Unsigned64,
    cfprEtherErrStatsAlignDeltaMax                                   Unsigned64,
    cfprEtherErrStatsAlignDeltaMin                                   Unsigned64,
    cfprEtherErrStatsDeferredTx                                      Unsigned64,
    cfprEtherErrStatsDeferredTxDelta                                 Counter64,
    cfprEtherErrStatsDeferredTxDeltaAvg                              Unsigned64,
    cfprEtherErrStatsDeferredTxDeltaMax                              Unsigned64,
    cfprEtherErrStatsDeferredTxDeltaMin                              Unsigned64,
    cfprEtherErrStatsFcs                                             Unsigned64,
    cfprEtherErrStatsFcsDelta                                        Counter64,
    cfprEtherErrStatsFcsDeltaAvg                                     Unsigned64,
    cfprEtherErrStatsFcsDeltaMax                                     Unsigned64,
    cfprEtherErrStatsFcsDeltaMin                                     Unsigned64,
    cfprEtherErrStatsIntMacRx                                        Unsigned64,
    cfprEtherErrStatsIntMacRxDelta                                   Counter64,
    cfprEtherErrStatsIntMacRxDeltaAvg                                Unsigned64,
    cfprEtherErrStatsIntMacRxDeltaMax                                Unsigned64,
    cfprEtherErrStatsIntMacRxDeltaMin                                Unsigned64,
    cfprEtherErrStatsIntMacTx                                        Unsigned64,
    cfprEtherErrStatsIntMacTxDelta                                   Counter64,
    cfprEtherErrStatsIntMacTxDeltaAvg                                Unsigned64,
    cfprEtherErrStatsIntMacTxDeltaMax                                Unsigned64,
    cfprEtherErrStatsIntMacTxDeltaMin                                Unsigned64,
    cfprEtherErrStatsIntervals                                       Gauge32,
    cfprEtherErrStatsOutDiscard                                      Unsigned64,
    cfprEtherErrStatsOutDiscardDelta                                 Counter64,
    cfprEtherErrStatsOutDiscardDeltaAvg                              Unsigned64,
    cfprEtherErrStatsOutDiscardDeltaMax                              Unsigned64,
    cfprEtherErrStatsOutDiscardDeltaMin                              Unsigned64,
    cfprEtherErrStatsRcv                                             Unsigned64,
    cfprEtherErrStatsRcvDelta                                        Counter64,
    cfprEtherErrStatsRcvDeltaAvg                                     Unsigned64,
    cfprEtherErrStatsRcvDeltaMax                                     Unsigned64,
    cfprEtherErrStatsRcvDeltaMin                                     Unsigned64,
    cfprEtherErrStatsSuspect                                         TruthValue,
    cfprEtherErrStatsThresholded                                     CfprEtherErrStatsThresholded,
    cfprEtherErrStatsTimeCollected                                   DateAndTime,
    cfprEtherErrStatsUnderSize                                       Unsigned64,
    cfprEtherErrStatsUnderSizeDelta                                  Counter64,
    cfprEtherErrStatsUnderSizeDeltaAvg                               Unsigned64,
    cfprEtherErrStatsUnderSizeDeltaMax                               Unsigned64,
    cfprEtherErrStatsUnderSizeDeltaMin                               Unsigned64,
    cfprEtherErrStatsUpdate                                          Gauge32,
    cfprEtherErrStatsXmit                                            Unsigned64,
    cfprEtherErrStatsXmitDelta                                       Counter64,
    cfprEtherErrStatsXmitDeltaAvg                                    Unsigned64,
    cfprEtherErrStatsXmitDeltaMax                                    Unsigned64,
    cfprEtherErrStatsXmitDeltaMin                                    Unsigned64
}

cfprEtherErrStatsInstanceId OBJECT-TYPE
    SYNTAX       CfprManagedObjectId
    MAX-ACCESS   not-accessible
    STATUS       current
    DESCRIPTION
        "Instance identifier of the managed object."
    ::= { cfprEtherErrStatsEntry 1 }

cfprEtherErrStatsDn OBJECT-TYPE
    SYNTAX       CfprManagedObjectDn
    MAX-ACCESS   read-only
    STATUS       current
    DESCRIPTION
        "Cisco Firepower ether:ErrStats:dn managed object property"
    ::= { cfprEtherErrStatsEntry 2 }

cfprEtherErrStatsRn OBJECT-TYPE
    SYNTAX       SnmpAdminString
    MAX-ACCESS   read-only
    STATUS       current
    DESCRIPTION
        "Cisco Firepower ether:ErrStats:rn managed object property"
    ::= { cfprEtherErrStatsEntry 3 }

cfprEtherErrStatsAlign OBJECT-TYPE
    SYNTAX       Unsigned64
    MAX-ACCESS   read-only
    STATUS       current
    DESCRIPTION
        "Cisco Firepower ether:ErrStats:align managed object property"
    ::= { cfprEtherErrStatsEntry 4 }

cfprEtherErrStatsAlignDelta OBJECT-TYPE
    SYNTAX       Counter64
    MAX-ACCESS   read-only
    STATUS       current
    DESCRIPTION
        "Cisco Firepower ether:ErrStats:alignDelta managed
        object property"
    ::= { cfprEtherErrStatsEntry 5 }

cfprEtherErrStatsAlignDeltaAvg OBJECT-TYPE
    SYNTAX       Unsigned64
    MAX-ACCESS   read-only
    STATUS       current
    DESCRIPTION
        "Cisco Firepower ether:ErrStats:alignDeltaAvg managed
        object property"
    ::= { cfprEtherErrStatsEntry 6 }

cfprEtherErrStatsAlignDeltaMax OBJECT-TYPE
    SYNTAX       Unsigned64
    MAX-ACCESS   read-only
    STATUS       current
    DESCRIPTION
        "Cisco Firepower ether:ErrStats:alignDeltaMax managed
        object property"
    ::= { cfprEtherErrStatsEntry 7 }

cfprEtherErrStatsAlignDeltaMin OBJECT-TYPE
    SYNTAX       Unsigned64
    MAX-ACCESS   read-only
    STATUS       current
    DESCRIPTION
        "Cisco Firepower ether:ErrStats:alignDeltaMin managed
        object property"
    ::= { cfprEtherErrStatsEntry 8 }

cfprEtherErrStatsDeferredTx OBJECT-TYPE
    SYNTAX       Unsigned64
    MAX-ACCESS   read-only
    STATUS       current
    DESCRIPTION
        "Cisco Firepower ether:ErrStats:deferredTx managed
        object property"
    ::= { cfprEtherErrStatsEntry 9 }

cfprEtherErrStatsDeferredTxDelta OBJECT-TYPE
    SYNTAX       Counter64
    MAX-ACCESS   read-only
    STATUS       current
    DESCRIPTION
        "Cisco Firepower ether:ErrStats:deferredTxDelta
        managed object property"
    ::= { cfprEtherErrStatsEntry 10 }

cfprEtherErrStatsDeferredTxDeltaAvg OBJECT-TYPE
    SYNTAX       Unsigned64
    MAX-ACCESS   read-only
    STATUS       current
    DESCRIPTION
        "Cisco Firepower ether:ErrStats:deferredTxDeltaAvg
        managed object property"
    ::= { cfprEtherErrStatsEntry 11 }

cfprEtherErrStatsDeferredTxDeltaMax OBJECT-TYPE
    SYNTAX       Unsigned64
    MAX-ACCESS   read-only
    STATUS       current
    DESCRIPTION
        "Cisco Firepower ether:ErrStats:deferredTxDeltaMax
        managed object property"
    ::= { cfprEtherErrStatsEntry 12 }

cfprEtherErrStatsDeferredTxDeltaMin OBJECT-TYPE
    SYNTAX       Unsigned64
    MAX-ACCESS   read-only
    STATUS       current
    DESCRIPTION
        "Cisco Firepower ether:ErrStats:deferredTxDeltaMin
        managed object property"
    ::= { cfprEtherErrStatsEntry 13 }

cfprEtherErrStatsFcs OBJECT-TYPE
    SYNTAX       Unsigned64
    MAX-ACCESS   read-only
    STATUS       current
    DESCRIPTION
        "Cisco Firepower ether:ErrStats:fcs managed object property"
    ::= { cfprEtherErrStatsEntry 14 }

cfprEtherErrStatsFcsDelta OBJECT-TYPE
    SYNTAX       Counter64
    MAX-ACCESS   read-only
    STATUS       current
    DESCRIPTION
        "Cisco Firepower ether:ErrStats:fcsDelta managed object property"
    ::= { cfprEtherErrStatsEntry 15 }

cfprEtherErrStatsFcsDeltaAvg OBJECT-TYPE
    SYNTAX       Unsigned64
    MAX-ACCESS   read-only
    STATUS       current
    DESCRIPTION
        "Cisco Firepower ether:ErrStats:fcsDeltaAvg managed
        object property"
    ::= { cfprEtherErrStatsEntry 16 }

cfprEtherErrStatsFcsDeltaMax OBJECT-TYPE
    SYNTAX       Unsigned64
    MAX-ACCESS   read-only
    STATUS       current
    DESCRIPTION
        "Cisco Firepower ether:ErrStats:fcsDeltaMax managed
        object property"
    ::= { cfprEtherErrStatsEntry 17 }

cfprEtherErrStatsFcsDeltaMin OBJECT-TYPE
    SYNTAX       Unsigned64
    MAX-ACCESS   read-only
    STATUS       current
    DESCRIPTION
        "Cisco Firepower ether:ErrStats:fcsDeltaMin managed
        object property"
    ::= { cfprEtherErrStatsEntry 18 }

cfprEtherErrStatsIntMacRx OBJECT-TYPE
    SYNTAX       Unsigned64
    MAX-ACCESS   read-only
    STATUS       current
    DESCRIPTION
        "Cisco Firepower ether:ErrStats:intMacRx managed object property"
    ::= { cfprEtherErrStatsEntry 19 }

cfprEtherErrStatsIntMacRxDelta OBJECT-TYPE
    SYNTAX       Counter64
    MAX-ACCESS   read-only
    STATUS       current
    DESCRIPTION
        "Cisco Firepower ether:ErrStats:intMacRxDelta managed
        object property"
    ::= { cfprEtherErrStatsEntry 20 }

cfprEtherErrStatsIntMacRxDeltaAvg OBJECT-TYPE
    SYNTAX       Unsigned64
    MAX-ACCESS   read-only
    STATUS       current
    DESCRIPTION
        "Cisco Firepower ether:ErrStats:intMacRxDeltaAvg
        managed object property"
    ::= { cfprEtherErrStatsEntry 21 }

cfprEtherErrStatsIntMacRxDeltaMax OBJECT-TYPE
    SYNTAX       Unsigned64
    MAX-ACCESS   read-only
    STATUS       current
    DESCRIPTION
        "Cisco Firepower ether:ErrStats:intMacRxDeltaMax
        managed object property"
    ::= { cfprEtherErrStatsEntry 22 }

cfprEtherErrStatsIntMacRxDeltaMin OBJECT-TYPE
    SYNTAX       Unsigned64
    MAX-ACCESS   read-only
    STATUS       current
    DESCRIPTION
        "Cisco Firepower ether:ErrStats:intMacRxDeltaMin
        managed object property"
    ::= { cfprEtherErrStatsEntry 23 }

cfprEtherErrStatsIntMacTx OBJECT-TYPE
    SYNTAX       Unsigned64
    MAX-ACCESS   read-only
    STATUS       current
    DESCRIPTION
        "Cisco Firepower ether:ErrStats:intMacTx managed object property"
    ::= { cfprEtherErrStatsEntry 24 }

cfprEtherErrStatsIntMacTxDelta OBJECT-TYPE
    SYNTAX       Counter64
    MAX-ACCESS   read-only
    STATUS       current
    DESCRIPTION
        "Cisco Firepower ether:ErrStats:intMacTxDelta managed
        object property"
    ::= { cfprEtherErrStatsEntry 25 }

cfprEtherErrStatsIntMacTxDeltaAvg OBJECT-TYPE
    SYNTAX       Unsigned64
    MAX-ACCESS   read-only
    STATUS       current
    DESCRIPTION
        "Cisco Firepower ether:ErrStats:intMacTxDeltaAvg
        managed object property"
    ::= { cfprEtherErrStatsEntry 26 }

cfprEtherErrStatsIntMacTxDeltaMax OBJECT-TYPE
    SYNTAX       Unsigned64
    MAX-ACCESS   read-only
    STATUS       current
    DESCRIPTION
        "Cisco Firepower ether:ErrStats:intMacTxDeltaMax
        managed object property"
    ::= { cfprEtherErrStatsEntry 27 }

cfprEtherErrStatsIntMacTxDeltaMin OBJECT-TYPE
    SYNTAX       Unsigned64
    MAX-ACCESS   read-only
    STATUS       current
    DESCRIPTION
        "Cisco Firepower ether:ErrStats:intMacTxDeltaMin
        managed object property"
    ::= { cfprEtherErrStatsEntry 28 }

cfprEtherErrStatsIntervals OBJECT-TYPE
    SYNTAX       Gauge32
    MAX-ACCESS   read-only
    STATUS       current
    DESCRIPTION
        "Cisco Firepower ether:ErrStats:intervals managed object property"
    ::= { cfprEtherErrStatsEntry 29 }

cfprEtherErrStatsOutDiscard OBJECT-TYPE
    SYNTAX       Unsigned64
    MAX-ACCESS   read-only
    STATUS       current
    DESCRIPTION
        "Cisco Firepower ether:ErrStats:outDiscard managed
        object property"
    ::= { cfprEtherErrStatsEntry 30 }

cfprEtherErrStatsOutDiscardDelta OBJECT-TYPE
    SYNTAX       Counter64
    MAX-ACCESS   read-only
    STATUS       current
    DESCRIPTION
        "Cisco Firepower ether:ErrStats:outDiscardDelta
        managed object property"
    ::= { cfprEtherErrStatsEntry 31 }

cfprEtherErrStatsOutDiscardDeltaAvg OBJECT-TYPE
    SYNTAX       Unsigned64
    MAX-ACCESS   read-only
    STATUS       current
    DESCRIPTION
        "Cisco Firepower ether:ErrStats:outDiscardDeltaAvg
        managed object property"
    ::= { cfprEtherErrStatsEntry 32 }

cfprEtherErrStatsOutDiscardDeltaMax OBJECT-TYPE
    SYNTAX       Unsigned64
    MAX-ACCESS   read-only
    STATUS       current
    DESCRIPTION
        "Cisco Firepower ether:ErrStats:outDiscardDeltaMax
        managed object property"
    ::= { cfprEtherErrStatsEntry 33 }

cfprEtherErrStatsOutDiscardDeltaMin OBJECT-TYPE
    SYNTAX       Unsigned64
    MAX-ACCESS   read-only
    STATUS       current
    DESCRIPTION
        "Cisco Firepower ether:ErrStats:outDiscardDeltaMin
        managed object property"
    ::= { cfprEtherErrStatsEntry 34 }

cfprEtherErrStatsRcv OBJECT-TYPE
    SYNTAX       Unsigned64
    MAX-ACCESS   read-only
    STATUS       current
    DESCRIPTION
        "Cisco Firepower ether:ErrStats:rcv managed object property"
    ::= { cfprEtherErrStatsEntry 35 }

cfprEtherErrStatsRcvDelta OBJECT-TYPE
    SYNTAX       Counter64
    MAX-ACCESS   read-only
    STATUS       current
    DESCRIPTION
        "Cisco Firepower ether:ErrStats:rcvDelta managed object property"
    ::= { cfprEtherErrStatsEntry 36 }

cfprEtherErrStatsRcvDeltaAvg OBJECT-TYPE
    SYNTAX       Unsigned64
    MAX-ACCESS   read-only
    STATUS       current
    DESCRIPTION
        "Cisco Firepower ether:ErrStats:rcvDeltaAvg managed
        object property"
    ::= { cfprEtherErrStatsEntry 37 }

cfprEtherErrStatsRcvDeltaMax OBJECT-TYPE
    SYNTAX       Unsigned64
    MAX-ACCESS   read-only
    STATUS       current
    DESCRIPTION
        "Cisco Firepower ether:ErrStats:rcvDeltaMax managed
        object property"
    ::= { cfprEtherErrStatsEntry 38 }

cfprEtherErrStatsRcvDeltaMin OBJECT-TYPE
    SYNTAX       Unsigned64
    MAX-ACCESS   read-only
    STATUS       current
    DESCRIPTION
        "Cisco Firepower ether:ErrStats:rcvDeltaMin managed
        object property"
    ::= { cfprEtherErrStatsEntry 39 }

cfprEtherErrStatsSuspect OBJECT-TYPE
    SYNTAX       TruthValue
    MAX-ACCESS   read-only
    STATUS       current
    DESCRIPTION
        "Cisco Firepower ether:ErrStats:suspect managed object property"
    ::= { cfprEtherErrStatsEntry 40 }

cfprEtherErrStatsThresholded OBJECT-TYPE
    SYNTAX       CfprEtherErrStatsThresholded
    MAX-ACCESS   read-only
    STATUS       current
    DESCRIPTION
        "Cisco Firepower ether:ErrStats:thresholded managed
        object property"
    ::= { cfprEtherErrStatsEntry 41 }

cfprEtherErrStatsTimeCollected OBJECT-TYPE
    SYNTAX       DateAndTime
    MAX-ACCESS   read-only
    STATUS       current
    DESCRIPTION
        "Cisco Firepower ether:ErrStats:timeCollected managed
        object property"
    ::= { cfprEtherErrStatsEntry 42 }

cfprEtherErrStatsUnderSize OBJECT-TYPE
    SYNTAX       Unsigned64
    MAX-ACCESS   read-only
    STATUS       current
    DESCRIPTION
        "Cisco Firepower ether:ErrStats:underSize managed object property"
    ::= { cfprEtherErrStatsEntry 43 }

cfprEtherErrStatsUnderSizeDelta OBJECT-TYPE
    SYNTAX       Counter64
    MAX-ACCESS   read-only
    STATUS       current
    DESCRIPTION
        "Cisco Firepower ether:ErrStats:underSizeDelta
        managed object property"
    ::= { cfprEtherErrStatsEntry 44 }

cfprEtherErrStatsUnderSizeDeltaAvg OBJECT-TYPE
    SYNTAX       Unsigned64
    MAX-ACCESS   read-only
    STATUS       current
    DESCRIPTION
        "Cisco Firepower ether:ErrStats:underSizeDeltaAvg
        managed object property"
    ::= { cfprEtherErrStatsEntry 45 }

cfprEtherErrStatsUnderSizeDeltaMax OBJECT-TYPE
    SYNTAX       Unsigned64
    MAX-ACCESS   read-only
    STATUS       current
    DESCRIPTION
        "Cisco Firepower ether:ErrStats:underSizeDeltaMax
        managed object property"
    ::= { cfprEtherErrStatsEntry 46 }

cfprEtherErrStatsUnderSizeDeltaMin OBJECT-TYPE
    SYNTAX       Unsigned64
    MAX-ACCESS   read-only
    STATUS       current
    DESCRIPTION
        "Cisco Firepower ether:ErrStats:underSizeDeltaMin
        managed object property"
    ::= { cfprEtherErrStatsEntry 47 }

cfprEtherErrStatsUpdate OBJECT-TYPE
    SYNTAX       Gauge32
    MAX-ACCESS   read-only
    STATUS       current
    DESCRIPTION
        "Cisco Firepower ether:ErrStats:update managed object property"
    ::= { cfprEtherErrStatsEntry 48 }

cfprEtherErrStatsXmit OBJECT-TYPE
    SYNTAX       Unsigned64
    MAX-ACCESS   read-only
    STATUS       current
    DESCRIPTION
        "Cisco Firepower ether:ErrStats:xmit managed object property"
    ::= { cfprEtherErrStatsEntry 49 }

cfprEtherErrStatsXmitDelta OBJECT-TYPE
    SYNTAX       Counter64
    MAX-ACCESS   read-only
    STATUS       current
    DESCRIPTION
        "Cisco Firepower ether:ErrStats:xmitDelta managed object property"
    ::= { cfprEtherErrStatsEntry 50 }

cfprEtherErrStatsXmitDeltaAvg OBJECT-TYPE
    SYNTAX       Unsigned64
    MAX-ACCESS   read-only
    STATUS       current
    DESCRIPTION
        "Cisco Firepower ether:ErrStats:xmitDeltaAvg managed
        object property"
    ::= { cfprEtherErrStatsEntry 51 }

cfprEtherErrStatsXmitDeltaMax OBJECT-TYPE
    SYNTAX       Unsigned64
    MAX-ACCESS   read-only
    STATUS       current
    DESCRIPTION
        "Cisco Firepower ether:ErrStats:xmitDeltaMax managed
        object property"
    ::= { cfprEtherErrStatsEntry 52 }

cfprEtherErrStatsXmitDeltaMin OBJECT-TYPE
    SYNTAX       Unsigned64
    MAX-ACCESS   read-only
    STATUS       current
    DESCRIPTION
        "Cisco Firepower ether:ErrStats:xmitDeltaMin managed
        object property"
    ::= { cfprEtherErrStatsEntry 53 }

cfprEtherErrStatsHistTable OBJECT-TYPE
    SYNTAX           SEQUENCE OF CfprEtherErrStatsHistEntry
    MAX-ACCESS       not-accessible
    STATUS           current
    DESCRIPTION
        "Cisco Firepower ether:ErrStatsHist managed object table"
    ::= { cfprEtherObjects 2 }

cfprEtherErrStatsHistEntry OBJECT-TYPE
    SYNTAX           CfprEtherErrStatsHistEntry
    MAX-ACCESS       not-accessible
    STATUS           current
    DESCRIPTION
        "Entry for the cfprEtherErrStatsHistTable table."
    INDEX { cfprEtherErrStatsHistInstanceId }
    ::= { cfprEtherErrStatsHistTable 1 }

CfprEtherErrStatsHistEntry ::= SEQUENCE {
    cfprEtherErrStatsHistInstanceId                                  CfprManagedObjectId,
    cfprEtherErrStatsHistDn                                          CfprManagedObjectDn,
    cfprEtherErrStatsHistRn                                          SnmpAdminString,
    cfprEtherErrStatsHistAlign                                       Unsigned64,
    cfprEtherErrStatsHistAlignDelta                                  Unsigned64,
    cfprEtherErrStatsHistAlignDeltaAvg                               Unsigned64,
    cfprEtherErrStatsHistAlignDeltaMax                               Unsigned64,
    cfprEtherErrStatsHistAlignDeltaMin                               Unsigned64,
    cfprEtherErrStatsHistDeferredTx                                  Unsigned64,
    cfprEtherErrStatsHistDeferredTxDelta                             Unsigned64,
    cfprEtherErrStatsHistDeferredTxDeltaAvg                          Unsigned64,
    cfprEtherErrStatsHistDeferredTxDeltaMax                          Unsigned64,
    cfprEtherErrStatsHistDeferredTxDeltaMin                          Unsigned64,
    cfprEtherErrStatsHistFcs                                         Unsigned64,
    cfprEtherErrStatsHistFcsDelta                                    Unsigned64,
    cfprEtherErrStatsHistFcsDeltaAvg                                 Unsigned64,
    cfprEtherErrStatsHistFcsDeltaMax                                 Unsigned64,
    cfprEtherErrStatsHistFcsDeltaMin                                 Unsigned64,
    cfprEtherErrStatsHistId                                          Unsigned64,
    cfprEtherErrStatsHistIntMacRx                                    Unsigned64,
    cfprEtherErrStatsHistIntMacRxDelta                               Unsigned64,
    cfprEtherErrStatsHistIntMacRxDeltaAvg                            Unsigned64,
    cfprEtherErrStatsHistIntMacRxDeltaMax                            Unsigned64,
    cfprEtherErrStatsHistIntMacRxDeltaMin                            Unsigned64,
    cfprEtherErrStatsHistIntMacTx                                    Unsigned64,
    cfprEtherErrStatsHistIntMacTxDelta                               Unsigned64,
    cfprEtherErrStatsHistIntMacTxDeltaAvg                            Unsigned64,
    cfprEtherErrStatsHistIntMacTxDeltaMax                            Unsigned64,
    cfprEtherErrStatsHistIntMacTxDeltaMin                            Unsigned64,
    cfprEtherErrStatsHistMostRecent                                  TruthValue,
    cfprEtherErrStatsHistOutDiscard                                  Unsigned64,
    cfprEtherErrStatsHistOutDiscardDelta                             Unsigned64,
    cfprEtherErrStatsHistOutDiscardDeltaAvg                          Unsigned64,
    cfprEtherErrStatsHistOutDiscardDeltaMax                          Unsigned64,
    cfprEtherErrStatsHistOutDiscardDeltaMin                          Unsigned64,
    cfprEtherErrStatsHistRcv                                         Unsigned64,
    cfprEtherErrStatsHistRcvDelta                                    Unsigned64,
    cfprEtherErrStatsHistRcvDeltaAvg                                 Unsigned64,
    cfprEtherErrStatsHistRcvDeltaMax                                 Unsigned64,
    cfprEtherErrStatsHistRcvDeltaMin                                 Unsigned64,
    cfprEtherErrStatsHistSuspect                                     TruthValue,
    cfprEtherErrStatsHistThresholded                                 CfprEtherErrStatsHistThresholded,
    cfprEtherErrStatsHistTimeCollected                               DateAndTime,
    cfprEtherErrStatsHistUnderSize                                   Unsigned64,
    cfprEtherErrStatsHistUnderSizeDelta                              Unsigned64,
    cfprEtherErrStatsHistUnderSizeDeltaAvg                           Unsigned64,
    cfprEtherErrStatsHistUnderSizeDeltaMax                           Unsigned64,
    cfprEtherErrStatsHistUnderSizeDeltaMin                           Unsigned64,
    cfprEtherErrStatsHistXmit                                        Unsigned64,
    cfprEtherErrStatsHistXmitDelta                                   Unsigned64,
    cfprEtherErrStatsHistXmitDeltaAvg                                Unsigned64,
    cfprEtherErrStatsHistXmitDeltaMax                                Unsigned64,
    cfprEtherErrStatsHistXmitDeltaMin                                Unsigned64
}

cfprEtherErrStatsHistInstanceId OBJECT-TYPE
    SYNTAX       CfprManagedObjectId
    MAX-ACCESS   not-accessible
    STATUS       current
    DESCRIPTION
        "Instance identifier of the managed object."
    ::= { cfprEtherErrStatsHistEntry 1 }

cfprEtherErrStatsHistDn OBJECT-TYPE
    SYNTAX       CfprManagedObjectDn
    MAX-ACCESS   read-only
    STATUS       current
    DESCRIPTION
        "Cisco Firepower ether:ErrStatsHist:dn managed object property"
    ::= { cfprEtherErrStatsHistEntry 2 }

cfprEtherErrStatsHistRn OBJECT-TYPE
    SYNTAX       SnmpAdminString
    MAX-ACCESS   read-only
    STATUS       current
    DESCRIPTION
        "Cisco Firepower ether:ErrStatsHist:rn managed object property"
    ::= { cfprEtherErrStatsHistEntry 3 }

cfprEtherErrStatsHistAlign OBJECT-TYPE
    SYNTAX       Unsigned64
    MAX-ACCESS   read-only
    STATUS       current
    DESCRIPTION
        "Cisco Firepower ether:ErrStatsHist:align managed object property"
    ::= { cfprEtherErrStatsHistEntry 4 }

cfprEtherErrStatsHistAlignDelta OBJECT-TYPE
    SYNTAX       Unsigned64
    MAX-ACCESS   read-only
    STATUS       current
    DESCRIPTION
        "Cisco Firepower ether:ErrStatsHist:alignDelta
        managed object property"
    ::= { cfprEtherErrStatsHistEntry 5 }

cfprEtherErrStatsHistAlignDeltaAvg OBJECT-TYPE
    SYNTAX       Unsigned64
    MAX-ACCESS   read-only
    STATUS       current
    DESCRIPTION
        "Cisco Firepower ether:ErrStatsHist:alignDeltaAvg
        managed object property"
    ::= { cfprEtherErrStatsHistEntry 6 }

cfprEtherErrStatsHistAlignDeltaMax OBJECT-TYPE
    SYNTAX       Unsigned64
    MAX-ACCESS   read-only
    STATUS       current
    DESCRIPTION
        "Cisco Firepower ether:ErrStatsHist:alignDeltaMax
        managed object property"
    ::= { cfprEtherErrStatsHistEntry 7 }

cfprEtherErrStatsHistAlignDeltaMin OBJECT-TYPE
    SYNTAX       Unsigned64
    MAX-ACCESS   read-only
    STATUS       current
    DESCRIPTION
        "Cisco Firepower ether:ErrStatsHist:alignDeltaMin
        managed object property"
    ::= { cfprEtherErrStatsHistEntry 8 }

cfprEtherErrStatsHistDeferredTx OBJECT-TYPE
    SYNTAX       Unsigned64
    MAX-ACCESS   read-only
    STATUS       current
    DESCRIPTION
        "Cisco Firepower ether:ErrStatsHist:deferredTx
        managed object property"
    ::= { cfprEtherErrStatsHistEntry 9 }

cfprEtherErrStatsHistDeferredTxDelta OBJECT-TYPE
    SYNTAX       Unsigned64
    MAX-ACCESS   read-only
    STATUS       current
    DESCRIPTION
        "Cisco Firepower ether:ErrStatsHist:deferredTxDelta
        managed object property"
    ::= { cfprEtherErrStatsHistEntry 10 }

cfprEtherErrStatsHistDeferredTxDeltaAvg OBJECT-TYPE
    SYNTAX       Unsigned64
    MAX-ACCESS   read-only
    STATUS       current
    DESCRIPTION
        "Cisco Firepower ether:ErrStatsHist:deferredTxDeltaAvg
        managed object property"
    ::= { cfprEtherErrStatsHistEntry 11 }

cfprEtherErrStatsHistDeferredTxDeltaMax OBJECT-TYPE
    SYNTAX       Unsigned64
    MAX-ACCESS   read-only
    STATUS       current
    DESCRIPTION
        "Cisco Firepower ether:ErrStatsHist:deferredTxDeltaMax
        managed object property"
    ::= { cfprEtherErrStatsHistEntry 12 }

cfprEtherErrStatsHistDeferredTxDeltaMin OBJECT-TYPE
    SYNTAX       Unsigned64
    MAX-ACCESS   read-only
    STATUS       current
    DESCRIPTION
        "Cisco Firepower ether:ErrStatsHist:deferredTxDeltaMin
        managed object property"
    ::= { cfprEtherErrStatsHistEntry 13 }

cfprEtherErrStatsHistFcs OBJECT-TYPE
    SYNTAX       Unsigned64
    MAX-ACCESS   read-only
    STATUS       current
    DESCRIPTION
        "Cisco Firepower ether:ErrStatsHist:fcs managed object property"
    ::= { cfprEtherErrStatsHistEntry 14 }

cfprEtherErrStatsHistFcsDelta OBJECT-TYPE
    SYNTAX       Unsigned64
    MAX-ACCESS   read-only
    STATUS       current
    DESCRIPTION
        "Cisco Firepower ether:ErrStatsHist:fcsDelta managed
        object property"
    ::= { cfprEtherErrStatsHistEntry 15 }

cfprEtherErrStatsHistFcsDeltaAvg OBJECT-TYPE
    SYNTAX       Unsigned64
    MAX-ACCESS   read-only
    STATUS       current
    DESCRIPTION
        "Cisco Firepower ether:ErrStatsHist:fcsDeltaAvg
        managed object property"
    ::= { cfprEtherErrStatsHistEntry 16 }

cfprEtherErrStatsHistFcsDeltaMax OBJECT-TYPE
    SYNTAX       Unsigned64
    MAX-ACCESS   read-only
    STATUS       current
    DESCRIPTION
        "Cisco Firepower ether:ErrStatsHist:fcsDeltaMax
        managed object property"
    ::= { cfprEtherErrStatsHistEntry 17 }

cfprEtherErrStatsHistFcsDeltaMin OBJECT-TYPE
    SYNTAX       Unsigned64
    MAX-ACCESS   read-only
    STATUS       current
    DESCRIPTION
        "Cisco Firepower ether:ErrStatsHist:fcsDeltaMin
        managed object property"
    ::= { cfprEtherErrStatsHistEntry 18 }

cfprEtherErrStatsHistId OBJECT-TYPE
    SYNTAX       Unsigned64
    MAX-ACCESS   read-only
    STATUS       current
    DESCRIPTION
        "Cisco Firepower ether:ErrStatsHist:id managed object property"
    ::= { cfprEtherErrStatsHistEntry 19 }

cfprEtherErrStatsHistIntMacRx OBJECT-TYPE
    SYNTAX       Unsigned64
    MAX-ACCESS   read-only
    STATUS       current
    DESCRIPTION
        "Cisco Firepower ether:ErrStatsHist:intMacRx managed
        object property"
    ::= { cfprEtherErrStatsHistEntry 20 }

cfprEtherErrStatsHistIntMacRxDelta OBJECT-TYPE
    SYNTAX       Unsigned64
    MAX-ACCESS   read-only
    STATUS       current
    DESCRIPTION
        "Cisco Firepower ether:ErrStatsHist:intMacRxDelta
        managed object property"
    ::= { cfprEtherErrStatsHistEntry 21 }

cfprEtherErrStatsHistIntMacRxDeltaAvg OBJECT-TYPE
    SYNTAX       Unsigned64
    MAX-ACCESS   read-only
    STATUS       current
    DESCRIPTION
        "Cisco Firepower ether:ErrStatsHist:intMacRxDeltaAvg
        managed object property"
    ::= { cfprEtherErrStatsHistEntry 22 }

cfprEtherErrStatsHistIntMacRxDeltaMax OBJECT-TYPE
    SYNTAX       Unsigned64
    MAX-ACCESS   read-only
    STATUS       current
    DESCRIPTION
        "Cisco Firepower ether:ErrStatsHist:intMacRxDeltaMax
        managed object property"
    ::= { cfprEtherErrStatsHistEntry 23 }

cfprEtherErrStatsHistIntMacRxDeltaMin OBJECT-TYPE
    SYNTAX       Unsigned64
    MAX-ACCESS   read-only
    STATUS       current
    DESCRIPTION
        "Cisco Firepower ether:ErrStatsHist:intMacRxDeltaMin
        managed object property"
    ::= { cfprEtherErrStatsHistEntry 24 }

cfprEtherErrStatsHistIntMacTx OBJECT-TYPE
    SYNTAX       Unsigned64
    MAX-ACCESS   read-only
    STATUS       current
    DESCRIPTION
        "Cisco Firepower ether:ErrStatsHist:intMacTx managed
        object property"
    ::= { cfprEtherErrStatsHistEntry 25 }

cfprEtherErrStatsHistIntMacTxDelta OBJECT-TYPE
    SYNTAX       Unsigned64
    MAX-ACCESS   read-only
    STATUS       current
    DESCRIPTION
        "Cisco Firepower ether:ErrStatsHist:intMacTxDelta
        managed object property"
    ::= { cfprEtherErrStatsHistEntry 26 }

cfprEtherErrStatsHistIntMacTxDeltaAvg OBJECT-TYPE
    SYNTAX       Unsigned64
    MAX-ACCESS   read-only
    STATUS       current
    DESCRIPTION
        "Cisco Firepower ether:ErrStatsHist:intMacTxDeltaAvg
        managed object property"
    ::= { cfprEtherErrStatsHistEntry 27 }

cfprEtherErrStatsHistIntMacTxDeltaMax OBJECT-TYPE
    SYNTAX       Unsigned64
    MAX-ACCESS   read-only
    STATUS       current
    DESCRIPTION
        "Cisco Firepower ether:ErrStatsHist:intMacTxDeltaMax
        managed object property"
    ::= { cfprEtherErrStatsHistEntry 28 }

cfprEtherErrStatsHistIntMacTxDeltaMin OBJECT-TYPE
    SYNTAX       Unsigned64
    MAX-ACCESS   read-only
    STATUS       current
    DESCRIPTION
        "Cisco Firepower ether:ErrStatsHist:intMacTxDeltaMin
        managed object property"
    ::= { cfprEtherErrStatsHistEntry 29 }

cfprEtherErrStatsHistMostRecent OBJECT-TYPE
    SYNTAX       TruthValue
    MAX-ACCESS   read-only
    STATUS       current
    DESCRIPTION
        "Cisco Firepower ether:ErrStatsHist:mostRecent
        managed object property"
    ::= { cfprEtherErrStatsHistEntry 30 }

cfprEtherErrStatsHistOutDiscard OBJECT-TYPE
    SYNTAX       Unsigned64
    MAX-ACCESS   read-only
    STATUS       current
    DESCRIPTION
        "Cisco Firepower ether:ErrStatsHist:outDiscard
        managed object property"
    ::= { cfprEtherErrStatsHistEntry 31 }

cfprEtherErrStatsHistOutDiscardDelta OBJECT-TYPE
    SYNTAX       Unsigned64
    MAX-ACCESS   read-only
    STATUS       current
    DESCRIPTION
        "Cisco Firepower ether:ErrStatsHist:outDiscardDelta
        managed object property"
    ::= { cfprEtherErrStatsHistEntry 32 }

cfprEtherErrStatsHistOutDiscardDeltaAvg OBJECT-TYPE
    SYNTAX       Unsigned64
    MAX-ACCESS   read-only
    STATUS       current
    DESCRIPTION
        "Cisco Firepower ether:ErrStatsHist:outDiscardDeltaAvg
        managed object property"
    ::= { cfprEtherErrStatsHistEntry 33 }

cfprEtherErrStatsHistOutDiscardDeltaMax OBJECT-TYPE
    SYNTAX       Unsigned64
    MAX-ACCESS   read-only
    STATUS       current
    DESCRIPTION
        "Cisco Firepower ether:ErrStatsHist:outDiscardDeltaMax
        managed object property"
    ::= { cfprEtherErrStatsHistEntry 34 }

cfprEtherErrStatsHistOutDiscardDeltaMin OBJECT-TYPE
    SYNTAX       Unsigned64
    MAX-ACCESS   read-only
    STATUS       current
    DESCRIPTION
        "Cisco Firepower ether:ErrStatsHist:outDiscardDeltaMin
        managed object property"
    ::= { cfprEtherErrStatsHistEntry 35 }

cfprEtherErrStatsHistRcv OBJECT-TYPE
    SYNTAX       Unsigned64
    MAX-ACCESS   read-only
    STATUS       current
    DESCRIPTION
        "Cisco Firepower ether:ErrStatsHist:rcv managed object property"
    ::= { cfprEtherErrStatsHistEntry 36 }

cfprEtherErrStatsHistRcvDelta OBJECT-TYPE
    SYNTAX       Unsigned64
    MAX-ACCESS   read-only
    STATUS       current
    DESCRIPTION
        "Cisco Firepower ether:ErrStatsHist:rcvDelta managed
        object property"
    ::= { cfprEtherErrStatsHistEntry 37 }

cfprEtherErrStatsHistRcvDeltaAvg OBJECT-TYPE
    SYNTAX       Unsigned64
    MAX-ACCESS   read-only
    STATUS       current
    DESCRIPTION
        "Cisco Firepower ether:ErrStatsHist:rcvDeltaAvg
        managed object property"
    ::= { cfprEtherErrStatsHistEntry 38 }

cfprEtherErrStatsHistRcvDeltaMax OBJECT-TYPE
    SYNTAX       Unsigned64
    MAX-ACCESS   read-only
    STATUS       current
    DESCRIPTION
        "Cisco Firepower ether:ErrStatsHist:rcvDeltaMax
        managed object property"
    ::= { cfprEtherErrStatsHistEntry 39 }

cfprEtherErrStatsHistRcvDeltaMin OBJECT-TYPE
    SYNTAX       Unsigned64
    MAX-ACCESS   read-only
    STATUS       current
    DESCRIPTION
        "Cisco Firepower ether:ErrStatsHist:rcvDeltaMin
        managed object property"
    ::= { cfprEtherErrStatsHistEntry 40 }

cfprEtherErrStatsHistSuspect OBJECT-TYPE
    SYNTAX       TruthValue
    MAX-ACCESS   read-only
    STATUS       current
    DESCRIPTION
        "Cisco Firepower ether:ErrStatsHist:suspect managed
        object property"
    ::= { cfprEtherErrStatsHistEntry 41 }

cfprEtherErrStatsHistThresholded OBJECT-TYPE
    SYNTAX       CfprEtherErrStatsHistThresholded
    MAX-ACCESS   read-only
    STATUS       current
    DESCRIPTION
        "Cisco Firepower ether:ErrStatsHist:thresholded
        managed object property"
    ::= { cfprEtherErrStatsHistEntry 42 }

cfprEtherErrStatsHistTimeCollected OBJECT-TYPE
    SYNTAX       DateAndTime
    MAX-ACCESS   read-only
    STATUS       current
    DESCRIPTION
        "Cisco Firepower ether:ErrStatsHist:timeCollected
        managed object property"
    ::= { cfprEtherErrStatsHistEntry 43 }

cfprEtherErrStatsHistUnderSize OBJECT-TYPE
    SYNTAX       Unsigned64
    MAX-ACCESS   read-only
    STATUS       current
    DESCRIPTION
        "Cisco Firepower ether:ErrStatsHist:underSize managed
        object property"
    ::= { cfprEtherErrStatsHistEntry 44 }

cfprEtherErrStatsHistUnderSizeDelta OBJECT-TYPE
    SYNTAX       Unsigned64
    MAX-ACCESS   read-only
    STATUS       current
    DESCRIPTION
        "Cisco Firepower ether:ErrStatsHist:underSizeDelta
        managed object property"
    ::= { cfprEtherErrStatsHistEntry 45 }

cfprEtherErrStatsHistUnderSizeDeltaAvg OBJECT-TYPE
    SYNTAX       Unsigned64
    MAX-ACCESS   read-only
    STATUS       current
    DESCRIPTION
        "Cisco Firepower ether:ErrStatsHist:underSizeDeltaAvg
        managed object property"
    ::= { cfprEtherErrStatsHistEntry 46 }

cfprEtherErrStatsHistUnderSizeDeltaMax OBJECT-TYPE
    SYNTAX       Unsigned64
    MAX-ACCESS   read-only
    STATUS       current
    DESCRIPTION
        "Cisco Firepower ether:ErrStatsHist:underSizeDeltaMax
        managed object property"
    ::= { cfprEtherErrStatsHistEntry 47 }

cfprEtherErrStatsHistUnderSizeDeltaMin OBJECT-TYPE
    SYNTAX       Unsigned64
    MAX-ACCESS   read-only
    STATUS       current
    DESCRIPTION
        "Cisco Firepower ether:ErrStatsHist:underSizeDeltaMin
        managed object property"
    ::= { cfprEtherErrStatsHistEntry 48 }

cfprEtherErrStatsHistXmit OBJECT-TYPE
    SYNTAX       Unsigned64
    MAX-ACCESS   read-only
    STATUS       current
    DESCRIPTION
        "Cisco Firepower ether:ErrStatsHist:xmit managed object property"
    ::= { cfprEtherErrStatsHistEntry 49 }

cfprEtherErrStatsHistXmitDelta OBJECT-TYPE
    SYNTAX       Unsigned64
    MAX-ACCESS   read-only
    STATUS       current
    DESCRIPTION
        "Cisco Firepower ether:ErrStatsHist:xmitDelta managed
        object property"
    ::= { cfprEtherErrStatsHistEntry 50 }

cfprEtherErrStatsHistXmitDeltaAvg OBJECT-TYPE
    SYNTAX       Unsigned64
    MAX-ACCESS   read-only
    STATUS       current
    DESCRIPTION
        "Cisco Firepower ether:ErrStatsHist:xmitDeltaAvg
        managed object property"
    ::= { cfprEtherErrStatsHistEntry 51 }

cfprEtherErrStatsHistXmitDeltaMax OBJECT-TYPE
    SYNTAX       Unsigned64
    MAX-ACCESS   read-only
    STATUS       current
    DESCRIPTION
        "Cisco Firepower ether:ErrStatsHist:xmitDeltaMax
        managed object property"
    ::= { cfprEtherErrStatsHistEntry 52 }

cfprEtherErrStatsHistXmitDeltaMin OBJECT-TYPE
    SYNTAX       Unsigned64
    MAX-ACCESS   read-only
    STATUS       current
    DESCRIPTION
        "Cisco Firepower ether:ErrStatsHist:xmitDeltaMin
        managed object property"
    ::= { cfprEtherErrStatsHistEntry 53 }

cfprEtherFailToWireTable OBJECT-TYPE
    SYNTAX           SEQUENCE OF CfprEtherFailToWireEntry
    MAX-ACCESS       not-accessible
    STATUS           current
    DESCRIPTION
        "Cisco Firepower ether:FailToWire managed object table"
    ::= { cfprEtherObjects 32 }

cfprEtherFailToWireEntry OBJECT-TYPE
    SYNTAX           CfprEtherFailToWireEntry
    MAX-ACCESS       not-accessible
    STATUS           current
    DESCRIPTION
        "Entry for the cfprEtherFailToWireTable table."
    INDEX { cfprEtherFailToWireInstanceId }
    ::= { cfprEtherFailToWireTable 1 }

CfprEtherFailToWireEntry ::= SEQUENCE {
    cfprEtherFailToWireInstanceId                                    CfprManagedObjectId,
    cfprEtherFailToWireDn                                            CfprManagedObjectDn,
    cfprEtherFailToWireRn                                            SnmpAdminString,
    cfprEtherFailToWireLocale                                        CfprNetworkLocale,
    cfprEtherFailToWireName                                          SnmpAdminString,
    cfprEtherFailToWireTransport                                     CfprNetworkTransport,
    cfprEtherFailToWireType                                          CfprNetworkConnectionType
}

cfprEtherFailToWireInstanceId OBJECT-TYPE
    SYNTAX       CfprManagedObjectId
    MAX-ACCESS   not-accessible
    STATUS       current
    DESCRIPTION
        "Instance identifier of the managed object."
    ::= { cfprEtherFailToWireEntry 1 }

cfprEtherFailToWireDn OBJECT-TYPE
    SYNTAX       CfprManagedObjectDn
    MAX-ACCESS   read-only
    STATUS       current
    DESCRIPTION
        "Cisco Firepower ether:FailToWire:dn managed object property"
    ::= { cfprEtherFailToWireEntry 2 }

cfprEtherFailToWireRn OBJECT-TYPE
    SYNTAX       SnmpAdminString
    MAX-ACCESS   read-only
    STATUS       current
    DESCRIPTION
        "Cisco Firepower ether:FailToWire:rn managed object property"
    ::= { cfprEtherFailToWireEntry 3 }

cfprEtherFailToWireLocale OBJECT-TYPE
    SYNTAX       CfprNetworkLocale
    MAX-ACCESS   read-only
    STATUS       current
    DESCRIPTION
        "Cisco Firepower ether:FailToWire:locale managed object property"
    ::= { cfprEtherFailToWireEntry 4 }

cfprEtherFailToWireName OBJECT-TYPE
    SYNTAX       SnmpAdminString
    MAX-ACCESS   read-only
    STATUS       current
    DESCRIPTION
        "Cisco Firepower ether:FailToWire:name managed object property"
    ::= { cfprEtherFailToWireEntry 5 }

cfprEtherFailToWireTransport OBJECT-TYPE
    SYNTAX       CfprNetworkTransport
    MAX-ACCESS   read-only
    STATUS       current
    DESCRIPTION
        "Cisco Firepower ether:FailToWire:transport managed
        object property"
    ::= { cfprEtherFailToWireEntry 6 }

cfprEtherFailToWireType OBJECT-TYPE
    SYNTAX       CfprNetworkConnectionType
    MAX-ACCESS   read-only
    STATUS       current
    DESCRIPTION
        "Cisco Firepower ether:FailToWire:type managed object property"
    ::= { cfprEtherFailToWireEntry 7 }

cfprEtherFcoeInterfaceStatsTable OBJECT-TYPE
    SYNTAX           SEQUENCE OF CfprEtherFcoeInterfaceStatsEntry
    MAX-ACCESS       not-accessible
    STATUS           current
    DESCRIPTION
        "Cisco Firepower ether:FcoeInterfaceStats managed object table"
    ::= { cfprEtherObjects 3 }

cfprEtherFcoeInterfaceStatsEntry OBJECT-TYPE
    SYNTAX           CfprEtherFcoeInterfaceStatsEntry
    MAX-ACCESS       not-accessible
    STATUS           current
    DESCRIPTION
        "Entry for the cfprEtherFcoeInterfaceStatsTable table."
    INDEX { cfprEtherFcoeInterfaceStatsInstanceId }
    ::= { cfprEtherFcoeInterfaceStatsTable 1 }

CfprEtherFcoeInterfaceStatsEntry ::= SEQUENCE {
    cfprEtherFcoeInterfaceStatsInstanceId                            CfprManagedObjectId,
    cfprEtherFcoeInterfaceStatsDn                                    CfprManagedObjectDn,
    cfprEtherFcoeInterfaceStatsRn                                    SnmpAdminString,
    cfprEtherFcoeInterfaceStatsBytesRx                               Unsigned64,
    cfprEtherFcoeInterfaceStatsBytesRxDelta                          Counter64,
    cfprEtherFcoeInterfaceStatsBytesRxDeltaAvg                       Unsigned64,
    cfprEtherFcoeInterfaceStatsBytesRxDeltaMax                       Unsigned64,
    cfprEtherFcoeInterfaceStatsBytesRxDeltaMin                       Unsigned64,
    cfprEtherFcoeInterfaceStatsBytesTx                               Unsigned64,
    cfprEtherFcoeInterfaceStatsBytesTxDelta                          Counter64,
    cfprEtherFcoeInterfaceStatsBytesTxDeltaAvg                       Unsigned64,
    cfprEtherFcoeInterfaceStatsBytesTxDeltaMax                       Unsigned64,
    cfprEtherFcoeInterfaceStatsBytesTxDeltaMin                       Unsigned64,
    cfprEtherFcoeInterfaceStatsDroppedRx                             Unsigned64,
    cfprEtherFcoeInterfaceStatsDroppedRxDelta                        Counter64,
    cfprEtherFcoeInterfaceStatsDroppedRxDeltaAvg                     Unsigned64,
    cfprEtherFcoeInterfaceStatsDroppedRxDeltaMax                     Unsigned64,
    cfprEtherFcoeInterfaceStatsDroppedRxDeltaMin                     Unsigned64,
    cfprEtherFcoeInterfaceStatsDroppedTx                             Unsigned64,
    cfprEtherFcoeInterfaceStatsDroppedTxDelta                        Counter64,
    cfprEtherFcoeInterfaceStatsDroppedTxDeltaAvg                     Unsigned64,
    cfprEtherFcoeInterfaceStatsDroppedTxDeltaMax                     Unsigned64,
    cfprEtherFcoeInterfaceStatsDroppedTxDeltaMin                     Unsigned64,
    cfprEtherFcoeInterfaceStatsErrorsRx                              Unsigned64,
    cfprEtherFcoeInterfaceStatsErrorsRxDelta                         Counter64,
    cfprEtherFcoeInterfaceStatsErrorsRxDeltaAvg                      Unsigned64,
    cfprEtherFcoeInterfaceStatsErrorsRxDeltaMax                      Unsigned64,
    cfprEtherFcoeInterfaceStatsErrorsRxDeltaMin                      Unsigned64,
    cfprEtherFcoeInterfaceStatsErrorsTx                              Unsigned64,
    cfprEtherFcoeInterfaceStatsErrorsTxDelta                         Counter64,
    cfprEtherFcoeInterfaceStatsErrorsTxDeltaAvg                      Unsigned64,
    cfprEtherFcoeInterfaceStatsErrorsTxDeltaMax                      Unsigned64,
    cfprEtherFcoeInterfaceStatsErrorsTxDeltaMin                      Unsigned64,
    cfprEtherFcoeInterfaceStatsIntervals                             Gauge32,
    cfprEtherFcoeInterfaceStatsPacketsRx                             Unsigned64,
    cfprEtherFcoeInterfaceStatsPacketsRxDelta                        Counter64,
    cfprEtherFcoeInterfaceStatsPacketsRxDeltaAvg                     Unsigned64,
    cfprEtherFcoeInterfaceStatsPacketsRxDeltaMax                     Unsigned64,
    cfprEtherFcoeInterfaceStatsPacketsRxDeltaMin                     Unsigned64,
    cfprEtherFcoeInterfaceStatsPacketsTx                             Unsigned64,
    cfprEtherFcoeInterfaceStatsPacketsTxDelta                        Counter64,
    cfprEtherFcoeInterfaceStatsPacketsTxDeltaAvg                     Unsigned64,
    cfprEtherFcoeInterfaceStatsPacketsTxDeltaMax                     Unsigned64,
    cfprEtherFcoeInterfaceStatsPacketsTxDeltaMin                     Unsigned64,
    cfprEtherFcoeInterfaceStatsSuspect                               TruthValue,
    cfprEtherFcoeInterfaceStatsThresholded                           CfprEtherFcoeInterfaceStatsThresholded,
    cfprEtherFcoeInterfaceStatsTimeCollected                         DateAndTime,
    cfprEtherFcoeInterfaceStatsUpdate                                Gauge32
}

cfprEtherFcoeInterfaceStatsInstanceId OBJECT-TYPE
    SYNTAX       CfprManagedObjectId
    MAX-ACCESS   not-accessible
    STATUS       current
    DESCRIPTION
        "Instance identifier of the managed object."
    ::= { cfprEtherFcoeInterfaceStatsEntry 1 }

cfprEtherFcoeInterfaceStatsDn OBJECT-TYPE
    SYNTAX       CfprManagedObjectDn
    MAX-ACCESS   read-only
    STATUS       current
    DESCRIPTION
        "Cisco Firepower ether:FcoeInterfaceStats:dn managed
        object property"
    ::= { cfprEtherFcoeInterfaceStatsEntry 2 }

cfprEtherFcoeInterfaceStatsRn OBJECT-TYPE
    SYNTAX       SnmpAdminString
    MAX-ACCESS   read-only
    STATUS       current
    DESCRIPTION
        "Cisco Firepower ether:FcoeInterfaceStats:rn managed
        object property"
    ::= { cfprEtherFcoeInterfaceStatsEntry 3 }

cfprEtherFcoeInterfaceStatsBytesRx OBJECT-TYPE
    SYNTAX       Unsigned64
    MAX-ACCESS   read-only
    STATUS       current
    DESCRIPTION
        "Cisco Firepower ether:FcoeInterfaceStats:bytesRx
        managed object property"
    ::= { cfprEtherFcoeInterfaceStatsEntry 4 }

cfprEtherFcoeInterfaceStatsBytesRxDelta OBJECT-TYPE
    SYNTAX       Counter64
    MAX-ACCESS   read-only
    STATUS       current
    DESCRIPTION
        "Cisco Firepower ether:FcoeInterfaceStats:bytesRxDelta
        managed object property"
    ::= { cfprEtherFcoeInterfaceStatsEntry 5 }

cfprEtherFcoeInterfaceStatsBytesRxDeltaAvg OBJECT-TYPE
    SYNTAX       Unsigned64
    MAX-ACCESS   read-only
    STATUS       current
    DESCRIPTION
        "Cisco Firepower ether:FcoeInterfaceStats:bytesRxDeltaAvg
        managed object property"
    ::= { cfprEtherFcoeInterfaceStatsEntry 6 }

cfprEtherFcoeInterfaceStatsBytesRxDeltaMax OBJECT-TYPE
    SYNTAX       Unsigned64
    MAX-ACCESS   read-only
    STATUS       current
    DESCRIPTION
        "Cisco Firepower ether:FcoeInterfaceStats:bytesRxDeltaMax
        managed object property"
    ::= { cfprEtherFcoeInterfaceStatsEntry 7 }

cfprEtherFcoeInterfaceStatsBytesRxDeltaMin OBJECT-TYPE
    SYNTAX       Unsigned64
    MAX-ACCESS   read-only
    STATUS       current
    DESCRIPTION
        "Cisco Firepower ether:FcoeInterfaceStats:bytesRxDeltaMin
        managed object property"
    ::= { cfprEtherFcoeInterfaceStatsEntry 8 }

cfprEtherFcoeInterfaceStatsBytesTx OBJECT-TYPE
    SYNTAX       Unsigned64
    MAX-ACCESS   read-only
    STATUS       current
    DESCRIPTION
        "Cisco Firepower ether:FcoeInterfaceStats:bytesTx
        managed object property"
    ::= { cfprEtherFcoeInterfaceStatsEntry 9 }

cfprEtherFcoeInterfaceStatsBytesTxDelta OBJECT-TYPE
    SYNTAX       Counter64
    MAX-ACCESS   read-only
    STATUS       current
    DESCRIPTION
        "Cisco Firepower ether:FcoeInterfaceStats:bytesTxDelta
        managed object property"
    ::= { cfprEtherFcoeInterfaceStatsEntry 10 }

cfprEtherFcoeInterfaceStatsBytesTxDeltaAvg OBJECT-TYPE
    SYNTAX       Unsigned64
    MAX-ACCESS   read-only
    STATUS       current
    DESCRIPTION
        "Cisco Firepower ether:FcoeInterfaceStats:bytesTxDeltaAvg
        managed object property"
    ::= { cfprEtherFcoeInterfaceStatsEntry 11 }

cfprEtherFcoeInterfaceStatsBytesTxDeltaMax OBJECT-TYPE
    SYNTAX       Unsigned64
    MAX-ACCESS   read-only
    STATUS       current
    DESCRIPTION
        "Cisco Firepower ether:FcoeInterfaceStats:bytesTxDeltaMax
        managed object property"
    ::= { cfprEtherFcoeInterfaceStatsEntry 12 }

cfprEtherFcoeInterfaceStatsBytesTxDeltaMin OBJECT-TYPE
    SYNTAX       Unsigned64
    MAX-ACCESS   read-only
    STATUS       current
    DESCRIPTION
        "Cisco Firepower ether:FcoeInterfaceStats:bytesTxDeltaMin
        managed object property"
    ::= { cfprEtherFcoeInterfaceStatsEntry 13 }

cfprEtherFcoeInterfaceStatsDroppedRx OBJECT-TYPE
    SYNTAX       Unsigned64
    MAX-ACCESS   read-only
    STATUS       current
    DESCRIPTION
        "Cisco Firepower ether:FcoeInterfaceStats:droppedRx
        managed object property"
    ::= { cfprEtherFcoeInterfaceStatsEntry 14 }

cfprEtherFcoeInterfaceStatsDroppedRxDelta OBJECT-TYPE
    SYNTAX       Counter64
    MAX-ACCESS   read-only
    STATUS       current
    DESCRIPTION
        "Cisco Firepower ether:FcoeInterfaceStats:droppedRxDelta
        managed object property"
    ::= { cfprEtherFcoeInterfaceStatsEntry 15 }

cfprEtherFcoeInterfaceStatsDroppedRxDeltaAvg OBJECT-TYPE
    SYNTAX       Unsigned64
    MAX-ACCESS   read-only
    STATUS       current
    DESCRIPTION
        "Cisco Firepower ether:FcoeInterfaceStats:droppedRxDeltaAvg
        managed object property"
    ::= { cfprEtherFcoeInterfaceStatsEntry 16 }

cfprEtherFcoeInterfaceStatsDroppedRxDeltaMax OBJECT-TYPE
    SYNTAX       Unsigned64
    MAX-ACCESS   read-only
    STATUS       current
    DESCRIPTION
        "Cisco Firepower ether:FcoeInterfaceStats:droppedRxDeltaMax
        managed object property"
    ::= { cfprEtherFcoeInterfaceStatsEntry 17 }

cfprEtherFcoeInterfaceStatsDroppedRxDeltaMin OBJECT-TYPE
    SYNTAX       Unsigned64
    MAX-ACCESS   read-only
    STATUS       current
    DESCRIPTION
        "Cisco Firepower ether:FcoeInterfaceStats:droppedRxDeltaMin
        managed object property"
    ::= { cfprEtherFcoeInterfaceStatsEntry 18 }

cfprEtherFcoeInterfaceStatsDroppedTx OBJECT-TYPE
    SYNTAX       Unsigned64
    MAX-ACCESS   read-only
    STATUS       current
    DESCRIPTION
        "Cisco Firepower ether:FcoeInterfaceStats:droppedTx
        managed object property"
    ::= { cfprEtherFcoeInterfaceStatsEntry 19 }

cfprEtherFcoeInterfaceStatsDroppedTxDelta OBJECT-TYPE
    SYNTAX       Counter64
    MAX-ACCESS   read-only
    STATUS       current
    DESCRIPTION
        "Cisco Firepower ether:FcoeInterfaceStats:droppedTxDelta
        managed object property"
    ::= { cfprEtherFcoeInterfaceStatsEntry 20 }

cfprEtherFcoeInterfaceStatsDroppedTxDeltaAvg OBJECT-TYPE
    SYNTAX       Unsigned64
    MAX-ACCESS   read-only
    STATUS       current
    DESCRIPTION
        "Cisco Firepower ether:FcoeInterfaceStats:droppedTxDeltaAvg
        managed object property"
    ::= { cfprEtherFcoeInterfaceStatsEntry 21 }

cfprEtherFcoeInterfaceStatsDroppedTxDeltaMax OBJECT-TYPE
    SYNTAX       Unsigned64
    MAX-ACCESS   read-only
    STATUS       current
    DESCRIPTION
        "Cisco Firepower ether:FcoeInterfaceStats:droppedTxDeltaMax
        managed object property"
    ::= { cfprEtherFcoeInterfaceStatsEntry 22 }

cfprEtherFcoeInterfaceStatsDroppedTxDeltaMin OBJECT-TYPE
    SYNTAX       Unsigned64
    MAX-ACCESS   read-only
    STATUS       current
    DESCRIPTION
        "Cisco Firepower ether:FcoeInterfaceStats:droppedTxDeltaMin
        managed object property"
    ::= { cfprEtherFcoeInterfaceStatsEntry 23 }

cfprEtherFcoeInterfaceStatsErrorsRx OBJECT-TYPE
    SYNTAX       Unsigned64
    MAX-ACCESS   read-only
    STATUS       current
    DESCRIPTION
        "Cisco Firepower ether:FcoeInterfaceStats:errorsRx
        managed object property"
    ::= { cfprEtherFcoeInterfaceStatsEntry 24 }

cfprEtherFcoeInterfaceStatsErrorsRxDelta OBJECT-TYPE
    SYNTAX       Counter64
    MAX-ACCESS   read-only
    STATUS       current
    DESCRIPTION
        "Cisco Firepower ether:FcoeInterfaceStats:errorsRxDelta
        managed object property"
    ::= { cfprEtherFcoeInterfaceStatsEntry 25 }

cfprEtherFcoeInterfaceStatsErrorsRxDeltaAvg OBJECT-TYPE
    SYNTAX       Unsigned64
    MAX-ACCESS   read-only
    STATUS       current
    DESCRIPTION
        "Cisco Firepower ether:FcoeInterfaceStats:errorsRxDeltaAvg
        managed object property"
    ::= { cfprEtherFcoeInterfaceStatsEntry 26 }

cfprEtherFcoeInterfaceStatsErrorsRxDeltaMax OBJECT-TYPE
    SYNTAX       Unsigned64
    MAX-ACCESS   read-only
    STATUS       current
    DESCRIPTION
        "Cisco Firepower ether:FcoeInterfaceStats:errorsRxDeltaMax
        managed object property"
    ::= { cfprEtherFcoeInterfaceStatsEntry 27 }

cfprEtherFcoeInterfaceStatsErrorsRxDeltaMin OBJECT-TYPE
    SYNTAX       Unsigned64
    MAX-ACCESS   read-only
    STATUS       current
    DESCRIPTION
        "Cisco Firepower ether:FcoeInterfaceStats:errorsRxDeltaMin
        managed object property"
    ::= { cfprEtherFcoeInterfaceStatsEntry 28 }

cfprEtherFcoeInterfaceStatsErrorsTx OBJECT-TYPE
    SYNTAX       Unsigned64
    MAX-ACCESS   read-only
    STATUS       current
    DESCRIPTION
        "Cisco Firepower ether:FcoeInterfaceStats:errorsTx
        managed object property"
    ::= { cfprEtherFcoeInterfaceStatsEntry 29 }

cfprEtherFcoeInterfaceStatsErrorsTxDelta OBJECT-TYPE
    SYNTAX       Counter64
    MAX-ACCESS   read-only
    STATUS       current
    DESCRIPTION
        "Cisco Firepower ether:FcoeInterfaceStats:errorsTxDelta
        managed object property"
    ::= { cfprEtherFcoeInterfaceStatsEntry 30 }

cfprEtherFcoeInterfaceStatsErrorsTxDeltaAvg OBJECT-TYPE
    SYNTAX       Unsigned64
    MAX-ACCESS   read-only
    STATUS       current
    DESCRIPTION
        "Cisco Firepower ether:FcoeInterfaceStats:errorsTxDeltaAvg
        managed object property"
    ::= { cfprEtherFcoeInterfaceStatsEntry 31 }

cfprEtherFcoeInterfaceStatsErrorsTxDeltaMax OBJECT-TYPE
    SYNTAX       Unsigned64
    MAX-ACCESS   read-only
    STATUS       current
    DESCRIPTION
        "Cisco Firepower ether:FcoeInterfaceStats:errorsTxDeltaMax
        managed object property"
    ::= { cfprEtherFcoeInterfaceStatsEntry 32 }

cfprEtherFcoeInterfaceStatsErrorsTxDeltaMin OBJECT-TYPE
    SYNTAX       Unsigned64
    MAX-ACCESS   read-only
    STATUS       current
    DESCRIPTION
        "Cisco Firepower ether:FcoeInterfaceStats:errorsTxDeltaMin
        managed object property"
    ::= { cfprEtherFcoeInterfaceStatsEntry 33 }

cfprEtherFcoeInterfaceStatsIntervals OBJECT-TYPE
    SYNTAX       Gauge32
    MAX-ACCESS   read-only
    STATUS       current
    DESCRIPTION
        "Cisco Firepower ether:FcoeInterfaceStats:intervals
        managed object property"
    ::= { cfprEtherFcoeInterfaceStatsEntry 34 }

cfprEtherFcoeInterfaceStatsPacketsRx OBJECT-TYPE
    SYNTAX       Unsigned64
    MAX-ACCESS   read-only
    STATUS       current
    DESCRIPTION
        "Cisco Firepower ether:FcoeInterfaceStats:packetsRx
        managed object property"
    ::= { cfprEtherFcoeInterfaceStatsEntry 35 }

cfprEtherFcoeInterfaceStatsPacketsRxDelta OBJECT-TYPE
    SYNTAX       Counter64
    MAX-ACCESS   read-only
    STATUS       current
    DESCRIPTION
        "Cisco Firepower ether:FcoeInterfaceStats:packetsRxDelta
        managed object property"
    ::= { cfprEtherFcoeInterfaceStatsEntry 36 }

cfprEtherFcoeInterfaceStatsPacketsRxDeltaAvg OBJECT-TYPE
    SYNTAX       Unsigned64
    MAX-ACCESS   read-only
    STATUS       current
    DESCRIPTION
        "Cisco Firepower ether:FcoeInterfaceStats:packetsRxDeltaAvg
        managed object property"
    ::= { cfprEtherFcoeInterfaceStatsEntry 37 }

cfprEtherFcoeInterfaceStatsPacketsRxDeltaMax OBJECT-TYPE
    SYNTAX       Unsigned64
    MAX-ACCESS   read-only
    STATUS       current
    DESCRIPTION
        "Cisco Firepower ether:FcoeInterfaceStats:packetsRxDeltaMax
        managed object property"
    ::= { cfprEtherFcoeInterfaceStatsEntry 38 }

cfprEtherFcoeInterfaceStatsPacketsRxDeltaMin OBJECT-TYPE
    SYNTAX       Unsigned64
    MAX-ACCESS   read-only
    STATUS       current
    DESCRIPTION
        "Cisco Firepower ether:FcoeInterfaceStats:packetsRxDeltaMin
        managed object property"
    ::= { cfprEtherFcoeInterfaceStatsEntry 39 }

cfprEtherFcoeInterfaceStatsPacketsTx OBJECT-TYPE
    SYNTAX       Unsigned64
    MAX-ACCESS   read-only
    STATUS       current
    DESCRIPTION
        "Cisco Firepower ether:FcoeInterfaceStats:packetsTx
        managed object property"
    ::= { cfprEtherFcoeInterfaceStatsEntry 40 }

cfprEtherFcoeInterfaceStatsPacketsTxDelta OBJECT-TYPE
    SYNTAX       Counter64
    MAX-ACCESS   read-only
    STATUS       current
    DESCRIPTION
        "Cisco Firepower ether:FcoeInterfaceStats:packetsTxDelta
        managed object property"
    ::= { cfprEtherFcoeInterfaceStatsEntry 41 }

cfprEtherFcoeInterfaceStatsPacketsTxDeltaAvg OBJECT-TYPE
    SYNTAX       Unsigned64
    MAX-ACCESS   read-only
    STATUS       current
    DESCRIPTION
        "Cisco Firepower ether:FcoeInterfaceStats:packetsTxDeltaAvg
        managed object property"
    ::= { cfprEtherFcoeInterfaceStatsEntry 42 }

cfprEtherFcoeInterfaceStatsPacketsTxDeltaMax OBJECT-TYPE
    SYNTAX       Unsigned64
    MAX-ACCESS   read-only
    STATUS       current
    DESCRIPTION
        "Cisco Firepower ether:FcoeInterfaceStats:packetsTxDeltaMax
        managed object property"
    ::= { cfprEtherFcoeInterfaceStatsEntry 43 }

cfprEtherFcoeInterfaceStatsPacketsTxDeltaMin OBJECT-TYPE
    SYNTAX       Unsigned64
    MAX-ACCESS   read-only
    STATUS       current
    DESCRIPTION
        "Cisco Firepower ether:FcoeInterfaceStats:packetsTxDeltaMin
        managed object property"
    ::= { cfprEtherFcoeInterfaceStatsEntry 44 }

cfprEtherFcoeInterfaceStatsSuspect OBJECT-TYPE
    SYNTAX       TruthValue
    MAX-ACCESS   read-only
    STATUS       current
    DESCRIPTION
        "Cisco Firepower ether:FcoeInterfaceStats:suspect
        managed object property"
    ::= { cfprEtherFcoeInterfaceStatsEntry 45 }

cfprEtherFcoeInterfaceStatsThresholded OBJECT-TYPE
    SYNTAX       CfprEtherFcoeInterfaceStatsThresholded
    MAX-ACCESS   read-only
    STATUS       current
    DESCRIPTION
        "Cisco Firepower ether:FcoeInterfaceStats:thresholded
        managed object property"
    ::= { cfprEtherFcoeInterfaceStatsEntry 46 }

cfprEtherFcoeInterfaceStatsTimeCollected OBJECT-TYPE
    SYNTAX       DateAndTime
    MAX-ACCESS   read-only
    STATUS       current
    DESCRIPTION
        "Cisco Firepower ether:FcoeInterfaceStats:timeCollected
        managed object property"
    ::= { cfprEtherFcoeInterfaceStatsEntry 47 }

cfprEtherFcoeInterfaceStatsUpdate OBJECT-TYPE
    SYNTAX       Gauge32
    MAX-ACCESS   read-only
    STATUS       current
    DESCRIPTION
        "Cisco Firepower ether:FcoeInterfaceStats:update
        managed object property"
    ::= { cfprEtherFcoeInterfaceStatsEntry 48 }

cfprEtherFcoeInterfaceStatsHistTable OBJECT-TYPE
    SYNTAX           SEQUENCE OF CfprEtherFcoeInterfaceStatsHistEntry
    MAX-ACCESS       not-accessible
    STATUS           current
    DESCRIPTION
        "Cisco Firepower ether:FcoeInterfaceStatsHist managed
        object table"
    ::= { cfprEtherObjects 4 }

cfprEtherFcoeInterfaceStatsHistEntry OBJECT-TYPE
    SYNTAX           CfprEtherFcoeInterfaceStatsHistEntry
    MAX-ACCESS       not-accessible
    STATUS           current
    DESCRIPTION
        "Entry for the cfprEtherFcoeInterfaceStatsHistTable table."
    INDEX { cfprEtherFcoeInterfaceStatsHistInstanceId }
    ::= { cfprEtherFcoeInterfaceStatsHistTable 1 }

CfprEtherFcoeInterfaceStatsHistEntry ::= SEQUENCE {
    cfprEtherFcoeInterfaceStatsHistInstanceId                        CfprManagedObjectId,
    cfprEtherFcoeInterfaceStatsHistDn                                CfprManagedObjectDn,
    cfprEtherFcoeInterfaceStatsHistRn                                SnmpAdminString,
    cfprEtherFcoeInterfaceStatsHistBytesRx                           Unsigned64,
    cfprEtherFcoeInterfaceStatsHistBytesRxDelta                      Unsigned64,
    cfprEtherFcoeInterfaceStatsHistBytesRxDeltaAvg                   Unsigned64,
    cfprEtherFcoeInterfaceStatsHistBytesRxDeltaMax                   Unsigned64,
    cfprEtherFcoeInterfaceStatsHistBytesRxDeltaMin                   Unsigned64,
    cfprEtherFcoeInterfaceStatsHistBytesTx                           Unsigned64,
    cfprEtherFcoeInterfaceStatsHistBytesTxDelta                      Unsigned64,
    cfprEtherFcoeInterfaceStatsHistBytesTxDeltaAvg                   Unsigned64,
    cfprEtherFcoeInterfaceStatsHistBytesTxDeltaMax                   Unsigned64,
    cfprEtherFcoeInterfaceStatsHistBytesTxDeltaMin                   Unsigned64,
    cfprEtherFcoeInterfaceStatsHistDroppedRx                         Unsigned64,
    cfprEtherFcoeInterfaceStatsHistDroppedRxDelta                    Unsigned64,
    cfprEtherFcoeInterfaceStatsHistDroppedRxDeltaAvg                 Unsigned64,
    cfprEtherFcoeInterfaceStatsHistDroppedRxDeltaMax                 Unsigned64,
    cfprEtherFcoeInterfaceStatsHistDroppedRxDeltaMin                 Unsigned64,
    cfprEtherFcoeInterfaceStatsHistDroppedTx                         Unsigned64,
    cfprEtherFcoeInterfaceStatsHistDroppedTxDelta                    Unsigned64,
    cfprEtherFcoeInterfaceStatsHistDroppedTxDeltaAvg                 Unsigned64,
    cfprEtherFcoeInterfaceStatsHistDroppedTxDeltaMax                 Unsigned64,
    cfprEtherFcoeInterfaceStatsHistDroppedTxDeltaMin                 Unsigned64,
    cfprEtherFcoeInterfaceStatsHistErrorsRx                          Unsigned64,
    cfprEtherFcoeInterfaceStatsHistErrorsRxDelta                     Unsigned64,
    cfprEtherFcoeInterfaceStatsHistErrorsRxDeltaAvg                  Unsigned64,
    cfprEtherFcoeInterfaceStatsHistErrorsRxDeltaMax                  Unsigned64,
    cfprEtherFcoeInterfaceStatsHistErrorsRxDeltaMin                  Unsigned64,
    cfprEtherFcoeInterfaceStatsHistErrorsTx                          Unsigned64,
    cfprEtherFcoeInterfaceStatsHistErrorsTxDelta                     Unsigned64,
    cfprEtherFcoeInterfaceStatsHistErrorsTxDeltaAvg                  Unsigned64,
    cfprEtherFcoeInterfaceStatsHistErrorsTxDeltaMax                  Unsigned64,
    cfprEtherFcoeInterfaceStatsHistErrorsTxDeltaMin                  Unsigned64,
    cfprEtherFcoeInterfaceStatsHistId                                Unsigned64,
    cfprEtherFcoeInterfaceStatsHistMostRecent                        TruthValue,
    cfprEtherFcoeInterfaceStatsHistPacketsRx                         Unsigned64,
    cfprEtherFcoeInterfaceStatsHistPacketsRxDelta                    Unsigned64,
    cfprEtherFcoeInterfaceStatsHistPacketsRxDeltaAvg                 Unsigned64,
    cfprEtherFcoeInterfaceStatsHistPacketsRxDeltaMax                 Unsigned64,
    cfprEtherFcoeInterfaceStatsHistPacketsRxDeltaMin                 Unsigned64,
    cfprEtherFcoeInterfaceStatsHistPacketsTx                         Unsigned64,
    cfprEtherFcoeInterfaceStatsHistPacketsTxDelta                    Unsigned64,
    cfprEtherFcoeInterfaceStatsHistPacketsTxDeltaAvg                 Unsigned64,
    cfprEtherFcoeInterfaceStatsHistPacketsTxDeltaMax                 Unsigned64,
    cfprEtherFcoeInterfaceStatsHistPacketsTxDeltaMin                 Unsigned64,
    cfprEtherFcoeInterfaceStatsHistSuspect                           TruthValue,
    cfprEtherFcoeInterfaceStatsHistThresholded                       CfprEtherFcoeInterfaceStatsHistThresholded,
    cfprEtherFcoeInterfaceStatsHistTimeCollected                     DateAndTime
}

cfprEtherFcoeInterfaceStatsHistInstanceId OBJECT-TYPE
    SYNTAX       CfprManagedObjectId
    MAX-ACCESS   not-accessible
    STATUS       current
    DESCRIPTION
        "Instance identifier of the managed object."
    ::= { cfprEtherFcoeInterfaceStatsHistEntry 1 }

cfprEtherFcoeInterfaceStatsHistDn OBJECT-TYPE
    SYNTAX       CfprManagedObjectDn
    MAX-ACCESS   read-only
    STATUS       current
    DESCRIPTION
        "Cisco Firepower ether:FcoeInterfaceStatsHist:dn
        managed object property"
    ::= { cfprEtherFcoeInterfaceStatsHistEntry 2 }

cfprEtherFcoeInterfaceStatsHistRn OBJECT-TYPE
    SYNTAX       SnmpAdminString
    MAX-ACCESS   read-only
    STATUS       current
    DESCRIPTION
        "Cisco Firepower ether:FcoeInterfaceStatsHist:rn
        managed object property"
    ::= { cfprEtherFcoeInterfaceStatsHistEntry 3 }

cfprEtherFcoeInterfaceStatsHistBytesRx OBJECT-TYPE
    SYNTAX       Unsigned64
    MAX-ACCESS   read-only
    STATUS       current
    DESCRIPTION
        "Cisco Firepower ether:FcoeInterfaceStatsHist:bytesRx
        managed object property"
    ::= { cfprEtherFcoeInterfaceStatsHistEntry 4 }

cfprEtherFcoeInterfaceStatsHistBytesRxDelta OBJECT-TYPE
    SYNTAX       Unsigned64
    MAX-ACCESS   read-only
    STATUS       current
    DESCRIPTION
        "Cisco Firepower ether:FcoeInterfaceStatsHist:bytesRxDelta
        managed object property"
    ::= { cfprEtherFcoeInterfaceStatsHistEntry 5 }

cfprEtherFcoeInterfaceStatsHistBytesRxDeltaAvg OBJECT-TYPE
    SYNTAX       Unsigned64
    MAX-ACCESS   read-only
    STATUS       current
    DESCRIPTION
        "Cisco Firepower ether:FcoeInterfaceStatsHist:bytesRxDeltaAvg
        managed object property"
    ::= { cfprEtherFcoeInterfaceStatsHistEntry 6 }

cfprEtherFcoeInterfaceStatsHistBytesRxDeltaMax OBJECT-TYPE
    SYNTAX       Unsigned64
    MAX-ACCESS   read-only
    STATUS       current
    DESCRIPTION
        "Cisco Firepower ether:FcoeInterfaceStatsHist:bytesRxDeltaMax
        managed object property"
    ::= { cfprEtherFcoeInterfaceStatsHistEntry 7 }

cfprEtherFcoeInterfaceStatsHistBytesRxDeltaMin OBJECT-TYPE
    SYNTAX       Unsigned64
    MAX-ACCESS   read-only
    STATUS       current
    DESCRIPTION
        "Cisco Firepower ether:FcoeInterfaceStatsHist:bytesRxDeltaMin
        managed object property"
    ::= { cfprEtherFcoeInterfaceStatsHistEntry 8 }

cfprEtherFcoeInterfaceStatsHistBytesTx OBJECT-TYPE
    SYNTAX       Unsigned64
    MAX-ACCESS   read-only
    STATUS       current
    DESCRIPTION
        "Cisco Firepower ether:FcoeInterfaceStatsHist:bytesTx
        managed object property"
    ::= { cfprEtherFcoeInterfaceStatsHistEntry 9 }

cfprEtherFcoeInterfaceStatsHistBytesTxDelta OBJECT-TYPE
    SYNTAX       Unsigned64
    MAX-ACCESS   read-only
    STATUS       current
    DESCRIPTION
        "Cisco Firepower ether:FcoeInterfaceStatsHist:bytesTxDelta
        managed object property"
    ::= { cfprEtherFcoeInterfaceStatsHistEntry 10 }

cfprEtherFcoeInterfaceStatsHistBytesTxDeltaAvg OBJECT-TYPE
    SYNTAX       Unsigned64
    MAX-ACCESS   read-only
    STATUS       current
    DESCRIPTION
        "Cisco Firepower ether:FcoeInterfaceStatsHist:bytesTxDeltaAvg
        managed object property"
    ::= { cfprEtherFcoeInterfaceStatsHistEntry 11 }

cfprEtherFcoeInterfaceStatsHistBytesTxDeltaMax OBJECT-TYPE
    SYNTAX       Unsigned64
    MAX-ACCESS   read-only
    STATUS       current
    DESCRIPTION
        "Cisco Firepower ether:FcoeInterfaceStatsHist:bytesTxDeltaMax
        managed object property"
    ::= { cfprEtherFcoeInterfaceStatsHistEntry 12 }

cfprEtherFcoeInterfaceStatsHistBytesTxDeltaMin OBJECT-TYPE
    SYNTAX       Unsigned64
    MAX-ACCESS   read-only
    STATUS       current
    DESCRIPTION
        "Cisco Firepower ether:FcoeInterfaceStatsHist:bytesTxDeltaMin
        managed object property"
    ::= { cfprEtherFcoeInterfaceStatsHistEntry 13 }

cfprEtherFcoeInterfaceStatsHistDroppedRx OBJECT-TYPE
    SYNTAX       Unsigned64
    MAX-ACCESS   read-only
    STATUS       current
    DESCRIPTION
        "Cisco Firepower ether:FcoeInterfaceStatsHist:droppedRx
        managed object property"
    ::= { cfprEtherFcoeInterfaceStatsHistEntry 14 }

cfprEtherFcoeInterfaceStatsHistDroppedRxDelta OBJECT-TYPE
    SYNTAX       Unsigned64
    MAX-ACCESS   read-only
    STATUS       current
    DESCRIPTION
        "Cisco Firepower ether:FcoeInterfaceStatsHist:droppedRxDelta
        managed object property"
    ::= { cfprEtherFcoeInterfaceStatsHistEntry 15 }

cfprEtherFcoeInterfaceStatsHistDroppedRxDeltaAvg OBJECT-TYPE
    SYNTAX       Unsigned64
    MAX-ACCESS   read-only
    STATUS       current
    DESCRIPTION
        "Cisco Firepower ether:FcoeInterfaceStatsHist:droppedRxDeltaAvg
        managed object property"
    ::= { cfprEtherFcoeInterfaceStatsHistEntry 16 }

cfprEtherFcoeInterfaceStatsHistDroppedRxDeltaMax OBJECT-TYPE
    SYNTAX       Unsigned64
    MAX-ACCESS   read-only
    STATUS       current
    DESCRIPTION
        "Cisco Firepower ether:FcoeInterfaceStatsHist:droppedRxDeltaMax
        managed object property"
    ::= { cfprEtherFcoeInterfaceStatsHistEntry 17 }

cfprEtherFcoeInterfaceStatsHistDroppedRxDeltaMin OBJECT-TYPE
    SYNTAX       Unsigned64
    MAX-ACCESS   read-only
    STATUS       current
    DESCRIPTION
        "Cisco Firepower ether:FcoeInterfaceStatsHist:droppedRxDeltaMin
        managed object property"
    ::= { cfprEtherFcoeInterfaceStatsHistEntry 18 }

cfprEtherFcoeInterfaceStatsHistDroppedTx OBJECT-TYPE
    SYNTAX       Unsigned64
    MAX-ACCESS   read-only
    STATUS       current
    DESCRIPTION
        "Cisco Firepower ether:FcoeInterfaceStatsHist:droppedTx
        managed object property"
    ::= { cfprEtherFcoeInterfaceStatsHistEntry 19 }

cfprEtherFcoeInterfaceStatsHistDroppedTxDelta OBJECT-TYPE
    SYNTAX       Unsigned64
    MAX-ACCESS   read-only
    STATUS       current
    DESCRIPTION
        "Cisco Firepower ether:FcoeInterfaceStatsHist:droppedTxDelta
        managed object property"
    ::= { cfprEtherFcoeInterfaceStatsHistEntry 20 }

cfprEtherFcoeInterfaceStatsHistDroppedTxDeltaAvg OBJECT-TYPE
    SYNTAX       Unsigned64
    MAX-ACCESS   read-only
    STATUS       current
    DESCRIPTION
        "Cisco Firepower ether:FcoeInterfaceStatsHist:droppedTxDeltaAvg
        managed object property"
    ::= { cfprEtherFcoeInterfaceStatsHistEntry 21 }

cfprEtherFcoeInterfaceStatsHistDroppedTxDeltaMax OBJECT-TYPE
    SYNTAX       Unsigned64
    MAX-ACCESS   read-only
    STATUS       current
    DESCRIPTION
        "Cisco Firepower ether:FcoeInterfaceStatsHist:droppedTxDeltaMax
        managed object property"
    ::= { cfprEtherFcoeInterfaceStatsHistEntry 22 }

cfprEtherFcoeInterfaceStatsHistDroppedTxDeltaMin OBJECT-TYPE
    SYNTAX       Unsigned64
    MAX-ACCESS   read-only
    STATUS       current
    DESCRIPTION
        "Cisco Firepower ether:FcoeInterfaceStatsHist:droppedTxDeltaMin
        managed object property"
    ::= { cfprEtherFcoeInterfaceStatsHistEntry 23 }

cfprEtherFcoeInterfaceStatsHistErrorsRx OBJECT-TYPE
    SYNTAX       Unsigned64
    MAX-ACCESS   read-only
    STATUS       current
    DESCRIPTION
        "Cisco Firepower ether:FcoeInterfaceStatsHist:errorsRx
        managed object property"
    ::= { cfprEtherFcoeInterfaceStatsHistEntry 24 }

cfprEtherFcoeInterfaceStatsHistErrorsRxDelta OBJECT-TYPE
    SYNTAX       Unsigned64
    MAX-ACCESS   read-only
    STATUS       current
    DESCRIPTION
        "Cisco Firepower ether:FcoeInterfaceStatsHist:errorsRxDelta
        managed object property"
    ::= { cfprEtherFcoeInterfaceStatsHistEntry 25 }

cfprEtherFcoeInterfaceStatsHistErrorsRxDeltaAvg OBJECT-TYPE
    SYNTAX       Unsigned64
    MAX-ACCESS   read-only
    STATUS       current
    DESCRIPTION
        "Cisco Firepower ether:FcoeInterfaceStatsHist:errorsRxDeltaAvg
        managed object property"
    ::= { cfprEtherFcoeInterfaceStatsHistEntry 26 }

cfprEtherFcoeInterfaceStatsHistErrorsRxDeltaMax OBJECT-TYPE
    SYNTAX       Unsigned64
    MAX-ACCESS   read-only
    STATUS       current
    DESCRIPTION
        "Cisco Firepower ether:FcoeInterfaceStatsHist:errorsRxDeltaMax
        managed object property"
    ::= { cfprEtherFcoeInterfaceStatsHistEntry 27 }

cfprEtherFcoeInterfaceStatsHistErrorsRxDeltaMin OBJECT-TYPE
    SYNTAX       Unsigned64
    MAX-ACCESS   read-only
    STATUS       current
    DESCRIPTION
        "Cisco Firepower ether:FcoeInterfaceStatsHist:errorsRxDeltaMin
        managed object property"
    ::= { cfprEtherFcoeInterfaceStatsHistEntry 28 }

cfprEtherFcoeInterfaceStatsHistErrorsTx OBJECT-TYPE
    SYNTAX       Unsigned64
    MAX-ACCESS   read-only
    STATUS       current
    DESCRIPTION
        "Cisco Firepower ether:FcoeInterfaceStatsHist:errorsTx
        managed object property"
    ::= { cfprEtherFcoeInterfaceStatsHistEntry 29 }

cfprEtherFcoeInterfaceStatsHistErrorsTxDelta OBJECT-TYPE
    SYNTAX       Unsigned64
    MAX-ACCESS   read-only
    STATUS       current
    DESCRIPTION
        "Cisco Firepower ether:FcoeInterfaceStatsHist:errorsTxDelta
        managed object property"
    ::= { cfprEtherFcoeInterfaceStatsHistEntry 30 }

cfprEtherFcoeInterfaceStatsHistErrorsTxDeltaAvg OBJECT-TYPE
    SYNTAX       Unsigned64
    MAX-ACCESS   read-only
    STATUS       current
    DESCRIPTION
        "Cisco Firepower ether:FcoeInterfaceStatsHist:errorsTxDeltaAvg
        managed object property"
    ::= { cfprEtherFcoeInterfaceStatsHistEntry 31 }

cfprEtherFcoeInterfaceStatsHistErrorsTxDeltaMax OBJECT-TYPE
    SYNTAX       Unsigned64
    MAX-ACCESS   read-only
    STATUS       current
    DESCRIPTION
        "Cisco Firepower ether:FcoeInterfaceStatsHist:errorsTxDeltaMax
        managed object property"
    ::= { cfprEtherFcoeInterfaceStatsHistEntry 32 }

cfprEtherFcoeInterfaceStatsHistErrorsTxDeltaMin OBJECT-TYPE
    SYNTAX       Unsigned64
    MAX-ACCESS   read-only
    STATUS       current
    DESCRIPTION
        "Cisco Firepower ether:FcoeInterfaceStatsHist:errorsTxDeltaMin
        managed object property"
    ::= { cfprEtherFcoeInterfaceStatsHistEntry 33 }

cfprEtherFcoeInterfaceStatsHistId OBJECT-TYPE
    SYNTAX       Unsigned64
    MAX-ACCESS   read-only
    STATUS       current
    DESCRIPTION
        "Cisco Firepower ether:FcoeInterfaceStatsHist:id
        managed object property"
    ::= { cfprEtherFcoeInterfaceStatsHistEntry 34 }

cfprEtherFcoeInterfaceStatsHistMostRecent OBJECT-TYPE
    SYNTAX       TruthValue
    MAX-ACCESS   read-only
    STATUS       current
    DESCRIPTION
        "Cisco Firepower ether:FcoeInterfaceStatsHist:mostRecent
        managed object property"
    ::= { cfprEtherFcoeInterfaceStatsHistEntry 35 }

cfprEtherFcoeInterfaceStatsHistPacketsRx OBJECT-TYPE
    SYNTAX       Unsigned64
    MAX-ACCESS   read-only
    STATUS       current
    DESCRIPTION
        "Cisco Firepower ether:FcoeInterfaceStatsHist:packetsRx
        managed object property"
    ::= { cfprEtherFcoeInterfaceStatsHistEntry 36 }

cfprEtherFcoeInterfaceStatsHistPacketsRxDelta OBJECT-TYPE
    SYNTAX       Unsigned64
    MAX-ACCESS   read-only
    STATUS       current
    DESCRIPTION
        "Cisco Firepower ether:FcoeInterfaceStatsHist:packetsRxDelta
        managed object property"
    ::= { cfprEtherFcoeInterfaceStatsHistEntry 37 }

cfprEtherFcoeInterfaceStatsHistPacketsRxDeltaAvg OBJECT-TYPE
    SYNTAX       Unsigned64
    MAX-ACCESS   read-only
    STATUS       current
    DESCRIPTION
        "Cisco Firepower ether:FcoeInterfaceStatsHist:packetsRxDeltaAvg
        managed object property"
    ::= { cfprEtherFcoeInterfaceStatsHistEntry 38 }

cfprEtherFcoeInterfaceStatsHistPacketsRxDeltaMax OBJECT-TYPE
    SYNTAX       Unsigned64
    MAX-ACCESS   read-only
    STATUS       current
    DESCRIPTION
        "Cisco Firepower ether:FcoeInterfaceStatsHist:packetsRxDeltaMax
        managed object property"
    ::= { cfprEtherFcoeInterfaceStatsHistEntry 39 }

cfprEtherFcoeInterfaceStatsHistPacketsRxDeltaMin OBJECT-TYPE
    SYNTAX       Unsigned64
    MAX-ACCESS   read-only
    STATUS       current
    DESCRIPTION
        "Cisco Firepower ether:FcoeInterfaceStatsHist:packetsRxDeltaMin
        managed object property"
    ::= { cfprEtherFcoeInterfaceStatsHistEntry 40 }

cfprEtherFcoeInterfaceStatsHistPacketsTx OBJECT-TYPE
    SYNTAX       Unsigned64
    MAX-ACCESS   read-only
    STATUS       current
    DESCRIPTION
        "Cisco Firepower ether:FcoeInterfaceStatsHist:packetsTx
        managed object property"
    ::= { cfprEtherFcoeInterfaceStatsHistEntry 41 }

cfprEtherFcoeInterfaceStatsHistPacketsTxDelta OBJECT-TYPE
    SYNTAX       Unsigned64
    MAX-ACCESS   read-only
    STATUS       current
    DESCRIPTION
        "Cisco Firepower ether:FcoeInterfaceStatsHist:packetsTxDelta
        managed object property"
    ::= { cfprEtherFcoeInterfaceStatsHistEntry 42 }

cfprEtherFcoeInterfaceStatsHistPacketsTxDeltaAvg OBJECT-TYPE
    SYNTAX       Unsigned64
    MAX-ACCESS   read-only
    STATUS       current
    DESCRIPTION
        "Cisco Firepower ether:FcoeInterfaceStatsHist:packetsTxDeltaAvg
        managed object property"
    ::= { cfprEtherFcoeInterfaceStatsHistEntry 43 }

cfprEtherFcoeInterfaceStatsHistPacketsTxDeltaMax OBJECT-TYPE
    SYNTAX       Unsigned64
    MAX-ACCESS   read-only
    STATUS       current
    DESCRIPTION
        "Cisco Firepower ether:FcoeInterfaceStatsHist:packetsTxDeltaMax
        managed object property"
    ::= { cfprEtherFcoeInterfaceStatsHistEntry 44 }

cfprEtherFcoeInterfaceStatsHistPacketsTxDeltaMin OBJECT-TYPE
    SYNTAX       Unsigned64
    MAX-ACCESS   read-only
    STATUS       current
    DESCRIPTION
        "Cisco Firepower ether:FcoeInterfaceStatsHist:packetsTxDeltaMin
        managed object property"
    ::= { cfprEtherFcoeInterfaceStatsHistEntry 45 }

cfprEtherFcoeInterfaceStatsHistSuspect OBJECT-TYPE
    SYNTAX       TruthValue
    MAX-ACCESS   read-only
    STATUS       current
    DESCRIPTION
        "Cisco Firepower ether:FcoeInterfaceStatsHist:suspect
        managed object property"
    ::= { cfprEtherFcoeInterfaceStatsHistEntry 46 }

cfprEtherFcoeInterfaceStatsHistThresholded OBJECT-TYPE
    SYNTAX       CfprEtherFcoeInterfaceStatsHistThresholded
    MAX-ACCESS   read-only
    STATUS       current
    DESCRIPTION
        "Cisco Firepower ether:FcoeInterfaceStatsHist:thresholded
        managed object property"
    ::= { cfprEtherFcoeInterfaceStatsHistEntry 47 }

cfprEtherFcoeInterfaceStatsHistTimeCollected OBJECT-TYPE
    SYNTAX       DateAndTime
    MAX-ACCESS   read-only
    STATUS       current
    DESCRIPTION
        "Cisco Firepower ether:FcoeInterfaceStatsHist:timeCollected
        managed object property"
    ::= { cfprEtherFcoeInterfaceStatsHistEntry 48 }

cfprEtherFtwPortPairTable OBJECT-TYPE
    SYNTAX           SEQUENCE OF CfprEtherFtwPortPairEntry
    MAX-ACCESS       not-accessible
    STATUS           current
    DESCRIPTION
        "Cisco Firepower ether:FtwPortPair managed object table"
    ::= { cfprEtherObjects 33 }

cfprEtherFtwPortPairEntry OBJECT-TYPE
    SYNTAX           CfprEtherFtwPortPairEntry
    MAX-ACCESS       not-accessible
    STATUS           current
    DESCRIPTION
        "Entry for the cfprEtherFtwPortPairTable table."
    INDEX { cfprEtherFtwPortPairInstanceId }
    ::= { cfprEtherFtwPortPairTable 1 }

CfprEtherFtwPortPairEntry ::= SEQUENCE {
    cfprEtherFtwPortPairInstanceId                                   CfprManagedObjectId,
    cfprEtherFtwPortPairDn                                           CfprManagedObjectDn,
    cfprEtherFtwPortPairRn                                           SnmpAdminString,
    cfprEtherFtwPortPairAggrPortId                                   Gauge32,
    cfprEtherFtwPortPairChassisId                                    Gauge32,
    cfprEtherFtwPortPairEpDn                                         SnmpAdminString,
    cfprEtherFtwPortPairFsmDescr                                     SnmpAdminString,
    cfprEtherFtwPortPairFsmPrev                                      SnmpAdminString,
    cfprEtherFtwPortPairFsmProgr                                     Gauge32,
    cfprEtherFtwPortPairFsmRmtInvErrCode                             Gauge32,
    cfprEtherFtwPortPairFsmRmtInvErrDescr                            SnmpAdminString,
    cfprEtherFtwPortPairFsmRmtInvRslt                                CfprConditionRemoteInvRslt,
    cfprEtherFtwPortPairFsmStageDescr                                SnmpAdminString,
    cfprEtherFtwPortPairFsmStamp                                     DateAndTime,
    cfprEtherFtwPortPairFsmStatus                                    SnmpAdminString,
    cfprEtherFtwPortPairFsmTry                                       Gauge32,
    cfprEtherFtwPortPairIfRole                                       CfprNetworkPortRole,
    cfprEtherFtwPortPairIfType                                       CfprNetworkPhysEpIfType,
    cfprEtherFtwPortPairLocale                                       CfprNetworkLocale,
    cfprEtherFtwPortPairMode                                         CfprEtherFtwPortPairMode,
    cfprEtherFtwPortPairName                                         SnmpAdminString,
    cfprEtherFtwPortPairOperMode                                     CfprEtherFtwOperMode,
    cfprEtherFtwPortPairPeerAggrPortId                               Gauge32,
    cfprEtherFtwPortPairPeerChassisId                                Gauge32,
    cfprEtherFtwPortPairPeerDn                                       SnmpAdminString,
    cfprEtherFtwPortPairPeerPortId                                   Gauge32,
    cfprEtherFtwPortPairPeerPortName                                 SnmpAdminString,
    cfprEtherFtwPortPairPeerSlotId                                   Gauge32,
    cfprEtherFtwPortPairPortId                                       Gauge32,
    cfprEtherFtwPortPairPortName                                     SnmpAdminString,
    cfprEtherFtwPortPairSlotId                                       Gauge32,
    cfprEtherFtwPortPairSwitchId                                     CfprNetworkSwitchId,
    cfprEtherFtwPortPairTransport                                    CfprNetworkTransport,
    cfprEtherFtwPortPairTs                                           DateAndTime,
    cfprEtherFtwPortPairType                                         CfprNetworkConnectionType,
    cfprEtherFtwPortPairWdtStart                                     Gauge32,
    cfprEtherFtwPortPairWdtState                                     CfprEtherFtwPortPairWdtState
}

cfprEtherFtwPortPairInstanceId OBJECT-TYPE
    SYNTAX       CfprManagedObjectId
    MAX-ACCESS   not-accessible
    STATUS       current
    DESCRIPTION
        "Instance identifier of the managed object."
    ::= { cfprEtherFtwPortPairEntry 1 }

cfprEtherFtwPortPairDn OBJECT-TYPE
    SYNTAX       CfprManagedObjectDn
    MAX-ACCESS   read-only
    STATUS       current
    DESCRIPTION
        "Cisco Firepower ether:FtwPortPair:dn managed object property"
    ::= { cfprEtherFtwPortPairEntry 2 }

cfprEtherFtwPortPairRn OBJECT-TYPE
    SYNTAX       SnmpAdminString
    MAX-ACCESS   read-only
    STATUS       current
    DESCRIPTION
        "Cisco Firepower ether:FtwPortPair:rn managed object property"
    ::= { cfprEtherFtwPortPairEntry 3 }

cfprEtherFtwPortPairAggrPortId OBJECT-TYPE
    SYNTAX       Gauge32
    MAX-ACCESS   read-only
    STATUS       current
    DESCRIPTION
        "Cisco Firepower ether:FtwPortPair:aggrPortId managed
        object property"
    ::= { cfprEtherFtwPortPairEntry 4 }

cfprEtherFtwPortPairChassisId OBJECT-TYPE
    SYNTAX       Gauge32
    MAX-ACCESS   read-only
    STATUS       current
    DESCRIPTION
        "Cisco Firepower ether:FtwPortPair:chassisId managed
        object property"
    ::= { cfprEtherFtwPortPairEntry 5 }

cfprEtherFtwPortPairEpDn OBJECT-TYPE
    SYNTAX       SnmpAdminString
    MAX-ACCESS   read-only
    STATUS       current
    DESCRIPTION
        "Cisco Firepower ether:FtwPortPair:epDn managed object property"
    ::= { cfprEtherFtwPortPairEntry 6 }

cfprEtherFtwPortPairFsmDescr OBJECT-TYPE
    SYNTAX       SnmpAdminString
    MAX-ACCESS   read-only
    STATUS       current
    DESCRIPTION
        "Cisco Firepower ether:FtwPortPair:fsmDescr managed
        object property"
    ::= { cfprEtherFtwPortPairEntry 7 }

cfprEtherFtwPortPairFsmPrev OBJECT-TYPE
    SYNTAX       SnmpAdminString
    MAX-ACCESS   read-only
    STATUS       current
    DESCRIPTION
        "Cisco Firepower ether:FtwPortPair:fsmPrev managed
        object property"
    ::= { cfprEtherFtwPortPairEntry 8 }

cfprEtherFtwPortPairFsmProgr OBJECT-TYPE
    SYNTAX       Gauge32
    MAX-ACCESS   read-only
    STATUS       current
    DESCRIPTION
        "Cisco Firepower ether:FtwPortPair:fsmProgr managed
        object property"
    ::= { cfprEtherFtwPortPairEntry 9 }

cfprEtherFtwPortPairFsmRmtInvErrCode OBJECT-TYPE
    SYNTAX       Gauge32
    MAX-ACCESS   read-only
    STATUS       current
    DESCRIPTION
        "Cisco Firepower ether:FtwPortPair:fsmRmtInvErrCode
        managed object property"
    ::= { cfprEtherFtwPortPairEntry 10 }

cfprEtherFtwPortPairFsmRmtInvErrDescr OBJECT-TYPE
    SYNTAX       SnmpAdminString
    MAX-ACCESS   read-only
    STATUS       current
    DESCRIPTION
        "Cisco Firepower ether:FtwPortPair:fsmRmtInvErrDescr
        managed object property"
    ::= { cfprEtherFtwPortPairEntry 11 }

cfprEtherFtwPortPairFsmRmtInvRslt OBJECT-TYPE
    SYNTAX       CfprConditionRemoteInvRslt
    MAX-ACCESS   read-only
    STATUS       current
    DESCRIPTION
        "Cisco Firepower ether:FtwPortPair:fsmRmtInvRslt
        managed object property"
    ::= { cfprEtherFtwPortPairEntry 12 }

cfprEtherFtwPortPairFsmStageDescr OBJECT-TYPE
    SYNTAX       SnmpAdminString
    MAX-ACCESS   read-only
    STATUS       current
    DESCRIPTION
        "Cisco Firepower ether:FtwPortPair:fsmStageDescr
        managed object property"
    ::= { cfprEtherFtwPortPairEntry 13 }

cfprEtherFtwPortPairFsmStamp OBJECT-TYPE
    SYNTAX       DateAndTime
    MAX-ACCESS   read-only
    STATUS       current
    DESCRIPTION
        "Cisco Firepower ether:FtwPortPair:fsmStamp managed
        object property"
    ::= { cfprEtherFtwPortPairEntry 14 }

cfprEtherFtwPortPairFsmStatus OBJECT-TYPE
    SYNTAX       SnmpAdminString
    MAX-ACCESS   read-only
    STATUS       current
    DESCRIPTION
        "Cisco Firepower ether:FtwPortPair:fsmStatus managed
        object property"
    ::= { cfprEtherFtwPortPairEntry 15 }

cfprEtherFtwPortPairFsmTry OBJECT-TYPE
    SYNTAX       Gauge32
    MAX-ACCESS   read-only
    STATUS       current
    DESCRIPTION
        "Cisco Firepower ether:FtwPortPair:fsmTry managed object property"
    ::= { cfprEtherFtwPortPairEntry 16 }

cfprEtherFtwPortPairIfRole OBJECT-TYPE
    SYNTAX       CfprNetworkPortRole
    MAX-ACCESS   read-only
    STATUS       current
    DESCRIPTION
        "Cisco Firepower ether:FtwPortPair:ifRole managed object property"
    ::= { cfprEtherFtwPortPairEntry 17 }

cfprEtherFtwPortPairIfType OBJECT-TYPE
    SYNTAX       CfprNetworkPhysEpIfType
    MAX-ACCESS   read-only
    STATUS       current
    DESCRIPTION
        "Cisco Firepower ether:FtwPortPair:ifType managed object property"
    ::= { cfprEtherFtwPortPairEntry 18 }

cfprEtherFtwPortPairLocale OBJECT-TYPE
    SYNTAX       CfprNetworkLocale
    MAX-ACCESS   read-only
    STATUS       current
    DESCRIPTION
        "Cisco Firepower ether:FtwPortPair:locale managed object property"
    ::= { cfprEtherFtwPortPairEntry 19 }

cfprEtherFtwPortPairMode OBJECT-TYPE
    SYNTAX       CfprEtherFtwPortPairMode
    MAX-ACCESS   read-only
    STATUS       current
    DESCRIPTION
        "Cisco Firepower ether:FtwPortPair:mode managed object property"
    ::= { cfprEtherFtwPortPairEntry 20 }

cfprEtherFtwPortPairName OBJECT-TYPE
    SYNTAX       SnmpAdminString
    MAX-ACCESS   read-only
    STATUS       current
    DESCRIPTION
        "Cisco Firepower ether:FtwPortPair:name managed object property"
    ::= { cfprEtherFtwPortPairEntry 21 }

cfprEtherFtwPortPairOperMode OBJECT-TYPE
    SYNTAX       CfprEtherFtwOperMode
    MAX-ACCESS   read-only
    STATUS       current
    DESCRIPTION
        "Cisco Firepower ether:FtwPortPair:operMode managed
        object property"
    ::= { cfprEtherFtwPortPairEntry 22 }

cfprEtherFtwPortPairPeerAggrPortId OBJECT-TYPE
    SYNTAX       Gauge32
    MAX-ACCESS   read-only
    STATUS       current
    DESCRIPTION
        "Cisco Firepower ether:FtwPortPair:peerAggrPortId
        managed object property"
    ::= { cfprEtherFtwPortPairEntry 23 }

cfprEtherFtwPortPairPeerChassisId OBJECT-TYPE
    SYNTAX       Gauge32
    MAX-ACCESS   read-only
    STATUS       current
    DESCRIPTION
        "Cisco Firepower ether:FtwPortPair:peerChassisId
        managed object property"
    ::= { cfprEtherFtwPortPairEntry 24 }

cfprEtherFtwPortPairPeerDn OBJECT-TYPE
    SYNTAX       SnmpAdminString
    MAX-ACCESS   read-only
    STATUS       current
    DESCRIPTION
        "Cisco Firepower ether:FtwPortPair:peerDn managed object property"
    ::= { cfprEtherFtwPortPairEntry 25 }

cfprEtherFtwPortPairPeerPortId OBJECT-TYPE
    SYNTAX       Gauge32
    MAX-ACCESS   read-only
    STATUS       current
    DESCRIPTION
        "Cisco Firepower ether:FtwPortPair:peerPortId managed
        object property"
    ::= { cfprEtherFtwPortPairEntry 26 }

cfprEtherFtwPortPairPeerPortName OBJECT-TYPE
    SYNTAX       SnmpAdminString
    MAX-ACCESS   read-only
    STATUS       current
    DESCRIPTION
        "Cisco Firepower ether:FtwPortPair:peerPortName
        managed object property"
    ::= { cfprEtherFtwPortPairEntry 27 }

cfprEtherFtwPortPairPeerSlotId OBJECT-TYPE
    SYNTAX       Gauge32
    MAX-ACCESS   read-only
    STATUS       current
    DESCRIPTION
        "Cisco Firepower ether:FtwPortPair:peerSlotId managed
        object property"
    ::= { cfprEtherFtwPortPairEntry 28 }

cfprEtherFtwPortPairPortId OBJECT-TYPE
    SYNTAX       Gauge32
    MAX-ACCESS   read-only
    STATUS       current
    DESCRIPTION
        "Cisco Firepower ether:FtwPortPair:portId managed object property"
    ::= { cfprEtherFtwPortPairEntry 29 }

cfprEtherFtwPortPairPortName OBJECT-TYPE
    SYNTAX       SnmpAdminString
    MAX-ACCESS   read-only
    STATUS       current
    DESCRIPTION
        "Cisco Firepower ether:FtwPortPair:portName managed
        object property"
    ::= { cfprEtherFtwPortPairEntry 30 }

cfprEtherFtwPortPairSlotId OBJECT-TYPE
    SYNTAX       Gauge32
    MAX-ACCESS   read-only
    STATUS       current
    DESCRIPTION
        "Cisco Firepower ether:FtwPortPair:slotId managed object property"
    ::= { cfprEtherFtwPortPairEntry 31 }

cfprEtherFtwPortPairSwitchId OBJECT-TYPE
    SYNTAX       CfprNetworkSwitchId
    MAX-ACCESS   read-only
    STATUS       current
    DESCRIPTION
        "Cisco Firepower ether:FtwPortPair:switchId managed
        object property"
    ::= { cfprEtherFtwPortPairEntry 32 }

cfprEtherFtwPortPairTransport OBJECT-TYPE
    SYNTAX       CfprNetworkTransport
    MAX-ACCESS   read-only
    STATUS       current
    DESCRIPTION
        "Cisco Firepower ether:FtwPortPair:transport managed
        object property"
    ::= { cfprEtherFtwPortPairEntry 33 }

cfprEtherFtwPortPairTs OBJECT-TYPE
    SYNTAX       DateAndTime
    MAX-ACCESS   read-only
    STATUS       current
    DESCRIPTION
        "Cisco Firepower ether:FtwPortPair:ts managed object property"
    ::= { cfprEtherFtwPortPairEntry 34 }

cfprEtherFtwPortPairType OBJECT-TYPE
    SYNTAX       CfprNetworkConnectionType
    MAX-ACCESS   read-only
    STATUS       current
    DESCRIPTION
        "Cisco Firepower ether:FtwPortPair:type managed object property"
    ::= { cfprEtherFtwPortPairEntry 35 }

cfprEtherFtwPortPairWdtStart OBJECT-TYPE
    SYNTAX       Gauge32
    MAX-ACCESS   read-only
    STATUS       current
    DESCRIPTION
        "Cisco Firepower ether:FtwPortPair:wdtStart managed
        object property"
    ::= { cfprEtherFtwPortPairEntry 36 }

cfprEtherFtwPortPairWdtState OBJECT-TYPE
    SYNTAX       CfprEtherFtwPortPairWdtState
    MAX-ACCESS   read-only
    STATUS       current
    DESCRIPTION
        "Cisco Firepower ether:FtwPortPair:wdtState managed
        object property"
    ::= { cfprEtherFtwPortPairEntry 37 }

cfprEtherFtwPortPairFsmTable OBJECT-TYPE
    SYNTAX           SEQUENCE OF CfprEtherFtwPortPairFsmEntry
    MAX-ACCESS       not-accessible
    STATUS           current
    DESCRIPTION
        "Cisco Firepower ether:FtwPortPairFsm managed object table"
    ::= { cfprEtherObjects 34 }

cfprEtherFtwPortPairFsmEntry OBJECT-TYPE
    SYNTAX           CfprEtherFtwPortPairFsmEntry
    MAX-ACCESS       not-accessible
    STATUS           current
    DESCRIPTION
        "Entry for the cfprEtherFtwPortPairFsmTable table."
    INDEX { cfprEtherFtwPortPairFsmInstanceId }
    ::= { cfprEtherFtwPortPairFsmTable 1 }

CfprEtherFtwPortPairFsmEntry ::= SEQUENCE {
    cfprEtherFtwPortPairFsmInstanceId                                CfprManagedObjectId,
    cfprEtherFtwPortPairFsmDn                                        CfprManagedObjectDn,
    cfprEtherFtwPortPairFsmRn                                        SnmpAdminString,
    cfprEtherFtwPortPairFsmCompletionTime                            DateAndTime,
    cfprEtherFtwPortPairFsmCurrentFsm                                CfprEtherFtwPortPairFsmCurrentFsm,
    cfprEtherFtwPortPairFsmDescrData                                 SnmpAdminString,
    cfprEtherFtwPortPairFsmFsmStatus                                 CfprFsmFsmStageStatus,
    cfprEtherFtwPortPairFsmProgress                                  Gauge32,
    cfprEtherFtwPortPairFsmRmtErrCode                                Gauge32,
    cfprEtherFtwPortPairFsmRmtErrDescr                               SnmpAdminString,
    cfprEtherFtwPortPairFsmRmtRslt                                   CfprConditionRemoteInvRslt
}

cfprEtherFtwPortPairFsmInstanceId OBJECT-TYPE
    SYNTAX       CfprManagedObjectId
    MAX-ACCESS   not-accessible
    STATUS       current
    DESCRIPTION
        "Instance identifier of the managed object."
    ::= { cfprEtherFtwPortPairFsmEntry 1 }

cfprEtherFtwPortPairFsmDn OBJECT-TYPE
    SYNTAX       CfprManagedObjectDn
    MAX-ACCESS   read-only
    STATUS       current
    DESCRIPTION
        "Cisco Firepower ether:FtwPortPairFsm:dn managed object property"
    ::= { cfprEtherFtwPortPairFsmEntry 2 }

cfprEtherFtwPortPairFsmRn OBJECT-TYPE
    SYNTAX       SnmpAdminString
    MAX-ACCESS   read-only
    STATUS       current
    DESCRIPTION
        "Cisco Firepower ether:FtwPortPairFsm:rn managed object property"
    ::= { cfprEtherFtwPortPairFsmEntry 3 }

cfprEtherFtwPortPairFsmCompletionTime OBJECT-TYPE
    SYNTAX       DateAndTime
    MAX-ACCESS   read-only
    STATUS       current
    DESCRIPTION
        "Cisco Firepower ether:FtwPortPairFsm:completionTime
        managed object property"
    ::= { cfprEtherFtwPortPairFsmEntry 4 }

cfprEtherFtwPortPairFsmCurrentFsm OBJECT-TYPE
    SYNTAX       CfprEtherFtwPortPairFsmCurrentFsm
    MAX-ACCESS   read-only
    STATUS       current
    DESCRIPTION
        "Cisco Firepower ether:FtwPortPairFsm:currentFsm
        managed object property"
    ::= { cfprEtherFtwPortPairFsmEntry 5 }

cfprEtherFtwPortPairFsmDescrData OBJECT-TYPE
    SYNTAX       SnmpAdminString
    MAX-ACCESS   read-only
    STATUS       current
    DESCRIPTION
        "Cisco Firepower ether:FtwPortPairFsm:descr managed
        object property"
    ::= { cfprEtherFtwPortPairFsmEntry 6 }

cfprEtherFtwPortPairFsmFsmStatus OBJECT-TYPE
    SYNTAX       CfprFsmFsmStageStatus
    MAX-ACCESS   read-only
    STATUS       current
    DESCRIPTION
        "Cisco Firepower ether:FtwPortPairFsm:fsmStatus
        managed object property"
    ::= { cfprEtherFtwPortPairFsmEntry 7 }

cfprEtherFtwPortPairFsmProgress OBJECT-TYPE
    SYNTAX       Gauge32
    MAX-ACCESS   read-only
    STATUS       current
    DESCRIPTION
        "Cisco Firepower ether:FtwPortPairFsm:progress
        managed object property"
    ::= { cfprEtherFtwPortPairFsmEntry 8 }

cfprEtherFtwPortPairFsmRmtErrCode OBJECT-TYPE
    SYNTAX       Gauge32
    MAX-ACCESS   read-only
    STATUS       current
    DESCRIPTION
        "Cisco Firepower ether:FtwPortPairFsm:rmtErrCode
        managed object property"
    ::= { cfprEtherFtwPortPairFsmEntry 9 }

cfprEtherFtwPortPairFsmRmtErrDescr OBJECT-TYPE
    SYNTAX       SnmpAdminString
    MAX-ACCESS   read-only
    STATUS       current
    DESCRIPTION
        "Cisco Firepower ether:FtwPortPairFsm:rmtErrDescr
        managed object property"
    ::= { cfprEtherFtwPortPairFsmEntry 10 }

cfprEtherFtwPortPairFsmRmtRslt OBJECT-TYPE
    SYNTAX       CfprConditionRemoteInvRslt
    MAX-ACCESS   read-only
    STATUS       current
    DESCRIPTION
        "Cisco Firepower ether:FtwPortPairFsm:rmtRslt managed
        object property"
    ::= { cfprEtherFtwPortPairFsmEntry 11 }

cfprEtherFtwPortPairFsmStageTable OBJECT-TYPE
    SYNTAX           SEQUENCE OF CfprEtherFtwPortPairFsmStageEntry
    MAX-ACCESS       not-accessible
    STATUS           current
    DESCRIPTION
        "Cisco Firepower ether:FtwPortPairFsmStage managed object table"
    ::= { cfprEtherObjects 35 }

cfprEtherFtwPortPairFsmStageEntry OBJECT-TYPE
    SYNTAX           CfprEtherFtwPortPairFsmStageEntry
    MAX-ACCESS       not-accessible
    STATUS           current
    DESCRIPTION
        "Entry for the cfprEtherFtwPortPairFsmStageTable table."
    INDEX { cfprEtherFtwPortPairFsmStageInstanceId }
    ::= { cfprEtherFtwPortPairFsmStageTable 1 }

CfprEtherFtwPortPairFsmStageEntry ::= SEQUENCE {
    cfprEtherFtwPortPairFsmStageInstanceId                           CfprManagedObjectId,
    cfprEtherFtwPortPairFsmStageDn                                   CfprManagedObjectDn,
    cfprEtherFtwPortPairFsmStageRn                                   SnmpAdminString,
    cfprEtherFtwPortPairFsmStageDescrData                            SnmpAdminString,
    cfprEtherFtwPortPairFsmStageLastUpdateTime                       DateAndTime,
    cfprEtherFtwPortPairFsmStageName                                 CfprEtherFtwPortPairFsmStageName,
    cfprEtherFtwPortPairFsmStageOrder                                Gauge32,
    cfprEtherFtwPortPairFsmStageRetry                                Gauge32,
    cfprEtherFtwPortPairFsmStageStageStatus                          CfprFsmFsmStageStatus
}

cfprEtherFtwPortPairFsmStageInstanceId OBJECT-TYPE
    SYNTAX       CfprManagedObjectId
    MAX-ACCESS   not-accessible
    STATUS       current
    DESCRIPTION
        "Instance identifier of the managed object."
    ::= { cfprEtherFtwPortPairFsmStageEntry 1 }

cfprEtherFtwPortPairFsmStageDn OBJECT-TYPE
    SYNTAX       CfprManagedObjectDn
    MAX-ACCESS   read-only
    STATUS       current
    DESCRIPTION
        "Cisco Firepower ether:FtwPortPairFsmStage:dn managed
        object property"
    ::= { cfprEtherFtwPortPairFsmStageEntry 2 }

cfprEtherFtwPortPairFsmStageRn OBJECT-TYPE
    SYNTAX       SnmpAdminString
    MAX-ACCESS   read-only
    STATUS       current
    DESCRIPTION
        "Cisco Firepower ether:FtwPortPairFsmStage:rn managed
        object property"
    ::= { cfprEtherFtwPortPairFsmStageEntry 3 }

cfprEtherFtwPortPairFsmStageDescrData OBJECT-TYPE
    SYNTAX       SnmpAdminString
    MAX-ACCESS   read-only
    STATUS       current
    DESCRIPTION
        "Cisco Firepower ether:FtwPortPairFsmStage:descr
        managed object property"
    ::= { cfprEtherFtwPortPairFsmStageEntry 4 }

cfprEtherFtwPortPairFsmStageLastUpdateTime OBJECT-TYPE
    SYNTAX       DateAndTime
    MAX-ACCESS   read-only
    STATUS       current
    DESCRIPTION
        "Cisco Firepower ether:FtwPortPairFsmStage:lastUpdateTime
        managed object property"
    ::= { cfprEtherFtwPortPairFsmStageEntry 5 }

cfprEtherFtwPortPairFsmStageName OBJECT-TYPE
    SYNTAX       CfprEtherFtwPortPairFsmStageName
    MAX-ACCESS   read-only
    STATUS       current
    DESCRIPTION
        "Cisco Firepower ether:FtwPortPairFsmStage:name
        managed object property"
    ::= { cfprEtherFtwPortPairFsmStageEntry 6 }

cfprEtherFtwPortPairFsmStageOrder OBJECT-TYPE
    SYNTAX       Gauge32
    MAX-ACCESS   read-only
    STATUS       current
    DESCRIPTION
        "Cisco Firepower ether:FtwPortPairFsmStage:order
        managed object property"
    ::= { cfprEtherFtwPortPairFsmStageEntry 7 }

cfprEtherFtwPortPairFsmStageRetry OBJECT-TYPE
    SYNTAX       Gauge32
    MAX-ACCESS   read-only
    STATUS       current
    DESCRIPTION
        "Cisco Firepower ether:FtwPortPairFsmStage:retry
        managed object property"
    ::= { cfprEtherFtwPortPairFsmStageEntry 8 }

cfprEtherFtwPortPairFsmStageStageStatus OBJECT-TYPE
    SYNTAX       CfprFsmFsmStageStatus
    MAX-ACCESS   read-only
    STATUS       current
    DESCRIPTION
        "Cisco Firepower ether:FtwPortPairFsmStage:stageStatus
        managed object property"
    ::= { cfprEtherFtwPortPairFsmStageEntry 9 }

cfprEtherFtwPortPairFsmTaskTable OBJECT-TYPE
    SYNTAX           SEQUENCE OF CfprEtherFtwPortPairFsmTaskEntry
    MAX-ACCESS       not-accessible
    STATUS           current
    DESCRIPTION
        "Cisco Firepower ether:FtwPortPairFsmTask managed object table"
    ::= { cfprEtherObjects 36 }

cfprEtherFtwPortPairFsmTaskEntry OBJECT-TYPE
    SYNTAX           CfprEtherFtwPortPairFsmTaskEntry
    MAX-ACCESS       not-accessible
    STATUS           current
    DESCRIPTION
        "Entry for the cfprEtherFtwPortPairFsmTaskTable table."
    INDEX { cfprEtherFtwPortPairFsmTaskInstanceId }
    ::= { cfprEtherFtwPortPairFsmTaskTable 1 }

CfprEtherFtwPortPairFsmTaskEntry ::= SEQUENCE {
    cfprEtherFtwPortPairFsmTaskInstanceId                            CfprManagedObjectId,
    cfprEtherFtwPortPairFsmTaskDn                                    CfprManagedObjectDn,
    cfprEtherFtwPortPairFsmTaskRn                                    SnmpAdminString,
    cfprEtherFtwPortPairFsmTaskCompletion                            CfprFsmCompletion,
    cfprEtherFtwPortPairFsmTaskFlags                                 CfprFsmFlags,
    cfprEtherFtwPortPairFsmTaskItem                                  CfprEtherFtwPortPairFsmTaskItem,
    cfprEtherFtwPortPairFsmTaskSeqId                                 Gauge32
}

cfprEtherFtwPortPairFsmTaskInstanceId OBJECT-TYPE
    SYNTAX       CfprManagedObjectId
    MAX-ACCESS   not-accessible
    STATUS       current
    DESCRIPTION
        "Instance identifier of the managed object."
    ::= { cfprEtherFtwPortPairFsmTaskEntry 1 }

cfprEtherFtwPortPairFsmTaskDn OBJECT-TYPE
    SYNTAX       CfprManagedObjectDn
    MAX-ACCESS   read-only
    STATUS       current
    DESCRIPTION
        "Cisco Firepower ether:FtwPortPairFsmTask:dn managed
        object property"
    ::= { cfprEtherFtwPortPairFsmTaskEntry 2 }

cfprEtherFtwPortPairFsmTaskRn OBJECT-TYPE
    SYNTAX       SnmpAdminString
    MAX-ACCESS   read-only
    STATUS       current
    DESCRIPTION
        "Cisco Firepower ether:FtwPortPairFsmTask:rn managed
        object property"
    ::= { cfprEtherFtwPortPairFsmTaskEntry 3 }

cfprEtherFtwPortPairFsmTaskCompletion OBJECT-TYPE
    SYNTAX       CfprFsmCompletion
    MAX-ACCESS   read-only
    STATUS       current
    DESCRIPTION
        "Cisco Firepower ether:FtwPortPairFsmTask:completion
        managed object property"
    ::= { cfprEtherFtwPortPairFsmTaskEntry 4 }

cfprEtherFtwPortPairFsmTaskFlags OBJECT-TYPE
    SYNTAX       CfprFsmFlags
    MAX-ACCESS   read-only
    STATUS       current
    DESCRIPTION
        "Cisco Firepower ether:FtwPortPairFsmTask:flags
        managed object property"
    ::= { cfprEtherFtwPortPairFsmTaskEntry 5 }

cfprEtherFtwPortPairFsmTaskItem OBJECT-TYPE
    SYNTAX       CfprEtherFtwPortPairFsmTaskItem
    MAX-ACCESS   read-only
    STATUS       current
    DESCRIPTION
        "Cisco Firepower ether:FtwPortPairFsmTask:item
        managed object property"
    ::= { cfprEtherFtwPortPairFsmTaskEntry 6 }

cfprEtherFtwPortPairFsmTaskSeqId OBJECT-TYPE
    SYNTAX       Gauge32
    MAX-ACCESS   read-only
    STATUS       current
    DESCRIPTION
        "Cisco Firepower ether:FtwPortPairFsmTask:seqId
        managed object property"
    ::= { cfprEtherFtwPortPairFsmTaskEntry 7 }

cfprEtherLossStatsTable OBJECT-TYPE
    SYNTAX           SEQUENCE OF CfprEtherLossStatsEntry
    MAX-ACCESS       not-accessible
    STATUS           current
    DESCRIPTION
        "Cisco Firepower ether:LossStats managed object table"
    ::= { cfprEtherObjects 5 }

cfprEtherLossStatsEntry OBJECT-TYPE
    SYNTAX           CfprEtherLossStatsEntry
    MAX-ACCESS       not-accessible
    STATUS           current
    DESCRIPTION
        "Entry for the cfprEtherLossStatsTable table."
    INDEX { cfprEtherLossStatsInstanceId }
    ::= { cfprEtherLossStatsTable 1 }

CfprEtherLossStatsEntry ::= SEQUENCE {
    cfprEtherLossStatsInstanceId                                     CfprManagedObjectId,
    cfprEtherLossStatsDn                                             CfprManagedObjectDn,
    cfprEtherLossStatsRn                                             SnmpAdminString,
    cfprEtherLossStatsSQETest                                        Unsigned64,
    cfprEtherLossStatsSQETestDelta                                   Counter64,
    cfprEtherLossStatsSQETestDeltaAvg                                Unsigned64,
    cfprEtherLossStatsSQETestDeltaMax                                Unsigned64,
    cfprEtherLossStatsSQETestDeltaMin                                Unsigned64,
    cfprEtherLossStatsCarrierSense                                   Unsigned64,
    cfprEtherLossStatsCarrierSenseDelta                              Counter64,
    cfprEtherLossStatsCarrierSenseDeltaAvg                           Unsigned64,
    cfprEtherLossStatsCarrierSenseDeltaMax                           Unsigned64,
    cfprEtherLossStatsCarrierSenseDeltaMin                           Unsigned64,
    cfprEtherLossStatsExcessCollision                                Unsigned64,
    cfprEtherLossStatsExcessCollisionDelta                           Counter64,
    cfprEtherLossStatsExcessCollisionDeltaAvg                        Unsigned64,
    cfprEtherLossStatsExcessCollisionDeltaMax                        Unsigned64,
    cfprEtherLossStatsExcessCollisionDeltaMin                        Unsigned64,
    cfprEtherLossStatsGiants                                         Unsigned64,
    cfprEtherLossStatsGiantsDelta                                    Counter64,
    cfprEtherLossStatsGiantsDeltaAvg                                 Unsigned64,
    cfprEtherLossStatsGiantsDeltaMax                                 Unsigned64,
    cfprEtherLossStatsGiantsDeltaMin                                 Unsigned64,
    cfprEtherLossStatsIntervals                                      Gauge32,
    cfprEtherLossStatsLateCollision                                  Unsigned64,
    cfprEtherLossStatsLateCollisionDelta                             Counter64,
    cfprEtherLossStatsLateCollisionDeltaAvg                          Unsigned64,
    cfprEtherLossStatsLateCollisionDeltaMax                          Unsigned64,
    cfprEtherLossStatsLateCollisionDeltaMin                          Unsigned64,
    cfprEtherLossStatsMultiCollision                                 Unsigned64,
    cfprEtherLossStatsMultiCollisionDelta                            Counter64,
    cfprEtherLossStatsMultiCollisionDeltaAvg                         Unsigned64,
    cfprEtherLossStatsMultiCollisionDeltaMax                         Unsigned64,
    cfprEtherLossStatsMultiCollisionDeltaMin                         Unsigned64,
    cfprEtherLossStatsSingleCollision                                Unsigned64,
    cfprEtherLossStatsSingleCollisionDelta                           Counter64,
    cfprEtherLossStatsSingleCollisionDeltaAvg                        Unsigned64,
    cfprEtherLossStatsSingleCollisionDeltaMax                        Unsigned64,
    cfprEtherLossStatsSingleCollisionDeltaMin                        Unsigned64,
    cfprEtherLossStatsSuspect                                        TruthValue,
    cfprEtherLossStatsSymbol                                         Unsigned64,
    cfprEtherLossStatsSymbolDelta                                    Counter64,
    cfprEtherLossStatsSymbolDeltaAvg                                 Unsigned64,
    cfprEtherLossStatsSymbolDeltaMax                                 Unsigned64,
    cfprEtherLossStatsSymbolDeltaMin                                 Unsigned64,
    cfprEtherLossStatsThresholded                                    CfprEtherLossStatsThresholded,
    cfprEtherLossStatsTimeCollected                                  DateAndTime,
    cfprEtherLossStatsUpdate                                         Gauge32
}

cfprEtherLossStatsInstanceId OBJECT-TYPE
    SYNTAX       CfprManagedObjectId
    MAX-ACCESS   not-accessible
    STATUS       current
    DESCRIPTION
        "Instance identifier of the managed object."
    ::= { cfprEtherLossStatsEntry 1 }

cfprEtherLossStatsDn OBJECT-TYPE
    SYNTAX       CfprManagedObjectDn
    MAX-ACCESS   read-only
    STATUS       current
    DESCRIPTION
        "Cisco Firepower ether:LossStats:dn managed object property"
    ::= { cfprEtherLossStatsEntry 2 }

cfprEtherLossStatsRn OBJECT-TYPE
    SYNTAX       SnmpAdminString
    MAX-ACCESS   read-only
    STATUS       current
    DESCRIPTION
        "Cisco Firepower ether:LossStats:rn managed object property"
    ::= { cfprEtherLossStatsEntry 3 }

cfprEtherLossStatsSQETest OBJECT-TYPE
    SYNTAX       Unsigned64
    MAX-ACCESS   read-only
    STATUS       current
    DESCRIPTION
        "Cisco Firepower ether:LossStats:SQETest managed object property"
    ::= { cfprEtherLossStatsEntry 4 }

cfprEtherLossStatsSQETestDelta OBJECT-TYPE
    SYNTAX       Counter64
    MAX-ACCESS   read-only
    STATUS       current
    DESCRIPTION
        "Cisco Firepower ether:LossStats:SQETestDelta managed
        object property"
    ::= { cfprEtherLossStatsEntry 5 }

cfprEtherLossStatsSQETestDeltaAvg OBJECT-TYPE
    SYNTAX       Unsigned64
    MAX-ACCESS   read-only
    STATUS       current
    DESCRIPTION
        "Cisco Firepower ether:LossStats:SQETestDeltaAvg
        managed object property"
    ::= { cfprEtherLossStatsEntry 6 }

cfprEtherLossStatsSQETestDeltaMax OBJECT-TYPE
    SYNTAX       Unsigned64
    MAX-ACCESS   read-only
    STATUS       current
    DESCRIPTION
        "Cisco Firepower ether:LossStats:SQETestDeltaMax
        managed object property"
    ::= { cfprEtherLossStatsEntry 7 }

cfprEtherLossStatsSQETestDeltaMin OBJECT-TYPE
    SYNTAX       Unsigned64
    MAX-ACCESS   read-only
    STATUS       current
    DESCRIPTION
        "Cisco Firepower ether:LossStats:SQETestDeltaMin
        managed object property"
    ::= { cfprEtherLossStatsEntry 8 }

cfprEtherLossStatsCarrierSense OBJECT-TYPE
    SYNTAX       Unsigned64
    MAX-ACCESS   read-only
    STATUS       current
    DESCRIPTION
        "Cisco Firepower ether:LossStats:carrierSense managed
        object property"
    ::= { cfprEtherLossStatsEntry 9 }

cfprEtherLossStatsCarrierSenseDelta OBJECT-TYPE
    SYNTAX       Counter64
    MAX-ACCESS   read-only
    STATUS       current
    DESCRIPTION
        "Cisco Firepower ether:LossStats:carrierSenseDelta
        managed object property"
    ::= { cfprEtherLossStatsEntry 10 }

cfprEtherLossStatsCarrierSenseDeltaAvg OBJECT-TYPE
    SYNTAX       Unsigned64
    MAX-ACCESS   read-only
    STATUS       current
    DESCRIPTION
        "Cisco Firepower ether:LossStats:carrierSenseDeltaAvg
        managed object property"
    ::= { cfprEtherLossStatsEntry 11 }

cfprEtherLossStatsCarrierSenseDeltaMax OBJECT-TYPE
    SYNTAX       Unsigned64
    MAX-ACCESS   read-only
    STATUS       current
    DESCRIPTION
        "Cisco Firepower ether:LossStats:carrierSenseDeltaMax
        managed object property"
    ::= { cfprEtherLossStatsEntry 12 }

cfprEtherLossStatsCarrierSenseDeltaMin OBJECT-TYPE
    SYNTAX       Unsigned64
    MAX-ACCESS   read-only
    STATUS       current
    DESCRIPTION
        "Cisco Firepower ether:LossStats:carrierSenseDeltaMin
        managed object property"
    ::= { cfprEtherLossStatsEntry 13 }

cfprEtherLossStatsExcessCollision OBJECT-TYPE
    SYNTAX       Unsigned64
    MAX-ACCESS   read-only
    STATUS       current
    DESCRIPTION
        "Cisco Firepower ether:LossStats:excessCollision
        managed object property"
    ::= { cfprEtherLossStatsEntry 14 }

cfprEtherLossStatsExcessCollisionDelta OBJECT-TYPE
    SYNTAX       Counter64
    MAX-ACCESS   read-only
    STATUS       current
    DESCRIPTION
        "Cisco Firepower ether:LossStats:excessCollisionDelta
        managed object property"
    ::= { cfprEtherLossStatsEntry 15 }

cfprEtherLossStatsExcessCollisionDeltaAvg OBJECT-TYPE
    SYNTAX       Unsigned64
    MAX-ACCESS   read-only
    STATUS       current
    DESCRIPTION
        "Cisco Firepower ether:LossStats:excessCollisionDeltaAvg
        managed object property"
    ::= { cfprEtherLossStatsEntry 16 }

cfprEtherLossStatsExcessCollisionDeltaMax OBJECT-TYPE
    SYNTAX       Unsigned64
    MAX-ACCESS   read-only
    STATUS       current
    DESCRIPTION
        "Cisco Firepower ether:LossStats:excessCollisionDeltaMax
        managed object property"
    ::= { cfprEtherLossStatsEntry 17 }

cfprEtherLossStatsExcessCollisionDeltaMin OBJECT-TYPE
    SYNTAX       Unsigned64
    MAX-ACCESS   read-only
    STATUS       current
    DESCRIPTION
        "Cisco Firepower ether:LossStats:excessCollisionDeltaMin
        managed object property"
    ::= { cfprEtherLossStatsEntry 18 }

cfprEtherLossStatsGiants OBJECT-TYPE
    SYNTAX       Unsigned64
    MAX-ACCESS   read-only
    STATUS       current
    DESCRIPTION
        "Cisco Firepower ether:LossStats:giants managed object property"
    ::= { cfprEtherLossStatsEntry 19 }

cfprEtherLossStatsGiantsDelta OBJECT-TYPE
    SYNTAX       Counter64
    MAX-ACCESS   read-only
    STATUS       current
    DESCRIPTION
        "Cisco Firepower ether:LossStats:giantsDelta managed
        object property"
    ::= { cfprEtherLossStatsEntry 20 }

cfprEtherLossStatsGiantsDeltaAvg OBJECT-TYPE
    SYNTAX       Unsigned64
    MAX-ACCESS   read-only
    STATUS       current
    DESCRIPTION
        "Cisco Firepower ether:LossStats:giantsDeltaAvg
        managed object property"
    ::= { cfprEtherLossStatsEntry 21 }

cfprEtherLossStatsGiantsDeltaMax OBJECT-TYPE
    SYNTAX       Unsigned64
    MAX-ACCESS   read-only
    STATUS       current
    DESCRIPTION
        "Cisco Firepower ether:LossStats:giantsDeltaMax
        managed object property"
    ::= { cfprEtherLossStatsEntry 22 }

cfprEtherLossStatsGiantsDeltaMin OBJECT-TYPE
    SYNTAX       Unsigned64
    MAX-ACCESS   read-only
    STATUS       current
    DESCRIPTION
        "Cisco Firepower ether:LossStats:giantsDeltaMin
        managed object property"
    ::= { cfprEtherLossStatsEntry 23 }

cfprEtherLossStatsIntervals OBJECT-TYPE
    SYNTAX       Gauge32
    MAX-ACCESS   read-only
    STATUS       current
    DESCRIPTION
        "Cisco Firepower ether:LossStats:intervals managed
        object property"
    ::= { cfprEtherLossStatsEntry 24 }

cfprEtherLossStatsLateCollision OBJECT-TYPE
    SYNTAX       Unsigned64
    MAX-ACCESS   read-only
    STATUS       current
    DESCRIPTION
        "Cisco Firepower ether:LossStats:lateCollision
        managed object property"
    ::= { cfprEtherLossStatsEntry 25 }

cfprEtherLossStatsLateCollisionDelta OBJECT-TYPE
    SYNTAX       Counter64
    MAX-ACCESS   read-only
    STATUS       current
    DESCRIPTION
        "Cisco Firepower ether:LossStats:lateCollisionDelta
        managed object property"
    ::= { cfprEtherLossStatsEntry 26 }

cfprEtherLossStatsLateCollisionDeltaAvg OBJECT-TYPE
    SYNTAX       Unsigned64
    MAX-ACCESS   read-only
    STATUS       current
    DESCRIPTION
        "Cisco Firepower ether:LossStats:lateCollisionDeltaAvg
        managed object property"
    ::= { cfprEtherLossStatsEntry 27 }

cfprEtherLossStatsLateCollisionDeltaMax OBJECT-TYPE
    SYNTAX       Unsigned64
    MAX-ACCESS   read-only
    STATUS       current
    DESCRIPTION
        "Cisco Firepower ether:LossStats:lateCollisionDeltaMax
        managed object property"
    ::= { cfprEtherLossStatsEntry 28 }

cfprEtherLossStatsLateCollisionDeltaMin OBJECT-TYPE
    SYNTAX       Unsigned64
    MAX-ACCESS   read-only
    STATUS       current
    DESCRIPTION
        "Cisco Firepower ether:LossStats:lateCollisionDeltaMin
        managed object property"
    ::= { cfprEtherLossStatsEntry 29 }

cfprEtherLossStatsMultiCollision OBJECT-TYPE
    SYNTAX       Unsigned64
    MAX-ACCESS   read-only
    STATUS       current
    DESCRIPTION
        "Cisco Firepower ether:LossStats:multiCollision
        managed object property"
    ::= { cfprEtherLossStatsEntry 30 }

cfprEtherLossStatsMultiCollisionDelta OBJECT-TYPE
    SYNTAX       Counter64
    MAX-ACCESS   read-only
    STATUS       current
    DESCRIPTION
        "Cisco Firepower ether:LossStats:multiCollisionDelta
        managed object property"
    ::= { cfprEtherLossStatsEntry 31 }

cfprEtherLossStatsMultiCollisionDeltaAvg OBJECT-TYPE
    SYNTAX       Unsigned64
    MAX-ACCESS   read-only
    STATUS       current
    DESCRIPTION
        "Cisco Firepower ether:LossStats:multiCollisionDeltaAvg
        managed object property"
    ::= { cfprEtherLossStatsEntry 32 }

cfprEtherLossStatsMultiCollisionDeltaMax OBJECT-TYPE
    SYNTAX       Unsigned64
    MAX-ACCESS   read-only
    STATUS       current
    DESCRIPTION
        "Cisco Firepower ether:LossStats:multiCollisionDeltaMax
        managed object property"
    ::= { cfprEtherLossStatsEntry 33 }

cfprEtherLossStatsMultiCollisionDeltaMin OBJECT-TYPE
    SYNTAX       Unsigned64
    MAX-ACCESS   read-only
    STATUS       current
    DESCRIPTION
        "Cisco Firepower ether:LossStats:multiCollisionDeltaMin
        managed object property"
    ::= { cfprEtherLossStatsEntry 34 }

cfprEtherLossStatsSingleCollision OBJECT-TYPE
    SYNTAX       Unsigned64
    MAX-ACCESS   read-only
    STATUS       current
    DESCRIPTION
        "Cisco Firepower ether:LossStats:singleCollision
        managed object property"
    ::= { cfprEtherLossStatsEntry 35 }

cfprEtherLossStatsSingleCollisionDelta OBJECT-TYPE
    SYNTAX       Counter64
    MAX-ACCESS   read-only
    STATUS       current
    DESCRIPTION
        "Cisco Firepower ether:LossStats:singleCollisionDelta
        managed object property"
    ::= { cfprEtherLossStatsEntry 36 }

cfprEtherLossStatsSingleCollisionDeltaAvg OBJECT-TYPE
    SYNTAX       Unsigned64
    MAX-ACCESS   read-only
    STATUS       current
    DESCRIPTION
        "Cisco Firepower ether:LossStats:singleCollisionDeltaAvg
        managed object property"
    ::= { cfprEtherLossStatsEntry 37 }

cfprEtherLossStatsSingleCollisionDeltaMax OBJECT-TYPE
    SYNTAX       Unsigned64
    MAX-ACCESS   read-only
    STATUS       current
    DESCRIPTION
        "Cisco Firepower ether:LossStats:singleCollisionDeltaMax
        managed object property"
    ::= { cfprEtherLossStatsEntry 38 }

cfprEtherLossStatsSingleCollisionDeltaMin OBJECT-TYPE
    SYNTAX       Unsigned64
    MAX-ACCESS   read-only
    STATUS       current
    DESCRIPTION
        "Cisco Firepower ether:LossStats:singleCollisionDeltaMin
        managed object property"
    ::= { cfprEtherLossStatsEntry 39 }

cfprEtherLossStatsSuspect OBJECT-TYPE
    SYNTAX       TruthValue
    MAX-ACCESS   read-only
    STATUS       current
    DESCRIPTION
        "Cisco Firepower ether:LossStats:suspect managed object property"
    ::= { cfprEtherLossStatsEntry 40 }

cfprEtherLossStatsSymbol OBJECT-TYPE
    SYNTAX       Unsigned64
    MAX-ACCESS   read-only
    STATUS       current
    DESCRIPTION
        "Cisco Firepower ether:LossStats:symbol managed object property"
    ::= { cfprEtherLossStatsEntry 41 }

cfprEtherLossStatsSymbolDelta OBJECT-TYPE
    SYNTAX       Counter64
    MAX-ACCESS   read-only
    STATUS       current
    DESCRIPTION
        "Cisco Firepower ether:LossStats:symbolDelta managed
        object property"
    ::= { cfprEtherLossStatsEntry 42 }

cfprEtherLossStatsSymbolDeltaAvg OBJECT-TYPE
    SYNTAX       Unsigned64
    MAX-ACCESS   read-only
    STATUS       current
    DESCRIPTION
        "Cisco Firepower ether:LossStats:symbolDeltaAvg
        managed object property"
    ::= { cfprEtherLossStatsEntry 43 }

cfprEtherLossStatsSymbolDeltaMax OBJECT-TYPE
    SYNTAX       Unsigned64
    MAX-ACCESS   read-only
    STATUS       current
    DESCRIPTION
        "Cisco Firepower ether:LossStats:symbolDeltaMax
        managed object property"
    ::= { cfprEtherLossStatsEntry 44 }

cfprEtherLossStatsSymbolDeltaMin OBJECT-TYPE
    SYNTAX       Unsigned64
    MAX-ACCESS   read-only
    STATUS       current
    DESCRIPTION
        "Cisco Firepower ether:LossStats:symbolDeltaMin
        managed object property"
    ::= { cfprEtherLossStatsEntry 45 }

cfprEtherLossStatsThresholded OBJECT-TYPE
    SYNTAX       CfprEtherLossStatsThresholded
    MAX-ACCESS   read-only
    STATUS       current
    DESCRIPTION
        "Cisco Firepower ether:LossStats:thresholded managed
        object property"
    ::= { cfprEtherLossStatsEntry 46 }

cfprEtherLossStatsTimeCollected OBJECT-TYPE
    SYNTAX       DateAndTime
    MAX-ACCESS   read-only
    STATUS       current
    DESCRIPTION
        "Cisco Firepower ether:LossStats:timeCollected
        managed object property"
    ::= { cfprEtherLossStatsEntry 47 }

cfprEtherLossStatsUpdate OBJECT-TYPE
    SYNTAX       Gauge32
    MAX-ACCESS   read-only
    STATUS       current
    DESCRIPTION
        "Cisco Firepower ether:LossStats:update managed object property"
    ::= { cfprEtherLossStatsEntry 48 }

cfprEtherLossStatsHistTable OBJECT-TYPE
    SYNTAX           SEQUENCE OF CfprEtherLossStatsHistEntry
    MAX-ACCESS       not-accessible
    STATUS           current
    DESCRIPTION
        "Cisco Firepower ether:LossStatsHist managed object table"
    ::= { cfprEtherObjects 6 }

cfprEtherLossStatsHistEntry OBJECT-TYPE
    SYNTAX           CfprEtherLossStatsHistEntry
    MAX-ACCESS       not-accessible
    STATUS           current
    DESCRIPTION
        "Entry for the cfprEtherLossStatsHistTable table."
    INDEX { cfprEtherLossStatsHistInstanceId }
    ::= { cfprEtherLossStatsHistTable 1 }

CfprEtherLossStatsHistEntry ::= SEQUENCE {
    cfprEtherLossStatsHistInstanceId                                 CfprManagedObjectId,
    cfprEtherLossStatsHistDn                                         CfprManagedObjectDn,
    cfprEtherLossStatsHistRn                                         SnmpAdminString,
    cfprEtherLossStatsHistSQETest                                    Unsigned64,
    cfprEtherLossStatsHistSQETestDelta                               Unsigned64,
    cfprEtherLossStatsHistSQETestDeltaAvg                            Unsigned64,
    cfprEtherLossStatsHistSQETestDeltaMax                            Unsigned64,
    cfprEtherLossStatsHistSQETestDeltaMin                            Unsigned64,
    cfprEtherLossStatsHistCarrierSense                               Unsigned64,
    cfprEtherLossStatsHistCarrierSenseDelta                          Unsigned64,
    cfprEtherLossStatsHistCarrierSenseDeltaAvg                       Unsigned64,
    cfprEtherLossStatsHistCarrierSenseDeltaMax                       Unsigned64,
    cfprEtherLossStatsHistCarrierSenseDeltaMin                       Unsigned64,
    cfprEtherLossStatsHistExcessCollision                            Unsigned64,
    cfprEtherLossStatsHistExcessCollisionDelta                       Unsigned64,
    cfprEtherLossStatsHistExcessCollisionDeltaAvg                    Unsigned64,
    cfprEtherLossStatsHistExcessCollisionDeltaMax                    Unsigned64,
    cfprEtherLossStatsHistExcessCollisionDeltaMin                    Unsigned64,
    cfprEtherLossStatsHistGiants                                     Unsigned64,
    cfprEtherLossStatsHistGiantsDelta                                Unsigned64,
    cfprEtherLossStatsHistGiantsDeltaAvg                             Unsigned64,
    cfprEtherLossStatsHistGiantsDeltaMax                             Unsigned64,
    cfprEtherLossStatsHistGiantsDeltaMin                             Unsigned64,
    cfprEtherLossStatsHistId                                         Unsigned64,
    cfprEtherLossStatsHistLateCollision                              Unsigned64,
    cfprEtherLossStatsHistLateCollisionDelta                         Unsigned64,
    cfprEtherLossStatsHistLateCollisionDeltaAvg                      Unsigned64,
    cfprEtherLossStatsHistLateCollisionDeltaMax                      Unsigned64,
    cfprEtherLossStatsHistLateCollisionDeltaMin                      Unsigned64,
    cfprEtherLossStatsHistMostRecent                                 TruthValue,
    cfprEtherLossStatsHistMultiCollision                             Unsigned64,
    cfprEtherLossStatsHistMultiCollisionDelta                        Unsigned64,
    cfprEtherLossStatsHistMultiCollisionDeltaAvg                     Unsigned64,
    cfprEtherLossStatsHistMultiCollisionDeltaMax                     Unsigned64,
    cfprEtherLossStatsHistMultiCollisionDeltaMin                     Unsigned64,
    cfprEtherLossStatsHistSingleCollision                            Unsigned64,
    cfprEtherLossStatsHistSingleCollisionDelta                       Unsigned64,
    cfprEtherLossStatsHistSingleCollisionDeltaAvg                    Unsigned64,
    cfprEtherLossStatsHistSingleCollisionDeltaMax                    Unsigned64,
    cfprEtherLossStatsHistSingleCollisionDeltaMin                    Unsigned64,
    cfprEtherLossStatsHistSuspect                                    TruthValue,
    cfprEtherLossStatsHistSymbol                                     Unsigned64,
    cfprEtherLossStatsHistSymbolDelta                                Unsigned64,
    cfprEtherLossStatsHistSymbolDeltaAvg                             Unsigned64,
    cfprEtherLossStatsHistSymbolDeltaMax                             Unsigned64,
    cfprEtherLossStatsHistSymbolDeltaMin                             Unsigned64,
    cfprEtherLossStatsHistThresholded                                CfprEtherLossStatsHistThresholded,
    cfprEtherLossStatsHistTimeCollected                              DateAndTime
}

cfprEtherLossStatsHistInstanceId OBJECT-TYPE
    SYNTAX       CfprManagedObjectId
    MAX-ACCESS   not-accessible
    STATUS       current
    DESCRIPTION
        "Instance identifier of the managed object."
    ::= { cfprEtherLossStatsHistEntry 1 }

cfprEtherLossStatsHistDn OBJECT-TYPE
    SYNTAX       CfprManagedObjectDn
    MAX-ACCESS   read-only
    STATUS       current
    DESCRIPTION
        "Cisco Firepower ether:LossStatsHist:dn managed object property"
    ::= { cfprEtherLossStatsHistEntry 2 }

cfprEtherLossStatsHistRn OBJECT-TYPE
    SYNTAX       SnmpAdminString
    MAX-ACCESS   read-only
    STATUS       current
    DESCRIPTION
        "Cisco Firepower ether:LossStatsHist:rn managed object property"
    ::= { cfprEtherLossStatsHistEntry 3 }

cfprEtherLossStatsHistSQETest OBJECT-TYPE
    SYNTAX       Unsigned64
    MAX-ACCESS   read-only
    STATUS       current
    DESCRIPTION
        "Cisco Firepower ether:LossStatsHist:SQETest managed
        object property"
    ::= { cfprEtherLossStatsHistEntry 4 }

cfprEtherLossStatsHistSQETestDelta OBJECT-TYPE
    SYNTAX       Unsigned64
    MAX-ACCESS   read-only
    STATUS       current
    DESCRIPTION
        "Cisco Firepower ether:LossStatsHist:SQETestDelta
        managed object property"
    ::= { cfprEtherLossStatsHistEntry 5 }

cfprEtherLossStatsHistSQETestDeltaAvg OBJECT-TYPE
    SYNTAX       Unsigned64
    MAX-ACCESS   read-only
    STATUS       current
    DESCRIPTION
        "Cisco Firepower ether:LossStatsHist:SQETestDeltaAvg
        managed object property"
    ::= { cfprEtherLossStatsHistEntry 6 }

cfprEtherLossStatsHistSQETestDeltaMax OBJECT-TYPE
    SYNTAX       Unsigned64
    MAX-ACCESS   read-only
    STATUS       current
    DESCRIPTION
        "Cisco Firepower ether:LossStatsHist:SQETestDeltaMax
        managed object property"
    ::= { cfprEtherLossStatsHistEntry 7 }

cfprEtherLossStatsHistSQETestDeltaMin OBJECT-TYPE
    SYNTAX       Unsigned64
    MAX-ACCESS   read-only
    STATUS       current
    DESCRIPTION
        "Cisco Firepower ether:LossStatsHist:SQETestDeltaMin
        managed object property"
    ::= { cfprEtherLossStatsHistEntry 8 }

cfprEtherLossStatsHistCarrierSense OBJECT-TYPE
    SYNTAX       Unsigned64
    MAX-ACCESS   read-only
    STATUS       current
    DESCRIPTION
        "Cisco Firepower ether:LossStatsHist:carrierSense
        managed object property"
    ::= { cfprEtherLossStatsHistEntry 9 }

cfprEtherLossStatsHistCarrierSenseDelta OBJECT-TYPE
    SYNTAX       Unsigned64
    MAX-ACCESS   read-only
    STATUS       current
    DESCRIPTION
        "Cisco Firepower ether:LossStatsHist:carrierSenseDelta
        managed object property"
    ::= { cfprEtherLossStatsHistEntry 10 }

cfprEtherLossStatsHistCarrierSenseDeltaAvg OBJECT-TYPE
    SYNTAX       Unsigned64
    MAX-ACCESS   read-only
    STATUS       current
    DESCRIPTION
        "Cisco Firepower ether:LossStatsHist:carrierSenseDeltaAvg
        managed object property"
    ::= { cfprEtherLossStatsHistEntry 11 }

cfprEtherLossStatsHistCarrierSenseDeltaMax OBJECT-TYPE
    SYNTAX       Unsigned64
    MAX-ACCESS   read-only
    STATUS       current
    DESCRIPTION
        "Cisco Firepower ether:LossStatsHist:carrierSenseDeltaMax
        managed object property"
    ::= { cfprEtherLossStatsHistEntry 12 }

cfprEtherLossStatsHistCarrierSenseDeltaMin OBJECT-TYPE
    SYNTAX       Unsigned64
    MAX-ACCESS   read-only
    STATUS       current
    DESCRIPTION
        "Cisco Firepower ether:LossStatsHist:carrierSenseDeltaMin
        managed object property"
    ::= { cfprEtherLossStatsHistEntry 13 }

cfprEtherLossStatsHistExcessCollision OBJECT-TYPE
    SYNTAX       Unsigned64
    MAX-ACCESS   read-only
    STATUS       current
    DESCRIPTION
        "Cisco Firepower ether:LossStatsHist:excessCollision
        managed object property"
    ::= { cfprEtherLossStatsHistEntry 14 }

cfprEtherLossStatsHistExcessCollisionDelta OBJECT-TYPE
    SYNTAX       Unsigned64
    MAX-ACCESS   read-only
    STATUS       current
    DESCRIPTION
        "Cisco Firepower ether:LossStatsHist:excessCollisionDelta
        managed object property"
    ::= { cfprEtherLossStatsHistEntry 15 }

cfprEtherLossStatsHistExcessCollisionDeltaAvg OBJECT-TYPE
    SYNTAX       Unsigned64
    MAX-ACCESS   read-only
    STATUS       current
    DESCRIPTION
        "Cisco Firepower ether:LossStatsHist:excessCollisionDeltaAvg
        managed object property"
    ::= { cfprEtherLossStatsHistEntry 16 }

cfprEtherLossStatsHistExcessCollisionDeltaMax OBJECT-TYPE
    SYNTAX       Unsigned64
    MAX-ACCESS   read-only
    STATUS       current
    DESCRIPTION
        "Cisco Firepower ether:LossStatsHist:excessCollisionDeltaMax
        managed object property"
    ::= { cfprEtherLossStatsHistEntry 17 }

cfprEtherLossStatsHistExcessCollisionDeltaMin OBJECT-TYPE
    SYNTAX       Unsigned64
    MAX-ACCESS   read-only
    STATUS       current
    DESCRIPTION
        "Cisco Firepower ether:LossStatsHist:excessCollisionDeltaMin
        managed object property"
    ::= { cfprEtherLossStatsHistEntry 18 }

cfprEtherLossStatsHistGiants OBJECT-TYPE
    SYNTAX       Unsigned64
    MAX-ACCESS   read-only
    STATUS       current
    DESCRIPTION
        "Cisco Firepower ether:LossStatsHist:giants managed
        object property"
    ::= { cfprEtherLossStatsHistEntry 19 }

cfprEtherLossStatsHistGiantsDelta OBJECT-TYPE
    SYNTAX       Unsigned64
    MAX-ACCESS   read-only
    STATUS       current
    DESCRIPTION
        "Cisco Firepower ether:LossStatsHist:giantsDelta
        managed object property"
    ::= { cfprEtherLossStatsHistEntry 20 }

cfprEtherLossStatsHistGiantsDeltaAvg OBJECT-TYPE
    SYNTAX       Unsigned64
    MAX-ACCESS   read-only
    STATUS       current
    DESCRIPTION
        "Cisco Firepower ether:LossStatsHist:giantsDeltaAvg
        managed object property"
    ::= { cfprEtherLossStatsHistEntry 21 }

cfprEtherLossStatsHistGiantsDeltaMax OBJECT-TYPE
    SYNTAX       Unsigned64
    MAX-ACCESS   read-only
    STATUS       current
    DESCRIPTION
        "Cisco Firepower ether:LossStatsHist:giantsDeltaMax
        managed object property"
    ::= { cfprEtherLossStatsHistEntry 22 }

cfprEtherLossStatsHistGiantsDeltaMin OBJECT-TYPE
    SYNTAX       Unsigned64
    MAX-ACCESS   read-only
    STATUS       current
    DESCRIPTION
        "Cisco Firepower ether:LossStatsHist:giantsDeltaMin
        managed object property"
    ::= { cfprEtherLossStatsHistEntry 23 }

cfprEtherLossStatsHistId OBJECT-TYPE
    SYNTAX       Unsigned64
    MAX-ACCESS   read-only
    STATUS       current
    DESCRIPTION
        "Cisco Firepower ether:LossStatsHist:id managed object property"
    ::= { cfprEtherLossStatsHistEntry 24 }

cfprEtherLossStatsHistLateCollision OBJECT-TYPE
    SYNTAX       Unsigned64
    MAX-ACCESS   read-only
    STATUS       current
    DESCRIPTION
        "Cisco Firepower ether:LossStatsHist:lateCollision
        managed object property"
    ::= { cfprEtherLossStatsHistEntry 25 }

cfprEtherLossStatsHistLateCollisionDelta OBJECT-TYPE
    SYNTAX       Unsigned64
    MAX-ACCESS   read-only
    STATUS       current
    DESCRIPTION
        "Cisco Firepower ether:LossStatsHist:lateCollisionDelta
        managed object property"
    ::= { cfprEtherLossStatsHistEntry 26 }

cfprEtherLossStatsHistLateCollisionDeltaAvg OBJECT-TYPE
    SYNTAX       Unsigned64
    MAX-ACCESS   read-only
    STATUS       current
    DESCRIPTION
        "Cisco Firepower ether:LossStatsHist:lateCollisionDeltaAvg
        managed object property"
    ::= { cfprEtherLossStatsHistEntry 27 }

cfprEtherLossStatsHistLateCollisionDeltaMax OBJECT-TYPE
    SYNTAX       Unsigned64
    MAX-ACCESS   read-only
    STATUS       current
    DESCRIPTION
        "Cisco Firepower ether:LossStatsHist:lateCollisionDeltaMax
        managed object property"
    ::= { cfprEtherLossStatsHistEntry 28 }

cfprEtherLossStatsHistLateCollisionDeltaMin OBJECT-TYPE
    SYNTAX       Unsigned64
    MAX-ACCESS   read-only
    STATUS       current
    DESCRIPTION
        "Cisco Firepower ether:LossStatsHist:lateCollisionDeltaMin
        managed object property"
    ::= { cfprEtherLossStatsHistEntry 29 }

cfprEtherLossStatsHistMostRecent OBJECT-TYPE
    SYNTAX       TruthValue
    MAX-ACCESS   read-only
    STATUS       current
    DESCRIPTION
        "Cisco Firepower ether:LossStatsHist:mostRecent
        managed object property"
    ::= { cfprEtherLossStatsHistEntry 30 }

cfprEtherLossStatsHistMultiCollision OBJECT-TYPE
    SYNTAX       Unsigned64
    MAX-ACCESS   read-only
    STATUS       current
    DESCRIPTION
        "Cisco Firepower ether:LossStatsHist:multiCollision
        managed object property"
    ::= { cfprEtherLossStatsHistEntry 31 }

cfprEtherLossStatsHistMultiCollisionDelta OBJECT-TYPE
    SYNTAX       Unsigned64
    MAX-ACCESS   read-only
    STATUS       current
    DESCRIPTION
        "Cisco Firepower ether:LossStatsHist:multiCollisionDelta
        managed object property"
    ::= { cfprEtherLossStatsHistEntry 32 }

cfprEtherLossStatsHistMultiCollisionDeltaAvg OBJECT-TYPE
    SYNTAX       Unsigned64
    MAX-ACCESS   read-only
    STATUS       current
    DESCRIPTION
        "Cisco Firepower ether:LossStatsHist:multiCollisionDeltaAvg
        managed object property"
    ::= { cfprEtherLossStatsHistEntry 33 }

cfprEtherLossStatsHistMultiCollisionDeltaMax OBJECT-TYPE
    SYNTAX       Unsigned64
    MAX-ACCESS   read-only
    STATUS       current
    DESCRIPTION
        "Cisco Firepower ether:LossStatsHist:multiCollisionDeltaMax
        managed object property"
    ::= { cfprEtherLossStatsHistEntry 34 }

cfprEtherLossStatsHistMultiCollisionDeltaMin OBJECT-TYPE
    SYNTAX       Unsigned64
    MAX-ACCESS   read-only
    STATUS       current
    DESCRIPTION
        "Cisco Firepower ether:LossStatsHist:multiCollisionDeltaMin
        managed object property"
    ::= { cfprEtherLossStatsHistEntry 35 }

cfprEtherLossStatsHistSingleCollision OBJECT-TYPE
    SYNTAX       Unsigned64
    MAX-ACCESS   read-only
    STATUS       current
    DESCRIPTION
        "Cisco Firepower ether:LossStatsHist:singleCollision
        managed object property"
    ::= { cfprEtherLossStatsHistEntry 36 }

cfprEtherLossStatsHistSingleCollisionDelta OBJECT-TYPE
    SYNTAX       Unsigned64
    MAX-ACCESS   read-only
    STATUS       current
    DESCRIPTION
        "Cisco Firepower ether:LossStatsHist:singleCollisionDelta
        managed object property"
    ::= { cfprEtherLossStatsHistEntry 37 }

cfprEtherLossStatsHistSingleCollisionDeltaAvg OBJECT-TYPE
    SYNTAX       Unsigned64
    MAX-ACCESS   read-only
    STATUS       current
    DESCRIPTION
        "Cisco Firepower ether:LossStatsHist:singleCollisionDeltaAvg
        managed object property"
    ::= { cfprEtherLossStatsHistEntry 38 }

cfprEtherLossStatsHistSingleCollisionDeltaMax OBJECT-TYPE
    SYNTAX       Unsigned64
    MAX-ACCESS   read-only
    STATUS       current
    DESCRIPTION
        "Cisco Firepower ether:LossStatsHist:singleCollisionDeltaMax
        managed object property"
    ::= { cfprEtherLossStatsHistEntry 39 }

cfprEtherLossStatsHistSingleCollisionDeltaMin OBJECT-TYPE
    SYNTAX       Unsigned64
    MAX-ACCESS   read-only
    STATUS       current
    DESCRIPTION
        "Cisco Firepower ether:LossStatsHist:singleCollisionDeltaMin
        managed object property"
    ::= { cfprEtherLossStatsHistEntry 40 }

cfprEtherLossStatsHistSuspect OBJECT-TYPE
    SYNTAX       TruthValue
    MAX-ACCESS   read-only
    STATUS       current
    DESCRIPTION
        "Cisco Firepower ether:LossStatsHist:suspect managed
        object property"
    ::= { cfprEtherLossStatsHistEntry 41 }

cfprEtherLossStatsHistSymbol OBJECT-TYPE
    SYNTAX       Unsigned64
    MAX-ACCESS   read-only
    STATUS       current
    DESCRIPTION
        "Cisco Firepower ether:LossStatsHist:symbol managed
        object property"
    ::= { cfprEtherLossStatsHistEntry 42 }

cfprEtherLossStatsHistSymbolDelta OBJECT-TYPE
    SYNTAX       Unsigned64
    MAX-ACCESS   read-only
    STATUS       current
    DESCRIPTION
        "Cisco Firepower ether:LossStatsHist:symbolDelta
        managed object property"
    ::= { cfprEtherLossStatsHistEntry 43 }

cfprEtherLossStatsHistSymbolDeltaAvg OBJECT-TYPE
    SYNTAX       Unsigned64
    MAX-ACCESS   read-only
    STATUS       current
    DESCRIPTION
        "Cisco Firepower ether:LossStatsHist:symbolDeltaAvg
        managed object property"
    ::= { cfprEtherLossStatsHistEntry 44 }

cfprEtherLossStatsHistSymbolDeltaMax OBJECT-TYPE
    SYNTAX       Unsigned64
    MAX-ACCESS   read-only
    STATUS       current
    DESCRIPTION
        "Cisco Firepower ether:LossStatsHist:symbolDeltaMax
        managed object property"
    ::= { cfprEtherLossStatsHistEntry 45 }

cfprEtherLossStatsHistSymbolDeltaMin OBJECT-TYPE
    SYNTAX       Unsigned64
    MAX-ACCESS   read-only
    STATUS       current
    DESCRIPTION
        "Cisco Firepower ether:LossStatsHist:symbolDeltaMin
        managed object property"
    ::= { cfprEtherLossStatsHistEntry 46 }

cfprEtherLossStatsHistThresholded OBJECT-TYPE
    SYNTAX       CfprEtherLossStatsHistThresholded
    MAX-ACCESS   read-only
    STATUS       current
    DESCRIPTION
        "Cisco Firepower ether:LossStatsHist:thresholded
        managed object property"
    ::= { cfprEtherLossStatsHistEntry 47 }

cfprEtherLossStatsHistTimeCollected OBJECT-TYPE
    SYNTAX       DateAndTime
    MAX-ACCESS   read-only
    STATUS       current
    DESCRIPTION
        "Cisco Firepower ether:LossStatsHist:timeCollected
        managed object property"
    ::= { cfprEtherLossStatsHistEntry 48 }

cfprEtherNiErrStatsTable OBJECT-TYPE
    SYNTAX           SEQUENCE OF CfprEtherNiErrStatsEntry
    MAX-ACCESS       not-accessible
    STATUS           current
    DESCRIPTION
        "Cisco Firepower ether:NiErrStats managed object table"
    ::= { cfprEtherObjects 7 }

cfprEtherNiErrStatsEntry OBJECT-TYPE
    SYNTAX           CfprEtherNiErrStatsEntry
    MAX-ACCESS       not-accessible
    STATUS           current
    DESCRIPTION
        "Entry for the cfprEtherNiErrStatsTable table."
    INDEX { cfprEtherNiErrStatsInstanceId }
    ::= { cfprEtherNiErrStatsTable 1 }

CfprEtherNiErrStatsEntry ::= SEQUENCE {
    cfprEtherNiErrStatsInstanceId                                    CfprManagedObjectId,
    cfprEtherNiErrStatsDn                                            CfprManagedObjectDn,
    cfprEtherNiErrStatsRn                                            SnmpAdminString,
    cfprEtherNiErrStatsCrc                                           Unsigned64,
    cfprEtherNiErrStatsCrcDelta                                      Counter64,
    cfprEtherNiErrStatsCrcDeltaAvg                                   Unsigned64,
    cfprEtherNiErrStatsCrcDeltaMax                                   Unsigned64,
    cfprEtherNiErrStatsCrcDeltaMin                                   Unsigned64,
    cfprEtherNiErrStatsFrameTx                                       Unsigned64,
    cfprEtherNiErrStatsFrameTxDelta                                  Counter64,
    cfprEtherNiErrStatsFrameTxDeltaAvg                               Unsigned64,
    cfprEtherNiErrStatsFrameTxDeltaMax                               Unsigned64,
    cfprEtherNiErrStatsFrameTxDeltaMin                               Unsigned64,
    cfprEtherNiErrStatsInRange                                       Unsigned64,
    cfprEtherNiErrStatsInRangeDelta                                  Counter64,
    cfprEtherNiErrStatsInRangeDeltaAvg                               Unsigned64,
    cfprEtherNiErrStatsInRangeDeltaMax                               Unsigned64,
    cfprEtherNiErrStatsInRangeDeltaMin                               Unsigned64,
    cfprEtherNiErrStatsIntervals                                     Gauge32,
    cfprEtherNiErrStatsSuspect                                       TruthValue,
    cfprEtherNiErrStatsThresholded                                   CfprEtherNiErrStatsThresholded,
    cfprEtherNiErrStatsTimeCollected                                 DateAndTime,
    cfprEtherNiErrStatsTooLong                                       Unsigned64,
    cfprEtherNiErrStatsTooLongDelta                                  Counter64,
    cfprEtherNiErrStatsTooLongDeltaAvg                               Unsigned64,
    cfprEtherNiErrStatsTooLongDeltaMax                               Unsigned64,
    cfprEtherNiErrStatsTooLongDeltaMin                               Unsigned64,
    cfprEtherNiErrStatsTooShort                                      Unsigned64,
    cfprEtherNiErrStatsTooShortDelta                                 Counter64,
    cfprEtherNiErrStatsTooShortDeltaAvg                              Unsigned64,
    cfprEtherNiErrStatsTooShortDeltaMax                              Unsigned64,
    cfprEtherNiErrStatsTooShortDeltaMin                              Unsigned64,
    cfprEtherNiErrStatsUpdate                                        Gauge32
}

cfprEtherNiErrStatsInstanceId OBJECT-TYPE
    SYNTAX       CfprManagedObjectId
    MAX-ACCESS   not-accessible
    STATUS       current
    DESCRIPTION
        "Instance identifier of the managed object."
    ::= { cfprEtherNiErrStatsEntry 1 }

cfprEtherNiErrStatsDn OBJECT-TYPE
    SYNTAX       CfprManagedObjectDn
    MAX-ACCESS   read-only
    STATUS       current
    DESCRIPTION
        "Cisco Firepower ether:NiErrStats:dn managed object property"
    ::= { cfprEtherNiErrStatsEntry 2 }

cfprEtherNiErrStatsRn OBJECT-TYPE
    SYNTAX       SnmpAdminString
    MAX-ACCESS   read-only
    STATUS       current
    DESCRIPTION
        "Cisco Firepower ether:NiErrStats:rn managed object property"
    ::= { cfprEtherNiErrStatsEntry 3 }

cfprEtherNiErrStatsCrc OBJECT-TYPE
    SYNTAX       Unsigned64
    MAX-ACCESS   read-only
    STATUS       current
    DESCRIPTION
        "Cisco Firepower ether:NiErrStats:crc managed object property"
    ::= { cfprEtherNiErrStatsEntry 4 }

cfprEtherNiErrStatsCrcDelta OBJECT-TYPE
    SYNTAX       Counter64
    MAX-ACCESS   read-only
    STATUS       current
    DESCRIPTION
        "Cisco Firepower ether:NiErrStats:crcDelta managed
        object property"
    ::= { cfprEtherNiErrStatsEntry 5 }

cfprEtherNiErrStatsCrcDeltaAvg OBJECT-TYPE
    SYNTAX       Unsigned64
    MAX-ACCESS   read-only
    STATUS       current
    DESCRIPTION
        "Cisco Firepower ether:NiErrStats:crcDeltaAvg managed
        object property"
    ::= { cfprEtherNiErrStatsEntry 6 }

cfprEtherNiErrStatsCrcDeltaMax OBJECT-TYPE
    SYNTAX       Unsigned64
    MAX-ACCESS   read-only
    STATUS       current
    DESCRIPTION
        "Cisco Firepower ether:NiErrStats:crcDeltaMax managed
        object property"
    ::= { cfprEtherNiErrStatsEntry 7 }

cfprEtherNiErrStatsCrcDeltaMin OBJECT-TYPE
    SYNTAX       Unsigned64
    MAX-ACCESS   read-only
    STATUS       current
    DESCRIPTION
        "Cisco Firepower ether:NiErrStats:crcDeltaMin managed
        object property"
    ::= { cfprEtherNiErrStatsEntry 8 }

cfprEtherNiErrStatsFrameTx OBJECT-TYPE
    SYNTAX       Unsigned64
    MAX-ACCESS   read-only
    STATUS       current
    DESCRIPTION
        "Cisco Firepower ether:NiErrStats:frameTx managed object property"
    ::= { cfprEtherNiErrStatsEntry 9 }

cfprEtherNiErrStatsFrameTxDelta OBJECT-TYPE
    SYNTAX       Counter64
    MAX-ACCESS   read-only
    STATUS       current
    DESCRIPTION
        "Cisco Firepower ether:NiErrStats:frameTxDelta
        managed object property"
    ::= { cfprEtherNiErrStatsEntry 10 }

cfprEtherNiErrStatsFrameTxDeltaAvg OBJECT-TYPE
    SYNTAX       Unsigned64
    MAX-ACCESS   read-only
    STATUS       current
    DESCRIPTION
        "Cisco Firepower ether:NiErrStats:frameTxDeltaAvg
        managed object property"
    ::= { cfprEtherNiErrStatsEntry 11 }

cfprEtherNiErrStatsFrameTxDeltaMax OBJECT-TYPE
    SYNTAX       Unsigned64
    MAX-ACCESS   read-only
    STATUS       current
    DESCRIPTION
        "Cisco Firepower ether:NiErrStats:frameTxDeltaMax
        managed object property"
    ::= { cfprEtherNiErrStatsEntry 12 }

cfprEtherNiErrStatsFrameTxDeltaMin OBJECT-TYPE
    SYNTAX       Unsigned64
    MAX-ACCESS   read-only
    STATUS       current
    DESCRIPTION
        "Cisco Firepower ether:NiErrStats:frameTxDeltaMin
        managed object property"
    ::= { cfprEtherNiErrStatsEntry 13 }

cfprEtherNiErrStatsInRange OBJECT-TYPE
    SYNTAX       Unsigned64
    MAX-ACCESS   read-only
    STATUS       current
    DESCRIPTION
        "Cisco Firepower ether:NiErrStats:inRange managed object property"
    ::= { cfprEtherNiErrStatsEntry 14 }

cfprEtherNiErrStatsInRangeDelta OBJECT-TYPE
    SYNTAX       Counter64
    MAX-ACCESS   read-only
    STATUS       current
    DESCRIPTION
        "Cisco Firepower ether:NiErrStats:inRangeDelta
        managed object property"
    ::= { cfprEtherNiErrStatsEntry 15 }

cfprEtherNiErrStatsInRangeDeltaAvg OBJECT-TYPE
    SYNTAX       Unsigned64
    MAX-ACCESS   read-only
    STATUS       current
    DESCRIPTION
        "Cisco Firepower ether:NiErrStats:inRangeDeltaAvg
        managed object property"
    ::= { cfprEtherNiErrStatsEntry 16 }

cfprEtherNiErrStatsInRangeDeltaMax OBJECT-TYPE
    SYNTAX       Unsigned64
    MAX-ACCESS   read-only
    STATUS       current
    DESCRIPTION
        "Cisco Firepower ether:NiErrStats:inRangeDeltaMax
        managed object property"
    ::= { cfprEtherNiErrStatsEntry 17 }

cfprEtherNiErrStatsInRangeDeltaMin OBJECT-TYPE
    SYNTAX       Unsigned64
    MAX-ACCESS   read-only
    STATUS       current
    DESCRIPTION
        "Cisco Firepower ether:NiErrStats:inRangeDeltaMin
        managed object property"
    ::= { cfprEtherNiErrStatsEntry 18 }

cfprEtherNiErrStatsIntervals OBJECT-TYPE
    SYNTAX       Gauge32
    MAX-ACCESS   read-only
    STATUS       current
    DESCRIPTION
        "Cisco Firepower ether:NiErrStats:intervals managed
        object property"
    ::= { cfprEtherNiErrStatsEntry 19 }

cfprEtherNiErrStatsSuspect OBJECT-TYPE
    SYNTAX       TruthValue
    MAX-ACCESS   read-only
    STATUS       current
    DESCRIPTION
        "Cisco Firepower ether:NiErrStats:suspect managed object property"
    ::= { cfprEtherNiErrStatsEntry 20 }

cfprEtherNiErrStatsThresholded OBJECT-TYPE
    SYNTAX       CfprEtherNiErrStatsThresholded
    MAX-ACCESS   read-only
    STATUS       current
    DESCRIPTION
        "Cisco Firepower ether:NiErrStats:thresholded managed
        object property"
    ::= { cfprEtherNiErrStatsEntry 21 }

cfprEtherNiErrStatsTimeCollected OBJECT-TYPE
    SYNTAX       DateAndTime
    MAX-ACCESS   read-only
    STATUS       current
    DESCRIPTION
        "Cisco Firepower ether:NiErrStats:timeCollected
        managed object property"
    ::= { cfprEtherNiErrStatsEntry 22 }

cfprEtherNiErrStatsTooLong OBJECT-TYPE
    SYNTAX       Unsigned64
    MAX-ACCESS   read-only
    STATUS       current
    DESCRIPTION
        "Cisco Firepower ether:NiErrStats:tooLong managed object property"
    ::= { cfprEtherNiErrStatsEntry 23 }

cfprEtherNiErrStatsTooLongDelta OBJECT-TYPE
    SYNTAX       Counter64
    MAX-ACCESS   read-only
    STATUS       current
    DESCRIPTION
        "Cisco Firepower ether:NiErrStats:tooLongDelta
        managed object property"
    ::= { cfprEtherNiErrStatsEntry 24 }

cfprEtherNiErrStatsTooLongDeltaAvg OBJECT-TYPE
    SYNTAX       Unsigned64
    MAX-ACCESS   read-only
    STATUS       current
    DESCRIPTION
        "Cisco Firepower ether:NiErrStats:tooLongDeltaAvg
        managed object property"
    ::= { cfprEtherNiErrStatsEntry 25 }

cfprEtherNiErrStatsTooLongDeltaMax OBJECT-TYPE
    SYNTAX       Unsigned64
    MAX-ACCESS   read-only
    STATUS       current
    DESCRIPTION
        "Cisco Firepower ether:NiErrStats:tooLongDeltaMax
        managed object property"
    ::= { cfprEtherNiErrStatsEntry 26 }

cfprEtherNiErrStatsTooLongDeltaMin OBJECT-TYPE
    SYNTAX       Unsigned64
    MAX-ACCESS   read-only
    STATUS       current
    DESCRIPTION
        "Cisco Firepower ether:NiErrStats:tooLongDeltaMin
        managed object property"
    ::= { cfprEtherNiErrStatsEntry 27 }

cfprEtherNiErrStatsTooShort OBJECT-TYPE
    SYNTAX       Unsigned64
    MAX-ACCESS   read-only
    STATUS       current
    DESCRIPTION
        "Cisco Firepower ether:NiErrStats:tooShort managed
        object property"
    ::= { cfprEtherNiErrStatsEntry 28 }

cfprEtherNiErrStatsTooShortDelta OBJECT-TYPE
    SYNTAX       Counter64
    MAX-ACCESS   read-only
    STATUS       current
    DESCRIPTION
        "Cisco Firepower ether:NiErrStats:tooShortDelta
        managed object property"
    ::= { cfprEtherNiErrStatsEntry 29 }

cfprEtherNiErrStatsTooShortDeltaAvg OBJECT-TYPE
    SYNTAX       Unsigned64
    MAX-ACCESS   read-only
    STATUS       current
    DESCRIPTION
        "Cisco Firepower ether:NiErrStats:tooShortDeltaAvg
        managed object property"
    ::= { cfprEtherNiErrStatsEntry 30 }

cfprEtherNiErrStatsTooShortDeltaMax OBJECT-TYPE
    SYNTAX       Unsigned64
    MAX-ACCESS   read-only
    STATUS       current
    DESCRIPTION
        "Cisco Firepower ether:NiErrStats:tooShortDeltaMax
        managed object property"
    ::= { cfprEtherNiErrStatsEntry 31 }

cfprEtherNiErrStatsTooShortDeltaMin OBJECT-TYPE
    SYNTAX       Unsigned64
    MAX-ACCESS   read-only
    STATUS       current
    DESCRIPTION
        "Cisco Firepower ether:NiErrStats:tooShortDeltaMin
        managed object property"
    ::= { cfprEtherNiErrStatsEntry 32 }

cfprEtherNiErrStatsUpdate OBJECT-TYPE
    SYNTAX       Gauge32
    MAX-ACCESS   read-only
    STATUS       current
    DESCRIPTION
        "Cisco Firepower ether:NiErrStats:update managed object property"
    ::= { cfprEtherNiErrStatsEntry 33 }

cfprEtherNiErrStatsHistTable OBJECT-TYPE
    SYNTAX           SEQUENCE OF CfprEtherNiErrStatsHistEntry
    MAX-ACCESS       not-accessible
    STATUS           current
    DESCRIPTION
        "Cisco Firepower ether:NiErrStatsHist managed object table"
    ::= { cfprEtherObjects 8 }

cfprEtherNiErrStatsHistEntry OBJECT-TYPE
    SYNTAX           CfprEtherNiErrStatsHistEntry
    MAX-ACCESS       not-accessible
    STATUS           current
    DESCRIPTION
        "Entry for the cfprEtherNiErrStatsHistTable table."
    INDEX { cfprEtherNiErrStatsHistInstanceId }
    ::= { cfprEtherNiErrStatsHistTable 1 }

CfprEtherNiErrStatsHistEntry ::= SEQUENCE {
    cfprEtherNiErrStatsHistInstanceId                                CfprManagedObjectId,
    cfprEtherNiErrStatsHistDn                                        CfprManagedObjectDn,
    cfprEtherNiErrStatsHistRn                                        SnmpAdminString,
    cfprEtherNiErrStatsHistCrc                                       Unsigned64,
    cfprEtherNiErrStatsHistCrcDelta                                  Unsigned64,
    cfprEtherNiErrStatsHistCrcDeltaAvg                               Unsigned64,
    cfprEtherNiErrStatsHistCrcDeltaMax                               Unsigned64,
    cfprEtherNiErrStatsHistCrcDeltaMin                               Unsigned64,
    cfprEtherNiErrStatsHistFrameTx                                   Unsigned64,
    cfprEtherNiErrStatsHistFrameTxDelta                              Unsigned64,
    cfprEtherNiErrStatsHistFrameTxDeltaAvg                           Unsigned64,
    cfprEtherNiErrStatsHistFrameTxDeltaMax                           Unsigned64,
    cfprEtherNiErrStatsHistFrameTxDeltaMin                           Unsigned64,
    cfprEtherNiErrStatsHistId                                        Unsigned64,
    cfprEtherNiErrStatsHistInRange                                   Unsigned64,
    cfprEtherNiErrStatsHistInRangeDelta                              Unsigned64,
    cfprEtherNiErrStatsHistInRangeDeltaAvg                           Unsigned64,
    cfprEtherNiErrStatsHistInRangeDeltaMax                           Unsigned64,
    cfprEtherNiErrStatsHistInRangeDeltaMin                           Unsigned64,
    cfprEtherNiErrStatsHistMostRecent                                TruthValue,
    cfprEtherNiErrStatsHistSuspect                                   TruthValue,
    cfprEtherNiErrStatsHistThresholded                               CfprEtherNiErrStatsHistThresholded,
    cfprEtherNiErrStatsHistTimeCollected                             DateAndTime,
    cfprEtherNiErrStatsHistTooLong                                   Unsigned64,
    cfprEtherNiErrStatsHistTooLongDelta                              Unsigned64,
    cfprEtherNiErrStatsHistTooLongDeltaAvg                           Unsigned64,
    cfprEtherNiErrStatsHistTooLongDeltaMax                           Unsigned64,
    cfprEtherNiErrStatsHistTooLongDeltaMin                           Unsigned64,
    cfprEtherNiErrStatsHistTooShort                                  Unsigned64,
    cfprEtherNiErrStatsHistTooShortDelta                             Unsigned64,
    cfprEtherNiErrStatsHistTooShortDeltaAvg                          Unsigned64,
    cfprEtherNiErrStatsHistTooShortDeltaMax                          Unsigned64,
    cfprEtherNiErrStatsHistTooShortDeltaMin                          Unsigned64
}

cfprEtherNiErrStatsHistInstanceId OBJECT-TYPE
    SYNTAX       CfprManagedObjectId
    MAX-ACCESS   not-accessible
    STATUS       current
    DESCRIPTION
        "Instance identifier of the managed object."
    ::= { cfprEtherNiErrStatsHistEntry 1 }

cfprEtherNiErrStatsHistDn OBJECT-TYPE
    SYNTAX       CfprManagedObjectDn
    MAX-ACCESS   read-only
    STATUS       current
    DESCRIPTION
        "Cisco Firepower ether:NiErrStatsHist:dn managed object property"
    ::= { cfprEtherNiErrStatsHistEntry 2 }

cfprEtherNiErrStatsHistRn OBJECT-TYPE
    SYNTAX       SnmpAdminString
    MAX-ACCESS   read-only
    STATUS       current
    DESCRIPTION
        "Cisco Firepower ether:NiErrStatsHist:rn managed object property"
    ::= { cfprEtherNiErrStatsHistEntry 3 }

cfprEtherNiErrStatsHistCrc OBJECT-TYPE
    SYNTAX       Unsigned64
    MAX-ACCESS   read-only
    STATUS       current
    DESCRIPTION
        "Cisco Firepower ether:NiErrStatsHist:crc managed object property"
    ::= { cfprEtherNiErrStatsHistEntry 4 }

cfprEtherNiErrStatsHistCrcDelta OBJECT-TYPE
    SYNTAX       Unsigned64
    MAX-ACCESS   read-only
    STATUS       current
    DESCRIPTION
        "Cisco Firepower ether:NiErrStatsHist:crcDelta
        managed object property"
    ::= { cfprEtherNiErrStatsHistEntry 5 }

cfprEtherNiErrStatsHistCrcDeltaAvg OBJECT-TYPE
    SYNTAX       Unsigned64
    MAX-ACCESS   read-only
    STATUS       current
    DESCRIPTION
        "Cisco Firepower ether:NiErrStatsHist:crcDeltaAvg
        managed object property"
    ::= { cfprEtherNiErrStatsHistEntry 6 }

cfprEtherNiErrStatsHistCrcDeltaMax OBJECT-TYPE
    SYNTAX       Unsigned64
    MAX-ACCESS   read-only
    STATUS       current
    DESCRIPTION
        "Cisco Firepower ether:NiErrStatsHist:crcDeltaMax
        managed object property"
    ::= { cfprEtherNiErrStatsHistEntry 7 }

cfprEtherNiErrStatsHistCrcDeltaMin OBJECT-TYPE
    SYNTAX       Unsigned64
    MAX-ACCESS   read-only
    STATUS       current
    DESCRIPTION
        "Cisco Firepower ether:NiErrStatsHist:crcDeltaMin
        managed object property"
    ::= { cfprEtherNiErrStatsHistEntry 8 }

cfprEtherNiErrStatsHistFrameTx OBJECT-TYPE
    SYNTAX       Unsigned64
    MAX-ACCESS   read-only
    STATUS       current
    DESCRIPTION
        "Cisco Firepower ether:NiErrStatsHist:frameTx managed
        object property"
    ::= { cfprEtherNiErrStatsHistEntry 9 }

cfprEtherNiErrStatsHistFrameTxDelta OBJECT-TYPE
    SYNTAX       Unsigned64
    MAX-ACCESS   read-only
    STATUS       current
    DESCRIPTION
        "Cisco Firepower ether:NiErrStatsHist:frameTxDelta
        managed object property"
    ::= { cfprEtherNiErrStatsHistEntry 10 }

cfprEtherNiErrStatsHistFrameTxDeltaAvg OBJECT-TYPE
    SYNTAX       Unsigned64
    MAX-ACCESS   read-only
    STATUS       current
    DESCRIPTION
        "Cisco Firepower ether:NiErrStatsHist:frameTxDeltaAvg
        managed object property"
    ::= { cfprEtherNiErrStatsHistEntry 11 }

cfprEtherNiErrStatsHistFrameTxDeltaMax OBJECT-TYPE
    SYNTAX       Unsigned64
    MAX-ACCESS   read-only
    STATUS       current
    DESCRIPTION
        "Cisco Firepower ether:NiErrStatsHist:frameTxDeltaMax
        managed object property"
    ::= { cfprEtherNiErrStatsHistEntry 12 }

cfprEtherNiErrStatsHistFrameTxDeltaMin OBJECT-TYPE
    SYNTAX       Unsigned64
    MAX-ACCESS   read-only
    STATUS       current
    DESCRIPTION
        "Cisco Firepower ether:NiErrStatsHist:frameTxDeltaMin
        managed object property"
    ::= { cfprEtherNiErrStatsHistEntry 13 }

cfprEtherNiErrStatsHistId OBJECT-TYPE
    SYNTAX       Unsigned64
    MAX-ACCESS   read-only
    STATUS       current
    DESCRIPTION
        "Cisco Firepower ether:NiErrStatsHist:id managed object property"
    ::= { cfprEtherNiErrStatsHistEntry 14 }

cfprEtherNiErrStatsHistInRange OBJECT-TYPE
    SYNTAX       Unsigned64
    MAX-ACCESS   read-only
    STATUS       current
    DESCRIPTION
        "Cisco Firepower ether:NiErrStatsHist:inRange managed
        object property"
    ::= { cfprEtherNiErrStatsHistEntry 15 }

cfprEtherNiErrStatsHistInRangeDelta OBJECT-TYPE
    SYNTAX       Unsigned64
    MAX-ACCESS   read-only
    STATUS       current
    DESCRIPTION
        "Cisco Firepower ether:NiErrStatsHist:inRangeDelta
        managed object property"
    ::= { cfprEtherNiErrStatsHistEntry 16 }

cfprEtherNiErrStatsHistInRangeDeltaAvg OBJECT-TYPE
    SYNTAX       Unsigned64
    MAX-ACCESS   read-only
    STATUS       current
    DESCRIPTION
        "Cisco Firepower ether:NiErrStatsHist:inRangeDeltaAvg
        managed object property"
    ::= { cfprEtherNiErrStatsHistEntry 17 }

cfprEtherNiErrStatsHistInRangeDeltaMax OBJECT-TYPE
    SYNTAX       Unsigned64
    MAX-ACCESS   read-only
    STATUS       current
    DESCRIPTION
        "Cisco Firepower ether:NiErrStatsHist:inRangeDeltaMax
        managed object property"
    ::= { cfprEtherNiErrStatsHistEntry 18 }

cfprEtherNiErrStatsHistInRangeDeltaMin OBJECT-TYPE
    SYNTAX       Unsigned64
    MAX-ACCESS   read-only
    STATUS       current
    DESCRIPTION
        "Cisco Firepower ether:NiErrStatsHist:inRangeDeltaMin
        managed object property"
    ::= { cfprEtherNiErrStatsHistEntry 19 }

cfprEtherNiErrStatsHistMostRecent OBJECT-TYPE
    SYNTAX       TruthValue
    MAX-ACCESS   read-only
    STATUS       current
    DESCRIPTION
        "Cisco Firepower ether:NiErrStatsHist:mostRecent
        managed object property"
    ::= { cfprEtherNiErrStatsHistEntry 20 }

cfprEtherNiErrStatsHistSuspect OBJECT-TYPE
    SYNTAX       TruthValue
    MAX-ACCESS   read-only
    STATUS       current
    DESCRIPTION
        "Cisco Firepower ether:NiErrStatsHist:suspect managed
        object property"
    ::= { cfprEtherNiErrStatsHistEntry 21 }

cfprEtherNiErrStatsHistThresholded OBJECT-TYPE
    SYNTAX       CfprEtherNiErrStatsHistThresholded
    MAX-ACCESS   read-only
    STATUS       current
    DESCRIPTION
        "Cisco Firepower ether:NiErrStatsHist:thresholded
        managed object property"
    ::= { cfprEtherNiErrStatsHistEntry 22 }

cfprEtherNiErrStatsHistTimeCollected OBJECT-TYPE
    SYNTAX       DateAndTime
    MAX-ACCESS   read-only
    STATUS       current
    DESCRIPTION
        "Cisco Firepower ether:NiErrStatsHist:timeCollected
        managed object property"
    ::= { cfprEtherNiErrStatsHistEntry 23 }

cfprEtherNiErrStatsHistTooLong OBJECT-TYPE
    SYNTAX       Unsigned64
    MAX-ACCESS   read-only
    STATUS       current
    DESCRIPTION
        "Cisco Firepower ether:NiErrStatsHist:tooLong managed
        object property"
    ::= { cfprEtherNiErrStatsHistEntry 24 }

cfprEtherNiErrStatsHistTooLongDelta OBJECT-TYPE
    SYNTAX       Unsigned64
    MAX-ACCESS   read-only
    STATUS       current
    DESCRIPTION
        "Cisco Firepower ether:NiErrStatsHist:tooLongDelta
        managed object property"
    ::= { cfprEtherNiErrStatsHistEntry 25 }

cfprEtherNiErrStatsHistTooLongDeltaAvg OBJECT-TYPE
    SYNTAX       Unsigned64
    MAX-ACCESS   read-only
    STATUS       current
    DESCRIPTION
        "Cisco Firepower ether:NiErrStatsHist:tooLongDeltaAvg
        managed object property"
    ::= { cfprEtherNiErrStatsHistEntry 26 }

cfprEtherNiErrStatsHistTooLongDeltaMax OBJECT-TYPE
    SYNTAX       Unsigned64
    MAX-ACCESS   read-only
    STATUS       current
    DESCRIPTION
        "Cisco Firepower ether:NiErrStatsHist:tooLongDeltaMax
        managed object property"
    ::= { cfprEtherNiErrStatsHistEntry 27 }

cfprEtherNiErrStatsHistTooLongDeltaMin OBJECT-TYPE
    SYNTAX       Unsigned64
    MAX-ACCESS   read-only
    STATUS       current
    DESCRIPTION
        "Cisco Firepower ether:NiErrStatsHist:tooLongDeltaMin
        managed object property"
    ::= { cfprEtherNiErrStatsHistEntry 28 }

cfprEtherNiErrStatsHistTooShort OBJECT-TYPE
    SYNTAX       Unsigned64
    MAX-ACCESS   read-only
    STATUS       current
    DESCRIPTION
        "Cisco Firepower ether:NiErrStatsHist:tooShort
        managed object property"
    ::= { cfprEtherNiErrStatsHistEntry 29 }

cfprEtherNiErrStatsHistTooShortDelta OBJECT-TYPE
    SYNTAX       Unsigned64
    MAX-ACCESS   read-only
    STATUS       current
    DESCRIPTION
        "Cisco Firepower ether:NiErrStatsHist:tooShortDelta
        managed object property"
    ::= { cfprEtherNiErrStatsHistEntry 30 }

cfprEtherNiErrStatsHistTooShortDeltaAvg OBJECT-TYPE
    SYNTAX       Unsigned64
    MAX-ACCESS   read-only
    STATUS       current
    DESCRIPTION
        "Cisco Firepower ether:NiErrStatsHist:tooShortDeltaAvg
        managed object property"
    ::= { cfprEtherNiErrStatsHistEntry 31 }

cfprEtherNiErrStatsHistTooShortDeltaMax OBJECT-TYPE
    SYNTAX       Unsigned64
    MAX-ACCESS   read-only
    STATUS       current
    DESCRIPTION
        "Cisco Firepower ether:NiErrStatsHist:tooShortDeltaMax
        managed object property"
    ::= { cfprEtherNiErrStatsHistEntry 32 }

cfprEtherNiErrStatsHistTooShortDeltaMin OBJECT-TYPE
    SYNTAX       Unsigned64
    MAX-ACCESS   read-only
    STATUS       current
    DESCRIPTION
        "Cisco Firepower ether:NiErrStatsHist:tooShortDeltaMin
        managed object property"
    ::= { cfprEtherNiErrStatsHistEntry 33 }

cfprEtherNicIfConfigTable OBJECT-TYPE
    SYNTAX           SEQUENCE OF CfprEtherNicIfConfigEntry
    MAX-ACCESS       not-accessible
    STATUS           current
    DESCRIPTION
        "Cisco Firepower ether:NicIfConfig managed object table"
    ::= { cfprEtherObjects 9 }

cfprEtherNicIfConfigEntry OBJECT-TYPE
    SYNTAX           CfprEtherNicIfConfigEntry
    MAX-ACCESS       not-accessible
    STATUS           current
    DESCRIPTION
        "Entry for the cfprEtherNicIfConfigTable table."
    INDEX { cfprEtherNicIfConfigInstanceId }
    ::= { cfprEtherNicIfConfigTable 1 }

CfprEtherNicIfConfigEntry ::= SEQUENCE {
    cfprEtherNicIfConfigInstanceId                                   CfprManagedObjectId,
    cfprEtherNicIfConfigDn                                           CfprManagedObjectDn,
    cfprEtherNicIfConfigRn                                           SnmpAdminString
}

cfprEtherNicIfConfigInstanceId OBJECT-TYPE
    SYNTAX       CfprManagedObjectId
    MAX-ACCESS   not-accessible
    STATUS       current
    DESCRIPTION
        "Instance identifier of the managed object."
    ::= { cfprEtherNicIfConfigEntry 1 }

cfprEtherNicIfConfigDn OBJECT-TYPE
    SYNTAX       CfprManagedObjectDn
    MAX-ACCESS   read-only
    STATUS       current
    DESCRIPTION
        "Cisco Firepower ether:NicIfConfig:dn managed object property"
    ::= { cfprEtherNicIfConfigEntry 2 }

cfprEtherNicIfConfigRn OBJECT-TYPE
    SYNTAX       SnmpAdminString
    MAX-ACCESS   read-only
    STATUS       current
    DESCRIPTION
        "Cisco Firepower ether:NicIfConfig:rn managed object property"
    ::= { cfprEtherNicIfConfigEntry 3 }

cfprEtherPIoTable OBJECT-TYPE
    SYNTAX           SEQUENCE OF CfprEtherPIoEntry
    MAX-ACCESS       not-accessible
    STATUS           current
    DESCRIPTION
        "Cisco Firepower ether:PIo managed object table"
    ::= { cfprEtherObjects 10 }

cfprEtherPIoEntry OBJECT-TYPE
    SYNTAX           CfprEtherPIoEntry
    MAX-ACCESS       not-accessible
    STATUS           current
    DESCRIPTION
        "Entry for the cfprEtherPIoTable table."
    INDEX { cfprEtherPIoInstanceId }
    ::= { cfprEtherPIoTable 1 }

CfprEtherPIoEntry ::= SEQUENCE {
    cfprEtherPIoInstanceId                                           CfprManagedObjectId,
    cfprEtherPIoDn                                                   CfprManagedObjectDn,
    cfprEtherPIoRn                                                   SnmpAdminString,
    cfprEtherPIoAdminState                                           CfprFabricAdminState,
    cfprEtherPIoAdminTransport                                       CfprNetworkTransport,
    cfprEtherPIoAggrPortId                                           Gauge32,
    cfprEtherPIoChassisId                                            Gauge32,
    cfprEtherPIoEncap                                                CfprPortEncap,
    cfprEtherPIoEpDn                                                 SnmpAdminString,
    cfprEtherPIoFltAggr                                              Unsigned64,
    cfprEtherPIoFsmDescr                                             SnmpAdminString,
    cfprEtherPIoFsmPrev                                              SnmpAdminString,
    cfprEtherPIoFsmProgr                                             Gauge32,
    cfprEtherPIoFsmRmtInvErrCode                                     Gauge32,
    cfprEtherPIoFsmRmtInvErrDescr                                    SnmpAdminString,
    cfprEtherPIoFsmRmtInvRslt                                        CfprConditionRemoteInvRslt,
    cfprEtherPIoFsmStageDescr                                        SnmpAdminString,
    cfprEtherPIoFsmStamp                                             DateAndTime,
    cfprEtherPIoFsmStatus                                            SnmpAdminString,
    cfprEtherPIoFsmTry                                               Gauge32,
    cfprEtherPIoIfRole                                               CfprNetworkPortRole,
    cfprEtherPIoIfType                                               CfprNetworkPhysEpIfType,
    cfprEtherPIoIsPortChannelMember                                  TruthValue,
    cfprEtherPIoLc                                                   CfprFsmLifecycle,
    cfprEtherPIoLicGP                                                Unsigned64,
    cfprEtherPIoLicState                                             CfprLicenseState,
    cfprEtherPIoLocale                                               CfprNetworkLocale,
    cfprEtherPIoMac                                                  MacAddress,
    cfprEtherPIoMode                                                 CfprPortMode,
    cfprEtherPIoModel                                                SnmpAdminString,
    cfprEtherPIoName                                                 SnmpAdminString,
    cfprEtherPIoOperSpeed                                            CfprPortEthSpeed,
    cfprEtherPIoOperState                                            CfprNetworkPortOperState,
    cfprEtherPIoPeerAggrPortId                                       Gauge32,
    cfprEtherPIoPeerChassisId                                        Gauge32,
    cfprEtherPIoPeerDn                                               SnmpAdminString,
    cfprEtherPIoPeerPortId                                           Gauge32,
    cfprEtherPIoPeerSlotId                                           Gauge32,
    cfprEtherPIoPortId                                               Gauge32,
    cfprEtherPIoRevision                                             SnmpAdminString,
    cfprEtherPIoSerial                                               SnmpAdminString,
    cfprEtherPIoSlotId                                               Gauge32,
    cfprEtherPIoStateQual                                            SnmpAdminString,
    cfprEtherPIoSwitchId                                             CfprNetworkSwitchId,
    cfprEtherPIoTransport                                            CfprNetworkTransport,
    cfprEtherPIoTs                                                   DateAndTime,
    cfprEtherPIoType                                                 CfprNetworkConnectionType,
    cfprEtherPIoUnifiedPort                                          TruthValue,
    cfprEtherPIoUsrLbl                                               SnmpAdminString,
    cfprEtherPIoVendor                                               SnmpAdminString,
    cfprEtherPIoXcvrType                                             CfprEquipmentXcvrType,
    cfprEtherPIoFtwPhyDn                                             SnmpAdminString,
    cfprEtherPIoOperDuplex                                           CfprPortDuplex
}

cfprEtherPIoInstanceId OBJECT-TYPE
    SYNTAX       CfprManagedObjectId
    MAX-ACCESS   not-accessible
    STATUS       current
    DESCRIPTION
        "Instance identifier of the managed object."
    ::= { cfprEtherPIoEntry 1 }

cfprEtherPIoDn OBJECT-TYPE
    SYNTAX       CfprManagedObjectDn
    MAX-ACCESS   read-only
    STATUS       current
    DESCRIPTION
        "Cisco Firepower ether:PIo:dn managed object property"
    ::= { cfprEtherPIoEntry 2 }

cfprEtherPIoRn OBJECT-TYPE
    SYNTAX       SnmpAdminString
    MAX-ACCESS   read-only
    STATUS       current
    DESCRIPTION
        "Cisco Firepower ether:PIo:rn managed object property"
    ::= { cfprEtherPIoEntry 3 }

cfprEtherPIoAdminState OBJECT-TYPE
    SYNTAX       CfprFabricAdminState
    MAX-ACCESS   read-only
    STATUS       current
    DESCRIPTION
        "Cisco Firepower ether:PIo:adminState managed object property"
    ::= { cfprEtherPIoEntry 4 }

cfprEtherPIoAdminTransport OBJECT-TYPE
    SYNTAX       CfprNetworkTransport
    MAX-ACCESS   read-only
    STATUS       current
    DESCRIPTION
        "Cisco Firepower ether:PIo:adminTransport managed object property"
    ::= { cfprEtherPIoEntry 5 }

cfprEtherPIoAggrPortId OBJECT-TYPE
    SYNTAX       Gauge32
    MAX-ACCESS   read-only
    STATUS       current
    DESCRIPTION
        "Cisco Firepower ether:PIo:aggrPortId managed object property"
    ::= { cfprEtherPIoEntry 6 }

cfprEtherPIoChassisId OBJECT-TYPE
    SYNTAX       Gauge32
    MAX-ACCESS   read-only
    STATUS       current
    DESCRIPTION
        "Cisco Firepower ether:PIo:chassisId managed object property"
    ::= { cfprEtherPIoEntry 7 }

cfprEtherPIoEncap OBJECT-TYPE
    SYNTAX       CfprPortEncap
    MAX-ACCESS   read-only
    STATUS       current
    DESCRIPTION
        "Cisco Firepower ether:PIo:encap managed object property"
    ::= { cfprEtherPIoEntry 8 }

cfprEtherPIoEpDn OBJECT-TYPE
    SYNTAX       SnmpAdminString
    MAX-ACCESS   read-only
    STATUS       current
    DESCRIPTION
        "Cisco Firepower ether:PIo:epDn managed object property"
    ::= { cfprEtherPIoEntry 9 }

cfprEtherPIoFltAggr OBJECT-TYPE
    SYNTAX       Unsigned64
    MAX-ACCESS   read-only
    STATUS       current
    DESCRIPTION
        "Cisco Firepower ether:PIo:fltAggr managed object property"
    ::= { cfprEtherPIoEntry 10 }

cfprEtherPIoFsmDescr OBJECT-TYPE
    SYNTAX       SnmpAdminString
    MAX-ACCESS   read-only
    STATUS       current
    DESCRIPTION
        "Cisco Firepower ether:PIo:fsmDescr managed object property"
    ::= { cfprEtherPIoEntry 11 }

cfprEtherPIoFsmPrev OBJECT-TYPE
    SYNTAX       SnmpAdminString
    MAX-ACCESS   read-only
    STATUS       current
    DESCRIPTION
        "Cisco Firepower ether:PIo:fsmPrev managed object property"
    ::= { cfprEtherPIoEntry 12 }

cfprEtherPIoFsmProgr OBJECT-TYPE
    SYNTAX       Gauge32
    MAX-ACCESS   read-only
    STATUS       current
    DESCRIPTION
        "Cisco Firepower ether:PIo:fsmProgr managed object property"
    ::= { cfprEtherPIoEntry 13 }

cfprEtherPIoFsmRmtInvErrCode OBJECT-TYPE
    SYNTAX       Gauge32
    MAX-ACCESS   read-only
    STATUS       current
    DESCRIPTION
        "Cisco Firepower ether:PIo:fsmRmtInvErrCode managed
        object property"
    ::= { cfprEtherPIoEntry 14 }

cfprEtherPIoFsmRmtInvErrDescr OBJECT-TYPE
    SYNTAX       SnmpAdminString
    MAX-ACCESS   read-only
    STATUS       current
    DESCRIPTION
        "Cisco Firepower ether:PIo:fsmRmtInvErrDescr managed
        object property"
    ::= { cfprEtherPIoEntry 15 }

cfprEtherPIoFsmRmtInvRslt OBJECT-TYPE
    SYNTAX       CfprConditionRemoteInvRslt
    MAX-ACCESS   read-only
    STATUS       current
    DESCRIPTION
        "Cisco Firepower ether:PIo:fsmRmtInvRslt managed object property"
    ::= { cfprEtherPIoEntry 16 }

cfprEtherPIoFsmStageDescr OBJECT-TYPE
    SYNTAX       SnmpAdminString
    MAX-ACCESS   read-only
    STATUS       current
    DESCRIPTION
        "Cisco Firepower ether:PIo:fsmStageDescr managed object property"
    ::= { cfprEtherPIoEntry 17 }

cfprEtherPIoFsmStamp OBJECT-TYPE
    SYNTAX       DateAndTime
    MAX-ACCESS   read-only
    STATUS       current
    DESCRIPTION
        "Cisco Firepower ether:PIo:fsmStamp managed object property"
    ::= { cfprEtherPIoEntry 18 }

cfprEtherPIoFsmStatus OBJECT-TYPE
    SYNTAX       SnmpAdminString
    MAX-ACCESS   read-only
    STATUS       current
    DESCRIPTION
        "Cisco Firepower ether:PIo:fsmStatus managed object property"
    ::= { cfprEtherPIoEntry 19 }

cfprEtherPIoFsmTry OBJECT-TYPE
    SYNTAX       Gauge32
    MAX-ACCESS   read-only
    STATUS       current
    DESCRIPTION
        "Cisco Firepower ether:PIo:fsmTry managed object property"
    ::= { cfprEtherPIoEntry 20 }

cfprEtherPIoIfRole OBJECT-TYPE
    SYNTAX       CfprNetworkPortRole
    MAX-ACCESS   read-only
    STATUS       current
    DESCRIPTION
        "Cisco Firepower ether:PIo:ifRole managed object property"
    ::= { cfprEtherPIoEntry 21 }

cfprEtherPIoIfType OBJECT-TYPE
    SYNTAX       CfprNetworkPhysEpIfType
    MAX-ACCESS   read-only
    STATUS       current
    DESCRIPTION
        "Cisco Firepower ether:PIo:ifType managed object property"
    ::= { cfprEtherPIoEntry 22 }

cfprEtherPIoIsPortChannelMember OBJECT-TYPE
    SYNTAX       TruthValue
    MAX-ACCESS   read-only
    STATUS       current
    DESCRIPTION
        "Cisco Firepower ether:PIo:isPortChannelMember
        managed object property"
    ::= { cfprEtherPIoEntry 23 }

cfprEtherPIoLc OBJECT-TYPE
    SYNTAX       CfprFsmLifecycle
    MAX-ACCESS   read-only
    STATUS       current
    DESCRIPTION
        "Cisco Firepower ether:PIo:lc managed object property"
    ::= { cfprEtherPIoEntry 24 }

cfprEtherPIoLicGP OBJECT-TYPE
    SYNTAX       Unsigned64
    MAX-ACCESS   read-only
    STATUS       current
    DESCRIPTION
        "Cisco Firepower ether:PIo:licGP managed object property"
    ::= { cfprEtherPIoEntry 25 }

cfprEtherPIoLicState OBJECT-TYPE
    SYNTAX       CfprLicenseState
    MAX-ACCESS   read-only
    STATUS       current
    DESCRIPTION
        "Cisco Firepower ether:PIo:licState managed object property"
    ::= { cfprEtherPIoEntry 26 }

cfprEtherPIoLocale OBJECT-TYPE
    SYNTAX       CfprNetworkLocale
    MAX-ACCESS   read-only
    STATUS       current
    DESCRIPTION
        "Cisco Firepower ether:PIo:locale managed object property"
    ::= { cfprEtherPIoEntry 27 }

cfprEtherPIoMac OBJECT-TYPE
    SYNTAX       MacAddress
    MAX-ACCESS   read-only
    STATUS       current
    DESCRIPTION
        "Cisco Firepower ether:PIo:mac managed object property"
    ::= { cfprEtherPIoEntry 28 }

cfprEtherPIoMode OBJECT-TYPE
    SYNTAX       CfprPortMode
    MAX-ACCESS   read-only
    STATUS       current
    DESCRIPTION
        "Cisco Firepower ether:PIo:mode managed object property"
    ::= { cfprEtherPIoEntry 29 }

cfprEtherPIoModel OBJECT-TYPE
    SYNTAX       SnmpAdminString
    MAX-ACCESS   read-only
    STATUS       current
    DESCRIPTION
        "Cisco Firepower ether:PIo:model managed object property"
    ::= { cfprEtherPIoEntry 30 }

cfprEtherPIoName OBJECT-TYPE
    SYNTAX       SnmpAdminString
    MAX-ACCESS   read-only
    STATUS       current
    DESCRIPTION
        "Cisco Firepower ether:PIo:name managed object property"
    ::= { cfprEtherPIoEntry 31 }

cfprEtherPIoOperSpeed OBJECT-TYPE
    SYNTAX       CfprPortEthSpeed
    MAX-ACCESS   read-only
    STATUS       current
    DESCRIPTION
        "Cisco Firepower ether:PIo:operSpeed managed object property"
    ::= { cfprEtherPIoEntry 32 }

cfprEtherPIoOperState OBJECT-TYPE
    SYNTAX       CfprNetworkPortOperState
    MAX-ACCESS   read-only
    STATUS       current
    DESCRIPTION
        "Cisco Firepower ether:PIo:operState managed object property"
    ::= { cfprEtherPIoEntry 33 }

cfprEtherPIoPeerAggrPortId OBJECT-TYPE
    SYNTAX       Gauge32
    MAX-ACCESS   read-only
    STATUS       current
    DESCRIPTION
        "Cisco Firepower ether:PIo:peerAggrPortId managed object property"
    ::= { cfprEtherPIoEntry 34 }

cfprEtherPIoPeerChassisId OBJECT-TYPE
    SYNTAX       Gauge32
    MAX-ACCESS   read-only
    STATUS       current
    DESCRIPTION
        "Cisco Firepower ether:PIo:peerChassisId managed object property"
    ::= { cfprEtherPIoEntry 35 }

cfprEtherPIoPeerDn OBJECT-TYPE
    SYNTAX       SnmpAdminString
    MAX-ACCESS   read-only
    STATUS       current
    DESCRIPTION
        "Cisco Firepower ether:PIo:peerDn managed object property"
    ::= { cfprEtherPIoEntry 36 }

cfprEtherPIoPeerPortId OBJECT-TYPE
    SYNTAX       Gauge32
    MAX-ACCESS   read-only
    STATUS       current
    DESCRIPTION
        "Cisco Firepower ether:PIo:peerPortId managed object property"
    ::= { cfprEtherPIoEntry 37 }

cfprEtherPIoPeerSlotId OBJECT-TYPE
    SYNTAX       Gauge32
    MAX-ACCESS   read-only
    STATUS       current
    DESCRIPTION
        "Cisco Firepower ether:PIo:peerSlotId managed object property"
    ::= { cfprEtherPIoEntry 38 }

cfprEtherPIoPortId OBJECT-TYPE
    SYNTAX       Gauge32
    MAX-ACCESS   read-only
    STATUS       current
    DESCRIPTION
        "Cisco Firepower ether:PIo:portId managed object property"
    ::= { cfprEtherPIoEntry 39 }

cfprEtherPIoRevision OBJECT-TYPE
    SYNTAX       SnmpAdminString
    MAX-ACCESS   read-only
    STATUS       current
    DESCRIPTION
        "Cisco Firepower ether:PIo:revision managed object property"
    ::= { cfprEtherPIoEntry 40 }

cfprEtherPIoSerial OBJECT-TYPE
    SYNTAX       SnmpAdminString
    MAX-ACCESS   read-only
    STATUS       current
    DESCRIPTION
        "Cisco Firepower ether:PIo:serial managed object property"
    ::= { cfprEtherPIoEntry 41 }

cfprEtherPIoSlotId OBJECT-TYPE
    SYNTAX       Gauge32
    MAX-ACCESS   read-only
    STATUS       current
    DESCRIPTION
        "Cisco Firepower ether:PIo:slotId managed object property"
    ::= { cfprEtherPIoEntry 42 }

cfprEtherPIoStateQual OBJECT-TYPE
    SYNTAX       SnmpAdminString
    MAX-ACCESS   read-only
    STATUS       current
    DESCRIPTION
        "Cisco Firepower ether:PIo:stateQual managed object property"
    ::= { cfprEtherPIoEntry 43 }

cfprEtherPIoSwitchId OBJECT-TYPE
    SYNTAX       CfprNetworkSwitchId
    MAX-ACCESS   read-only
    STATUS       current
    DESCRIPTION
        "Cisco Firepower ether:PIo:switchId managed object property"
    ::= { cfprEtherPIoEntry 44 }

cfprEtherPIoTransport OBJECT-TYPE
    SYNTAX       CfprNetworkTransport
    MAX-ACCESS   read-only
    STATUS       current
    DESCRIPTION
        "Cisco Firepower ether:PIo:transport managed object property"
    ::= { cfprEtherPIoEntry 45 }

cfprEtherPIoTs OBJECT-TYPE
    SYNTAX       DateAndTime
    MAX-ACCESS   read-only
    STATUS       current
    DESCRIPTION
        "Cisco Firepower ether:PIo:ts managed object property"
    ::= { cfprEtherPIoEntry 46 }

cfprEtherPIoType OBJECT-TYPE
    SYNTAX       CfprNetworkConnectionType
    MAX-ACCESS   read-only
    STATUS       current
    DESCRIPTION
        "Cisco Firepower ether:PIo:type managed object property"
    ::= { cfprEtherPIoEntry 47 }

cfprEtherPIoUnifiedPort OBJECT-TYPE
    SYNTAX       TruthValue
    MAX-ACCESS   read-only
    STATUS       current
    DESCRIPTION
        "Cisco Firepower ether:PIo:unifiedPort managed object property"
    ::= { cfprEtherPIoEntry 48 }

cfprEtherPIoUsrLbl OBJECT-TYPE
    SYNTAX       SnmpAdminString
    MAX-ACCESS   read-only
    STATUS       current
    DESCRIPTION
        "Cisco Firepower ether:PIo:usrLbl managed object property"
    ::= { cfprEtherPIoEntry 49 }

cfprEtherPIoVendor OBJECT-TYPE
    SYNTAX       SnmpAdminString
    MAX-ACCESS   read-only
    STATUS       current
    DESCRIPTION
        "Cisco Firepower ether:PIo:vendor managed object property"
    ::= { cfprEtherPIoEntry 50 }

cfprEtherPIoXcvrType OBJECT-TYPE
    SYNTAX       CfprEquipmentXcvrType
    MAX-ACCESS   read-only
    STATUS       current
    DESCRIPTION
        "Cisco Firepower ether:PIo:xcvrType managed object property"
    ::= { cfprEtherPIoEntry 51 }

cfprEtherPIoFtwPhyDn OBJECT-TYPE
    SYNTAX       SnmpAdminString
    MAX-ACCESS   read-only
    STATUS       current
    DESCRIPTION
        "Cisco Firepower ether:PIo:ftwPhyDn managed object property"
    ::= { cfprEtherPIoEntry 52 }

cfprEtherPIoOperDuplex OBJECT-TYPE
    SYNTAX       CfprPortDuplex
    MAX-ACCESS   read-only
    STATUS       current
    DESCRIPTION
        "Cisco Firepower ether:PIo:operDuplex managed object property"
    ::= { cfprEtherPIoEntry 53 }

cfprEtherPIoEndPointTable OBJECT-TYPE
    SYNTAX           SEQUENCE OF CfprEtherPIoEndPointEntry
    MAX-ACCESS       not-accessible
    STATUS           current
    DESCRIPTION
        "Cisco Firepower ether:PIoEndPoint managed object table"
    ::= { cfprEtherObjects 11 }

cfprEtherPIoEndPointEntry OBJECT-TYPE
    SYNTAX           CfprEtherPIoEndPointEntry
    MAX-ACCESS       not-accessible
    STATUS           current
    DESCRIPTION
        "Entry for the cfprEtherPIoEndPointTable table."
    INDEX { cfprEtherPIoEndPointInstanceId }
    ::= { cfprEtherPIoEndPointTable 1 }

CfprEtherPIoEndPointEntry ::= SEQUENCE {
    cfprEtherPIoEndPointInstanceId                                   CfprManagedObjectId,
    cfprEtherPIoEndPointDn                                           CfprManagedObjectDn,
    cfprEtherPIoEndPointRn                                           SnmpAdminString,
    cfprEtherPIoEndPointEndPointDn                                   SnmpAdminString,
    cfprEtherPIoEndPointEpCloudType                                  CfprEtherCloudType,
    cfprEtherPIoEndPointUsrLbl                                       SnmpAdminString
}

cfprEtherPIoEndPointInstanceId OBJECT-TYPE
    SYNTAX       CfprManagedObjectId
    MAX-ACCESS   not-accessible
    STATUS       current
    DESCRIPTION
        "Instance identifier of the managed object."
    ::= { cfprEtherPIoEndPointEntry 1 }

cfprEtherPIoEndPointDn OBJECT-TYPE
    SYNTAX       CfprManagedObjectDn
    MAX-ACCESS   read-only
    STATUS       current
    DESCRIPTION
        "Cisco Firepower ether:PIoEndPoint:dn managed object property"
    ::= { cfprEtherPIoEndPointEntry 2 }

cfprEtherPIoEndPointRn OBJECT-TYPE
    SYNTAX       SnmpAdminString
    MAX-ACCESS   read-only
    STATUS       current
    DESCRIPTION
        "Cisco Firepower ether:PIoEndPoint:rn managed object property"
    ::= { cfprEtherPIoEndPointEntry 3 }

cfprEtherPIoEndPointEndPointDn OBJECT-TYPE
    SYNTAX       SnmpAdminString
    MAX-ACCESS   read-only
    STATUS       current
    DESCRIPTION
        "Cisco Firepower ether:PIoEndPoint:EndPointDn managed
        object property"
    ::= { cfprEtherPIoEndPointEntry 4 }

cfprEtherPIoEndPointEpCloudType OBJECT-TYPE
    SYNTAX       CfprEtherCloudType
    MAX-ACCESS   read-only
    STATUS       current
    DESCRIPTION
        "Cisco Firepower ether:PIoEndPoint:epCloudType
        managed object property"
    ::= { cfprEtherPIoEndPointEntry 5 }

cfprEtherPIoEndPointUsrLbl OBJECT-TYPE
    SYNTAX       SnmpAdminString
    MAX-ACCESS   read-only
    STATUS       current
    DESCRIPTION
        "Cisco Firepower ether:PIoEndPoint:usrLbl managed object property"
    ::= { cfprEtherPIoEndPointEntry 6 }

cfprEtherPIoFsmTable OBJECT-TYPE
    SYNTAX           SEQUENCE OF CfprEtherPIoFsmEntry
    MAX-ACCESS       not-accessible
    STATUS           current
    DESCRIPTION
        "Cisco Firepower ether:PIoFsm managed object table"
    ::= { cfprEtherObjects 12 }

cfprEtherPIoFsmEntry OBJECT-TYPE
    SYNTAX           CfprEtherPIoFsmEntry
    MAX-ACCESS       not-accessible
    STATUS           current
    DESCRIPTION
        "Entry for the cfprEtherPIoFsmTable table."
    INDEX { cfprEtherPIoFsmInstanceId }
    ::= { cfprEtherPIoFsmTable 1 }

CfprEtherPIoFsmEntry ::= SEQUENCE {
    cfprEtherPIoFsmInstanceId                                        CfprManagedObjectId,
    cfprEtherPIoFsmDn                                                CfprManagedObjectDn,
    cfprEtherPIoFsmRn                                                SnmpAdminString,
    cfprEtherPIoFsmCompletionTime                                    DateAndTime,
    cfprEtherPIoFsmCurrentFsm                                        CfprEtherPIoFsmCurrentFsm,
    cfprEtherPIoFsmDescrData                                         SnmpAdminString,
    cfprEtherPIoFsmFsmStatus                                         CfprFsmFsmStageStatus,
    cfprEtherPIoFsmProgress                                          Gauge32,
    cfprEtherPIoFsmRmtErrCode                                        Gauge32,
    cfprEtherPIoFsmRmtErrDescr                                       SnmpAdminString,
    cfprEtherPIoFsmRmtRslt                                           CfprConditionRemoteInvRslt
}

cfprEtherPIoFsmInstanceId OBJECT-TYPE
    SYNTAX       CfprManagedObjectId
    MAX-ACCESS   not-accessible
    STATUS       current
    DESCRIPTION
        "Instance identifier of the managed object."
    ::= { cfprEtherPIoFsmEntry 1 }

cfprEtherPIoFsmDn OBJECT-TYPE
    SYNTAX       CfprManagedObjectDn
    MAX-ACCESS   read-only
    STATUS       current
    DESCRIPTION
        "Cisco Firepower ether:PIoFsm:dn managed object property"
    ::= { cfprEtherPIoFsmEntry 2 }

cfprEtherPIoFsmRn OBJECT-TYPE
    SYNTAX       SnmpAdminString
    MAX-ACCESS   read-only
    STATUS       current
    DESCRIPTION
        "Cisco Firepower ether:PIoFsm:rn managed object property"
    ::= { cfprEtherPIoFsmEntry 3 }

cfprEtherPIoFsmCompletionTime OBJECT-TYPE
    SYNTAX       DateAndTime
    MAX-ACCESS   read-only
    STATUS       current
    DESCRIPTION
        "Cisco Firepower ether:PIoFsm:completionTime managed
        object property"
    ::= { cfprEtherPIoFsmEntry 4 }

cfprEtherPIoFsmCurrentFsm OBJECT-TYPE
    SYNTAX       CfprEtherPIoFsmCurrentFsm
    MAX-ACCESS   read-only
    STATUS       current
    DESCRIPTION
        "Cisco Firepower ether:PIoFsm:currentFsm managed object property"
    ::= { cfprEtherPIoFsmEntry 5 }

cfprEtherPIoFsmDescrData OBJECT-TYPE
    SYNTAX       SnmpAdminString
    MAX-ACCESS   read-only
    STATUS       current
    DESCRIPTION
        "Cisco Firepower ether:PIoFsm:descr managed object property"
    ::= { cfprEtherPIoFsmEntry 6 }

cfprEtherPIoFsmFsmStatus OBJECT-TYPE
    SYNTAX       CfprFsmFsmStageStatus
    MAX-ACCESS   read-only
    STATUS       current
    DESCRIPTION
        "Cisco Firepower ether:PIoFsm:fsmStatus managed object property"
    ::= { cfprEtherPIoFsmEntry 7 }

cfprEtherPIoFsmProgress OBJECT-TYPE
    SYNTAX       Gauge32
    MAX-ACCESS   read-only
    STATUS       current
    DESCRIPTION
        "Cisco Firepower ether:PIoFsm:progress managed object property"
    ::= { cfprEtherPIoFsmEntry 8 }

cfprEtherPIoFsmRmtErrCode OBJECT-TYPE
    SYNTAX       Gauge32
    MAX-ACCESS   read-only
    STATUS       current
    DESCRIPTION
        "Cisco Firepower ether:PIoFsm:rmtErrCode managed object property"
    ::= { cfprEtherPIoFsmEntry 9 }

cfprEtherPIoFsmRmtErrDescr OBJECT-TYPE
    SYNTAX       SnmpAdminString
    MAX-ACCESS   read-only
    STATUS       current
    DESCRIPTION
        "Cisco Firepower ether:PIoFsm:rmtErrDescr managed object property"
    ::= { cfprEtherPIoFsmEntry 10 }

cfprEtherPIoFsmRmtRslt OBJECT-TYPE
    SYNTAX       CfprConditionRemoteInvRslt
    MAX-ACCESS   read-only
    STATUS       current
    DESCRIPTION
        "Cisco Firepower ether:PIoFsm:rmtRslt managed object property"
    ::= { cfprEtherPIoFsmEntry 11 }

cfprEtherPIoFsmStageTable OBJECT-TYPE
    SYNTAX           SEQUENCE OF CfprEtherPIoFsmStageEntry
    MAX-ACCESS       not-accessible
    STATUS           current
    DESCRIPTION
        "Cisco Firepower ether:PIoFsmStage managed object table"
    ::= { cfprEtherObjects 13 }

cfprEtherPIoFsmStageEntry OBJECT-TYPE
    SYNTAX           CfprEtherPIoFsmStageEntry
    MAX-ACCESS       not-accessible
    STATUS           current
    DESCRIPTION
        "Entry for the cfprEtherPIoFsmStageTable table."
    INDEX { cfprEtherPIoFsmStageInstanceId }
    ::= { cfprEtherPIoFsmStageTable 1 }

CfprEtherPIoFsmStageEntry ::= SEQUENCE {
    cfprEtherPIoFsmStageInstanceId                                   CfprManagedObjectId,
    cfprEtherPIoFsmStageDn                                           CfprManagedObjectDn,
    cfprEtherPIoFsmStageRn                                           SnmpAdminString,
    cfprEtherPIoFsmStageDescrData                                    SnmpAdminString,
    cfprEtherPIoFsmStageLastUpdateTime                               DateAndTime,
    cfprEtherPIoFsmStageName                                         CfprEtherPIoFsmStageName,
    cfprEtherPIoFsmStageOrder                                        Gauge32,
    cfprEtherPIoFsmStageRetry                                        Gauge32,
    cfprEtherPIoFsmStageStageStatus                                  CfprFsmFsmStageStatus
}

cfprEtherPIoFsmStageInstanceId OBJECT-TYPE
    SYNTAX       CfprManagedObjectId
    MAX-ACCESS   not-accessible
    STATUS       current
    DESCRIPTION
        "Instance identifier of the managed object."
    ::= { cfprEtherPIoFsmStageEntry 1 }

cfprEtherPIoFsmStageDn OBJECT-TYPE
    SYNTAX       CfprManagedObjectDn
    MAX-ACCESS   read-only
    STATUS       current
    DESCRIPTION
        "Cisco Firepower ether:PIoFsmStage:dn managed object property"
    ::= { cfprEtherPIoFsmStageEntry 2 }

cfprEtherPIoFsmStageRn OBJECT-TYPE
    SYNTAX       SnmpAdminString
    MAX-ACCESS   read-only
    STATUS       current
    DESCRIPTION
        "Cisco Firepower ether:PIoFsmStage:rn managed object property"
    ::= { cfprEtherPIoFsmStageEntry 3 }

cfprEtherPIoFsmStageDescrData OBJECT-TYPE
    SYNTAX       SnmpAdminString
    MAX-ACCESS   read-only
    STATUS       current
    DESCRIPTION
        "Cisco Firepower ether:PIoFsmStage:descr managed object property"
    ::= { cfprEtherPIoFsmStageEntry 4 }

cfprEtherPIoFsmStageLastUpdateTime OBJECT-TYPE
    SYNTAX       DateAndTime
    MAX-ACCESS   read-only
    STATUS       current
    DESCRIPTION
        "Cisco Firepower ether:PIoFsmStage:lastUpdateTime
        managed object property"
    ::= { cfprEtherPIoFsmStageEntry 5 }

cfprEtherPIoFsmStageName OBJECT-TYPE
    SYNTAX       CfprEtherPIoFsmStageName
    MAX-ACCESS   read-only
    STATUS       current
    DESCRIPTION
        "Cisco Firepower ether:PIoFsmStage:name managed object property"
    ::= { cfprEtherPIoFsmStageEntry 6 }

cfprEtherPIoFsmStageOrder OBJECT-TYPE
    SYNTAX       Gauge32
    MAX-ACCESS   read-only
    STATUS       current
    DESCRIPTION
        "Cisco Firepower ether:PIoFsmStage:order managed object property"
    ::= { cfprEtherPIoFsmStageEntry 7 }

cfprEtherPIoFsmStageRetry OBJECT-TYPE
    SYNTAX       Gauge32
    MAX-ACCESS   read-only
    STATUS       current
    DESCRIPTION
        "Cisco Firepower ether:PIoFsmStage:retry managed object property"
    ::= { cfprEtherPIoFsmStageEntry 8 }

cfprEtherPIoFsmStageStageStatus OBJECT-TYPE
    SYNTAX       CfprFsmFsmStageStatus
    MAX-ACCESS   read-only
    STATUS       current
    DESCRIPTION
        "Cisco Firepower ether:PIoFsmStage:stageStatus
        managed object property"
    ::= { cfprEtherPIoFsmStageEntry 9 }

cfprEtherPauseStatsTable OBJECT-TYPE
    SYNTAX           SEQUENCE OF CfprEtherPauseStatsEntry
    MAX-ACCESS       not-accessible
    STATUS           current
    DESCRIPTION
        "Cisco Firepower ether:PauseStats managed object table"
    ::= { cfprEtherObjects 14 }

cfprEtherPauseStatsEntry OBJECT-TYPE
    SYNTAX           CfprEtherPauseStatsEntry
    MAX-ACCESS       not-accessible
    STATUS           current
    DESCRIPTION
        "Entry for the cfprEtherPauseStatsTable table."
    INDEX { cfprEtherPauseStatsInstanceId }
    ::= { cfprEtherPauseStatsTable 1 }

CfprEtherPauseStatsEntry ::= SEQUENCE {
    cfprEtherPauseStatsInstanceId                                    CfprManagedObjectId,
    cfprEtherPauseStatsDn                                            CfprManagedObjectDn,
    cfprEtherPauseStatsRn                                            SnmpAdminString,
    cfprEtherPauseStatsIntervals                                     Gauge32,
    cfprEtherPauseStatsRecvPause                                     Unsigned64,
    cfprEtherPauseStatsRecvPauseDelta                                Counter64,
    cfprEtherPauseStatsRecvPauseDeltaAvg                             Unsigned64,
    cfprEtherPauseStatsRecvPauseDeltaMax                             Unsigned64,
    cfprEtherPauseStatsRecvPauseDeltaMin                             Unsigned64,
    cfprEtherPauseStatsResets                                        Unsigned64,
    cfprEtherPauseStatsResetsDelta                                   Counter64,
    cfprEtherPauseStatsResetsDeltaAvg                                Unsigned64,
    cfprEtherPauseStatsResetsDeltaMax                                Unsigned64,
    cfprEtherPauseStatsResetsDeltaMin                                Unsigned64,
    cfprEtherPauseStatsSuspect                                       TruthValue,
    cfprEtherPauseStatsThresholded                                   CfprEtherPauseStatsThresholded,
    cfprEtherPauseStatsTimeCollected                                 DateAndTime,
    cfprEtherPauseStatsUpdate                                        Gauge32,
    cfprEtherPauseStatsXmitPause                                     Unsigned64,
    cfprEtherPauseStatsXmitPauseDelta                                Counter64,
    cfprEtherPauseStatsXmitPauseDeltaAvg                             Unsigned64,
    cfprEtherPauseStatsXmitPauseDeltaMax                             Unsigned64,
    cfprEtherPauseStatsXmitPauseDeltaMin                             Unsigned64
}

cfprEtherPauseStatsInstanceId OBJECT-TYPE
    SYNTAX       CfprManagedObjectId
    MAX-ACCESS   not-accessible
    STATUS       current
    DESCRIPTION
        "Instance identifier of the managed object."
    ::= { cfprEtherPauseStatsEntry 1 }

cfprEtherPauseStatsDn OBJECT-TYPE
    SYNTAX       CfprManagedObjectDn
    MAX-ACCESS   read-only
    STATUS       current
    DESCRIPTION
        "Cisco Firepower ether:PauseStats:dn managed object property"
    ::= { cfprEtherPauseStatsEntry 2 }

cfprEtherPauseStatsRn OBJECT-TYPE
    SYNTAX       SnmpAdminString
    MAX-ACCESS   read-only
    STATUS       current
    DESCRIPTION
        "Cisco Firepower ether:PauseStats:rn managed object property"
    ::= { cfprEtherPauseStatsEntry 3 }

cfprEtherPauseStatsIntervals OBJECT-TYPE
    SYNTAX       Gauge32
    MAX-ACCESS   read-only
    STATUS       current
    DESCRIPTION
        "Cisco Firepower ether:PauseStats:intervals managed
        object property"
    ::= { cfprEtherPauseStatsEntry 4 }

cfprEtherPauseStatsRecvPause OBJECT-TYPE
    SYNTAX       Unsigned64
    MAX-ACCESS   read-only
    STATUS       current
    DESCRIPTION
        "Cisco Firepower ether:PauseStats:recvPause managed
        object property"
    ::= { cfprEtherPauseStatsEntry 5 }

cfprEtherPauseStatsRecvPauseDelta OBJECT-TYPE
    SYNTAX       Counter64
    MAX-ACCESS   read-only
    STATUS       current
    DESCRIPTION
        "Cisco Firepower ether:PauseStats:recvPauseDelta
        managed object property"
    ::= { cfprEtherPauseStatsEntry 6 }

cfprEtherPauseStatsRecvPauseDeltaAvg OBJECT-TYPE
    SYNTAX       Unsigned64
    MAX-ACCESS   read-only
    STATUS       current
    DESCRIPTION
        "Cisco Firepower ether:PauseStats:recvPauseDeltaAvg
        managed object property"
    ::= { cfprEtherPauseStatsEntry 7 }

cfprEtherPauseStatsRecvPauseDeltaMax OBJECT-TYPE
    SYNTAX       Unsigned64
    MAX-ACCESS   read-only
    STATUS       current
    DESCRIPTION
        "Cisco Firepower ether:PauseStats:recvPauseDeltaMax
        managed object property"
    ::= { cfprEtherPauseStatsEntry 8 }

cfprEtherPauseStatsRecvPauseDeltaMin OBJECT-TYPE
    SYNTAX       Unsigned64
    MAX-ACCESS   read-only
    STATUS       current
    DESCRIPTION
        "Cisco Firepower ether:PauseStats:recvPauseDeltaMin
        managed object property"
    ::= { cfprEtherPauseStatsEntry 9 }

cfprEtherPauseStatsResets OBJECT-TYPE
    SYNTAX       Unsigned64
    MAX-ACCESS   read-only
    STATUS       current
    DESCRIPTION
        "Cisco Firepower ether:PauseStats:resets managed object property"
    ::= { cfprEtherPauseStatsEntry 10 }

cfprEtherPauseStatsResetsDelta OBJECT-TYPE
    SYNTAX       Counter64
    MAX-ACCESS   read-only
    STATUS       current
    DESCRIPTION
        "Cisco Firepower ether:PauseStats:resetsDelta managed
        object property"
    ::= { cfprEtherPauseStatsEntry 11 }

cfprEtherPauseStatsResetsDeltaAvg OBJECT-TYPE
    SYNTAX       Unsigned64
    MAX-ACCESS   read-only
    STATUS       current
    DESCRIPTION
        "Cisco Firepower ether:PauseStats:resetsDeltaAvg
        managed object property"
    ::= { cfprEtherPauseStatsEntry 12 }

cfprEtherPauseStatsResetsDeltaMax OBJECT-TYPE
    SYNTAX       Unsigned64
    MAX-ACCESS   read-only
    STATUS       current
    DESCRIPTION
        "Cisco Firepower ether:PauseStats:resetsDeltaMax
        managed object property"
    ::= { cfprEtherPauseStatsEntry 13 }

cfprEtherPauseStatsResetsDeltaMin OBJECT-TYPE
    SYNTAX       Unsigned64
    MAX-ACCESS   read-only
    STATUS       current
    DESCRIPTION
        "Cisco Firepower ether:PauseStats:resetsDeltaMin
        managed object property"
    ::= { cfprEtherPauseStatsEntry 14 }

cfprEtherPauseStatsSuspect OBJECT-TYPE
    SYNTAX       TruthValue
    MAX-ACCESS   read-only
    STATUS       current
    DESCRIPTION
        "Cisco Firepower ether:PauseStats:suspect managed object property"
    ::= { cfprEtherPauseStatsEntry 15 }

cfprEtherPauseStatsThresholded OBJECT-TYPE
    SYNTAX       CfprEtherPauseStatsThresholded
    MAX-ACCESS   read-only
    STATUS       current
    DESCRIPTION
        "Cisco Firepower ether:PauseStats:thresholded managed
        object property"
    ::= { cfprEtherPauseStatsEntry 16 }

cfprEtherPauseStatsTimeCollected OBJECT-TYPE
    SYNTAX       DateAndTime
    MAX-ACCESS   read-only
    STATUS       current
    DESCRIPTION
        "Cisco Firepower ether:PauseStats:timeCollected
        managed object property"
    ::= { cfprEtherPauseStatsEntry 17 }

cfprEtherPauseStatsUpdate OBJECT-TYPE
    SYNTAX       Gauge32
    MAX-ACCESS   read-only
    STATUS       current
    DESCRIPTION
        "Cisco Firepower ether:PauseStats:update managed object property"
    ::= { cfprEtherPauseStatsEntry 18 }

cfprEtherPauseStatsXmitPause OBJECT-TYPE
    SYNTAX       Unsigned64
    MAX-ACCESS   read-only
    STATUS       current
    DESCRIPTION
        "Cisco Firepower ether:PauseStats:xmitPause managed
        object property"
    ::= { cfprEtherPauseStatsEntry 19 }

cfprEtherPauseStatsXmitPauseDelta OBJECT-TYPE
    SYNTAX       Counter64
    MAX-ACCESS   read-only
    STATUS       current
    DESCRIPTION
        "Cisco Firepower ether:PauseStats:xmitPauseDelta
        managed object property"
    ::= { cfprEtherPauseStatsEntry 20 }

cfprEtherPauseStatsXmitPauseDeltaAvg OBJECT-TYPE
    SYNTAX       Unsigned64
    MAX-ACCESS   read-only
    STATUS       current
    DESCRIPTION
        "Cisco Firepower ether:PauseStats:xmitPauseDeltaAvg
        managed object property"
    ::= { cfprEtherPauseStatsEntry 21 }

cfprEtherPauseStatsXmitPauseDeltaMax OBJECT-TYPE
    SYNTAX       Unsigned64
    MAX-ACCESS   read-only
    STATUS       current
    DESCRIPTION
        "Cisco Firepower ether:PauseStats:xmitPauseDeltaMax
        managed object property"
    ::= { cfprEtherPauseStatsEntry 22 }

cfprEtherPauseStatsXmitPauseDeltaMin OBJECT-TYPE
    SYNTAX       Unsigned64
    MAX-ACCESS   read-only
    STATUS       current
    DESCRIPTION
        "Cisco Firepower ether:PauseStats:xmitPauseDeltaMin
        managed object property"
    ::= { cfprEtherPauseStatsEntry 23 }

cfprEtherPauseStatsHistTable OBJECT-TYPE
    SYNTAX           SEQUENCE OF CfprEtherPauseStatsHistEntry
    MAX-ACCESS       not-accessible
    STATUS           current
    DESCRIPTION
        "Cisco Firepower ether:PauseStatsHist managed object table"
    ::= { cfprEtherObjects 15 }

cfprEtherPauseStatsHistEntry OBJECT-TYPE
    SYNTAX           CfprEtherPauseStatsHistEntry
    MAX-ACCESS       not-accessible
    STATUS           current
    DESCRIPTION
        "Entry for the cfprEtherPauseStatsHistTable table."
    INDEX { cfprEtherPauseStatsHistInstanceId }
    ::= { cfprEtherPauseStatsHistTable 1 }

CfprEtherPauseStatsHistEntry ::= SEQUENCE {
    cfprEtherPauseStatsHistInstanceId                                CfprManagedObjectId,
    cfprEtherPauseStatsHistDn                                        CfprManagedObjectDn,
    cfprEtherPauseStatsHistRn                                        SnmpAdminString,
    cfprEtherPauseStatsHistId                                        Unsigned64,
    cfprEtherPauseStatsHistMostRecent                                TruthValue,
    cfprEtherPauseStatsHistRecvPause                                 Unsigned64,
    cfprEtherPauseStatsHistRecvPauseDelta                            Unsigned64,
    cfprEtherPauseStatsHistRecvPauseDeltaAvg                         Unsigned64,
    cfprEtherPauseStatsHistRecvPauseDeltaMax                         Unsigned64,
    cfprEtherPauseStatsHistRecvPauseDeltaMin                         Unsigned64,
    cfprEtherPauseStatsHistResets                                    Unsigned64,
    cfprEtherPauseStatsHistResetsDelta                               Unsigned64,
    cfprEtherPauseStatsHistResetsDeltaAvg                            Unsigned64,
    cfprEtherPauseStatsHistResetsDeltaMax                            Unsigned64,
    cfprEtherPauseStatsHistResetsDeltaMin                            Unsigned64,
    cfprEtherPauseStatsHistSuspect                                   TruthValue,
    cfprEtherPauseStatsHistThresholded                               CfprEtherPauseStatsHistThresholded,
    cfprEtherPauseStatsHistTimeCollected                             DateAndTime,
    cfprEtherPauseStatsHistXmitPause                                 Unsigned64,
    cfprEtherPauseStatsHistXmitPauseDelta                            Unsigned64,
    cfprEtherPauseStatsHistXmitPauseDeltaAvg                         Unsigned64,
    cfprEtherPauseStatsHistXmitPauseDeltaMax                         Unsigned64,
    cfprEtherPauseStatsHistXmitPauseDeltaMin                         Unsigned64
}

cfprEtherPauseStatsHistInstanceId OBJECT-TYPE
    SYNTAX       CfprManagedObjectId
    MAX-ACCESS   not-accessible
    STATUS       current
    DESCRIPTION
        "Instance identifier of the managed object."
    ::= { cfprEtherPauseStatsHistEntry 1 }

cfprEtherPauseStatsHistDn OBJECT-TYPE
    SYNTAX       CfprManagedObjectDn
    MAX-ACCESS   read-only
    STATUS       current
    DESCRIPTION
        "Cisco Firepower ether:PauseStatsHist:dn managed object property"
    ::= { cfprEtherPauseStatsHistEntry 2 }

cfprEtherPauseStatsHistRn OBJECT-TYPE
    SYNTAX       SnmpAdminString
    MAX-ACCESS   read-only
    STATUS       current
    DESCRIPTION
        "Cisco Firepower ether:PauseStatsHist:rn managed object property"
    ::= { cfprEtherPauseStatsHistEntry 3 }

cfprEtherPauseStatsHistId OBJECT-TYPE
    SYNTAX       Unsigned64
    MAX-ACCESS   read-only
    STATUS       current
    DESCRIPTION
        "Cisco Firepower ether:PauseStatsHist:id managed object property"
    ::= { cfprEtherPauseStatsHistEntry 4 }

cfprEtherPauseStatsHistMostRecent OBJECT-TYPE
    SYNTAX       TruthValue
    MAX-ACCESS   read-only
    STATUS       current
    DESCRIPTION
        "Cisco Firepower ether:PauseStatsHist:mostRecent
        managed object property"
    ::= { cfprEtherPauseStatsHistEntry 5 }

cfprEtherPauseStatsHistRecvPause OBJECT-TYPE
    SYNTAX       Unsigned64
    MAX-ACCESS   read-only
    STATUS       current
    DESCRIPTION
        "Cisco Firepower ether:PauseStatsHist:recvPause
        managed object property"
    ::= { cfprEtherPauseStatsHistEntry 6 }

cfprEtherPauseStatsHistRecvPauseDelta OBJECT-TYPE
    SYNTAX       Unsigned64
    MAX-ACCESS   read-only
    STATUS       current
    DESCRIPTION
        "Cisco Firepower ether:PauseStatsHist:recvPauseDelta
        managed object property"
    ::= { cfprEtherPauseStatsHistEntry 7 }

cfprEtherPauseStatsHistRecvPauseDeltaAvg OBJECT-TYPE
    SYNTAX       Unsigned64
    MAX-ACCESS   read-only
    STATUS       current
    DESCRIPTION
        "Cisco Firepower ether:PauseStatsHist:recvPauseDeltaAvg
        managed object property"
    ::= { cfprEtherPauseStatsHistEntry 8 }

cfprEtherPauseStatsHistRecvPauseDeltaMax OBJECT-TYPE
    SYNTAX       Unsigned64
    MAX-ACCESS   read-only
    STATUS       current
    DESCRIPTION
        "Cisco Firepower ether:PauseStatsHist:recvPauseDeltaMax
        managed object property"
    ::= { cfprEtherPauseStatsHistEntry 9 }

cfprEtherPauseStatsHistRecvPauseDeltaMin OBJECT-TYPE
    SYNTAX       Unsigned64
    MAX-ACCESS   read-only
    STATUS       current
    DESCRIPTION
        "Cisco Firepower ether:PauseStatsHist:recvPauseDeltaMin
        managed object property"
    ::= { cfprEtherPauseStatsHistEntry 10 }

cfprEtherPauseStatsHistResets OBJECT-TYPE
    SYNTAX       Unsigned64
    MAX-ACCESS   read-only
    STATUS       current
    DESCRIPTION
        "Cisco Firepower ether:PauseStatsHist:resets managed
        object property"
    ::= { cfprEtherPauseStatsHistEntry 11 }

cfprEtherPauseStatsHistResetsDelta OBJECT-TYPE
    SYNTAX       Unsigned64
    MAX-ACCESS   read-only
    STATUS       current
    DESCRIPTION
        "Cisco Firepower ether:PauseStatsHist:resetsDelta
        managed object property"
    ::= { cfprEtherPauseStatsHistEntry 12 }

cfprEtherPauseStatsHistResetsDeltaAvg OBJECT-TYPE
    SYNTAX       Unsigned64
    MAX-ACCESS   read-only
    STATUS       current
    DESCRIPTION
        "Cisco Firepower ether:PauseStatsHist:resetsDeltaAvg
        managed object property"
    ::= { cfprEtherPauseStatsHistEntry 13 }

cfprEtherPauseStatsHistResetsDeltaMax OBJECT-TYPE
    SYNTAX       Unsigned64
    MAX-ACCESS   read-only
    STATUS       current
    DESCRIPTION
        "Cisco Firepower ether:PauseStatsHist:resetsDeltaMax
        managed object property"
    ::= { cfprEtherPauseStatsHistEntry 14 }

cfprEtherPauseStatsHistResetsDeltaMin OBJECT-TYPE
    SYNTAX       Unsigned64
    MAX-ACCESS   read-only
    STATUS       current
    DESCRIPTION
        "Cisco Firepower ether:PauseStatsHist:resetsDeltaMin
        managed object property"
    ::= { cfprEtherPauseStatsHistEntry 15 }

cfprEtherPauseStatsHistSuspect OBJECT-TYPE
    SYNTAX       TruthValue
    MAX-ACCESS   read-only
    STATUS       current
    DESCRIPTION
        "Cisco Firepower ether:PauseStatsHist:suspect managed
        object property"
    ::= { cfprEtherPauseStatsHistEntry 16 }

cfprEtherPauseStatsHistThresholded OBJECT-TYPE
    SYNTAX       CfprEtherPauseStatsHistThresholded
    MAX-ACCESS   read-only
    STATUS       current
    DESCRIPTION
        "Cisco Firepower ether:PauseStatsHist:thresholded
        managed object property"
    ::= { cfprEtherPauseStatsHistEntry 17 }

cfprEtherPauseStatsHistTimeCollected OBJECT-TYPE
    SYNTAX       DateAndTime
    MAX-ACCESS   read-only
    STATUS       current
    DESCRIPTION
        "Cisco Firepower ether:PauseStatsHist:timeCollected
        managed object property"
    ::= { cfprEtherPauseStatsHistEntry 18 }

cfprEtherPauseStatsHistXmitPause OBJECT-TYPE
    SYNTAX       Unsigned64
    MAX-ACCESS   read-only
    STATUS       current
    DESCRIPTION
        "Cisco Firepower ether:PauseStatsHist:xmitPause
        managed object property"
    ::= { cfprEtherPauseStatsHistEntry 19 }

cfprEtherPauseStatsHistXmitPauseDelta OBJECT-TYPE
    SYNTAX       Unsigned64
    MAX-ACCESS   read-only
    STATUS       current
    DESCRIPTION
        "Cisco Firepower ether:PauseStatsHist:xmitPauseDelta
        managed object property"
    ::= { cfprEtherPauseStatsHistEntry 20 }

cfprEtherPauseStatsHistXmitPauseDeltaAvg OBJECT-TYPE
    SYNTAX       Unsigned64
    MAX-ACCESS   read-only
    STATUS       current
    DESCRIPTION
        "Cisco Firepower ether:PauseStatsHist:xmitPauseDeltaAvg
        managed object property"
    ::= { cfprEtherPauseStatsHistEntry 21 }

cfprEtherPauseStatsHistXmitPauseDeltaMax OBJECT-TYPE
    SYNTAX       Unsigned64
    MAX-ACCESS   read-only
    STATUS       current
    DESCRIPTION
        "Cisco Firepower ether:PauseStatsHist:xmitPauseDeltaMax
        managed object property"
    ::= { cfprEtherPauseStatsHistEntry 22 }

cfprEtherPauseStatsHistXmitPauseDeltaMin OBJECT-TYPE
    SYNTAX       Unsigned64
    MAX-ACCESS   read-only
    STATUS       current
    DESCRIPTION
        "Cisco Firepower ether:PauseStatsHist:xmitPauseDeltaMin
        managed object property"
    ::= { cfprEtherPauseStatsHistEntry 23 }

cfprEtherPortChanIdElemTable OBJECT-TYPE
    SYNTAX           SEQUENCE OF CfprEtherPortChanIdElemEntry
    MAX-ACCESS       not-accessible
    STATUS           current
    DESCRIPTION
        "Cisco Firepower ether:PortChanIdElem managed object table"
    ::= { cfprEtherObjects 16 }

cfprEtherPortChanIdElemEntry OBJECT-TYPE
    SYNTAX           CfprEtherPortChanIdElemEntry
    MAX-ACCESS       not-accessible
    STATUS           current
    DESCRIPTION
        "Entry for the cfprEtherPortChanIdElemTable table."
    INDEX { cfprEtherPortChanIdElemInstanceId }
    ::= { cfprEtherPortChanIdElemTable 1 }

CfprEtherPortChanIdElemEntry ::= SEQUENCE {
    cfprEtherPortChanIdElemInstanceId                                CfprManagedObjectId,
    cfprEtherPortChanIdElemDn                                        CfprManagedObjectDn,
    cfprEtherPortChanIdElemRn                                        SnmpAdminString,
    cfprEtherPortChanIdElemId                                        Gauge32
}

cfprEtherPortChanIdElemInstanceId OBJECT-TYPE
    SYNTAX       CfprManagedObjectId
    MAX-ACCESS   not-accessible
    STATUS       current
    DESCRIPTION
        "Instance identifier of the managed object."
    ::= { cfprEtherPortChanIdElemEntry 1 }

cfprEtherPortChanIdElemDn OBJECT-TYPE
    SYNTAX       CfprManagedObjectDn
    MAX-ACCESS   read-only
    STATUS       current
    DESCRIPTION
        "Cisco Firepower ether:PortChanIdElem:dn managed object property"
    ::= { cfprEtherPortChanIdElemEntry 2 }

cfprEtherPortChanIdElemRn OBJECT-TYPE
    SYNTAX       SnmpAdminString
    MAX-ACCESS   read-only
    STATUS       current
    DESCRIPTION
        "Cisco Firepower ether:PortChanIdElem:rn managed object property"
    ::= { cfprEtherPortChanIdElemEntry 3 }

cfprEtherPortChanIdElemId OBJECT-TYPE
    SYNTAX       Gauge32
    MAX-ACCESS   read-only
    STATUS       current
    DESCRIPTION
        "Cisco Firepower ether:PortChanIdElem:id managed object property"
    ::= { cfprEtherPortChanIdElemEntry 4 }

cfprEtherPortChanIdUniverseTable OBJECT-TYPE
    SYNTAX           SEQUENCE OF CfprEtherPortChanIdUniverseEntry
    MAX-ACCESS       not-accessible
    STATUS           current
    DESCRIPTION
        "Cisco Firepower ether:PortChanIdUniverse managed object table"
    ::= { cfprEtherObjects 17 }

cfprEtherPortChanIdUniverseEntry OBJECT-TYPE
    SYNTAX           CfprEtherPortChanIdUniverseEntry
    MAX-ACCESS       not-accessible
    STATUS           current
    DESCRIPTION
        "Entry for the cfprEtherPortChanIdUniverseTable table."
    INDEX { cfprEtherPortChanIdUniverseInstanceId }
    ::= { cfprEtherPortChanIdUniverseTable 1 }

CfprEtherPortChanIdUniverseEntry ::= SEQUENCE {
    cfprEtherPortChanIdUniverseInstanceId                            CfprManagedObjectId,
    cfprEtherPortChanIdUniverseDn                                    CfprManagedObjectDn,
    cfprEtherPortChanIdUniverseRn                                    SnmpAdminString
}

cfprEtherPortChanIdUniverseInstanceId OBJECT-TYPE
    SYNTAX       CfprManagedObjectId
    MAX-ACCESS   not-accessible
    STATUS       current
    DESCRIPTION
        "Instance identifier of the managed object."
    ::= { cfprEtherPortChanIdUniverseEntry 1 }

cfprEtherPortChanIdUniverseDn OBJECT-TYPE
    SYNTAX       CfprManagedObjectDn
    MAX-ACCESS   read-only
    STATUS       current
    DESCRIPTION
        "Cisco Firepower ether:PortChanIdUniverse:dn managed
        object property"
    ::= { cfprEtherPortChanIdUniverseEntry 2 }

cfprEtherPortChanIdUniverseRn OBJECT-TYPE
    SYNTAX       SnmpAdminString
    MAX-ACCESS   read-only
    STATUS       current
    DESCRIPTION
        "Cisco Firepower ether:PortChanIdUniverse:rn managed
        object property"
    ::= { cfprEtherPortChanIdUniverseEntry 3 }

cfprEtherRxStatsTable OBJECT-TYPE
    SYNTAX           SEQUENCE OF CfprEtherRxStatsEntry
    MAX-ACCESS       not-accessible
    STATUS           current
    DESCRIPTION
        "Cisco Firepower ether:RxStats managed object table"
    ::= { cfprEtherObjects 18 }

cfprEtherRxStatsEntry OBJECT-TYPE
    SYNTAX           CfprEtherRxStatsEntry
    MAX-ACCESS       not-accessible
    STATUS           current
    DESCRIPTION
        "Entry for the cfprEtherRxStatsTable table."
    INDEX { cfprEtherRxStatsInstanceId }
    ::= { cfprEtherRxStatsTable 1 }

CfprEtherRxStatsEntry ::= SEQUENCE {
    cfprEtherRxStatsInstanceId                                       CfprManagedObjectId,
    cfprEtherRxStatsDn                                               CfprManagedObjectDn,
    cfprEtherRxStatsRn                                               SnmpAdminString,
    cfprEtherRxStatsBroadcastPackets                                 Unsigned64,
    cfprEtherRxStatsBroadcastPacketsDelta                            Counter64,
    cfprEtherRxStatsBroadcastPacketsDeltaAvg                         Unsigned64,
    cfprEtherRxStatsBroadcastPacketsDeltaMax                         Unsigned64,
    cfprEtherRxStatsBroadcastPacketsDeltaMin                         Unsigned64,
    cfprEtherRxStatsIntervals                                        Gauge32,
    cfprEtherRxStatsJumboPackets                                     Unsigned64,
    cfprEtherRxStatsJumboPacketsDelta                                Counter64,
    cfprEtherRxStatsJumboPacketsDeltaAvg                             Unsigned64,
    cfprEtherRxStatsJumboPacketsDeltaMax                             Unsigned64,
    cfprEtherRxStatsJumboPacketsDeltaMin                             Unsigned64,
    cfprEtherRxStatsMulticastPackets                                 Unsigned64,
    cfprEtherRxStatsMulticastPacketsDelta                            Counter64,
    cfprEtherRxStatsMulticastPacketsDeltaAvg                         Unsigned64,
    cfprEtherRxStatsMulticastPacketsDeltaMax                         Unsigned64,
    cfprEtherRxStatsMulticastPacketsDeltaMin                         Unsigned64,
    cfprEtherRxStatsSuspect                                          TruthValue,
    cfprEtherRxStatsThresholded                                      CfprEtherRxStatsThresholded,
    cfprEtherRxStatsTimeCollected                                    DateAndTime,
    cfprEtherRxStatsTotalBytes                                       Unsigned64,
    cfprEtherRxStatsTotalBytesDelta                                  Counter64,
    cfprEtherRxStatsTotalBytesDeltaAvg                               Unsigned64,
    cfprEtherRxStatsTotalBytesDeltaMax                               Unsigned64,
    cfprEtherRxStatsTotalBytesDeltaMin                               Unsigned64,
    cfprEtherRxStatsTotalPackets                                     Unsigned64,
    cfprEtherRxStatsTotalPacketsDelta                                Counter64,
    cfprEtherRxStatsTotalPacketsDeltaAvg                             Unsigned64,
    cfprEtherRxStatsTotalPacketsDeltaMax                             Unsigned64,
    cfprEtherRxStatsTotalPacketsDeltaMin                             Unsigned64,
    cfprEtherRxStatsUnicastPackets                                   Unsigned64,
    cfprEtherRxStatsUnicastPacketsDelta                              Counter64,
    cfprEtherRxStatsUnicastPacketsDeltaAvg                           Unsigned64,
    cfprEtherRxStatsUnicastPacketsDeltaMax                           Unsigned64,
    cfprEtherRxStatsUnicastPacketsDeltaMin                           Unsigned64,
    cfprEtherRxStatsUpdate                                           Gauge32
}

cfprEtherRxStatsInstanceId OBJECT-TYPE
    SYNTAX       CfprManagedObjectId
    MAX-ACCESS   not-accessible
    STATUS       current
    DESCRIPTION
        "Instance identifier of the managed object."
    ::= { cfprEtherRxStatsEntry 1 }

cfprEtherRxStatsDn OBJECT-TYPE
    SYNTAX       CfprManagedObjectDn
    MAX-ACCESS   read-only
    STATUS       current
    DESCRIPTION
        "Cisco Firepower ether:RxStats:dn managed object property"
    ::= { cfprEtherRxStatsEntry 2 }

cfprEtherRxStatsRn OBJECT-TYPE
    SYNTAX       SnmpAdminString
    MAX-ACCESS   read-only
    STATUS       current
    DESCRIPTION
        "Cisco Firepower ether:RxStats:rn managed object property"
    ::= { cfprEtherRxStatsEntry 3 }

cfprEtherRxStatsBroadcastPackets OBJECT-TYPE
    SYNTAX       Unsigned64
    MAX-ACCESS   read-only
    STATUS       current
    DESCRIPTION
        "Cisco Firepower ether:RxStats:broadcastPackets
        managed object property"
    ::= { cfprEtherRxStatsEntry 4 }

cfprEtherRxStatsBroadcastPacketsDelta OBJECT-TYPE
    SYNTAX       Counter64
    MAX-ACCESS   read-only
    STATUS       current
    DESCRIPTION
        "Cisco Firepower ether:RxStats:broadcastPacketsDelta
        managed object property"
    ::= { cfprEtherRxStatsEntry 5 }

cfprEtherRxStatsBroadcastPacketsDeltaAvg OBJECT-TYPE
    SYNTAX       Unsigned64
    MAX-ACCESS   read-only
    STATUS       current
    DESCRIPTION
        "Cisco Firepower ether:RxStats:broadcastPacketsDeltaAvg
        managed object property"
    ::= { cfprEtherRxStatsEntry 6 }

cfprEtherRxStatsBroadcastPacketsDeltaMax OBJECT-TYPE
    SYNTAX       Unsigned64
    MAX-ACCESS   read-only
    STATUS       current
    DESCRIPTION
        "Cisco Firepower ether:RxStats:broadcastPacketsDeltaMax
        managed object property"
    ::= { cfprEtherRxStatsEntry 7 }

cfprEtherRxStatsBroadcastPacketsDeltaMin OBJECT-TYPE
    SYNTAX       Unsigned64
    MAX-ACCESS   read-only
    STATUS       current
    DESCRIPTION
        "Cisco Firepower ether:RxStats:broadcastPacketsDeltaMin
        managed object property"
    ::= { cfprEtherRxStatsEntry 8 }

cfprEtherRxStatsIntervals OBJECT-TYPE
    SYNTAX       Gauge32
    MAX-ACCESS   read-only
    STATUS       current
    DESCRIPTION
        "Cisco Firepower ether:RxStats:intervals managed object property"
    ::= { cfprEtherRxStatsEntry 9 }

cfprEtherRxStatsJumboPackets OBJECT-TYPE
    SYNTAX       Unsigned64
    MAX-ACCESS   read-only
    STATUS       current
    DESCRIPTION
        "Cisco Firepower ether:RxStats:jumboPackets managed
        object property"
    ::= { cfprEtherRxStatsEntry 10 }

cfprEtherRxStatsJumboPacketsDelta OBJECT-TYPE
    SYNTAX       Counter64
    MAX-ACCESS   read-only
    STATUS       current
    DESCRIPTION
        "Cisco Firepower ether:RxStats:jumboPacketsDelta
        managed object property"
    ::= { cfprEtherRxStatsEntry 11 }

cfprEtherRxStatsJumboPacketsDeltaAvg OBJECT-TYPE
    SYNTAX       Unsigned64
    MAX-ACCESS   read-only
    STATUS       current
    DESCRIPTION
        "Cisco Firepower ether:RxStats:jumboPacketsDeltaAvg
        managed object property"
    ::= { cfprEtherRxStatsEntry 12 }

cfprEtherRxStatsJumboPacketsDeltaMax OBJECT-TYPE
    SYNTAX       Unsigned64
    MAX-ACCESS   read-only
    STATUS       current
    DESCRIPTION
        "Cisco Firepower ether:RxStats:jumboPacketsDeltaMax
        managed object property"
    ::= { cfprEtherRxStatsEntry 13 }

cfprEtherRxStatsJumboPacketsDeltaMin OBJECT-TYPE
    SYNTAX       Unsigned64
    MAX-ACCESS   read-only
    STATUS       current
    DESCRIPTION
        "Cisco Firepower ether:RxStats:jumboPacketsDeltaMin
        managed object property"
    ::= { cfprEtherRxStatsEntry 14 }

cfprEtherRxStatsMulticastPackets OBJECT-TYPE
    SYNTAX       Unsigned64
    MAX-ACCESS   read-only
    STATUS       current
    DESCRIPTION
        "Cisco Firepower ether:RxStats:multicastPackets
        managed object property"
    ::= { cfprEtherRxStatsEntry 15 }

cfprEtherRxStatsMulticastPacketsDelta OBJECT-TYPE
    SYNTAX       Counter64
    MAX-ACCESS   read-only
    STATUS       current
    DESCRIPTION
        "Cisco Firepower ether:RxStats:multicastPacketsDelta
        managed object property"
    ::= { cfprEtherRxStatsEntry 16 }

cfprEtherRxStatsMulticastPacketsDeltaAvg OBJECT-TYPE
    SYNTAX       Unsigned64
    MAX-ACCESS   read-only
    STATUS       current
    DESCRIPTION
        "Cisco Firepower ether:RxStats:multicastPacketsDeltaAvg
        managed object property"
    ::= { cfprEtherRxStatsEntry 17 }

cfprEtherRxStatsMulticastPacketsDeltaMax OBJECT-TYPE
    SYNTAX       Unsigned64
    MAX-ACCESS   read-only
    STATUS       current
    DESCRIPTION
        "Cisco Firepower ether:RxStats:multicastPacketsDeltaMax
        managed object property"
    ::= { cfprEtherRxStatsEntry 18 }

cfprEtherRxStatsMulticastPacketsDeltaMin OBJECT-TYPE
    SYNTAX       Unsigned64
    MAX-ACCESS   read-only
    STATUS       current
    DESCRIPTION
        "Cisco Firepower ether:RxStats:multicastPacketsDeltaMin
        managed object property"
    ::= { cfprEtherRxStatsEntry 19 }

cfprEtherRxStatsSuspect OBJECT-TYPE
    SYNTAX       TruthValue
    MAX-ACCESS   read-only
    STATUS       current
    DESCRIPTION
        "Cisco Firepower ether:RxStats:suspect managed object property"
    ::= { cfprEtherRxStatsEntry 20 }

cfprEtherRxStatsThresholded OBJECT-TYPE
    SYNTAX       CfprEtherRxStatsThresholded
    MAX-ACCESS   read-only
    STATUS       current
    DESCRIPTION
        "Cisco Firepower ether:RxStats:thresholded managed
        object property"
    ::= { cfprEtherRxStatsEntry 21 }

cfprEtherRxStatsTimeCollected OBJECT-TYPE
    SYNTAX       DateAndTime
    MAX-ACCESS   read-only
    STATUS       current
    DESCRIPTION
        "Cisco Firepower ether:RxStats:timeCollected managed
        object property"
    ::= { cfprEtherRxStatsEntry 22 }

cfprEtherRxStatsTotalBytes OBJECT-TYPE
    SYNTAX       Unsigned64
    MAX-ACCESS   read-only
    STATUS       current
    DESCRIPTION
        "Cisco Firepower ether:RxStats:totalBytes managed object property"
    ::= { cfprEtherRxStatsEntry 23 }

cfprEtherRxStatsTotalBytesDelta OBJECT-TYPE
    SYNTAX       Counter64
    MAX-ACCESS   read-only
    STATUS       current
    DESCRIPTION
        "Cisco Firepower ether:RxStats:totalBytesDelta
        managed object property"
    ::= { cfprEtherRxStatsEntry 24 }

cfprEtherRxStatsTotalBytesDeltaAvg OBJECT-TYPE
    SYNTAX       Unsigned64
    MAX-ACCESS   read-only
    STATUS       current
    DESCRIPTION
        "Cisco Firepower ether:RxStats:totalBytesDeltaAvg
        managed object property"
    ::= { cfprEtherRxStatsEntry 25 }

cfprEtherRxStatsTotalBytesDeltaMax OBJECT-TYPE
    SYNTAX       Unsigned64
    MAX-ACCESS   read-only
    STATUS       current
    DESCRIPTION
        "Cisco Firepower ether:RxStats:totalBytesDeltaMax
        managed object property"
    ::= { cfprEtherRxStatsEntry 26 }

cfprEtherRxStatsTotalBytesDeltaMin OBJECT-TYPE
    SYNTAX       Unsigned64
    MAX-ACCESS   read-only
    STATUS       current
    DESCRIPTION
        "Cisco Firepower ether:RxStats:totalBytesDeltaMin
        managed object property"
    ::= { cfprEtherRxStatsEntry 27 }

cfprEtherRxStatsTotalPackets OBJECT-TYPE
    SYNTAX       Unsigned64
    MAX-ACCESS   read-only
    STATUS       current
    DESCRIPTION
        "Cisco Firepower ether:RxStats:totalPackets managed
        object property"
    ::= { cfprEtherRxStatsEntry 28 }

cfprEtherRxStatsTotalPacketsDelta OBJECT-TYPE
    SYNTAX       Counter64
    MAX-ACCESS   read-only
    STATUS       current
    DESCRIPTION
        "Cisco Firepower ether:RxStats:totalPacketsDelta
        managed object property"
    ::= { cfprEtherRxStatsEntry 29 }

cfprEtherRxStatsTotalPacketsDeltaAvg OBJECT-TYPE
    SYNTAX       Unsigned64
    MAX-ACCESS   read-only
    STATUS       current
    DESCRIPTION
        "Cisco Firepower ether:RxStats:totalPacketsDeltaAvg
        managed object property"
    ::= { cfprEtherRxStatsEntry 30 }

cfprEtherRxStatsTotalPacketsDeltaMax OBJECT-TYPE
    SYNTAX       Unsigned64
    MAX-ACCESS   read-only
    STATUS       current
    DESCRIPTION
        "Cisco Firepower ether:RxStats:totalPacketsDeltaMax
        managed object property"
    ::= { cfprEtherRxStatsEntry 31 }

cfprEtherRxStatsTotalPacketsDeltaMin OBJECT-TYPE
    SYNTAX       Unsigned64
    MAX-ACCESS   read-only
    STATUS       current
    DESCRIPTION
        "Cisco Firepower ether:RxStats:totalPacketsDeltaMin
        managed object property"
    ::= { cfprEtherRxStatsEntry 32 }

cfprEtherRxStatsUnicastPackets OBJECT-TYPE
    SYNTAX       Unsigned64
    MAX-ACCESS   read-only
    STATUS       current
    DESCRIPTION
        "Cisco Firepower ether:RxStats:unicastPackets managed
        object property"
    ::= { cfprEtherRxStatsEntry 33 }

cfprEtherRxStatsUnicastPacketsDelta OBJECT-TYPE
    SYNTAX       Counter64
    MAX-ACCESS   read-only
    STATUS       current
    DESCRIPTION
        "Cisco Firepower ether:RxStats:unicastPacketsDelta
        managed object property"
    ::= { cfprEtherRxStatsEntry 34 }

cfprEtherRxStatsUnicastPacketsDeltaAvg OBJECT-TYPE
    SYNTAX       Unsigned64
    MAX-ACCESS   read-only
    STATUS       current
    DESCRIPTION
        "Cisco Firepower ether:RxStats:unicastPacketsDeltaAvg
        managed object property"
    ::= { cfprEtherRxStatsEntry 35 }

cfprEtherRxStatsUnicastPacketsDeltaMax OBJECT-TYPE
    SYNTAX       Unsigned64
    MAX-ACCESS   read-only
    STATUS       current
    DESCRIPTION
        "Cisco Firepower ether:RxStats:unicastPacketsDeltaMax
        managed object property"
    ::= { cfprEtherRxStatsEntry 36 }

cfprEtherRxStatsUnicastPacketsDeltaMin OBJECT-TYPE
    SYNTAX       Unsigned64
    MAX-ACCESS   read-only
    STATUS       current
    DESCRIPTION
        "Cisco Firepower ether:RxStats:unicastPacketsDeltaMin
        managed object property"
    ::= { cfprEtherRxStatsEntry 37 }

cfprEtherRxStatsUpdate OBJECT-TYPE
    SYNTAX       Gauge32
    MAX-ACCESS   read-only
    STATUS       current
    DESCRIPTION
        "Cisco Firepower ether:RxStats:update managed object property"
    ::= { cfprEtherRxStatsEntry 38 }

cfprEtherRxStatsHistTable OBJECT-TYPE
    SYNTAX           SEQUENCE OF CfprEtherRxStatsHistEntry
    MAX-ACCESS       not-accessible
    STATUS           current
    DESCRIPTION
        "Cisco Firepower ether:RxStatsHist managed object table"
    ::= { cfprEtherObjects 19 }

cfprEtherRxStatsHistEntry OBJECT-TYPE
    SYNTAX           CfprEtherRxStatsHistEntry
    MAX-ACCESS       not-accessible
    STATUS           current
    DESCRIPTION
        "Entry for the cfprEtherRxStatsHistTable table."
    INDEX { cfprEtherRxStatsHistInstanceId }
    ::= { cfprEtherRxStatsHistTable 1 }

CfprEtherRxStatsHistEntry ::= SEQUENCE {
    cfprEtherRxStatsHistInstanceId                                   CfprManagedObjectId,
    cfprEtherRxStatsHistDn                                           CfprManagedObjectDn,
    cfprEtherRxStatsHistRn                                           SnmpAdminString,
    cfprEtherRxStatsHistBroadcastPackets                             Unsigned64,
    cfprEtherRxStatsHistBroadcastPacketsDelta                        Unsigned64,
    cfprEtherRxStatsHistBroadcastPacketsDeltaAvg                     Unsigned64,
    cfprEtherRxStatsHistBroadcastPacketsDeltaMax                     Unsigned64,
    cfprEtherRxStatsHistBroadcastPacketsDeltaMin                     Unsigned64,
    cfprEtherRxStatsHistId                                           Unsigned64,
    cfprEtherRxStatsHistJumboPackets                                 Unsigned64,
    cfprEtherRxStatsHistJumboPacketsDelta                            Unsigned64,
    cfprEtherRxStatsHistJumboPacketsDeltaAvg                         Unsigned64,
    cfprEtherRxStatsHistJumboPacketsDeltaMax                         Unsigned64,
    cfprEtherRxStatsHistJumboPacketsDeltaMin                         Unsigned64,
    cfprEtherRxStatsHistMostRecent                                   TruthValue,
    cfprEtherRxStatsHistMulticastPackets                             Unsigned64,
    cfprEtherRxStatsHistMulticastPacketsDelta                        Unsigned64,
    cfprEtherRxStatsHistMulticastPacketsDeltaAvg                     Unsigned64,
    cfprEtherRxStatsHistMulticastPacketsDeltaMax                     Unsigned64,
    cfprEtherRxStatsHistMulticastPacketsDeltaMin                     Unsigned64,
    cfprEtherRxStatsHistSuspect                                      TruthValue,
    cfprEtherRxStatsHistThresholded                                  CfprEtherRxStatsHistThresholded,
    cfprEtherRxStatsHistTimeCollected                                DateAndTime,
    cfprEtherRxStatsHistTotalBytes                                   Unsigned64,
    cfprEtherRxStatsHistTotalBytesDelta                              Unsigned64,
    cfprEtherRxStatsHistTotalBytesDeltaAvg                           Unsigned64,
    cfprEtherRxStatsHistTotalBytesDeltaMax                           Unsigned64,
    cfprEtherRxStatsHistTotalBytesDeltaMin                           Unsigned64,
    cfprEtherRxStatsHistTotalPackets                                 Unsigned64,
    cfprEtherRxStatsHistTotalPacketsDelta                            Unsigned64,
    cfprEtherRxStatsHistTotalPacketsDeltaAvg                         Unsigned64,
    cfprEtherRxStatsHistTotalPacketsDeltaMax                         Unsigned64,
    cfprEtherRxStatsHistTotalPacketsDeltaMin                         Unsigned64,
    cfprEtherRxStatsHistUnicastPackets                               Unsigned64,
    cfprEtherRxStatsHistUnicastPacketsDelta                          Unsigned64,
    cfprEtherRxStatsHistUnicastPacketsDeltaAvg                       Unsigned64,
    cfprEtherRxStatsHistUnicastPacketsDeltaMax                       Unsigned64,
    cfprEtherRxStatsHistUnicastPacketsDeltaMin                       Unsigned64
}

cfprEtherRxStatsHistInstanceId OBJECT-TYPE
    SYNTAX       CfprManagedObjectId
    MAX-ACCESS   not-accessible
    STATUS       current
    DESCRIPTION
        "Instance identifier of the managed object."
    ::= { cfprEtherRxStatsHistEntry 1 }

cfprEtherRxStatsHistDn OBJECT-TYPE
    SYNTAX       CfprManagedObjectDn
    MAX-ACCESS   read-only
    STATUS       current
    DESCRIPTION
        "Cisco Firepower ether:RxStatsHist:dn managed object property"
    ::= { cfprEtherRxStatsHistEntry 2 }

cfprEtherRxStatsHistRn OBJECT-TYPE
    SYNTAX       SnmpAdminString
    MAX-ACCESS   read-only
    STATUS       current
    DESCRIPTION
        "Cisco Firepower ether:RxStatsHist:rn managed object property"
    ::= { cfprEtherRxStatsHistEntry 3 }

cfprEtherRxStatsHistBroadcastPackets OBJECT-TYPE
    SYNTAX       Unsigned64
    MAX-ACCESS   read-only
    STATUS       current
    DESCRIPTION
        "Cisco Firepower ether:RxStatsHist:broadcastPackets
        managed object property"
    ::= { cfprEtherRxStatsHistEntry 4 }

cfprEtherRxStatsHistBroadcastPacketsDelta OBJECT-TYPE
    SYNTAX       Unsigned64
    MAX-ACCESS   read-only
    STATUS       current
    DESCRIPTION
        "Cisco Firepower ether:RxStatsHist:broadcastPacketsDelta
        managed object property"
    ::= { cfprEtherRxStatsHistEntry 5 }

cfprEtherRxStatsHistBroadcastPacketsDeltaAvg OBJECT-TYPE
    SYNTAX       Unsigned64
    MAX-ACCESS   read-only
    STATUS       current
    DESCRIPTION
        "Cisco Firepower ether:RxStatsHist:broadcastPacketsDeltaAvg
        managed object property"
    ::= { cfprEtherRxStatsHistEntry 6 }

cfprEtherRxStatsHistBroadcastPacketsDeltaMax OBJECT-TYPE
    SYNTAX       Unsigned64
    MAX-ACCESS   read-only
    STATUS       current
    DESCRIPTION
        "Cisco Firepower ether:RxStatsHist:broadcastPacketsDeltaMax
        managed object property"
    ::= { cfprEtherRxStatsHistEntry 7 }

cfprEtherRxStatsHistBroadcastPacketsDeltaMin OBJECT-TYPE
    SYNTAX       Unsigned64
    MAX-ACCESS   read-only
    STATUS       current
    DESCRIPTION
        "Cisco Firepower ether:RxStatsHist:broadcastPacketsDeltaMin
        managed object property"
    ::= { cfprEtherRxStatsHistEntry 8 }

cfprEtherRxStatsHistId OBJECT-TYPE
    SYNTAX       Unsigned64
    MAX-ACCESS   read-only
    STATUS       current
    DESCRIPTION
        "Cisco Firepower ether:RxStatsHist:id managed object property"
    ::= { cfprEtherRxStatsHistEntry 9 }

cfprEtherRxStatsHistJumboPackets OBJECT-TYPE
    SYNTAX       Unsigned64
    MAX-ACCESS   read-only
    STATUS       current
    DESCRIPTION
        "Cisco Firepower ether:RxStatsHist:jumboPackets
        managed object property"
    ::= { cfprEtherRxStatsHistEntry 10 }

cfprEtherRxStatsHistJumboPacketsDelta OBJECT-TYPE
    SYNTAX       Unsigned64
    MAX-ACCESS   read-only
    STATUS       current
    DESCRIPTION
        "Cisco Firepower ether:RxStatsHist:jumboPacketsDelta
        managed object property"
    ::= { cfprEtherRxStatsHistEntry 11 }

cfprEtherRxStatsHistJumboPacketsDeltaAvg OBJECT-TYPE
    SYNTAX       Unsigned64
    MAX-ACCESS   read-only
    STATUS       current
    DESCRIPTION
        "Cisco Firepower ether:RxStatsHist:jumboPacketsDeltaAvg
        managed object property"
    ::= { cfprEtherRxStatsHistEntry 12 }

cfprEtherRxStatsHistJumboPacketsDeltaMax OBJECT-TYPE
    SYNTAX       Unsigned64
    MAX-ACCESS   read-only
    STATUS       current
    DESCRIPTION
        "Cisco Firepower ether:RxStatsHist:jumboPacketsDeltaMax
        managed object property"
    ::= { cfprEtherRxStatsHistEntry 13 }

cfprEtherRxStatsHistJumboPacketsDeltaMin OBJECT-TYPE
    SYNTAX       Unsigned64
    MAX-ACCESS   read-only
    STATUS       current
    DESCRIPTION
        "Cisco Firepower ether:RxStatsHist:jumboPacketsDeltaMin
        managed object property"
    ::= { cfprEtherRxStatsHistEntry 14 }

cfprEtherRxStatsHistMostRecent OBJECT-TYPE
    SYNTAX       TruthValue
    MAX-ACCESS   read-only
    STATUS       current
    DESCRIPTION
        "Cisco Firepower ether:RxStatsHist:mostRecent managed
        object property"
    ::= { cfprEtherRxStatsHistEntry 15 }

cfprEtherRxStatsHistMulticastPackets OBJECT-TYPE
    SYNTAX       Unsigned64
    MAX-ACCESS   read-only
    STATUS       current
    DESCRIPTION
        "Cisco Firepower ether:RxStatsHist:multicastPackets
        managed object property"
    ::= { cfprEtherRxStatsHistEntry 16 }

cfprEtherRxStatsHistMulticastPacketsDelta OBJECT-TYPE
    SYNTAX       Unsigned64
    MAX-ACCESS   read-only
    STATUS       current
    DESCRIPTION
        "Cisco Firepower ether:RxStatsHist:multicastPacketsDelta
        managed object property"
    ::= { cfprEtherRxStatsHistEntry 17 }

cfprEtherRxStatsHistMulticastPacketsDeltaAvg OBJECT-TYPE
    SYNTAX       Unsigned64
    MAX-ACCESS   read-only
    STATUS       current
    DESCRIPTION
        "Cisco Firepower ether:RxStatsHist:multicastPacketsDeltaAvg
        managed object property"
    ::= { cfprEtherRxStatsHistEntry 18 }

cfprEtherRxStatsHistMulticastPacketsDeltaMax OBJECT-TYPE
    SYNTAX       Unsigned64
    MAX-ACCESS   read-only
    STATUS       current
    DESCRIPTION
        "Cisco Firepower ether:RxStatsHist:multicastPacketsDeltaMax
        managed object property"
    ::= { cfprEtherRxStatsHistEntry 19 }

cfprEtherRxStatsHistMulticastPacketsDeltaMin OBJECT-TYPE
    SYNTAX       Unsigned64
    MAX-ACCESS   read-only
    STATUS       current
    DESCRIPTION
        "Cisco Firepower ether:RxStatsHist:multicastPacketsDeltaMin
        managed object property"
    ::= { cfprEtherRxStatsHistEntry 20 }

cfprEtherRxStatsHistSuspect OBJECT-TYPE
    SYNTAX       TruthValue
    MAX-ACCESS   read-only
    STATUS       current
    DESCRIPTION
        "Cisco Firepower ether:RxStatsHist:suspect managed
        object property"
    ::= { cfprEtherRxStatsHistEntry 21 }

cfprEtherRxStatsHistThresholded OBJECT-TYPE
    SYNTAX       CfprEtherRxStatsHistThresholded
    MAX-ACCESS   read-only
    STATUS       current
    DESCRIPTION
        "Cisco Firepower ether:RxStatsHist:thresholded
        managed object property"
    ::= { cfprEtherRxStatsHistEntry 22 }

cfprEtherRxStatsHistTimeCollected OBJECT-TYPE
    SYNTAX       DateAndTime
    MAX-ACCESS   read-only
    STATUS       current
    DESCRIPTION
        "Cisco Firepower ether:RxStatsHist:timeCollected
        managed object property"
    ::= { cfprEtherRxStatsHistEntry 23 }

cfprEtherRxStatsHistTotalBytes OBJECT-TYPE
    SYNTAX       Unsigned64
    MAX-ACCESS   read-only
    STATUS       current
    DESCRIPTION
        "Cisco Firepower ether:RxStatsHist:totalBytes managed
        object property"
    ::= { cfprEtherRxStatsHistEntry 24 }

cfprEtherRxStatsHistTotalBytesDelta OBJECT-TYPE
    SYNTAX       Unsigned64
    MAX-ACCESS   read-only
    STATUS       current
    DESCRIPTION
        "Cisco Firepower ether:RxStatsHist:totalBytesDelta
        managed object property"
    ::= { cfprEtherRxStatsHistEntry 25 }

cfprEtherRxStatsHistTotalBytesDeltaAvg OBJECT-TYPE
    SYNTAX       Unsigned64
    MAX-ACCESS   read-only
    STATUS       current
    DESCRIPTION
        "Cisco Firepower ether:RxStatsHist:totalBytesDeltaAvg
        managed object property"
    ::= { cfprEtherRxStatsHistEntry 26 }

cfprEtherRxStatsHistTotalBytesDeltaMax OBJECT-TYPE
    SYNTAX       Unsigned64
    MAX-ACCESS   read-only
    STATUS       current
    DESCRIPTION
        "Cisco Firepower ether:RxStatsHist:totalBytesDeltaMax
        managed object property"
    ::= { cfprEtherRxStatsHistEntry 27 }

cfprEtherRxStatsHistTotalBytesDeltaMin OBJECT-TYPE
    SYNTAX       Unsigned64
    MAX-ACCESS   read-only
    STATUS       current
    DESCRIPTION
        "Cisco Firepower ether:RxStatsHist:totalBytesDeltaMin
        managed object property"
    ::= { cfprEtherRxStatsHistEntry 28 }

cfprEtherRxStatsHistTotalPackets OBJECT-TYPE
    SYNTAX       Unsigned64
    MAX-ACCESS   read-only
    STATUS       current
    DESCRIPTION
        "Cisco Firepower ether:RxStatsHist:totalPackets
        managed object property"
    ::= { cfprEtherRxStatsHistEntry 29 }

cfprEtherRxStatsHistTotalPacketsDelta OBJECT-TYPE
    SYNTAX       Unsigned64
    MAX-ACCESS   read-only
    STATUS       current
    DESCRIPTION
        "Cisco Firepower ether:RxStatsHist:totalPacketsDelta
        managed object property"
    ::= { cfprEtherRxStatsHistEntry 30 }

cfprEtherRxStatsHistTotalPacketsDeltaAvg OBJECT-TYPE
    SYNTAX       Unsigned64
    MAX-ACCESS   read-only
    STATUS       current
    DESCRIPTION
        "Cisco Firepower ether:RxStatsHist:totalPacketsDeltaAvg
        managed object property"
    ::= { cfprEtherRxStatsHistEntry 31 }

cfprEtherRxStatsHistTotalPacketsDeltaMax OBJECT-TYPE
    SYNTAX       Unsigned64
    MAX-ACCESS   read-only
    STATUS       current
    DESCRIPTION
        "Cisco Firepower ether:RxStatsHist:totalPacketsDeltaMax
        managed object property"
    ::= { cfprEtherRxStatsHistEntry 32 }

cfprEtherRxStatsHistTotalPacketsDeltaMin OBJECT-TYPE
    SYNTAX       Unsigned64
    MAX-ACCESS   read-only
    STATUS       current
    DESCRIPTION
        "Cisco Firepower ether:RxStatsHist:totalPacketsDeltaMin
        managed object property"
    ::= { cfprEtherRxStatsHistEntry 33 }

cfprEtherRxStatsHistUnicastPackets OBJECT-TYPE
    SYNTAX       Unsigned64
    MAX-ACCESS   read-only
    STATUS       current
    DESCRIPTION
        "Cisco Firepower ether:RxStatsHist:unicastPackets
        managed object property"
    ::= { cfprEtherRxStatsHistEntry 34 }

cfprEtherRxStatsHistUnicastPacketsDelta OBJECT-TYPE
    SYNTAX       Unsigned64
    MAX-ACCESS   read-only
    STATUS       current
    DESCRIPTION
        "Cisco Firepower ether:RxStatsHist:unicastPacketsDelta
        managed object property"
    ::= { cfprEtherRxStatsHistEntry 35 }

cfprEtherRxStatsHistUnicastPacketsDeltaAvg OBJECT-TYPE
    SYNTAX       Unsigned64
    MAX-ACCESS   read-only
    STATUS       current
    DESCRIPTION
        "Cisco Firepower ether:RxStatsHist:unicastPacketsDeltaAvg
        managed object property"
    ::= { cfprEtherRxStatsHistEntry 36 }

cfprEtherRxStatsHistUnicastPacketsDeltaMax OBJECT-TYPE
    SYNTAX       Unsigned64
    MAX-ACCESS   read-only
    STATUS       current
    DESCRIPTION
        "Cisco Firepower ether:RxStatsHist:unicastPacketsDeltaMax
        managed object property"
    ::= { cfprEtherRxStatsHistEntry 37 }

cfprEtherRxStatsHistUnicastPacketsDeltaMin OBJECT-TYPE
    SYNTAX       Unsigned64
    MAX-ACCESS   read-only
    STATUS       current
    DESCRIPTION
        "Cisco Firepower ether:RxStatsHist:unicastPacketsDeltaMin
        managed object property"
    ::= { cfprEtherRxStatsHistEntry 38 }

cfprEtherServerIntFIoTable OBJECT-TYPE
    SYNTAX           SEQUENCE OF CfprEtherServerIntFIoEntry
    MAX-ACCESS       not-accessible
    STATUS           current
    DESCRIPTION
        "Cisco Firepower ether:ServerIntFIo managed object table"
    ::= { cfprEtherObjects 20 }

cfprEtherServerIntFIoEntry OBJECT-TYPE
    SYNTAX           CfprEtherServerIntFIoEntry
    MAX-ACCESS       not-accessible
    STATUS           current
    DESCRIPTION
        "Entry for the cfprEtherServerIntFIoTable table."
    INDEX { cfprEtherServerIntFIoInstanceId }
    ::= { cfprEtherServerIntFIoTable 1 }

CfprEtherServerIntFIoEntry ::= SEQUENCE {
    cfprEtherServerIntFIoInstanceId                                  CfprManagedObjectId,
    cfprEtherServerIntFIoDn                                          CfprManagedObjectDn,
    cfprEtherServerIntFIoRn                                          SnmpAdminString,
    cfprEtherServerIntFIoAdminSpeed                                  CfprPortEthSpeed,
    cfprEtherServerIntFIoAdminState                                  CfprEtherServerIntFIoAdminState,
    cfprEtherServerIntFIoAggrPortId                                  Gauge32,
    cfprEtherServerIntFIoChassisId                                   Gauge32,
    cfprEtherServerIntFIoEncap                                       CfprPortEncap,
    cfprEtherServerIntFIoEpDn                                        SnmpAdminString,
    cfprEtherServerIntFIoFltAggr                                     Unsigned64,
    cfprEtherServerIntFIoFsmDescr                                    SnmpAdminString,
    cfprEtherServerIntFIoFsmPrev                                     SnmpAdminString,
    cfprEtherServerIntFIoFsmProgr                                    Gauge32,
    cfprEtherServerIntFIoFsmRmtInvErrCode                            Gauge32,
    cfprEtherServerIntFIoFsmRmtInvErrDescr                           SnmpAdminString,
    cfprEtherServerIntFIoFsmRmtInvRslt                               CfprConditionRemoteInvRslt,
    cfprEtherServerIntFIoFsmStageDescr                               SnmpAdminString,
    cfprEtherServerIntFIoFsmStamp                                    DateAndTime,
    cfprEtherServerIntFIoFsmStatus                                   SnmpAdminString,
    cfprEtherServerIntFIoFsmTry                                      Gauge32,
    cfprEtherServerIntFIoIfRole                                      CfprEtherServerIntFIoIfRole,
    cfprEtherServerIntFIoIfType                                      CfprNetworkPhysEpIfType,
    cfprEtherServerIntFIoLocale                                      CfprEtherServerIntFIoLocale,
    cfprEtherServerIntFIoMac                                         MacAddress,
    cfprEtherServerIntFIoMode                                        CfprPortMode,
    cfprEtherServerIntFIoModel                                       SnmpAdminString,
    cfprEtherServerIntFIoName                                        SnmpAdminString,
    cfprEtherServerIntFIoNsSize                                      Gauge32,
    cfprEtherServerIntFIoOperBorderAggrPortId                        Gauge32,
    cfprEtherServerIntFIoOperBorderPortId                            Gauge32,
    cfprEtherServerIntFIoOperBorderSlotId                            Gauge32,
    cfprEtherServerIntFIoOperState                                   CfprNetworkPortOperState,
    cfprEtherServerIntFIoPeerAggrPortId                              Gauge32,
    cfprEtherServerIntFIoPeerChassisId                               Gauge32,
    cfprEtherServerIntFIoPeerDn                                      SnmpAdminString,
    cfprEtherServerIntFIoPeerEncap                                   Gauge32,
    cfprEtherServerIntFIoPeerPortId                                  Gauge32,
    cfprEtherServerIntFIoPeerSlotId                                  Gauge32,
    cfprEtherServerIntFIoPortId                                      Gauge32,
    cfprEtherServerIntFIoRevision                                    SnmpAdminString,
    cfprEtherServerIntFIoSerial                                      SnmpAdminString,
    cfprEtherServerIntFIoSlotId                                      Gauge32,
    cfprEtherServerIntFIoStateQual                                   SnmpAdminString,
    cfprEtherServerIntFIoSwitchId                                    CfprNetworkSwitchId,
    cfprEtherServerIntFIoTransport                                   CfprEtherServerIntFIoTransport,
    cfprEtherServerIntFIoTs                                          DateAndTime,
    cfprEtherServerIntFIoType                                        CfprEtherServerIntFIoType,
    cfprEtherServerIntFIoVendor                                      SnmpAdminString,
    cfprEtherServerIntFIoXcvrType                                    CfprEquipmentXcvrType
}

cfprEtherServerIntFIoInstanceId OBJECT-TYPE
    SYNTAX       CfprManagedObjectId
    MAX-ACCESS   not-accessible
    STATUS       current
    DESCRIPTION
        "Instance identifier of the managed object."
    ::= { cfprEtherServerIntFIoEntry 1 }

cfprEtherServerIntFIoDn OBJECT-TYPE
    SYNTAX       CfprManagedObjectDn
    MAX-ACCESS   read-only
    STATUS       current
    DESCRIPTION
        "Cisco Firepower ether:ServerIntFIo:dn managed object property"
    ::= { cfprEtherServerIntFIoEntry 2 }

cfprEtherServerIntFIoRn OBJECT-TYPE
    SYNTAX       SnmpAdminString
    MAX-ACCESS   read-only
    STATUS       current
    DESCRIPTION
        "Cisco Firepower ether:ServerIntFIo:rn managed object property"
    ::= { cfprEtherServerIntFIoEntry 3 }

cfprEtherServerIntFIoAdminSpeed OBJECT-TYPE
    SYNTAX       CfprPortEthSpeed
    MAX-ACCESS   read-only
    STATUS       current
    DESCRIPTION
        "Cisco Firepower ether:ServerIntFIo:adminSpeed
        managed object property"
    ::= { cfprEtherServerIntFIoEntry 4 }

cfprEtherServerIntFIoAdminState OBJECT-TYPE
    SYNTAX       CfprEtherServerIntFIoAdminState
    MAX-ACCESS   read-only
    STATUS       current
    DESCRIPTION
        "Cisco Firepower ether:ServerIntFIo:adminState
        managed object property"
    ::= { cfprEtherServerIntFIoEntry 5 }

cfprEtherServerIntFIoAggrPortId OBJECT-TYPE
    SYNTAX       Gauge32
    MAX-ACCESS   read-only
    STATUS       current
    DESCRIPTION
        "Cisco Firepower ether:ServerIntFIo:aggrPortId
        managed object property"
    ::= { cfprEtherServerIntFIoEntry 6 }

cfprEtherServerIntFIoChassisId OBJECT-TYPE
    SYNTAX       Gauge32
    MAX-ACCESS   read-only
    STATUS       current
    DESCRIPTION
        "Cisco Firepower ether:ServerIntFIo:chassisId managed
        object property"
    ::= { cfprEtherServerIntFIoEntry 7 }

cfprEtherServerIntFIoEncap OBJECT-TYPE
    SYNTAX       CfprPortEncap
    MAX-ACCESS   read-only
    STATUS       current
    DESCRIPTION
        "Cisco Firepower ether:ServerIntFIo:encap managed object property"
    ::= { cfprEtherServerIntFIoEntry 8 }

cfprEtherServerIntFIoEpDn OBJECT-TYPE
    SYNTAX       SnmpAdminString
    MAX-ACCESS   read-only
    STATUS       current
    DESCRIPTION
        "Cisco Firepower ether:ServerIntFIo:epDn managed object property"
    ::= { cfprEtherServerIntFIoEntry 9 }

cfprEtherServerIntFIoFltAggr OBJECT-TYPE
    SYNTAX       Unsigned64
    MAX-ACCESS   read-only
    STATUS       current
    DESCRIPTION
        "Cisco Firepower ether:ServerIntFIo:fltAggr managed
        object property"
    ::= { cfprEtherServerIntFIoEntry 10 }

cfprEtherServerIntFIoFsmDescr OBJECT-TYPE
    SYNTAX       SnmpAdminString
    MAX-ACCESS   read-only
    STATUS       current
    DESCRIPTION
        "Cisco Firepower ether:ServerIntFIo:fsmDescr managed
        object property"
    ::= { cfprEtherServerIntFIoEntry 11 }

cfprEtherServerIntFIoFsmPrev OBJECT-TYPE
    SYNTAX       SnmpAdminString
    MAX-ACCESS   read-only
    STATUS       current
    DESCRIPTION
        "Cisco Firepower ether:ServerIntFIo:fsmPrev managed
        object property"
    ::= { cfprEtherServerIntFIoEntry 12 }

cfprEtherServerIntFIoFsmProgr OBJECT-TYPE
    SYNTAX       Gauge32
    MAX-ACCESS   read-only
    STATUS       current
    DESCRIPTION
        "Cisco Firepower ether:ServerIntFIo:fsmProgr managed
        object property"
    ::= { cfprEtherServerIntFIoEntry 13 }

cfprEtherServerIntFIoFsmRmtInvErrCode OBJECT-TYPE
    SYNTAX       Gauge32
    MAX-ACCESS   read-only
    STATUS       current
    DESCRIPTION
        "Cisco Firepower ether:ServerIntFIo:fsmRmtInvErrCode
        managed object property"
    ::= { cfprEtherServerIntFIoEntry 14 }

cfprEtherServerIntFIoFsmRmtInvErrDescr OBJECT-TYPE
    SYNTAX       SnmpAdminString
    MAX-ACCESS   read-only
    STATUS       current
    DESCRIPTION
        "Cisco Firepower ether:ServerIntFIo:fsmRmtInvErrDescr
        managed object property"
    ::= { cfprEtherServerIntFIoEntry 15 }

cfprEtherServerIntFIoFsmRmtInvRslt OBJECT-TYPE
    SYNTAX       CfprConditionRemoteInvRslt
    MAX-ACCESS   read-only
    STATUS       current
    DESCRIPTION
        "Cisco Firepower ether:ServerIntFIo:fsmRmtInvRslt
        managed object property"
    ::= { cfprEtherServerIntFIoEntry 16 }

cfprEtherServerIntFIoFsmStageDescr OBJECT-TYPE
    SYNTAX       SnmpAdminString
    MAX-ACCESS   read-only
    STATUS       current
    DESCRIPTION
        "Cisco Firepower ether:ServerIntFIo:fsmStageDescr
        managed object property"
    ::= { cfprEtherServerIntFIoEntry 17 }

cfprEtherServerIntFIoFsmStamp OBJECT-TYPE
    SYNTAX       DateAndTime
    MAX-ACCESS   read-only
    STATUS       current
    DESCRIPTION
        "Cisco Firepower ether:ServerIntFIo:fsmStamp managed
        object property"
    ::= { cfprEtherServerIntFIoEntry 18 }

cfprEtherServerIntFIoFsmStatus OBJECT-TYPE
    SYNTAX       SnmpAdminString
    MAX-ACCESS   read-only
    STATUS       current
    DESCRIPTION
        "Cisco Firepower ether:ServerIntFIo:fsmStatus managed
        object property"
    ::= { cfprEtherServerIntFIoEntry 19 }

cfprEtherServerIntFIoFsmTry OBJECT-TYPE
    SYNTAX       Gauge32
    MAX-ACCESS   read-only
    STATUS       current
    DESCRIPTION
        "Cisco Firepower ether:ServerIntFIo:fsmTry managed
        object property"
    ::= { cfprEtherServerIntFIoEntry 20 }

cfprEtherServerIntFIoIfRole OBJECT-TYPE
    SYNTAX       CfprEtherServerIntFIoIfRole
    MAX-ACCESS   read-only
    STATUS       current
    DESCRIPTION
        "Cisco Firepower ether:ServerIntFIo:ifRole managed
        object property"
    ::= { cfprEtherServerIntFIoEntry 21 }

cfprEtherServerIntFIoIfType OBJECT-TYPE
    SYNTAX       CfprNetworkPhysEpIfType
    MAX-ACCESS   read-only
    STATUS       current
    DESCRIPTION
        "Cisco Firepower ether:ServerIntFIo:ifType managed
        object property"
    ::= { cfprEtherServerIntFIoEntry 22 }

cfprEtherServerIntFIoLocale OBJECT-TYPE
    SYNTAX       CfprEtherServerIntFIoLocale
    MAX-ACCESS   read-only
    STATUS       current
    DESCRIPTION
        "Cisco Firepower ether:ServerIntFIo:locale managed
        object property"
    ::= { cfprEtherServerIntFIoEntry 23 }

cfprEtherServerIntFIoMac OBJECT-TYPE
    SYNTAX       MacAddress
    MAX-ACCESS   read-only
    STATUS       current
    DESCRIPTION
        "Cisco Firepower ether:ServerIntFIo:mac managed object property"
    ::= { cfprEtherServerIntFIoEntry 24 }

cfprEtherServerIntFIoMode OBJECT-TYPE
    SYNTAX       CfprPortMode
    MAX-ACCESS   read-only
    STATUS       current
    DESCRIPTION
        "Cisco Firepower ether:ServerIntFIo:mode managed object property"
    ::= { cfprEtherServerIntFIoEntry 25 }

cfprEtherServerIntFIoModel OBJECT-TYPE
    SYNTAX       SnmpAdminString
    MAX-ACCESS   read-only
    STATUS       current
    DESCRIPTION
        "Cisco Firepower ether:ServerIntFIo:model managed object property"
    ::= { cfprEtherServerIntFIoEntry 26 }

cfprEtherServerIntFIoName OBJECT-TYPE
    SYNTAX       SnmpAdminString
    MAX-ACCESS   read-only
    STATUS       current
    DESCRIPTION
        "Cisco Firepower ether:ServerIntFIo:name managed object property"
    ::= { cfprEtherServerIntFIoEntry 27 }

cfprEtherServerIntFIoNsSize OBJECT-TYPE
    SYNTAX       Gauge32
    MAX-ACCESS   read-only
    STATUS       current
    DESCRIPTION
        "Cisco Firepower ether:ServerIntFIo:nsSize managed
        object property"
    ::= { cfprEtherServerIntFIoEntry 28 }

cfprEtherServerIntFIoOperBorderAggrPortId OBJECT-TYPE
    SYNTAX       Gauge32
    MAX-ACCESS   read-only
    STATUS       current
    DESCRIPTION
        "Cisco Firepower ether:ServerIntFIo:operBorderAggrPortId
        managed object property"
    ::= { cfprEtherServerIntFIoEntry 29 }

cfprEtherServerIntFIoOperBorderPortId OBJECT-TYPE
    SYNTAX       Gauge32
    MAX-ACCESS   read-only
    STATUS       current
    DESCRIPTION
        "Cisco Firepower ether:ServerIntFIo:operBorderPortId
        managed object property"
    ::= { cfprEtherServerIntFIoEntry 30 }

cfprEtherServerIntFIoOperBorderSlotId OBJECT-TYPE
    SYNTAX       Gauge32
    MAX-ACCESS   read-only
    STATUS       current
    DESCRIPTION
        "Cisco Firepower ether:ServerIntFIo:operBorderSlotId
        managed object property"
    ::= { cfprEtherServerIntFIoEntry 31 }

cfprEtherServerIntFIoOperState OBJECT-TYPE
    SYNTAX       CfprNetworkPortOperState
    MAX-ACCESS   read-only
    STATUS       current
    DESCRIPTION
        "Cisco Firepower ether:ServerIntFIo:operState managed
        object property"
    ::= { cfprEtherServerIntFIoEntry 32 }

cfprEtherServerIntFIoPeerAggrPortId OBJECT-TYPE
    SYNTAX       Gauge32
    MAX-ACCESS   read-only
    STATUS       current
    DESCRIPTION
        "Cisco Firepower ether:ServerIntFIo:peerAggrPortId
        managed object property"
    ::= { cfprEtherServerIntFIoEntry 33 }

cfprEtherServerIntFIoPeerChassisId OBJECT-TYPE
    SYNTAX       Gauge32
    MAX-ACCESS   read-only
    STATUS       current
    DESCRIPTION
        "Cisco Firepower ether:ServerIntFIo:peerChassisId
        managed object property"
    ::= { cfprEtherServerIntFIoEntry 34 }

cfprEtherServerIntFIoPeerDn OBJECT-TYPE
    SYNTAX       SnmpAdminString
    MAX-ACCESS   read-only
    STATUS       current
    DESCRIPTION
        "Cisco Firepower ether:ServerIntFIo:peerDn managed
        object property"
    ::= { cfprEtherServerIntFIoEntry 35 }

cfprEtherServerIntFIoPeerEncap OBJECT-TYPE
    SYNTAX       Gauge32
    MAX-ACCESS   read-only
    STATUS       current
    DESCRIPTION
        "Cisco Firepower ether:ServerIntFIo:peerEncap managed
        object property"
    ::= { cfprEtherServerIntFIoEntry 36 }

cfprEtherServerIntFIoPeerPortId OBJECT-TYPE
    SYNTAX       Gauge32
    MAX-ACCESS   read-only
    STATUS       current
    DESCRIPTION
        "Cisco Firepower ether:ServerIntFIo:peerPortId
        managed object property"
    ::= { cfprEtherServerIntFIoEntry 37 }

cfprEtherServerIntFIoPeerSlotId OBJECT-TYPE
    SYNTAX       Gauge32
    MAX-ACCESS   read-only
    STATUS       current
    DESCRIPTION
        "Cisco Firepower ether:ServerIntFIo:peerSlotId
        managed object property"
    ::= { cfprEtherServerIntFIoEntry 38 }

cfprEtherServerIntFIoPortId OBJECT-TYPE
    SYNTAX       Gauge32
    MAX-ACCESS   read-only
    STATUS       current
    DESCRIPTION
        "Cisco Firepower ether:ServerIntFIo:portId managed
        object property"
    ::= { cfprEtherServerIntFIoEntry 39 }

cfprEtherServerIntFIoRevision OBJECT-TYPE
    SYNTAX       SnmpAdminString
    MAX-ACCESS   read-only
    STATUS       current
    DESCRIPTION
        "Cisco Firepower ether:ServerIntFIo:revision managed
        object property"
    ::= { cfprEtherServerIntFIoEntry 40 }

cfprEtherServerIntFIoSerial OBJECT-TYPE
    SYNTAX       SnmpAdminString
    MAX-ACCESS   read-only
    STATUS       current
    DESCRIPTION
        "Cisco Firepower ether:ServerIntFIo:serial managed
        object property"
    ::= { cfprEtherServerIntFIoEntry 41 }

cfprEtherServerIntFIoSlotId OBJECT-TYPE
    SYNTAX       Gauge32
    MAX-ACCESS   read-only
    STATUS       current
    DESCRIPTION
        "Cisco Firepower ether:ServerIntFIo:slotId managed
        object property"
    ::= { cfprEtherServerIntFIoEntry 42 }

cfprEtherServerIntFIoStateQual OBJECT-TYPE
    SYNTAX       SnmpAdminString
    MAX-ACCESS   read-only
    STATUS       current
    DESCRIPTION
        "Cisco Firepower ether:ServerIntFIo:stateQual managed
        object property"
    ::= { cfprEtherServerIntFIoEntry 43 }

cfprEtherServerIntFIoSwitchId OBJECT-TYPE
    SYNTAX       CfprNetworkSwitchId
    MAX-ACCESS   read-only
    STATUS       current
    DESCRIPTION
        "Cisco Firepower ether:ServerIntFIo:switchId managed
        object property"
    ::= { cfprEtherServerIntFIoEntry 44 }

cfprEtherServerIntFIoTransport OBJECT-TYPE
    SYNTAX       CfprEtherServerIntFIoTransport
    MAX-ACCESS   read-only
    STATUS       current
    DESCRIPTION
        "Cisco Firepower ether:ServerIntFIo:transport managed
        object property"
    ::= { cfprEtherServerIntFIoEntry 45 }

cfprEtherServerIntFIoTs OBJECT-TYPE
    SYNTAX       DateAndTime
    MAX-ACCESS   read-only
    STATUS       current
    DESCRIPTION
        "Cisco Firepower ether:ServerIntFIo:ts managed object property"
    ::= { cfprEtherServerIntFIoEntry 46 }

cfprEtherServerIntFIoType OBJECT-TYPE
    SYNTAX       CfprEtherServerIntFIoType
    MAX-ACCESS   read-only
    STATUS       current
    DESCRIPTION
        "Cisco Firepower ether:ServerIntFIo:type managed object property"
    ::= { cfprEtherServerIntFIoEntry 47 }

cfprEtherServerIntFIoVendor OBJECT-TYPE
    SYNTAX       SnmpAdminString
    MAX-ACCESS   read-only
    STATUS       current
    DESCRIPTION
        "Cisco Firepower ether:ServerIntFIo:vendor managed
        object property"
    ::= { cfprEtherServerIntFIoEntry 48 }

cfprEtherServerIntFIoXcvrType OBJECT-TYPE
    SYNTAX       CfprEquipmentXcvrType
    MAX-ACCESS   read-only
    STATUS       current
    DESCRIPTION
        "Cisco Firepower ether:ServerIntFIo:xcvrType managed
        object property"
    ::= { cfprEtherServerIntFIoEntry 49 }

cfprEtherServerIntFIoFsmTable OBJECT-TYPE
    SYNTAX           SEQUENCE OF CfprEtherServerIntFIoFsmEntry
    MAX-ACCESS       not-accessible
    STATUS           current
    DESCRIPTION
        "Cisco Firepower ether:ServerIntFIoFsm managed object table"
    ::= { cfprEtherObjects 21 }

cfprEtherServerIntFIoFsmEntry OBJECT-TYPE
    SYNTAX           CfprEtherServerIntFIoFsmEntry
    MAX-ACCESS       not-accessible
    STATUS           current
    DESCRIPTION
        "Entry for the cfprEtherServerIntFIoFsmTable table."
    INDEX { cfprEtherServerIntFIoFsmInstanceId }
    ::= { cfprEtherServerIntFIoFsmTable 1 }

CfprEtherServerIntFIoFsmEntry ::= SEQUENCE {
    cfprEtherServerIntFIoFsmInstanceId                               CfprManagedObjectId,
    cfprEtherServerIntFIoFsmDn                                       CfprManagedObjectDn,
    cfprEtherServerIntFIoFsmRn                                       SnmpAdminString,
    cfprEtherServerIntFIoFsmCompletionTime                           DateAndTime,
    cfprEtherServerIntFIoFsmCurrentFsm                               CfprEtherServerIntFIoFsmCurrentFsm,
    cfprEtherServerIntFIoFsmDescrData                                SnmpAdminString,
    cfprEtherServerIntFIoFsmFsmStatus                                CfprFsmFsmStageStatus,
    cfprEtherServerIntFIoFsmProgress                                 Gauge32,
    cfprEtherServerIntFIoFsmRmtErrCode                               Gauge32,
    cfprEtherServerIntFIoFsmRmtErrDescr                              SnmpAdminString,
    cfprEtherServerIntFIoFsmRmtRslt                                  CfprConditionRemoteInvRslt
}

cfprEtherServerIntFIoFsmInstanceId OBJECT-TYPE
    SYNTAX       CfprManagedObjectId
    MAX-ACCESS   not-accessible
    STATUS       current
    DESCRIPTION
        "Instance identifier of the managed object."
    ::= { cfprEtherServerIntFIoFsmEntry 1 }

cfprEtherServerIntFIoFsmDn OBJECT-TYPE
    SYNTAX       CfprManagedObjectDn
    MAX-ACCESS   read-only
    STATUS       current
    DESCRIPTION
        "Cisco Firepower ether:ServerIntFIoFsm:dn managed object property"
    ::= { cfprEtherServerIntFIoFsmEntry 2 }

cfprEtherServerIntFIoFsmRn OBJECT-TYPE
    SYNTAX       SnmpAdminString
    MAX-ACCESS   read-only
    STATUS       current
    DESCRIPTION
        "Cisco Firepower ether:ServerIntFIoFsm:rn managed object property"
    ::= { cfprEtherServerIntFIoFsmEntry 3 }

cfprEtherServerIntFIoFsmCompletionTime OBJECT-TYPE
    SYNTAX       DateAndTime
    MAX-ACCESS   read-only
    STATUS       current
    DESCRIPTION
        "Cisco Firepower ether:ServerIntFIoFsm:completionTime
        managed object property"
    ::= { cfprEtherServerIntFIoFsmEntry 4 }

cfprEtherServerIntFIoFsmCurrentFsm OBJECT-TYPE
    SYNTAX       CfprEtherServerIntFIoFsmCurrentFsm
    MAX-ACCESS   read-only
    STATUS       current
    DESCRIPTION
        "Cisco Firepower ether:ServerIntFIoFsm:currentFsm
        managed object property"
    ::= { cfprEtherServerIntFIoFsmEntry 5 }

cfprEtherServerIntFIoFsmDescrData OBJECT-TYPE
    SYNTAX       SnmpAdminString
    MAX-ACCESS   read-only
    STATUS       current
    DESCRIPTION
        "Cisco Firepower ether:ServerIntFIoFsm:descr managed
        object property"
    ::= { cfprEtherServerIntFIoFsmEntry 6 }

cfprEtherServerIntFIoFsmFsmStatus OBJECT-TYPE
    SYNTAX       CfprFsmFsmStageStatus
    MAX-ACCESS   read-only
    STATUS       current
    DESCRIPTION
        "Cisco Firepower ether:ServerIntFIoFsm:fsmStatus
        managed object property"
    ::= { cfprEtherServerIntFIoFsmEntry 7 }

cfprEtherServerIntFIoFsmProgress OBJECT-TYPE
    SYNTAX       Gauge32
    MAX-ACCESS   read-only
    STATUS       current
    DESCRIPTION
        "Cisco Firepower ether:ServerIntFIoFsm:progress
        managed object property"
    ::= { cfprEtherServerIntFIoFsmEntry 8 }

cfprEtherServerIntFIoFsmRmtErrCode OBJECT-TYPE
    SYNTAX       Gauge32
    MAX-ACCESS   read-only
    STATUS       current
    DESCRIPTION
        "Cisco Firepower ether:ServerIntFIoFsm:rmtErrCode
        managed object property"
    ::= { cfprEtherServerIntFIoFsmEntry 9 }

cfprEtherServerIntFIoFsmRmtErrDescr OBJECT-TYPE
    SYNTAX       SnmpAdminString
    MAX-ACCESS   read-only
    STATUS       current
    DESCRIPTION
        "Cisco Firepower ether:ServerIntFIoFsm:rmtErrDescr
        managed object property"
    ::= { cfprEtherServerIntFIoFsmEntry 10 }

cfprEtherServerIntFIoFsmRmtRslt OBJECT-TYPE
    SYNTAX       CfprConditionRemoteInvRslt
    MAX-ACCESS   read-only
    STATUS       current
    DESCRIPTION
        "Cisco Firepower ether:ServerIntFIoFsm:rmtRslt
        managed object property"
    ::= { cfprEtherServerIntFIoFsmEntry 11 }

cfprEtherServerIntFIoFsmStageTable OBJECT-TYPE
    SYNTAX           SEQUENCE OF CfprEtherServerIntFIoFsmStageEntry
    MAX-ACCESS       not-accessible
    STATUS           current
    DESCRIPTION
        "Cisco Firepower ether:ServerIntFIoFsmStage managed object table"
    ::= { cfprEtherObjects 22 }

cfprEtherServerIntFIoFsmStageEntry OBJECT-TYPE
    SYNTAX           CfprEtherServerIntFIoFsmStageEntry
    MAX-ACCESS       not-accessible
    STATUS           current
    DESCRIPTION
        "Entry for the cfprEtherServerIntFIoFsmStageTable table."
    INDEX { cfprEtherServerIntFIoFsmStageInstanceId }
    ::= { cfprEtherServerIntFIoFsmStageTable 1 }

CfprEtherServerIntFIoFsmStageEntry ::= SEQUENCE {
    cfprEtherServerIntFIoFsmStageInstanceId                          CfprManagedObjectId,
    cfprEtherServerIntFIoFsmStageDn                                  CfprManagedObjectDn,
    cfprEtherServerIntFIoFsmStageRn                                  SnmpAdminString,
    cfprEtherServerIntFIoFsmStageDescrData                           SnmpAdminString,
    cfprEtherServerIntFIoFsmStageLastUpdateTime                      DateAndTime,
    cfprEtherServerIntFIoFsmStageName                                CfprEtherServerIntFIoFsmStageName,
    cfprEtherServerIntFIoFsmStageOrder                               Gauge32,
    cfprEtherServerIntFIoFsmStageRetry                               Gauge32,
    cfprEtherServerIntFIoFsmStageStageStatus                         CfprFsmFsmStageStatus
}

cfprEtherServerIntFIoFsmStageInstanceId OBJECT-TYPE
    SYNTAX       CfprManagedObjectId
    MAX-ACCESS   not-accessible
    STATUS       current
    DESCRIPTION
        "Instance identifier of the managed object."
    ::= { cfprEtherServerIntFIoFsmStageEntry 1 }

cfprEtherServerIntFIoFsmStageDn OBJECT-TYPE
    SYNTAX       CfprManagedObjectDn
    MAX-ACCESS   read-only
    STATUS       current
    DESCRIPTION
        "Cisco Firepower ether:ServerIntFIoFsmStage:dn
        managed object property"
    ::= { cfprEtherServerIntFIoFsmStageEntry 2 }

cfprEtherServerIntFIoFsmStageRn OBJECT-TYPE
    SYNTAX       SnmpAdminString
    MAX-ACCESS   read-only
    STATUS       current
    DESCRIPTION
        "Cisco Firepower ether:ServerIntFIoFsmStage:rn
        managed object property"
    ::= { cfprEtherServerIntFIoFsmStageEntry 3 }

cfprEtherServerIntFIoFsmStageDescrData OBJECT-TYPE
    SYNTAX       SnmpAdminString
    MAX-ACCESS   read-only
    STATUS       current
    DESCRIPTION
        "Cisco Firepower ether:ServerIntFIoFsmStage:descr
        managed object property"
    ::= { cfprEtherServerIntFIoFsmStageEntry 4 }

cfprEtherServerIntFIoFsmStageLastUpdateTime OBJECT-TYPE
    SYNTAX       DateAndTime
    MAX-ACCESS   read-only
    STATUS       current
    DESCRIPTION
        "Cisco Firepower ether:ServerIntFIoFsmStage:lastUpdateTime
        managed object property"
    ::= { cfprEtherServerIntFIoFsmStageEntry 5 }

cfprEtherServerIntFIoFsmStageName OBJECT-TYPE
    SYNTAX       CfprEtherServerIntFIoFsmStageName
    MAX-ACCESS   read-only
    STATUS       current
    DESCRIPTION
        "Cisco Firepower ether:ServerIntFIoFsmStage:name
        managed object property"
    ::= { cfprEtherServerIntFIoFsmStageEntry 6 }

cfprEtherServerIntFIoFsmStageOrder OBJECT-TYPE
    SYNTAX       Gauge32
    MAX-ACCESS   read-only
    STATUS       current
    DESCRIPTION
        "Cisco Firepower ether:ServerIntFIoFsmStage:order
        managed object property"
    ::= { cfprEtherServerIntFIoFsmStageEntry 7 }

cfprEtherServerIntFIoFsmStageRetry OBJECT-TYPE
    SYNTAX       Gauge32
    MAX-ACCESS   read-only
    STATUS       current
    DESCRIPTION
        "Cisco Firepower ether:ServerIntFIoFsmStage:retry
        managed object property"
    ::= { cfprEtherServerIntFIoFsmStageEntry 8 }

cfprEtherServerIntFIoFsmStageStageStatus OBJECT-TYPE
    SYNTAX       CfprFsmFsmStageStatus
    MAX-ACCESS   read-only
    STATUS       current
    DESCRIPTION
        "Cisco Firepower ether:ServerIntFIoFsmStage:stageStatus
        managed object property"
    ::= { cfprEtherServerIntFIoFsmStageEntry 9 }

cfprEtherServerIntFIoFsmTaskTable OBJECT-TYPE
    SYNTAX           SEQUENCE OF CfprEtherServerIntFIoFsmTaskEntry
    MAX-ACCESS       not-accessible
    STATUS           current
    DESCRIPTION
        "Cisco Firepower ether:ServerIntFIoFsmTask managed object table"
    ::= { cfprEtherObjects 23 }

cfprEtherServerIntFIoFsmTaskEntry OBJECT-TYPE
    SYNTAX           CfprEtherServerIntFIoFsmTaskEntry
    MAX-ACCESS       not-accessible
    STATUS           current
    DESCRIPTION
        "Entry for the cfprEtherServerIntFIoFsmTaskTable table."
    INDEX { cfprEtherServerIntFIoFsmTaskInstanceId }
    ::= { cfprEtherServerIntFIoFsmTaskTable 1 }

CfprEtherServerIntFIoFsmTaskEntry ::= SEQUENCE {
    cfprEtherServerIntFIoFsmTaskInstanceId                           CfprManagedObjectId,
    cfprEtherServerIntFIoFsmTaskDn                                   CfprManagedObjectDn,
    cfprEtherServerIntFIoFsmTaskRn                                   SnmpAdminString,
    cfprEtherServerIntFIoFsmTaskCompletion                           CfprFsmCompletion,
    cfprEtherServerIntFIoFsmTaskFlags                                CfprFsmFlags,
    cfprEtherServerIntFIoFsmTaskItem                                 CfprEtherServerIntFIoFsmTaskItem,
    cfprEtherServerIntFIoFsmTaskSeqId                                Gauge32
}

cfprEtherServerIntFIoFsmTaskInstanceId OBJECT-TYPE
    SYNTAX       CfprManagedObjectId
    MAX-ACCESS   not-accessible
    STATUS       current
    DESCRIPTION
        "Instance identifier of the managed object."
    ::= { cfprEtherServerIntFIoFsmTaskEntry 1 }

cfprEtherServerIntFIoFsmTaskDn OBJECT-TYPE
    SYNTAX       CfprManagedObjectDn
    MAX-ACCESS   read-only
    STATUS       current
    DESCRIPTION
        "Cisco Firepower ether:ServerIntFIoFsmTask:dn managed
        object property"
    ::= { cfprEtherServerIntFIoFsmTaskEntry 2 }

cfprEtherServerIntFIoFsmTaskRn OBJECT-TYPE
    SYNTAX       SnmpAdminString
    MAX-ACCESS   read-only
    STATUS       current
    DESCRIPTION
        "Cisco Firepower ether:ServerIntFIoFsmTask:rn managed
        object property"
    ::= { cfprEtherServerIntFIoFsmTaskEntry 3 }

cfprEtherServerIntFIoFsmTaskCompletion OBJECT-TYPE
    SYNTAX       CfprFsmCompletion
    MAX-ACCESS   read-only
    STATUS       current
    DESCRIPTION
        "Cisco Firepower ether:ServerIntFIoFsmTask:completion
        managed object property"
    ::= { cfprEtherServerIntFIoFsmTaskEntry 4 }

cfprEtherServerIntFIoFsmTaskFlags OBJECT-TYPE
    SYNTAX       CfprFsmFlags
    MAX-ACCESS   read-only
    STATUS       current
    DESCRIPTION
        "Cisco Firepower ether:ServerIntFIoFsmTask:flags
        managed object property"
    ::= { cfprEtherServerIntFIoFsmTaskEntry 5 }

cfprEtherServerIntFIoFsmTaskItem OBJECT-TYPE
    SYNTAX       CfprEtherServerIntFIoFsmTaskItem
    MAX-ACCESS   read-only
    STATUS       current
    DESCRIPTION
        "Cisco Firepower ether:ServerIntFIoFsmTask:item
        managed object property"
    ::= { cfprEtherServerIntFIoFsmTaskEntry 6 }

cfprEtherServerIntFIoFsmTaskSeqId OBJECT-TYPE
    SYNTAX       Gauge32
    MAX-ACCESS   read-only
    STATUS       current
    DESCRIPTION
        "Cisco Firepower ether:ServerIntFIoFsmTask:seqId
        managed object property"
    ::= { cfprEtherServerIntFIoFsmTaskEntry 7 }

cfprEtherServerIntFIoPcTable OBJECT-TYPE
    SYNTAX           SEQUENCE OF CfprEtherServerIntFIoPcEntry
    MAX-ACCESS       not-accessible
    STATUS           current
    DESCRIPTION
        "Cisco Firepower ether:ServerIntFIoPc managed object table"
    ::= { cfprEtherObjects 24 }

cfprEtherServerIntFIoPcEntry OBJECT-TYPE
    SYNTAX           CfprEtherServerIntFIoPcEntry
    MAX-ACCESS       not-accessible
    STATUS           current
    DESCRIPTION
        "Entry for the cfprEtherServerIntFIoPcTable table."
    INDEX { cfprEtherServerIntFIoPcInstanceId }
    ::= { cfprEtherServerIntFIoPcTable 1 }

CfprEtherServerIntFIoPcEntry ::= SEQUENCE {
    cfprEtherServerIntFIoPcInstanceId                                CfprManagedObjectId,
    cfprEtherServerIntFIoPcDn                                        CfprManagedObjectDn,
    cfprEtherServerIntFIoPcRn                                        SnmpAdminString,
    cfprEtherServerIntFIoPcChassisId                                 Gauge32,
    cfprEtherServerIntFIoPcEpDn                                      SnmpAdminString,
    cfprEtherServerIntFIoPcFltAggr                                   Unsigned64,
    cfprEtherServerIntFIoPcIfRole                                    CfprEtherServerIntFIoPcIfRole,
    cfprEtherServerIntFIoPcIfType                                    CfprEtherCIoEpIfType,
    cfprEtherServerIntFIoPcLocale                                    CfprEtherInternalPcLocale,
    cfprEtherServerIntFIoPcName                                      SnmpAdminString,
    cfprEtherServerIntFIoPcOperSpeed                                 CfprPortEthSpeed,
    cfprEtherServerIntFIoPcOperState                                 CfprNetworkPortOperState,
    cfprEtherServerIntFIoPcPeerDn                                    SnmpAdminString,
    cfprEtherServerIntFIoPcPortId                                    CfprEtherServerIntFIoPcPortId,
    cfprEtherServerIntFIoPcStateQual                                 SnmpAdminString,
    cfprEtherServerIntFIoPcSwitchId                                  CfprNetworkSwitchId,
    cfprEtherServerIntFIoPcTransport                                 CfprEtherServerIntFIoPcTransport,
    cfprEtherServerIntFIoPcType                                      CfprEtherServerIntFIoPcType
}

cfprEtherServerIntFIoPcInstanceId OBJECT-TYPE
    SYNTAX       CfprManagedObjectId
    MAX-ACCESS   not-accessible
    STATUS       current
    DESCRIPTION
        "Instance identifier of the managed object."
    ::= { cfprEtherServerIntFIoPcEntry 1 }

cfprEtherServerIntFIoPcDn OBJECT-TYPE
    SYNTAX       CfprManagedObjectDn
    MAX-ACCESS   read-only
    STATUS       current
    DESCRIPTION
        "Cisco Firepower ether:ServerIntFIoPc:dn managed object property"
    ::= { cfprEtherServerIntFIoPcEntry 2 }

cfprEtherServerIntFIoPcRn OBJECT-TYPE
    SYNTAX       SnmpAdminString
    MAX-ACCESS   read-only
    STATUS       current
    DESCRIPTION
        "Cisco Firepower ether:ServerIntFIoPc:rn managed object property"
    ::= { cfprEtherServerIntFIoPcEntry 3 }

cfprEtherServerIntFIoPcChassisId OBJECT-TYPE
    SYNTAX       Gauge32
    MAX-ACCESS   read-only
    STATUS       current
    DESCRIPTION
        "Cisco Firepower ether:ServerIntFIoPc:chassisId
        managed object property"
    ::= { cfprEtherServerIntFIoPcEntry 4 }

cfprEtherServerIntFIoPcEpDn OBJECT-TYPE
    SYNTAX       SnmpAdminString
    MAX-ACCESS   read-only
    STATUS       current
    DESCRIPTION
        "Cisco Firepower ether:ServerIntFIoPc:epDn managed
        object property"
    ::= { cfprEtherServerIntFIoPcEntry 5 }

cfprEtherServerIntFIoPcFltAggr OBJECT-TYPE
    SYNTAX       Unsigned64
    MAX-ACCESS   read-only
    STATUS       current
    DESCRIPTION
        "Cisco Firepower ether:ServerIntFIoPc:fltAggr managed
        object property"
    ::= { cfprEtherServerIntFIoPcEntry 6 }

cfprEtherServerIntFIoPcIfRole OBJECT-TYPE
    SYNTAX       CfprEtherServerIntFIoPcIfRole
    MAX-ACCESS   read-only
    STATUS       current
    DESCRIPTION
        "Cisco Firepower ether:ServerIntFIoPc:ifRole managed
        object property"
    ::= { cfprEtherServerIntFIoPcEntry 7 }

cfprEtherServerIntFIoPcIfType OBJECT-TYPE
    SYNTAX       CfprEtherCIoEpIfType
    MAX-ACCESS   read-only
    STATUS       current
    DESCRIPTION
        "Cisco Firepower ether:ServerIntFIoPc:ifType managed
        object property"
    ::= { cfprEtherServerIntFIoPcEntry 8 }

cfprEtherServerIntFIoPcLocale OBJECT-TYPE
    SYNTAX       CfprEtherInternalPcLocale
    MAX-ACCESS   read-only
    STATUS       current
    DESCRIPTION
        "Cisco Firepower ether:ServerIntFIoPc:locale managed
        object property"
    ::= { cfprEtherServerIntFIoPcEntry 9 }

cfprEtherServerIntFIoPcName OBJECT-TYPE
    SYNTAX       SnmpAdminString
    MAX-ACCESS   read-only
    STATUS       current
    DESCRIPTION
        "Cisco Firepower ether:ServerIntFIoPc:name managed
        object property"
    ::= { cfprEtherServerIntFIoPcEntry 10 }

cfprEtherServerIntFIoPcOperSpeed OBJECT-TYPE
    SYNTAX       CfprPortEthSpeed
    MAX-ACCESS   read-only
    STATUS       current
    DESCRIPTION
        "Cisco Firepower ether:ServerIntFIoPc:operSpeed
        managed object property"
    ::= { cfprEtherServerIntFIoPcEntry 11 }

cfprEtherServerIntFIoPcOperState OBJECT-TYPE
    SYNTAX       CfprNetworkPortOperState
    MAX-ACCESS   read-only
    STATUS       current
    DESCRIPTION
        "Cisco Firepower ether:ServerIntFIoPc:operState
        managed object property"
    ::= { cfprEtherServerIntFIoPcEntry 12 }

cfprEtherServerIntFIoPcPeerDn OBJECT-TYPE
    SYNTAX       SnmpAdminString
    MAX-ACCESS   read-only
    STATUS       current
    DESCRIPTION
        "Cisco Firepower ether:ServerIntFIoPc:peerDn managed
        object property"
    ::= { cfprEtherServerIntFIoPcEntry 13 }

cfprEtherServerIntFIoPcPortId OBJECT-TYPE
    SYNTAX       CfprEtherServerIntFIoPcPortId
    MAX-ACCESS   read-only
    STATUS       current
    DESCRIPTION
        "Cisco Firepower ether:ServerIntFIoPc:portId managed
        object property"
    ::= { cfprEtherServerIntFIoPcEntry 14 }

cfprEtherServerIntFIoPcStateQual OBJECT-TYPE
    SYNTAX       SnmpAdminString
    MAX-ACCESS   read-only
    STATUS       current
    DESCRIPTION
        "Cisco Firepower ether:ServerIntFIoPc:stateQual
        managed object property"
    ::= { cfprEtherServerIntFIoPcEntry 15 }

cfprEtherServerIntFIoPcSwitchId OBJECT-TYPE
    SYNTAX       CfprNetworkSwitchId
    MAX-ACCESS   read-only
    STATUS       current
    DESCRIPTION
        "Cisco Firepower ether:ServerIntFIoPc:switchId
        managed object property"
    ::= { cfprEtherServerIntFIoPcEntry 16 }

cfprEtherServerIntFIoPcTransport OBJECT-TYPE
    SYNTAX       CfprEtherServerIntFIoPcTransport
    MAX-ACCESS   read-only
    STATUS       current
    DESCRIPTION
        "Cisco Firepower ether:ServerIntFIoPc:transport
        managed object property"
    ::= { cfprEtherServerIntFIoPcEntry 17 }

cfprEtherServerIntFIoPcType OBJECT-TYPE
    SYNTAX       CfprEtherServerIntFIoPcType
    MAX-ACCESS   read-only
    STATUS       current
    DESCRIPTION
        "Cisco Firepower ether:ServerIntFIoPc:type managed
        object property"
    ::= { cfprEtherServerIntFIoPcEntry 18 }

cfprEtherServerIntFIoPcEpTable OBJECT-TYPE
    SYNTAX           SEQUENCE OF CfprEtherServerIntFIoPcEpEntry
    MAX-ACCESS       not-accessible
    STATUS           current
    DESCRIPTION
        "Cisco Firepower ether:ServerIntFIoPcEp managed object table"
    ::= { cfprEtherObjects 25 }

cfprEtherServerIntFIoPcEpEntry OBJECT-TYPE
    SYNTAX           CfprEtherServerIntFIoPcEpEntry
    MAX-ACCESS       not-accessible
    STATUS           current
    DESCRIPTION
        "Entry for the cfprEtherServerIntFIoPcEpTable table."
    INDEX { cfprEtherServerIntFIoPcEpInstanceId }
    ::= { cfprEtherServerIntFIoPcEpTable 1 }

CfprEtherServerIntFIoPcEpEntry ::= SEQUENCE {
    cfprEtherServerIntFIoPcEpInstanceId                              CfprManagedObjectId,
    cfprEtherServerIntFIoPcEpDnData                                  CfprManagedObjectDn,
    cfprEtherServerIntFIoPcEpRn                                      SnmpAdminString,
    cfprEtherServerIntFIoPcEpAdminState                              CfprEtherExternalEpAdminState,
    cfprEtherServerIntFIoPcEpAggrPortId                              Gauge32,
    cfprEtherServerIntFIoPcEpChassisId                               Gauge32,
    cfprEtherServerIntFIoPcEpEpDn                                    SnmpAdminString,
    cfprEtherServerIntFIoPcEpIfRole                                  CfprEtherServerIntFIoPcEpIfRole,
    cfprEtherServerIntFIoPcEpIfType                                  CfprEtherPIoEpIfType,
    cfprEtherServerIntFIoPcEpLocale                                  CfprEtherExternalEpLocale,
    cfprEtherServerIntFIoPcEpMembership                              CfprFabricMembershipStatus,
    cfprEtherServerIntFIoPcEpName                                    SnmpAdminString,
    cfprEtherServerIntFIoPcEpPeerAggrPortId                          Gauge32,
    cfprEtherServerIntFIoPcEpPeerChassisId                           Gauge32,
    cfprEtherServerIntFIoPcEpPeerDn                                  SnmpAdminString,
    cfprEtherServerIntFIoPcEpPeerPortId                              Gauge32,
    cfprEtherServerIntFIoPcEpPeerSlotId                              Gauge32,
    cfprEtherServerIntFIoPcEpPortId                                  CfprEtherServerIntFIoPcEpPortId,
    cfprEtherServerIntFIoPcEpSlotId                                  Gauge32,
    cfprEtherServerIntFIoPcEpSwitchId                                CfprNetworkSwitchId,
    cfprEtherServerIntFIoPcEpTransport                               CfprNetworkTransport,
    cfprEtherServerIntFIoPcEpType                                    CfprEtherIntFIoEpType
}

cfprEtherServerIntFIoPcEpInstanceId OBJECT-TYPE
    SYNTAX       CfprManagedObjectId
    MAX-ACCESS   not-accessible
    STATUS       current
    DESCRIPTION
        "Instance identifier of the managed object."
    ::= { cfprEtherServerIntFIoPcEpEntry 1 }

cfprEtherServerIntFIoPcEpDnData OBJECT-TYPE
    SYNTAX       CfprManagedObjectDn
    MAX-ACCESS   read-only
    STATUS       current
    DESCRIPTION
        "Cisco Firepower ether:ServerIntFIoPcEp:dn managed
        object property"
    ::= { cfprEtherServerIntFIoPcEpEntry 2 }

cfprEtherServerIntFIoPcEpRn OBJECT-TYPE
    SYNTAX       SnmpAdminString
    MAX-ACCESS   read-only
    STATUS       current
    DESCRIPTION
        "Cisco Firepower ether:ServerIntFIoPcEp:rn managed
        object property"
    ::= { cfprEtherServerIntFIoPcEpEntry 3 }

cfprEtherServerIntFIoPcEpAdminState OBJECT-TYPE
    SYNTAX       CfprEtherExternalEpAdminState
    MAX-ACCESS   read-only
    STATUS       current
    DESCRIPTION
        "Cisco Firepower ether:ServerIntFIoPcEp:adminState
        managed object property"
    ::= { cfprEtherServerIntFIoPcEpEntry 4 }

cfprEtherServerIntFIoPcEpAggrPortId OBJECT-TYPE
    SYNTAX       Gauge32
    MAX-ACCESS   read-only
    STATUS       current
    DESCRIPTION
        "Cisco Firepower ether:ServerIntFIoPcEp:aggrPortId
        managed object property"
    ::= { cfprEtherServerIntFIoPcEpEntry 5 }

cfprEtherServerIntFIoPcEpChassisId OBJECT-TYPE
    SYNTAX       Gauge32
    MAX-ACCESS   read-only
    STATUS       current
    DESCRIPTION
        "Cisco Firepower ether:ServerIntFIoPcEp:chassisId
        managed object property"
    ::= { cfprEtherServerIntFIoPcEpEntry 6 }

cfprEtherServerIntFIoPcEpEpDn OBJECT-TYPE
    SYNTAX       SnmpAdminString
    MAX-ACCESS   read-only
    STATUS       current
    DESCRIPTION
        "Cisco Firepower ether:ServerIntFIoPcEp:epDn managed
        object property"
    ::= { cfprEtherServerIntFIoPcEpEntry 7 }

cfprEtherServerIntFIoPcEpIfRole OBJECT-TYPE
    SYNTAX       CfprEtherServerIntFIoPcEpIfRole
    MAX-ACCESS   read-only
    STATUS       current
    DESCRIPTION
        "Cisco Firepower ether:ServerIntFIoPcEp:ifRole
        managed object property"
    ::= { cfprEtherServerIntFIoPcEpEntry 8 }

cfprEtherServerIntFIoPcEpIfType OBJECT-TYPE
    SYNTAX       CfprEtherPIoEpIfType
    MAX-ACCESS   read-only
    STATUS       current
    DESCRIPTION
        "Cisco Firepower ether:ServerIntFIoPcEp:ifType
        managed object property"
    ::= { cfprEtherServerIntFIoPcEpEntry 9 }

cfprEtherServerIntFIoPcEpLocale OBJECT-TYPE
    SYNTAX       CfprEtherExternalEpLocale
    MAX-ACCESS   read-only
    STATUS       current
    DESCRIPTION
        "Cisco Firepower ether:ServerIntFIoPcEp:locale
        managed object property"
    ::= { cfprEtherServerIntFIoPcEpEntry 10 }

cfprEtherServerIntFIoPcEpMembership OBJECT-TYPE
    SYNTAX       CfprFabricMembershipStatus
    MAX-ACCESS   read-only
    STATUS       current
    DESCRIPTION
        "Cisco Firepower ether:ServerIntFIoPcEp:membership
        managed object property"
    ::= { cfprEtherServerIntFIoPcEpEntry 11 }

cfprEtherServerIntFIoPcEpName OBJECT-TYPE
    SYNTAX       SnmpAdminString
    MAX-ACCESS   read-only
    STATUS       current
    DESCRIPTION
        "Cisco Firepower ether:ServerIntFIoPcEp:name managed
        object property"
    ::= { cfprEtherServerIntFIoPcEpEntry 12 }

cfprEtherServerIntFIoPcEpPeerAggrPortId OBJECT-TYPE
    SYNTAX       Gauge32
    MAX-ACCESS   read-only
    STATUS       current
    DESCRIPTION
        "Cisco Firepower ether:ServerIntFIoPcEp:peerAggrPortId
        managed object property"
    ::= { cfprEtherServerIntFIoPcEpEntry 13 }

cfprEtherServerIntFIoPcEpPeerChassisId OBJECT-TYPE
    SYNTAX       Gauge32
    MAX-ACCESS   read-only
    STATUS       current
    DESCRIPTION
        "Cisco Firepower ether:ServerIntFIoPcEp:peerChassisId
        managed object property"
    ::= { cfprEtherServerIntFIoPcEpEntry 14 }

cfprEtherServerIntFIoPcEpPeerDn OBJECT-TYPE
    SYNTAX       SnmpAdminString
    MAX-ACCESS   read-only
    STATUS       current
    DESCRIPTION
        "Cisco Firepower ether:ServerIntFIoPcEp:peerDn
        managed object property"
    ::= { cfprEtherServerIntFIoPcEpEntry 15 }

cfprEtherServerIntFIoPcEpPeerPortId OBJECT-TYPE
    SYNTAX       Gauge32
    MAX-ACCESS   read-only
    STATUS       current
    DESCRIPTION
        "Cisco Firepower ether:ServerIntFIoPcEp:peerPortId
        managed object property"
    ::= { cfprEtherServerIntFIoPcEpEntry 16 }

cfprEtherServerIntFIoPcEpPeerSlotId OBJECT-TYPE
    SYNTAX       Gauge32
    MAX-ACCESS   read-only
    STATUS       current
    DESCRIPTION
        "Cisco Firepower ether:ServerIntFIoPcEp:peerSlotId
        managed object property"
    ::= { cfprEtherServerIntFIoPcEpEntry 17 }

cfprEtherServerIntFIoPcEpPortId OBJECT-TYPE
    SYNTAX       CfprEtherServerIntFIoPcEpPortId
    MAX-ACCESS   read-only
    STATUS       current
    DESCRIPTION
        "Cisco Firepower ether:ServerIntFIoPcEp:portId
        managed object property"
    ::= { cfprEtherServerIntFIoPcEpEntry 18 }

cfprEtherServerIntFIoPcEpSlotId OBJECT-TYPE
    SYNTAX       Gauge32
    MAX-ACCESS   read-only
    STATUS       current
    DESCRIPTION
        "Cisco Firepower ether:ServerIntFIoPcEp:slotId
        managed object property"
    ::= { cfprEtherServerIntFIoPcEpEntry 19 }

cfprEtherServerIntFIoPcEpSwitchId OBJECT-TYPE
    SYNTAX       CfprNetworkSwitchId
    MAX-ACCESS   read-only
    STATUS       current
    DESCRIPTION
        "Cisco Firepower ether:ServerIntFIoPcEp:switchId
        managed object property"
    ::= { cfprEtherServerIntFIoPcEpEntry 20 }

cfprEtherServerIntFIoPcEpTransport OBJECT-TYPE
    SYNTAX       CfprNetworkTransport
    MAX-ACCESS   read-only
    STATUS       current
    DESCRIPTION
        "Cisco Firepower ether:ServerIntFIoPcEp:transport
        managed object property"
    ::= { cfprEtherServerIntFIoPcEpEntry 21 }

cfprEtherServerIntFIoPcEpType OBJECT-TYPE
    SYNTAX       CfprEtherIntFIoEpType
    MAX-ACCESS   read-only
    STATUS       current
    DESCRIPTION
        "Cisco Firepower ether:ServerIntFIoPcEp:type managed
        object property"
    ::= { cfprEtherServerIntFIoPcEpEntry 22 }

cfprEtherSwIfConfigTable OBJECT-TYPE
    SYNTAX           SEQUENCE OF CfprEtherSwIfConfigEntry
    MAX-ACCESS       not-accessible
    STATUS           current
    DESCRIPTION
        "Cisco Firepower ether:SwIfConfig managed object table"
    ::= { cfprEtherObjects 26 }

cfprEtherSwIfConfigEntry OBJECT-TYPE
    SYNTAX           CfprEtherSwIfConfigEntry
    MAX-ACCESS       not-accessible
    STATUS           current
    DESCRIPTION
        "Entry for the cfprEtherSwIfConfigTable table."
    INDEX { cfprEtherSwIfConfigInstanceId }
    ::= { cfprEtherSwIfConfigTable 1 }

CfprEtherSwIfConfigEntry ::= SEQUENCE {
    cfprEtherSwIfConfigInstanceId                                    CfprManagedObjectId,
    cfprEtherSwIfConfigDn                                            CfprManagedObjectDn,
    cfprEtherSwIfConfigRn                                            SnmpAdminString
}

cfprEtherSwIfConfigInstanceId OBJECT-TYPE
    SYNTAX       CfprManagedObjectId
    MAX-ACCESS   not-accessible
    STATUS       current
    DESCRIPTION
        "Instance identifier of the managed object."
    ::= { cfprEtherSwIfConfigEntry 1 }

cfprEtherSwIfConfigDn OBJECT-TYPE
    SYNTAX       CfprManagedObjectDn
    MAX-ACCESS   read-only
    STATUS       current
    DESCRIPTION
        "Cisco Firepower ether:SwIfConfig:dn managed object property"
    ::= { cfprEtherSwIfConfigEntry 2 }

cfprEtherSwIfConfigRn OBJECT-TYPE
    SYNTAX       SnmpAdminString
    MAX-ACCESS   read-only
    STATUS       current
    DESCRIPTION
        "Cisco Firepower ether:SwIfConfig:rn managed object property"
    ::= { cfprEtherSwIfConfigEntry 3 }

cfprEtherSwitchIntFIoTable OBJECT-TYPE
    SYNTAX           SEQUENCE OF CfprEtherSwitchIntFIoEntry
    MAX-ACCESS       not-accessible
    STATUS           current
    DESCRIPTION
        "Cisco Firepower ether:SwitchIntFIo managed object table"
    ::= { cfprEtherObjects 27 }

cfprEtherSwitchIntFIoEntry OBJECT-TYPE
    SYNTAX           CfprEtherSwitchIntFIoEntry
    MAX-ACCESS       not-accessible
    STATUS           current
    DESCRIPTION
        "Entry for the cfprEtherSwitchIntFIoTable table."
    INDEX { cfprEtherSwitchIntFIoInstanceId }
    ::= { cfprEtherSwitchIntFIoTable 1 }

CfprEtherSwitchIntFIoEntry ::= SEQUENCE {
    cfprEtherSwitchIntFIoInstanceId                                  CfprManagedObjectId,
    cfprEtherSwitchIntFIoDn                                          CfprManagedObjectDn,
    cfprEtherSwitchIntFIoRn                                          SnmpAdminString,
    cfprEtherSwitchIntFIoAck                                         CfprEtherSwitchIntFIoAck,
    cfprEtherSwitchIntFIoAdminState                                  CfprFabricAdminState,
    cfprEtherSwitchIntFIoAggrPortId                                  Gauge32,
    cfprEtherSwitchIntFIoChassisId                                   Gauge32,
    cfprEtherSwitchIntFIoDelFeTs                                     Unsigned64,
    cfprEtherSwitchIntFIoDiscovery                                   CfprEtherSatelliteConnectionDisc,
    cfprEtherSwitchIntFIoEncap                                       CfprPortEncap,
    cfprEtherSwitchIntFIoEpDn                                        SnmpAdminString,
    cfprEtherSwitchIntFIoFltAggr                                     Unsigned64,
    cfprEtherSwitchIntFIoIfRole                                      CfprEtherSwitchIntFIoIfRole,
    cfprEtherSwitchIntFIoIfType                                      CfprNetworkPhysEpIfType,
    cfprEtherSwitchIntFIoLocale                                      CfprEtherSwitchIntFIoLocale,
    cfprEtherSwitchIntFIoMode                                        CfprPortMode,
    cfprEtherSwitchIntFIoModel                                       SnmpAdminString,
    cfprEtherSwitchIntFIoName                                        SnmpAdminString,
    cfprEtherSwitchIntFIoNewFeTs                                     Unsigned64,
    cfprEtherSwitchIntFIoOperState                                   CfprNetworkPortOperState,
    cfprEtherSwitchIntFIoPeerAggrPortId                              Gauge32,
    cfprEtherSwitchIntFIoPeerChassisId                               Gauge32,
    cfprEtherSwitchIntFIoPeerDn                                      SnmpAdminString,
    cfprEtherSwitchIntFIoPeerPortId                                  Gauge32,
    cfprEtherSwitchIntFIoPeerSlotId                                  Gauge32,
    cfprEtherSwitchIntFIoPortId                                      Gauge32,
    cfprEtherSwitchIntFIoRevision                                    SnmpAdminString,
    cfprEtherSwitchIntFIoSerial                                      SnmpAdminString,
    cfprEtherSwitchIntFIoSlotId                                      Gauge32,
    cfprEtherSwitchIntFIoStateQual                                   SnmpAdminString,
    cfprEtherSwitchIntFIoSwitchId                                    CfprNetworkSwitchId,
    cfprEtherSwitchIntFIoTransport                                   CfprEtherSwitchIntFIoTransport,
    cfprEtherSwitchIntFIoTs                                          DateAndTime,
    cfprEtherSwitchIntFIoType                                        CfprEtherSwitchIntFIoType,
    cfprEtherSwitchIntFIoVendor                                      SnmpAdminString,
    cfprEtherSwitchIntFIoXcvrType                                    CfprEquipmentXcvrType
}

cfprEtherSwitchIntFIoInstanceId OBJECT-TYPE
    SYNTAX       CfprManagedObjectId
    MAX-ACCESS   not-accessible
    STATUS       current
    DESCRIPTION
        "Instance identifier of the managed object."
    ::= { cfprEtherSwitchIntFIoEntry 1 }

cfprEtherSwitchIntFIoDn OBJECT-TYPE
    SYNTAX       CfprManagedObjectDn
    MAX-ACCESS   read-only
    STATUS       current
    DESCRIPTION
        "Cisco Firepower ether:SwitchIntFIo:dn managed object property"
    ::= { cfprEtherSwitchIntFIoEntry 2 }

cfprEtherSwitchIntFIoRn OBJECT-TYPE
    SYNTAX       SnmpAdminString
    MAX-ACCESS   read-only
    STATUS       current
    DESCRIPTION
        "Cisco Firepower ether:SwitchIntFIo:rn managed object property"
    ::= { cfprEtherSwitchIntFIoEntry 3 }

cfprEtherSwitchIntFIoAck OBJECT-TYPE
    SYNTAX       CfprEtherSwitchIntFIoAck
    MAX-ACCESS   read-only
    STATUS       current
    DESCRIPTION
        "Cisco Firepower ether:SwitchIntFIo:ack managed object property"
    ::= { cfprEtherSwitchIntFIoEntry 4 }

cfprEtherSwitchIntFIoAdminState OBJECT-TYPE
    SYNTAX       CfprFabricAdminState
    MAX-ACCESS   read-only
    STATUS       current
    DESCRIPTION
        "Cisco Firepower ether:SwitchIntFIo:adminState
        managed object property"
    ::= { cfprEtherSwitchIntFIoEntry 5 }

cfprEtherSwitchIntFIoAggrPortId OBJECT-TYPE
    SYNTAX       Gauge32
    MAX-ACCESS   read-only
    STATUS       current
    DESCRIPTION
        "Cisco Firepower ether:SwitchIntFIo:aggrPortId
        managed object property"
    ::= { cfprEtherSwitchIntFIoEntry 6 }

cfprEtherSwitchIntFIoChassisId OBJECT-TYPE
    SYNTAX       Gauge32
    MAX-ACCESS   read-only
    STATUS       current
    DESCRIPTION
        "Cisco Firepower ether:SwitchIntFIo:chassisId managed
        object property"
    ::= { cfprEtherSwitchIntFIoEntry 7 }

cfprEtherSwitchIntFIoDelFeTs OBJECT-TYPE
    SYNTAX       Unsigned64
    MAX-ACCESS   read-only
    STATUS       current
    DESCRIPTION
        "Cisco Firepower ether:SwitchIntFIo:delFeTs managed
        object property"
    ::= { cfprEtherSwitchIntFIoEntry 8 }

cfprEtherSwitchIntFIoDiscovery OBJECT-TYPE
    SYNTAX       CfprEtherSatelliteConnectionDisc
    MAX-ACCESS   read-only
    STATUS       current
    DESCRIPTION
        "Cisco Firepower ether:SwitchIntFIo:discovery managed
        object property"
    ::= { cfprEtherSwitchIntFIoEntry 9 }

cfprEtherSwitchIntFIoEncap OBJECT-TYPE
    SYNTAX       CfprPortEncap
    MAX-ACCESS   read-only
    STATUS       current
    DESCRIPTION
        "Cisco Firepower ether:SwitchIntFIo:encap managed object property"
    ::= { cfprEtherSwitchIntFIoEntry 10 }

cfprEtherSwitchIntFIoEpDn OBJECT-TYPE
    SYNTAX       SnmpAdminString
    MAX-ACCESS   read-only
    STATUS       current
    DESCRIPTION
        "Cisco Firepower ether:SwitchIntFIo:epDn managed object property"
    ::= { cfprEtherSwitchIntFIoEntry 11 }

cfprEtherSwitchIntFIoFltAggr OBJECT-TYPE
    SYNTAX       Unsigned64
    MAX-ACCESS   read-only
    STATUS       current
    DESCRIPTION
        "Cisco Firepower ether:SwitchIntFIo:fltAggr managed
        object property"
    ::= { cfprEtherSwitchIntFIoEntry 12 }

cfprEtherSwitchIntFIoIfRole OBJECT-TYPE
    SYNTAX       CfprEtherSwitchIntFIoIfRole
    MAX-ACCESS   read-only
    STATUS       current
    DESCRIPTION
        "Cisco Firepower ether:SwitchIntFIo:ifRole managed
        object property"
    ::= { cfprEtherSwitchIntFIoEntry 13 }

cfprEtherSwitchIntFIoIfType OBJECT-TYPE
    SYNTAX       CfprNetworkPhysEpIfType
    MAX-ACCESS   read-only
    STATUS       current
    DESCRIPTION
        "Cisco Firepower ether:SwitchIntFIo:ifType managed
        object property"
    ::= { cfprEtherSwitchIntFIoEntry 14 }

cfprEtherSwitchIntFIoLocale OBJECT-TYPE
    SYNTAX       CfprEtherSwitchIntFIoLocale
    MAX-ACCESS   read-only
    STATUS       current
    DESCRIPTION
        "Cisco Firepower ether:SwitchIntFIo:locale managed
        object property"
    ::= { cfprEtherSwitchIntFIoEntry 15 }

cfprEtherSwitchIntFIoMode OBJECT-TYPE
    SYNTAX       CfprPortMode
    MAX-ACCESS   read-only
    STATUS       current
    DESCRIPTION
        "Cisco Firepower ether:SwitchIntFIo:mode managed object property"
    ::= { cfprEtherSwitchIntFIoEntry 16 }

cfprEtherSwitchIntFIoModel OBJECT-TYPE
    SYNTAX       SnmpAdminString
    MAX-ACCESS   read-only
    STATUS       current
    DESCRIPTION
        "Cisco Firepower ether:SwitchIntFIo:model managed object property"
    ::= { cfprEtherSwitchIntFIoEntry 17 }

cfprEtherSwitchIntFIoName OBJECT-TYPE
    SYNTAX       SnmpAdminString
    MAX-ACCESS   read-only
    STATUS       current
    DESCRIPTION
        "Cisco Firepower ether:SwitchIntFIo:name managed object property"
    ::= { cfprEtherSwitchIntFIoEntry 18 }

cfprEtherSwitchIntFIoNewFeTs OBJECT-TYPE
    SYNTAX       Unsigned64
    MAX-ACCESS   read-only
    STATUS       current
    DESCRIPTION
        "Cisco Firepower ether:SwitchIntFIo:newFeTs managed
        object property"
    ::= { cfprEtherSwitchIntFIoEntry 19 }

cfprEtherSwitchIntFIoOperState OBJECT-TYPE
    SYNTAX       CfprNetworkPortOperState
    MAX-ACCESS   read-only
    STATUS       current
    DESCRIPTION
        "Cisco Firepower ether:SwitchIntFIo:operState managed
        object property"
    ::= { cfprEtherSwitchIntFIoEntry 20 }

cfprEtherSwitchIntFIoPeerAggrPortId OBJECT-TYPE
    SYNTAX       Gauge32
    MAX-ACCESS   read-only
    STATUS       current
    DESCRIPTION
        "Cisco Firepower ether:SwitchIntFIo:peerAggrPortId
        managed object property"
    ::= { cfprEtherSwitchIntFIoEntry 21 }

cfprEtherSwitchIntFIoPeerChassisId OBJECT-TYPE
    SYNTAX       Gauge32
    MAX-ACCESS   read-only
    STATUS       current
    DESCRIPTION
        "Cisco Firepower ether:SwitchIntFIo:peerChassisId
        managed object property"
    ::= { cfprEtherSwitchIntFIoEntry 22 }

cfprEtherSwitchIntFIoPeerDn OBJECT-TYPE
    SYNTAX       SnmpAdminString
    MAX-ACCESS   read-only
    STATUS       current
    DESCRIPTION
        "Cisco Firepower ether:SwitchIntFIo:peerDn managed
        object property"
    ::= { cfprEtherSwitchIntFIoEntry 23 }

cfprEtherSwitchIntFIoPeerPortId OBJECT-TYPE
    SYNTAX       Gauge32
    MAX-ACCESS   read-only
    STATUS       current
    DESCRIPTION
        "Cisco Firepower ether:SwitchIntFIo:peerPortId
        managed object property"
    ::= { cfprEtherSwitchIntFIoEntry 24 }

cfprEtherSwitchIntFIoPeerSlotId OBJECT-TYPE
    SYNTAX       Gauge32
    MAX-ACCESS   read-only
    STATUS       current
    DESCRIPTION
        "Cisco Firepower ether:SwitchIntFIo:peerSlotId
        managed object property"
    ::= { cfprEtherSwitchIntFIoEntry 25 }

cfprEtherSwitchIntFIoPortId OBJECT-TYPE
    SYNTAX       Gauge32
    MAX-ACCESS   read-only
    STATUS       current
    DESCRIPTION
        "Cisco Firepower ether:SwitchIntFIo:portId managed
        object property"
    ::= { cfprEtherSwitchIntFIoEntry 26 }

cfprEtherSwitchIntFIoRevision OBJECT-TYPE
    SYNTAX       SnmpAdminString
    MAX-ACCESS   read-only
    STATUS       current
    DESCRIPTION
        "Cisco Firepower ether:SwitchIntFIo:revision managed
        object property"
    ::= { cfprEtherSwitchIntFIoEntry 27 }

cfprEtherSwitchIntFIoSerial OBJECT-TYPE
    SYNTAX       SnmpAdminString
    MAX-ACCESS   read-only
    STATUS       current
    DESCRIPTION
        "Cisco Firepower ether:SwitchIntFIo:serial managed
        object property"
    ::= { cfprEtherSwitchIntFIoEntry 28 }

cfprEtherSwitchIntFIoSlotId OBJECT-TYPE
    SYNTAX       Gauge32
    MAX-ACCESS   read-only
    STATUS       current
    DESCRIPTION
        "Cisco Firepower ether:SwitchIntFIo:slotId managed
        object property"
    ::= { cfprEtherSwitchIntFIoEntry 29 }

cfprEtherSwitchIntFIoStateQual OBJECT-TYPE
    SYNTAX       SnmpAdminString
    MAX-ACCESS   read-only
    STATUS       current
    DESCRIPTION
        "Cisco Firepower ether:SwitchIntFIo:stateQual managed
        object property"
    ::= { cfprEtherSwitchIntFIoEntry 30 }

cfprEtherSwitchIntFIoSwitchId OBJECT-TYPE
    SYNTAX       CfprNetworkSwitchId
    MAX-ACCESS   read-only
    STATUS       current
    DESCRIPTION
        "Cisco Firepower ether:SwitchIntFIo:switchId managed
        object property"
    ::= { cfprEtherSwitchIntFIoEntry 31 }

cfprEtherSwitchIntFIoTransport OBJECT-TYPE
    SYNTAX       CfprEtherSwitchIntFIoTransport
    MAX-ACCESS   read-only
    STATUS       current
    DESCRIPTION
        "Cisco Firepower ether:SwitchIntFIo:transport managed
        object property"
    ::= { cfprEtherSwitchIntFIoEntry 32 }

cfprEtherSwitchIntFIoTs OBJECT-TYPE
    SYNTAX       DateAndTime
    MAX-ACCESS   read-only
    STATUS       current
    DESCRIPTION
        "Cisco Firepower ether:SwitchIntFIo:ts managed object property"
    ::= { cfprEtherSwitchIntFIoEntry 33 }

cfprEtherSwitchIntFIoType OBJECT-TYPE
    SYNTAX       CfprEtherSwitchIntFIoType
    MAX-ACCESS   read-only
    STATUS       current
    DESCRIPTION
        "Cisco Firepower ether:SwitchIntFIo:type managed object property"
    ::= { cfprEtherSwitchIntFIoEntry 34 }

cfprEtherSwitchIntFIoVendor OBJECT-TYPE
    SYNTAX       SnmpAdminString
    MAX-ACCESS   read-only
    STATUS       current
    DESCRIPTION
        "Cisco Firepower ether:SwitchIntFIo:vendor managed
        object property"
    ::= { cfprEtherSwitchIntFIoEntry 35 }

cfprEtherSwitchIntFIoXcvrType OBJECT-TYPE
    SYNTAX       CfprEquipmentXcvrType
    MAX-ACCESS   read-only
    STATUS       current
    DESCRIPTION
        "Cisco Firepower ether:SwitchIntFIo:xcvrType managed
        object property"
    ::= { cfprEtherSwitchIntFIoEntry 36 }

cfprEtherSwitchIntFIoPcTable OBJECT-TYPE
    SYNTAX           SEQUENCE OF CfprEtherSwitchIntFIoPcEntry
    MAX-ACCESS       not-accessible
    STATUS           current
    DESCRIPTION
        "Cisco Firepower ether:SwitchIntFIoPc managed object table"
    ::= { cfprEtherObjects 28 }

cfprEtherSwitchIntFIoPcEntry OBJECT-TYPE
    SYNTAX           CfprEtherSwitchIntFIoPcEntry
    MAX-ACCESS       not-accessible
    STATUS           current
    DESCRIPTION
        "Entry for the cfprEtherSwitchIntFIoPcTable table."
    INDEX { cfprEtherSwitchIntFIoPcInstanceId }
    ::= { cfprEtherSwitchIntFIoPcTable 1 }

CfprEtherSwitchIntFIoPcEntry ::= SEQUENCE {
    cfprEtherSwitchIntFIoPcInstanceId                                CfprManagedObjectId,
    cfprEtherSwitchIntFIoPcDn                                        CfprManagedObjectDn,
    cfprEtherSwitchIntFIoPcRn                                        SnmpAdminString,
    cfprEtherSwitchIntFIoPcAdminState                                CfprEtherExternalPcAdminState,
    cfprEtherSwitchIntFIoPcChassisId                                 Gauge32,
    cfprEtherSwitchIntFIoPcEpDn                                      SnmpAdminString,
    cfprEtherSwitchIntFIoPcFltAggr                                   Unsigned64,
    cfprEtherSwitchIntFIoPcIfRole                                    CfprEtherSwitchIntFIoPcIfRole,
    cfprEtherSwitchIntFIoPcIfType                                    CfprEtherCIoEpIfType,
    cfprEtherSwitchIntFIoPcLocale                                    CfprEtherExternalPcLocale,
    cfprEtherSwitchIntFIoPcName                                      SnmpAdminString,
    cfprEtherSwitchIntFIoPcOperSpeed                                 CfprPortEthSpeed,
    cfprEtherSwitchIntFIoPcOperState                                 CfprNetworkPortOperState,
    cfprEtherSwitchIntFIoPcPeerDn                                    SnmpAdminString,
    cfprEtherSwitchIntFIoPcPortId                                    CfprEtherSwitchIntFIoPcPortId,
    cfprEtherSwitchIntFIoPcStateQual                                 SnmpAdminString,
    cfprEtherSwitchIntFIoPcSwitchId                                  CfprNetworkSwitchId,
    cfprEtherSwitchIntFIoPcTransport                                 CfprEtherSwitchIntFIoPcTransport,
    cfprEtherSwitchIntFIoPcType                                      CfprEtherSwitchIntFIoPcType
}

cfprEtherSwitchIntFIoPcInstanceId OBJECT-TYPE
    SYNTAX       CfprManagedObjectId
    MAX-ACCESS   not-accessible
    STATUS       current
    DESCRIPTION
        "Instance identifier of the managed object."
    ::= { cfprEtherSwitchIntFIoPcEntry 1 }

cfprEtherSwitchIntFIoPcDn OBJECT-TYPE
    SYNTAX       CfprManagedObjectDn
    MAX-ACCESS   read-only
    STATUS       current
    DESCRIPTION
        "Cisco Firepower ether:SwitchIntFIoPc:dn managed object property"
    ::= { cfprEtherSwitchIntFIoPcEntry 2 }

cfprEtherSwitchIntFIoPcRn OBJECT-TYPE
    SYNTAX       SnmpAdminString
    MAX-ACCESS   read-only
    STATUS       current
    DESCRIPTION
        "Cisco Firepower ether:SwitchIntFIoPc:rn managed object property"
    ::= { cfprEtherSwitchIntFIoPcEntry 3 }

cfprEtherSwitchIntFIoPcAdminState OBJECT-TYPE
    SYNTAX       CfprEtherExternalPcAdminState
    MAX-ACCESS   read-only
    STATUS       current
    DESCRIPTION
        "Cisco Firepower ether:SwitchIntFIoPc:adminState
        managed object property"
    ::= { cfprEtherSwitchIntFIoPcEntry 4 }

cfprEtherSwitchIntFIoPcChassisId OBJECT-TYPE
    SYNTAX       Gauge32
    MAX-ACCESS   read-only
    STATUS       current
    DESCRIPTION
        "Cisco Firepower ether:SwitchIntFIoPc:chassisId
        managed object property"
    ::= { cfprEtherSwitchIntFIoPcEntry 5 }

cfprEtherSwitchIntFIoPcEpDn OBJECT-TYPE
    SYNTAX       SnmpAdminString
    MAX-ACCESS   read-only
    STATUS       current
    DESCRIPTION
        "Cisco Firepower ether:SwitchIntFIoPc:epDn managed
        object property"
    ::= { cfprEtherSwitchIntFIoPcEntry 6 }

cfprEtherSwitchIntFIoPcFltAggr OBJECT-TYPE
    SYNTAX       Unsigned64
    MAX-ACCESS   read-only
    STATUS       current
    DESCRIPTION
        "Cisco Firepower ether:SwitchIntFIoPc:fltAggr managed
        object property"
    ::= { cfprEtherSwitchIntFIoPcEntry 7 }

cfprEtherSwitchIntFIoPcIfRole OBJECT-TYPE
    SYNTAX       CfprEtherSwitchIntFIoPcIfRole
    MAX-ACCESS   read-only
    STATUS       current
    DESCRIPTION
        "Cisco Firepower ether:SwitchIntFIoPc:ifRole managed
        object property"
    ::= { cfprEtherSwitchIntFIoPcEntry 8 }

cfprEtherSwitchIntFIoPcIfType OBJECT-TYPE
    SYNTAX       CfprEtherCIoEpIfType
    MAX-ACCESS   read-only
    STATUS       current
    DESCRIPTION
        "Cisco Firepower ether:SwitchIntFIoPc:ifType managed
        object property"
    ::= { cfprEtherSwitchIntFIoPcEntry 9 }

cfprEtherSwitchIntFIoPcLocale OBJECT-TYPE
    SYNTAX       CfprEtherExternalPcLocale
    MAX-ACCESS   read-only
    STATUS       current
    DESCRIPTION
        "Cisco Firepower ether:SwitchIntFIoPc:locale managed
        object property"
    ::= { cfprEtherSwitchIntFIoPcEntry 10 }

cfprEtherSwitchIntFIoPcName OBJECT-TYPE
    SYNTAX       SnmpAdminString
    MAX-ACCESS   read-only
    STATUS       current
    DESCRIPTION
        "Cisco Firepower ether:SwitchIntFIoPc:name managed
        object property"
    ::= { cfprEtherSwitchIntFIoPcEntry 11 }

cfprEtherSwitchIntFIoPcOperSpeed OBJECT-TYPE
    SYNTAX       CfprPortEthSpeed
    MAX-ACCESS   read-only
    STATUS       current
    DESCRIPTION
        "Cisco Firepower ether:SwitchIntFIoPc:operSpeed
        managed object property"
    ::= { cfprEtherSwitchIntFIoPcEntry 12 }

cfprEtherSwitchIntFIoPcOperState OBJECT-TYPE
    SYNTAX       CfprNetworkPortOperState
    MAX-ACCESS   read-only
    STATUS       current
    DESCRIPTION
        "Cisco Firepower ether:SwitchIntFIoPc:operState
        managed object property"
    ::= { cfprEtherSwitchIntFIoPcEntry 13 }

cfprEtherSwitchIntFIoPcPeerDn OBJECT-TYPE
    SYNTAX       SnmpAdminString
    MAX-ACCESS   read-only
    STATUS       current
    DESCRIPTION
        "Cisco Firepower ether:SwitchIntFIoPc:peerDn managed
        object property"
    ::= { cfprEtherSwitchIntFIoPcEntry 14 }

cfprEtherSwitchIntFIoPcPortId OBJECT-TYPE
    SYNTAX       CfprEtherSwitchIntFIoPcPortId
    MAX-ACCESS   read-only
    STATUS       current
    DESCRIPTION
        "Cisco Firepower ether:SwitchIntFIoPc:portId managed
        object property"
    ::= { cfprEtherSwitchIntFIoPcEntry 15 }

cfprEtherSwitchIntFIoPcStateQual OBJECT-TYPE
    SYNTAX       SnmpAdminString
    MAX-ACCESS   read-only
    STATUS       current
    DESCRIPTION
        "Cisco Firepower ether:SwitchIntFIoPc:stateQual
        managed object property"
    ::= { cfprEtherSwitchIntFIoPcEntry 16 }

cfprEtherSwitchIntFIoPcSwitchId OBJECT-TYPE
    SYNTAX       CfprNetworkSwitchId
    MAX-ACCESS   read-only
    STATUS       current
    DESCRIPTION
        "Cisco Firepower ether:SwitchIntFIoPc:switchId
        managed object property"
    ::= { cfprEtherSwitchIntFIoPcEntry 17 }

cfprEtherSwitchIntFIoPcTransport OBJECT-TYPE
    SYNTAX       CfprEtherSwitchIntFIoPcTransport
    MAX-ACCESS   read-only
    STATUS       current
    DESCRIPTION
        "Cisco Firepower ether:SwitchIntFIoPc:transport
        managed object property"
    ::= { cfprEtherSwitchIntFIoPcEntry 18 }

cfprEtherSwitchIntFIoPcType OBJECT-TYPE
    SYNTAX       CfprEtherSwitchIntFIoPcType
    MAX-ACCESS   read-only
    STATUS       current
    DESCRIPTION
        "Cisco Firepower ether:SwitchIntFIoPc:type managed
        object property"
    ::= { cfprEtherSwitchIntFIoPcEntry 19 }

cfprEtherSwitchIntFIoPcEpTable OBJECT-TYPE
    SYNTAX           SEQUENCE OF CfprEtherSwitchIntFIoPcEpEntry
    MAX-ACCESS       not-accessible
    STATUS           current
    DESCRIPTION
        "Cisco Firepower ether:SwitchIntFIoPcEp managed object table"
    ::= { cfprEtherObjects 29 }

cfprEtherSwitchIntFIoPcEpEntry OBJECT-TYPE
    SYNTAX           CfprEtherSwitchIntFIoPcEpEntry
    MAX-ACCESS       not-accessible
    STATUS           current
    DESCRIPTION
        "Entry for the cfprEtherSwitchIntFIoPcEpTable table."
    INDEX { cfprEtherSwitchIntFIoPcEpInstanceId }
    ::= { cfprEtherSwitchIntFIoPcEpTable 1 }

CfprEtherSwitchIntFIoPcEpEntry ::= SEQUENCE {
    cfprEtherSwitchIntFIoPcEpInstanceId                              CfprManagedObjectId,
    cfprEtherSwitchIntFIoPcEpDnData                                  CfprManagedObjectDn,
    cfprEtherSwitchIntFIoPcEpRn                                      SnmpAdminString,
    cfprEtherSwitchIntFIoPcEpAckState                                CfprEquipmentChassisConfigState,
    cfprEtherSwitchIntFIoPcEpAdminState                              CfprEtherExternalEpAdminState,
    cfprEtherSwitchIntFIoPcEpAggrPortId                              Gauge32,
    cfprEtherSwitchIntFIoPcEpChassisId                               Gauge32,
    cfprEtherSwitchIntFIoPcEpEpDn                                    SnmpAdminString,
    cfprEtherSwitchIntFIoPcEpIfRole                                  CfprEtherSwitchIntFIoPcEpIfRole,
    cfprEtherSwitchIntFIoPcEpIfType                                  CfprEtherPIoEpIfType,
    cfprEtherSwitchIntFIoPcEpLocale                                  CfprEtherExternalEpLocale,
    cfprEtherSwitchIntFIoPcEpMembership                              CfprFabricMembershipStatus,
    cfprEtherSwitchIntFIoPcEpName                                    SnmpAdminString,
    cfprEtherSwitchIntFIoPcEpPeerAggrPortId                          Gauge32,
    cfprEtherSwitchIntFIoPcEpPeerChassisId                           Gauge32,
    cfprEtherSwitchIntFIoPcEpPeerDn                                  SnmpAdminString,
    cfprEtherSwitchIntFIoPcEpPeerPortId                              Gauge32,
    cfprEtherSwitchIntFIoPcEpPeerSlotId                              Gauge32,
    cfprEtherSwitchIntFIoPcEpPortId                                  CfprEtherSwitchIntFIoPcEpPortId,
    cfprEtherSwitchIntFIoPcEpSlotId                                  Gauge32,
    cfprEtherSwitchIntFIoPcEpStatusChangeTs                          DateAndTime,
    cfprEtherSwitchIntFIoPcEpSwitchId                                CfprNetworkSwitchId,
    cfprEtherSwitchIntFIoPcEpTransport                               CfprNetworkTransport,
    cfprEtherSwitchIntFIoPcEpType                                    CfprEtherIntFIoEpType
}

cfprEtherSwitchIntFIoPcEpInstanceId OBJECT-TYPE
    SYNTAX       CfprManagedObjectId
    MAX-ACCESS   not-accessible
    STATUS       current
    DESCRIPTION
        "Instance identifier of the managed object."
    ::= { cfprEtherSwitchIntFIoPcEpEntry 1 }

cfprEtherSwitchIntFIoPcEpDnData OBJECT-TYPE
    SYNTAX       CfprManagedObjectDn
    MAX-ACCESS   read-only
    STATUS       current
    DESCRIPTION
        "Cisco Firepower ether:SwitchIntFIoPcEp:dn managed
        object property"
    ::= { cfprEtherSwitchIntFIoPcEpEntry 2 }

cfprEtherSwitchIntFIoPcEpRn OBJECT-TYPE
    SYNTAX       SnmpAdminString
    MAX-ACCESS   read-only
    STATUS       current
    DESCRIPTION
        "Cisco Firepower ether:SwitchIntFIoPcEp:rn managed
        object property"
    ::= { cfprEtherSwitchIntFIoPcEpEntry 3 }

cfprEtherSwitchIntFIoPcEpAckState OBJECT-TYPE
    SYNTAX       CfprEquipmentChassisConfigState
    MAX-ACCESS   read-only
    STATUS       current
    DESCRIPTION
        "Cisco Firepower ether:SwitchIntFIoPcEp:ackState
        managed object property"
    ::= { cfprEtherSwitchIntFIoPcEpEntry 4 }

cfprEtherSwitchIntFIoPcEpAdminState OBJECT-TYPE
    SYNTAX       CfprEtherExternalEpAdminState
    MAX-ACCESS   read-only
    STATUS       current
    DESCRIPTION
        "Cisco Firepower ether:SwitchIntFIoPcEp:adminState
        managed object property"
    ::= { cfprEtherSwitchIntFIoPcEpEntry 5 }

cfprEtherSwitchIntFIoPcEpAggrPortId OBJECT-TYPE
    SYNTAX       Gauge32
    MAX-ACCESS   read-only
    STATUS       current
    DESCRIPTION
        "Cisco Firepower ether:SwitchIntFIoPcEp:aggrPortId
        managed object property"
    ::= { cfprEtherSwitchIntFIoPcEpEntry 6 }

cfprEtherSwitchIntFIoPcEpChassisId OBJECT-TYPE
    SYNTAX       Gauge32
    MAX-ACCESS   read-only
    STATUS       current
    DESCRIPTION
        "Cisco Firepower ether:SwitchIntFIoPcEp:chassisId
        managed object property"
    ::= { cfprEtherSwitchIntFIoPcEpEntry 7 }

cfprEtherSwitchIntFIoPcEpEpDn OBJECT-TYPE
    SYNTAX       SnmpAdminString
    MAX-ACCESS   read-only
    STATUS       current
    DESCRIPTION
        "Cisco Firepower ether:SwitchIntFIoPcEp:epDn managed
        object property"
    ::= { cfprEtherSwitchIntFIoPcEpEntry 8 }

cfprEtherSwitchIntFIoPcEpIfRole OBJECT-TYPE
    SYNTAX       CfprEtherSwitchIntFIoPcEpIfRole
    MAX-ACCESS   read-only
    STATUS       current
    DESCRIPTION
        "Cisco Firepower ether:SwitchIntFIoPcEp:ifRole
        managed object property"
    ::= { cfprEtherSwitchIntFIoPcEpEntry 9 }

cfprEtherSwitchIntFIoPcEpIfType OBJECT-TYPE
    SYNTAX       CfprEtherPIoEpIfType
    MAX-ACCESS   read-only
    STATUS       current
    DESCRIPTION
        "Cisco Firepower ether:SwitchIntFIoPcEp:ifType
        managed object property"
    ::= { cfprEtherSwitchIntFIoPcEpEntry 10 }

cfprEtherSwitchIntFIoPcEpLocale OBJECT-TYPE
    SYNTAX       CfprEtherExternalEpLocale
    MAX-ACCESS   read-only
    STATUS       current
    DESCRIPTION
        "Cisco Firepower ether:SwitchIntFIoPcEp:locale
        managed object property"
    ::= { cfprEtherSwitchIntFIoPcEpEntry 11 }

cfprEtherSwitchIntFIoPcEpMembership OBJECT-TYPE
    SYNTAX       CfprFabricMembershipStatus
    MAX-ACCESS   read-only
    STATUS       current
    DESCRIPTION
        "Cisco Firepower ether:SwitchIntFIoPcEp:membership
        managed object property"
    ::= { cfprEtherSwitchIntFIoPcEpEntry 12 }

cfprEtherSwitchIntFIoPcEpName OBJECT-TYPE
    SYNTAX       SnmpAdminString
    MAX-ACCESS   read-only
    STATUS       current
    DESCRIPTION
        "Cisco Firepower ether:SwitchIntFIoPcEp:name managed
        object property"
    ::= { cfprEtherSwitchIntFIoPcEpEntry 13 }

cfprEtherSwitchIntFIoPcEpPeerAggrPortId OBJECT-TYPE
    SYNTAX       Gauge32
    MAX-ACCESS   read-only
    STATUS       current
    DESCRIPTION
        "Cisco Firepower ether:SwitchIntFIoPcEp:peerAggrPortId
        managed object property"
    ::= { cfprEtherSwitchIntFIoPcEpEntry 14 }

cfprEtherSwitchIntFIoPcEpPeerChassisId OBJECT-TYPE
    SYNTAX       Gauge32
    MAX-ACCESS   read-only
    STATUS       current
    DESCRIPTION
        "Cisco Firepower ether:SwitchIntFIoPcEp:peerChassisId
        managed object property"
    ::= { cfprEtherSwitchIntFIoPcEpEntry 15 }

cfprEtherSwitchIntFIoPcEpPeerDn OBJECT-TYPE
    SYNTAX       SnmpAdminString
    MAX-ACCESS   read-only
    STATUS       current
    DESCRIPTION
        "Cisco Firepower ether:SwitchIntFIoPcEp:peerDn
        managed object property"
    ::= { cfprEtherSwitchIntFIoPcEpEntry 16 }

cfprEtherSwitchIntFIoPcEpPeerPortId OBJECT-TYPE
    SYNTAX       Gauge32
    MAX-ACCESS   read-only
    STATUS       current
    DESCRIPTION
        "Cisco Firepower ether:SwitchIntFIoPcEp:peerPortId
        managed object property"
    ::= { cfprEtherSwitchIntFIoPcEpEntry 17 }

cfprEtherSwitchIntFIoPcEpPeerSlotId OBJECT-TYPE
    SYNTAX       Gauge32
    MAX-ACCESS   read-only
    STATUS       current
    DESCRIPTION
        "Cisco Firepower ether:SwitchIntFIoPcEp:peerSlotId
        managed object property"
    ::= { cfprEtherSwitchIntFIoPcEpEntry 18 }

cfprEtherSwitchIntFIoPcEpPortId OBJECT-TYPE
    SYNTAX       CfprEtherSwitchIntFIoPcEpPortId
    MAX-ACCESS   read-only
    STATUS       current
    DESCRIPTION
        "Cisco Firepower ether:SwitchIntFIoPcEp:portId
        managed object property"
    ::= { cfprEtherSwitchIntFIoPcEpEntry 19 }

cfprEtherSwitchIntFIoPcEpSlotId OBJECT-TYPE
    SYNTAX       Gauge32
    MAX-ACCESS   read-only
    STATUS       current
    DESCRIPTION
        "Cisco Firepower ether:SwitchIntFIoPcEp:slotId
        managed object property"
    ::= { cfprEtherSwitchIntFIoPcEpEntry 20 }

cfprEtherSwitchIntFIoPcEpStatusChangeTs OBJECT-TYPE
    SYNTAX       DateAndTime
    MAX-ACCESS   read-only
    STATUS       current
    DESCRIPTION
        "Cisco Firepower ether:SwitchIntFIoPcEp:statusChangeTs
        managed object property"
    ::= { cfprEtherSwitchIntFIoPcEpEntry 21 }

cfprEtherSwitchIntFIoPcEpSwitchId OBJECT-TYPE
    SYNTAX       CfprNetworkSwitchId
    MAX-ACCESS   read-only
    STATUS       current
    DESCRIPTION
        "Cisco Firepower ether:SwitchIntFIoPcEp:switchId
        managed object property"
    ::= { cfprEtherSwitchIntFIoPcEpEntry 22 }

cfprEtherSwitchIntFIoPcEpTransport OBJECT-TYPE
    SYNTAX       CfprNetworkTransport
    MAX-ACCESS   read-only
    STATUS       current
    DESCRIPTION
        "Cisco Firepower ether:SwitchIntFIoPcEp:transport
        managed object property"
    ::= { cfprEtherSwitchIntFIoPcEpEntry 23 }

cfprEtherSwitchIntFIoPcEpType OBJECT-TYPE
    SYNTAX       CfprEtherIntFIoEpType
    MAX-ACCESS   read-only
    STATUS       current
    DESCRIPTION
        "Cisco Firepower ether:SwitchIntFIoPcEp:type managed
        object property"
    ::= { cfprEtherSwitchIntFIoPcEpEntry 24 }

cfprEtherTxStatsTable OBJECT-TYPE
    SYNTAX           SEQUENCE OF CfprEtherTxStatsEntry
    MAX-ACCESS       not-accessible
    STATUS           current
    DESCRIPTION
        "Cisco Firepower ether:TxStats managed object table"
    ::= { cfprEtherObjects 30 }

cfprEtherTxStatsEntry OBJECT-TYPE
    SYNTAX           CfprEtherTxStatsEntry
    MAX-ACCESS       not-accessible
    STATUS           current
    DESCRIPTION
        "Entry for the cfprEtherTxStatsTable table."
    INDEX { cfprEtherTxStatsInstanceId }
    ::= { cfprEtherTxStatsTable 1 }

CfprEtherTxStatsEntry ::= SEQUENCE {
    cfprEtherTxStatsInstanceId                                       CfprManagedObjectId,
    cfprEtherTxStatsDn                                               CfprManagedObjectDn,
    cfprEtherTxStatsRn                                               SnmpAdminString,
    cfprEtherTxStatsBroadcastPackets                                 Unsigned64,
    cfprEtherTxStatsBroadcastPacketsDelta                            Counter64,
    cfprEtherTxStatsBroadcastPacketsDeltaAvg                         Unsigned64,
    cfprEtherTxStatsBroadcastPacketsDeltaMax                         Unsigned64,
    cfprEtherTxStatsBroadcastPacketsDeltaMin                         Unsigned64,
    cfprEtherTxStatsIntervals                                        Gauge32,
    cfprEtherTxStatsJumboPackets                                     Unsigned64,
    cfprEtherTxStatsJumboPacketsDelta                                Counter64,
    cfprEtherTxStatsJumboPacketsDeltaAvg                             Unsigned64,
    cfprEtherTxStatsJumboPacketsDeltaMax                             Unsigned64,
    cfprEtherTxStatsJumboPacketsDeltaMin                             Unsigned64,
    cfprEtherTxStatsMulticastPackets                                 Unsigned64,
    cfprEtherTxStatsMulticastPacketsDelta                            Counter64,
    cfprEtherTxStatsMulticastPacketsDeltaAvg                         Unsigned64,
    cfprEtherTxStatsMulticastPacketsDeltaMax                         Unsigned64,
    cfprEtherTxStatsMulticastPacketsDeltaMin                         Unsigned64,
    cfprEtherTxStatsSuspect                                          TruthValue,
    cfprEtherTxStatsThresholded                                      CfprEtherTxStatsThresholded,
    cfprEtherTxStatsTimeCollected                                    DateAndTime,
    cfprEtherTxStatsTotalBytes                                       Unsigned64,
    cfprEtherTxStatsTotalBytesDelta                                  Counter64,
    cfprEtherTxStatsTotalBytesDeltaAvg                               Unsigned64,
    cfprEtherTxStatsTotalBytesDeltaMax                               Unsigned64,
    cfprEtherTxStatsTotalBytesDeltaMin                               Unsigned64,
    cfprEtherTxStatsTotalPackets                                     Unsigned64,
    cfprEtherTxStatsTotalPacketsDelta                                Counter64,
    cfprEtherTxStatsTotalPacketsDeltaAvg                             Unsigned64,
    cfprEtherTxStatsTotalPacketsDeltaMax                             Unsigned64,
    cfprEtherTxStatsTotalPacketsDeltaMin                             Unsigned64,
    cfprEtherTxStatsUnicastPackets                                   Unsigned64,
    cfprEtherTxStatsUnicastPacketsDelta                              Counter64,
    cfprEtherTxStatsUnicastPacketsDeltaAvg                           Unsigned64,
    cfprEtherTxStatsUnicastPacketsDeltaMax                           Unsigned64,
    cfprEtherTxStatsUnicastPacketsDeltaMin                           Unsigned64,
    cfprEtherTxStatsUpdate                                           Gauge32
}

cfprEtherTxStatsInstanceId OBJECT-TYPE
    SYNTAX       CfprManagedObjectId
    MAX-ACCESS   not-accessible
    STATUS       current
    DESCRIPTION
        "Instance identifier of the managed object."
    ::= { cfprEtherTxStatsEntry 1 }

cfprEtherTxStatsDn OBJECT-TYPE
    SYNTAX       CfprManagedObjectDn
    MAX-ACCESS   read-only
    STATUS       current
    DESCRIPTION
        "Cisco Firepower ether:TxStats:dn managed object property"
    ::= { cfprEtherTxStatsEntry 2 }

cfprEtherTxStatsRn OBJECT-TYPE
    SYNTAX       SnmpAdminString
    MAX-ACCESS   read-only
    STATUS       current
    DESCRIPTION
        "Cisco Firepower ether:TxStats:rn managed object property"
    ::= { cfprEtherTxStatsEntry 3 }

cfprEtherTxStatsBroadcastPackets OBJECT-TYPE
    SYNTAX       Unsigned64
    MAX-ACCESS   read-only
    STATUS       current
    DESCRIPTION
        "Cisco Firepower ether:TxStats:broadcastPackets
        managed object property"
    ::= { cfprEtherTxStatsEntry 4 }

cfprEtherTxStatsBroadcastPacketsDelta OBJECT-TYPE
    SYNTAX       Counter64
    MAX-ACCESS   read-only
    STATUS       current
    DESCRIPTION
        "Cisco Firepower ether:TxStats:broadcastPacketsDelta
        managed object property"
    ::= { cfprEtherTxStatsEntry 5 }

cfprEtherTxStatsBroadcastPacketsDeltaAvg OBJECT-TYPE
    SYNTAX       Unsigned64
    MAX-ACCESS   read-only
    STATUS       current
    DESCRIPTION
        "Cisco Firepower ether:TxStats:broadcastPacketsDeltaAvg
        managed object property"
    ::= { cfprEtherTxStatsEntry 6 }

cfprEtherTxStatsBroadcastPacketsDeltaMax OBJECT-TYPE
    SYNTAX       Unsigned64
    MAX-ACCESS   read-only
    STATUS       current
    DESCRIPTION
        "Cisco Firepower ether:TxStats:broadcastPacketsDeltaMax
        managed object property"
    ::= { cfprEtherTxStatsEntry 7 }

cfprEtherTxStatsBroadcastPacketsDeltaMin OBJECT-TYPE
    SYNTAX       Unsigned64
    MAX-ACCESS   read-only
    STATUS       current
    DESCRIPTION
        "Cisco Firepower ether:TxStats:broadcastPacketsDeltaMin
        managed object property"
    ::= { cfprEtherTxStatsEntry 8 }

cfprEtherTxStatsIntervals OBJECT-TYPE
    SYNTAX       Gauge32
    MAX-ACCESS   read-only
    STATUS       current
    DESCRIPTION
        "Cisco Firepower ether:TxStats:intervals managed object property"
    ::= { cfprEtherTxStatsEntry 9 }

cfprEtherTxStatsJumboPackets OBJECT-TYPE
    SYNTAX       Unsigned64
    MAX-ACCESS   read-only
    STATUS       current
    DESCRIPTION
        "Cisco Firepower ether:TxStats:jumboPackets managed
        object property"
    ::= { cfprEtherTxStatsEntry 10 }

cfprEtherTxStatsJumboPacketsDelta OBJECT-TYPE
    SYNTAX       Counter64
    MAX-ACCESS   read-only
    STATUS       current
    DESCRIPTION
        "Cisco Firepower ether:TxStats:jumboPacketsDelta
        managed object property"
    ::= { cfprEtherTxStatsEntry 11 }

cfprEtherTxStatsJumboPacketsDeltaAvg OBJECT-TYPE
    SYNTAX       Unsigned64
    MAX-ACCESS   read-only
    STATUS       current
    DESCRIPTION
        "Cisco Firepower ether:TxStats:jumboPacketsDeltaAvg
        managed object property"
    ::= { cfprEtherTxStatsEntry 12 }

cfprEtherTxStatsJumboPacketsDeltaMax OBJECT-TYPE
    SYNTAX       Unsigned64
    MAX-ACCESS   read-only
    STATUS       current
    DESCRIPTION
        "Cisco Firepower ether:TxStats:jumboPacketsDeltaMax
        managed object property"
    ::= { cfprEtherTxStatsEntry 13 }

cfprEtherTxStatsJumboPacketsDeltaMin OBJECT-TYPE
    SYNTAX       Unsigned64
    MAX-ACCESS   read-only
    STATUS       current
    DESCRIPTION
        "Cisco Firepower ether:TxStats:jumboPacketsDeltaMin
        managed object property"
    ::= { cfprEtherTxStatsEntry 14 }

cfprEtherTxStatsMulticastPackets OBJECT-TYPE
    SYNTAX       Unsigned64
    MAX-ACCESS   read-only
    STATUS       current
    DESCRIPTION
        "Cisco Firepower ether:TxStats:multicastPackets
        managed object property"
    ::= { cfprEtherTxStatsEntry 15 }

cfprEtherTxStatsMulticastPacketsDelta OBJECT-TYPE
    SYNTAX       Counter64
    MAX-ACCESS   read-only
    STATUS       current
    DESCRIPTION
        "Cisco Firepower ether:TxStats:multicastPacketsDelta
        managed object property"
    ::= { cfprEtherTxStatsEntry 16 }

cfprEtherTxStatsMulticastPacketsDeltaAvg OBJECT-TYPE
    SYNTAX       Unsigned64
    MAX-ACCESS   read-only
    STATUS       current
    DESCRIPTION
        "Cisco Firepower ether:TxStats:multicastPacketsDeltaAvg
        managed object property"
    ::= { cfprEtherTxStatsEntry 17 }

cfprEtherTxStatsMulticastPacketsDeltaMax OBJECT-TYPE
    SYNTAX       Unsigned64
    MAX-ACCESS   read-only
    STATUS       current
    DESCRIPTION
        "Cisco Firepower ether:TxStats:multicastPacketsDeltaMax
        managed object property"
    ::= { cfprEtherTxStatsEntry 18 }

cfprEtherTxStatsMulticastPacketsDeltaMin OBJECT-TYPE
    SYNTAX       Unsigned64
    MAX-ACCESS   read-only
    STATUS       current
    DESCRIPTION
        "Cisco Firepower ether:TxStats:multicastPacketsDeltaMin
        managed object property"
    ::= { cfprEtherTxStatsEntry 19 }

cfprEtherTxStatsSuspect OBJECT-TYPE
    SYNTAX       TruthValue
    MAX-ACCESS   read-only
    STATUS       current
    DESCRIPTION
        "Cisco Firepower ether:TxStats:suspect managed object property"
    ::= { cfprEtherTxStatsEntry 20 }

cfprEtherTxStatsThresholded OBJECT-TYPE
    SYNTAX       CfprEtherTxStatsThresholded
    MAX-ACCESS   read-only
    STATUS       current
    DESCRIPTION
        "Cisco Firepower ether:TxStats:thresholded managed
        object property"
    ::= { cfprEtherTxStatsEntry 21 }

cfprEtherTxStatsTimeCollected OBJECT-TYPE
    SYNTAX       DateAndTime
    MAX-ACCESS   read-only
    STATUS       current
    DESCRIPTION
        "Cisco Firepower ether:TxStats:timeCollected managed
        object property"
    ::= { cfprEtherTxStatsEntry 22 }

cfprEtherTxStatsTotalBytes OBJECT-TYPE
    SYNTAX       Unsigned64
    MAX-ACCESS   read-only
    STATUS       current
    DESCRIPTION
        "Cisco Firepower ether:TxStats:totalBytes managed object property"
    ::= { cfprEtherTxStatsEntry 23 }

cfprEtherTxStatsTotalBytesDelta OBJECT-TYPE
    SYNTAX       Counter64
    MAX-ACCESS   read-only
    STATUS       current
    DESCRIPTION
        "Cisco Firepower ether:TxStats:totalBytesDelta
        managed object property"
    ::= { cfprEtherTxStatsEntry 24 }

cfprEtherTxStatsTotalBytesDeltaAvg OBJECT-TYPE
    SYNTAX       Unsigned64
    MAX-ACCESS   read-only
    STATUS       current
    DESCRIPTION
        "Cisco Firepower ether:TxStats:totalBytesDeltaAvg
        managed object property"
    ::= { cfprEtherTxStatsEntry 25 }

cfprEtherTxStatsTotalBytesDeltaMax OBJECT-TYPE
    SYNTAX       Unsigned64
    MAX-ACCESS   read-only
    STATUS       current
    DESCRIPTION
        "Cisco Firepower ether:TxStats:totalBytesDeltaMax
        managed object property"
    ::= { cfprEtherTxStatsEntry 26 }

cfprEtherTxStatsTotalBytesDeltaMin OBJECT-TYPE
    SYNTAX       Unsigned64
    MAX-ACCESS   read-only
    STATUS       current
    DESCRIPTION
        "Cisco Firepower ether:TxStats:totalBytesDeltaMin
        managed object property"
    ::= { cfprEtherTxStatsEntry 27 }

cfprEtherTxStatsTotalPackets OBJECT-TYPE
    SYNTAX       Unsigned64
    MAX-ACCESS   read-only
    STATUS       current
    DESCRIPTION
        "Cisco Firepower ether:TxStats:totalPackets managed
        object property"
    ::= { cfprEtherTxStatsEntry 28 }

cfprEtherTxStatsTotalPacketsDelta OBJECT-TYPE
    SYNTAX       Counter64
    MAX-ACCESS   read-only
    STATUS       current
    DESCRIPTION
        "Cisco Firepower ether:TxStats:totalPacketsDelta
        managed object property"
    ::= { cfprEtherTxStatsEntry 29 }

cfprEtherTxStatsTotalPacketsDeltaAvg OBJECT-TYPE
    SYNTAX       Unsigned64
    MAX-ACCESS   read-only
    STATUS       current
    DESCRIPTION
        "Cisco Firepower ether:TxStats:totalPacketsDeltaAvg
        managed object property"
    ::= { cfprEtherTxStatsEntry 30 }

cfprEtherTxStatsTotalPacketsDeltaMax OBJECT-TYPE
    SYNTAX       Unsigned64
    MAX-ACCESS   read-only
    STATUS       current
    DESCRIPTION
        "Cisco Firepower ether:TxStats:totalPacketsDeltaMax
        managed object property"
    ::= { cfprEtherTxStatsEntry 31 }

cfprEtherTxStatsTotalPacketsDeltaMin OBJECT-TYPE
    SYNTAX       Unsigned64
    MAX-ACCESS   read-only
    STATUS       current
    DESCRIPTION
        "Cisco Firepower ether:TxStats:totalPacketsDeltaMin
        managed object property"
    ::= { cfprEtherTxStatsEntry 32 }

cfprEtherTxStatsUnicastPackets OBJECT-TYPE
    SYNTAX       Unsigned64
    MAX-ACCESS   read-only
    STATUS       current
    DESCRIPTION
        "Cisco Firepower ether:TxStats:unicastPackets managed
        object property"
    ::= { cfprEtherTxStatsEntry 33 }

cfprEtherTxStatsUnicastPacketsDelta OBJECT-TYPE
    SYNTAX       Counter64
    MAX-ACCESS   read-only
    STATUS       current
    DESCRIPTION
        "Cisco Firepower ether:TxStats:unicastPacketsDelta
        managed object property"
    ::= { cfprEtherTxStatsEntry 34 }

cfprEtherTxStatsUnicastPacketsDeltaAvg OBJECT-TYPE
    SYNTAX       Unsigned64
    MAX-ACCESS   read-only
    STATUS       current
    DESCRIPTION
        "Cisco Firepower ether:TxStats:unicastPacketsDeltaAvg
        managed object property"
    ::= { cfprEtherTxStatsEntry 35 }

cfprEtherTxStatsUnicastPacketsDeltaMax OBJECT-TYPE
    SYNTAX       Unsigned64
    MAX-ACCESS   read-only
    STATUS       current
    DESCRIPTION
        "Cisco Firepower ether:TxStats:unicastPacketsDeltaMax
        managed object property"
    ::= { cfprEtherTxStatsEntry 36 }

cfprEtherTxStatsUnicastPacketsDeltaMin OBJECT-TYPE
    SYNTAX       Unsigned64
    MAX-ACCESS   read-only
    STATUS       current
    DESCRIPTION
        "Cisco Firepower ether:TxStats:unicastPacketsDeltaMin
        managed object property"
    ::= { cfprEtherTxStatsEntry 37 }

cfprEtherTxStatsUpdate OBJECT-TYPE
    SYNTAX       Gauge32
    MAX-ACCESS   read-only
    STATUS       current
    DESCRIPTION
        "Cisco Firepower ether:TxStats:update managed object property"
    ::= { cfprEtherTxStatsEntry 38 }

cfprEtherTxStatsHistTable OBJECT-TYPE
    SYNTAX           SEQUENCE OF CfprEtherTxStatsHistEntry
    MAX-ACCESS       not-accessible
    STATUS           current
    DESCRIPTION
        "Cisco Firepower ether:TxStatsHist managed object table"
    ::= { cfprEtherObjects 31 }

cfprEtherTxStatsHistEntry OBJECT-TYPE
    SYNTAX           CfprEtherTxStatsHistEntry
    MAX-ACCESS       not-accessible
    STATUS           current
    DESCRIPTION
        "Entry for the cfprEtherTxStatsHistTable table."
    INDEX { cfprEtherTxStatsHistInstanceId }
    ::= { cfprEtherTxStatsHistTable 1 }

CfprEtherTxStatsHistEntry ::= SEQUENCE {
    cfprEtherTxStatsHistInstanceId                                   CfprManagedObjectId,
    cfprEtherTxStatsHistDn                                           CfprManagedObjectDn,
    cfprEtherTxStatsHistRn                                           SnmpAdminString,
    cfprEtherTxStatsHistBroadcastPackets                             Unsigned64,
    cfprEtherTxStatsHistBroadcastPacketsDelta                        Unsigned64,
    cfprEtherTxStatsHistBroadcastPacketsDeltaAvg                     Unsigned64,
    cfprEtherTxStatsHistBroadcastPacketsDeltaMax                     Unsigned64,
    cfprEtherTxStatsHistBroadcastPacketsDeltaMin                     Unsigned64,
    cfprEtherTxStatsHistId                                           Unsigned64,
    cfprEtherTxStatsHistJumboPackets                                 Unsigned64,
    cfprEtherTxStatsHistJumboPacketsDelta                            Unsigned64,
    cfprEtherTxStatsHistJumboPacketsDeltaAvg                         Unsigned64,
    cfprEtherTxStatsHistJumboPacketsDeltaMax                         Unsigned64,
    cfprEtherTxStatsHistJumboPacketsDeltaMin                         Unsigned64,
    cfprEtherTxStatsHistMostRecent                                   TruthValue,
    cfprEtherTxStatsHistMulticastPackets                             Unsigned64,
    cfprEtherTxStatsHistMulticastPacketsDelta                        Unsigned64,
    cfprEtherTxStatsHistMulticastPacketsDeltaAvg                     Unsigned64,
    cfprEtherTxStatsHistMulticastPacketsDeltaMax                     Unsigned64,
    cfprEtherTxStatsHistMulticastPacketsDeltaMin                     Unsigned64,
    cfprEtherTxStatsHistSuspect                                      TruthValue,
    cfprEtherTxStatsHistThresholded                                  CfprEtherTxStatsHistThresholded,
    cfprEtherTxStatsHistTimeCollected                                DateAndTime,
    cfprEtherTxStatsHistTotalBytes                                   Unsigned64,
    cfprEtherTxStatsHistTotalBytesDelta                              Unsigned64,
    cfprEtherTxStatsHistTotalBytesDeltaAvg                           Unsigned64,
    cfprEtherTxStatsHistTotalBytesDeltaMax                           Unsigned64,
    cfprEtherTxStatsHistTotalBytesDeltaMin                           Unsigned64,
    cfprEtherTxStatsHistTotalPackets                                 Unsigned64,
    cfprEtherTxStatsHistTotalPacketsDelta                            Unsigned64,
    cfprEtherTxStatsHistTotalPacketsDeltaAvg                         Unsigned64,
    cfprEtherTxStatsHistTotalPacketsDeltaMax                         Unsigned64,
    cfprEtherTxStatsHistTotalPacketsDeltaMin                         Unsigned64,
    cfprEtherTxStatsHistUnicastPackets                               Unsigned64,
    cfprEtherTxStatsHistUnicastPacketsDelta                          Unsigned64,
    cfprEtherTxStatsHistUnicastPacketsDeltaAvg                       Unsigned64,
    cfprEtherTxStatsHistUnicastPacketsDeltaMax                       Unsigned64,
    cfprEtherTxStatsHistUnicastPacketsDeltaMin                       Unsigned64
}

cfprEtherTxStatsHistInstanceId OBJECT-TYPE
    SYNTAX       CfprManagedObjectId
    MAX-ACCESS   not-accessible
    STATUS       current
    DESCRIPTION
        "Instance identifier of the managed object."
    ::= { cfprEtherTxStatsHistEntry 1 }

cfprEtherTxStatsHistDn OBJECT-TYPE
    SYNTAX       CfprManagedObjectDn
    MAX-ACCESS   read-only
    STATUS       current
    DESCRIPTION
        "Cisco Firepower ether:TxStatsHist:dn managed object property"
    ::= { cfprEtherTxStatsHistEntry 2 }

cfprEtherTxStatsHistRn OBJECT-TYPE
    SYNTAX       SnmpAdminString
    MAX-ACCESS   read-only
    STATUS       current
    DESCRIPTION
        "Cisco Firepower ether:TxStatsHist:rn managed object property"
    ::= { cfprEtherTxStatsHistEntry 3 }

cfprEtherTxStatsHistBroadcastPackets OBJECT-TYPE
    SYNTAX       Unsigned64
    MAX-ACCESS   read-only
    STATUS       current
    DESCRIPTION
        "Cisco Firepower ether:TxStatsHist:broadcastPackets
        managed object property"
    ::= { cfprEtherTxStatsHistEntry 4 }

cfprEtherTxStatsHistBroadcastPacketsDelta OBJECT-TYPE
    SYNTAX       Unsigned64
    MAX-ACCESS   read-only
    STATUS       current
    DESCRIPTION
        "Cisco Firepower ether:TxStatsHist:broadcastPacketsDelta
        managed object property"
    ::= { cfprEtherTxStatsHistEntry 5 }

cfprEtherTxStatsHistBroadcastPacketsDeltaAvg OBJECT-TYPE
    SYNTAX       Unsigned64
    MAX-ACCESS   read-only
    STATUS       current
    DESCRIPTION
        "Cisco Firepower ether:TxStatsHist:broadcastPacketsDeltaAvg
        managed object property"
    ::= { cfprEtherTxStatsHistEntry 6 }

cfprEtherTxStatsHistBroadcastPacketsDeltaMax OBJECT-TYPE
    SYNTAX       Unsigned64
    MAX-ACCESS   read-only
    STATUS       current
    DESCRIPTION
        "Cisco Firepower ether:TxStatsHist:broadcastPacketsDeltaMax
        managed object property"
    ::= { cfprEtherTxStatsHistEntry 7 }

cfprEtherTxStatsHistBroadcastPacketsDeltaMin OBJECT-TYPE
    SYNTAX       Unsigned64
    MAX-ACCESS   read-only
    STATUS       current
    DESCRIPTION
        "Cisco Firepower ether:TxStatsHist:broadcastPacketsDeltaMin
        managed object property"
    ::= { cfprEtherTxStatsHistEntry 8 }

cfprEtherTxStatsHistId OBJECT-TYPE
    SYNTAX       Unsigned64
    MAX-ACCESS   read-only
    STATUS       current
    DESCRIPTION
        "Cisco Firepower ether:TxStatsHist:id managed object property"
    ::= { cfprEtherTxStatsHistEntry 9 }

cfprEtherTxStatsHistJumboPackets OBJECT-TYPE
    SYNTAX       Unsigned64
    MAX-ACCESS   read-only
    STATUS       current
    DESCRIPTION
        "Cisco Firepower ether:TxStatsHist:jumboPackets
        managed object property"
    ::= { cfprEtherTxStatsHistEntry 10 }

cfprEtherTxStatsHistJumboPacketsDelta OBJECT-TYPE
    SYNTAX       Unsigned64
    MAX-ACCESS   read-only
    STATUS       current
    DESCRIPTION
        "Cisco Firepower ether:TxStatsHist:jumboPacketsDelta
        managed object property"
    ::= { cfprEtherTxStatsHistEntry 11 }

cfprEtherTxStatsHistJumboPacketsDeltaAvg OBJECT-TYPE
    SYNTAX       Unsigned64
    MAX-ACCESS   read-only
    STATUS       current
    DESCRIPTION
        "Cisco Firepower ether:TxStatsHist:jumboPacketsDeltaAvg
        managed object property"
    ::= { cfprEtherTxStatsHistEntry 12 }

cfprEtherTxStatsHistJumboPacketsDeltaMax OBJECT-TYPE
    SYNTAX       Unsigned64
    MAX-ACCESS   read-only
    STATUS       current
    DESCRIPTION
        "Cisco Firepower ether:TxStatsHist:jumboPacketsDeltaMax
        managed object property"
    ::= { cfprEtherTxStatsHistEntry 13 }

cfprEtherTxStatsHistJumboPacketsDeltaMin OBJECT-TYPE
    SYNTAX       Unsigned64
    MAX-ACCESS   read-only
    STATUS       current
    DESCRIPTION
        "Cisco Firepower ether:TxStatsHist:jumboPacketsDeltaMin
        managed object property"
    ::= { cfprEtherTxStatsHistEntry 14 }

cfprEtherTxStatsHistMostRecent OBJECT-TYPE
    SYNTAX       TruthValue
    MAX-ACCESS   read-only
    STATUS       current
    DESCRIPTION
        "Cisco Firepower ether:TxStatsHist:mostRecent managed
        object property"
    ::= { cfprEtherTxStatsHistEntry 15 }

cfprEtherTxStatsHistMulticastPackets OBJECT-TYPE
    SYNTAX       Unsigned64
    MAX-ACCESS   read-only
    STATUS       current
    DESCRIPTION
        "Cisco Firepower ether:TxStatsHist:multicastPackets
        managed object property"
    ::= { cfprEtherTxStatsHistEntry 16 }

cfprEtherTxStatsHistMulticastPacketsDelta OBJECT-TYPE
    SYNTAX       Unsigned64
    MAX-ACCESS   read-only
    STATUS       current
    DESCRIPTION
        "Cisco Firepower ether:TxStatsHist:multicastPacketsDelta
        managed object property"
    ::= { cfprEtherTxStatsHistEntry 17 }

cfprEtherTxStatsHistMulticastPacketsDeltaAvg OBJECT-TYPE
    SYNTAX       Unsigned64
    MAX-ACCESS   read-only
    STATUS       current
    DESCRIPTION
        "Cisco Firepower ether:TxStatsHist:multicastPacketsDeltaAvg
        managed object property"
    ::= { cfprEtherTxStatsHistEntry 18 }

cfprEtherTxStatsHistMulticastPacketsDeltaMax OBJECT-TYPE
    SYNTAX       Unsigned64
    MAX-ACCESS   read-only
    STATUS       current
    DESCRIPTION
        "Cisco Firepower ether:TxStatsHist:multicastPacketsDeltaMax
        managed object property"
    ::= { cfprEtherTxStatsHistEntry 19 }

cfprEtherTxStatsHistMulticastPacketsDeltaMin OBJECT-TYPE
    SYNTAX       Unsigned64
    MAX-ACCESS   read-only
    STATUS       current
    DESCRIPTION
        "Cisco Firepower ether:TxStatsHist:multicastPacketsDeltaMin
        managed object property"
    ::= { cfprEtherTxStatsHistEntry 20 }

cfprEtherTxStatsHistSuspect OBJECT-TYPE
    SYNTAX       TruthValue
    MAX-ACCESS   read-only
    STATUS       current
    DESCRIPTION
        "Cisco Firepower ether:TxStatsHist:suspect managed
        object property"
    ::= { cfprEtherTxStatsHistEntry 21 }

cfprEtherTxStatsHistThresholded OBJECT-TYPE
    SYNTAX       CfprEtherTxStatsHistThresholded
    MAX-ACCESS   read-only
    STATUS       current
    DESCRIPTION
        "Cisco Firepower ether:TxStatsHist:thresholded
        managed object property"
    ::= { cfprEtherTxStatsHistEntry 22 }

cfprEtherTxStatsHistTimeCollected OBJECT-TYPE
    SYNTAX       DateAndTime
    MAX-ACCESS   read-only
    STATUS       current
    DESCRIPTION
        "Cisco Firepower ether:TxStatsHist:timeCollected
        managed object property"
    ::= { cfprEtherTxStatsHistEntry 23 }

cfprEtherTxStatsHistTotalBytes OBJECT-TYPE
    SYNTAX       Unsigned64
    MAX-ACCESS   read-only
    STATUS       current
    DESCRIPTION
        "Cisco Firepower ether:TxStatsHist:totalBytes managed
        object property"
    ::= { cfprEtherTxStatsHistEntry 24 }

cfprEtherTxStatsHistTotalBytesDelta OBJECT-TYPE
    SYNTAX       Unsigned64
    MAX-ACCESS   read-only
    STATUS       current
    DESCRIPTION
        "Cisco Firepower ether:TxStatsHist:totalBytesDelta
        managed object property"
    ::= { cfprEtherTxStatsHistEntry 25 }

cfprEtherTxStatsHistTotalBytesDeltaAvg OBJECT-TYPE
    SYNTAX       Unsigned64
    MAX-ACCESS   read-only
    STATUS       current
    DESCRIPTION
        "Cisco Firepower ether:TxStatsHist:totalBytesDeltaAvg
        managed object property"
    ::= { cfprEtherTxStatsHistEntry 26 }

cfprEtherTxStatsHistTotalBytesDeltaMax OBJECT-TYPE
    SYNTAX       Unsigned64
    MAX-ACCESS   read-only
    STATUS       current
    DESCRIPTION
        "Cisco Firepower ether:TxStatsHist:totalBytesDeltaMax
        managed object property"
    ::= { cfprEtherTxStatsHistEntry 27 }

cfprEtherTxStatsHistTotalBytesDeltaMin OBJECT-TYPE
    SYNTAX       Unsigned64
    MAX-ACCESS   read-only
    STATUS       current
    DESCRIPTION
        "Cisco Firepower ether:TxStatsHist:totalBytesDeltaMin
        managed object property"
    ::= { cfprEtherTxStatsHistEntry 28 }

cfprEtherTxStatsHistTotalPackets OBJECT-TYPE
    SYNTAX       Unsigned64
    MAX-ACCESS   read-only
    STATUS       current
    DESCRIPTION
        "Cisco Firepower ether:TxStatsHist:totalPackets
        managed object property"
    ::= { cfprEtherTxStatsHistEntry 29 }

cfprEtherTxStatsHistTotalPacketsDelta OBJECT-TYPE
    SYNTAX       Unsigned64
    MAX-ACCESS   read-only
    STATUS       current
    DESCRIPTION
        "Cisco Firepower ether:TxStatsHist:totalPacketsDelta
        managed object property"
    ::= { cfprEtherTxStatsHistEntry 30 }

cfprEtherTxStatsHistTotalPacketsDeltaAvg OBJECT-TYPE
    SYNTAX       Unsigned64
    MAX-ACCESS   read-only
    STATUS       current
    DESCRIPTION
        "Cisco Firepower ether:TxStatsHist:totalPacketsDeltaAvg
        managed object property"
    ::= { cfprEtherTxStatsHistEntry 31 }

cfprEtherTxStatsHistTotalPacketsDeltaMax OBJECT-TYPE
    SYNTAX       Unsigned64
    MAX-ACCESS   read-only
    STATUS       current
    DESCRIPTION
        "Cisco Firepower ether:TxStatsHist:totalPacketsDeltaMax
        managed object property"
    ::= { cfprEtherTxStatsHistEntry 32 }

cfprEtherTxStatsHistTotalPacketsDeltaMin OBJECT-TYPE
    SYNTAX       Unsigned64
    MAX-ACCESS   read-only
    STATUS       current
    DESCRIPTION
        "Cisco Firepower ether:TxStatsHist:totalPacketsDeltaMin
        managed object property"
    ::= { cfprEtherTxStatsHistEntry 33 }

cfprEtherTxStatsHistUnicastPackets OBJECT-TYPE
    SYNTAX       Unsigned64
    MAX-ACCESS   read-only
    STATUS       current
    DESCRIPTION
        "Cisco Firepower ether:TxStatsHist:unicastPackets
        managed object property"
    ::= { cfprEtherTxStatsHistEntry 34 }

cfprEtherTxStatsHistUnicastPacketsDelta OBJECT-TYPE
    SYNTAX       Unsigned64
    MAX-ACCESS   read-only
    STATUS       current
    DESCRIPTION
        "Cisco Firepower ether:TxStatsHist:unicastPacketsDelta
        managed object property"
    ::= { cfprEtherTxStatsHistEntry 35 }

cfprEtherTxStatsHistUnicastPacketsDeltaAvg OBJECT-TYPE
    SYNTAX       Unsigned64
    MAX-ACCESS   read-only
    STATUS       current
    DESCRIPTION
        "Cisco Firepower ether:TxStatsHist:unicastPacketsDeltaAvg
        managed object property"
    ::= { cfprEtherTxStatsHistEntry 36 }

cfprEtherTxStatsHistUnicastPacketsDeltaMax OBJECT-TYPE
    SYNTAX       Unsigned64
    MAX-ACCESS   read-only
    STATUS       current
    DESCRIPTION
        "Cisco Firepower ether:TxStatsHist:unicastPacketsDeltaMax
        managed object property"
    ::= { cfprEtherTxStatsHistEntry 37 }

cfprEtherTxStatsHistUnicastPacketsDeltaMin OBJECT-TYPE
    SYNTAX       Unsigned64
    MAX-ACCESS   read-only
    STATUS       current
    DESCRIPTION
        "Cisco Firepower ether:TxStatsHist:unicastPacketsDeltaMin
        managed object property"
    ::= { cfprEtherTxStatsHistEntry 38 }

END
