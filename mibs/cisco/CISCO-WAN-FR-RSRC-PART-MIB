-- *****************************************************************
-- ciscoWanFrRsrcPartMIB
--
-- September 2002, Subra Hegde
--
-- Copyright (c) 2002 by cisco Systems, Inc.
-- All rights reserved.
-- ****************************************************************

CISCO-WAN-FR-RSRC-PART-MIB DEFINITIONS ::= BEGIN
IMPORTS
    MODULE-IDENTITY,
    OBJECT-TYPE,
    Integer32
                               FROM SNMPv2-SMI
    MODULE-COMPLIANCE,
    OBJECT-GROUP               FROM SNMPv2-CONF
    frPortCnfResPartGrp	       FROM BASIS-MIB
    ciscoWan                   FROM CISCOWAN-SMI;

ciscoWanFrRsrcPartMIB MODULE-IDENTITY
    LAST-UPDATED    "200209040000Z"
    ORGANIZATION    "Cisco Systems, Inc."
    CONTACT-INFO
            "       Cisco Systems
                        Customer Service

                Postal: 170 W Tasman Drive
                        San Jose, CA  95134
                        USA

                        Tel: +1 800 553-NETS

                E-mail: cs-wanatm@cisco.com"
    DESCRIPTION
        "The MIB module to configure the resource partition
        on Frame Relay Ports.

        Terminlogies used:

        LCN  : Logical Connection Number.
        DLCI : Data Link Connection Identifier.
               A unique number assigned to a PVC endpoint in
               a frame relay network. This identifies a particular
               PVC endpoint within a user's access channel in a
               frame relay network and has local significance only
               to that channel."

    REVISION    "200209040000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been
        modified."
    ::= { ciscoWan 45 }


-- ***********************************************************************
--
--
--              LOGICAL PORT CONFIG Resource Partition Group
--
--
-- ***********************************************************************

frPortCnfResPartGrpTable	OBJECT-TYPE
    SYNTAX      SEQUENCE OF FrPortCnfResPartGrpEntry
    MAX-ACCESS  not-accessible
    STATUS      current
    DESCRIPTION
        "This table is for configuring resource partition
        parameters. A resource partition is configured
        on frame relay port. The frame relay port
        if available in ifTable is identified by ifType
        values frameRelayService(44) and frForward(158)."
    ::= {frPortCnfResPartGrp 1}

frPortCnfResPartGrpEntry		OBJECT-TYPE
    SYNTAX      FrPortCnfResPartGrpEntry
    MAX-ACCESS  not-accessible
    STATUS      current
    DESCRIPTION
        "An entry for a resource partition. A resource
        partition has to be created before connections
        can be added on a frame relay port."
	INDEX  { frResPartPortNum, frResPartCtrlrNum }
	::= { frPortCnfResPartGrpTable 1 }

FrPortCnfResPartGrpEntry ::=
    SEQUENCE {
        frResPartPortNum	Integer32,
        frResPartCtrlrNum	INTEGER,
        frResPartRowStatus	INTEGER,
        frResPartNumOfLcnAvail	Integer32,
        frResPartDlciLow	Integer32,
        frResPartDlciHigh	Integer32,
        frResPartIngrPctBW	Integer32,
        frResPartEgrPctBW	Integer32,
        frResPartCtrlrID        Integer32
}

frResPartPortNum	OBJECT-TYPE
    SYNTAX      Integer32(1..2147483647)
    MAX-ACCESS  read-only
    STATUS      current
    DESCRIPTION
        "The value of this object identifies the frame
        relay port. The value of this object must be
        same as the value of 'portNum' from frPortCnfPortGrpTable.

        If frame relay port is available in ifTable,
        then the value of this object must be same as the
        ifIndex value of frame relay ports with
        ifType frameRelayService(44) and frForward(158)."
    REFERENCE
        "portNum object in CISCO-WAN-FR-PORT-MIB.my"
    ::= { frPortCnfResPartGrpEntry 1 }

frResPartCtrlrNum OBJECT-TYPE
    SYNTAX      INTEGER {
                    par (1),
                    pnni(2),
                    tag (3)
                 }
    MAX-ACCESS  read-only
    STATUS      current
    DESCRIPTION
        "This object identifies the controller
        which can be used for accessing the resources.

         The possible values are :
           par(1) : Portable Auto Route controller.
                  : This value is applicable in Release 1.x.

           pnni(2): PNNI  Controller.
                  : This value is applicable in Release 2.x.

           tag(3) : MPLS(Formerly known as Tag Switch)Controller
        "
    ::= { frPortCnfResPartGrpEntry 2 }

frResPartRowStatus OBJECT-TYPE
    SYNTAX     INTEGER {
                   add (1),
                   del (2),
                   mod (3)
               }
    MAX-ACCESS  read-write
    STATUS      current
    DESCRIPTION
        "This object is used for adding/deleting/modifying
        resource partition on a frame relay port.

        In MGX Release 1.x:
            To add an entry, this object should be set to add, value for
            other objects should not be specified. FRSM will choose
            default values for all other objects.

        In MGX Release 2.x:
            To add an entry, this object should be set to add, value
            for  frResPartCtrlrID may be specified. FRSM will choose
            default values for all other objects.

        To delete an entry, this object has to be set to del.

        Currently the value mod is not supported.

        The resource partition can be deleted only after
        deleting all the connections (LCNs)."
    ::= { frPortCnfResPartGrpEntry 3 }

frResPartNumOfLcnAvail OBJECT-TYPE
    SYNTAX      Integer32 (0..16000)
    MAX-ACCESS  read-write
    STATUS      current
    DESCRIPTION
        " This represents number of LCNs available for this
        controller and this port.
        FRSM VHS 2CT3 can support LCNs upto 4000.
        FRSM12 can support LCNs upto 16000.
    "
    ::= { frPortCnfResPartGrpEntry 4 }

frResPartDlciLow OBJECT-TYPE
    SYNTAX      Integer32 (0..8388607)
    MAX-ACCESS  read-write
    STATUS      current
    DESCRIPTION
        "This represents low end of reserved DLCI."
    ::= { frPortCnfResPartGrpEntry 5 }

frResPartDlciHigh OBJECT-TYPE
    SYNTAX      Integer32 (0..8388607)
    MAX-ACCESS  read-write
    STATUS      current
    DESCRIPTION
        "This represents high end of reserved DLCI."
    ::= { frPortCnfResPartGrpEntry 6 }

frResPartIngrPctBW OBJECT-TYPE
    SYNTAX      Integer32 (0..100)
    UNITS       "percentage"
    MAX-ACCESS  read-write
    STATUS      current
    DESCRIPTION
        "The percentage of total ingress bandwidth reserved."
    ::= { frPortCnfResPartGrpEntry 7 }

frResPartEgrPctBW OBJECT-TYPE
    SYNTAX      Integer32 (0..100)
    UNITS       "percentage"
    MAX-ACCESS  read-write
    STATUS      current
    DESCRIPTION
        "The percentage of total egress bandwidth reserved."
    ::= { frPortCnfResPartGrpEntry 8 }

frResPartCtrlrID OBJECT-TYPE
    SYNTAX     Integer32(1..255)
    MAX-ACCESS read-write
    STATUS     current
    DESCRIPTION
        "This is the controller identifier for the
        resource patition.
        The  default value is set for PNNI controller.
        Refer object frResPartCtrlrNum."
    DEFVAL { 2 }
    ::= { frPortCnfResPartGrpEntry 9 }


-- conformance information

cwfRsrcPartMIBConformance OBJECT IDENTIFIER ::= { ciscoWanFrRsrcPartMIB 2 }

cwfRsrcPartMIBCompliances OBJECT IDENTIFIER ::= { cwfRsrcPartMIBConformance 1 }

cwfRsrcPartMIBGroups      OBJECT IDENTIFIER ::= { cwfRsrcPartMIBConformance 2 }


-- compliance statements

ciscoWanFrRsrcPartCompliance MODULE-COMPLIANCE
    STATUS  current
    DESCRIPTION
        "The compliance statement for entities which implement
        the Frame Relay Resource Partition MIB."
    MODULE  -- this module
        MANDATORY-GROUPS { ciscoWanFrRsrcPartGroup }
    ::= { cwfRsrcPartMIBCompliances 1 }

ciscoWanFrRsrcPartGroup OBJECT-GROUP
    OBJECTS {
        frResPartPortNum,
	frResPartCtrlrNum,
	frResPartRowStatus,
	frResPartNumOfLcnAvail,
	frResPartDlciLow,
	frResPartDlciHigh,
	frResPartIngrPctBW,
	frResPartEgrPctBW,
        frResPartCtrlrID
    }
    STATUS current
    DESCRIPTION
        "A collection of objects providing the
        Frame Relay Port resource partition configuration
        information."
    ::= { cwfRsrcPartMIBGroups 1 }
END
