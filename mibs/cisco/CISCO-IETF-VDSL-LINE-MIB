-- CISCO-IETF-VDSL-LINE-MIB.my : Description of managed objects for VDSL
   -- line interfaces.
   --
   -- February 2002, Kalyan R. Dharanipragada
   --
   -- Copyright (c) 1999-2002 by cisco Systems, Inc.
   -- All rights reserved.

   -- This MIB module is based on the Internet Draft
   -- draft-ietf-adslmib-vdsl-00.txt.  In terms of object syntax and
   -- semantics, the content of this Cisco MIB is the same as
   -- the corresponding Internet Draft revision except for the fact that
   -- several tables in the internet draft which were based on the draft
   -- High capacity MIB textual conventions have been left out.
   -- This Cisco MIB was created due to the "subject to change" nature
   -- of Internet Drafts. This Cisco MIB may later be deprecated, and
   -- the stable RFC, which may replace the Internet Draft, may be
   -- implemented in its place.

    CISCO-IETF-VDSL-LINE-MIB DEFINITIONS ::= BEGIN

    IMPORTS

    MODULE-IDENTITY,
    OBJECT-TYPE,
    Gauge32,
    Integer32,
    NOTIFICATION-TYPE                    FROM SNMPv2-SMI
    TEXTUAL-CONVENTION,
    RowStatus,
    TruthValue                      FROM SNMPv2-TC
    MODULE-COMPLIANCE,
    OBJECT-GROUP,
    NOTIFICATION-GROUP              FROM SNMPv2-CONF
    ifIndex                         FROM IF-MIB
    SnmpAdminString                 FROM SNMP-FRAMEWORK-MIB
    ciscoExperiment                 FROM CISCO-SMI;

    ciscoIetfVdslMIB MODULE-IDENTITY
    LAST-UPDATED "200204180000Z" -- April 18, 2002
    ORGANIZATION "Cisco Systems"
    CONTACT-INFO "Cisco Systems
                    Customer Service

                    Postal: 170 W Tasman Drive
                    San Jose, CA 95134

                    Tel: +1 800 553-NETS

                    E-mail: cs-2900lre@cisco.com"
    DESCRIPTION
        "The MIB module defining objects for the management of a pair of
        VDSL modems at each end of the VDSL line.  Each VDSL line has
        an entry in an ifTable.

        An agent may reside at either end of the VDSL line however the
        MIB is designed to require no management communication between
        them beyond that inherent in the low-level VDSL line protocol.
        The agent may monitor and control this protocol for its needs.

        VDSL lines may support optional Fast or Interleaved channels.
        If these are supported, additional entries corresponding to the
        supported channels must be created in the ifTable. Thus a VDSL
        line that supports both channels will have three entries in the
        ifTable, one for each physical, fast, and interleaved, whose
        ifType values are equal to vdsl(97), fast(125), and
        interleaved(124), respectively. The ifStackTable is used to
        represent the relationship between the entries.

        Naming Conventions:
            Vtuc -- (VTUC) modem at near (Central) end of line
            Vtur -- (VTUR) modem at Remote end of line
            Vtu  -- One of either Vtuc or Vtur
            Curr -- Current
            Prev -- Previous
            Atn  -- Attenuation
            ES   -- Errored Second.
            LCS  -- Line Code Specific
            Lof  -- Loss of Frame
            Lol  -- Loss of Link
            Los  -- Loss of Signal
            Lpr  -- Loss of Power
            xyzs -- interval of Seconds in which xyz occurs
                    (e.g., xyz=Lof, Los, Lpr)
            Max  -- Maximum
            Mgn  -- Margin
            Min  -- Minimum
            Psd  -- Power Spectral Density
            Snr  -- Signal to Noise Ratio
            Tx   -- Transmit
            Blks -- Blocks, a data unit, see cvdslVtuXChanCrcBlockLength
            "


    REVISION "200204180000Z" -- April 18, 2002
    DESCRIPTION "This is a cisco version of the Internet draft"

    ::= { ciscoExperiment 87 }

    cvdslLineMib    OBJECT IDENTIFIER ::= { ciscoIetfVdslMIB 1 }
    cvdslMibObjects OBJECT IDENTIFIER ::= { cvdslLineMib 1 }

    --
    -- textual conventions used in this MIB
    --

    CVdslLineCodingType ::= TEXTUAL-CONVENTION
        STATUS       current
        DESCRIPTION
            "This data type is used as the syntax for the VDSL
             Line Code."
        SYNTAX  INTEGER
            {
            other(1), -- none of the following
            mcm(2),   -- Multiple Carrier Modulation
            scm(3)    -- Single Carrier Modulation
            }

    CVdslLineEntity ::= TEXTUAL-CONVENTION
        STATUS       current
        DESCRIPTION
            "Identifies a modem as being either Vtuc or Vtur.  A
            VDSL line consists of two modems, a Vtuc and a Vtur."
        SYNTAX  INTEGER
            {
            vtuc(1), -- central site modem
            vtur(2)  -- remote site modem
            }

    --
    -- objects
    --

    cvdslLineTable OBJECT-TYPE
        SYNTAX       SEQUENCE OF CvdslLineEntry
        MAX-ACCESS   not-accessible
        STATUS       current
        DESCRIPTION
            "This table includes common attributes describing
            both ends of the line.  It is required for all VDSL
            physical interfaces.  VDSL physical interfaces are
            those ifEntries where ifType is equal to vdsl(97)."
        ::= { cvdslMibObjects 1 }

    cvdslLineEntry OBJECT-TYPE
        SYNTAX       CvdslLineEntry
        MAX-ACCESS   not-accessible
        STATUS       current
        DESCRIPTION  "An entry in the cvdslLineTable."
        INDEX        { ifIndex }
        ::= { cvdslLineTable 1 }

    CvdslLineEntry ::=
        SEQUENCE
            {
            cvdslLineCoding                         CVdslLineCodingType,
            cvdslLineType                           INTEGER,
            cvdslLineConfProfile                    Integer32,
            cvdslLineAlarmConfProfile               Integer32
            }

    cvdslLineCoding OBJECT-TYPE
        SYNTAX       CVdslLineCodingType
        MAX-ACCESS   read-only
        STATUS       current
        DESCRIPTION
            "Specifies the VDSL coding type used on this line."
        ::= { cvdslLineEntry 1 }

    cvdslLineType OBJECT-TYPE
        SYNTAX       INTEGER
            {
            noChannel(1),         -- no channels exist
            fastOnly(2),          -- fast channel only
            slowOnly(3),          -- slow channel only
            either(4),            -- either fast or slow channel exist
            both(5)               -- both fast and slow channels exist
            }
        MAX-ACCESS   read-only
        STATUS       current
        DESCRIPTION
            "Defines the type of VDSL physical line
            entity that exists, by defining whether and how
            the line is channelized.  If the line is channelized,
            the value will be other than noChannel(1).  This
            object defines which channel type(s) are supported.

            In the case that the line is channelized, the manager
            can use the ifStackTable to determine the ifIndex for
            the associated channel(s)."
        ::= { cvdslLineEntry 2 }

    cvdslLineConfProfile OBJECT-TYPE
        SYNTAX       Integer32
        MAX-ACCESS   read-write
        STATUS       current
        DESCRIPTION
            "The value of this object identifies the rows
            in the VDSL Line Configuration Profile Table,
            ( cvdslLineConfProfileTable ), which apply for this
            VDSL line, and channels if applicable."
        ::= { cvdslLineEntry 3 }

    cvdslLineAlarmConfProfile OBJECT-TYPE
        SYNTAX       Integer32
        MAX-ACCESS   read-write
        STATUS       current
        DESCRIPTION
            "The value of this object identifies the rows in the VDSL
            Line Alarm Configuration Profile Table,
            ( cvdslLineAlarmConfProfileTable ), which apply to this
            VDSL line, and channels if applicable."
        ::= { cvdslLineEntry 4 }

    cvdslPhysTable OBJECT-TYPE
        SYNTAX       SEQUENCE OF CvdslPhysEntry
        MAX-ACCESS   not-accessible
        STATUS       current
        DESCRIPTION
            "This table provides one row for each Vtu.  Each row
            contains the Physical Layer Parameters table for that
            Vtu.  VDSL physical interfaces are those ifEntries where
            ifType is equal to vdsl(97)."
        ::= { cvdslMibObjects 2 }

    cvdslPhysEntry OBJECT-TYPE
        SYNTAX       CvdslPhysEntry
        MAX-ACCESS   not-accessible
        STATUS       current
        DESCRIPTION  "An entry in the cvdslPhysTable."
        INDEX        { ifIndex, cvdslPhysSide }
        ::= { cvdslPhysTable 1 }

    CvdslPhysEntry ::=
        SEQUENCE
            {
            cvdslPhysSide                           CVdslLineEntity,
            cvdslInvSerialNumber                    SnmpAdminString,
            cvdslInvVendorID                        SnmpAdminString,
            cvdslInvVersionNumber                   SnmpAdminString,
            cvdslCurrSnrMgn                         INTEGER,
            cvdslCurrAtn                            Gauge32,
            cvdslCurrStatus                         BITS,
            cvdslCurrOutputPwr                      INTEGER,
            cvdslCurrAttainableRate                 Gauge32
            }

    cvdslPhysSide OBJECT-TYPE
        SYNTAX       CVdslLineEntity
        MAX-ACCESS   not-accessible
        STATUS       current
        DESCRIPTION
            "Identifies whether the modem is the Vtuc or Vtur."
        ::= { cvdslPhysEntry 1 }

    cvdslInvSerialNumber OBJECT-TYPE
        SYNTAX       SnmpAdminString(SIZE (0..32))
        MAX-ACCESS   read-only
        STATUS       current
        DESCRIPTION
            "The vendor specific string that identifies the
            vendor equipment."
        ::= { cvdslPhysEntry 2 }

    cvdslInvVendorID OBJECT-TYPE
        SYNTAX       SnmpAdminString (SIZE (0..16))
        MAX-ACCESS   read-only
        STATUS       current
        DESCRIPTION
            "The vendor ID code is a copy of the binary vendor
            identification field defined by the PHY[10] and
            expressed as readable characters."
        ::= { cvdslPhysEntry 3 }

    cvdslInvVersionNumber OBJECT-TYPE
        SYNTAX       SnmpAdminString (SIZE (0..16))
        MAX-ACCESS   read-only
        STATUS       current
        DESCRIPTION
            "The vendor specific version number sent by this Vtu
            as part of the initialization messages.  It is a copy
            of the binary version number field defined by the
            PHY[10] and expressed as readable characters."
        ::= { cvdslPhysEntry 4 }

    cvdslCurrSnrMgn OBJECT-TYPE
        SYNTAX       INTEGER(-640..640)
        UNITS        "tenth dB"
        MAX-ACCESS   read-only
        STATUS       current
        DESCRIPTION
            "Noise Margin as seen by this Vtu with respect to its
            received signal in tenth dB."
         ::= { cvdslPhysEntry 5 }

    cvdslCurrAtn OBJECT-TYPE
        SYNTAX       Gauge32(0..630)
        UNITS        "tenth dB"
        MAX-ACCESS   read-only
        STATUS       current
        DESCRIPTION
            "Measured difference in the total power transmitted by
            the peer Vtu and the total power received by this Vtu."
         ::= { cvdslPhysEntry 6 }

    cvdslCurrStatus OBJECT-TYPE
        SYNTAX       BITS
            {
            noDefect(0),
            lossOfFraming(1),
            lossOfSignal(2),
            lossOfPower(3),
            lossOfSignalQuality(4),
            lossOfLink(5),
            dataInitFailure(6),
            configInitFailure(7),
            protocolInitFailure(8),
            noPeerVtuPresent(9)
            }
        MAX-ACCESS  read-only
        STATUS      current
        DESCRIPTION
            "Indicates current state of the Vtu line.  This is a
            bit-map of possible conditions.  The various bit
            positions are:

            0   noDefect             There no defects on the line

            1   lossOfFraming        Vtu failure due to not receiving
                                     valid frame.

            2   lossOfSignal         Vtu failure due to not receiving
                                     signal.

            3   lossOfPower          Vtu failure due to loss of power.

            4   lossOfSignalQuality  Loss of Signal Quality is declared
                                     when the Noise Margin falls below
                                     the Minimum Noise Margin, or the
                                     bit-error-rate exceeds 10^-7.

            5   lossOfLink           Vtu failure due to inability to
                                     link with peer Vtu.

            6   dataInitFailure      Vtu failure during initialization
                                     due to bit errors corrupting
                                     startup exchange data.

            7   configInitFailure    Vtu failure during initialization
                                     due to peer Vtu not able to support
                                     requested configuration.

            8   protocolInitFailure  Vtu failure during initialization
                                     due to incompatible protocol used
                                     by the peer Vtu.

            9   noPeerVtuPresent     Vtu failure during initialization
                                     due to no activation sequence
                                     detected from peer Vtu.

            This is intended to supplement ifOperStatus."
         ::= { cvdslPhysEntry 7 }

    cvdslCurrOutputPwr OBJECT-TYPE
        SYNTAX       INTEGER (-310..310)
        UNITS        "tenth dBm"
        MAX-ACCESS   read-only
        STATUS       current
        DESCRIPTION
            "Measured total output power transmitted by this ATU.
            This is the measurement that was reported during
            the last activation sequence."
        ::= { cvdslPhysEntry 8 }

    cvdslCurrAttainableRate OBJECT-TYPE
        SYNTAX       Gauge32
        UNITS        "bps"
        MAX-ACCESS   read-only
        STATUS       current
        DESCRIPTION
            "Indicates the maximum currently attainable data rate
            by the Vtu.  This value will be equal or greater than
            the current line rate."
        ::= { cvdslPhysEntry 9 }

    cvdslChanTable OBJECT-TYPE
        SYNTAX       SEQUENCE OF CvdslChanEntry
        MAX-ACCESS   not-accessible
        STATUS       current
        DESCRIPTION
            "This table provides one row for each Vtu channel.
            VDSL channel interfaces are those ifEntries where
            ifType is equal to interleave(124) or fast(125)."
        ::= { cvdslMibObjects 3 }

    cvdslChanEntry OBJECT-TYPE
        SYNTAX       CvdslChanEntry
        MAX-ACCESS   not-accessible
        STATUS       current
        DESCRIPTION
            "An entry in the cvdslChanTable."
        INDEX        { ifIndex, cvdslPhysSide }
        ::= { cvdslChanTable 1 }

    CvdslChanEntry ::=
        SEQUENCE
            {
            cvdslChanInterleaveDelay                Gauge32,
            cvdslChanCrcBlockLength                 Gauge32
            }

    cvdslChanInterleaveDelay OBJECT-TYPE
        SYNTAX       Gauge32
        UNITS        "milli-seconds"
        MAX-ACCESS   read-only
        STATUS       current
        DESCRIPTION
            "Interleave Delay for this channel.

            Interleave delay applies only to the interleave
            (slow) channel and defines the mapping (relative
            spacing) between subsequent input bytes at the
            interleaver input and their placement in the bit
            stream at the interleaver output.  Larger numbers
            provide greater separation between consecutive
            input bytes in the output bit stream allowing for
            improved impulse noise immunity at the expense of
            payload latency.

            In the case where the ifType is fast(125), the
            object is not instantiated."
        ::= { cvdslChanEntry 1 }

    cvdslChanCrcBlockLength OBJECT-TYPE
        SYNTAX       Gauge32
        UNITS        "byte"
        MAX-ACCESS   read-only
        STATUS       current
        DESCRIPTION
            "Indicates the length of the channel data-block
            on which the CRC operates."
        ::= { cvdslChanEntry 2 }


-- ::= { cvdslMibObjects 4 } not used, cvdslPerfDataTable removed
-- ::= { cvdslMibObjects 5 } not used, cvdslPerfIntervalTable removed
-- ::= { cvdslMibObjects 6 } not used, cvdslChanPerfDataTable removed
-- ::= { cvdslMibObjects 7 } not used, cvdslChanIntervalTable removed


    cvdslLineConfProfileTable OBJECT-TYPE
        SYNTAX         SEQUENCE OF CvdslLineConfProfileEntry
        MAX-ACCESS     not-accessible
        STATUS         current
        DESCRIPTION
            "This table contains information on the VDSL line
            configuration.  One entry in this table reflects a
            profile defined by a manager which can be used to
            configure the VDSL line."
        ::= { cvdslMibObjects 8 }

    cvdslLineConfProfileEntry OBJECT-TYPE
        SYNTAX         CvdslLineConfProfileEntry
        MAX-ACCESS     not-accessible
        STATUS         current
        DESCRIPTION
            "Each entry consists of a list of parameters that
            represents the configuration of a VDSL modem.  A
            default profile with an index of 1 will always exist
            and its parameters will be set to vendor specific
            values, unless otherwise specified in this document."
        INDEX { cvdslPhysSide, cvdslLineConfProfileIndex }
        ::= { cvdslLineConfProfileTable 1 }

    CvdslLineConfProfileEntry ::=
        SEQUENCE
            {
            cvdslLineConfProfileIndex               Integer32,
            cvdslLineConfProfileName                SnmpAdminString,
            cvdslLineConfTargetSnrMgn               INTEGER,
            cvdslLineConfTxSpeed                    INTEGER,
            cvdslLineConfRxSpeed                    INTEGER,
            cvdslLineConfProfileRowStatus           RowStatus
            }

    cvdslLineConfProfileIndex OBJECT-TYPE
        SYNTAX       Integer32 (1..2147483647)
        MAX-ACCESS   not-accessible
        STATUS       current
        DESCRIPTION
            "This object is used by the line configuration table
            in order to identify a row in that table.  The system
            will always provide a default profile whose value is 1."
        ::= { cvdslLineConfProfileEntry 1 }


    cvdslLineConfProfileName OBJECT-TYPE
        SYNTAX       SnmpAdminString (SIZE (1..32))
        MAX-ACCESS   read-create
        STATUS       current
        DESCRIPTION
            "The name for this profile as specified by a user."
        ::= { cvdslLineConfProfileEntry 2 }

    cvdslLineConfTargetSnrMgn OBJECT-TYPE
        SYNTAX       INTEGER (0..310)
        UNITS        "tenth dB"
        MAX-ACCESS   read-create
        STATUS       current
        DESCRIPTION
            "Configured Target Signal/Noise Margin.  This is the
            Noise Margin the modem must achieve with a BER of 10-7
            or better to successfully complete initialization."
        ::= { cvdslLineConfProfileEntry 3 }

    cvdslLineConfTxSpeed OBJECT-TYPE
        SYNTAX       INTEGER (1..2147483647)
        UNITS        "bits per second"
        MAX-ACCESS   read-create
        STATUS       current
        DESCRIPTION
            "Transmit speed for this modem.  The corresponding modem
            on the other end of the VDSL line will have an equal
            cvdslLineConfRxSpeed value."
        ::= { cvdslLineConfProfileEntry 4 }

    cvdslLineConfRxSpeed OBJECT-TYPE
        SYNTAX       INTEGER (1..2147483647)
        UNITS        "bits per second"
        MAX-ACCESS   read-create
        STATUS       current
        DESCRIPTION
            "Receive speed for this modem.  The corresponding modem
            on the other end of the VDSL line will have an equal
            cvdslLineConfTxSpeed value."
        ::= { cvdslLineConfProfileEntry 5 }

    cvdslLineConfProfileRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines.
            The DEFVAL profile cannot be deleted."
        ::= { cvdslLineConfProfileEntry 6 }

    --
    -- Multiple carrier modulation (MCM) configuration profile tables
    --

    cvdslLineMCMConfProfileTable OBJECT-TYPE
        SYNTAX       SEQUENCE OF CvdslLineMCMConfProfileEntry
        MAX-ACCESS   not-accessible
        STATUS       current
        DESCRIPTION
            "This table contains information on the VDSL line
            configuration.  One entry in this table reflects a
            profile defined by a manager which can be used to
            configure the VDSL line."
        ::= { cvdslMibObjects 9 }

    cvdslLineMCMConfProfileEntry OBJECT-TYPE
        SYNTAX       CvdslLineMCMConfProfileEntry
        MAX-ACCESS   not-accessible
        STATUS       current
        DESCRIPTION
            "Each entry consists of a list of parameters that
            represents the configuration of a multiple carrier
            modulation VDSL modem.    A default profile with an
            index of 1 will always exist and its parameters will
            be set to vendor specific values, unless otherwise
            specified in this document."
        INDEX { cvdslPhysSide, cvdslLineConfProfileIndex }
        ::= { cvdslLineMCMConfProfileTable 1 }

    CvdslLineMCMConfProfileEntry ::=
        SEQUENCE
            {
            cvdslMCMConfProfileTxWindowLength       INTEGER,
            cvdslMCMConfProfileRowStatus            RowStatus
            }

    cvdslMCMConfProfileTxWindowLength OBJECT-TYPE
        SYNTAX       INTEGER(1..255)
        UNITS        "samples"
        MAX-ACCESS   read-create
        STATUS       current
        DESCRIPTION
            "Specifies the length of the transmit window, counted
            in samples at the sampling rate corresponding to the
            negotiated value of N."
        ::= { cvdslLineMCMConfProfileEntry 1 }

    cvdslMCMConfProfileRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileEntry 2 }

    cvdslLineMCMConfProfileTxBandTable OBJECT-TYPE
        SYNTAX       SEQUENCE OF CvdslLineMCMConfProfileTxBandEntry
        MAX-ACCESS   not-accessible
        STATUS       current
        DESCRIPTION
            "This table contains transmit band descriptor configuration
            information for a VDSL line.  Each entry in this table
            reflects the configuration for one of possibly many bands
            with a multiple carrier modulation (MCM) VDSL line.
            These entries are defined by a manager and can be used to
            configure the VDSL line."
        ::= { cvdslMibObjects 10 }

    cvdslLineMCMConfProfileTxBandEntry OBJECT-TYPE
        SYNTAX       CvdslLineMCMConfProfileTxBandEntry
        MAX-ACCESS   not-accessible
        STATUS       current
        DESCRIPTION
            "Each entry consists of a transmit band descriptor, which
            is defined by a start and a stop tone index.

            A default profile with an index of 1 will always exist and
            its parameters will be set to vendor specific values,
            unless otherwise specified in this document."
        INDEX { cvdslPhysSide, cvdslLineConfProfileIndex,
                cvdslMCMConfProfileTxBandNumber  }
        ::= { cvdslLineMCMConfProfileTxBandTable 1 }

    CvdslLineMCMConfProfileTxBandEntry ::=
        SEQUENCE
            {
            cvdslMCMConfProfileTxBandNumber           INTEGER,
            cvdslMCMConfProfileTxBandStart            INTEGER,
            cvdslMCMConfProfileTxBandStop             INTEGER,
            cvdslMCMConfProfileTxBandRowStatus        RowStatus
            }

    cvdslMCMConfProfileTxBandNumber OBJECT-TYPE
        SYNTAX       INTEGER (1..2147483647)
        MAX-ACCESS   not-accessible
        STATUS       current
        DESCRIPTION
            "The index for this band descriptor entry."
        ::= { cvdslLineMCMConfProfileTxBandEntry 1 }

    cvdslMCMConfProfileTxBandStart OBJECT-TYPE
        SYNTAX       INTEGER (1..2147483647)
        MAX-ACCESS   read-create
        STATUS       current
        DESCRIPTION
            "Start tone index for this band."
        ::= { cvdslLineMCMConfProfileTxBandEntry 2 }

    cvdslMCMConfProfileTxBandStop OBJECT-TYPE
        SYNTAX       INTEGER (1..2147483647)
        MAX-ACCESS   read-create
        STATUS       current
        DESCRIPTION
            "Stop tone index for this band."
        ::= { cvdslLineMCMConfProfileTxBandEntry 3 }

    cvdslMCMConfProfileTxBandRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileTxBandEntry 4 }

    cvdslLineMCMConfProfileRxBandTable OBJECT-TYPE
        SYNTAX       SEQUENCE OF CvdslLineMCMConfProfileRxBandEntry
        MAX-ACCESS   not-accessible
        STATUS       current
        DESCRIPTION
            "This table contains receive band descriptor configuration
            information for a VDSL line.  Each entry in this table
            reflects the configuration for one of possibly many bands
            with a multiple carrier modulation (MCM) VDSL line.
            These entries are defined by a manager and can be used to
            configure the VDSL line."
        ::= { cvdslMibObjects 11 }

    cvdslLineMCMConfProfileRxBandEntry OBJECT-TYPE
        SYNTAX       CvdslLineMCMConfProfileRxBandEntry
        MAX-ACCESS   not-accessible
        STATUS       current
        DESCRIPTION
            "Each entry consists of a transmit band descriptor, which
            defines the start and stop bands and the power spectral
            density (PSD) for that band.

            A default profile with an index of 1 will always exist and
            its parameters will be set to vendor specific values,
            unless otherwise specified in this document."
        INDEX { cvdslPhysSide, cvdslLineConfProfileIndex,
                cvdslMCMConfProfileRxBandNumber }
        ::= { cvdslLineMCMConfProfileRxBandTable 1 }

    CvdslLineMCMConfProfileRxBandEntry ::=
        SEQUENCE
            {
            cvdslMCMConfProfileRxBandNumber           INTEGER,
            cvdslMCMConfProfileRxBandStart            INTEGER,
            cvdslMCMConfProfileRxBandStop             INTEGER,
            cvdslMCMConfProfileRxBandRowStatus        RowStatus
            }

    cvdslMCMConfProfileRxBandNumber OBJECT-TYPE
        SYNTAX       INTEGER (1..2147483647)
        MAX-ACCESS   not-accessible
        STATUS       current
        DESCRIPTION
            "The index for this band descriptor entry."
        ::= { cvdslLineMCMConfProfileRxBandEntry 1 }

    cvdslMCMConfProfileRxBandStart OBJECT-TYPE
        SYNTAX       INTEGER (1..2147483647)
        MAX-ACCESS   read-create
        STATUS       current
        DESCRIPTION
            "Start tone index for this band."
        ::= { cvdslLineMCMConfProfileRxBandEntry 2 }

    cvdslMCMConfProfileRxBandStop OBJECT-TYPE
        SYNTAX       INTEGER (1..2147483647)
        MAX-ACCESS   read-create
        STATUS       current
        DESCRIPTION
            "Stop tone index for this band."
        ::= { cvdslLineMCMConfProfileRxBandEntry 3 }

    cvdslMCMConfProfileRxBandRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileRxBandEntry 4 }

    cvdslLineMCMConfProfileTxPSDTable OBJECT-TYPE
        SYNTAX       SEQUENCE OF CvdslLineMCMConfProfileTxPSDEntry
        MAX-ACCESS   not-accessible
        STATUS       current
        DESCRIPTION
            "This table contains transmit PSD mask descriptor
            configuration information for a VDSL line.  Each entry in
            this table reflects the configuration for one tone within
            a multiple carrier modulation (MCM) VDSL line.  These
            entries are defined by a manager and can be used to
            configure the VDSL line."
        ::= { cvdslMibObjects 12 }

    cvdslLineMCMConfProfileTxPSDEntry OBJECT-TYPE
        SYNTAX       CvdslLineMCMConfProfileTxPSDEntry
        MAX-ACCESS   not-accessible
        STATUS       current
        DESCRIPTION
            "Each entry consists of a transmit PSD mask descriptor,
            which defines the power spectral density (PSD) for a tone.

            A default profile with an index of 1 will always exist and
            its parameters will be set to vendor specific values,
            unless otherwise specified in this document."
        INDEX { cvdslPhysSide, cvdslLineConfProfileIndex,
                cvdslMCMConfProfileTxPSDNumber  }
        ::= { cvdslLineMCMConfProfileTxPSDTable 1 }

    CvdslLineMCMConfProfileTxPSDEntry ::=
        SEQUENCE
            {
            cvdslMCMConfProfileTxPSDNumber            INTEGER,
            cvdslMCMConfProfileTxPSDTone              INTEGER,
            cvdslMCMConfProfileTxPSDPSD               INTEGER,
            cvdslMCMConfProfileTxPSDRowStatus         RowStatus
            }

    cvdslMCMConfProfileTxPSDNumber OBJECT-TYPE
        SYNTAX       INTEGER (1..2147483647)
        MAX-ACCESS   not-accessible
        STATUS       current
        DESCRIPTION
            "The index for this mask descriptor entry."
        ::= { cvdslLineMCMConfProfileTxPSDEntry 1 }

    cvdslMCMConfProfileTxPSDTone OBJECT-TYPE
        SYNTAX       INTEGER (1..2147483647)
        MAX-ACCESS   read-create
        STATUS       current
        DESCRIPTION
            "The tone index for which the PSD is being specified."
        ::= { cvdslLineMCMConfProfileTxPSDEntry 2 }

    cvdslMCMConfProfileTxPSDPSD OBJECT-TYPE
        SYNTAX       INTEGER (1..2147483647)
        UNITS        "0.5dB"
        MAX-ACCESS   read-create
        STATUS       current
        DESCRIPTION
            "Power Spectral Density level in steps of 0.5dB with
            an offset of -140dbm/Hz."
        ::= { cvdslLineMCMConfProfileTxPSDEntry 3 }

    cvdslMCMConfProfileTxPSDRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileTxPSDEntry 4 }

    cvdslLineMCMConfProfileMaxTxPSDTable OBJECT-TYPE
        SYNTAX       SEQUENCE OF CvdslLineMCMConfProfileMaxTxPSDEntry
        MAX-ACCESS   not-accessible
        STATUS       current
        DESCRIPTION
            "This table contains transmit maximum PSD mask descriptor
            configuration information for a VDSL line.  Each entry in
            this table reflects the configuration for one tone within
            a multiple carrier modulation (MCM) VDSL modem.  These
            entries are defined by a manager and can be used to
            configure the VDSL line."
        ::= { cvdslMibObjects 13 }

    cvdslLineMCMConfProfileMaxTxPSDEntry OBJECT-TYPE
        SYNTAX       CvdslLineMCMConfProfileMaxTxPSDEntry
        MAX-ACCESS   not-accessible
        STATUS       current
        DESCRIPTION
            "Each entry consists of a transmit PSD mask descriptor,
            which defines the maximum power spectral density (PSD)
            for a tone.

            A default profile with an index of 1 will always exist and
            its parameters will be set to vendor specific values,
            unless otherwise specified in this document."
        INDEX { cvdslPhysSide, cvdslLineConfProfileIndex,
                cvdslMCMConfProfileMaxTxPSDNumber }
        ::= { cvdslLineMCMConfProfileMaxTxPSDTable 1 }

    CvdslLineMCMConfProfileMaxTxPSDEntry ::=
        SEQUENCE
            {
            cvdslMCMConfProfileMaxTxPSDNumber            INTEGER,
            cvdslMCMConfProfileMaxTxPSDTone              INTEGER,
            cvdslMCMConfProfileMaxTxPSDPSD               INTEGER,
            cvdslMCMConfProfileMaxTxPSDRowStatus         RowStatus
            }

    cvdslMCMConfProfileMaxTxPSDNumber OBJECT-TYPE
        SYNTAX       INTEGER (1..2147483647)
        MAX-ACCESS   not-accessible
        STATUS       current
        DESCRIPTION
            "The index for this band descriptor entry."
        ::= { cvdslLineMCMConfProfileMaxTxPSDEntry 1 }

    cvdslMCMConfProfileMaxTxPSDTone OBJECT-TYPE
        SYNTAX       INTEGER (1..2147483647)
        MAX-ACCESS   read-create
        STATUS       current
        DESCRIPTION
            "The tone index for which the PSD is being specified."
        ::= { cvdslLineMCMConfProfileMaxTxPSDEntry 2 }

    cvdslMCMConfProfileMaxTxPSDPSD OBJECT-TYPE
        SYNTAX       INTEGER (1..2147483647)
        UNITS        "0.5dB"
        MAX-ACCESS   read-create
        STATUS       current
        DESCRIPTION
            "Power Spectral Density level in steps of 0.5dB with
            an offset of -140dbm/Hz."
        ::= { cvdslLineMCMConfProfileMaxTxPSDEntry 3 }

    cvdslMCMConfProfileMaxTxPSDRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileMaxTxPSDEntry 4 }

    cvdslLineMCMConfProfileMaxRxPSDTable OBJECT-TYPE
        SYNTAX       SEQUENCE OF CvdslLineMCMConfProfileMaxRxPSDEntry
        MAX-ACCESS   not-accessible
        STATUS       current
        DESCRIPTION
            "This table contains maximum receive PSD mask descriptor
            configuration information for a VDSL line.  Each entry in
            this table reflects the configuration for one tone within
            a multiple carrier modulation (MCM) VDSL modem.  These
            entries are defined by a manager and can be used to
            configure the VDSL line."
        ::= { cvdslMibObjects 14 }

    cvdslLineMCMConfProfileMaxRxPSDEntry OBJECT-TYPE
        SYNTAX       CvdslLineMCMConfProfileMaxRxPSDEntry
        MAX-ACCESS   not-accessible
        STATUS       current
        DESCRIPTION
            "Each entry consists of a transmit PSD mask descriptor,
            which defines the power spectral density (PSD) for a
            tone.

            A default profile with an index of 1 will always exist and
            its parameters will be set to vendor specific values,
            unless otherwise specified in this document."
        INDEX { cvdslPhysSide, cvdslLineConfProfileIndex,
                cvdslMCMConfProfileMaxRxPSDNumber }
        ::= { cvdslLineMCMConfProfileMaxRxPSDTable 1 }

    CvdslLineMCMConfProfileMaxRxPSDEntry ::=
        SEQUENCE
            {
            cvdslMCMConfProfileMaxRxPSDNumber            INTEGER,
            cvdslMCMConfProfileMaxRxPSDTone              INTEGER,
            cvdslMCMConfProfileMaxRxPSDPSD               INTEGER,
            cvdslMCMConfProfileMaxRxPSDRowStatus         RowStatus
            }

    cvdslMCMConfProfileMaxRxPSDNumber OBJECT-TYPE
        SYNTAX       INTEGER (1..2147483647)
        MAX-ACCESS   not-accessible
        STATUS       current
        DESCRIPTION
            "The index for this band descriptor entry."
        ::= { cvdslLineMCMConfProfileMaxRxPSDEntry 1 }

    cvdslMCMConfProfileMaxRxPSDTone OBJECT-TYPE
        SYNTAX       INTEGER (1..2147483647)
        MAX-ACCESS   read-create
        STATUS       current
        DESCRIPTION
            "The tone index for which the PSD is being specified."
        ::= { cvdslLineMCMConfProfileMaxRxPSDEntry 2 }

    cvdslMCMConfProfileMaxRxPSDPSD OBJECT-TYPE
        SYNTAX       INTEGER (1..2147483647)
        UNITS        "0.5dB"
        MAX-ACCESS   read-create
        STATUS       current
        DESCRIPTION
            "Power Spectral Density level in steps of 0.5dB with
            an offset of -140dbm/Hz."
        ::= { cvdslLineMCMConfProfileMaxRxPSDEntry 3 }

    cvdslMCMConfProfileMaxRxPSDRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineMCMConfProfileMaxRxPSDEntry 4 }

    --
    -- Single carrier modulation (SCM) configuration profile table
    --

    cvdslLineSCMConfProfileTable OBJECT-TYPE
        SYNTAX       SEQUENCE OF CvdslLineSCMConfProfileEntry
        MAX-ACCESS   not-accessible
        STATUS       current
        DESCRIPTION
            "This table contains information on the VDSL line
            configuration.  One entry in this table reflects a
            profile defined by a manager which can be used to
            configure the VDSL line."
        ::= { cvdslMibObjects 15 }

    cvdslLineSCMConfProfileEntry OBJECT-TYPE
        SYNTAX       CvdslLineSCMConfProfileEntry
        MAX-ACCESS   not-accessible
        STATUS       current
        DESCRIPTION
            "Each entry consists of a list of parameters that
            represents the configuration of a single carrier
            modulation VDSL modem.

            A default profile with an index of 1 will always exist and
            its parameters will be set to vendor specific values,
            unless otherwise specified in this document."
        INDEX { cvdslPhysSide, cvdslLineConfProfileIndex }
        ::= { cvdslLineSCMConfProfileTable 1 }

    CvdslLineSCMConfProfileEntry ::=
        SEQUENCE
            {
            cvdslSCMConfProfileInterleaveDepth      INTEGER,
            cvdslSCMConfProfileFastCodewordSize     INTEGER,
            cvdslSCMConfProfileTransmitPSDMask      BITS,
            cvdslSCMConfProfileTransmitPSDLevel     INTEGER,
            cvdslSCMConfProfileSymbolRateProfile    INTEGER,
            cvdslSCMConfProfileConstellationSize    INTEGER,
            cvdslSCMConfProfileCenterFrequency      INTEGER,
            cvdslSCMConfProfileRowStatus            RowStatus
            }

    cvdslSCMConfProfileInterleaveDepth OBJECT-TYPE
        SYNTAX       INTEGER (1..2147483647)
        UNITS        "octets"
        MAX-ACCESS   read-create
        STATUS       current
        DESCRIPTION
            "Specifies the interleaving depth."
        ::= { cvdslLineSCMConfProfileEntry 1 }

    cvdslSCMConfProfileFastCodewordSize OBJECT-TYPE
        SYNTAX       INTEGER(0..180)
        UNITS        "octets"
        MAX-ACCESS   read-create
        STATUS       current
        DESCRIPTION
            "Specifies the length in octets of the fast codeword.
            A value of 0 indicates that the single latency transport
            class is to be utilized."
        ::= { cvdslLineSCMConfProfileEntry 2 }

    cvdslSCMConfProfileTransmitPSDMask OBJECT-TYPE
        SYNTAX       BITS
            {
            vendorNotch1(0),     -- vendor specific notch
            vendorNotch2(1),     -- vendor specific notch
            amateurBand30m(2),   -- amateur radio 30m band notch
            amateurBand40m(3),   -- amateur radio 40m band notch
            amateurBand80m(4),   -- amateur radio 80m band notch
            amateurBand160m(5)   -- amateur radio 160m band notch
            }
        MAX-ACCESS   read-create
        STATUS       current
        DESCRIPTION
            "The transmit power spectral density mask code."
        ::= { cvdslLineSCMConfProfileEntry 3 }

    cvdslSCMConfProfileTransmitPSDLevel OBJECT-TYPE
        SYNTAX       INTEGER (1..2147483647)
        UNITS        "dBm/Hz"
        MAX-ACCESS   read-create
        STATUS       current
        DESCRIPTION
            "The transmit power spectral density for the VDSL modem."
        ::= { cvdslLineSCMConfProfileEntry 4 }

    cvdslSCMConfProfileSymbolRateProfile OBJECT-TYPE
        SYNTAX       INTEGER (1..2147483647)
        UNITS        "kbaud"
        MAX-ACCESS   read-create
        STATUS       current
        DESCRIPTION
            "The symbol rate profile calculated as S = SR/BSR, where
            SR is the required symbol rate in kbaud, BSR  = 67.5."
        ::= { cvdslLineSCMConfProfileEntry 5 }

    cvdslSCMConfProfileConstellationSize OBJECT-TYPE
        SYNTAX       INTEGER(0..15)
        UNITS        "log2"
        MAX-ACCESS   read-create
        STATUS       current
        DESCRIPTION
            "Specifies the constellation size."
        ::= { cvdslLineSCMConfProfileEntry 6 }

    cvdslSCMConfProfileCenterFrequency OBJECT-TYPE
        SYNTAX       INTEGER(0..511)
        UNITS        "kHz"
        MAX-ACCESS   read-create
        STATUS       current
        DESCRIPTION
            "Specifies the center frequency profile K."
        ::= { cvdslLineSCMConfProfileEntry 7 }

    cvdslSCMConfProfileRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineSCMConfProfileEntry 8 }

    --
    -- Alarm configuration profile table
    --

    cvdslLineAlarmConfProfileTable OBJECT-TYPE
        SYNTAX       SEQUENCE OF CvdslLineAlarmConfProfileEntry
        MAX-ACCESS   not-accessible
        STATUS       current
        DESCRIPTION
            "This table contains information on the VDSL line alarm
            configuration.  One entry in this table reflects a profile
            defined by a manager which can be used to configure the
            VDSL line alarm thresholds."
        ::= { cvdslMibObjects 16 }

    cvdslLineAlarmConfProfileEntry OBJECT-TYPE
        SYNTAX       CvdslLineAlarmConfProfileEntry
        MAX-ACCESS   not-accessible
        STATUS       current
        DESCRIPTION
            "Each entry consists of a list of parameters that
            represents the configuration of a VDSL line alarm
            profile.
            A default profile with an index of 1 will always exist and
            its parameters will be set to vendor specific values,
            unless otherwise specified in this document."
        INDEX { cvdslPhysSide, cvdslLineAlarmConfProfileIndex }
        ::= { cvdslLineAlarmConfProfileTable 1 }

    CvdslLineAlarmConfProfileEntry ::=
        SEQUENCE
            {
            cvdslLineAlarmConfProfileIndex        Integer32,
            cvdslLineAlarmConfProfileName         SnmpAdminString,
            cvdslInitFailureNotificationEnable    TruthValue,
            cvdslLineAlarmConfProfileRowStatus    RowStatus
            }
    cvdslLineAlarmConfProfileIndex OBJECT-TYPE
        SYNTAX       Integer32 (1..2147483647)
        MAX-ACCESS   not-accessible
        STATUS       current
        DESCRIPTION
            "This object is used by the line alarm configuration table
            in order to identify a row in that table.  The system will
            always provide a default profile whose index is 1."
        ::= { cvdslLineAlarmConfProfileEntry 1 }


    cvdslLineAlarmConfProfileName OBJECT-TYPE
        SYNTAX       SnmpAdminString (SIZE (1..32))
        MAX-ACCESS   read-create
        STATUS       current
        DESCRIPTION
            "The name for this profile as specified by a user."
        ::= { cvdslLineAlarmConfProfileEntry 2 }

    cvdslInitFailureNotificationEnable OBJECT-TYPE
        SYNTAX       TruthValue
        MAX-ACCESS   read-create
        STATUS       current
        DESCRIPTION
            "This object specifies if a cvdslInitFailureNotification
            notification will be generated if an initialization
            failure occurs."
        ::= { cvdslLineAlarmConfProfileEntry 3 }

    cvdslLineAlarmConfProfileRowStatus OBJECT-TYPE
        SYNTAX       RowStatus
        MAX-ACCESS   read-create
        STATUS       current
        DESCRIPTION
            "This object is used to create a new row or modify or
            delete an existing row in this table.

            A profile activated by setting this object to `active'.
            When `active' is set, the system will validate the profile.

            Before a profile can be deleted or taken out of
            service, (by setting this object to `destroy' or
            `outOfService') it must be first unreferenced
            from all associated lines."
        ::= { cvdslLineAlarmConfProfileEntry 4 }

    -- Notification definitions

    cvdslNotifications OBJECT IDENTIFIER ::= { cvdslLineMib 0 }

    cvdslInitFailureNotification NOTIFICATION-TYPE
        OBJECTS       {
                      cvdslCurrStatus
                      }
        STATUS        current
        DESCRIPTION
            "Vtu initialization failed.  See cvdslCurrStatus for
            potential reasons."
        ::= { cvdslNotifications 1 }

    -- conformance information

    cvdslConformance OBJECT IDENTIFIER ::= { cvdslLineMib 3 }
    cvdslGroups OBJECT IDENTIFIER ::= { cvdslConformance 1 }
    cvdslCompliances OBJECT IDENTIFIER ::= { cvdslConformance 2 }

    cvdslLineMibCompliance MODULE-COMPLIANCE
        STATUS  current
        DESCRIPTION
            "The compliance statement for SNMP entities which
            manage VDSL interfaces."

        MODULE  -- this module
        MANDATORY-GROUPS
            {
            cvdslGroup
            }

        GROUP       cvdslMCMGroup
        DESCRIPTION
            "This group is mandatory for VDSL Lines which
            utilize multiple carrier modulation.

            This group should not be implemented for VDSL lines
            which utilize single carrier modulation."

        GROUP       cvdslSCMGroup
        DESCRIPTION
            "This group is mandatory for VDSL lines which
            utilize single carrier modulation.

            This group should not be implemented for VDSL lines
            which utilize multiple carrier modulation"
        ::= { cvdslCompliances 1 }

    -- units of conformance

        cvdslGroup OBJECT-GROUP
            OBJECTS
                {
                cvdslLineCoding,
                cvdslLineType,
                cvdslLineConfProfile,
                cvdslLineAlarmConfProfile,
                cvdslInvSerialNumber,
                cvdslInvVendorID,
                cvdslInvVersionNumber,
                cvdslCurrSnrMgn,
                cvdslCurrAtn,
                cvdslCurrStatus,
                cvdslCurrOutputPwr,
                cvdslCurrAttainableRate,
                cvdslChanInterleaveDelay,
                cvdslChanCrcBlockLength,
                cvdslLineConfProfileName,
                cvdslLineConfTargetSnrMgn,
                cvdslLineConfTxSpeed,
                cvdslLineConfRxSpeed,
                cvdslLineConfProfileRowStatus,
                cvdslLineAlarmConfProfileName,
                cvdslInitFailureNotificationEnable,
                cvdslLineAlarmConfProfileRowStatus
                }
            STATUS     current
            DESCRIPTION
                "A collection of objects providing information about
                 a VDSL Line."
            ::= { cvdslGroups 1 }

        cvdslMCMGroup OBJECT-GROUP
             OBJECTS
                {
                cvdslMCMConfProfileTxWindowLength,
                cvdslMCMConfProfileRowStatus,
                cvdslMCMConfProfileTxBandStart,
                cvdslMCMConfProfileTxBandStop,
                cvdslMCMConfProfileTxBandRowStatus,
                cvdslMCMConfProfileRxBandStart,
                cvdslMCMConfProfileRxBandStop,
                cvdslMCMConfProfileRxBandRowStatus,
                cvdslMCMConfProfileTxPSDTone,
                cvdslMCMConfProfileTxPSDPSD,
                cvdslMCMConfProfileTxPSDRowStatus,
                cvdslMCMConfProfileMaxTxPSDTone,
                cvdslMCMConfProfileMaxTxPSDPSD,
                cvdslMCMConfProfileMaxTxPSDRowStatus,
                cvdslMCMConfProfileMaxRxPSDTone,
                cvdslMCMConfProfileMaxRxPSDPSD,
                cvdslMCMConfProfileMaxRxPSDRowStatus
                }
             STATUS     current
             DESCRIPTION
                 "A collection of objects providing configuration
                 information for a VDSL line based upon multiple carrier
                 modulation modem."
         ::= { cvdslGroups 2 }

        cvdslSCMGroup    OBJECT-GROUP
            OBJECTS
                {
                cvdslSCMConfProfileInterleaveDepth,
                cvdslSCMConfProfileFastCodewordSize,
                cvdslSCMConfProfileTransmitPSDMask,
                cvdslSCMConfProfileTransmitPSDLevel,
                cvdslSCMConfProfileSymbolRateProfile,
                cvdslSCMConfProfileConstellationSize,
                cvdslSCMConfProfileCenterFrequency,
                cvdslSCMConfProfileRowStatus
                }
            STATUS      current
            DESCRIPTION
                 "A collection of objects providing configuration
                 information for a VDSL line based upon single carrier
                 modulation modem."
        ::= { cvdslGroups 3 }

        cvdslNotificationGroup    NOTIFICATION-GROUP
            NOTIFICATIONS
                {
                cvdslInitFailureNotification
                }
            STATUS      current
            DESCRIPTION
                 "This group supports notifications of significant
                 conditions associated with VDSL Lines."
        ::= { cvdslGroups 4 }

    END
