-- *********************************************************************
-- CISCO-FIREPOWER-LSMAINT-MIB.my
--
-- MIB representation of the Cisco Firepower
-- LSMAINT management information model package
--
-- Created March 2020 by Charles Bullis
--
-- Copyright (c) 2005-2020 Cisco Systems, Inc. All rights reserved.
--
-- *********************************************************************

CISCO-FIREPOWER-LSMAINT-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprLsConfigIssues,
    CfprLsmaintAckChangeDetails,
    CfprLsmaintAckChanges,
    CfprLsmaintAckDisr,
    CfprLsmaintChangeMode,
    CfprPolicyPolicyOwner,
    CfprTrigAckMode,
    CfprTrigAckOperState,
    CfprTrigAckPrevOperState,
    CfprTrigAdminState
        FROM CISCO-FIREPOWER-TC-MIB;

cfprLsmaintObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        LSMAINT management information model package"
    ::= { ciscoFirepowerMIBObjects 48 }

cfprLsmaintAckTable OBJECT-TYPE
    SYNTAX           SEQUENCE OF CfprLsmaintAckEntry
    MAX-ACCESS       not-accessible
    STATUS           current
    DESCRIPTION
        "Cisco Firepower lsmaint:Ack managed object table"
    ::= { cfprLsmaintObjects 1 }

cfprLsmaintAckEntry OBJECT-TYPE
    SYNTAX           CfprLsmaintAckEntry
    MAX-ACCESS       not-accessible
    STATUS           current
    DESCRIPTION
        "Entry for the cfprLsmaintAckTable table."
    INDEX { cfprLsmaintAckInstanceId }
    ::= { cfprLsmaintAckTable 1 }

CfprLsmaintAckEntry ::= SEQUENCE {
    cfprLsmaintAckInstanceId                                         CfprManagedObjectId,
    cfprLsmaintAckDn                                                 CfprManagedObjectDn,
    cfprLsmaintAckRn                                                 SnmpAdminString,
    cfprLsmaintAckAcked                                              DateAndTime,
    cfprLsmaintAckAckedBy                                            SnmpAdminString,
    cfprLsmaintAckAdminState                                         CfprTrigAdminState,
    cfprLsmaintAckAutoDelete                                         TruthValue,
    cfprLsmaintAckChangeBy                                           SnmpAdminString,
    cfprLsmaintAckChangeDetails                                      CfprLsmaintAckChangeDetails,
    cfprLsmaintAckChangeMode                                         CfprLsmaintChangeMode,
    cfprLsmaintAckChanges                                            CfprLsmaintAckChanges,
    cfprLsmaintAckConfigIssues                                       CfprLsConfigIssues,
    cfprLsmaintAckDeploymentMode                                     CfprTrigAckMode,
    cfprLsmaintAckDescr                                              SnmpAdminString,
    cfprLsmaintAckDisr                                               CfprLsmaintAckDisr,
    cfprLsmaintAckIgnoreCap                                          TruthValue,
    cfprLsmaintAckIntId                                              SnmpAdminString,
    cfprLsmaintAckModified                                           DateAndTime,
    cfprLsmaintAckName                                               SnmpAdminString,
    cfprLsmaintAckOldPnDn                                            SnmpAdminString,
    cfprLsmaintAckOperScheduler                                      SnmpAdminString,
    cfprLsmaintAckOperState                                          CfprTrigAckOperState,
    cfprLsmaintAckPolicyLevel                                        Gauge32,
    cfprLsmaintAckPolicyOwner                                        CfprPolicyPolicyOwner,
    cfprLsmaintAckPrevOperState                                      CfprTrigAckPrevOperState,
    cfprLsmaintAckScheduler                                          SnmpAdminString
}

cfprLsmaintAckInstanceId OBJECT-TYPE
    SYNTAX       CfprManagedObjectId
    MAX-ACCESS   not-accessible
    STATUS       current
    DESCRIPTION
        "Instance identifier of the managed object."
    ::= { cfprLsmaintAckEntry 1 }

cfprLsmaintAckDn OBJECT-TYPE
    SYNTAX       CfprManagedObjectDn
    MAX-ACCESS   read-only
    STATUS       current
    DESCRIPTION
        "Cisco Firepower lsmaint:Ack:dn managed object property"
    ::= { cfprLsmaintAckEntry 2 }

cfprLsmaintAckRn OBJECT-TYPE
    SYNTAX       SnmpAdminString
    MAX-ACCESS   read-only
    STATUS       current
    DESCRIPTION
        "Cisco Firepower lsmaint:Ack:rn managed object property"
    ::= { cfprLsmaintAckEntry 3 }

cfprLsmaintAckAcked OBJECT-TYPE
    SYNTAX       DateAndTime
    MAX-ACCESS   read-only
    STATUS       current
    DESCRIPTION
        "Cisco Firepower lsmaint:Ack:acked managed object property"
    ::= { cfprLsmaintAckEntry 4 }

cfprLsmaintAckAckedBy OBJECT-TYPE
    SYNTAX       SnmpAdminString
    MAX-ACCESS   read-only
    STATUS       current
    DESCRIPTION
        "Cisco Firepower lsmaint:Ack:ackedBy managed object property"
    ::= { cfprLsmaintAckEntry 5 }

cfprLsmaintAckAdminState OBJECT-TYPE
    SYNTAX       CfprTrigAdminState
    MAX-ACCESS   read-only
    STATUS       current
    DESCRIPTION
        "Cisco Firepower lsmaint:Ack:adminState managed object property"
    ::= { cfprLsmaintAckEntry 6 }

cfprLsmaintAckAutoDelete OBJECT-TYPE
    SYNTAX       TruthValue
    MAX-ACCESS   read-only
    STATUS       current
    DESCRIPTION
        "Cisco Firepower lsmaint:Ack:autoDelete managed object property"
    ::= { cfprLsmaintAckEntry 7 }

cfprLsmaintAckChangeBy OBJECT-TYPE
    SYNTAX       SnmpAdminString
    MAX-ACCESS   read-only
    STATUS       current
    DESCRIPTION
        "Cisco Firepower lsmaint:Ack:changeBy managed object property"
    ::= { cfprLsmaintAckEntry 8 }

cfprLsmaintAckChangeDetails OBJECT-TYPE
    SYNTAX       CfprLsmaintAckChangeDetails
    MAX-ACCESS   read-only
    STATUS       current
    DESCRIPTION
        "Cisco Firepower lsmaint:Ack:changeDetails managed
        object property"
    ::= { cfprLsmaintAckEntry 9 }

cfprLsmaintAckChangeMode OBJECT-TYPE
    SYNTAX       CfprLsmaintChangeMode
    MAX-ACCESS   read-only
    STATUS       current
    DESCRIPTION
        "Cisco Firepower lsmaint:Ack:changeMode managed object property"
    ::= { cfprLsmaintAckEntry 10 }

cfprLsmaintAckChanges OBJECT-TYPE
    SYNTAX       CfprLsmaintAckChanges
    MAX-ACCESS   read-only
    STATUS       current
    DESCRIPTION
        "Cisco Firepower lsmaint:Ack:changes managed object property"
    ::= { cfprLsmaintAckEntry 11 }

cfprLsmaintAckConfigIssues OBJECT-TYPE
    SYNTAX       CfprLsConfigIssues
    MAX-ACCESS   read-only
    STATUS       current
    DESCRIPTION
        "Cisco Firepower lsmaint:Ack:configIssues managed object property"
    ::= { cfprLsmaintAckEntry 12 }

cfprLsmaintAckDeploymentMode OBJECT-TYPE
    SYNTAX       CfprTrigAckMode
    MAX-ACCESS   read-only
    STATUS       current
    DESCRIPTION
        "Cisco Firepower lsmaint:Ack:deploymentMode managed
        object property"
    ::= { cfprLsmaintAckEntry 13 }

cfprLsmaintAckDescr OBJECT-TYPE
    SYNTAX       SnmpAdminString
    MAX-ACCESS   read-only
    STATUS       current
    DESCRIPTION
        "Cisco Firepower lsmaint:Ack:descr managed object property"
    ::= { cfprLsmaintAckEntry 14 }

cfprLsmaintAckDisr OBJECT-TYPE
    SYNTAX       CfprLsmaintAckDisr
    MAX-ACCESS   read-only
    STATUS       current
    DESCRIPTION
        "Cisco Firepower lsmaint:Ack:disr managed object property"
    ::= { cfprLsmaintAckEntry 15 }

cfprLsmaintAckIgnoreCap OBJECT-TYPE
    SYNTAX       TruthValue
    MAX-ACCESS   read-only
    STATUS       current
    DESCRIPTION
        "Cisco Firepower lsmaint:Ack:ignoreCap managed object property"
    ::= { cfprLsmaintAckEntry 16 }

cfprLsmaintAckIntId OBJECT-TYPE
    SYNTAX       SnmpAdminString
    MAX-ACCESS   read-only
    STATUS       current
    DESCRIPTION
        "Cisco Firepower lsmaint:Ack:intId managed object property"
    ::= { cfprLsmaintAckEntry 17 }

cfprLsmaintAckModified OBJECT-TYPE
    SYNTAX       DateAndTime
    MAX-ACCESS   read-only
    STATUS       current
    DESCRIPTION
        "Cisco Firepower lsmaint:Ack:modified managed object property"
    ::= { cfprLsmaintAckEntry 18 }

cfprLsmaintAckName OBJECT-TYPE
    SYNTAX       SnmpAdminString
    MAX-ACCESS   read-only
    STATUS       current
    DESCRIPTION
        "Cisco Firepower lsmaint:Ack:name managed object property"
    ::= { cfprLsmaintAckEntry 19 }

cfprLsmaintAckOldPnDn OBJECT-TYPE
    SYNTAX       SnmpAdminString
    MAX-ACCESS   read-only
    STATUS       current
    DESCRIPTION
        "Cisco Firepower lsmaint:Ack:oldPnDn managed object property"
    ::= { cfprLsmaintAckEntry 20 }

cfprLsmaintAckOperScheduler OBJECT-TYPE
    SYNTAX       SnmpAdminString
    MAX-ACCESS   read-only
    STATUS       current
    DESCRIPTION
        "Cisco Firepower lsmaint:Ack:operScheduler managed
        object property"
    ::= { cfprLsmaintAckEntry 21 }

cfprLsmaintAckOperState OBJECT-TYPE
    SYNTAX       CfprTrigAckOperState
    MAX-ACCESS   read-only
    STATUS       current
    DESCRIPTION
        "Cisco Firepower lsmaint:Ack:operState managed object property"
    ::= { cfprLsmaintAckEntry 22 }

cfprLsmaintAckPolicyLevel OBJECT-TYPE
    SYNTAX       Gauge32
    MAX-ACCESS   read-only
    STATUS       current
    DESCRIPTION
        "Cisco Firepower lsmaint:Ack:policyLevel managed object property"
    ::= { cfprLsmaintAckEntry 23 }

cfprLsmaintAckPolicyOwner OBJECT-TYPE
    SYNTAX       CfprPolicyPolicyOwner
    MAX-ACCESS   read-only
    STATUS       current
    DESCRIPTION
        "Cisco Firepower lsmaint:Ack:policyOwner managed object property"
    ::= { cfprLsmaintAckEntry 24 }

cfprLsmaintAckPrevOperState OBJECT-TYPE
    SYNTAX       CfprTrigAckPrevOperState
    MAX-ACCESS   read-only
    STATUS       current
    DESCRIPTION
        "Cisco Firepower lsmaint:Ack:prevOperState managed
        object property"
    ::= { cfprLsmaintAckEntry 25 }

cfprLsmaintAckScheduler OBJECT-TYPE
    SYNTAX       SnmpAdminString
    MAX-ACCESS   read-only
    STATUS       current
    DESCRIPTION
        "Cisco Firepower lsmaint:Ack:scheduler managed object property"
    ::= { cfprLsmaintAckEntry 26 }

cfprLsmaintMaintPolicyTable OBJECT-TYPE
    SYNTAX           SEQUENCE OF CfprLsmaintMaintPolicyEntry
    MAX-ACCESS       not-accessible
    STATUS           current
    DESCRIPTION
        "Cisco Firepower lsmaint:MaintPolicy managed object table"
    ::= { cfprLsmaintObjects 2 }

cfprLsmaintMaintPolicyEntry OBJECT-TYPE
    SYNTAX           CfprLsmaintMaintPolicyEntry
    MAX-ACCESS       not-accessible
    STATUS           current
    DESCRIPTION
        "Entry for the cfprLsmaintMaintPolicyTable table."
    INDEX { cfprLsmaintMaintPolicyInstanceId }
    ::= { cfprLsmaintMaintPolicyTable 1 }

CfprLsmaintMaintPolicyEntry ::= SEQUENCE {
    cfprLsmaintMaintPolicyInstanceId                                 CfprManagedObjectId,
    cfprLsmaintMaintPolicyDn                                         CfprManagedObjectDn,
    cfprLsmaintMaintPolicyRn                                         SnmpAdminString,
    cfprLsmaintMaintPolicyDescr                                      SnmpAdminString,
    cfprLsmaintMaintPolicyIntId                                      SnmpAdminString,
    cfprLsmaintMaintPolicyName                                       SnmpAdminString,
    cfprLsmaintMaintPolicyOperSchedName                              SnmpAdminString,
    cfprLsmaintMaintPolicyPolicyLevel                                Gauge32,
    cfprLsmaintMaintPolicyPolicyOwner                                CfprPolicyPolicyOwner,
    cfprLsmaintMaintPolicySchedName                                  SnmpAdminString,
    cfprLsmaintMaintPolicyUptimeDisr                                 CfprTrigAckMode
}

cfprLsmaintMaintPolicyInstanceId OBJECT-TYPE
    SYNTAX       CfprManagedObjectId
    MAX-ACCESS   not-accessible
    STATUS       current
    DESCRIPTION
        "Instance identifier of the managed object."
    ::= { cfprLsmaintMaintPolicyEntry 1 }

cfprLsmaintMaintPolicyDn OBJECT-TYPE
    SYNTAX       CfprManagedObjectDn
    MAX-ACCESS   read-only
    STATUS       current
    DESCRIPTION
        "Cisco Firepower lsmaint:MaintPolicy:dn managed object property"
    ::= { cfprLsmaintMaintPolicyEntry 2 }

cfprLsmaintMaintPolicyRn OBJECT-TYPE
    SYNTAX       SnmpAdminString
    MAX-ACCESS   read-only
    STATUS       current
    DESCRIPTION
        "Cisco Firepower lsmaint:MaintPolicy:rn managed object property"
    ::= { cfprLsmaintMaintPolicyEntry 3 }

cfprLsmaintMaintPolicyDescr OBJECT-TYPE
    SYNTAX       SnmpAdminString
    MAX-ACCESS   read-only
    STATUS       current
    DESCRIPTION
        "Cisco Firepower lsmaint:MaintPolicy:descr managed
        object property"
    ::= { cfprLsmaintMaintPolicyEntry 4 }

cfprLsmaintMaintPolicyIntId OBJECT-TYPE
    SYNTAX       SnmpAdminString
    MAX-ACCESS   read-only
    STATUS       current
    DESCRIPTION
        "Cisco Firepower lsmaint:MaintPolicy:intId managed
        object property"
    ::= { cfprLsmaintMaintPolicyEntry 5 }

cfprLsmaintMaintPolicyName OBJECT-TYPE
    SYNTAX       SnmpAdminString
    MAX-ACCESS   read-only
    STATUS       current
    DESCRIPTION
        "Cisco Firepower lsmaint:MaintPolicy:name managed object property"
    ::= { cfprLsmaintMaintPolicyEntry 6 }

cfprLsmaintMaintPolicyOperSchedName OBJECT-TYPE
    SYNTAX       SnmpAdminString
    MAX-ACCESS   read-only
    STATUS       current
    DESCRIPTION
        "Cisco Firepower lsmaint:MaintPolicy:operSchedName
        managed object property"
    ::= { cfprLsmaintMaintPolicyEntry 7 }

cfprLsmaintMaintPolicyPolicyLevel OBJECT-TYPE
    SYNTAX       Gauge32
    MAX-ACCESS   read-only
    STATUS       current
    DESCRIPTION
        "Cisco Firepower lsmaint:MaintPolicy:policyLevel
        managed object property"
    ::= { cfprLsmaintMaintPolicyEntry 8 }

cfprLsmaintMaintPolicyPolicyOwner OBJECT-TYPE
    SYNTAX       CfprPolicyPolicyOwner
    MAX-ACCESS   read-only
    STATUS       current
    DESCRIPTION
        "Cisco Firepower lsmaint:MaintPolicy:policyOwner
        managed object property"
    ::= { cfprLsmaintMaintPolicyEntry 9 }

cfprLsmaintMaintPolicySchedName OBJECT-TYPE
    SYNTAX       SnmpAdminString
    MAX-ACCESS   read-only
    STATUS       current
    DESCRIPTION
        "Cisco Firepower lsmaint:MaintPolicy:schedName
        managed object property"
    ::= { cfprLsmaintMaintPolicyEntry 10 }

cfprLsmaintMaintPolicyUptimeDisr OBJECT-TYPE
    SYNTAX       CfprTrigAckMode
    MAX-ACCESS   read-only
    STATUS       current
    DESCRIPTION
        "Cisco Firepower lsmaint:MaintPolicy:uptimeDisr
        managed object property"
    ::= { cfprLsmaintMaintPolicyEntry 11 }

END
