--***********************************************************
-- CISCO-DMN-DSG-TIME.mib : Mib file for Time Information.
--
-- August 2010, TEL MIB Team
--
-- Copyright (c) 1999-2010 by Cisco Systems, Inc.
-- All rights reserved.
--***********************************************************

CISCO-DMN-DSG-TIME-MIB

DEFINITIONS ::= BEGIN

IMPORTS
    MODULE-IDENTITY,
    OBJECT-TYPE
        FROM SNMPv2-SMI
   DisplayString
        FROM SNMPv2-TC
    OBJECT-GROUP, MODULE-COMPLIANCE
        FROM SNMPv2-CONF
    ciscoDSGUtilities
        FROM CISCO-DMN-DSG-ROOT-MIB;

ciscoDSGTime  MODULE-IDENTITY
    LAST-UPDATED  "201008301100Z" -- August 30 2010 11:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION   "Cisco Time Information MIB."

    REVISION       "201008301100Z"
    DESCRIPTION    "V01.00.02 2010-08-30
                   Updated for adherence to SNMPv2 format."

    REVISION      "201004120600Z"
    DESCRIPTION   "V01.00.01 2010-04-12
                   The description of timeCurrent is updated."

    REVISION      "200912201200Z"
    DESCRIPTION   "V01.00.00 2009-12-20
                   Initial Version."

    ::= { ciscoDSGUtilities 23 }


timeInfo                       OBJECT IDENTIFIER ::= { ciscoDSGTime 1 }

--******************************
-- Time Information Branch
--******************************

timeFormat OBJECT-TYPE
     SYNTAX    INTEGER {
               twentyFourHr(1),
               twentyFourHrSuspendZero(2),
               twelveHr(3),
               twelveHrSuspendZero(4)
          }
     MAX-ACCESS  read-write
     STATUS  current
     DESCRIPTION
         "Time format to be used to display the time."
     ::= { timeInfo 1 }

timeDateFormat OBJECT-TYPE
     SYNTAX  INTEGER {
             yyyymmdd(1),
             ddmmyyyy(2),
             mmddyyyy(3)
          }
     MAX-ACCESS  read-write
     STATUS  current
     DESCRIPTION
         "Date format to be used to display the date."
     ::= { timeInfo 2 }


timeGMTOffset OBJECT-TYPE
     SYNTAX  INTEGER {
             minusTwelve(1),
             minusEleven(2),
             minusTen(3),
             minusNine(4),
             minusEight(5),
             minusSeven(6),
             minusSix(7),
             minusFive(8),
             minusFour(9),
             minusThreeAndAHalf(10),
             minusTwo(12),
             minusOne(13),
             zeroGMT(14),
             plusOne(15),
             plusTwo(16),
             plusThree(17),
             plusThreeAndAHalf(18),
             plusFour(19),
             plusFourAndAHalf(20),
             plusFive(21),
             plusFiveAndAHalf(22),
             plusFiveAndThreeQuarter(23),
             plusSix(24),
             plusSixAndAHalf(25),
             plusSeven(26),
             plusEight(27),
             plusNine(28),
             plusNineAndAHalf(29),
             plusTen(30),
             plusEleven(31),
             plusTwelve(32),
             plusThirteen(33)
         }
     MAX-ACCESS  read-write
     STATUS  current
     DESCRIPTION
         "Local Time Offset.
          -12 to +13 hours
         ( 01 ) - 12.0, ( 02 ) - 11.0
         ( 03 ) - 10.0, ( 04 ) - 9.0
         ( 05 ) - 8.0,  ( 06 ) - 7.0
         ( 07 ) - 6.0,  ( 08 ) - 5.0
         ( 09 ) - 4.0,  ( 10 ) - 3.5
         ( 12 ) - 2.0,  ( 13 ) - 1.0
         ( 14 ) - 0.0,  ( 15 ) + 1.0
         ( 16 ) + 2.0,  ( 17 ) + 3.0
         ( 18 ) + 3.5,  ( 19 ) + 4.0
         ( 20 ) + 4.5,  ( 21 ) + 5.0
         ( 22 ) + 5.5,  ( 23 ) + 5.75
         ( 24 ) + 6.0,  ( 25 ) + 6.5
         ( 26 ) + 7.0,  ( 27 ) + 8.0
         ( 28 ) + 9.0,  ( 29 ) + 9.5
         ( 30 ) + 10.0, ( 31 ) + 11.0
         ( 32 ) + 12.0, ( 33 ) + 13.0"
     ::= { timeInfo 3 }

timeCurrent  OBJECT-TYPE
     SYNTAX  DisplayString (SIZE(0..30))
     MAX-ACCESS  read-only
     STATUS  current
     DESCRIPTION
         "It displays the current date and time taking into account the
         value of timeGMTOffset, as per the format specified by
         timeDateFormat and timeFormat."
     ::= { timeInfo 4 }

END
