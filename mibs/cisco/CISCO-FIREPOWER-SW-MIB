-- *********************************************************************
-- CISCO-FIREPOWER-SW-MIB.my
--
-- MIB representation of the Cisco Firepower
-- SW management information model package
--
-- Created March 2020 by Charles Bullis
--
-- Copyright (c) 2005-2020 Cisco Systems, Inc. All rights reserved.
--
-- *********************************************************************

CISCO-FIREPOWER-SW-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoFirepowerMIBObjects,
    CfprManagedObjectId,
    CfprManagedObjectDn
        FROM CISCO-FIREPOWER-MIB
    CfprConditionRemoteInvRslt,
    CfprDpsecForgedTransmit,
    CfprFabricAVlanAssocPrimaryVlanSwitchId,
    CfprFabricAVlanSharing,
    CfprFabricAVlanTransport,
    CfprFabricAVlanType,
    CfprFabricAVsanTransport,
    CfprFabricAVsanType,
    CfprFabricAdminState,
    CfprFabricDefaultZoningState,
    CfprFabricDirection,
    CfprFabricEpVlanVlanType,
    CfprFabricEthEstcPortMode,
    CfprFabricEthPcProtocol,
    CfprFabricExternalEpLocale,
    CfprFabricFcZoneSharingMode,
    CfprFabricFillPattern,
    CfprFabricFlowMonIpv4Keys,
    CfprFabricFlowMonIpv6Keys,
    CfprFabricFlowMonKeyType,
    CfprFabricFlowMonL2Keys,
    CfprFabricFlowMonNonKeys,
    CfprFabricNFExporterVersion,
    CfprFabricNFTransport,
    CfprFabricPIoEpIfType,
    CfprFabricPIoEpOperState,
    CfprFabricPIoEpPortId,
    CfprFabricPIoEpSlotId,
    CfprFabricPktCaptureAppendFlag,
    CfprFabricPort,
    CfprFabricQosPrio,
    CfprFabricRecoveryAction,
    CfprFabricSpannedCluster,
    CfprFabricTrafficDirection,
    CfprFabricVlanAssocPrimaryVlanState,
    CfprFabricVlanOperState,
    CfprFabricVlanOverlapState,
    CfprFabricVnetEpIfRole,
    CfprFabricVnetEpLocale,
    CfprFabricVnetEpPolicyOwner,
    CfprFabricVsanOperState,
    CfprFabricWarnings,
    CfprFabricZoningState,
    CfprFlowctrlFlowControlRx,
    CfprFlowctrlFlowControlTx,
    CfprFlowctrlPriorityPause,
    CfprFsmCompletion,
    CfprFsmFlags,
    CfprFsmFsmStageStatus,
    CfprFsmLifecycle,
    CfprLicenseState,
    CfprLsFcZoneState,
    CfprNetworkConnectionType,
    CfprNetworkLocale,
    CfprNetworkPortRole,
    CfprNetworkSwitchId,
    CfprNetworkTransport,
    CfprNetworkVlanCountStatus,
    CfprNetworkVnetEpIfType,
    CfprNhTpHashType,
    CfprNwctrlAdminState,
    CfprNwctrlLinkFailAction,
    CfprNwctrlLldpAdminStateBitmask,
    CfprPortDuplex,
    CfprPortEthSpeed,
    CfprPortSpeed,
    CfprSwAccessDomainFsmCurrentFsm,
    CfprSwAccessDomainFsmStageName,
    CfprSwAccessDomainFsmTaskItem,
    CfprSwAccessDomainLocale,
    CfprSwAccessDomainType,
    CfprSwAccessEpLocale,
    CfprSwAccessEpTransport,
    CfprSwAdminState,
    CfprSwBorderDomainLocale,
    CfprSwBorderEpLocale,
    CfprSwBorderPcLocale,
    CfprSwBreakoutType,
    CfprSwCIoEpIfType,
    CfprSwCardEnvStatsHistThresholded,
    CfprSwCardEnvStatsThresholded,
    CfprSwCimcId,
    CfprSwConfMode,
    CfprSwConfigStatus,
    CfprSwEnvStatsHistThresholded,
    CfprSwEnvStatsThresholded,
    CfprSwEstcEpLocale,
    CfprSwEthEstcEpTransport,
    CfprSwEthEstcPcTransport,
    CfprSwEthFlowMonSessionTransport,
    CfprSwEthFlowMonSessionType,
    CfprSwEthLanBorderFsmCurrentFsm,
    CfprSwEthLanBorderFsmStageName,
    CfprSwEthLanBorderFsmTaskFlags,
    CfprSwEthLanBorderFsmTaskItem,
    CfprSwEthLanBorderTransport,
    CfprSwEthLanEpInlineState,
    CfprSwEthLanEpTransport,
    CfprSwEthLanEpUdldAdminState,
    CfprSwEthLanEpUdldMode,
    CfprSwEthLanFlowMonExporterTransport,
    CfprSwEthLanFlowMonExporterType,
    CfprSwEthLanFlowMonFsmCurrentFsm,
    CfprSwEthLanFlowMonFsmStageName,
    CfprSwEthLanFlowMonFsmTaskItem,
    CfprSwEthLanFlowMonTransport,
    CfprSwEthLanFlowMonitorTransport,
    CfprSwEthLanFlowMonitorType,
    CfprSwEthLanFlowRecordDefTransport,
    CfprSwEthLanFlowRecordDefType,
    CfprSwEthLanMonTransport,
    CfprSwEthLanPcInlineState,
    CfprSwEthLanPcTransport,
    CfprSwEthMonDestEpTransport,
    CfprSwEthMonFsmCurrentFsm,
    CfprSwEthMonFsmStageName,
    CfprSwEthMonFsmTaskItem,
    CfprSwEthMonSrcEpTransport,
    CfprSwEthMonTransport,
    CfprSwEthMonType,
    CfprSwEthTargetEpAdminState,
    CfprSwEthTargetEpTransport,
    CfprSwExtUtilityFsmCurrentFsm,
    CfprSwExtUtilityFsmStageName,
    CfprSwExtUtilityFsmTaskItem,
    CfprSwFabricZoneNsAllocStatus,
    CfprSwFcEstcEpTransport,
    CfprSwFcMonDestEpTransport,
    CfprSwFcMonFsmCurrentFsm,
    CfprSwFcMonFsmStageName,
    CfprSwFcMonFsmTaskItem,
    CfprSwFcMonSrcEpTransport,
    CfprSwFcMonTransport,
    CfprSwFcMonType,
    CfprSwFcSanBorderFsmCurrentFsm,
    CfprSwFcSanBorderFsmStageName,
    CfprSwFcSanBorderFsmTaskItem,
    CfprSwFcSanBorderTransport,
    CfprSwFcSanBorderUplinkTrunking,
    CfprSwFcSanEpTransport,
    CfprSwFcSanMonTransport,
    CfprSwFcSanPcTransport,
    CfprSwFcServerZoneGroupLc,
    CfprSwFcZoneLc,
    CfprSwFcZoneMemberLc,
    CfprSwFcZoneSetLc,
    CfprSwFcoeEstcEpTransport,
    CfprSwFcoeSanEpTransport,
    CfprSwFcoeSanEpUdldAdminState,
    CfprSwFcoeSanEpUdldMode,
    CfprSwFcoeSanPcTransport,
    CfprSwFlowMonitorAdminState,
    CfprSwLanBorderType,
    CfprSwLanEpIfRole,
    CfprSwLanEpType,
    CfprSwLanMonType,
    CfprSwLanPcIfRole,
    CfprSwLanPcType,
    CfprSwMonAdminState,
    CfprSwMonDomainLocale,
    CfprSwMonLifeCycle,
    CfprSwMonSrcEpLocale,
    CfprSwNFConfigStatus,
    CfprSwNetflowExporterProtocol,
    CfprSwNetflowMonSessionProtocol,
    CfprSwNetflowMonitorProtocol,
    CfprSwNetflowRecordDefProtocol,
    CfprSwPIoEpIfType,
    CfprSwPIoEpLc,
    CfprSwPcMode,
    CfprSwPcModeState,
    CfprSwPeerStatus,
    CfprSwPhysFsmCurrentFsm,
    CfprSwPhysFsmStageName,
    CfprSwPhysFsmTaskItem,
    CfprSwPktCaptureLifeCycle,
    CfprSwPortBreakoutPortId,
    CfprSwPortBreakoutSlotId,
    CfprSwSanBorderType,
    CfprSwSanEpIfRole,
    CfprSwSanEpType,
    CfprSwSanMonType,
    CfprSwSanPcIfRole,
    CfprSwSanPcType,
    CfprSwSspEthLanMonTransport,
    CfprSwSspEthMonFsmCurrentFsm,
    CfprSwSspEthMonFsmStageName,
    CfprSwSspEthMonFsmTaskFlags,
    CfprSwSspEthMonFsmTaskItem,
    CfprSwSspEthMonSrcPhyEpFsmCurrentFsm,
    CfprSwSspEthMonSrcPhyEpFsmStageName,
    CfprSwSspEthMonSrcPhyEpFsmTaskItem,
    CfprSwSspEthMonTransport,
    CfprSwSspEthMonType,
    CfprSwSspLanMonType,
    CfprSwSspMonAdminState,
    CfprSwSspMonDelPcap,
    CfprSwSspMonDomainLocale,
    CfprSwSubGroupAggrPortId,
    CfprSwSubGroupSlotId,
    CfprSwSystemStatsHistThresholded,
    CfprSwSystemStatsThresholded,
    CfprSwTargetEpType,
    CfprSwUlanPurpose,
    CfprSwUtilityDomainFsmCurrentFsm,
    CfprSwUtilityDomainFsmStageName,
    CfprSwUtilityDomainFsmTaskItem,
    CfprSwUtilityDomainLocale,
    CfprSwUtilityDomainType,
    CfprSwVlanCompType,
    CfprSwVlanConfigStatusType,
    CfprSwVlanGroupType,
    CfprSwVlanLc,
    CfprSwVlanPortNsAllocStatus
        FROM CISCO-FIREPOWER-TC-MIB;

cfprSwObjects MODULE-IDENTITY
    LAST-UPDATED    "202003100000Z"
    ORGANIZATION    "Cisco Systems Inc."
    CONTACT-INFO
        "Cisco Systems
        Customer Service

        Postal: 170 W Tasman Drive
        San Jose, CA  95134
        USA

        Tel: +1 800 553-NETS

        E-mail: firepower-mibs@cisco.com"
    DESCRIPTION
        "MIB representation of the Cisco Firepower
        SW management information model package"
    ::= { ciscoFirepowerMIBObjects 75 }

cfprSwAccessDomainTable OBJECT-TYPE
    SYNTAX           SEQUENCE OF CfprSwAccessDomainEntry
    MAX-ACCESS       not-accessible
    STATUS           current
    DESCRIPTION
        "Cisco Firepower sw:AccessDomain managed object table"
    ::= { cfprSwObjects 1 }

cfprSwAccessDomainEntry OBJECT-TYPE
    SYNTAX           CfprSwAccessDomainEntry
    MAX-ACCESS       not-accessible
    STATUS           current
    DESCRIPTION
        "Entry for the cfprSwAccessDomainTable table."
    INDEX { cfprSwAccessDomainInstanceId }
    ::= { cfprSwAccessDomainTable 1 }

CfprSwAccessDomainEntry ::= SEQUENCE {
    cfprSwAccessDomainInstanceId                                     CfprManagedObjectId,
    cfprSwAccessDomainDn                                             CfprManagedObjectDn,
    cfprSwAccessDomainRn                                             SnmpAdminString,
    cfprSwAccessDomainFsmDescr                                       SnmpAdminString,
    cfprSwAccessDomainFsmPrev                                        SnmpAdminString,
    cfprSwAccessDomainFsmProgr                                       Gauge32,
    cfprSwAccessDomainFsmRmtInvErrCode                               Gauge32,
    cfprSwAccessDomainFsmRmtInvErrDescr                              SnmpAdminString,
    cfprSwAccessDomainFsmRmtInvRslt                                  CfprConditionRemoteInvRslt,
    cfprSwAccessDomainFsmStageDescr                                  SnmpAdminString,
    cfprSwAccessDomainFsmStamp                                       DateAndTime,
    cfprSwAccessDomainFsmStatus                                      SnmpAdminString,
    cfprSwAccessDomainFsmTry                                         Gauge32,
    cfprSwAccessDomainLocale                                         CfprSwAccessDomainLocale,
    cfprSwAccessDomainName                                           SnmpAdminString,
    cfprSwAccessDomainSwitchId                                       CfprNetworkSwitchId,
    cfprSwAccessDomainTransport                                      CfprNetworkTransport,
    cfprSwAccessDomainType                                           CfprSwAccessDomainType
}

cfprSwAccessDomainInstanceId OBJECT-TYPE
    SYNTAX       CfprManagedObjectId
    MAX-ACCESS   not-accessible
    STATUS       current
    DESCRIPTION
        "Instance identifier of the managed object."
    ::= { cfprSwAccessDomainEntry 1 }

cfprSwAccessDomainDn OBJECT-TYPE
    SYNTAX       CfprManagedObjectDn
    MAX-ACCESS   read-only
    STATUS       current
    DESCRIPTION
        "Cisco Firepower sw:AccessDomain:dn managed object property"
    ::= { cfprSwAccessDomainEntry 2 }

cfprSwAccessDomainRn OBJECT-TYPE
    SYNTAX       SnmpAdminString
    MAX-ACCESS   read-only
    STATUS       current
    DESCRIPTION
        "Cisco Firepower sw:AccessDomain:rn managed object property"
    ::= { cfprSwAccessDomainEntry 3 }

cfprSwAccessDomainFsmDescr OBJECT-TYPE
    SYNTAX       SnmpAdminString
    MAX-ACCESS   read-only
    STATUS       current
    DESCRIPTION
        "Cisco Firepower sw:AccessDomain:fsmDescr managed object property"
    ::= { cfprSwAccessDomainEntry 4 }

cfprSwAccessDomainFsmPrev OBJECT-TYPE
    SYNTAX       SnmpAdminString
    MAX-ACCESS   read-only
    STATUS       current
    DESCRIPTION
        "Cisco Firepower sw:AccessDomain:fsmPrev managed object property"
    ::= { cfprSwAccessDomainEntry 5 }

cfprSwAccessDomainFsmProgr OBJECT-TYPE
    SYNTAX       Gauge32
    MAX-ACCESS   read-only
    STATUS       current
    DESCRIPTION
        "Cisco Firepower sw:AccessDomain:fsmProgr managed object property"
    ::= { cfprSwAccessDomainEntry 6 }

cfprSwAccessDomainFsmRmtInvErrCode OBJECT-TYPE
    SYNTAX       Gauge32
    MAX-ACCESS   read-only
    STATUS       current
    DESCRIPTION
        "Cisco Firepower sw:AccessDomain:fsmRmtInvErrCode
        managed object property"
    ::= { cfprSwAccessDomainEntry 7 }

cfprSwAccessDomainFsmRmtInvErrDescr OBJECT-TYPE
    SYNTAX       SnmpAdminString
    MAX-ACCESS   read-only
    STATUS       current
    DESCRIPTION
        "Cisco Firepower sw:AccessDomain:fsmRmtInvErrDescr
        managed object property"
    ::= { cfprSwAccessDomainEntry 8 }

cfprSwAccessDomainFsmRmtInvRslt OBJECT-TYPE
    SYNTAX       CfprConditionRemoteInvRslt
    MAX-ACCESS   read-only
    STATUS       current
    DESCRIPTION
        "Cisco Firepower sw:AccessDomain:fsmRmtInvRslt
        managed object property"
    ::= { cfprSwAccessDomainEntry 9 }

cfprSwAccessDomainFsmStageDescr OBJECT-TYPE
    SYNTAX       SnmpAdminString
    MAX-ACCESS   read-only
    STATUS       current
    DESCRIPTION
        "Cisco Firepower sw:AccessDomain:fsmStageDescr
        managed object property"
    ::= { cfprSwAccessDomainEntry 10 }

cfprSwAccessDomainFsmStamp OBJECT-TYPE
    SYNTAX       DateAndTime
    MAX-ACCESS   read-only
    STATUS       current
    DESCRIPTION
        "Cisco Firepower sw:AccessDomain:fsmStamp managed object property"
    ::= { cfprSwAccessDomainEntry 11 }

cfprSwAccessDomainFsmStatus OBJECT-TYPE
    SYNTAX       SnmpAdminString
    MAX-ACCESS   read-only
    STATUS       current
    DESCRIPTION
        "Cisco Firepower sw:AccessDomain:fsmStatus managed
        object property"
    ::= { cfprSwAccessDomainEntry 12 }

cfprSwAccessDomainFsmTry OBJECT-TYPE
    SYNTAX       Gauge32
    MAX-ACCESS   read-only
    STATUS       current
    DESCRIPTION
        "Cisco Firepower sw:AccessDomain:fsmTry managed object property"
    ::= { cfprSwAccessDomainEntry 13 }

cfprSwAccessDomainLocale OBJECT-TYPE
    SYNTAX       CfprSwAccessDomainLocale
    MAX-ACCESS   read-only
    STATUS       current
    DESCRIPTION
        "Cisco Firepower sw:AccessDomain:locale managed object property"
    ::= { cfprSwAccessDomainEntry 14 }

cfprSwAccessDomainName OBJECT-TYPE
    SYNTAX       SnmpAdminString
    MAX-ACCESS   read-only
    STATUS       current
    DESCRIPTION
        "Cisco Firepower sw:AccessDomain:name managed object property"
    ::= { cfprSwAccessDomainEntry 15 }

cfprSwAccessDomainSwitchId OBJECT-TYPE
    SYNTAX       CfprNetworkSwitchId
    MAX-ACCESS   read-only
    STATUS       current
    DESCRIPTION
        "Cisco Firepower sw:AccessDomain:switchId managed object property"
    ::= { cfprSwAccessDomainEntry 16 }

cfprSwAccessDomainTransport OBJECT-TYPE
    SYNTAX       CfprNetworkTransport
    MAX-ACCESS   read-only
    STATUS       current
    DESCRIPTION
        "Cisco Firepower sw:AccessDomain:transport managed
        object property"
    ::= { cfprSwAccessDomainEntry 17 }

cfprSwAccessDomainType OBJECT-TYPE
    SYNTAX       CfprSwAccessDomainType
    MAX-ACCESS   read-only
    STATUS       current
    DESCRIPTION
        "Cisco Firepower sw:AccessDomain:type managed object property"
    ::= { cfprSwAccessDomainEntry 18 }

cfprSwAccessDomainFsmTable OBJECT-TYPE
    SYNTAX           SEQUENCE OF CfprSwAccessDomainFsmEntry
    MAX-ACCESS       not-accessible
    STATUS           current
    DESCRIPTION
        "Cisco Firepower sw:AccessDomainFsm managed object table"
    ::= { cfprSwObjects 2 }

cfprSwAccessDomainFsmEntry OBJECT-TYPE
    SYNTAX           CfprSwAccessDomainFsmEntry
    MAX-ACCESS       not-accessible
    STATUS           current
    DESCRIPTION
        "Entry for the cfprSwAccessDomainFsmTable table."
    INDEX { cfprSwAccessDomainFsmInstanceId }
    ::= { cfprSwAccessDomainFsmTable 1 }

CfprSwAccessDomainFsmEntry ::= SEQUENCE {
    cfprSwAccessDomainFsmInstanceId                                  CfprManagedObjectId,
    cfprSwAccessDomainFsmDn                                          CfprManagedObjectDn,
    cfprSwAccessDomainFsmRn                                          SnmpAdminString,
    cfprSwAccessDomainFsmCompletionTime                              DateAndTime,
    cfprSwAccessDomainFsmCurrentFsm                                  CfprSwAccessDomainFsmCurrentFsm,
    cfprSwAccessDomainFsmDescrData                                   SnmpAdminString,
    cfprSwAccessDomainFsmFsmStatus                                   CfprFsmFsmStageStatus,
    cfprSwAccessDomainFsmProgress                                    Gauge32,
    cfprSwAccessDomainFsmRmtErrCode                                  Gauge32,
    cfprSwAccessDomainFsmRmtErrDescr                                 SnmpAdminString,
    cfprSwAccessDomainFsmRmtRslt                                     CfprConditionRemoteInvRslt
}

cfprSwAccessDomainFsmInstanceId OBJECT-TYPE
    SYNTAX       CfprManagedObjectId
    MAX-ACCESS   not-accessible
    STATUS       current
    DESCRIPTION
        "Instance identifier of the managed object."
    ::= { cfprSwAccessDomainFsmEntry 1 }

cfprSwAccessDomainFsmDn OBJECT-TYPE
    SYNTAX       CfprManagedObjectDn
    MAX-ACCESS   read-only
    STATUS       current
    DESCRIPTION
        "Cisco Firepower sw:AccessDomainFsm:dn managed object property"
    ::= { cfprSwAccessDomainFsmEntry 2 }

cfprSwAccessDomainFsmRn OBJECT-TYPE
    SYNTAX       SnmpAdminString
    MAX-ACCESS   read-only
    STATUS       current
    DESCRIPTION
        "Cisco Firepower sw:AccessDomainFsm:rn managed object property"
    ::= { cfprSwAccessDomainFsmEntry 3 }

cfprSwAccessDomainFsmCompletionTime OBJECT-TYPE
    SYNTAX       DateAndTime
    MAX-ACCESS   read-only
    STATUS       current
    DESCRIPTION
        "Cisco Firepower sw:AccessDomainFsm:completionTime
        managed object property"
    ::= { cfprSwAccessDomainFsmEntry 4 }

cfprSwAccessDomainFsmCurrentFsm OBJECT-TYPE
    SYNTAX       CfprSwAccessDomainFsmCurrentFsm
    MAX-ACCESS   read-only
    STATUS       current
    DESCRIPTION
        "Cisco Firepower sw:AccessDomainFsm:currentFsm
        managed object property"
    ::= { cfprSwAccessDomainFsmEntry 5 }

cfprSwAccessDomainFsmDescrData OBJECT-TYPE
    SYNTAX       SnmpAdminString
    MAX-ACCESS   read-only
    STATUS       current
    DESCRIPTION
        "Cisco Firepower sw:AccessDomainFsm:descr managed object property"
    ::= { cfprSwAccessDomainFsmEntry 6 }

cfprSwAccessDomainFsmFsmStatus OBJECT-TYPE
    SYNTAX       CfprFsmFsmStageStatus
    MAX-ACCESS   read-only
    STATUS       current
    DESCRIPTION
        "Cisco Firepower sw:AccessDomainFsm:fsmStatus managed
        object property"
    ::= { cfprSwAccessDomainFsmEntry 7 }

cfprSwAccessDomainFsmProgress OBJECT-TYPE
    SYNTAX       Gauge32
    MAX-ACCESS   read-only
    STATUS       current
    DESCRIPTION
        "Cisco Firepower sw:AccessDomainFsm:progress managed
        object property"
    ::= { cfprSwAccessDomainFsmEntry 8 }

cfprSwAccessDomainFsmRmtErrCode OBJECT-TYPE
    SYNTAX       Gauge32
    MAX-ACCESS   read-only
    STATUS       current
    DESCRIPTION
        "Cisco Firepower sw:AccessDomainFsm:rmtErrCode
        managed object property"
    ::= { cfprSwAccessDomainFsmEntry 9 }

cfprSwAccessDomainFsmRmtErrDescr OBJECT-TYPE
    SYNTAX       SnmpAdminString
    MAX-ACCESS   read-only
    STATUS       current
    DESCRIPTION
        "Cisco Firepower sw:AccessDomainFsm:rmtErrDescr
        managed object property"
    ::= { cfprSwAccessDomainFsmEntry 10 }

cfprSwAccessDomainFsmRmtRslt OBJECT-TYPE
    SYNTAX       CfprConditionRemoteInvRslt
    MAX-ACCESS   read-only
    STATUS       current
    DESCRIPTION
        "Cisco Firepower sw:AccessDomainFsm:rmtRslt managed
        object property"
    ::= { cfprSwAccessDomainFsmEntry 11 }

cfprSwAccessDomainFsmStageTable OBJECT-TYPE
    SYNTAX           SEQUENCE OF CfprSwAccessDomainFsmStageEntry
    MAX-ACCESS       not-accessible
    STATUS           current
    DESCRIPTION
        "Cisco Firepower sw:AccessDomainFsmStage managed object table"
    ::= { cfprSwObjects 3 }

cfprSwAccessDomainFsmStageEntry OBJECT-TYPE
    SYNTAX           CfprSwAccessDomainFsmStageEntry
    MAX-ACCESS       not-accessible
    STATUS           current
    DESCRIPTION
        "Entry for the cfprSwAccessDomainFsmStageTable table."
    INDEX { cfprSwAccessDomainFsmStageInstanceId }
    ::= { cfprSwAccessDomainFsmStageTable 1 }

CfprSwAccessDomainFsmStageEntry ::= SEQUENCE {
    cfprSwAccessDomainFsmStageInstanceId                             CfprManagedObjectId,
    cfprSwAccessDomainFsmStageDn                                     CfprManagedObjectDn,
    cfprSwAccessDomainFsmStageRn                                     SnmpAdminString,
    cfprSwAccessDomainFsmStageDescrData                              SnmpAdminString,
    cfprSwAccessDomainFsmStageLastUpdateTime                         DateAndTime,
    cfprSwAccessDomainFsmStageName                                   CfprSwAccessDomainFsmStageName,
    cfprSwAccessDomainFsmStageOrder                                  Gauge32,
    cfprSwAccessDomainFsmStageRetry                                  Gauge32,
    cfprSwAccessDomainFsmStageStageStatus                            CfprFsmFsmStageStatus
}

cfprSwAccessDomainFsmStageInstanceId OBJECT-TYPE
    SYNTAX       CfprManagedObjectId
    MAX-ACCESS   not-accessible
    STATUS       current
    DESCRIPTION
        "Instance identifier of the managed object."
    ::= { cfprSwAccessDomainFsmStageEntry 1 }

cfprSwAccessDomainFsmStageDn OBJECT-TYPE
    SYNTAX       CfprManagedObjectDn
    MAX-ACCESS   read-only
    STATUS       current
    DESCRIPTION
        "Cisco Firepower sw:AccessDomainFsmStage:dn managed
        object property"
    ::= { cfprSwAccessDomainFsmStageEntry 2 }

cfprSwAccessDomainFsmStageRn OBJECT-TYPE
    SYNTAX       SnmpAdminString
    MAX-ACCESS   read-only
    STATUS       current
    DESCRIPTION
        "Cisco Firepower sw:AccessDomainFsmStage:rn managed
        object property"
    ::= { cfprSwAccessDomainFsmStageEntry 3 }

cfprSwAccessDomainFsmStageDescrData OBJECT-TYPE
    SYNTAX       SnmpAdminString
    MAX-ACCESS   read-only
    STATUS       current
    DESCRIPTION
        "Cisco Firepower sw:AccessDomainFsmStage:descr
        managed object property"
    ::= { cfprSwAccessDomainFsmStageEntry 4 }

cfprSwAccessDomainFsmStageLastUpdateTime OBJECT-TYPE
    SYNTAX       DateAndTime
    MAX-ACCESS   read-only
    STATUS       current
    DESCRIPTION
        "Cisco Firepower sw:AccessDomainFsmStage:lastUpdateTime
        managed object property"
    ::= { cfprSwAccessDomainFsmStageEntry 5 }

cfprSwAccessDomainFsmStageName OBJECT-TYPE
    SYNTAX       CfprSwAccessDomainFsmStageName
    MAX-ACCESS   read-only
    STATUS       current
    DESCRIPTION
        "Cisco Firepower sw:AccessDomainFsmStage:name managed
        object property"
    ::= { cfprSwAccessDomainFsmStageEntry 6 }

cfprSwAccessDomainFsmStageOrder OBJECT-TYPE
    SYNTAX       Gauge32
    MAX-ACCESS   read-only
    STATUS       current
    DESCRIPTION
        "Cisco Firepower sw:AccessDomainFsmStage:order
        managed object property"
    ::= { cfprSwAccessDomainFsmStageEntry 7 }

cfprSwAccessDomainFsmStageRetry OBJECT-TYPE
    SYNTAX       Gauge32
    MAX-ACCESS   read-only
    STATUS       current
    DESCRIPTION
        "Cisco Firepower sw:AccessDomainFsmStage:retry
        managed object property"
    ::= { cfprSwAccessDomainFsmStageEntry 8 }

cfprSwAccessDomainFsmStageStageStatus OBJECT-TYPE
    SYNTAX       CfprFsmFsmStageStatus
    MAX-ACCESS   read-only
    STATUS       current
    DESCRIPTION
        "Cisco Firepower sw:AccessDomainFsmStage:stageStatus
        managed object property"
    ::= { cfprSwAccessDomainFsmStageEntry 9 }

cfprSwAccessDomainFsmTaskTable OBJECT-TYPE
    SYNTAX           SEQUENCE OF CfprSwAccessDomainFsmTaskEntry
    MAX-ACCESS       not-accessible
    STATUS           current
    DESCRIPTION
        "Cisco Firepower sw:AccessDomainFsmTask managed object table"
    ::= { cfprSwObjects 4 }

cfprSwAccessDomainFsmTaskEntry OBJECT-TYPE
    SYNTAX           CfprSwAccessDomainFsmTaskEntry
    MAX-ACCESS       not-accessible
    STATUS           current
    DESCRIPTION
        "Entry for the cfprSwAccessDomainFsmTaskTable table."
    INDEX { cfprSwAccessDomainFsmTaskInstanceId }
    ::= { cfprSwAccessDomainFsmTaskTable 1 }

CfprSwAccessDomainFsmTaskEntry ::= SEQUENCE {
    cfprSwAccessDomainFsmTaskInstanceId                              CfprManagedObjectId,
    cfprSwAccessDomainFsmTaskDn                                      CfprManagedObjectDn,
    cfprSwAccessDomainFsmTaskRn                                      SnmpAdminString,
    cfprSwAccessDomainFsmTaskCompletion                              CfprFsmCompletion,
    cfprSwAccessDomainFsmTaskFlags                                   CfprFsmFlags,
    cfprSwAccessDomainFsmTaskItem                                    CfprSwAccessDomainFsmTaskItem,
    cfprSwAccessDomainFsmTaskSeqId                                   Gauge32
}

cfprSwAccessDomainFsmTaskInstanceId OBJECT-TYPE
    SYNTAX       CfprManagedObjectId
    MAX-ACCESS   not-accessible
    STATUS       current
    DESCRIPTION
        "Instance identifier of the managed object."
    ::= { cfprSwAccessDomainFsmTaskEntry 1 }

cfprSwAccessDomainFsmTaskDn OBJECT-TYPE
    SYNTAX       CfprManagedObjectDn
    MAX-ACCESS   read-only
    STATUS       current
    DESCRIPTION
        "Cisco Firepower sw:AccessDomainFsmTask:dn managed
        object property"
    ::= { cfprSwAccessDomainFsmTaskEntry 2 }

cfprSwAccessDomainFsmTaskRn OBJECT-TYPE
    SYNTAX       SnmpAdminString
    MAX-ACCESS   read-only
    STATUS       current
    DESCRIPTION
        "Cisco Firepower sw:AccessDomainFsmTask:rn managed
        object property"
    ::= { cfprSwAccessDomainFsmTaskEntry 3 }

cfprSwAccessDomainFsmTaskCompletion OBJECT-TYPE
    SYNTAX       CfprFsmCompletion
    MAX-ACCESS   read-only
    STATUS       current
    DESCRIPTION
        "Cisco Firepower sw:AccessDomainFsmTask:completion
        managed object property"
    ::= { cfprSwAccessDomainFsmTaskEntry 4 }

cfprSwAccessDomainFsmTaskFlags OBJECT-TYPE
    SYNTAX       CfprFsmFlags
    MAX-ACCESS   read-only
    STATUS       current
    DESCRIPTION
        "Cisco Firepower sw:AccessDomainFsmTask:flags managed
        object property"
    ::= { cfprSwAccessDomainFsmTaskEntry 5 }

cfprSwAccessDomainFsmTaskItem OBJECT-TYPE
    SYNTAX       CfprSwAccessDomainFsmTaskItem
    MAX-ACCESS   read-only
    STATUS       current
    DESCRIPTION
        "Cisco Firepower sw:AccessDomainFsmTask:item managed
        object property"
    ::= { cfprSwAccessDomainFsmTaskEntry 6 }

cfprSwAccessDomainFsmTaskSeqId OBJECT-TYPE
    SYNTAX       Gauge32
    MAX-ACCESS   read-only
    STATUS       current
    DESCRIPTION
        "Cisco Firepower sw:AccessDomainFsmTask:seqId managed
        object property"
    ::= { cfprSwAccessDomainFsmTaskEntry 7 }

cfprSwAccessEpTable OBJECT-TYPE
    SYNTAX           SEQUENCE OF CfprSwAccessEpEntry
    MAX-ACCESS       not-accessible
    STATUS           current
    DESCRIPTION
        "Cisco Firepower sw:AccessEp managed object table"
    ::= { cfprSwObjects 5 }

cfprSwAccessEpEntry OBJECT-TYPE
    SYNTAX           CfprSwAccessEpEntry
    MAX-ACCESS       not-accessible
    STATUS           current
    DESCRIPTION
        "Entry for the cfprSwAccessEpTable table."
    INDEX { cfprSwAccessEpInstanceId }
    ::= { cfprSwAccessEpTable 1 }

CfprSwAccessEpEntry ::= SEQUENCE {
    cfprSwAccessEpInstanceId                                         CfprManagedObjectId,
    cfprSwAccessEpDn                                                 CfprManagedObjectDn,
    cfprSwAccessEpRn                                                 SnmpAdminString,
    cfprSwAccessEpAdminState                                         CfprFabricAdminState,
    cfprSwAccessEpAggrPortId                                         Gauge32,
    cfprSwAccessEpChassisId                                          Gauge32,
    cfprSwAccessEpEncap                                              Gauge32,
    cfprSwAccessEpEpDn                                               SnmpAdminString,
    cfprSwAccessEpIfRole                                             CfprNetworkPortRole,
    cfprSwAccessEpIfType                                             CfprSwPIoEpIfType,
    cfprSwAccessEpLc                                                 CfprSwPIoEpLc,
    cfprSwAccessEpLocale                                             CfprSwAccessEpLocale,
    cfprSwAccessEpName                                               SnmpAdminString,
    cfprSwAccessEpNsSize                                             Gauge32,
    cfprSwAccessEpPeerAggrPortId                                     Gauge32,
    cfprSwAccessEpPeerChassisId                                      Gauge32,
    cfprSwAccessEpPeerDn                                             SnmpAdminString,
    cfprSwAccessEpPeerPortId                                         Gauge32,
    cfprSwAccessEpPeerSlotId                                         Gauge32,
    cfprSwAccessEpPortId                                             Gauge32,
    cfprSwAccessEpSlotId                                             Gauge32,
    cfprSwAccessEpSwitchId                                           CfprNetworkSwitchId,
    cfprSwAccessEpTransport                                          CfprSwAccessEpTransport,
    cfprSwAccessEpType                                               CfprNetworkConnectionType
}

cfprSwAccessEpInstanceId OBJECT-TYPE
    SYNTAX       CfprManagedObjectId
    MAX-ACCESS   not-accessible
    STATUS       current
    DESCRIPTION
        "Instance identifier of the managed object."
    ::= { cfprSwAccessEpEntry 1 }

cfprSwAccessEpDn OBJECT-TYPE
    SYNTAX       CfprManagedObjectDn
    MAX-ACCESS   read-only
    STATUS       current
    DESCRIPTION
        "Cisco Firepower sw:AccessEp:dn managed object property"
    ::= { cfprSwAccessEpEntry 2 }

cfprSwAccessEpRn OBJECT-TYPE
    SYNTAX       SnmpAdminString
    MAX-ACCESS   read-only
    STATUS       current
    DESCRIPTION
        "Cisco Firepower sw:AccessEp:rn managed object property"
    ::= { cfprSwAccessEpEntry 3 }

cfprSwAccessEpAdminState OBJECT-TYPE
    SYNTAX       CfprFabricAdminState
    MAX-ACCESS   read-only
    STATUS       current
    DESCRIPTION
        "Cisco Firepower sw:AccessEp:adminState managed object property"
    ::= { cfprSwAccessEpEntry 4 }

cfprSwAccessEpAggrPortId OBJECT-TYPE
    SYNTAX       Gauge32
    MAX-ACCESS   read-only
    STATUS       current
    DESCRIPTION
        "Cisco Firepower sw:AccessEp:aggrPortId managed object property"
    ::= { cfprSwAccessEpEntry 5 }

cfprSwAccessEpChassisId OBJECT-TYPE
    SYNTAX       Gauge32
    MAX-ACCESS   read-only
    STATUS       current
    DESCRIPTION
        "Cisco Firepower sw:AccessEp:chassisId managed object property"
    ::= { cfprSwAccessEpEntry 6 }

cfprSwAccessEpEncap OBJECT-TYPE
    SYNTAX       Gauge32
    MAX-ACCESS   read-only
    STATUS       current
    DESCRIPTION
        "Cisco Firepower sw:AccessEp:encap managed object property"
    ::= { cfprSwAccessEpEntry 7 }

cfprSwAccessEpEpDn OBJECT-TYPE
    SYNTAX       SnmpAdminString
    MAX-ACCESS   read-only
    STATUS       current
    DESCRIPTION
        "Cisco Firepower sw:AccessEp:epDn managed object property"
    ::= { cfprSwAccessEpEntry 8 }

cfprSwAccessEpIfRole OBJECT-TYPE
    SYNTAX       CfprNetworkPortRole
    MAX-ACCESS   read-only
    STATUS       current
    DESCRIPTION
        "Cisco Firepower sw:AccessEp:ifRole managed object property"
    ::= { cfprSwAccessEpEntry 9 }

cfprSwAccessEpIfType OBJECT-TYPE
    SYNTAX       CfprSwPIoEpIfType
    MAX-ACCESS   read-only
    STATUS       current
    DESCRIPTION
        "Cisco Firepower sw:AccessEp:ifType managed object property"
    ::= { cfprSwAccessEpEntry 10 }

cfprSwAccessEpLc OBJECT-TYPE
    SYNTAX       CfprSwPIoEpLc
    MAX-ACCESS   read-only
    STATUS       current
    DESCRIPTION
        "Cisco Firepower sw:AccessEp:lc managed object property"
    ::= { cfprSwAccessEpEntry 11 }

cfprSwAccessEpLocale OBJECT-TYPE
    SYNTAX       CfprSwAccessEpLocale
    MAX-ACCESS   read-only
    STATUS       current
    DESCRIPTION
        "Cisco Firepower sw:AccessEp:locale managed object property"
    ::= { cfprSwAccessEpEntry 12 }

cfprSwAccessEpName OBJECT-TYPE
    SYNTAX       SnmpAdminString
    MAX-ACCESS   read-only
    STATUS       current
    DESCRIPTION
        "Cisco Firepower sw:AccessEp:name managed object property"
    ::= { cfprSwAccessEpEntry 13 }

cfprSwAccessEpNsSize OBJECT-TYPE
    SYNTAX       Gauge32
    MAX-ACCESS   read-only
    STATUS       current
    DESCRIPTION
        "Cisco Firepower sw:AccessEp:nsSize managed object property"
    ::= { cfprSwAccessEpEntry 14 }

cfprSwAccessEpPeerAggrPortId OBJECT-TYPE
    SYNTAX       Gauge32
    MAX-ACCESS   read-only
    STATUS       current
    DESCRIPTION
        "Cisco Firepower sw:AccessEp:peerAggrPortId managed
        object property"
    ::= { cfprSwAccessEpEntry 15 }

cfprSwAccessEpPeerChassisId OBJECT-TYPE
    SYNTAX       Gauge32
    MAX-ACCESS   read-only
    STATUS       current
    DESCRIPTION
        "Cisco Firepower sw:AccessEp:peerChassisId managed
        object property"
    ::= { cfprSwAccessEpEntry 16 }

cfprSwAccessEpPeerDn OBJECT-TYPE
    SYNTAX       SnmpAdminString
    MAX-ACCESS   read-only
    STATUS       current
    DESCRIPTION
        "Cisco Firepower sw:AccessEp:peerDn managed object property"
    ::= { cfprSwAccessEpEntry 17 }

cfprSwAccessEpPeerPortId OBJECT-TYPE
    SYNTAX       Gauge32
    MAX-ACCESS   read-only
    STATUS       current
    DESCRIPTION
        "Cisco Firepower sw:AccessEp:peerPortId managed object property"
    ::= { cfprSwAccessEpEntry 18 }

cfprSwAccessEpPeerSlotId OBJECT-TYPE
    SYNTAX       Gauge32
    MAX-ACCESS   read-only
    STATUS       current
    DESCRIPTION
        "Cisco Firepower sw:AccessEp:peerSlotId managed object property"
    ::= { cfprSwAccessEpEntry 19 }

cfprSwAccessEpPortId OBJECT-TYPE
    SYNTAX       Gauge32
    MAX-ACCESS   read-only
    STATUS       current
    DESCRIPTION
        "Cisco Firepower sw:AccessEp:portId managed object property"
    ::= { cfprSwAccessEpEntry 20 }

cfprSwAccessEpSlotId OBJECT-TYPE
    SYNTAX       Gauge32
    MAX-ACCESS   read-only
    STATUS       current
    DESCRIPTION
        "Cisco Firepower sw:AccessEp:slotId managed object property"
    ::= { cfprSwAccessEpEntry 21 }

cfprSwAccessEpSwitchId OBJECT-TYPE
    SYNTAX       CfprNetworkSwitchId
    MAX-ACCESS   read-only
    STATUS       current
    DESCRIPTION
        "Cisco Firepower sw:AccessEp:switchId managed object property"
    ::= { cfprSwAccessEpEntry 22 }

cfprSwAccessEpTransport OBJECT-TYPE
    SYNTAX       CfprSwAccessEpTransport
    MAX-ACCESS   read-only
    STATUS       current
    DESCRIPTION
        "Cisco Firepower sw:AccessEp:transport managed object property"
    ::= { cfprSwAccessEpEntry 23 }

cfprSwAccessEpType OBJECT-TYPE
    SYNTAX       CfprNetworkConnectionType
    MAX-ACCESS   read-only
    STATUS       current
    DESCRIPTION
        "Cisco Firepower sw:AccessEp:type managed object property"
    ::= { cfprSwAccessEpEntry 24 }

cfprSwCardEnvStatsTable OBJECT-TYPE
    SYNTAX           SEQUENCE OF CfprSwCardEnvStatsEntry
    MAX-ACCESS       not-accessible
    STATUS           current
    DESCRIPTION
        "Cisco Firepower sw:CardEnvStats managed object table"
    ::= { cfprSwObjects 6 }

cfprSwCardEnvStatsEntry OBJECT-TYPE
    SYNTAX           CfprSwCardEnvStatsEntry
    MAX-ACCESS       not-accessible
    STATUS           current
    DESCRIPTION
        "Entry for the cfprSwCardEnvStatsTable table."
    INDEX { cfprSwCardEnvStatsInstanceId }
    ::= { cfprSwCardEnvStatsTable 1 }

CfprSwCardEnvStatsEntry ::= SEQUENCE {
    cfprSwCardEnvStatsInstanceId                                     CfprManagedObjectId,
    cfprSwCardEnvStatsDn                                             CfprManagedObjectDn,
    cfprSwCardEnvStatsRn                                             SnmpAdminString,
    cfprSwCardEnvStatsSlotOutlet1                                    INTEGER,
    cfprSwCardEnvStatsSlotOutlet1Avg                                 INTEGER,
    cfprSwCardEnvStatsSlotOutlet1Max                                 INTEGER,
    cfprSwCardEnvStatsSlotOutlet1Min                                 INTEGER,
    cfprSwCardEnvStatsSlotOutlet2                                    INTEGER,
    cfprSwCardEnvStatsSlotOutlet2Avg                                 INTEGER,
    cfprSwCardEnvStatsSlotOutlet2Max                                 INTEGER,
    cfprSwCardEnvStatsSlotOutlet2Min                                 INTEGER,
    cfprSwCardEnvStatsSlotOutlet3                                    INTEGER,
    cfprSwCardEnvStatsSlotOutlet3Avg                                 INTEGER,
    cfprSwCardEnvStatsSlotOutlet3Max                                 INTEGER,
    cfprSwCardEnvStatsSlotOutlet3Min                                 INTEGER,
    cfprSwCardEnvStatsIntervals                                      Gauge32,
    cfprSwCardEnvStatsSuspect                                        TruthValue,
    cfprSwCardEnvStatsThresholded                                    CfprSwCardEnvStatsThresholded,
    cfprSwCardEnvStatsTimeCollected                                  DateAndTime,
    cfprSwCardEnvStatsUpdate                                         Gauge32
}

cfprSwCardEnvStatsInstanceId OBJECT-TYPE
    SYNTAX       CfprManagedObjectId
    MAX-ACCESS   not-accessible
    STATUS       current
    DESCRIPTION
        "Instance identifier of the managed object."
    ::= { cfprSwCardEnvStatsEntry 1 }

cfprSwCardEnvStatsDn OBJECT-TYPE
    SYNTAX       CfprManagedObjectDn
    MAX-ACCESS   read-only
    STATUS       current
    DESCRIPTION
        "Cisco Firepower sw:CardEnvStats:dn managed object property"
    ::= { cfprSwCardEnvStatsEntry 2 }

cfprSwCardEnvStatsRn OBJECT-TYPE
    SYNTAX       SnmpAdminString
    MAX-ACCESS   read-only
    STATUS       current
    DESCRIPTION
        "Cisco Firepower sw:CardEnvStats:rn managed object property"
    ::= { cfprSwCardEnvStatsEntry 3 }

cfprSwCardEnvStatsSlotOutlet1 OBJECT-TYPE
    SYNTAX       INTEGER
    MAX-ACCESS   read-only
    STATUS       current
    DESCRIPTION
        "Cisco Firepower sw:CardEnvStats:SlotOutlet1 managed
        object property"
    ::= { cfprSwCardEnvStatsEntry 4 }

cfprSwCardEnvStatsSlotOutlet1Avg OBJECT-TYPE
    SYNTAX       INTEGER
    MAX-ACCESS   read-only
    STATUS       current
    DESCRIPTION
        "Cisco Firepower sw:CardEnvStats:SlotOutlet1Avg
        managed object property"
    ::= { cfprSwCardEnvStatsEntry 5 }

cfprSwCardEnvStatsSlotOutlet1Max OBJECT-TYPE
    SYNTAX       INTEGER
    MAX-ACCESS   read-only
    STATUS       current
    DESCRIPTION
        "Cisco Firepower sw:CardEnvStats:SlotOutlet1Max
        managed object property"
    ::= { cfprSwCardEnvStatsEntry 6 }

cfprSwCardEnvStatsSlotOutlet1Min OBJECT-TYPE
    SYNTAX       INTEGER
    MAX-ACCESS   read-only
    STATUS       current
    DESCRIPTION
        "Cisco Firepower sw:CardEnvStats:SlotOutlet1Min
        managed object property"
    ::= { cfprSwCardEnvStatsEntry 7 }

cfprSwCardEnvStatsSlotOutlet2 OBJECT-TYPE
    SYNTAX       INTEGER
    MAX-ACCESS   read-only
    STATUS       current
    DESCRIPTION
        "Cisco Firepower sw:CardEnvStats:SlotOutlet2 managed
        object property"
    ::= { cfprSwCardEnvStatsEntry 8 }

cfprSwCardEnvStatsSlotOutlet2Avg OBJECT-TYPE
    SYNTAX       INTEGER
    MAX-ACCESS   read-only
    STATUS       current
    DESCRIPTION
        "Cisco Firepower sw:CardEnvStats:SlotOutlet2Avg
        managed object property"
    ::= { cfprSwCardEnvStatsEntry 9 }

cfprSwCardEnvStatsSlotOutlet2Max OBJECT-TYPE
    SYNTAX       INTEGER
    MAX-ACCESS   read-only
    STATUS       current
    DESCRIPTION
        "Cisco Firepower sw:CardEnvStats:SlotOutlet2Max
        managed object property"
    ::= { cfprSwCardEnvStatsEntry 10 }

cfprSwCardEnvStatsSlotOutlet2Min OBJECT-TYPE
    SYNTAX       INTEGER
    MAX-ACCESS   read-only
    STATUS       current
    DESCRIPTION
        "Cisco Firepower sw:CardEnvStats:SlotOutlet2Min
        managed object property"
    ::= { cfprSwCardEnvStatsEntry 11 }

cfprSwCardEnvStatsSlotOutlet3 OBJECT-TYPE
    SYNTAX       INTEGER
    MAX-ACCESS   read-only
    STATUS       current
    DESCRIPTION
        "Cisco Firepower sw:CardEnvStats:SlotOutlet3 managed
        object property"
    ::= { cfprSwCardEnvStatsEntry 12 }

cfprSwCardEnvStatsSlotOutlet3Avg OBJECT-TYPE
    SYNTAX       INTEGER
    MAX-ACCESS   read-only
    STATUS       current
    DESCRIPTION
        "Cisco Firepower sw:CardEnvStats:SlotOutlet3Avg
        managed object property"
    ::= { cfprSwCardEnvStatsEntry 13 }

cfprSwCardEnvStatsSlotOutlet3Max OBJECT-TYPE
    SYNTAX       INTEGER
    MAX-ACCESS   read-only
    STATUS       current
    DESCRIPTION
        "Cisco Firepower sw:CardEnvStats:SlotOutlet3Max
        managed object property"
    ::= { cfprSwCardEnvStatsEntry 14 }

cfprSwCardEnvStatsSlotOutlet3Min OBJECT-TYPE
    SYNTAX       INTEGER
    MAX-ACCESS   read-only
    STATUS       current
    DESCRIPTION
        "Cisco Firepower sw:CardEnvStats:SlotOutlet3Min
        managed object property"
    ::= { cfprSwCardEnvStatsEntry 15 }

cfprSwCardEnvStatsIntervals OBJECT-TYPE
    SYNTAX       Gauge32
    MAX-ACCESS   read-only
    STATUS       current
    DESCRIPTION
        "Cisco Firepower sw:CardEnvStats:intervals managed
        object property"
    ::= { cfprSwCardEnvStatsEntry 16 }

cfprSwCardEnvStatsSuspect OBJECT-TYPE
    SYNTAX       TruthValue
    MAX-ACCESS   read-only
    STATUS       current
    DESCRIPTION
        "Cisco Firepower sw:CardEnvStats:suspect managed object property"
    ::= { cfprSwCardEnvStatsEntry 17 }

cfprSwCardEnvStatsThresholded OBJECT-TYPE
    SYNTAX       CfprSwCardEnvStatsThresholded
    MAX-ACCESS   read-only
    STATUS       current
    DESCRIPTION
        "Cisco Firepower sw:CardEnvStats:thresholded managed
        object property"
    ::= { cfprSwCardEnvStatsEntry 18 }

cfprSwCardEnvStatsTimeCollected OBJECT-TYPE
    SYNTAX       DateAndTime
    MAX-ACCESS   read-only
    STATUS       current
    DESCRIPTION
        "Cisco Firepower sw:CardEnvStats:timeCollected
        managed object property"
    ::= { cfprSwCardEnvStatsEntry 19 }

cfprSwCardEnvStatsUpdate OBJECT-TYPE
    SYNTAX       Gauge32
    MAX-ACCESS   read-only
    STATUS       current
    DESCRIPTION
        "Cisco Firepower sw:CardEnvStats:update managed object property"
    ::= { cfprSwCardEnvStatsEntry 20 }

cfprSwCardEnvStatsHistTable OBJECT-TYPE
    SYNTAX           SEQUENCE OF CfprSwCardEnvStatsHistEntry
    MAX-ACCESS       not-accessible
    STATUS           current
    DESCRIPTION
        "Cisco Firepower sw:CardEnvStatsHist managed object table"
    ::= { cfprSwObjects 7 }

cfprSwCardEnvStatsHistEntry OBJECT-TYPE
    SYNTAX           CfprSwCardEnvStatsHistEntry
    MAX-ACCESS       not-accessible
    STATUS           current
    DESCRIPTION
        "Entry for the cfprSwCardEnvStatsHistTable table."
    INDEX { cfprSwCardEnvStatsHistInstanceId }
    ::= { cfprSwCardEnvStatsHistTable 1 }

CfprSwCardEnvStatsHistEntry ::= SEQUENCE {
    cfprSwCardEnvStatsHistInstanceId                                 CfprManagedObjectId,
    cfprSwCardEnvStatsHistDn                                         CfprManagedObjectDn,
    cfprSwCardEnvStatsHistRn                                         SnmpAdminString,
    cfprSwCardEnvStatsHistSlotOutlet1                                INTEGER,
    cfprSwCardEnvStatsHistSlotOutlet1Avg                             INTEGER,
    cfprSwCardEnvStatsHistSlotOutlet1Max                             INTEGER,
    cfprSwCardEnvStatsHistSlotOutlet1Min                             INTEGER,
    cfprSwCardEnvStatsHistSlotOutlet2                                INTEGER,
    cfprSwCardEnvStatsHistSlotOutlet2Avg                             INTEGER,
    cfprSwCardEnvStatsHistSlotOutlet2Max                             INTEGER,
    cfprSwCardEnvStatsHistSlotOutlet2Min                             INTEGER,
    cfprSwCardEnvStatsHistSlotOutlet3                                INTEGER,
    cfprSwCardEnvStatsHistSlotOutlet3Avg                             INTEGER,
    cfprSwCardEnvStatsHistSlotOutlet3Max                             INTEGER,
    cfprSwCardEnvStatsHistSlotOutlet3Min                             INTEGER,
    cfprSwCardEnvStatsHistId                                         Unsigned64,
    cfprSwCardEnvStatsHistMostRecent                                 TruthValue,
    cfprSwCardEnvStatsHistSuspect                                    TruthValue,
    cfprSwCardEnvStatsHistThresholded                                CfprSwCardEnvStatsHistThresholded,
    cfprSwCardEnvStatsHistTimeCollected                              DateAndTime
}

cfprSwCardEnvStatsHistInstanceId OBJECT-TYPE
    SYNTAX       CfprManagedObjectId
    MAX-ACCESS   not-accessible
    STATUS       current
    DESCRIPTION
        "Instance identifier of the managed object."
    ::= { cfprSwCardEnvStatsHistEntry 1 }

cfprSwCardEnvStatsHistDn OBJECT-TYPE
    SYNTAX       CfprManagedObjectDn
    MAX-ACCESS   read-only
    STATUS       current
    DESCRIPTION
        "Cisco Firepower sw:CardEnvStatsHist:dn managed object property"
    ::= { cfprSwCardEnvStatsHistEntry 2 }

cfprSwCardEnvStatsHistRn OBJECT-TYPE
    SYNTAX       SnmpAdminString
    MAX-ACCESS   read-only
    STATUS       current
    DESCRIPTION
        "Cisco Firepower sw:CardEnvStatsHist:rn managed object property"
    ::= { cfprSwCardEnvStatsHistEntry 3 }

cfprSwCardEnvStatsHistSlotOutlet1 OBJECT-TYPE
    SYNTAX       INTEGER
    MAX-ACCESS   read-only
    STATUS       current
    DESCRIPTION
        "Cisco Firepower sw:CardEnvStatsHist:SlotOutlet1
        managed object property"
    ::= { cfprSwCardEnvStatsHistEntry 4 }

cfprSwCardEnvStatsHistSlotOutlet1Avg OBJECT-TYPE
    SYNTAX       INTEGER
    MAX-ACCESS   read-only
    STATUS       current
    DESCRIPTION
        "Cisco Firepower sw:CardEnvStatsHist:SlotOutlet1Avg
        managed object property"
    ::= { cfprSwCardEnvStatsHistEntry 5 }

cfprSwCardEnvStatsHistSlotOutlet1Max OBJECT-TYPE
    SYNTAX       INTEGER
    MAX-ACCESS   read-only
    STATUS       current
    DESCRIPTION
        "Cisco Firepower sw:CardEnvStatsHist:SlotOutlet1Max
        managed object property"
    ::= { cfprSwCardEnvStatsHistEntry 6 }

cfprSwCardEnvStatsHistSlotOutlet1Min OBJECT-TYPE
    SYNTAX       INTEGER
    MAX-ACCESS   read-only
    STATUS       current
    DESCRIPTION
        "Cisco Firepower sw:CardEnvStatsHist:SlotOutlet1Min
        managed object property"
    ::= { cfprSwCardEnvStatsHistEntry 7 }

cfprSwCardEnvStatsHistSlotOutlet2 OBJECT-TYPE
    SYNTAX       INTEGER
    MAX-ACCESS   read-only
    STATUS       current
    DESCRIPTION
        "Cisco Firepower sw:CardEnvStatsHist:SlotOutlet2
        managed object property"
    ::= { cfprSwCardEnvStatsHistEntry 8 }

cfprSwCardEnvStatsHistSlotOutlet2Avg OBJECT-TYPE
    SYNTAX       INTEGER
    MAX-ACCESS   read-only
    STATUS       current
    DESCRIPTION
        "Cisco Firepower sw:CardEnvStatsHist:SlotOutlet2Avg
        managed object property"
    ::= { cfprSwCardEnvStatsHistEntry 9 }

cfprSwCardEnvStatsHistSlotOutlet2Max OBJECT-TYPE
    SYNTAX       INTEGER
    MAX-ACCESS   read-only
    STATUS       current
    DESCRIPTION
        "Cisco Firepower sw:CardEnvStatsHist:SlotOutlet2Max
        managed object property"
    ::= { cfprSwCardEnvStatsHistEntry 10 }

cfprSwCardEnvStatsHistSlotOutlet2Min OBJECT-TYPE
    SYNTAX       INTEGER
    MAX-ACCESS   read-only
    STATUS       current
    DESCRIPTION
        "Cisco Firepower sw:CardEnvStatsHist:SlotOutlet2Min
        managed object property"
    ::= { cfprSwCardEnvStatsHistEntry 11 }

cfprSwCardEnvStatsHistSlotOutlet3 OBJECT-TYPE
    SYNTAX       INTEGER
    MAX-ACCESS   read-only
    STATUS       current
    DESCRIPTION
        "Cisco Firepower sw:CardEnvStatsHist:SlotOutlet3
        managed object property"
    ::= { cfprSwCardEnvStatsHistEntry 12 }

cfprSwCardEnvStatsHistSlotOutlet3Avg OBJECT-TYPE
    SYNTAX       INTEGER
    MAX-ACCESS   read-only
    STATUS       current
    DESCRIPTION
        "Cisco Firepower sw:CardEnvStatsHist:SlotOutlet3Avg
        managed object property"
    ::= { cfprSwCardEnvStatsHistEntry 13 }

cfprSwCardEnvStatsHistSlotOutlet3Max OBJECT-TYPE
    SYNTAX       INTEGER
    MAX-ACCESS   read-only
    STATUS       current
    DESCRIPTION
        "Cisco Firepower sw:CardEnvStatsHist:SlotOutlet3Max
        managed object property"
    ::= { cfprSwCardEnvStatsHistEntry 14 }

cfprSwCardEnvStatsHistSlotOutlet3Min OBJECT-TYPE
    SYNTAX       INTEGER
    MAX-ACCESS   read-only
    STATUS       current
    DESCRIPTION
        "Cisco Firepower sw:CardEnvStatsHist:SlotOutlet3Min
        managed object property"
    ::= { cfprSwCardEnvStatsHistEntry 15 }

cfprSwCardEnvStatsHistId OBJECT-TYPE
    SYNTAX       Unsigned64
    MAX-ACCESS   read-only
    STATUS       current
    DESCRIPTION
        "Cisco Firepower sw:CardEnvStatsHist:id managed object property"
    ::= { cfprSwCardEnvStatsHistEntry 16 }

cfprSwCardEnvStatsHistMostRecent OBJECT-TYPE
    SYNTAX       TruthValue
    MAX-ACCESS   read-only
    STATUS       current
    DESCRIPTION
        "Cisco Firepower sw:CardEnvStatsHist:mostRecent
        managed object property"
    ::= { cfprSwCardEnvStatsHistEntry 17 }

cfprSwCardEnvStatsHistSuspect OBJECT-TYPE
    SYNTAX       TruthValue
    MAX-ACCESS   read-only
    STATUS       current
    DESCRIPTION
        "Cisco Firepower sw:CardEnvStatsHist:suspect managed
        object property"
    ::= { cfprSwCardEnvStatsHistEntry 18 }

cfprSwCardEnvStatsHistThresholded OBJECT-TYPE
    SYNTAX       CfprSwCardEnvStatsHistThresholded
    MAX-ACCESS   read-only
    STATUS       current
    DESCRIPTION
        "Cisco Firepower sw:CardEnvStatsHist:thresholded
        managed object property"
    ::= { cfprSwCardEnvStatsHistEntry 19 }

cfprSwCardEnvStatsHistTimeCollected OBJECT-TYPE
    SYNTAX       DateAndTime
    MAX-ACCESS   read-only
    STATUS       current
    DESCRIPTION
        "Cisco Firepower sw:CardEnvStatsHist:timeCollected
        managed object property"
    ::= { cfprSwCardEnvStatsHistEntry 20 }

cfprSwCmclanTable OBJECT-TYPE
    SYNTAX           SEQUENCE OF CfprSwCmclanEntry
    MAX-ACCESS       not-accessible
    STATUS           current
    DESCRIPTION
        "Cisco Firepower sw:Cmclan managed object table"
    ::= { cfprSwObjects 8 }

cfprSwCmclanEntry OBJECT-TYPE
    SYNTAX           CfprSwCmclanEntry
    MAX-ACCESS       not-accessible
    STATUS           current
    DESCRIPTION
        "Entry for the cfprSwCmclanTable table."
    INDEX { cfprSwCmclanInstanceId }
    ::= { cfprSwCmclanTable 1 }

CfprSwCmclanEntry ::= SEQUENCE {
    cfprSwCmclanInstanceId                                           CfprManagedObjectId,
    cfprSwCmclanDn                                                   CfprManagedObjectDn,
    cfprSwCmclanRn                                                   SnmpAdminString,
    cfprSwCmclanCimcIds                                              CfprSwCimcId,
    cfprSwCmclanEpDn                                                 SnmpAdminString,
    cfprSwCmclanId                                                   Gauge32,
    cfprSwCmclanIfRole                                               CfprNetworkPortRole,
    cfprSwCmclanIfType                                               CfprNetworkVnetEpIfType,
    cfprSwCmclanLocale                                               CfprNetworkLocale,
    cfprSwCmclanName                                                 SnmpAdminString,
    cfprSwCmclanPeerDn                                               SnmpAdminString,
    cfprSwCmclanTransport                                            CfprNetworkTransport,
    cfprSwCmclanType                                                 CfprNetworkConnectionType
}

cfprSwCmclanInstanceId OBJECT-TYPE
    SYNTAX       CfprManagedObjectId
    MAX-ACCESS   not-accessible
    STATUS       current
    DESCRIPTION
        "Instance identifier of the managed object."
    ::= { cfprSwCmclanEntry 1 }

cfprSwCmclanDn OBJECT-TYPE
    SYNTAX       CfprManagedObjectDn
    MAX-ACCESS   read-only
    STATUS       current
    DESCRIPTION
        "Cisco Firepower sw:Cmclan:dn managed object property"
    ::= { cfprSwCmclanEntry 2 }

cfprSwCmclanRn OBJECT-TYPE
    SYNTAX       SnmpAdminString
    MAX-ACCESS   read-only
    STATUS       current
    DESCRIPTION
        "Cisco Firepower sw:Cmclan:rn managed object property"
    ::= { cfprSwCmclanEntry 3 }

cfprSwCmclanCimcIds OBJECT-TYPE
    SYNTAX       CfprSwCimcId
    MAX-ACCESS   read-only
    STATUS       current
    DESCRIPTION
        "Cisco Firepower sw:Cmclan:cimcIds managed object property"
    ::= { cfprSwCmclanEntry 4 }

cfprSwCmclanEpDn OBJECT-TYPE
    SYNTAX       SnmpAdminString
    MAX-ACCESS   read-only
    STATUS       current
    DESCRIPTION
        "Cisco Firepower sw:Cmclan:epDn managed object property"
    ::= { cfprSwCmclanEntry 5 }

cfprSwCmclanId OBJECT-TYPE
    SYNTAX       Gauge32
    MAX-ACCESS   read-only
    STATUS       current
    DESCRIPTION
        "Cisco Firepower sw:Cmclan:id managed object property"
    ::= { cfprSwCmclanEntry 6 }

cfprSwCmclanIfRole OBJECT-TYPE
    SYNTAX       CfprNetworkPortRole
    MAX-ACCESS   read-only
    STATUS       current
    DESCRIPTION
        "Cisco Firepower sw:Cmclan:ifRole managed object property"
    ::= { cfprSwCmclanEntry 7 }

cfprSwCmclanIfType OBJECT-TYPE
    SYNTAX       CfprNetworkVnetEpIfType
    MAX-ACCESS   read-only
    STATUS       current
    DESCRIPTION
        "Cisco Firepower sw:Cmclan:ifType managed object property"
    ::= { cfprSwCmclanEntry 8 }

cfprSwCmclanLocale OBJECT-TYPE
    SYNTAX       CfprNetworkLocale
    MAX-ACCESS   read-only
    STATUS       current
    DESCRIPTION
        "Cisco Firepower sw:Cmclan:locale managed object property"
    ::= { cfprSwCmclanEntry 9 }

cfprSwCmclanName OBJECT-TYPE
    SYNTAX       SnmpAdminString
    MAX-ACCESS   read-only
    STATUS       current
    DESCRIPTION
        "Cisco Firepower sw:Cmclan:name managed object property"
    ::= { cfprSwCmclanEntry 10 }

cfprSwCmclanPeerDn OBJECT-TYPE
    SYNTAX       SnmpAdminString
    MAX-ACCESS   read-only
    STATUS       current
    DESCRIPTION
        "Cisco Firepower sw:Cmclan:peerDn managed object property"
    ::= { cfprSwCmclanEntry 11 }

cfprSwCmclanTransport OBJECT-TYPE
    SYNTAX       CfprNetworkTransport
    MAX-ACCESS   read-only
    STATUS       current
    DESCRIPTION
        "Cisco Firepower sw:Cmclan:transport managed object property"
    ::= { cfprSwCmclanEntry 12 }

cfprSwCmclanType OBJECT-TYPE
    SYNTAX       CfprNetworkConnectionType
    MAX-ACCESS   read-only
    STATUS       current
    DESCRIPTION
        "Cisco Firepower sw:Cmclan:type managed object property"
    ::= { cfprSwCmclanEntry 13 }

cfprSwEnvStatsTable OBJECT-TYPE
    SYNTAX           SEQUENCE OF CfprSwEnvStatsEntry
    MAX-ACCESS       not-accessible
    STATUS           current
    DESCRIPTION
        "Cisco Firepower sw:EnvStats managed object table"
    ::= { cfprSwObjects 9 }

cfprSwEnvStatsEntry OBJECT-TYPE
    SYNTAX           CfprSwEnvStatsEntry
    MAX-ACCESS       not-accessible
    STATUS           current
    DESCRIPTION
        "Entry for the cfprSwEnvStatsTable table."
    INDEX { cfprSwEnvStatsInstanceId }
    ::= { cfprSwEnvStatsTable 1 }

CfprSwEnvStatsEntry ::= SEQUENCE {
    cfprSwEnvStatsInstanceId                                         CfprManagedObjectId,
    cfprSwEnvStatsDn                                                 CfprManagedObjectDn,
    cfprSwEnvStatsRn                                                 SnmpAdminString,
    cfprSwEnvStatsFanCtrlrInlet1                                     INTEGER,
    cfprSwEnvStatsFanCtrlrInlet1Avg                                  INTEGER,
    cfprSwEnvStatsFanCtrlrInlet1Max                                  INTEGER,
    cfprSwEnvStatsFanCtrlrInlet1Min                                  INTEGER,
    cfprSwEnvStatsFanCtrlrInlet2                                     INTEGER,
    cfprSwEnvStatsFanCtrlrInlet2Avg                                  INTEGER,
    cfprSwEnvStatsFanCtrlrInlet2Max                                  INTEGER,
    cfprSwEnvStatsFanCtrlrInlet2Min                                  INTEGER,
    cfprSwEnvStatsFanCtrlrInlet3                                     INTEGER,
    cfprSwEnvStatsFanCtrlrInlet3Avg                                  INTEGER,
    cfprSwEnvStatsFanCtrlrInlet3Max                                  INTEGER,
    cfprSwEnvStatsFanCtrlrInlet3Min                                  INTEGER,
    cfprSwEnvStatsFanCtrlrInlet4                                     INTEGER,
    cfprSwEnvStatsFanCtrlrInlet4Avg                                  INTEGER,
    cfprSwEnvStatsFanCtrlrInlet4Max                                  INTEGER,
    cfprSwEnvStatsFanCtrlrInlet4Min                                  INTEGER,
    cfprSwEnvStatsIntervals                                          Gauge32,
    cfprSwEnvStatsMainBoardOutlet1                                   INTEGER,
    cfprSwEnvStatsMainBoardOutlet1Avg                                INTEGER,
    cfprSwEnvStatsMainBoardOutlet1Max                                INTEGER,
    cfprSwEnvStatsMainBoardOutlet1Min                                INTEGER,
    cfprSwEnvStatsMainBoardOutlet2                                   INTEGER,
    cfprSwEnvStatsMainBoardOutlet2Avg                                INTEGER,
    cfprSwEnvStatsMainBoardOutlet2Max                                INTEGER,
    cfprSwEnvStatsMainBoardOutlet2Min                                INTEGER,
    cfprSwEnvStatsPsuCtrlrInlet1                                     INTEGER,
    cfprSwEnvStatsPsuCtrlrInlet1Avg                                  INTEGER,
    cfprSwEnvStatsPsuCtrlrInlet1Max                                  INTEGER,
    cfprSwEnvStatsPsuCtrlrInlet1Min                                  INTEGER,
    cfprSwEnvStatsPsuCtrlrInlet2                                     INTEGER,
    cfprSwEnvStatsPsuCtrlrInlet2Avg                                  INTEGER,
    cfprSwEnvStatsPsuCtrlrInlet2Max                                  INTEGER,
    cfprSwEnvStatsPsuCtrlrInlet2Min                                  INTEGER,
    cfprSwEnvStatsSuspect                                            TruthValue,
    cfprSwEnvStatsThresholded                                        CfprSwEnvStatsThresholded,
    cfprSwEnvStatsTimeCollected                                      DateAndTime,
    cfprSwEnvStatsUpdate                                             Gauge32
}

cfprSwEnvStatsInstanceId OBJECT-TYPE
    SYNTAX       CfprManagedObjectId
    MAX-ACCESS   not-accessible
    STATUS       current
    DESCRIPTION
        "Instance identifier of the managed object."
    ::= { cfprSwEnvStatsEntry 1 }

cfprSwEnvStatsDn OBJECT-TYPE
    SYNTAX       CfprManagedObjectDn
    MAX-ACCESS   read-only
    STATUS       current
    DESCRIPTION
        "Cisco Firepower sw:EnvStats:dn managed object property"
    ::= { cfprSwEnvStatsEntry 2 }

cfprSwEnvStatsRn OBJECT-TYPE
    SYNTAX       SnmpAdminString
    MAX-ACCESS   read-only
    STATUS       current
    DESCRIPTION
        "Cisco Firepower sw:EnvStats:rn managed object property"
    ::= { cfprSwEnvStatsEntry 3 }

cfprSwEnvStatsFanCtrlrInlet1 OBJECT-TYPE
    SYNTAX       INTEGER
    MAX-ACCESS   read-only
    STATUS       current
    DESCRIPTION
        "Cisco Firepower sw:EnvStats:fanCtrlrInlet1 managed
        object property"
    ::= { cfprSwEnvStatsEntry 4 }

cfprSwEnvStatsFanCtrlrInlet1Avg OBJECT-TYPE
    SYNTAX       INTEGER
    MAX-ACCESS   read-only
    STATUS       current
    DESCRIPTION
        "Cisco Firepower sw:EnvStats:fanCtrlrInlet1Avg
        managed object property"
    ::= { cfprSwEnvStatsEntry 5 }

cfprSwEnvStatsFanCtrlrInlet1Max OBJECT-TYPE
    SYNTAX       INTEGER
    MAX-ACCESS   read-only
    STATUS       current
    DESCRIPTION
        "Cisco Firepower sw:EnvStats:fanCtrlrInlet1Max
        managed object property"
    ::= { cfprSwEnvStatsEntry 6 }

cfprSwEnvStatsFanCtrlrInlet1Min OBJECT-TYPE
    SYNTAX       INTEGER
    MAX-ACCESS   read-only
    STATUS       current
    DESCRIPTION
        "Cisco Firepower sw:EnvStats:fanCtrlrInlet1Min
        managed object property"
    ::= { cfprSwEnvStatsEntry 7 }

cfprSwEnvStatsFanCtrlrInlet2 OBJECT-TYPE
    SYNTAX       INTEGER
    MAX-ACCESS   read-only
    STATUS       current
    DESCRIPTION
        "Cisco Firepower sw:EnvStats:fanCtrlrInlet2 managed
        object property"
    ::= { cfprSwEnvStatsEntry 8 }

cfprSwEnvStatsFanCtrlrInlet2Avg OBJECT-TYPE
    SYNTAX       INTEGER
    MAX-ACCESS   read-only
    STATUS       current
    DESCRIPTION
        "Cisco Firepower sw:EnvStats:fanCtrlrInlet2Avg
        managed object property"
    ::= { cfprSwEnvStatsEntry 9 }

cfprSwEnvStatsFanCtrlrInlet2Max OBJECT-TYPE
    SYNTAX       INTEGER
    MAX-ACCESS   read-only
    STATUS       current
    DESCRIPTION
        "Cisco Firepower sw:EnvStats:fanCtrlrInlet2Max
        managed object property"
    ::= { cfprSwEnvStatsEntry 10 }

cfprSwEnvStatsFanCtrlrInlet2Min OBJECT-TYPE
    SYNTAX       INTEGER
    MAX-ACCESS   read-only
    STATUS       current
    DESCRIPTION
        "Cisco Firepower sw:EnvStats:fanCtrlrInlet2Min
        managed object property"
    ::= { cfprSwEnvStatsEntry 11 }

cfprSwEnvStatsFanCtrlrInlet3 OBJECT-TYPE
    SYNTAX       INTEGER
    MAX-ACCESS   read-only
    STATUS       current
    DESCRIPTION
        "Cisco Firepower sw:EnvStats:fanCtrlrInlet3 managed
        object property"
    ::= { cfprSwEnvStatsEntry 12 }

cfprSwEnvStatsFanCtrlrInlet3Avg OBJECT-TYPE
    SYNTAX       INTEGER
    MAX-ACCESS   read-only
    STATUS       current
    DESCRIPTION
        "Cisco Firepower sw:EnvStats:fanCtrlrInlet3Avg
        managed object property"
    ::= { cfprSwEnvStatsEntry 13 }

cfprSwEnvStatsFanCtrlrInlet3Max OBJECT-TYPE
    SYNTAX       INTEGER
    MAX-ACCESS   read-only
    STATUS       current
    DESCRIPTION
        "Cisco Firepower sw:EnvStats:fanCtrlrInlet3Max
        managed object property"
    ::= { cfprSwEnvStatsEntry 14 }

cfprSwEnvStatsFanCtrlrInlet3Min OBJECT-TYPE
    SYNTAX       INTEGER
    MAX-ACCESS   read-only
    STATUS       current
    DESCRIPTION
        "Cisco Firepower sw:EnvStats:fanCtrlrInlet3Min
        managed object property"
    ::= { cfprSwEnvStatsEntry 15 }

cfprSwEnvStatsFanCtrlrInlet4 OBJECT-TYPE
    SYNTAX       INTEGER
    MAX-ACCESS   read-only
    STATUS       current
    DESCRIPTION
        "Cisco Firepower sw:EnvStats:fanCtrlrInlet4 managed
        object property"
    ::= { cfprSwEnvStatsEntry 16 }

cfprSwEnvStatsFanCtrlrInlet4Avg OBJECT-TYPE
    SYNTAX       INTEGER
    MAX-ACCESS   read-only
    STATUS       current
    DESCRIPTION
        "Cisco Firepower sw:EnvStats:fanCtrlrInlet4Avg
        managed object property"
    ::= { cfprSwEnvStatsEntry 17 }

cfprSwEnvStatsFanCtrlrInlet4Max OBJECT-TYPE
    SYNTAX       INTEGER
    MAX-ACCESS   read-only
    STATUS       current
    DESCRIPTION
        "Cisco Firepower sw:EnvStats:fanCtrlrInlet4Max
        managed object property"
    ::= { cfprSwEnvStatsEntry 18 }

cfprSwEnvStatsFanCtrlrInlet4Min OBJECT-TYPE
    SYNTAX       INTEGER
    MAX-ACCESS   read-only
    STATUS       current
    DESCRIPTION
        "Cisco Firepower sw:EnvStats:fanCtrlrInlet4Min
        managed object property"
    ::= { cfprSwEnvStatsEntry 19 }

cfprSwEnvStatsIntervals OBJECT-TYPE
    SYNTAX       Gauge32
    MAX-ACCESS   read-only
    STATUS       current
    DESCRIPTION
        "Cisco Firepower sw:EnvStats:intervals managed object property"
    ::= { cfprSwEnvStatsEntry 20 }

cfprSwEnvStatsMainBoardOutlet1 OBJECT-TYPE
    SYNTAX       INTEGER
    MAX-ACCESS   read-only
    STATUS       current
    DESCRIPTION
        "Cisco Firepower sw:EnvStats:mainBoardOutlet1 managed
        object property"
    ::= { cfprSwEnvStatsEntry 21 }

cfprSwEnvStatsMainBoardOutlet1Avg OBJECT-TYPE
    SYNTAX       INTEGER
    MAX-ACCESS   read-only
    STATUS       current
    DESCRIPTION
        "Cisco Firepower sw:EnvStats:mainBoardOutlet1Avg
        managed object property"
    ::= { cfprSwEnvStatsEntry 22 }

cfprSwEnvStatsMainBoardOutlet1Max OBJECT-TYPE
    SYNTAX       INTEGER
    MAX-ACCESS   read-only
    STATUS       current
    DESCRIPTION
        "Cisco Firepower sw:EnvStats:mainBoardOutlet1Max
        managed object property"
    ::= { cfprSwEnvStatsEntry 23 }

cfprSwEnvStatsMainBoardOutlet1Min OBJECT-TYPE
    SYNTAX       INTEGER
    MAX-ACCESS   read-only
    STATUS       current
    DESCRIPTION
        "Cisco Firepower sw:EnvStats:mainBoardOutlet1Min
        managed object property"
    ::= { cfprSwEnvStatsEntry 24 }

cfprSwEnvStatsMainBoardOutlet2 OBJECT-TYPE
    SYNTAX       INTEGER
    MAX-ACCESS   read-only
    STATUS       current
    DESCRIPTION
        "Cisco Firepower sw:EnvStats:mainBoardOutlet2 managed
        object property"
    ::= { cfprSwEnvStatsEntry 25 }

cfprSwEnvStatsMainBoardOutlet2Avg OBJECT-TYPE
    SYNTAX       INTEGER
    MAX-ACCESS   read-only
    STATUS       current
    DESCRIPTION
        "Cisco Firepower sw:EnvStats:mainBoardOutlet2Avg
        managed object property"
    ::= { cfprSwEnvStatsEntry 26 }

cfprSwEnvStatsMainBoardOutlet2Max OBJECT-TYPE
    SYNTAX       INTEGER
    MAX-ACCESS   read-only
    STATUS       current
    DESCRIPTION
        "Cisco Firepower sw:EnvStats:mainBoardOutlet2Max
        managed object property"
    ::= { cfprSwEnvStatsEntry 27 }

cfprSwEnvStatsMainBoardOutlet2Min OBJECT-TYPE
    SYNTAX       INTEGER
    MAX-ACCESS   read-only
    STATUS       current
    DESCRIPTION
        "Cisco Firepower sw:EnvStats:mainBoardOutlet2Min
        managed object property"
    ::= { cfprSwEnvStatsEntry 28 }

cfprSwEnvStatsPsuCtrlrInlet1 OBJECT-TYPE
    SYNTAX       INTEGER
    MAX-ACCESS   read-only
    STATUS       current
    DESCRIPTION
        "Cisco Firepower sw:EnvStats:psuCtrlrInlet1 managed
        object property"
    ::= { cfprSwEnvStatsEntry 29 }

cfprSwEnvStatsPsuCtrlrInlet1Avg OBJECT-TYPE
    SYNTAX       INTEGER
    MAX-ACCESS   read-only
    STATUS       current
    DESCRIPTION
        "Cisco Firepower sw:EnvStats:psuCtrlrInlet1Avg
        managed object property"
    ::= { cfprSwEnvStatsEntry 30 }

cfprSwEnvStatsPsuCtrlrInlet1Max OBJECT-TYPE
    SYNTAX       INTEGER
    MAX-ACCESS   read-only
    STATUS       current
    DESCRIPTION
        "Cisco Firepower sw:EnvStats:psuCtrlrInlet1Max
        managed object property"
    ::= { cfprSwEnvStatsEntry 31 }

cfprSwEnvStatsPsuCtrlrInlet1Min OBJECT-TYPE
    SYNTAX       INTEGER
    MAX-ACCESS   read-only
    STATUS       current
    DESCRIPTION
        "Cisco Firepower sw:EnvStats:psuCtrlrInlet1Min
        managed object property"
    ::= { cfprSwEnvStatsEntry 32 }

cfprSwEnvStatsPsuCtrlrInlet2 OBJECT-TYPE
    SYNTAX       INTEGER
    MAX-ACCESS   read-only
    STATUS       current
    DESCRIPTION
        "Cisco Firepower sw:EnvStats:psuCtrlrInlet2 managed
        object property"
    ::= { cfprSwEnvStatsEntry 33 }

cfprSwEnvStatsPsuCtrlrInlet2Avg OBJECT-TYPE
    SYNTAX       INTEGER
    MAX-ACCESS   read-only
    STATUS       current
    DESCRIPTION
        "Cisco Firepower sw:EnvStats:psuCtrlrInlet2Avg
        managed object property"
    ::= { cfprSwEnvStatsEntry 34 }

cfprSwEnvStatsPsuCtrlrInlet2Max OBJECT-TYPE
    SYNTAX       INTEGER
    MAX-ACCESS   read-only
    STATUS       current
    DESCRIPTION
        "Cisco Firepower sw:EnvStats:psuCtrlrInlet2Max
        managed object property"
    ::= { cfprSwEnvStatsEntry 35 }

cfprSwEnvStatsPsuCtrlrInlet2Min OBJECT-TYPE
    SYNTAX       INTEGER
    MAX-ACCESS   read-only
    STATUS       current
    DESCRIPTION
        "Cisco Firepower sw:EnvStats:psuCtrlrInlet2Min
        managed object property"
    ::= { cfprSwEnvStatsEntry 36 }

cfprSwEnvStatsSuspect OBJECT-TYPE
    SYNTAX       TruthValue
    MAX-ACCESS   read-only
    STATUS       current
    DESCRIPTION
        "Cisco Firepower sw:EnvStats:suspect managed object property"
    ::= { cfprSwEnvStatsEntry 37 }

cfprSwEnvStatsThresholded OBJECT-TYPE
    SYNTAX       CfprSwEnvStatsThresholded
    MAX-ACCESS   read-only
    STATUS       current
    DESCRIPTION
        "Cisco Firepower sw:EnvStats:thresholded managed object property"
    ::= { cfprSwEnvStatsEntry 38 }

cfprSwEnvStatsTimeCollected OBJECT-TYPE
    SYNTAX       DateAndTime
    MAX-ACCESS   read-only
    STATUS       current
    DESCRIPTION
        "Cisco Firepower sw:EnvStats:timeCollected managed
        object property"
    ::= { cfprSwEnvStatsEntry 39 }

cfprSwEnvStatsUpdate OBJECT-TYPE
    SYNTAX       Gauge32
    MAX-ACCESS   read-only
    STATUS       current
    DESCRIPTION
        "Cisco Firepower sw:EnvStats:update managed object property"
    ::= { cfprSwEnvStatsEntry 40 }

cfprSwEnvStatsHistTable OBJECT-TYPE
    SYNTAX           SEQUENCE OF CfprSwEnvStatsHistEntry
    MAX-ACCESS       not-accessible
    STATUS           current
    DESCRIPTION
        "Cisco Firepower sw:EnvStatsHist managed object table"
    ::= { cfprSwObjects 10 }

cfprSwEnvStatsHistEntry OBJECT-TYPE
    SYNTAX           CfprSwEnvStatsHistEntry
    MAX-ACCESS       not-accessible
    STATUS           current
    DESCRIPTION
        "Entry for the cfprSwEnvStatsHistTable table."
    INDEX { cfprSwEnvStatsHistInstanceId }
    ::= { cfprSwEnvStatsHistTable 1 }

CfprSwEnvStatsHistEntry ::= SEQUENCE {
    cfprSwEnvStatsHistInstanceId                                     CfprManagedObjectId,
    cfprSwEnvStatsHistDn                                             CfprManagedObjectDn,
    cfprSwEnvStatsHistRn                                             SnmpAdminString,
    cfprSwEnvStatsHistFanCtrlrInlet1                                 INTEGER,
    cfprSwEnvStatsHistFanCtrlrInlet1Avg                              INTEGER,
    cfprSwEnvStatsHistFanCtrlrInlet1Max                              INTEGER,
    cfprSwEnvStatsHistFanCtrlrInlet1Min                              INTEGER,
    cfprSwEnvStatsHistFanCtrlrInlet2                                 INTEGER,
    cfprSwEnvStatsHistFanCtrlrInlet2Avg                              INTEGER,
    cfprSwEnvStatsHistFanCtrlrInlet2Max                              INTEGER,
    cfprSwEnvStatsHistFanCtrlrInlet2Min                              INTEGER,
    cfprSwEnvStatsHistFanCtrlrInlet3                                 INTEGER,
    cfprSwEnvStatsHistFanCtrlrInlet3Avg                              INTEGER,
    cfprSwEnvStatsHistFanCtrlrInlet3Max                              INTEGER,
    cfprSwEnvStatsHistFanCtrlrInlet3Min                              INTEGER,
    cfprSwEnvStatsHistFanCtrlrInlet4                                 INTEGER,
    cfprSwEnvStatsHistFanCtrlrInlet4Avg                              INTEGER,
    cfprSwEnvStatsHistFanCtrlrInlet4Max                              INTEGER,
    cfprSwEnvStatsHistFanCtrlrInlet4Min                              INTEGER,
    cfprSwEnvStatsHistId                                             Unsigned64,
    cfprSwEnvStatsHistMainBoardOutlet1                               INTEGER,
    cfprSwEnvStatsHistMainBoardOutlet1Avg                            INTEGER,
    cfprSwEnvStatsHistMainBoardOutlet1Max                            INTEGER,
    cfprSwEnvStatsHistMainBoardOutlet1Min                            INTEGER,
    cfprSwEnvStatsHistMainBoardOutlet2                               INTEGER,
    cfprSwEnvStatsHistMainBoardOutlet2Avg                            INTEGER,
    cfprSwEnvStatsHistMainBoardOutlet2Max                            INTEGER,
    cfprSwEnvStatsHistMainBoardOutlet2Min                            INTEGER,
    cfprSwEnvStatsHistMostRecent                                     TruthValue,
    cfprSwEnvStatsHistPsuCtrlrInlet1                                 INTEGER,
    cfprSwEnvStatsHistPsuCtrlrInlet1Avg                              INTEGER,
    cfprSwEnvStatsHistPsuCtrlrInlet1Max                              INTEGER,
    cfprSwEnvStatsHistPsuCtrlrInlet1Min                              INTEGER,
    cfprSwEnvStatsHistPsuCtrlrInlet2                                 INTEGER,
    cfprSwEnvStatsHistPsuCtrlrInlet2Avg                              INTEGER,
    cfprSwEnvStatsHistPsuCtrlrInlet2Max                              INTEGER,
    cfprSwEnvStatsHistPsuCtrlrInlet2Min                              INTEGER,
    cfprSwEnvStatsHistSuspect                                        TruthValue,
    cfprSwEnvStatsHistThresholded                                    CfprSwEnvStatsHistThresholded,
    cfprSwEnvStatsHistTimeCollected                                  DateAndTime
}

cfprSwEnvStatsHistInstanceId OBJECT-TYPE
    SYNTAX       CfprManagedObjectId
    MAX-ACCESS   not-accessible
    STATUS       current
    DESCRIPTION
        "Instance identifier of the managed object."
    ::= { cfprSwEnvStatsHistEntry 1 }

cfprSwEnvStatsHistDn OBJECT-TYPE
    SYNTAX       CfprManagedObjectDn
    MAX-ACCESS   read-only
    STATUS       current
    DESCRIPTION
        "Cisco Firepower sw:EnvStatsHist:dn managed object property"
    ::= { cfprSwEnvStatsHistEntry 2 }

cfprSwEnvStatsHistRn OBJECT-TYPE
    SYNTAX       SnmpAdminString
    MAX-ACCESS   read-only
    STATUS       current
    DESCRIPTION
        "Cisco Firepower sw:EnvStatsHist:rn managed object property"
    ::= { cfprSwEnvStatsHistEntry 3 }

cfprSwEnvStatsHistFanCtrlrInlet1 OBJECT-TYPE
    SYNTAX       INTEGER
    MAX-ACCESS   read-only
    STATUS       current
    DESCRIPTION
        "Cisco Firepower sw:EnvStatsHist:fanCtrlrInlet1
        managed object property"
    ::= { cfprSwEnvStatsHistEntry 4 }

cfprSwEnvStatsHistFanCtrlrInlet1Avg OBJECT-TYPE
    SYNTAX       INTEGER
    MAX-ACCESS   read-only
    STATUS       current
    DESCRIPTION
        "Cisco Firepower sw:EnvStatsHist:fanCtrlrInlet1Avg
        managed object property"
    ::= { cfprSwEnvStatsHistEntry 5 }

cfprSwEnvStatsHistFanCtrlrInlet1Max OBJECT-TYPE
    SYNTAX       INTEGER
    MAX-ACCESS   read-only
    STATUS       current
    DESCRIPTION
        "Cisco Firepower sw:EnvStatsHist:fanCtrlrInlet1Max
        managed object property"
    ::= { cfprSwEnvStatsHistEntry 6 }

cfprSwEnvStatsHistFanCtrlrInlet1Min OBJECT-TYPE
    SYNTAX       INTEGER
    MAX-ACCESS   read-only
    STATUS       current
    DESCRIPTION
        "Cisco Firepower sw:EnvStatsHist:fanCtrlrInlet1Min
        managed object property"
    ::= { cfprSwEnvStatsHistEntry 7 }

cfprSwEnvStatsHistFanCtrlrInlet2 OBJECT-TYPE
    SYNTAX       INTEGER
    MAX-ACCESS   read-only
    STATUS       current
    DESCRIPTION
        "Cisco Firepower sw:EnvStatsHist:fanCtrlrInlet2
        managed object property"
    ::= { cfprSwEnvStatsHistEntry 8 }

cfprSwEnvStatsHistFanCtrlrInlet2Avg OBJECT-TYPE
    SYNTAX       INTEGER
    MAX-ACCESS   read-only
    STATUS       current
    DESCRIPTION
        "Cisco Firepower sw:EnvStatsHist:fanCtrlrInlet2Avg
        managed object property"
    ::= { cfprSwEnvStatsHistEntry 9 }

cfprSwEnvStatsHistFanCtrlrInlet2Max OBJECT-TYPE
    SYNTAX       INTEGER
    MAX-ACCESS   read-only
    STATUS       current
    DESCRIPTION
        "Cisco Firepower sw:EnvStatsHist:fanCtrlrInlet2Max
        managed object property"
    ::= { cfprSwEnvStatsHistEntry 10 }

cfprSwEnvStatsHistFanCtrlrInlet2Min OBJECT-TYPE
    SYNTAX       INTEGER
    MAX-ACCESS   read-only
    STATUS       current
    DESCRIPTION
        "Cisco Firepower sw:EnvStatsHist:fanCtrlrInlet2Min
        managed object property"
    ::= { cfprSwEnvStatsHistEntry 11 }

cfprSwEnvStatsHistFanCtrlrInlet3 OBJECT-TYPE
    SYNTAX       INTEGER
    MAX-ACCESS   read-only
    STATUS       current
    DESCRIPTION
        "Cisco Firepower sw:EnvStatsHist:fanCtrlrInlet3
        managed object property"
    ::= { cfprSwEnvStatsHistEntry 12 }

cfprSwEnvStatsHistFanCtrlrInlet3Avg OBJECT-TYPE
    SYNTAX       INTEGER
    MAX-ACCESS   read-only
    STATUS       current
    DESCRIPTION
        "Cisco Firepower sw:EnvStatsHist:fanCtrlrInlet3Avg
        managed object property"
    ::= { cfprSwEnvStatsHistEntry 13 }

cfprSwEnvStatsHistFanCtrlrInlet3Max OBJECT-TYPE
    SYNTAX       INTEGER
    MAX-ACCESS   read-only
    STATUS       current
    DESCRIPTION
        "Cisco Firepower sw:EnvStatsHist:fanCtrlrInlet3Max
        managed object property"
    ::= { cfprSwEnvStatsHistEntry 14 }

cfprSwEnvStatsHistFanCtrlrInlet3Min OBJECT-TYPE
    SYNTAX       INTEGER
    MAX-ACCESS   read-only
    STATUS       current
    DESCRIPTION
        "Cisco Firepower sw:EnvStatsHist:fanCtrlrInlet3Min
        managed object property"
    ::= { cfprSwEnvStatsHistEntry 15 }

cfprSwEnvStatsHistFanCtrlrInlet4 OBJECT-TYPE
    SYNTAX       INTEGER
    MAX-ACCESS   read-only
    STATUS       current
    DESCRIPTION
        "Cisco Firepower sw:EnvStatsHist:fanCtrlrInlet4
        managed object property"
    ::= { cfprSwEnvStatsHistEntry 16 }

cfprSwEnvStatsHistFanCtrlrInlet4Avg OBJECT-TYPE
    SYNTAX       INTEGER
    MAX-ACCESS   read-only
    STATUS       current
    DESCRIPTION
        "Cisco Firepower sw:EnvStatsHist:fanCtrlrInlet4Avg
        managed object property"
    ::= { cfprSwEnvStatsHistEntry 17 }

cfprSwEnvStatsHistFanCtrlrInlet4Max OBJECT-TYPE
    SYNTAX       INTEGER
    MAX-ACCESS   read-only
    STATUS       current
    DESCRIPTION
        "Cisco Firepower sw:EnvStatsHist:fanCtrlrInlet4Max
        managed object property"
    ::= { cfprSwEnvStatsHistEntry 18 }

cfprSwEnvStatsHistFanCtrlrInlet4Min OBJECT-TYPE
    SYNTAX       INTEGER
    MAX-ACCESS   read-only
    STATUS       current
    DESCRIPTION
        "Cisco Firepower sw:EnvStatsHist:fanCtrlrInlet4Min
        managed object property"
    ::= { cfprSwEnvStatsHistEntry 19 }

cfprSwEnvStatsHistId OBJECT-TYPE
    SYNTAX       Unsigned64
    MAX-ACCESS   read-only
    STATUS       current
    DESCRIPTION
        "Cisco Firepower sw:EnvStatsHist:id managed object property"
    ::= { cfprSwEnvStatsHistEntry 20 }

cfprSwEnvStatsHistMainBoardOutlet1 OBJECT-TYPE
    SYNTAX       INTEGER
    MAX-ACCESS   read-only
    STATUS       current
    DESCRIPTION
        "Cisco Firepower sw:EnvStatsHist:mainBoardOutlet1
        managed object property"
    ::= { cfprSwEnvStatsHistEntry 21 }

cfprSwEnvStatsHistMainBoardOutlet1Avg OBJECT-TYPE
    SYNTAX       INTEGER
    MAX-ACCESS   read-only
    STATUS       current
    DESCRIPTION
        "Cisco Firepower sw:EnvStatsHist:mainBoardOutlet1Avg
        managed object property"
    ::= { cfprSwEnvStatsHistEntry 22 }

cfprSwEnvStatsHistMainBoardOutlet1Max OBJECT-TYPE
    SYNTAX       INTEGER
    MAX-ACCESS   read-only
    STATUS       current
    DESCRIPTION
        "Cisco Firepower sw:EnvStatsHist:mainBoardOutlet1Max
        managed object property"
    ::= { cfprSwEnvStatsHistEntry 23 }

cfprSwEnvStatsHistMainBoardOutlet1Min OBJECT-TYPE
    SYNTAX       INTEGER
    MAX-ACCESS   read-only
    STATUS       current
    DESCRIPTION
        "Cisco Firepower sw:EnvStatsHist:mainBoardOutlet1Min
        managed object property"
    ::= { cfprSwEnvStatsHistEntry 24 }

cfprSwEnvStatsHistMainBoardOutlet2 OBJECT-TYPE
    SYNTAX       INTEGER
    MAX-ACCESS   read-only
    STATUS       current
    DESCRIPTION
        "Cisco Firepower sw:EnvStatsHist:mainBoardOutlet2
        managed object property"
    ::= { cfprSwEnvStatsHistEntry 25 }

cfprSwEnvStatsHistMainBoardOutlet2Avg OBJECT-TYPE
    SYNTAX       INTEGER
    MAX-ACCESS   read-only
    STATUS       current
    DESCRIPTION
        "Cisco Firepower sw:EnvStatsHist:mainBoardOutlet2Avg
        managed object property"
    ::= { cfprSwEnvStatsHistEntry 26 }

cfprSwEnvStatsHistMainBoardOutlet2Max OBJECT-TYPE
    SYNTAX       INTEGER
    MAX-ACCESS   read-only
    STATUS       current
    DESCRIPTION
        "Cisco Firepower sw:EnvStatsHist:mainBoardOutlet2Max
        managed object property"
    ::= { cfprSwEnvStatsHistEntry 27 }

cfprSwEnvStatsHistMainBoardOutlet2Min OBJECT-TYPE
    SYNTAX       INTEGER
    MAX-ACCESS   read-only
    STATUS       current
    DESCRIPTION
        "Cisco Firepower sw:EnvStatsHist:mainBoardOutlet2Min
        managed object property"
    ::= { cfprSwEnvStatsHistEntry 28 }

cfprSwEnvStatsHistMostRecent OBJECT-TYPE
    SYNTAX       TruthValue
    MAX-ACCESS   read-only
    STATUS       current
    DESCRIPTION
        "Cisco Firepower sw:EnvStatsHist:mostRecent managed
        object property"
    ::= { cfprSwEnvStatsHistEntry 29 }

cfprSwEnvStatsHistPsuCtrlrInlet1 OBJECT-TYPE
    SYNTAX       INTEGER
    MAX-ACCESS   read-only
    STATUS       current
    DESCRIPTION
        "Cisco Firepower sw:EnvStatsHist:psuCtrlrInlet1
        managed object property"
    ::= { cfprSwEnvStatsHistEntry 30 }

cfprSwEnvStatsHistPsuCtrlrInlet1Avg OBJECT-TYPE
    SYNTAX       INTEGER
    MAX-ACCESS   read-only
    STATUS       current
    DESCRIPTION
        "Cisco Firepower sw:EnvStatsHist:psuCtrlrInlet1Avg
        managed object property"
    ::= { cfprSwEnvStatsHistEntry 31 }

cfprSwEnvStatsHistPsuCtrlrInlet1Max OBJECT-TYPE
    SYNTAX       INTEGER
    MAX-ACCESS   read-only
    STATUS       current
    DESCRIPTION
        "Cisco Firepower sw:EnvStatsHist:psuCtrlrInlet1Max
        managed object property"
    ::= { cfprSwEnvStatsHistEntry 32 }

cfprSwEnvStatsHistPsuCtrlrInlet1Min OBJECT-TYPE
    SYNTAX       INTEGER
    MAX-ACCESS   read-only
    STATUS       current
    DESCRIPTION
        "Cisco Firepower sw:EnvStatsHist:psuCtrlrInlet1Min
        managed object property"
    ::= { cfprSwEnvStatsHistEntry 33 }

cfprSwEnvStatsHistPsuCtrlrInlet2 OBJECT-TYPE
    SYNTAX       INTEGER
    MAX-ACCESS   read-only
    STATUS       current
    DESCRIPTION
        "Cisco Firepower sw:EnvStatsHist:psuCtrlrInlet2
        managed object property"
    ::= { cfprSwEnvStatsHistEntry 34 }

cfprSwEnvStatsHistPsuCtrlrInlet2Avg OBJECT-TYPE
    SYNTAX       INTEGER
    MAX-ACCESS   read-only
    STATUS       current
    DESCRIPTION
        "Cisco Firepower sw:EnvStatsHist:psuCtrlrInlet2Avg
        managed object property"
    ::= { cfprSwEnvStatsHistEntry 35 }

cfprSwEnvStatsHistPsuCtrlrInlet2Max OBJECT-TYPE
    SYNTAX       INTEGER
    MAX-ACCESS   read-only
    STATUS       current
    DESCRIPTION
        "Cisco Firepower sw:EnvStatsHist:psuCtrlrInlet2Max
        managed object property"
    ::= { cfprSwEnvStatsHistEntry 36 }

cfprSwEnvStatsHistPsuCtrlrInlet2Min OBJECT-TYPE
    SYNTAX       INTEGER
    MAX-ACCESS   read-only
    STATUS       current
    DESCRIPTION
        "Cisco Firepower sw:EnvStatsHist:psuCtrlrInlet2Min
        managed object property"
    ::= { cfprSwEnvStatsHistEntry 37 }

cfprSwEnvStatsHistSuspect OBJECT-TYPE
    SYNTAX       TruthValue
    MAX-ACCESS   read-only
    STATUS       current
    DESCRIPTION
        "Cisco Firepower sw:EnvStatsHist:suspect managed object property"
    ::= { cfprSwEnvStatsHistEntry 38 }

cfprSwEnvStatsHistThresholded OBJECT-TYPE
    SYNTAX       CfprSwEnvStatsHistThresholded
    MAX-ACCESS   read-only
    STATUS       current
    DESCRIPTION
        "Cisco Firepower sw:EnvStatsHist:thresholded managed
        object property"
    ::= { cfprSwEnvStatsHistEntry 39 }

cfprSwEnvStatsHistTimeCollected OBJECT-TYPE
    SYNTAX       DateAndTime
    MAX-ACCESS   read-only
    STATUS       current
    DESCRIPTION
        "Cisco Firepower sw:EnvStatsHist:timeCollected
        managed object property"
    ::= { cfprSwEnvStatsHistEntry 40 }

cfprSwEthEstcEpTable OBJECT-TYPE
    SYNTAX           SEQUENCE OF CfprSwEthEstcEpEntry
    MAX-ACCESS       not-accessible
    STATUS           current
    DESCRIPTION
        "Cisco Firepower sw:EthEstcEp managed object table"
    ::= { cfprSwObjects 11 }

cfprSwEthEstcEpEntry OBJECT-TYPE
    SYNTAX           CfprSwEthEstcEpEntry
    MAX-ACCESS       not-accessible
    STATUS           current
    DESCRIPTION
        "Entry for the cfprSwEthEstcEpTable table."
    INDEX { cfprSwEthEstcEpInstanceId }
    ::= { cfprSwEthEstcEpTable 1 }

CfprSwEthEstcEpEntry ::= SEQUENCE {
    cfprSwEthEstcEpInstanceId                                        CfprManagedObjectId,
    cfprSwEthEstcEpDn                                                CfprManagedObjectDn,
    cfprSwEthEstcEpRn                                                SnmpAdminString,
    cfprSwEthEstcEpAdminSpeed                                        CfprPortEthSpeed,
    cfprSwEthEstcEpAdminState                                        CfprFabricAdminState,
    cfprSwEthEstcEpAggrPortId                                        Gauge32,
    cfprSwEthEstcEpBorderAggrPortId                                  Gauge32,
    cfprSwEthEstcEpBorderPortId                                      Gauge32,
    cfprSwEthEstcEpBorderSlotId                                      Gauge32,
    cfprSwEthEstcEpCdp                                               CfprNwctrlAdminState,
    cfprSwEthEstcEpChassisId                                         Gauge32,
    cfprSwEthEstcEpCosValue                                          Gauge32,
    cfprSwEthEstcEpEpDn                                              SnmpAdminString,
    cfprSwEthEstcEpForgeMac                                          CfprDpsecForgedTransmit,
    cfprSwEthEstcEpIfRole                                            CfprNetworkPortRole,
    cfprSwEthEstcEpIfType                                            CfprSwPIoEpIfType,
    cfprSwEthEstcEpLc                                                CfprSwPIoEpLc,
    cfprSwEthEstcEpLocale                                            CfprSwEstcEpLocale,
    cfprSwEthEstcEpName                                              SnmpAdminString,
    cfprSwEthEstcEpPcId                                              Gauge32,
    cfprSwEthEstcEpPeerAggrPortId                                    Gauge32,
    cfprSwEthEstcEpPeerChassisId                                     Gauge32,
    cfprSwEthEstcEpPeerDn                                            SnmpAdminString,
    cfprSwEthEstcEpPeerPortId                                        Gauge32,
    cfprSwEthEstcEpPeerSlotId                                        Gauge32,
    cfprSwEthEstcEpPinGroupName                                      SnmpAdminString,
    cfprSwEthEstcEpPortId                                            Gauge32,
    cfprSwEthEstcEpPortMode                                          CfprFabricEthEstcPortMode,
    cfprSwEthEstcEpPriorityFlowCtrl                                  CfprFlowctrlPriorityPause,
    cfprSwEthEstcEpRecvFlowCtrl                                      CfprFlowctrlFlowControlRx,
    cfprSwEthEstcEpSendFlowCtrl                                      CfprFlowctrlFlowControlTx,
    cfprSwEthEstcEpSlotId                                            Gauge32,
    cfprSwEthEstcEpSwitchId                                          CfprNetworkSwitchId,
    cfprSwEthEstcEpTransport                                         CfprSwEthEstcEpTransport,
    cfprSwEthEstcEpType                                              CfprNetworkConnectionType,
    cfprSwEthEstcEpUplinkFailAction                                  CfprNwctrlLinkFailAction
}

cfprSwEthEstcEpInstanceId OBJECT-TYPE
    SYNTAX       CfprManagedObjectId
    MAX-ACCESS   not-accessible
    STATUS       current
    DESCRIPTION
        "Instance identifier of the managed object."
    ::= { cfprSwEthEstcEpEntry 1 }

cfprSwEthEstcEpDn OBJECT-TYPE
    SYNTAX       CfprManagedObjectDn
    MAX-ACCESS   read-only
    STATUS       current
    DESCRIPTION
        "Cisco Firepower sw:EthEstcEp:dn managed object property"
    ::= { cfprSwEthEstcEpEntry 2 }

cfprSwEthEstcEpRn OBJECT-TYPE
    SYNTAX       SnmpAdminString
    MAX-ACCESS   read-only
    STATUS       current
    DESCRIPTION
        "Cisco Firepower sw:EthEstcEp:rn managed object property"
    ::= { cfprSwEthEstcEpEntry 3 }

cfprSwEthEstcEpAdminSpeed OBJECT-TYPE
    SYNTAX       CfprPortEthSpeed
    MAX-ACCESS   read-only
    STATUS       current
    DESCRIPTION
        "Cisco Firepower sw:EthEstcEp:adminSpeed managed object property"
    ::= { cfprSwEthEstcEpEntry 4 }

cfprSwEthEstcEpAdminState OBJECT-TYPE
    SYNTAX       CfprFabricAdminState
    MAX-ACCESS   read-only
    STATUS       current
    DESCRIPTION
        "Cisco Firepower sw:EthEstcEp:adminState managed object property"
    ::= { cfprSwEthEstcEpEntry 5 }

cfprSwEthEstcEpAggrPortId OBJECT-TYPE
    SYNTAX       Gauge32
    MAX-ACCESS   read-only
    STATUS       current
    DESCRIPTION
        "Cisco Firepower sw:EthEstcEp:aggrPortId managed object property"
    ::= { cfprSwEthEstcEpEntry 6 }

cfprSwEthEstcEpBorderAggrPortId OBJECT-TYPE
    SYNTAX       Gauge32
    MAX-ACCESS   read-only
    STATUS       current
    DESCRIPTION
        "Cisco Firepower sw:EthEstcEp:borderAggrPortId
        managed object property"
    ::= { cfprSwEthEstcEpEntry 7 }

cfprSwEthEstcEpBorderPortId OBJECT-TYPE
    SYNTAX       Gauge32
    MAX-ACCESS   read-only
    STATUS       current
    DESCRIPTION
        "Cisco Firepower sw:EthEstcEp:borderPortId managed
        object property"
    ::= { cfprSwEthEstcEpEntry 8 }

cfprSwEthEstcEpBorderSlotId OBJECT-TYPE
    SYNTAX       Gauge32
    MAX-ACCESS   read-only
    STATUS       current
    DESCRIPTION
        "Cisco Firepower sw:EthEstcEp:borderSlotId managed
        object property"
    ::= { cfprSwEthEstcEpEntry 9 }

cfprSwEthEstcEpCdp OBJECT-TYPE
    SYNTAX       CfprNwctrlAdminState
    MAX-ACCESS   read-only
    STATUS       current
    DESCRIPTION
        "Cisco Firepower sw:EthEstcEp:cdp managed object property"
    ::= { cfprSwEthEstcEpEntry 10 }

cfprSwEthEstcEpChassisId OBJECT-TYPE
    SYNTAX       Gauge32
    MAX-ACCESS   read-only
    STATUS       current
    DESCRIPTION
        "Cisco Firepower sw:EthEstcEp:chassisId managed object property"
    ::= { cfprSwEthEstcEpEntry 11 }

cfprSwEthEstcEpCosValue OBJECT-TYPE
    SYNTAX       Gauge32
    MAX-ACCESS   read-only
    STATUS       current
    DESCRIPTION
        "Cisco Firepower sw:EthEstcEp:cosValue managed object property"
    ::= { cfprSwEthEstcEpEntry 12 }

cfprSwEthEstcEpEpDn OBJECT-TYPE
    SYNTAX       SnmpAdminString
    MAX-ACCESS   read-only
    STATUS       current
    DESCRIPTION
        "Cisco Firepower sw:EthEstcEp:epDn managed object property"
    ::= { cfprSwEthEstcEpEntry 13 }

cfprSwEthEstcEpForgeMac OBJECT-TYPE
    SYNTAX       CfprDpsecForgedTransmit
    MAX-ACCESS   read-only
    STATUS       current
    DESCRIPTION
        "Cisco Firepower sw:EthEstcEp:forgeMac managed object property"
    ::= { cfprSwEthEstcEpEntry 14 }

cfprSwEthEstcEpIfRole OBJECT-TYPE
    SYNTAX       CfprNetworkPortRole
    MAX-ACCESS   read-only
    STATUS       current
    DESCRIPTION
        "Cisco Firepower sw:EthEstcEp:ifRole managed object property"
    ::= { cfprSwEthEstcEpEntry 15 }

cfprSwEthEstcEpIfType OBJECT-TYPE
    SYNTAX       CfprSwPIoEpIfType
    MAX-ACCESS   read-only
    STATUS       current
    DESCRIPTION
        "Cisco Firepower sw:EthEstcEp:ifType managed object property"
    ::= { cfprSwEthEstcEpEntry 16 }

cfprSwEthEstcEpLc OBJECT-TYPE
    SYNTAX       CfprSwPIoEpLc
    MAX-ACCESS   read-only
    STATUS       current
    DESCRIPTION
        "Cisco Firepower sw:EthEstcEp:lc managed object property"
    ::= { cfprSwEthEstcEpEntry 17 }

cfprSwEthEstcEpLocale OBJECT-TYPE
    SYNTAX       CfprSwEstcEpLocale
    MAX-ACCESS   read-only
    STATUS       current
    DESCRIPTION
        "Cisco Firepower sw:EthEstcEp:locale managed object property"
    ::= { cfprSwEthEstcEpEntry 18 }

cfprSwEthEstcEpName OBJECT-TYPE
    SYNTAX       SnmpAdminString
    MAX-ACCESS   read-only
    STATUS       current
    DESCRIPTION
        "Cisco Firepower sw:EthEstcEp:name managed object property"
    ::= { cfprSwEthEstcEpEntry 19 }

cfprSwEthEstcEpPcId OBJECT-TYPE
    SYNTAX       Gauge32
    MAX-ACCESS   read-only
    STATUS       current
    DESCRIPTION
        "Cisco Firepower sw:EthEstcEp:pcId managed object property"
    ::= { cfprSwEthEstcEpEntry 20 }

cfprSwEthEstcEpPeerAggrPortId OBJECT-TYPE
    SYNTAX       Gauge32
    MAX-ACCESS   read-only
    STATUS       current
    DESCRIPTION
        "Cisco Firepower sw:EthEstcEp:peerAggrPortId managed
        object property"
    ::= { cfprSwEthEstcEpEntry 21 }

cfprSwEthEstcEpPeerChassisId OBJECT-TYPE
    SYNTAX       Gauge32
    MAX-ACCESS   read-only
    STATUS       current
    DESCRIPTION
        "Cisco Firepower sw:EthEstcEp:peerChassisId managed
        object property"
    ::= { cfprSwEthEstcEpEntry 22 }

cfprSwEthEstcEpPeerDn OBJECT-TYPE
    SYNTAX       SnmpAdminString
    MAX-ACCESS   read-only
    STATUS       current
    DESCRIPTION
        "Cisco Firepower sw:EthEstcEp:peerDn managed object property"
    ::= { cfprSwEthEstcEpEntry 23 }

cfprSwEthEstcEpPeerPortId OBJECT-TYPE
    SYNTAX       Gauge32
    MAX-ACCESS   read-only
    STATUS       current
    DESCRIPTION
        "Cisco Firepower sw:EthEstcEp:peerPortId managed object property"
    ::= { cfprSwEthEstcEpEntry 24 }

cfprSwEthEstcEpPeerSlotId OBJECT-TYPE
    SYNTAX       Gauge32
    MAX-ACCESS   read-only
    STATUS       current
    DESCRIPTION
        "Cisco Firepower sw:EthEstcEp:peerSlotId managed object property"
    ::= { cfprSwEthEstcEpEntry 25 }

cfprSwEthEstcEpPinGroupName OBJECT-TYPE
    SYNTAX       SnmpAdminString
    MAX-ACCESS   read-only
    STATUS       current
    DESCRIPTION
        "Cisco Firepower sw:EthEstcEp:pinGroupName managed
        object property"
    ::= { cfprSwEthEstcEpEntry 26 }

cfprSwEthEstcEpPortId OBJECT-TYPE
    SYNTAX       Gauge32
    MAX-ACCESS   read-only
    STATUS       current
    DESCRIPTION
        "Cisco Firepower sw:EthEstcEp:portId managed object property"
    ::= { cfprSwEthEstcEpEntry 27 }

cfprSwEthEstcEpPortMode OBJECT-TYPE
    SYNTAX       CfprFabricEthEstcPortMode
    MAX-ACCESS   read-only
    STATUS       current
    DESCRIPTION
        "Cisco Firepower sw:EthEstcEp:portMode managed object property"
    ::= { cfprSwEthEstcEpEntry 28 }

cfprSwEthEstcEpPriorityFlowCtrl OBJECT-TYPE
    SYNTAX       CfprFlowctrlPriorityPause
    MAX-ACCESS   read-only
    STATUS       current
    DESCRIPTION
        "Cisco Firepower sw:EthEstcEp:priorityFlowCtrl
        managed object property"
    ::= { cfprSwEthEstcEpEntry 29 }

cfprSwEthEstcEpRecvFlowCtrl OBJECT-TYPE
    SYNTAX       CfprFlowctrlFlowControlRx
    MAX-ACCESS   read-only
    STATUS       current
    DESCRIPTION
        "Cisco Firepower sw:EthEstcEp:recvFlowCtrl managed
        object property"
    ::= { cfprSwEthEstcEpEntry 30 }

cfprSwEthEstcEpSendFlowCtrl OBJECT-TYPE
    SYNTAX       CfprFlowctrlFlowControlTx
    MAX-ACCESS   read-only
    STATUS       current
    DESCRIPTION
        "Cisco Firepower sw:EthEstcEp:sendFlowCtrl managed
        object property"
    ::= { cfprSwEthEstcEpEntry 31 }

cfprSwEthEstcEpSlotId OBJECT-TYPE
    SYNTAX       Gauge32
    MAX-ACCESS   read-only
    STATUS       current
    DESCRIPTION
        "Cisco Firepower sw:EthEstcEp:slotId managed object property"
    ::= { cfprSwEthEstcEpEntry 32 }

cfprSwEthEstcEpSwitchId OBJECT-TYPE
    SYNTAX       CfprNetworkSwitchId
    MAX-ACCESS   read-only
    STATUS       current
    DESCRIPTION
        "Cisco Firepower sw:EthEstcEp:switchId managed object property"
    ::= { cfprSwEthEstcEpEntry 33 }

cfprSwEthEstcEpTransport OBJECT-TYPE
    SYNTAX       CfprSwEthEstcEpTransport
    MAX-ACCESS   read-only
    STATUS       current
    DESCRIPTION
        "Cisco Firepower sw:EthEstcEp:transport managed object property"
    ::= { cfprSwEthEstcEpEntry 34 }

cfprSwEthEstcEpType OBJECT-TYPE
    SYNTAX       CfprNetworkConnectionType
    MAX-ACCESS   read-only
    STATUS       current
    DESCRIPTION
        "Cisco Firepower sw:EthEstcEp:type managed object property"
    ::= { cfprSwEthEstcEpEntry 35 }

cfprSwEthEstcEpUplinkFailAction OBJECT-TYPE
    SYNTAX       CfprNwctrlLinkFailAction
    MAX-ACCESS   read-only
    STATUS       current
    DESCRIPTION
        "Cisco Firepower sw:EthEstcEp:uplinkFailAction
        managed object property"
    ::= { cfprSwEthEstcEpEntry 36 }

cfprSwEthEstcPcTable OBJECT-TYPE
    SYNTAX           SEQUENCE OF CfprSwEthEstcPcEntry
    MAX-ACCESS       not-accessible
    STATUS           current
    DESCRIPTION
        "Cisco Firepower sw:EthEstcPc managed object table"
    ::= { cfprSwObjects 12 }

cfprSwEthEstcPcEntry OBJECT-TYPE
    SYNTAX           CfprSwEthEstcPcEntry
    MAX-ACCESS       not-accessible
    STATUS           current
    DESCRIPTION
        "Entry for the cfprSwEthEstcPcTable table."
    INDEX { cfprSwEthEstcPcInstanceId }
    ::= { cfprSwEthEstcPcTable 1 }

CfprSwEthEstcPcEntry ::= SEQUENCE {
    cfprSwEthEstcPcInstanceId                                        CfprManagedObjectId,
    cfprSwEthEstcPcDn                                                CfprManagedObjectDn,
    cfprSwEthEstcPcRn                                                SnmpAdminString,
    cfprSwEthEstcPcAdminSpeed                                        CfprPortEthSpeed,
    cfprSwEthEstcPcAdminState                                        CfprFabricAdminState,
    cfprSwEthEstcPcBorderAggrPortId                                  Gauge32,
    cfprSwEthEstcPcBorderPortId                                      Gauge32,
    cfprSwEthEstcPcBorderSlotId                                      Gauge32,
    cfprSwEthEstcPcCdp                                               CfprNwctrlAdminState,
    cfprSwEthEstcPcCosValue                                          Gauge32,
    cfprSwEthEstcPcEpDn                                              SnmpAdminString,
    cfprSwEthEstcPcForgeMac                                          CfprDpsecForgedTransmit,
    cfprSwEthEstcPcIfRole                                            CfprSwLanPcIfRole,
    cfprSwEthEstcPcIfType                                            CfprSwCIoEpIfType,
    cfprSwEthEstcPcLacpFastTimer                                     TruthValue,
    cfprSwEthEstcPcLacpSuspendIndividual                             TruthValue,
    cfprSwEthEstcPcLocale                                            CfprSwBorderPcLocale,
    cfprSwEthEstcPcMonTrafDir                                        CfprFabricTrafficDirection,
    cfprSwEthEstcPcName                                              SnmpAdminString,
    cfprSwEthEstcPcPeerDn                                            SnmpAdminString,
    cfprSwEthEstcPcPortId                                            Gauge32,
    cfprSwEthEstcPcPortMode                                          CfprFabricEthEstcPortMode,
    cfprSwEthEstcPcPriorityFlowCtrl                                  CfprFlowctrlPriorityPause,
    cfprSwEthEstcPcProtocol                                          CfprFabricEthPcProtocol,
    cfprSwEthEstcPcRecvFlowCtrl                                      CfprFlowctrlFlowControlRx,
    cfprSwEthEstcPcSendFlowCtrl                                      CfprFlowctrlFlowControlTx,
    cfprSwEthEstcPcSwitchId                                          CfprNetworkSwitchId,
    cfprSwEthEstcPcTransport                                         CfprSwEthEstcPcTransport,
    cfprSwEthEstcPcType                                              CfprSwLanPcType,
    cfprSwEthEstcPcUplinkFailAction                                  CfprNwctrlLinkFailAction
}

cfprSwEthEstcPcInstanceId OBJECT-TYPE
    SYNTAX       CfprManagedObjectId
    MAX-ACCESS   not-accessible
    STATUS       current
    DESCRIPTION
        "Instance identifier of the managed object."
    ::= { cfprSwEthEstcPcEntry 1 }

cfprSwEthEstcPcDn OBJECT-TYPE
    SYNTAX       CfprManagedObjectDn
    MAX-ACCESS   read-only
    STATUS       current
    DESCRIPTION
        "Cisco Firepower sw:EthEstcPc:dn managed object property"
    ::= { cfprSwEthEstcPcEntry 2 }

cfprSwEthEstcPcRn OBJECT-TYPE
    SYNTAX       SnmpAdminString
    MAX-ACCESS   read-only
    STATUS       current
    DESCRIPTION
        "Cisco Firepower sw:EthEstcPc:rn managed object property"
    ::= { cfprSwEthEstcPcEntry 3 }

cfprSwEthEstcPcAdminSpeed OBJECT-TYPE
    SYNTAX       CfprPortEthSpeed
    MAX-ACCESS   read-only
    STATUS       current
    DESCRIPTION
        "Cisco Firepower sw:EthEstcPc:adminSpeed managed object property"
    ::= { cfprSwEthEstcPcEntry 4 }

cfprSwEthEstcPcAdminState OBJECT-TYPE
    SYNTAX       CfprFabricAdminState
    MAX-ACCESS   read-only
    STATUS       current
    DESCRIPTION
        "Cisco Firepower sw:EthEstcPc:adminState managed object property"
    ::= { cfprSwEthEstcPcEntry 5 }

cfprSwEthEstcPcBorderAggrPortId OBJECT-TYPE
    SYNTAX       Gauge32
    MAX-ACCESS   read-only
    STATUS       current
    DESCRIPTION
        "Cisco Firepower sw:EthEstcPc:borderAggrPortId
        managed object property"
    ::= { cfprSwEthEstcPcEntry 6 }

cfprSwEthEstcPcBorderPortId OBJECT-TYPE
    SYNTAX       Gauge32
    MAX-ACCESS   read-only
    STATUS       current
    DESCRIPTION
        "Cisco Firepower sw:EthEstcPc:borderPortId managed
        object property"
    ::= { cfprSwEthEstcPcEntry 7 }

cfprSwEthEstcPcBorderSlotId OBJECT-TYPE
    SYNTAX       Gauge32
    MAX-ACCESS   read-only
    STATUS       current
    DESCRIPTION
        "Cisco Firepower sw:EthEstcPc:borderSlotId managed
        object property"
    ::= { cfprSwEthEstcPcEntry 8 }

cfprSwEthEstcPcCdp OBJECT-TYPE
    SYNTAX       CfprNwctrlAdminState
    MAX-ACCESS   read-only
    STATUS       current
    DESCRIPTION
        "Cisco Firepower sw:EthEstcPc:cdp managed object property"
    ::= { cfprSwEthEstcPcEntry 9 }

cfprSwEthEstcPcCosValue OBJECT-TYPE
    SYNTAX       Gauge32
    MAX-ACCESS   read-only
    STATUS       current
    DESCRIPTION
        "Cisco Firepower sw:EthEstcPc:cosValue managed object property"
    ::= { cfprSwEthEstcPcEntry 10 }

cfprSwEthEstcPcEpDn OBJECT-TYPE
    SYNTAX       SnmpAdminString
    MAX-ACCESS   read-only
    STATUS       current
    DESCRIPTION
        "Cisco Firepower sw:EthEstcPc:epDn managed object property"
    ::= { cfprSwEthEstcPcEntry 11 }

cfprSwEthEstcPcForgeMac OBJECT-TYPE
    SYNTAX       CfprDpsecForgedTransmit
    MAX-ACCESS   read-only
    STATUS       current
    DESCRIPTION
        "Cisco Firepower sw:EthEstcPc:forgeMac managed object property"
    ::= { cfprSwEthEstcPcEntry 12 }

cfprSwEthEstcPcIfRole OBJECT-TYPE
    SYNTAX       CfprSwLanPcIfRole
    MAX-ACCESS   read-only
    STATUS       current
    DESCRIPTION
        "Cisco Firepower sw:EthEstcPc:ifRole managed object property"
    ::= { cfprSwEthEstcPcEntry 13 }

cfprSwEthEstcPcIfType OBJECT-TYPE
    SYNTAX       CfprSwCIoEpIfType
    MAX-ACCESS   read-only
    STATUS       current
    DESCRIPTION
        "Cisco Firepower sw:EthEstcPc:ifType managed object property"
    ::= { cfprSwEthEstcPcEntry 14 }

cfprSwEthEstcPcLacpFastTimer OBJECT-TYPE
    SYNTAX       TruthValue
    MAX-ACCESS   read-only
    STATUS       current
    DESCRIPTION
        "Cisco Firepower sw:EthEstcPc:lacpFastTimer managed
        object property"
    ::= { cfprSwEthEstcPcEntry 15 }

cfprSwEthEstcPcLacpSuspendIndividual OBJECT-TYPE
    SYNTAX       TruthValue
    MAX-ACCESS   read-only
    STATUS       current
    DESCRIPTION
        "Cisco Firepower sw:EthEstcPc:lacpSuspendIndividual
        managed object property"
    ::= { cfprSwEthEstcPcEntry 16 }

cfprSwEthEstcPcLocale OBJECT-TYPE
    SYNTAX       CfprSwBorderPcLocale
    MAX-ACCESS   read-only
    STATUS       current
    DESCRIPTION
        "Cisco Firepower sw:EthEstcPc:locale managed object property"
    ::= { cfprSwEthEstcPcEntry 17 }

cfprSwEthEstcPcMonTrafDir OBJECT-TYPE
    SYNTAX       CfprFabricTrafficDirection
    MAX-ACCESS   read-only
    STATUS       current
    DESCRIPTION
        "Cisco Firepower sw:EthEstcPc:monTrafDir managed object property"
    ::= { cfprSwEthEstcPcEntry 18 }

cfprSwEthEstcPcName OBJECT-TYPE
    SYNTAX       SnmpAdminString
    MAX-ACCESS   read-only
    STATUS       current
    DESCRIPTION
        "Cisco Firepower sw:EthEstcPc:name managed object property"
    ::= { cfprSwEthEstcPcEntry 19 }

cfprSwEthEstcPcPeerDn OBJECT-TYPE
    SYNTAX       SnmpAdminString
    MAX-ACCESS   read-only
    STATUS       current
    DESCRIPTION
        "Cisco Firepower sw:EthEstcPc:peerDn managed object property"
    ::= { cfprSwEthEstcPcEntry 20 }

cfprSwEthEstcPcPortId OBJECT-TYPE
    SYNTAX       Gauge32
    MAX-ACCESS   read-only
    STATUS       current
    DESCRIPTION
        "Cisco Firepower sw:EthEstcPc:portId managed object property"
    ::= { cfprSwEthEstcPcEntry 21 }

cfprSwEthEstcPcPortMode OBJECT-TYPE
    SYNTAX       CfprFabricEthEstcPortMode
    MAX-ACCESS   read-only
    STATUS       current
    DESCRIPTION
        "Cisco Firepower sw:EthEstcPc:portMode managed object property"
    ::= { cfprSwEthEstcPcEntry 22 }

cfprSwEthEstcPcPriorityFlowCtrl OBJECT-TYPE
    SYNTAX       CfprFlowctrlPriorityPause
    MAX-ACCESS   read-only
    STATUS       current
    DESCRIPTION
        "Cisco Firepower sw:EthEstcPc:priorityFlowCtrl
        managed object property"
    ::= { cfprSwEthEstcPcEntry 23 }

cfprSwEthEstcPcProtocol OBJECT-TYPE
    SYNTAX       CfprFabricEthPcProtocol
    MAX-ACCESS   read-only
    STATUS       current
    DESCRIPTION
        "Cisco Firepower sw:EthEstcPc:protocol managed object property"
    ::= { cfprSwEthEstcPcEntry 24 }

cfprSwEthEstcPcRecvFlowCtrl OBJECT-TYPE
    SYNTAX       CfprFlowctrlFlowControlRx
    MAX-ACCESS   read-only
    STATUS       current
    DESCRIPTION
        "Cisco Firepower sw:EthEstcPc:recvFlowCtrl managed
        object property"
    ::= { cfprSwEthEstcPcEntry 25 }

cfprSwEthEstcPcSendFlowCtrl OBJECT-TYPE
    SYNTAX       CfprFlowctrlFlowControlTx
    MAX-ACCESS   read-only
    STATUS       current
    DESCRIPTION
        "Cisco Firepower sw:EthEstcPc:sendFlowCtrl managed
        object property"
    ::= { cfprSwEthEstcPcEntry 26 }

cfprSwEthEstcPcSwitchId OBJECT-TYPE
    SYNTAX       CfprNetworkSwitchId
    MAX-ACCESS   read-only
    STATUS       current
    DESCRIPTION
        "Cisco Firepower sw:EthEstcPc:switchId managed object property"
    ::= { cfprSwEthEstcPcEntry 27 }

cfprSwEthEstcPcTransport OBJECT-TYPE
    SYNTAX       CfprSwEthEstcPcTransport
    MAX-ACCESS   read-only
    STATUS       current
    DESCRIPTION
        "Cisco Firepower sw:EthEstcPc:transport managed object property"
    ::= { cfprSwEthEstcPcEntry 28 }

cfprSwEthEstcPcType OBJECT-TYPE
    SYNTAX       CfprSwLanPcType
    MAX-ACCESS   read-only
    STATUS       current
    DESCRIPTION
        "Cisco Firepower sw:EthEstcPc:type managed object property"
    ::= { cfprSwEthEstcPcEntry 29 }

cfprSwEthEstcPcUplinkFailAction OBJECT-TYPE
    SYNTAX       CfprNwctrlLinkFailAction
    MAX-ACCESS   read-only
    STATUS       current
    DESCRIPTION
        "Cisco Firepower sw:EthEstcPc:uplinkFailAction
        managed object property"
    ::= { cfprSwEthEstcPcEntry 30 }

cfprSwEthLanBorderTable OBJECT-TYPE
    SYNTAX           SEQUENCE OF CfprSwEthLanBorderEntry
    MAX-ACCESS       not-accessible
    STATUS           current
    DESCRIPTION
        "Cisco Firepower sw:EthLanBorder managed object table"
    ::= { cfprSwObjects 13 }

cfprSwEthLanBorderEntry OBJECT-TYPE
    SYNTAX           CfprSwEthLanBorderEntry
    MAX-ACCESS       not-accessible
    STATUS           current
    DESCRIPTION
        "Entry for the cfprSwEthLanBorderTable table."
    INDEX { cfprSwEthLanBorderInstanceId }
    ::= { cfprSwEthLanBorderTable 1 }

CfprSwEthLanBorderEntry ::= SEQUENCE {
    cfprSwEthLanBorderInstanceId                                     CfprManagedObjectId,
    cfprSwEthLanBorderDn                                             CfprManagedObjectDn,
    cfprSwEthLanBorderRn                                             SnmpAdminString,
    cfprSwEthLanBorderDeployFlag                                     BITS,
    cfprSwEthLanBorderFsmDescr                                       SnmpAdminString,
    cfprSwEthLanBorderFsmFlags                                       SnmpAdminString,
    cfprSwEthLanBorderFsmPrev                                        SnmpAdminString,
    cfprSwEthLanBorderFsmProgr                                       Gauge32,
    cfprSwEthLanBorderFsmRmtInvErrCode                               Gauge32,
    cfprSwEthLanBorderFsmRmtInvErrDescr                              SnmpAdminString,
    cfprSwEthLanBorderFsmRmtInvRslt                                  CfprConditionRemoteInvRslt,
    cfprSwEthLanBorderFsmStageDescr                                  SnmpAdminString,
    cfprSwEthLanBorderFsmStamp                                       DateAndTime,
    cfprSwEthLanBorderFsmStatus                                      SnmpAdminString,
    cfprSwEthLanBorderFsmTry                                         Gauge32,
    cfprSwEthLanBorderLocale                                         CfprSwBorderDomainLocale,
    cfprSwEthLanBorderName                                           SnmpAdminString,
    cfprSwEthLanBorderSwitchId                                       CfprNetworkSwitchId,
    cfprSwEthLanBorderTransport                                      CfprSwEthLanBorderTransport,
    cfprSwEthLanBorderType                                           CfprSwLanBorderType,
    cfprSwEthLanBorderUdldMsgInterval                                Gauge32,
    cfprSwEthLanBorderUdldRecoveryAction                             CfprFabricRecoveryAction
}

cfprSwEthLanBorderInstanceId OBJECT-TYPE
    SYNTAX       CfprManagedObjectId
    MAX-ACCESS   not-accessible
    STATUS       current
    DESCRIPTION
        "Instance identifier of the managed object."
    ::= { cfprSwEthLanBorderEntry 1 }

cfprSwEthLanBorderDn OBJECT-TYPE
    SYNTAX       CfprManagedObjectDn
    MAX-ACCESS   read-only
    STATUS       current
    DESCRIPTION
        "Cisco Firepower sw:EthLanBorder:dn managed object property"
    ::= { cfprSwEthLanBorderEntry 2 }

cfprSwEthLanBorderRn OBJECT-TYPE
    SYNTAX       SnmpAdminString
    MAX-ACCESS   read-only
    STATUS       current
    DESCRIPTION
        "Cisco Firepower sw:EthLanBorder:rn managed object property"
    ::= { cfprSwEthLanBorderEntry 3 }

cfprSwEthLanBorderDeployFlag OBJECT-TYPE
    SYNTAX       BITS
    MAX-ACCESS   read-only
    STATUS       current
    DESCRIPTION
        "Cisco Firepower sw:EthLanBorder:deployFlag managed
        object property"
    ::= { cfprSwEthLanBorderEntry 4 }

cfprSwEthLanBorderFsmDescr OBJECT-TYPE
    SYNTAX       SnmpAdminString
    MAX-ACCESS   read-only
    STATUS       current
    DESCRIPTION
        "Cisco Firepower sw:EthLanBorder:fsmDescr managed object property"
    ::= { cfprSwEthLanBorderEntry 5 }

cfprSwEthLanBorderFsmFlags OBJECT-TYPE
    SYNTAX       SnmpAdminString
    MAX-ACCESS   read-only
    STATUS       current
    DESCRIPTION
        "Cisco Firepower sw:EthLanBorder:fsmFlags managed object property"
    ::= { cfprSwEthLanBorderEntry 6 }

cfprSwEthLanBorderFsmPrev OBJECT-TYPE
    SYNTAX       SnmpAdminString
    MAX-ACCESS   read-only
    STATUS       current
    DESCRIPTION
        "Cisco Firepower sw:EthLanBorder:fsmPrev managed object property"
    ::= { cfprSwEthLanBorderEntry 7 }

cfprSwEthLanBorderFsmProgr OBJECT-TYPE
    SYNTAX       Gauge32
    MAX-ACCESS   read-only
    STATUS       current
    DESCRIPTION
        "Cisco Firepower sw:EthLanBorder:fsmProgr managed object property"
    ::= { cfprSwEthLanBorderEntry 8 }

cfprSwEthLanBorderFsmRmtInvErrCode OBJECT-TYPE
    SYNTAX       Gauge32
    MAX-ACCESS   read-only
    STATUS       current
    DESCRIPTION
        "Cisco Firepower sw:EthLanBorder:fsmRmtInvErrCode
        managed object property"
    ::= { cfprSwEthLanBorderEntry 9 }

cfprSwEthLanBorderFsmRmtInvErrDescr OBJECT-TYPE
    SYNTAX       SnmpAdminString
    MAX-ACCESS   read-only
    STATUS       current
    DESCRIPTION
        "Cisco Firepower sw:EthLanBorder:fsmRmtInvErrDescr
        managed object property"
    ::= { cfprSwEthLanBorderEntry 10 }

cfprSwEthLanBorderFsmRmtInvRslt OBJECT-TYPE
    SYNTAX       CfprConditionRemoteInvRslt
    MAX-ACCESS   read-only
    STATUS       current
    DESCRIPTION
        "Cisco Firepower sw:EthLanBorder:fsmRmtInvRslt
        managed object property"
    ::= { cfprSwEthLanBorderEntry 11 }

cfprSwEthLanBorderFsmStageDescr OBJECT-TYPE
    SYNTAX       SnmpAdminString
    MAX-ACCESS   read-only
    STATUS       current
    DESCRIPTION
        "Cisco Firepower sw:EthLanBorder:fsmStageDescr
        managed object property"
    ::= { cfprSwEthLanBorderEntry 12 }

cfprSwEthLanBorderFsmStamp OBJECT-TYPE
    SYNTAX       DateAndTime
    MAX-ACCESS   read-only
    STATUS       current
    DESCRIPTION
        "Cisco Firepower sw:EthLanBorder:fsmStamp managed object property"
    ::= { cfprSwEthLanBorderEntry 13 }

cfprSwEthLanBorderFsmStatus OBJECT-TYPE
    SYNTAX       SnmpAdminString
    MAX-ACCESS   read-only
    STATUS       current
    DESCRIPTION
        "Cisco Firepower sw:EthLanBorder:fsmStatus managed
        object property"
    ::= { cfprSwEthLanBorderEntry 14 }

cfprSwEthLanBorderFsmTry OBJECT-TYPE
    SYNTAX       Gauge32
    MAX-ACCESS   read-only
    STATUS       current
    DESCRIPTION
        "Cisco Firepower sw:EthLanBorder:fsmTry managed object property"
    ::= { cfprSwEthLanBorderEntry 15 }

cfprSwEthLanBorderLocale OBJECT-TYPE
    SYNTAX       CfprSwBorderDomainLocale
    MAX-ACCESS   read-only
    STATUS       current
    DESCRIPTION
        "Cisco Firepower sw:EthLanBorder:locale managed object property"
    ::= { cfprSwEthLanBorderEntry 16 }

cfprSwEthLanBorderName OBJECT-TYPE
    SYNTAX       SnmpAdminString
    MAX-ACCESS   read-only
    STATUS       current
    DESCRIPTION
        "Cisco Firepower sw:EthLanBorder:name managed object property"
    ::= { cfprSwEthLanBorderEntry 17 }

cfprSwEthLanBorderSwitchId OBJECT-TYPE
    SYNTAX       CfprNetworkSwitchId
    MAX-ACCESS   read-only
    STATUS       current
    DESCRIPTION
        "Cisco Firepower sw:EthLanBorder:switchId managed object property"
    ::= { cfprSwEthLanBorderEntry 18 }

cfprSwEthLanBorderTransport OBJECT-TYPE
    SYNTAX       CfprSwEthLanBorderTransport
    MAX-ACCESS   read-only
    STATUS       current
    DESCRIPTION
        "Cisco Firepower sw:EthLanBorder:transport managed
        object property"
    ::= { cfprSwEthLanBorderEntry 19 }

cfprSwEthLanBorderType OBJECT-TYPE
    SYNTAX       CfprSwLanBorderType
    MAX-ACCESS   read-only
    STATUS       current
    DESCRIPTION
        "Cisco Firepower sw:EthLanBorder:type managed object property"
    ::= { cfprSwEthLanBorderEntry 20 }

cfprSwEthLanBorderUdldMsgInterval OBJECT-TYPE
    SYNTAX       Gauge32
    MAX-ACCESS   read-only
    STATUS       current
    DESCRIPTION
        "Cisco Firepower sw:EthLanBorder:udldMsgInterval
        managed object property"
    ::= { cfprSwEthLanBorderEntry 21 }

cfprSwEthLanBorderUdldRecoveryAction OBJECT-TYPE
    SYNTAX       CfprFabricRecoveryAction
    MAX-ACCESS   read-only
    STATUS       current
    DESCRIPTION
        "Cisco Firepower sw:EthLanBorder:udldRecoveryAction
        managed object property"
    ::= { cfprSwEthLanBorderEntry 22 }

cfprSwEthLanBorderFsmTable OBJECT-TYPE
    SYNTAX           SEQUENCE OF CfprSwEthLanBorderFsmEntry
    MAX-ACCESS       not-accessible
    STATUS           current
    DESCRIPTION
        "Cisco Firepower sw:EthLanBorderFsm managed object table"
    ::= { cfprSwObjects 14 }

cfprSwEthLanBorderFsmEntry OBJECT-TYPE
    SYNTAX           CfprSwEthLanBorderFsmEntry
    MAX-ACCESS       not-accessible
    STATUS           current
    DESCRIPTION
        "Entry for the cfprSwEthLanBorderFsmTable table."
    INDEX { cfprSwEthLanBorderFsmInstanceId }
    ::= { cfprSwEthLanBorderFsmTable 1 }

CfprSwEthLanBorderFsmEntry ::= SEQUENCE {
    cfprSwEthLanBorderFsmInstanceId                                  CfprManagedObjectId,
    cfprSwEthLanBorderFsmDn                                          CfprManagedObjectDn,
    cfprSwEthLanBorderFsmRn                                          SnmpAdminString,
    cfprSwEthLanBorderFsmCompletionTime                              DateAndTime,
    cfprSwEthLanBorderFsmCurrentFsm                                  CfprSwEthLanBorderFsmCurrentFsm,
    cfprSwEthLanBorderFsmDescrData                                   SnmpAdminString,
    cfprSwEthLanBorderFsmFsmStatus                                   CfprFsmFsmStageStatus,
    cfprSwEthLanBorderFsmProgress                                    Gauge32,
    cfprSwEthLanBorderFsmRmtErrCode                                  Gauge32,
    cfprSwEthLanBorderFsmRmtErrDescr                                 SnmpAdminString,
    cfprSwEthLanBorderFsmRmtRslt                                     CfprConditionRemoteInvRslt
}

cfprSwEthLanBorderFsmInstanceId OBJECT-TYPE
    SYNTAX       CfprManagedObjectId
    MAX-ACCESS   not-accessible
    STATUS       current
    DESCRIPTION
        "Instance identifier of the managed object."
    ::= { cfprSwEthLanBorderFsmEntry 1 }

cfprSwEthLanBorderFsmDn OBJECT-TYPE
    SYNTAX       CfprManagedObjectDn
    MAX-ACCESS   read-only
    STATUS       current
    DESCRIPTION
        "Cisco Firepower sw:EthLanBorderFsm:dn managed object property"
    ::= { cfprSwEthLanBorderFsmEntry 2 }

cfprSwEthLanBorderFsmRn OBJECT-TYPE
    SYNTAX       SnmpAdminString
    MAX-ACCESS   read-only
    STATUS       current
    DESCRIPTION
        "Cisco Firepower sw:EthLanBorderFsm:rn managed object property"
    ::= { cfprSwEthLanBorderFsmEntry 3 }

cfprSwEthLanBorderFsmCompletionTime OBJECT-TYPE
    SYNTAX       DateAndTime
    MAX-ACCESS   read-only
    STATUS       current
    DESCRIPTION
        "Cisco Firepower sw:EthLanBorderFsm:completionTime
        managed object property"
    ::= { cfprSwEthLanBorderFsmEntry 4 }

cfprSwEthLanBorderFsmCurrentFsm OBJECT-TYPE
    SYNTAX       CfprSwEthLanBorderFsmCurrentFsm
    MAX-ACCESS   read-only
    STATUS       current
    DESCRIPTION
        "Cisco Firepower sw:EthLanBorderFsm:currentFsm
        managed object property"
    ::= { cfprSwEthLanBorderFsmEntry 5 }

cfprSwEthLanBorderFsmDescrData OBJECT-TYPE
    SYNTAX       SnmpAdminString
    MAX-ACCESS   read-only
    STATUS       current
    DESCRIPTION
        "Cisco Firepower sw:EthLanBorderFsm:descr managed object property"
    ::= { cfprSwEthLanBorderFsmEntry 6 }

cfprSwEthLanBorderFsmFsmStatus OBJECT-TYPE
    SYNTAX       CfprFsmFsmStageStatus
    MAX-ACCESS   read-only
    STATUS       current
    DESCRIPTION
        "Cisco Firepower sw:EthLanBorderFsm:fsmStatus managed
        object property"
    ::= { cfprSwEthLanBorderFsmEntry 7 }

cfprSwEthLanBorderFsmProgress OBJECT-TYPE
    SYNTAX       Gauge32
    MAX-ACCESS   read-only
    STATUS       current
    DESCRIPTION
        "Cisco Firepower sw:EthLanBorderFsm:progress managed
        object property"
    ::= { cfprSwEthLanBorderFsmEntry 8 }

cfprSwEthLanBorderFsmRmtErrCode OBJECT-TYPE
    SYNTAX       Gauge32
    MAX-ACCESS   read-only
    STATUS       current
    DESCRIPTION
        "Cisco Firepower sw:EthLanBorderFsm:rmtErrCode
        managed object property"
    ::= { cfprSwEthLanBorderFsmEntry 9 }

cfprSwEthLanBorderFsmRmtErrDescr OBJECT-TYPE
    SYNTAX       SnmpAdminString
    MAX-ACCESS   read-only
    STATUS       current
    DESCRIPTION
        "Cisco Firepower sw:EthLanBorderFsm:rmtErrDescr
        managed object property"
    ::= { cfprSwEthLanBorderFsmEntry 10 }

cfprSwEthLanBorderFsmRmtRslt OBJECT-TYPE
    SYNTAX       CfprConditionRemoteInvRslt
    MAX-ACCESS   read-only
    STATUS       current
    DESCRIPTION
        "Cisco Firepower sw:EthLanBorderFsm:rmtRslt managed
        object property"
    ::= { cfprSwEthLanBorderFsmEntry 11 }

cfprSwEthLanBorderFsmStageTable OBJECT-TYPE
    SYNTAX           SEQUENCE OF CfprSwEthLanBorderFsmStageEntry
    MAX-ACCESS       not-accessible
    STATUS           current
    DESCRIPTION
        "Cisco Firepower sw:EthLanBorderFsmStage managed object table"
    ::= { cfprSwObjects 15 }

cfprSwEthLanBorderFsmStageEntry OBJECT-TYPE
    SYNTAX           CfprSwEthLanBorderFsmStageEntry
    MAX-ACCESS       not-accessible
    STATUS           current
    DESCRIPTION
        "Entry for the cfprSwEthLanBorderFsmStageTable table."
    INDEX { cfprSwEthLanBorderFsmStageInstanceId }
    ::= { cfprSwEthLanBorderFsmStageTable 1 }

CfprSwEthLanBorderFsmStageEntry ::= SEQUENCE {
    cfprSwEthLanBorderFsmStageInstanceId                             CfprManagedObjectId,
    cfprSwEthLanBorderFsmStageDn                                     CfprManagedObjectDn,
    cfprSwEthLanBorderFsmStageRn                                     SnmpAdminString,
    cfprSwEthLanBorderFsmStageDescrData                              SnmpAdminString,
    cfprSwEthLanBorderFsmStageLastUpdateTime                         DateAndTime,
    cfprSwEthLanBorderFsmStageName                                   CfprSwEthLanBorderFsmStageName,
    cfprSwEthLanBorderFsmStageOrder                                  Gauge32,
    cfprSwEthLanBorderFsmStageRetry                                  Gauge32,
    cfprSwEthLanBorderFsmStageStageStatus                            CfprFsmFsmStageStatus
}

cfprSwEthLanBorderFsmStageInstanceId OBJECT-TYPE
    SYNTAX       CfprManagedObjectId
    MAX-ACCESS   not-accessible
    STATUS       current
    DESCRIPTION
        "Instance identifier of the managed object."
    ::= { cfprSwEthLanBorderFsmStageEntry 1 }

cfprSwEthLanBorderFsmStageDn OBJECT-TYPE
    SYNTAX       CfprManagedObjectDn
    MAX-ACCESS   read-only
    STATUS       current
    DESCRIPTION
        "Cisco Firepower sw:EthLanBorderFsmStage:dn managed
        object property"
    ::= { cfprSwEthLanBorderFsmStageEntry 2 }

cfprSwEthLanBorderFsmStageRn OBJECT-TYPE
    SYNTAX       SnmpAdminString
    MAX-ACCESS   read-only
    STATUS       current
    DESCRIPTION
        "Cisco Firepower sw:EthLanBorderFsmStage:rn managed
        object property"
    ::= { cfprSwEthLanBorderFsmStageEntry 3 }

cfprSwEthLanBorderFsmStageDescrData OBJECT-TYPE
    SYNTAX       SnmpAdminString
    MAX-ACCESS   read-only
    STATUS       current
    DESCRIPTION
        "Cisco Firepower sw:EthLanBorderFsmStage:descr
        managed object property"
    ::= { cfprSwEthLanBorderFsmStageEntry 4 }

cfprSwEthLanBorderFsmStageLastUpdateTime OBJECT-TYPE
    SYNTAX       DateAndTime
    MAX-ACCESS   read-only
    STATUS       current
    DESCRIPTION
        "Cisco Firepower sw:EthLanBorderFsmStage:lastUpdateTime
        managed object property"
    ::= { cfprSwEthLanBorderFsmStageEntry 5 }

cfprSwEthLanBorderFsmStageName OBJECT-TYPE
    SYNTAX       CfprSwEthLanBorderFsmStageName
    MAX-ACCESS   read-only
    STATUS       current
    DESCRIPTION
        "Cisco Firepower sw:EthLanBorderFsmStage:name managed
        object property"
    ::= { cfprSwEthLanBorderFsmStageEntry 6 }

cfprSwEthLanBorderFsmStageOrder OBJECT-TYPE
    SYNTAX       Gauge32
    MAX-ACCESS   read-only
    STATUS       current
    DESCRIPTION
        "Cisco Firepower sw:EthLanBorderFsmStage:order
        managed object property"
    ::= { cfprSwEthLanBorderFsmStageEntry 7 }

cfprSwEthLanBorderFsmStageRetry OBJECT-TYPE
    SYNTAX       Gauge32
    MAX-ACCESS   read-only
    STATUS       current
    DESCRIPTION
        "Cisco Firepower sw:EthLanBorderFsmStage:retry
        managed object property"
    ::= { cfprSwEthLanBorderFsmStageEntry 8 }

cfprSwEthLanBorderFsmStageStageStatus OBJECT-TYPE
    SYNTAX       CfprFsmFsmStageStatus
    MAX-ACCESS   read-only
    STATUS       current
    DESCRIPTION
        "Cisco Firepower sw:EthLanBorderFsmStage:stageStatus
        managed object property"
    ::= { cfprSwEthLanBorderFsmStageEntry 9 }

cfprSwEthLanBorderFsmTaskTable OBJECT-TYPE
    SYNTAX           SEQUENCE OF CfprSwEthLanBorderFsmTaskEntry
    MAX-ACCESS       not-accessible
    STATUS           current
    DESCRIPTION
        "Cisco Firepower sw:EthLanBorderFsmTask managed object table"
    ::= { cfprSwObjects 16 }

cfprSwEthLanBorderFsmTaskEntry OBJECT-TYPE
    SYNTAX           CfprSwEthLanBorderFsmTaskEntry
    MAX-ACCESS       not-accessible
    STATUS           current
    DESCRIPTION
        "Entry for the cfprSwEthLanBorderFsmTaskTable table."
    INDEX { cfprSwEthLanBorderFsmTaskInstanceId }
    ::= { cfprSwEthLanBorderFsmTaskTable 1 }

CfprSwEthLanBorderFsmTaskEntry ::= SEQUENCE {
    cfprSwEthLanBorderFsmTaskInstanceId                              CfprManagedObjectId,
    cfprSwEthLanBorderFsmTaskDn                                      CfprManagedObjectDn,
    cfprSwEthLanBorderFsmTaskRn                                      SnmpAdminString,
    cfprSwEthLanBorderFsmTaskCompletion                              CfprFsmCompletion,
    cfprSwEthLanBorderFsmTaskFlags                                   CfprSwEthLanBorderFsmTaskFlags,
    cfprSwEthLanBorderFsmTaskItem                                    CfprSwEthLanBorderFsmTaskItem,
    cfprSwEthLanBorderFsmTaskSeqId                                   Gauge32
}

cfprSwEthLanBorderFsmTaskInstanceId OBJECT-TYPE
    SYNTAX       CfprManagedObjectId
    MAX-ACCESS   not-accessible
    STATUS       current
    DESCRIPTION
        "Instance identifier of the managed object."
    ::= { cfprSwEthLanBorderFsmTaskEntry 1 }

cfprSwEthLanBorderFsmTaskDn OBJECT-TYPE
    SYNTAX       CfprManagedObjectDn
    MAX-ACCESS   read-only
    STATUS       current
    DESCRIPTION
        "Cisco Firepower sw:EthLanBorderFsmTask:dn managed
        object property"
    ::= { cfprSwEthLanBorderFsmTaskEntry 2 }

cfprSwEthLanBorderFsmTaskRn OBJECT-TYPE
    SYNTAX       SnmpAdminString
    MAX-ACCESS   read-only
    STATUS       current
    DESCRIPTION
        "Cisco Firepower sw:EthLanBorderFsmTask:rn managed
        object property"
    ::= { cfprSwEthLanBorderFsmTaskEntry 3 }

cfprSwEthLanBorderFsmTaskCompletion OBJECT-TYPE
    SYNTAX       CfprFsmCompletion
    MAX-ACCESS   read-only
    STATUS       current
    DESCRIPTION
        "Cisco Firepower sw:EthLanBorderFsmTask:completion
        managed object property"
    ::= { cfprSwEthLanBorderFsmTaskEntry 4 }

cfprSwEthLanBorderFsmTaskFlags OBJECT-TYPE
    SYNTAX       CfprSwEthLanBorderFsmTaskFlags
    MAX-ACCESS   read-only
    STATUS       current
    DESCRIPTION
        "Cisco Firepower sw:EthLanBorderFsmTask:flags managed
        object property"
    ::= { cfprSwEthLanBorderFsmTaskEntry 5 }

cfprSwEthLanBorderFsmTaskItem OBJECT-TYPE
    SYNTAX       CfprSwEthLanBorderFsmTaskItem
    MAX-ACCESS   read-only
    STATUS       current
    DESCRIPTION
        "Cisco Firepower sw:EthLanBorderFsmTask:item managed
        object property"
    ::= { cfprSwEthLanBorderFsmTaskEntry 6 }

cfprSwEthLanBorderFsmTaskSeqId OBJECT-TYPE
    SYNTAX       Gauge32
    MAX-ACCESS   read-only
    STATUS       current
    DESCRIPTION
        "Cisco Firepower sw:EthLanBorderFsmTask:seqId managed
        object property"
    ::= { cfprSwEthLanBorderFsmTaskEntry 7 }

cfprSwEthLanEpTable OBJECT-TYPE
    SYNTAX           SEQUENCE OF CfprSwEthLanEpEntry
    MAX-ACCESS       not-accessible
    STATUS           current
    DESCRIPTION
        "Cisco Firepower sw:EthLanEp managed object table"
    ::= { cfprSwObjects 17 }

cfprSwEthLanEpEntry OBJECT-TYPE
    SYNTAX           CfprSwEthLanEpEntry
    MAX-ACCESS       not-accessible
    STATUS           current
    DESCRIPTION
        "Entry for the cfprSwEthLanEpTable table."
    INDEX { cfprSwEthLanEpInstanceId }
    ::= { cfprSwEthLanEpTable 1 }

CfprSwEthLanEpEntry ::= SEQUENCE {
    cfprSwEthLanEpInstanceId                                         CfprManagedObjectId,
    cfprSwEthLanEpDn                                                 CfprManagedObjectDn,
    cfprSwEthLanEpRn                                                 SnmpAdminString,
    cfprSwEthLanEpAdminSpeed                                         CfprPortEthSpeed,
    cfprSwEthLanEpAdminState                                         CfprFabricAdminState,
    cfprSwEthLanEpAggrPortId                                         Gauge32,
    cfprSwEthLanEpChassisId                                          Gauge32,
    cfprSwEthLanEpDtagVlan                                           Gauge32,
    cfprSwEthLanEpEpDn                                               SnmpAdminString,
    cfprSwEthLanEpIfRole                                             CfprSwLanEpIfRole,
    cfprSwEthLanEpIfType                                             CfprSwPIoEpIfType,
    cfprSwEthLanEpLc                                                 CfprSwPIoEpLc,
    cfprSwEthLanEpLocale                                             CfprSwBorderEpLocale,
    cfprSwEthLanEpName                                               SnmpAdminString,
    cfprSwEthLanEpPcId                                               Gauge32,
    cfprSwEthLanEpPeerAggrPortId                                     Gauge32,
    cfprSwEthLanEpPeerChassisId                                      Gauge32,
    cfprSwEthLanEpPeerDn                                             SnmpAdminString,
    cfprSwEthLanEpPeerPortId                                         Gauge32,
    cfprSwEthLanEpPeerSlotId                                         Gauge32,
    cfprSwEthLanEpPortId                                             Gauge32,
    cfprSwEthLanEpPriorityFlowCtrl                                   CfprFlowctrlPriorityPause,
    cfprSwEthLanEpRecvFlowCtrl                                       CfprFlowctrlFlowControlRx,
    cfprSwEthLanEpSendFlowCtrl                                       CfprFlowctrlFlowControlTx,
    cfprSwEthLanEpSlotId                                             Gauge32,
    cfprSwEthLanEpSwitchId                                           CfprNetworkSwitchId,
    cfprSwEthLanEpTransport                                          CfprSwEthLanEpTransport,
    cfprSwEthLanEpType                                               CfprSwLanEpType,
    cfprSwEthLanEpUdldAdminState                                     CfprSwEthLanEpUdldAdminState,
    cfprSwEthLanEpUdldMode                                           CfprSwEthLanEpUdldMode,
    cfprSwEthLanEpAdminDuplex                                        CfprPortDuplex,
    cfprSwEthLanEpAutoNeg                                            TruthValue,
    cfprSwEthLanEpHashAlg                                            CfprNhTpHashType,
    cfprSwEthLanEpInlineState                                        CfprSwEthLanEpInlineState,
    cfprSwEthLanEpPcMode                                             CfprSwPcMode,
    cfprSwEthLanEpPcModeState                                        CfprSwPcModeState,
    cfprSwEthLanEpQosPrio                                            CfprFabricQosPrio,
    cfprSwEthLanEpLldp                                               CfprNwctrlLldpAdminStateBitmask,
    cfprSwEthLanEpAllowAneg                                          TruthValue
}

cfprSwEthLanEpInstanceId OBJECT-TYPE
    SYNTAX       CfprManagedObjectId
    MAX-ACCESS   not-accessible
    STATUS       current
    DESCRIPTION
        "Instance identifier of the managed object."
    ::= { cfprSwEthLanEpEntry 1 }

cfprSwEthLanEpDn OBJECT-TYPE
    SYNTAX       CfprManagedObjectDn
    MAX-ACCESS   read-only
    STATUS       current
    DESCRIPTION
        "Cisco Firepower sw:EthLanEp:dn managed object property"
    ::= { cfprSwEthLanEpEntry 2 }

cfprSwEthLanEpRn OBJECT-TYPE
    SYNTAX       SnmpAdminString
    MAX-ACCESS   read-only
    STATUS       current
    DESCRIPTION
        "Cisco Firepower sw:EthLanEp:rn managed object property"
    ::= { cfprSwEthLanEpEntry 3 }

cfprSwEthLanEpAdminSpeed OBJECT-TYPE
    SYNTAX       CfprPortEthSpeed
    MAX-ACCESS   read-only
    STATUS       current
    DESCRIPTION
        "Cisco Firepower sw:EthLanEp:adminSpeed managed object property"
    ::= { cfprSwEthLanEpEntry 4 }

cfprSwEthLanEpAdminState OBJECT-TYPE
    SYNTAX       CfprFabricAdminState
    MAX-ACCESS   read-only
    STATUS       current
    DESCRIPTION
        "Cisco Firepower sw:EthLanEp:adminState managed object property"
    ::= { cfprSwEthLanEpEntry 5 }

cfprSwEthLanEpAggrPortId OBJECT-TYPE
    SYNTAX       Gauge32
    MAX-ACCESS   read-only
    STATUS       current
    DESCRIPTION
        "Cisco Firepower sw:EthLanEp:aggrPortId managed object property"
    ::= { cfprSwEthLanEpEntry 6 }

cfprSwEthLanEpChassisId OBJECT-TYPE
    SYNTAX       Gauge32
    MAX-ACCESS   read-only
    STATUS       current
    DESCRIPTION
        "Cisco Firepower sw:EthLanEp:chassisId managed object property"
    ::= { cfprSwEthLanEpEntry 7 }

cfprSwEthLanEpDtagVlan OBJECT-TYPE
    SYNTAX       Gauge32
    MAX-ACCESS   read-only
    STATUS       current
    DESCRIPTION
        "Cisco Firepower sw:EthLanEp:dtagVlan managed object property"
    ::= { cfprSwEthLanEpEntry 8 }

cfprSwEthLanEpEpDn OBJECT-TYPE
    SYNTAX       SnmpAdminString
    MAX-ACCESS   read-only
    STATUS       current
    DESCRIPTION
        "Cisco Firepower sw:EthLanEp:epDn managed object property"
    ::= { cfprSwEthLanEpEntry 9 }

cfprSwEthLanEpIfRole OBJECT-TYPE
    SYNTAX       CfprSwLanEpIfRole
    MAX-ACCESS   read-only
    STATUS       current
    DESCRIPTION
        "Cisco Firepower sw:EthLanEp:ifRole managed object property"
    ::= { cfprSwEthLanEpEntry 10 }

cfprSwEthLanEpIfType OBJECT-TYPE
    SYNTAX       CfprSwPIoEpIfType
    MAX-ACCESS   read-only
    STATUS       current
    DESCRIPTION
        "Cisco Firepower sw:EthLanEp:ifType managed object property"
    ::= { cfprSwEthLanEpEntry 11 }

cfprSwEthLanEpLc OBJECT-TYPE
    SYNTAX       CfprSwPIoEpLc
    MAX-ACCESS   read-only
    STATUS       current
    DESCRIPTION
        "Cisco Firepower sw:EthLanEp:lc managed object property"
    ::= { cfprSwEthLanEpEntry 12 }

cfprSwEthLanEpLocale OBJECT-TYPE
    SYNTAX       CfprSwBorderEpLocale
    MAX-ACCESS   read-only
    STATUS       current
    DESCRIPTION
        "Cisco Firepower sw:EthLanEp:locale managed object property"
    ::= { cfprSwEthLanEpEntry 13 }

cfprSwEthLanEpName OBJECT-TYPE
    SYNTAX       SnmpAdminString
    MAX-ACCESS   read-only
    STATUS       current
    DESCRIPTION
        "Cisco Firepower sw:EthLanEp:name managed object property"
    ::= { cfprSwEthLanEpEntry 15 }

cfprSwEthLanEpPcId OBJECT-TYPE
    SYNTAX       Gauge32
    MAX-ACCESS   read-only
    STATUS       current
    DESCRIPTION
        "Cisco Firepower sw:EthLanEp:pcId managed object property"
    ::= { cfprSwEthLanEpEntry 16 }

cfprSwEthLanEpPeerAggrPortId OBJECT-TYPE
    SYNTAX       Gauge32
    MAX-ACCESS   read-only
    STATUS       current
    DESCRIPTION
        "Cisco Firepower sw:EthLanEp:peerAggrPortId managed
        object property"
    ::= { cfprSwEthLanEpEntry 17 }

cfprSwEthLanEpPeerChassisId OBJECT-TYPE
    SYNTAX       Gauge32
    MAX-ACCESS   read-only
    STATUS       current
    DESCRIPTION
        "Cisco Firepower sw:EthLanEp:peerChassisId managed
        object property"
    ::= { cfprSwEthLanEpEntry 18 }

cfprSwEthLanEpPeerDn OBJECT-TYPE
    SYNTAX       SnmpAdminString
    MAX-ACCESS   read-only
    STATUS       current
    DESCRIPTION
        "Cisco Firepower sw:EthLanEp:peerDn managed object property"
    ::= { cfprSwEthLanEpEntry 19 }

cfprSwEthLanEpPeerPortId OBJECT-TYPE
    SYNTAX       Gauge32
    MAX-ACCESS   read-only
    STATUS       current
    DESCRIPTION
        "Cisco Firepower sw:EthLanEp:peerPortId managed object property"
    ::= { cfprSwEthLanEpEntry 20 }

cfprSwEthLanEpPeerSlotId OBJECT-TYPE
    SYNTAX       Gauge32
    MAX-ACCESS   read-only
    STATUS       current
    DESCRIPTION
        "Cisco Firepower sw:EthLanEp:peerSlotId managed object property"
    ::= { cfprSwEthLanEpEntry 21 }

cfprSwEthLanEpPortId OBJECT-TYPE
    SYNTAX       Gauge32
    MAX-ACCESS   read-only
    STATUS       current
    DESCRIPTION
        "Cisco Firepower sw:EthLanEp:portId managed object property"
    ::= { cfprSwEthLanEpEntry 22 }

cfprSwEthLanEpPriorityFlowCtrl OBJECT-TYPE
    SYNTAX       CfprFlowctrlPriorityPause
    MAX-ACCESS   read-only
    STATUS       current
    DESCRIPTION
        "Cisco Firepower sw:EthLanEp:priorityFlowCtrl managed
        object property"
    ::= { cfprSwEthLanEpEntry 23 }

cfprSwEthLanEpRecvFlowCtrl OBJECT-TYPE
    SYNTAX       CfprFlowctrlFlowControlRx
    MAX-ACCESS   read-only
    STATUS       current
    DESCRIPTION
        "Cisco Firepower sw:EthLanEp:recvFlowCtrl managed object property"
    ::= { cfprSwEthLanEpEntry 24 }

cfprSwEthLanEpSendFlowCtrl OBJECT-TYPE
    SYNTAX       CfprFlowctrlFlowControlTx
    MAX-ACCESS   read-only
    STATUS       current
    DESCRIPTION
        "Cisco Firepower sw:EthLanEp:sendFlowCtrl managed object property"
    ::= { cfprSwEthLanEpEntry 25 }

cfprSwEthLanEpSlotId OBJECT-TYPE
    SYNTAX       Gauge32
    MAX-ACCESS   read-only
    STATUS       current
    DESCRIPTION
        "Cisco Firepower sw:EthLanEp:slotId managed object property"
    ::= { cfprSwEthLanEpEntry 26 }

cfprSwEthLanEpSwitchId OBJECT-TYPE
    SYNTAX       CfprNetworkSwitchId
    MAX-ACCESS   read-only
    STATUS       current
    DESCRIPTION
        "Cisco Firepower sw:EthLanEp:switchId managed object property"
    ::= { cfprSwEthLanEpEntry 27 }

cfprSwEthLanEpTransport OBJECT-TYPE
    SYNTAX       CfprSwEthLanEpTransport
    MAX-ACCESS   read-only
    STATUS       current
    DESCRIPTION
        "Cisco Firepower sw:EthLanEp:transport managed object property"
    ::= { cfprSwEthLanEpEntry 28 }

cfprSwEthLanEpType OBJECT-TYPE
    SYNTAX       CfprSwLanEpType
    MAX-ACCESS   read-only
    STATUS       current
    DESCRIPTION
        "Cisco Firepower sw:EthLanEp:type managed object property"
    ::= { cfprSwEthLanEpEntry 29 }

cfprSwEthLanEpUdldAdminState OBJECT-TYPE
    SYNTAX       CfprSwEthLanEpUdldAdminState
    MAX-ACCESS   read-only
    STATUS       current
    DESCRIPTION
        "Cisco Firepower sw:EthLanEp:udldAdminState managed
        object property"
    ::= { cfprSwEthLanEpEntry 30 }

cfprSwEthLanEpUdldMode OBJECT-TYPE
    SYNTAX       CfprSwEthLanEpUdldMode
    MAX-ACCESS   read-only
    STATUS       current
    DESCRIPTION
        "Cisco Firepower sw:EthLanEp:udldMode managed object property"
    ::= { cfprSwEthLanEpEntry 31 }

cfprSwEthLanEpAdminDuplex OBJECT-TYPE
    SYNTAX       CfprPortDuplex
    MAX-ACCESS   read-only
    STATUS       current
    DESCRIPTION
        "Cisco Firepower sw:EthLanEp:adminDuplex managed object property"
    ::= { cfprSwEthLanEpEntry 32 }

cfprSwEthLanEpAutoNeg OBJECT-TYPE
    SYNTAX       TruthValue
    MAX-ACCESS   read-only
    STATUS       current
    DESCRIPTION
        "Cisco Firepower sw:EthLanEp:autoNeg managed object property"
    ::= { cfprSwEthLanEpEntry 33 }

cfprSwEthLanEpHashAlg OBJECT-TYPE
    SYNTAX       CfprNhTpHashType
    MAX-ACCESS   read-only
    STATUS       current
    DESCRIPTION
        "Cisco Firepower sw:EthLanEp:hashAlg managed object property"
    ::= { cfprSwEthLanEpEntry 34 }

cfprSwEthLanEpInlineState OBJECT-TYPE
    SYNTAX       CfprSwEthLanEpInlineState
    MAX-ACCESS   read-only
    STATUS       current
    DESCRIPTION
        "Cisco Firepower sw:EthLanEp:inlineState managed object property"
    ::= { cfprSwEthLanEpEntry 35 }

cfprSwEthLanEpPcMode OBJECT-TYPE
    SYNTAX       CfprSwPcMode
    MAX-ACCESS   read-only
    STATUS       current
    DESCRIPTION
        "Cisco Firepower sw:EthLanEp:pcMode managed object property"
    ::= { cfprSwEthLanEpEntry 36 }

cfprSwEthLanEpPcModeState OBJECT-TYPE
    SYNTAX       CfprSwPcModeState
    MAX-ACCESS   read-only
    STATUS       current
    DESCRIPTION
        "Cisco Firepower sw:EthLanEp:pcModeState managed object property"
    ::= { cfprSwEthLanEpEntry 37 }

cfprSwEthLanEpQosPrio OBJECT-TYPE
    SYNTAX       CfprFabricQosPrio
    MAX-ACCESS   read-only
    STATUS       current
    DESCRIPTION
        "Cisco Firepower sw:EthLanEp:qosPrio managed object property"
    ::= { cfprSwEthLanEpEntry 38 }

cfprSwEthLanEpLldp OBJECT-TYPE
    SYNTAX       CfprNwctrlLldpAdminStateBitmask
    MAX-ACCESS   read-only
    STATUS       current
    DESCRIPTION
        "Cisco Firepower sw:EthLanEp:lldp managed object property"
    ::= { cfprSwEthLanEpEntry 39 }

cfprSwEthLanEpAllowAneg OBJECT-TYPE
    SYNTAX       TruthValue
    MAX-ACCESS   read-only
    STATUS       current
    DESCRIPTION
        "Cisco Firepower sw:EthLanEp:allowAneg managed object property"
    ::= { cfprSwEthLanEpEntry 40 }

cfprSwEthLanFlowMonTable OBJECT-TYPE
    SYNTAX           SEQUENCE OF CfprSwEthLanFlowMonEntry
    MAX-ACCESS       not-accessible
    STATUS           current
    DESCRIPTION
        "Cisco Firepower sw:EthLanFlowMon managed object table"
    ::= { cfprSwObjects 18 }

cfprSwEthLanFlowMonEntry OBJECT-TYPE
    SYNTAX           CfprSwEthLanFlowMonEntry
    MAX-ACCESS       not-accessible
    STATUS           current
    DESCRIPTION
        "Entry for the cfprSwEthLanFlowMonTable table."
    INDEX { cfprSwEthLanFlowMonInstanceId }
    ::= { cfprSwEthLanFlowMonTable 1 }

CfprSwEthLanFlowMonEntry ::= SEQUENCE {
    cfprSwEthLanFlowMonInstanceId                                    CfprManagedObjectId,
    cfprSwEthLanFlowMonDn                                            CfprManagedObjectDn,
    cfprSwEthLanFlowMonRn                                            SnmpAdminString,
    cfprSwEthLanFlowMonFsmDescr                                      SnmpAdminString,
    cfprSwEthLanFlowMonFsmPrev                                       SnmpAdminString,
    cfprSwEthLanFlowMonFsmProgr                                      Gauge32,
    cfprSwEthLanFlowMonFsmRmtInvErrCode                              Gauge32,
    cfprSwEthLanFlowMonFsmRmtInvErrDescr                             SnmpAdminString,
    cfprSwEthLanFlowMonFsmRmtInvRslt                                 CfprConditionRemoteInvRslt,
    cfprSwEthLanFlowMonFsmStageDescr                                 SnmpAdminString,
    cfprSwEthLanFlowMonFsmStamp                                      DateAndTime,
    cfprSwEthLanFlowMonFsmStatus                                     SnmpAdminString,
    cfprSwEthLanFlowMonFsmTry                                        Gauge32,
    cfprSwEthLanFlowMonLocale                                        CfprSwMonDomainLocale,
    cfprSwEthLanFlowMonName                                          SnmpAdminString,
    cfprSwEthLanFlowMonNetflowActiveTimeout                          Gauge32,
    cfprSwEthLanFlowMonNetflowInactiveTimeout                        Gauge32,
    cfprSwEthLanFlowMonSwitchId                                      CfprNetworkSwitchId,
    cfprSwEthLanFlowMonTransport                                     CfprSwEthLanFlowMonTransport,
    cfprSwEthLanFlowMonType                                          CfprSwLanMonType
}

cfprSwEthLanFlowMonInstanceId OBJECT-TYPE
    SYNTAX       CfprManagedObjectId
    MAX-ACCESS   not-accessible
    STATUS       current
    DESCRIPTION
        "Instance identifier of the managed object."
    ::= { cfprSwEthLanFlowMonEntry 1 }

cfprSwEthLanFlowMonDn OBJECT-TYPE
    SYNTAX       CfprManagedObjectDn
    MAX-ACCESS   read-only
    STATUS       current
    DESCRIPTION
        "Cisco Firepower sw:EthLanFlowMon:dn managed object property"
    ::= { cfprSwEthLanFlowMonEntry 2 }

cfprSwEthLanFlowMonRn OBJECT-TYPE
    SYNTAX       SnmpAdminString
    MAX-ACCESS   read-only
    STATUS       current
    DESCRIPTION
        "Cisco Firepower sw:EthLanFlowMon:rn managed object property"
    ::= { cfprSwEthLanFlowMonEntry 3 }

cfprSwEthLanFlowMonFsmDescr OBJECT-TYPE
    SYNTAX       SnmpAdminString
    MAX-ACCESS   read-only
    STATUS       current
    DESCRIPTION
        "Cisco Firepower sw:EthLanFlowMon:fsmDescr managed
        object property"
    ::= { cfprSwEthLanFlowMonEntry 4 }

cfprSwEthLanFlowMonFsmPrev OBJECT-TYPE
    SYNTAX       SnmpAdminString
    MAX-ACCESS   read-only
    STATUS       current
    DESCRIPTION
        "Cisco Firepower sw:EthLanFlowMon:fsmPrev managed object property"
    ::= { cfprSwEthLanFlowMonEntry 5 }

cfprSwEthLanFlowMonFsmProgr OBJECT-TYPE
    SYNTAX       Gauge32
    MAX-ACCESS   read-only
    STATUS       current
    DESCRIPTION
        "Cisco Firepower sw:EthLanFlowMon:fsmProgr managed
        object property"
    ::= { cfprSwEthLanFlowMonEntry 6 }

cfprSwEthLanFlowMonFsmRmtInvErrCode OBJECT-TYPE
    SYNTAX       Gauge32
    MAX-ACCESS   read-only
    STATUS       current
    DESCRIPTION
        "Cisco Firepower sw:EthLanFlowMon:fsmRmtInvErrCode
        managed object property"
    ::= { cfprSwEthLanFlowMonEntry 7 }

cfprSwEthLanFlowMonFsmRmtInvErrDescr OBJECT-TYPE
    SYNTAX       SnmpAdminString
    MAX-ACCESS   read-only
    STATUS       current
    DESCRIPTION
        "Cisco Firepower sw:EthLanFlowMon:fsmRmtInvErrDescr
        managed object property"
    ::= { cfprSwEthLanFlowMonEntry 8 }

cfprSwEthLanFlowMonFsmRmtInvRslt OBJECT-TYPE
    SYNTAX       CfprConditionRemoteInvRslt
    MAX-ACCESS   read-only
    STATUS       current
    DESCRIPTION
        "Cisco Firepower sw:EthLanFlowMon:fsmRmtInvRslt
        managed object property"
    ::= { cfprSwEthLanFlowMonEntry 9 }

cfprSwEthLanFlowMonFsmStageDescr OBJECT-TYPE
    SYNTAX       SnmpAdminString
    MAX-ACCESS   read-only
    STATUS       current
    DESCRIPTION
        "Cisco Firepower sw:EthLanFlowMon:fsmStageDescr
        managed object property"
    ::= { cfprSwEthLanFlowMonEntry 10 }

cfprSwEthLanFlowMonFsmStamp OBJECT-TYPE
    SYNTAX       DateAndTime
    MAX-ACCESS   read-only
    STATUS       current
    DESCRIPTION
        "Cisco Firepower sw:EthLanFlowMon:fsmStamp managed
        object property"
    ::= { cfprSwEthLanFlowMonEntry 11 }

cfprSwEthLanFlowMonFsmStatus OBJECT-TYPE
    SYNTAX       SnmpAdminString
    MAX-ACCESS   read-only
    STATUS       current
    DESCRIPTION
        "Cisco Firepower sw:EthLanFlowMon:fsmStatus managed
        object property"
    ::= { cfprSwEthLanFlowMonEntry 12 }

cfprSwEthLanFlowMonFsmTry OBJECT-TYPE
    SYNTAX       Gauge32
    MAX-ACCESS   read-only
    STATUS       current
    DESCRIPTION
        "Cisco Firepower sw:EthLanFlowMon:fsmTry managed object property"
    ::= { cfprSwEthLanFlowMonEntry 13 }

cfprSwEthLanFlowMonLocale OBJECT-TYPE
    SYNTAX       CfprSwMonDomainLocale
    MAX-ACCESS   read-only
    STATUS       current
    DESCRIPTION
        "Cisco Firepower sw:EthLanFlowMon:locale managed object property"
    ::= { cfprSwEthLanFlowMonEntry 14 }

cfprSwEthLanFlowMonName OBJECT-TYPE
    SYNTAX       SnmpAdminString
    MAX-ACCESS   read-only
    STATUS       current
    DESCRIPTION
        "Cisco Firepower sw:EthLanFlowMon:name managed object property"
    ::= { cfprSwEthLanFlowMonEntry 15 }

cfprSwEthLanFlowMonNetflowActiveTimeout OBJECT-TYPE
    SYNTAX       Gauge32
    MAX-ACCESS   read-only
    STATUS       current
    DESCRIPTION
        "Cisco Firepower sw:EthLanFlowMon:netflowActiveTimeout
        managed object property"
    ::= { cfprSwEthLanFlowMonEntry 16 }

cfprSwEthLanFlowMonNetflowInactiveTimeout OBJECT-TYPE
    SYNTAX       Gauge32
    MAX-ACCESS   read-only
    STATUS       current
    DESCRIPTION
        "Cisco Firepower sw:EthLanFlowMon:netflowInactiveTimeout
        managed object property"
    ::= { cfprSwEthLanFlowMonEntry 17 }

cfprSwEthLanFlowMonSwitchId OBJECT-TYPE
    SYNTAX       CfprNetworkSwitchId
    MAX-ACCESS   read-only
    STATUS       current
    DESCRIPTION
        "Cisco Firepower sw:EthLanFlowMon:switchId managed
        object property"
    ::= { cfprSwEthLanFlowMonEntry 18 }

cfprSwEthLanFlowMonTransport OBJECT-TYPE
    SYNTAX       CfprSwEthLanFlowMonTransport
    MAX-ACCESS   read-only
    STATUS       current
    DESCRIPTION
        "Cisco Firepower sw:EthLanFlowMon:transport managed
        object property"
    ::= { cfprSwEthLanFlowMonEntry 19 }

cfprSwEthLanFlowMonType OBJECT-TYPE
    SYNTAX       CfprSwLanMonType
    MAX-ACCESS   read-only
    STATUS       current
    DESCRIPTION
        "Cisco Firepower sw:EthLanFlowMon:type managed object property"
    ::= { cfprSwEthLanFlowMonEntry 20 }

cfprSwEthLanFlowMonFsmTable OBJECT-TYPE
    SYNTAX           SEQUENCE OF CfprSwEthLanFlowMonFsmEntry
    MAX-ACCESS       not-accessible
    STATUS           current
    DESCRIPTION
        "Cisco Firepower sw:EthLanFlowMonFsm managed object table"
    ::= { cfprSwObjects 19 }

cfprSwEthLanFlowMonFsmEntry OBJECT-TYPE
    SYNTAX           CfprSwEthLanFlowMonFsmEntry
    MAX-ACCESS       not-accessible
    STATUS           current
    DESCRIPTION
        "Entry for the cfprSwEthLanFlowMonFsmTable table."
    INDEX { cfprSwEthLanFlowMonFsmInstanceId }
    ::= { cfprSwEthLanFlowMonFsmTable 1 }

CfprSwEthLanFlowMonFsmEntry ::= SEQUENCE {
    cfprSwEthLanFlowMonFsmInstanceId                                 CfprManagedObjectId,
    cfprSwEthLanFlowMonFsmDn                                         CfprManagedObjectDn,
    cfprSwEthLanFlowMonFsmRn                                         SnmpAdminString,
    cfprSwEthLanFlowMonFsmCompletionTime                             DateAndTime,
    cfprSwEthLanFlowMonFsmCurrentFsm                                 CfprSwEthLanFlowMonFsmCurrentFsm,
    cfprSwEthLanFlowMonFsmDescrData                                  SnmpAdminString,
    cfprSwEthLanFlowMonFsmFsmStatus                                  CfprFsmFsmStageStatus,
    cfprSwEthLanFlowMonFsmProgress                                   Gauge32,
    cfprSwEthLanFlowMonFsmRmtErrCode                                 Gauge32,
    cfprSwEthLanFlowMonFsmRmtErrDescr                                SnmpAdminString,
    cfprSwEthLanFlowMonFsmRmtRslt                                    CfprConditionRemoteInvRslt
}

cfprSwEthLanFlowMonFsmInstanceId OBJECT-TYPE
    SYNTAX       CfprManagedObjectId
    MAX-ACCESS   not-accessible
    STATUS       current
    DESCRIPTION
        "Instance identifier of the managed object."
    ::= { cfprSwEthLanFlowMonFsmEntry 1 }

cfprSwEthLanFlowMonFsmDn OBJECT-TYPE
    SYNTAX       CfprManagedObjectDn
    MAX-ACCESS   read-only
    STATUS       current
    DESCRIPTION
        "Cisco Firepower sw:EthLanFlowMonFsm:dn managed object property"
    ::= { cfprSwEthLanFlowMonFsmEntry 2 }

cfprSwEthLanFlowMonFsmRn OBJECT-TYPE
    SYNTAX       SnmpAdminString
    MAX-ACCESS   read-only
    STATUS       current
    DESCRIPTION
        "Cisco Firepower sw:EthLanFlowMonFsm:rn managed object property"
    ::= { cfprSwEthLanFlowMonFsmEntry 3 }

cfprSwEthLanFlowMonFsmCompletionTime OBJECT-TYPE
    SYNTAX       DateAndTime
    MAX-ACCESS   read-only
    STATUS       current
    DESCRIPTION
        "Cisco Firepower sw:EthLanFlowMonFsm:completionTime
        managed object property"
    ::= { cfprSwEthLanFlowMonFsmEntry 4 }

cfprSwEthLanFlowMonFsmCurrentFsm OBJECT-TYPE
    SYNTAX       CfprSwEthLanFlowMonFsmCurrentFsm
    MAX-ACCESS   read-only
    STATUS       current
    DESCRIPTION
        "Cisco Firepower sw:EthLanFlowMonFsm:currentFsm
        managed object property"
    ::= { cfprSwEthLanFlowMonFsmEntry 5 }

cfprSwEthLanFlowMonFsmDescrData OBJECT-TYPE
    SYNTAX       SnmpAdminString
    MAX-ACCESS   read-only
    STATUS       current
    DESCRIPTION
        "Cisco Firepower sw:EthLanFlowMonFsm:descr managed
        object property"
    ::= { cfprSwEthLanFlowMonFsmEntry 6 }

cfprSwEthLanFlowMonFsmFsmStatus OBJECT-TYPE
    SYNTAX       CfprFsmFsmStageStatus
    MAX-ACCESS   read-only
    STATUS       current
    DESCRIPTION
        "Cisco Firepower sw:EthLanFlowMonFsm:fsmStatus
        managed object property"
    ::= { cfprSwEthLanFlowMonFsmEntry 7 }

cfprSwEthLanFlowMonFsmProgress OBJECT-TYPE
    SYNTAX       Gauge32
    MAX-ACCESS   read-only
    STATUS       current
    DESCRIPTION
        "Cisco Firepower sw:EthLanFlowMonFsm:progress managed
        object property"
    ::= { cfprSwEthLanFlowMonFsmEntry 8 }

cfprSwEthLanFlowMonFsmRmtErrCode OBJECT-TYPE
    SYNTAX       Gauge32
    MAX-ACCESS   read-only
    STATUS       current
    DESCRIPTION
        "Cisco Firepower sw:EthLanFlowMonFsm:rmtErrCode
        managed object property"
    ::= { cfprSwEthLanFlowMonFsmEntry 9 }

cfprSwEthLanFlowMonFsmRmtErrDescr OBJECT-TYPE
    SYNTAX       SnmpAdminString
    MAX-ACCESS   read-only
    STATUS       current
    DESCRIPTION
        "Cisco Firepower sw:EthLanFlowMonFsm:rmtErrDescr
        managed object property"
    ::= { cfprSwEthLanFlowMonFsmEntry 10 }

cfprSwEthLanFlowMonFsmRmtRslt OBJECT-TYPE
    SYNTAX       CfprConditionRemoteInvRslt
    MAX-ACCESS   read-only
    STATUS       current
    DESCRIPTION
        "Cisco Firepower sw:EthLanFlowMonFsm:rmtRslt managed
        object property"
    ::= { cfprSwEthLanFlowMonFsmEntry 11 }

cfprSwEthLanFlowMonFsmStageTable OBJECT-TYPE
    SYNTAX           SEQUENCE OF CfprSwEthLanFlowMonFsmStageEntry
    MAX-ACCESS       not-accessible
    STATUS           current
    DESCRIPTION
        "Cisco Firepower sw:EthLanFlowMonFsmStage managed object table"
    ::= { cfprSwObjects 20 }

cfprSwEthLanFlowMonFsmStageEntry OBJECT-TYPE
    SYNTAX           CfprSwEthLanFlowMonFsmStageEntry
    MAX-ACCESS       not-accessible
    STATUS           current
    DESCRIPTION
        "Entry for the cfprSwEthLanFlowMonFsmStageTable table."
    INDEX { cfprSwEthLanFlowMonFsmStageInstanceId }
    ::= { cfprSwEthLanFlowMonFsmStageTable 1 }

CfprSwEthLanFlowMonFsmStageEntry ::= SEQUENCE {
    cfprSwEthLanFlowMonFsmStageInstanceId                            CfprManagedObjectId,
    cfprSwEthLanFlowMonFsmStageDn                                    CfprManagedObjectDn,
    cfprSwEthLanFlowMonFsmStageRn                                    SnmpAdminString,
    cfprSwEthLanFlowMonFsmStageDescrData                             SnmpAdminString,
    cfprSwEthLanFlowMonFsmStageLastUpdateTime                        DateAndTime,
    cfprSwEthLanFlowMonFsmStageName                                  CfprSwEthLanFlowMonFsmStageName,
    cfprSwEthLanFlowMonFsmStageOrder                                 Gauge32,
    cfprSwEthLanFlowMonFsmStageRetry                                 Gauge32,
    cfprSwEthLanFlowMonFsmStageStageStatus                           CfprFsmFsmStageStatus
}

cfprSwEthLanFlowMonFsmStageInstanceId OBJECT-TYPE
    SYNTAX       CfprManagedObjectId
    MAX-ACCESS   not-accessible
    STATUS       current
    DESCRIPTION
        "Instance identifier of the managed object."
    ::= { cfprSwEthLanFlowMonFsmStageEntry 1 }

cfprSwEthLanFlowMonFsmStageDn OBJECT-TYPE
    SYNTAX       CfprManagedObjectDn
    MAX-ACCESS   read-only
    STATUS       current
    DESCRIPTION
        "Cisco Firepower sw:EthLanFlowMonFsmStage:dn managed
        object property"
    ::= { cfprSwEthLanFlowMonFsmStageEntry 2 }

cfprSwEthLanFlowMonFsmStageRn OBJECT-TYPE
    SYNTAX       SnmpAdminString
    MAX-ACCESS   read-only
    STATUS       current
    DESCRIPTION
        "Cisco Firepower sw:EthLanFlowMonFsmStage:rn managed
        object property"
    ::= { cfprSwEthLanFlowMonFsmStageEntry 3 }

cfprSwEthLanFlowMonFsmStageDescrData OBJECT-TYPE
    SYNTAX       SnmpAdminString
    MAX-ACCESS   read-only
    STATUS       current
    DESCRIPTION
        "Cisco Firepower sw:EthLanFlowMonFsmStage:descr
        managed object property"
    ::= { cfprSwEthLanFlowMonFsmStageEntry 4 }

cfprSwEthLanFlowMonFsmStageLastUpdateTime OBJECT-TYPE
    SYNTAX       DateAndTime
    MAX-ACCESS   read-only
    STATUS       current
    DESCRIPTION
        "Cisco Firepower sw:EthLanFlowMonFsmStage:lastUpdateTime
        managed object property"
    ::= { cfprSwEthLanFlowMonFsmStageEntry 5 }

cfprSwEthLanFlowMonFsmStageName OBJECT-TYPE
    SYNTAX       CfprSwEthLanFlowMonFsmStageName
    MAX-ACCESS   read-only
    STATUS       current
    DESCRIPTION
        "Cisco Firepower sw:EthLanFlowMonFsmStage:name
        managed object property"
    ::= { cfprSwEthLanFlowMonFsmStageEntry 6 }

cfprSwEthLanFlowMonFsmStageOrder OBJECT-TYPE
    SYNTAX       Gauge32
    MAX-ACCESS   read-only
    STATUS       current
    DESCRIPTION
        "Cisco Firepower sw:EthLanFlowMonFsmStage:order
        managed object property"
    ::= { cfprSwEthLanFlowMonFsmStageEntry 7 }

cfprSwEthLanFlowMonFsmStageRetry OBJECT-TYPE
    SYNTAX       Gauge32
    MAX-ACCESS   read-only
    STATUS       current
    DESCRIPTION
        "Cisco Firepower sw:EthLanFlowMonFsmStage:retry
        managed object property"
    ::= { cfprSwEthLanFlowMonFsmStageEntry 8 }

cfprSwEthLanFlowMonFsmStageStageStatus OBJECT-TYPE
    SYNTAX       CfprFsmFsmStageStatus
    MAX-ACCESS   read-only
    STATUS       current
    DESCRIPTION
        "Cisco Firepower sw:EthLanFlowMonFsmStage:stageStatus
        managed object property"
    ::= { cfprSwEthLanFlowMonFsmStageEntry 9 }

cfprSwEthLanFlowMonFsmTaskTable OBJECT-TYPE
    SYNTAX           SEQUENCE OF CfprSwEthLanFlowMonFsmTaskEntry
    MAX-ACCESS       not-accessible
    STATUS           current
    DESCRIPTION
        "Cisco Firepower sw:EthLanFlowMonFsmTask managed object table"
    ::= { cfprSwObjects 21 }

cfprSwEthLanFlowMonFsmTaskEntry OBJECT-TYPE
    SYNTAX           CfprSwEthLanFlowMonFsmTaskEntry
    MAX-ACCESS       not-accessible
    STATUS           current
    DESCRIPTION
        "Entry for the cfprSwEthLanFlowMonFsmTaskTable table."
    INDEX { cfprSwEthLanFlowMonFsmTaskInstanceId }
    ::= { cfprSwEthLanFlowMonFsmTaskTable 1 }

CfprSwEthLanFlowMonFsmTaskEntry ::= SEQUENCE {
    cfprSwEthLanFlowMonFsmTaskInstanceId                             CfprManagedObjectId,
    cfprSwEthLanFlowMonFsmTaskDn                                     CfprManagedObjectDn,
    cfprSwEthLanFlowMonFsmTaskRn                                     SnmpAdminString,
    cfprSwEthLanFlowMonFsmTaskCompletion                             CfprFsmCompletion,
    cfprSwEthLanFlowMonFsmTaskFlags                                  CfprFsmFlags,
    cfprSwEthLanFlowMonFsmTaskItem                                   CfprSwEthLanFlowMonFsmTaskItem,
    cfprSwEthLanFlowMonFsmTaskSeqId                                  Gauge32
}

cfprSwEthLanFlowMonFsmTaskInstanceId OBJECT-TYPE
    SYNTAX       CfprManagedObjectId
    MAX-ACCESS   not-accessible
    STATUS       current
    DESCRIPTION
        "Instance identifier of the managed object."
    ::= { cfprSwEthLanFlowMonFsmTaskEntry 1 }

cfprSwEthLanFlowMonFsmTaskDn OBJECT-TYPE
    SYNTAX       CfprManagedObjectDn
    MAX-ACCESS   read-only
    STATUS       current
    DESCRIPTION
        "Cisco Firepower sw:EthLanFlowMonFsmTask:dn managed
        object property"
    ::= { cfprSwEthLanFlowMonFsmTaskEntry 2 }

cfprSwEthLanFlowMonFsmTaskRn OBJECT-TYPE
    SYNTAX       SnmpAdminString
    MAX-ACCESS   read-only
    STATUS       current
    DESCRIPTION
        "Cisco Firepower sw:EthLanFlowMonFsmTask:rn managed
        object property"
    ::= { cfprSwEthLanFlowMonFsmTaskEntry 3 }

cfprSwEthLanFlowMonFsmTaskCompletion OBJECT-TYPE
    SYNTAX       CfprFsmCompletion
    MAX-ACCESS   read-only
    STATUS       current
    DESCRIPTION
        "Cisco Firepower sw:EthLanFlowMonFsmTask:completion
        managed object property"
    ::= { cfprSwEthLanFlowMonFsmTaskEntry 4 }

cfprSwEthLanFlowMonFsmTaskFlags OBJECT-TYPE
    SYNTAX       CfprFsmFlags
    MAX-ACCESS   read-only
    STATUS       current
    DESCRIPTION
        "Cisco Firepower sw:EthLanFlowMonFsmTask:flags
        managed object property"
    ::= { cfprSwEthLanFlowMonFsmTaskEntry 5 }

cfprSwEthLanFlowMonFsmTaskItem OBJECT-TYPE
    SYNTAX       CfprSwEthLanFlowMonFsmTaskItem
    MAX-ACCESS   read-only
    STATUS       current
    DESCRIPTION
        "Cisco Firepower sw:EthLanFlowMonFsmTask:item managed
        object property"
    ::= { cfprSwEthLanFlowMonFsmTaskEntry 6 }

cfprSwEthLanFlowMonFsmTaskSeqId OBJECT-TYPE
    SYNTAX       Gauge32
    MAX-ACCESS   read-only
    STATUS       current
    DESCRIPTION
        "Cisco Firepower sw:EthLanFlowMonFsmTask:seqId
        managed object property"
    ::= { cfprSwEthLanFlowMonFsmTaskEntry 7 }

cfprSwEthLanMonTable OBJECT-TYPE
    SYNTAX           SEQUENCE OF CfprSwEthLanMonEntry
    MAX-ACCESS       not-accessible
    STATUS           current
    DESCRIPTION
        "Cisco Firepower sw:EthLanMon managed object table"
    ::= { cfprSwObjects 22 }

cfprSwEthLanMonEntry OBJECT-TYPE
    SYNTAX           CfprSwEthLanMonEntry
    MAX-ACCESS       not-accessible
    STATUS           current
    DESCRIPTION
        "Entry for the cfprSwEthLanMonTable table."
    INDEX { cfprSwEthLanMonInstanceId }
    ::= { cfprSwEthLanMonTable 1 }

CfprSwEthLanMonEntry ::= SEQUENCE {
    cfprSwEthLanMonInstanceId                                        CfprManagedObjectId,
    cfprSwEthLanMonDn                                                CfprManagedObjectDn,
    cfprSwEthLanMonRn                                                SnmpAdminString,
    cfprSwEthLanMonLocale                                            CfprSwMonDomainLocale,
    cfprSwEthLanMonName                                              SnmpAdminString,
    cfprSwEthLanMonSwitchId                                          CfprNetworkSwitchId,
    cfprSwEthLanMonTransport                                         CfprSwEthLanMonTransport,
    cfprSwEthLanMonType                                              CfprSwLanMonType
}

cfprSwEthLanMonInstanceId OBJECT-TYPE
    SYNTAX       CfprManagedObjectId
    MAX-ACCESS   not-accessible
    STATUS       current
    DESCRIPTION
        "Instance identifier of the managed object."
    ::= { cfprSwEthLanMonEntry 1 }

cfprSwEthLanMonDn OBJECT-TYPE
    SYNTAX       CfprManagedObjectDn
    MAX-ACCESS   read-only
    STATUS       current
    DESCRIPTION
        "Cisco Firepower sw:EthLanMon:dn managed object property"
    ::= { cfprSwEthLanMonEntry 2 }

cfprSwEthLanMonRn OBJECT-TYPE
    SYNTAX       SnmpAdminString
    MAX-ACCESS   read-only
    STATUS       current
    DESCRIPTION
        "Cisco Firepower sw:EthLanMon:rn managed object property"
    ::= { cfprSwEthLanMonEntry 3 }

cfprSwEthLanMonLocale OBJECT-TYPE
    SYNTAX       CfprSwMonDomainLocale
    MAX-ACCESS   read-only
    STATUS       current
    DESCRIPTION
        "Cisco Firepower sw:EthLanMon:locale managed object property"
    ::= { cfprSwEthLanMonEntry 4 }

cfprSwEthLanMonName OBJECT-TYPE
    SYNTAX       SnmpAdminString
    MAX-ACCESS   read-only
    STATUS       current
    DESCRIPTION
        "Cisco Firepower sw:EthLanMon:name managed object property"
    ::= { cfprSwEthLanMonEntry 5 }

cfprSwEthLanMonSwitchId OBJECT-TYPE
    SYNTAX       CfprNetworkSwitchId
    MAX-ACCESS   read-only
    STATUS       current
    DESCRIPTION
        "Cisco Firepower sw:EthLanMon:switchId managed object property"
    ::= { cfprSwEthLanMonEntry 6 }

cfprSwEthLanMonTransport OBJECT-TYPE
    SYNTAX       CfprSwEthLanMonTransport
    MAX-ACCESS   read-only
    STATUS       current
    DESCRIPTION
        "Cisco Firepower sw:EthLanMon:transport managed object property"
    ::= { cfprSwEthLanMonEntry 7 }

cfprSwEthLanMonType OBJECT-TYPE
    SYNTAX       CfprSwLanMonType
    MAX-ACCESS   read-only
    STATUS       current
    DESCRIPTION
        "Cisco Firepower sw:EthLanMon:type managed object property"
    ::= { cfprSwEthLanMonEntry 8 }

cfprSwEthLanPcTable OBJECT-TYPE
    SYNTAX           SEQUENCE OF CfprSwEthLanPcEntry
    MAX-ACCESS       not-accessible
    STATUS           current
    DESCRIPTION
        "Cisco Firepower sw:EthLanPc managed object table"
    ::= { cfprSwObjects 23 }

cfprSwEthLanPcEntry OBJECT-TYPE
    SYNTAX           CfprSwEthLanPcEntry
    MAX-ACCESS       not-accessible
    STATUS           current
    DESCRIPTION
        "Entry for the cfprSwEthLanPcTable table."
    INDEX { cfprSwEthLanPcInstanceId }
    ::= { cfprSwEthLanPcTable 1 }

CfprSwEthLanPcEntry ::= SEQUENCE {
    cfprSwEthLanPcInstanceId                                         CfprManagedObjectId,
    cfprSwEthLanPcDn                                                 CfprManagedObjectDn,
    cfprSwEthLanPcRn                                                 SnmpAdminString,
    cfprSwEthLanPcAdminSpeed                                         CfprPortEthSpeed,
    cfprSwEthLanPcAdminState                                         CfprFabricAdminState,
    cfprSwEthLanPcClusterName                                        SnmpAdminString,
    cfprSwEthLanPcDtagVlan                                           Gauge32,
    cfprSwEthLanPcEpDn                                               SnmpAdminString,
    cfprSwEthLanPcIfRole                                             CfprSwLanPcIfRole,
    cfprSwEthLanPcIfType                                             CfprSwCIoEpIfType,
    cfprSwEthLanPcLacpFastTimer                                      TruthValue,
    cfprSwEthLanPcLacpSuspendIndividual                              TruthValue,
    cfprSwEthLanPcLocale                                             CfprSwBorderPcLocale,
    cfprSwEthLanPcMonTrafDir                                         CfprFabricTrafficDirection,
    cfprSwEthLanPcName                                               SnmpAdminString,
    cfprSwEthLanPcPeerDn                                             SnmpAdminString,
    cfprSwEthLanPcPortId                                             Gauge32,
    cfprSwEthLanPcPriorityFlowCtrl                                   CfprFlowctrlPriorityPause,
    cfprSwEthLanPcRecvFlowCtrl                                       CfprFlowctrlFlowControlRx,
    cfprSwEthLanPcSendFlowCtrl                                       CfprFlowctrlFlowControlTx,
    cfprSwEthLanPcSpannedCluster                                     CfprFabricSpannedCluster,
    cfprSwEthLanPcSwitchId                                           CfprNetworkSwitchId,
    cfprSwEthLanPcTransport                                          CfprSwEthLanPcTransport,
    cfprSwEthLanPcType                                               CfprSwLanPcType,
    cfprSwEthLanPcCluChassisId                                       Gauge32,
    cfprSwEthLanPcLacpDetach                                         CfprSwAdminState,
    cfprSwEthLanPcAdminDuplex                                        CfprPortDuplex,
    cfprSwEthLanPcAutoNeg                                            TruthValue,
    cfprSwEthLanPcHashAlg                                            CfprNhTpHashType,
    cfprSwEthLanPcInlineState                                        CfprSwEthLanPcInlineState,
    cfprSwEthLanPcPcMode                                             CfprSwPcMode,
    cfprSwEthLanPcPcModeState                                        CfprSwPcModeState,
    cfprSwEthLanPcQosPrio                                            CfprFabricQosPrio,
    cfprSwEthLanPcLldp                                               CfprNwctrlLldpAdminStateBitmask
}

cfprSwEthLanPcInstanceId OBJECT-TYPE
    SYNTAX       CfprManagedObjectId
    MAX-ACCESS   not-accessible
    STATUS       current
    DESCRIPTION
        "Instance identifier of the managed object."
    ::= { cfprSwEthLanPcEntry 1 }

cfprSwEthLanPcDn OBJECT-TYPE
    SYNTAX       CfprManagedObjectDn
    MAX-ACCESS   read-only
    STATUS       current
    DESCRIPTION
        "Cisco Firepower sw:EthLanPc:dn managed object property"
    ::= { cfprSwEthLanPcEntry 2 }

cfprSwEthLanPcRn OBJECT-TYPE
    SYNTAX       SnmpAdminString
    MAX-ACCESS   read-only
    STATUS       current
    DESCRIPTION
        "Cisco Firepower sw:EthLanPc:rn managed object property"
    ::= { cfprSwEthLanPcEntry 3 }

cfprSwEthLanPcAdminSpeed OBJECT-TYPE
    SYNTAX       CfprPortEthSpeed
    MAX-ACCESS   read-only
    STATUS       current
    DESCRIPTION
        "Cisco Firepower sw:EthLanPc:adminSpeed managed object property"
    ::= { cfprSwEthLanPcEntry 4 }

cfprSwEthLanPcAdminState OBJECT-TYPE
    SYNTAX       CfprFabricAdminState
    MAX-ACCESS   read-only
    STATUS       current
    DESCRIPTION
        "Cisco Firepower sw:EthLanPc:adminState managed object property"
    ::= { cfprSwEthLanPcEntry 5 }

cfprSwEthLanPcClusterName OBJECT-TYPE
    SYNTAX       SnmpAdminString
    MAX-ACCESS   read-only
    STATUS       current
    DESCRIPTION
        "Cisco Firepower sw:EthLanPc:clusterName managed object property"
    ::= { cfprSwEthLanPcEntry 6 }

cfprSwEthLanPcDtagVlan OBJECT-TYPE
    SYNTAX       Gauge32
    MAX-ACCESS   read-only
    STATUS       current
    DESCRIPTION
        "Cisco Firepower sw:EthLanPc:dtagVlan managed object property"
    ::= { cfprSwEthLanPcEntry 7 }

cfprSwEthLanPcEpDn OBJECT-TYPE
    SYNTAX       SnmpAdminString
    MAX-ACCESS   read-only
    STATUS       current
    DESCRIPTION
        "Cisco Firepower sw:EthLanPc:epDn managed object property"
    ::= { cfprSwEthLanPcEntry 8 }

cfprSwEthLanPcIfRole OBJECT-TYPE
    SYNTAX       CfprSwLanPcIfRole
    MAX-ACCESS   read-only
    STATUS       current
    DESCRIPTION
        "Cisco Firepower sw:EthLanPc:ifRole managed object property"
    ::= { cfprSwEthLanPcEntry 9 }

cfprSwEthLanPcIfType OBJECT-TYPE
    SYNTAX       CfprSwCIoEpIfType
    MAX-ACCESS   read-only
    STATUS       current
    DESCRIPTION
        "Cisco Firepower sw:EthLanPc:ifType managed object property"
    ::= { cfprSwEthLanPcEntry 10 }

cfprSwEthLanPcLacpFastTimer OBJECT-TYPE
    SYNTAX       TruthValue
    MAX-ACCESS   read-only
    STATUS       current
    DESCRIPTION
        "Cisco Firepower sw:EthLanPc:lacpFastTimer managed
        object property"
    ::= { cfprSwEthLanPcEntry 11 }

cfprSwEthLanPcLacpSuspendIndividual OBJECT-TYPE
    SYNTAX       TruthValue
    MAX-ACCESS   read-only
    STATUS       current
    DESCRIPTION
        "Cisco Firepower sw:EthLanPc:lacpSuspendIndividual
        managed object property"
    ::= { cfprSwEthLanPcEntry 12 }

cfprSwEthLanPcLocale OBJECT-TYPE
    SYNTAX       CfprSwBorderPcLocale
    MAX-ACCESS   read-only
    STATUS       current
    DESCRIPTION
        "Cisco Firepower sw:EthLanPc:locale managed object property"
    ::= { cfprSwEthLanPcEntry 13 }

cfprSwEthLanPcMonTrafDir OBJECT-TYPE
    SYNTAX       CfprFabricTrafficDirection
    MAX-ACCESS   read-only
    STATUS       current
    DESCRIPTION
        "Cisco Firepower sw:EthLanPc:monTrafDir managed object property"
    ::= { cfprSwEthLanPcEntry 14 }

cfprSwEthLanPcName OBJECT-TYPE
    SYNTAX       SnmpAdminString
    MAX-ACCESS   read-only
    STATUS       current
    DESCRIPTION
        "Cisco Firepower sw:EthLanPc:name managed object property"
    ::= { cfprSwEthLanPcEntry 16 }

cfprSwEthLanPcPeerDn OBJECT-TYPE
    SYNTAX       SnmpAdminString
    MAX-ACCESS   read-only
    STATUS       current
    DESCRIPTION
        "Cisco Firepower sw:EthLanPc:peerDn managed object property"
    ::= { cfprSwEthLanPcEntry 17 }

cfprSwEthLanPcPortId OBJECT-TYPE
    SYNTAX       Gauge32
    MAX-ACCESS   read-only
    STATUS       current
    DESCRIPTION
        "Cisco Firepower sw:EthLanPc:portId managed object property"
    ::= { cfprSwEthLanPcEntry 18 }

cfprSwEthLanPcPriorityFlowCtrl OBJECT-TYPE
    SYNTAX       CfprFlowctrlPriorityPause
    MAX-ACCESS   read-only
    STATUS       current
    DESCRIPTION
        "Cisco Firepower sw:EthLanPc:priorityFlowCtrl managed
        object property"
    ::= { cfprSwEthLanPcEntry 19 }

cfprSwEthLanPcRecvFlowCtrl OBJECT-TYPE
    SYNTAX       CfprFlowctrlFlowControlRx
    MAX-ACCESS   read-only
    STATUS       current
    DESCRIPTION
        "Cisco Firepower sw:EthLanPc:recvFlowCtrl managed object property"
    ::= { cfprSwEthLanPcEntry 20 }

cfprSwEthLanPcSendFlowCtrl OBJECT-TYPE
    SYNTAX       CfprFlowctrlFlowControlTx
    MAX-ACCESS   read-only
    STATUS       current
    DESCRIPTION
        "Cisco Firepower sw:EthLanPc:sendFlowCtrl managed object property"
    ::= { cfprSwEthLanPcEntry 21 }

cfprSwEthLanPcSpannedCluster OBJECT-TYPE
    SYNTAX       CfprFabricSpannedCluster
    MAX-ACCESS   read-only
    STATUS       current
    DESCRIPTION
        "Cisco Firepower sw:EthLanPc:spannedCluster managed
        object property"
    ::= { cfprSwEthLanPcEntry 22 }

cfprSwEthLanPcSwitchId OBJECT-TYPE
    SYNTAX       CfprNetworkSwitchId
    MAX-ACCESS   read-only
    STATUS       current
    DESCRIPTION
        "Cisco Firepower sw:EthLanPc:switchId managed object property"
    ::= { cfprSwEthLanPcEntry 23 }

cfprSwEthLanPcTransport OBJECT-TYPE
    SYNTAX       CfprSwEthLanPcTransport
    MAX-ACCESS   read-only
    STATUS       current
    DESCRIPTION
        "Cisco Firepower sw:EthLanPc:transport managed object property"
    ::= { cfprSwEthLanPcEntry 24 }

cfprSwEthLanPcType OBJECT-TYPE
    SYNTAX       CfprSwLanPcType
    MAX-ACCESS   read-only
    STATUS       current
    DESCRIPTION
        "Cisco Firepower sw:EthLanPc:type managed object property"
    ::= { cfprSwEthLanPcEntry 25 }

cfprSwEthLanPcCluChassisId OBJECT-TYPE
    SYNTAX       Gauge32
    MAX-ACCESS   read-only
    STATUS       current
    DESCRIPTION
        "Cisco Firepower sw:EthLanPc:cluChassisId managed object property"
    ::= { cfprSwEthLanPcEntry 26 }

cfprSwEthLanPcLacpDetach OBJECT-TYPE
    SYNTAX       CfprSwAdminState
    MAX-ACCESS   read-only
    STATUS       current
    DESCRIPTION
        "Cisco Firepower sw:EthLanPc:lacpDetach managed object property"
    ::= { cfprSwEthLanPcEntry 27 }

cfprSwEthLanPcAdminDuplex OBJECT-TYPE
    SYNTAX       CfprPortDuplex
    MAX-ACCESS   read-only
    STATUS       current
    DESCRIPTION
        "Cisco Firepower sw:EthLanPc:adminDuplex managed object property"
    ::= { cfprSwEthLanPcEntry 28 }

cfprSwEthLanPcAutoNeg OBJECT-TYPE
    SYNTAX       TruthValue
    MAX-ACCESS   read-only
    STATUS       current
    DESCRIPTION
        "Cisco Firepower sw:EthLanPc:autoNeg managed object property"
    ::= { cfprSwEthLanPcEntry 29 }

cfprSwEthLanPcHashAlg OBJECT-TYPE
    SYNTAX       CfprNhTpHashType
    MAX-ACCESS   read-only
    STATUS       current
    DESCRIPTION
        "Cisco Firepower sw:EthLanPc:hashAlg managed object property"
    ::= { cfprSwEthLanPcEntry 30 }

cfprSwEthLanPcInlineState OBJECT-TYPE
    SYNTAX       CfprSwEthLanPcInlineState
    MAX-ACCESS   read-only
    STATUS       current
    DESCRIPTION
        "Cisco Firepower sw:EthLanPc:inlineState managed object property"
    ::= { cfprSwEthLanPcEntry 31 }

cfprSwEthLanPcPcMode OBJECT-TYPE
    SYNTAX       CfprSwPcMode
    MAX-ACCESS   read-only
    STATUS       current
    DESCRIPTION
        "Cisco Firepower sw:EthLanPc:pcMode managed object property"
    ::= { cfprSwEthLanPcEntry 32 }

cfprSwEthLanPcPcModeState OBJECT-TYPE
    SYNTAX       CfprSwPcModeState
    MAX-ACCESS   read-only
    STATUS       current
    DESCRIPTION
        "Cisco Firepower sw:EthLanPc:pcModeState managed object property"
    ::= { cfprSwEthLanPcEntry 33 }

cfprSwEthLanPcQosPrio OBJECT-TYPE
    SYNTAX       CfprFabricQosPrio
    MAX-ACCESS   read-only
    STATUS       current
    DESCRIPTION
        "Cisco Firepower sw:EthLanPc:qosPrio managed object property"
    ::= { cfprSwEthLanPcEntry 34 }

cfprSwEthLanPcLldp OBJECT-TYPE
    SYNTAX       CfprNwctrlLldpAdminStateBitmask
    MAX-ACCESS   read-only
    STATUS       current
    DESCRIPTION
        "Cisco Firepower sw:EthLanPc:lldp managed object property"
    ::= { cfprSwEthLanPcEntry 35 }

cfprSwEthMonTable OBJECT-TYPE
    SYNTAX           SEQUENCE OF CfprSwEthMonEntry
    MAX-ACCESS       not-accessible
    STATUS           current
    DESCRIPTION
        "Cisco Firepower sw:EthMon managed object table"
    ::= { cfprSwObjects 24 }

cfprSwEthMonEntry OBJECT-TYPE
    SYNTAX           CfprSwEthMonEntry
    MAX-ACCESS       not-accessible
    STATUS           current
    DESCRIPTION
        "Entry for the cfprSwEthMonTable table."
    INDEX { cfprSwEthMonInstanceId }
    ::= { cfprSwEthMonTable 1 }

CfprSwEthMonEntry ::= SEQUENCE {
    cfprSwEthMonInstanceId                                           CfprManagedObjectId,
    cfprSwEthMonDn                                                   CfprManagedObjectDn,
    cfprSwEthMonRn                                                   SnmpAdminString,
    cfprSwEthMonAdminState                                           CfprSwMonAdminState,
    cfprSwEthMonFsmDescr                                             SnmpAdminString,
    cfprSwEthMonFsmPrev                                              SnmpAdminString,
    cfprSwEthMonFsmProgr                                             Gauge32,
    cfprSwEthMonFsmRmtInvErrCode                                     Gauge32,
    cfprSwEthMonFsmRmtInvErrDescr                                    SnmpAdminString,
    cfprSwEthMonFsmRmtInvRslt                                        CfprConditionRemoteInvRslt,
    cfprSwEthMonFsmStageDescr                                        SnmpAdminString,
    cfprSwEthMonFsmStamp                                             DateAndTime,
    cfprSwEthMonFsmStatus                                            SnmpAdminString,
    cfprSwEthMonFsmTry                                               Gauge32,
    cfprSwEthMonHasLastDest                                          TruthValue,
    cfprSwEthMonLifeCycle                                            CfprSwMonLifeCycle,
    cfprSwEthMonName                                                 SnmpAdminString,
    cfprSwEthMonPeerDn                                               SnmpAdminString,
    cfprSwEthMonSession                                              Gauge32,
    cfprSwEthMonSwitchId                                             CfprNetworkSwitchId,
    cfprSwEthMonTransport                                            CfprSwEthMonTransport,
    cfprSwEthMonType                                                 CfprSwEthMonType
}

cfprSwEthMonInstanceId OBJECT-TYPE
    SYNTAX       CfprManagedObjectId
    MAX-ACCESS   not-accessible
    STATUS       current
    DESCRIPTION
        "Instance identifier of the managed object."
    ::= { cfprSwEthMonEntry 1 }

cfprSwEthMonDn OBJECT-TYPE
    SYNTAX       CfprManagedObjectDn
    MAX-ACCESS   read-only
    STATUS       current
    DESCRIPTION
        "Cisco Firepower sw:EthMon:dn managed object property"
    ::= { cfprSwEthMonEntry 2 }

cfprSwEthMonRn OBJECT-TYPE
    SYNTAX       SnmpAdminString
    MAX-ACCESS   read-only
    STATUS       current
    DESCRIPTION
        "Cisco Firepower sw:EthMon:rn managed object property"
    ::= { cfprSwEthMonEntry 3 }

cfprSwEthMonAdminState OBJECT-TYPE
    SYNTAX       CfprSwMonAdminState
    MAX-ACCESS   read-only
    STATUS       current
    DESCRIPTION
        "Cisco Firepower sw:EthMon:adminState managed object property"
    ::= { cfprSwEthMonEntry 4 }

cfprSwEthMonFsmDescr OBJECT-TYPE
    SYNTAX       SnmpAdminString
    MAX-ACCESS   read-only
    STATUS       current
    DESCRIPTION
        "Cisco Firepower sw:EthMon:fsmDescr managed object property"
    ::= { cfprSwEthMonEntry 5 }

cfprSwEthMonFsmPrev OBJECT-TYPE
    SYNTAX       SnmpAdminString
    MAX-ACCESS   read-only
    STATUS       current
    DESCRIPTION
        "Cisco Firepower sw:EthMon:fsmPrev managed object property"
    ::= { cfprSwEthMonEntry 6 }

cfprSwEthMonFsmProgr OBJECT-TYPE
    SYNTAX       Gauge32
    MAX-ACCESS   read-only
    STATUS       current
    DESCRIPTION
        "Cisco Firepower sw:EthMon:fsmProgr managed object property"
    ::= { cfprSwEthMonEntry 7 }

cfprSwEthMonFsmRmtInvErrCode OBJECT-TYPE
    SYNTAX       Gauge32
    MAX-ACCESS   read-only
    STATUS       current
    DESCRIPTION
        "Cisco Firepower sw:EthMon:fsmRmtInvErrCode managed
        object property"
    ::= { cfprSwEthMonEntry 8 }

cfprSwEthMonFsmRmtInvErrDescr OBJECT-TYPE
    SYNTAX       SnmpAdminString
    MAX-ACCESS   read-only
    STATUS       current
    DESCRIPTION
        "Cisco Firepower sw:EthMon:fsmRmtInvErrDescr managed
        object property"
    ::= { cfprSwEthMonEntry 9 }

cfprSwEthMonFsmRmtInvRslt OBJECT-TYPE
    SYNTAX       CfprConditionRemoteInvRslt
    MAX-ACCESS   read-only
    STATUS       current
    DESCRIPTION
        "Cisco Firepower sw:EthMon:fsmRmtInvRslt managed object property"
    ::= { cfprSwEthMonEntry 10 }

cfprSwEthMonFsmStageDescr OBJECT-TYPE
    SYNTAX       SnmpAdminString
    MAX-ACCESS   read-only
    STATUS       current
    DESCRIPTION
        "Cisco Firepower sw:EthMon:fsmStageDescr managed object property"
    ::= { cfprSwEthMonEntry 11 }

cfprSwEthMonFsmStamp OBJECT-TYPE
    SYNTAX       DateAndTime
    MAX-ACCESS   read-only
    STATUS       current
    DESCRIPTION
        "Cisco Firepower sw:EthMon:fsmStamp managed object property"
    ::= { cfprSwEthMonEntry 12 }

cfprSwEthMonFsmStatus OBJECT-TYPE
    SYNTAX       SnmpAdminString
    MAX-ACCESS   read-only
    STATUS       current
    DESCRIPTION
        "Cisco Firepower sw:EthMon:fsmStatus managed object property"
    ::= { cfprSwEthMonEntry 13 }

cfprSwEthMonFsmTry OBJECT-TYPE
    SYNTAX       Gauge32
    MAX-ACCESS   read-only
    STATUS       current
    DESCRIPTION
        "Cisco Firepower sw:EthMon:fsmTry managed object property"
    ::= { cfprSwEthMonEntry 14 }

cfprSwEthMonHasLastDest OBJECT-TYPE
    SYNTAX       TruthValue
    MAX-ACCESS   read-only
    STATUS       current
    DESCRIPTION
        "Cisco Firepower sw:EthMon:hasLastDest managed object property"
    ::= { cfprSwEthMonEntry 15 }

cfprSwEthMonLifeCycle OBJECT-TYPE
    SYNTAX       CfprSwMonLifeCycle
    MAX-ACCESS   read-only
    STATUS       current
    DESCRIPTION
        "Cisco Firepower sw:EthMon:lifeCycle managed object property"
    ::= { cfprSwEthMonEntry 16 }

cfprSwEthMonName OBJECT-TYPE
    SYNTAX       SnmpAdminString
    MAX-ACCESS   read-only
    STATUS       current
    DESCRIPTION
        "Cisco Firepower sw:EthMon:name managed object property"
    ::= { cfprSwEthMonEntry 17 }

cfprSwEthMonPeerDn OBJECT-TYPE
    SYNTAX       SnmpAdminString
    MAX-ACCESS   read-only
    STATUS       current
    DESCRIPTION
        "Cisco Firepower sw:EthMon:peerDn managed object property"
    ::= { cfprSwEthMonEntry 18 }

cfprSwEthMonSession OBJECT-TYPE
    SYNTAX       Gauge32
    MAX-ACCESS   read-only
    STATUS       current
    DESCRIPTION
        "Cisco Firepower sw:EthMon:session managed object property"
    ::= { cfprSwEthMonEntry 19 }

cfprSwEthMonSwitchId OBJECT-TYPE
    SYNTAX       CfprNetworkSwitchId
    MAX-ACCESS   read-only
    STATUS       current
    DESCRIPTION
        "Cisco Firepower sw:EthMon:switchId managed object property"
    ::= { cfprSwEthMonEntry 20 }

cfprSwEthMonTransport OBJECT-TYPE
    SYNTAX       CfprSwEthMonTransport
    MAX-ACCESS   read-only
    STATUS       current
    DESCRIPTION
        "Cisco Firepower sw:EthMon:transport managed object property"
    ::= { cfprSwEthMonEntry 21 }

cfprSwEthMonType OBJECT-TYPE
    SYNTAX       CfprSwEthMonType
    MAX-ACCESS   read-only
    STATUS       current
    DESCRIPTION
        "Cisco Firepower sw:EthMon:type managed object property"
    ::= { cfprSwEthMonEntry 22 }

cfprSwEthMonDestEpTable OBJECT-TYPE
    SYNTAX           SEQUENCE OF CfprSwEthMonDestEpEntry
    MAX-ACCESS       not-accessible
    STATUS           current
    DESCRIPTION
        "Cisco Firepower sw:EthMonDestEp managed object table"
    ::= { cfprSwObjects 25 }

cfprSwEthMonDestEpEntry OBJECT-TYPE
    SYNTAX           CfprSwEthMonDestEpEntry
    MAX-ACCESS       not-accessible
    STATUS           current
    DESCRIPTION
        "Entry for the cfprSwEthMonDestEpTable table."
    INDEX { cfprSwEthMonDestEpInstanceId }
    ::= { cfprSwEthMonDestEpTable 1 }

CfprSwEthMonDestEpEntry ::= SEQUENCE {
    cfprSwEthMonDestEpInstanceId                                     CfprManagedObjectId,
    cfprSwEthMonDestEpDn                                             CfprManagedObjectDn,
    cfprSwEthMonDestEpRn                                             SnmpAdminString,
    cfprSwEthMonDestEpAdminSpeed                                     CfprPortEthSpeed,
    cfprSwEthMonDestEpAdminState                                     CfprFabricAdminState,
    cfprSwEthMonDestEpAggrPortId                                     Gauge32,
    cfprSwEthMonDestEpChassisId                                      Gauge32,
    cfprSwEthMonDestEpEpDn                                           SnmpAdminString,
    cfprSwEthMonDestEpIfRole                                         CfprNetworkPortRole,
    cfprSwEthMonDestEpIfType                                         CfprSwPIoEpIfType,
    cfprSwEthMonDestEpLc                                             CfprSwPIoEpLc,
    cfprSwEthMonDestEpLocale                                         CfprNetworkLocale,
    cfprSwEthMonDestEpName                                           SnmpAdminString,
    cfprSwEthMonDestEpPeerAggrPortId                                 Gauge32,
    cfprSwEthMonDestEpPeerChassisId                                  Gauge32,
    cfprSwEthMonDestEpPeerDn                                         SnmpAdminString,
    cfprSwEthMonDestEpPeerPortId                                     Gauge32,
    cfprSwEthMonDestEpPeerSlotId                                     Gauge32,
    cfprSwEthMonDestEpPortId                                         Gauge32,
    cfprSwEthMonDestEpSlotId                                         Gauge32,
    cfprSwEthMonDestEpSwitchId                                       CfprNetworkSwitchId,
    cfprSwEthMonDestEpTransport                                      CfprSwEthMonDestEpTransport,
    cfprSwEthMonDestEpType                                           CfprNetworkConnectionType
}

cfprSwEthMonDestEpInstanceId OBJECT-TYPE
    SYNTAX       CfprManagedObjectId
    MAX-ACCESS   not-accessible
    STATUS       current
    DESCRIPTION
        "Instance identifier of the managed object."
    ::= { cfprSwEthMonDestEpEntry 1 }

cfprSwEthMonDestEpDn OBJECT-TYPE
    SYNTAX       CfprManagedObjectDn
    MAX-ACCESS   read-only
    STATUS       current
    DESCRIPTION
        "Cisco Firepower sw:EthMonDestEp:dn managed object property"
    ::= { cfprSwEthMonDestEpEntry 2 }

cfprSwEthMonDestEpRn OBJECT-TYPE
    SYNTAX       SnmpAdminString
    MAX-ACCESS   read-only
    STATUS       current
    DESCRIPTION
        "Cisco Firepower sw:EthMonDestEp:rn managed object property"
    ::= { cfprSwEthMonDestEpEntry 3 }

cfprSwEthMonDestEpAdminSpeed OBJECT-TYPE
    SYNTAX       CfprPortEthSpeed
    MAX-ACCESS   read-only
    STATUS       current
    DESCRIPTION
        "Cisco Firepower sw:EthMonDestEp:adminSpeed managed
        object property"
    ::= { cfprSwEthMonDestEpEntry 4 }

cfprSwEthMonDestEpAdminState OBJECT-TYPE
    SYNTAX       CfprFabricAdminState
    MAX-ACCESS   read-only
    STATUS       current
    DESCRIPTION
        "Cisco Firepower sw:EthMonDestEp:adminState managed
        object property"
    ::= { cfprSwEthMonDestEpEntry 5 }

cfprSwEthMonDestEpAggrPortId OBJECT-TYPE
    SYNTAX       Gauge32
    MAX-ACCESS   read-only
    STATUS       current
    DESCRIPTION
        "Cisco Firepower sw:EthMonDestEp:aggrPortId managed
        object property"
    ::= { cfprSwEthMonDestEpEntry 6 }

cfprSwEthMonDestEpChassisId OBJECT-TYPE
    SYNTAX       Gauge32
    MAX-ACCESS   read-only
    STATUS       current
    DESCRIPTION
        "Cisco Firepower sw:EthMonDestEp:chassisId managed
        object property"
    ::= { cfprSwEthMonDestEpEntry 7 }

cfprSwEthMonDestEpEpDn OBJECT-TYPE
    SYNTAX       SnmpAdminString
    MAX-ACCESS   read-only
    STATUS       current
    DESCRIPTION
        "Cisco Firepower sw:EthMonDestEp:epDn managed object property"
    ::= { cfprSwEthMonDestEpEntry 8 }

cfprSwEthMonDestEpIfRole OBJECT-TYPE
    SYNTAX       CfprNetworkPortRole
    MAX-ACCESS   read-only
    STATUS       current
    DESCRIPTION
        "Cisco Firepower sw:EthMonDestEp:ifRole managed object property"
    ::= { cfprSwEthMonDestEpEntry 9 }

cfprSwEthMonDestEpIfType OBJECT-TYPE
    SYNTAX       CfprSwPIoEpIfType
    MAX-ACCESS   read-only
    STATUS       current
    DESCRIPTION
        "Cisco Firepower sw:EthMonDestEp:ifType managed object property"
    ::= { cfprSwEthMonDestEpEntry 10 }

cfprSwEthMonDestEpLc OBJECT-TYPE
    SYNTAX       CfprSwPIoEpLc
    MAX-ACCESS   read-only
    STATUS       current
    DESCRIPTION
        "Cisco Firepower sw:EthMonDestEp:lc managed object property"
    ::= { cfprSwEthMonDestEpEntry 11 }

cfprSwEthMonDestEpLocale OBJECT-TYPE
    SYNTAX       CfprNetworkLocale
    MAX-ACCESS   read-only
    STATUS       current
    DESCRIPTION
        "Cisco Firepower sw:EthMonDestEp:locale managed object property"
    ::= { cfprSwEthMonDestEpEntry 12 }

cfprSwEthMonDestEpName OBJECT-TYPE
    SYNTAX       SnmpAdminString
    MAX-ACCESS   read-only
    STATUS       current
    DESCRIPTION
        "Cisco Firepower sw:EthMonDestEp:name managed object property"
    ::= { cfprSwEthMonDestEpEntry 13 }

cfprSwEthMonDestEpPeerAggrPortId OBJECT-TYPE
    SYNTAX       Gauge32
    MAX-ACCESS   read-only
    STATUS       current
    DESCRIPTION
        "Cisco Firepower sw:EthMonDestEp:peerAggrPortId
        managed object property"
    ::= { cfprSwEthMonDestEpEntry 14 }

cfprSwEthMonDestEpPeerChassisId OBJECT-TYPE
    SYNTAX       Gauge32
    MAX-ACCESS   read-only
    STATUS       current
    DESCRIPTION
        "Cisco Firepower sw:EthMonDestEp:peerChassisId
        managed object property"
    ::= { cfprSwEthMonDestEpEntry 15 }

cfprSwEthMonDestEpPeerDn OBJECT-TYPE
    SYNTAX       SnmpAdminString
    MAX-ACCESS   read-only
    STATUS       current
    DESCRIPTION
        "Cisco Firepower sw:EthMonDestEp:peerDn managed object property"
    ::= { cfprSwEthMonDestEpEntry 16 }

cfprSwEthMonDestEpPeerPortId OBJECT-TYPE
    SYNTAX       Gauge32
    MAX-ACCESS   read-only
    STATUS       current
    DESCRIPTION
        "Cisco Firepower sw:EthMonDestEp:peerPortId managed
        object property"
    ::= { cfprSwEthMonDestEpEntry 17 }

cfprSwEthMonDestEpPeerSlotId OBJECT-TYPE
    SYNTAX       Gauge32
    MAX-ACCESS   read-only
    STATUS       current
    DESCRIPTION
        "Cisco Firepower sw:EthMonDestEp:peerSlotId managed
        object property"
    ::= { cfprSwEthMonDestEpEntry 18 }

cfprSwEthMonDestEpPortId OBJECT-TYPE
    SYNTAX       Gauge32
    MAX-ACCESS   read-only
    STATUS       current
    DESCRIPTION
        "Cisco Firepower sw:EthMonDestEp:portId managed object property"
    ::= { cfprSwEthMonDestEpEntry 19 }

cfprSwEthMonDestEpSlotId OBJECT-TYPE
    SYNTAX       Gauge32
    MAX-ACCESS   read-only
    STATUS       current
    DESCRIPTION
        "Cisco Firepower sw:EthMonDestEp:slotId managed object property"
    ::= { cfprSwEthMonDestEpEntry 20 }

cfprSwEthMonDestEpSwitchId OBJECT-TYPE
    SYNTAX       CfprNetworkSwitchId
    MAX-ACCESS   read-only
    STATUS       current
    DESCRIPTION
        "Cisco Firepower sw:EthMonDestEp:switchId managed object property"
    ::= { cfprSwEthMonDestEpEntry 21 }

cfprSwEthMonDestEpTransport OBJECT-TYPE
    SYNTAX       CfprSwEthMonDestEpTransport
    MAX-ACCESS   read-only
    STATUS       current
    DESCRIPTION
        "Cisco Firepower sw:EthMonDestEp:transport managed
        object property"
    ::= { cfprSwEthMonDestEpEntry 22 }

cfprSwEthMonDestEpType OBJECT-TYPE
    SYNTAX       CfprNetworkConnectionType
    MAX-ACCESS   read-only
    STATUS       current
    DESCRIPTION
        "Cisco Firepower sw:EthMonDestEp:type managed object property"
    ::= { cfprSwEthMonDestEpEntry 23 }

cfprSwEthMonFsmTable OBJECT-TYPE
    SYNTAX           SEQUENCE OF CfprSwEthMonFsmEntry
    MAX-ACCESS       not-accessible
    STATUS           current
    DESCRIPTION
        "Cisco Firepower sw:EthMonFsm managed object table"
    ::= { cfprSwObjects 26 }

cfprSwEthMonFsmEntry OBJECT-TYPE
    SYNTAX           CfprSwEthMonFsmEntry
    MAX-ACCESS       not-accessible
    STATUS           current
    DESCRIPTION
        "Entry for the cfprSwEthMonFsmTable table."
    INDEX { cfprSwEthMonFsmInstanceId }
    ::= { cfprSwEthMonFsmTable 1 }

CfprSwEthMonFsmEntry ::= SEQUENCE {
    cfprSwEthMonFsmInstanceId                                        CfprManagedObjectId,
    cfprSwEthMonFsmDn                                                CfprManagedObjectDn,
    cfprSwEthMonFsmRn                                                SnmpAdminString,
    cfprSwEthMonFsmCompletionTime                                    DateAndTime,
    cfprSwEthMonFsmCurrentFsm                                        CfprSwEthMonFsmCurrentFsm,
    cfprSwEthMonFsmDescrData                                         SnmpAdminString,
    cfprSwEthMonFsmFsmStatus                                         CfprFsmFsmStageStatus,
    cfprSwEthMonFsmProgress                                          Gauge32,
    cfprSwEthMonFsmRmtErrCode                                        Gauge32,
    cfprSwEthMonFsmRmtErrDescr                                       SnmpAdminString,
    cfprSwEthMonFsmRmtRslt                                           CfprConditionRemoteInvRslt
}

cfprSwEthMonFsmInstanceId OBJECT-TYPE
    SYNTAX       CfprManagedObjectId
    MAX-ACCESS   not-accessible
    STATUS       current
    DESCRIPTION
        "Instance identifier of the managed object."
    ::= { cfprSwEthMonFsmEntry 1 }

cfprSwEthMonFsmDn OBJECT-TYPE
    SYNTAX       CfprManagedObjectDn
    MAX-ACCESS   read-only
    STATUS       current
    DESCRIPTION
        "Cisco Firepower sw:EthMonFsm:dn managed object property"
    ::= { cfprSwEthMonFsmEntry 2 }

cfprSwEthMonFsmRn OBJECT-TYPE
    SYNTAX       SnmpAdminString
    MAX-ACCESS   read-only
    STATUS       current
    DESCRIPTION
        "Cisco Firepower sw:EthMonFsm:rn managed object property"
    ::= { cfprSwEthMonFsmEntry 3 }

cfprSwEthMonFsmCompletionTime OBJECT-TYPE
    SYNTAX       DateAndTime
    MAX-ACCESS   read-only
    STATUS       current
    DESCRIPTION
        "Cisco Firepower sw:EthMonFsm:completionTime managed
        object property"
    ::= { cfprSwEthMonFsmEntry 4 }

cfprSwEthMonFsmCurrentFsm OBJECT-TYPE
    SYNTAX       CfprSwEthMonFsmCurrentFsm
    MAX-ACCESS   read-only
    STATUS       current
    DESCRIPTION
        "Cisco Firepower sw:EthMonFsm:currentFsm managed object property"
    ::= { cfprSwEthMonFsmEntry 5 }

cfprSwEthMonFsmDescrData OBJECT-TYPE
    SYNTAX       SnmpAdminString
    MAX-ACCESS   read-only
    STATUS       current
    DESCRIPTION
        "Cisco Firepower sw:EthMonFsm:descr managed object property"
    ::= { cfprSwEthMonFsmEntry 6 }

cfprSwEthMonFsmFsmStatus OBJECT-TYPE
    SYNTAX       CfprFsmFsmStageStatus
    MAX-ACCESS   read-only
    STATUS       current
    DESCRIPTION
        "Cisco Firepower sw:EthMonFsm:fsmStatus managed object property"
    ::= { cfprSwEthMonFsmEntry 7 }

cfprSwEthMonFsmProgress OBJECT-TYPE
    SYNTAX       Gauge32
    MAX-ACCESS   read-only
    STATUS       current
    DESCRIPTION
        "Cisco Firepower sw:EthMonFsm:progress managed object property"
    ::= { cfprSwEthMonFsmEntry 8 }

cfprSwEthMonFsmRmtErrCode OBJECT-TYPE
    SYNTAX       Gauge32
    MAX-ACCESS   read-only
    STATUS       current
    DESCRIPTION
        "Cisco Firepower sw:EthMonFsm:rmtErrCode managed object property"
    ::= { cfprSwEthMonFsmEntry 9 }

cfprSwEthMonFsmRmtErrDescr OBJECT-TYPE
    SYNTAX       SnmpAdminString
    MAX-ACCESS   read-only
    STATUS       current
    DESCRIPTION
        "Cisco Firepower sw:EthMonFsm:rmtErrDescr managed object property"
    ::= { cfprSwEthMonFsmEntry 10 }

cfprSwEthMonFsmRmtRslt OBJECT-TYPE
    SYNTAX       CfprConditionRemoteInvRslt
    MAX-ACCESS   read-only
    STATUS       current
    DESCRIPTION
        "Cisco Firepower sw:EthMonFsm:rmtRslt managed object property"
    ::= { cfprSwEthMonFsmEntry 11 }

cfprSwEthMonFsmStageTable OBJECT-TYPE
    SYNTAX           SEQUENCE OF CfprSwEthMonFsmStageEntry
    MAX-ACCESS       not-accessible
    STATUS           current
    DESCRIPTION
        "Cisco Firepower sw:EthMonFsmStage managed object table"
    ::= { cfprSwObjects 27 }

cfprSwEthMonFsmStageEntry OBJECT-TYPE
    SYNTAX           CfprSwEthMonFsmStageEntry
    MAX-ACCESS       not-accessible
    STATUS           current
    DESCRIPTION
        "Entry for the cfprSwEthMonFsmStageTable table."
    INDEX { cfprSwEthMonFsmStageInstanceId }
    ::= { cfprSwEthMonFsmStageTable 1 }

CfprSwEthMonFsmStageEntry ::= SEQUENCE {
    cfprSwEthMonFsmStageInstanceId                                   CfprManagedObjectId,
    cfprSwEthMonFsmStageDn                                           CfprManagedObjectDn,
    cfprSwEthMonFsmStageRn                                           SnmpAdminString,
    cfprSwEthMonFsmStageDescrData                                    SnmpAdminString,
    cfprSwEthMonFsmStageLastUpdateTime                               DateAndTime,
    cfprSwEthMonFsmStageName                                         CfprSwEthMonFsmStageName,
    cfprSwEthMonFsmStageOrder                                        Gauge32,
    cfprSwEthMonFsmStageRetry                                        Gauge32,
    cfprSwEthMonFsmStageStageStatus                                  CfprFsmFsmStageStatus
}

cfprSwEthMonFsmStageInstanceId OBJECT-TYPE
    SYNTAX       CfprManagedObjectId
    MAX-ACCESS   not-accessible
    STATUS       current
    DESCRIPTION
        "Instance identifier of the managed object."
    ::= { cfprSwEthMonFsmStageEntry 1 }

cfprSwEthMonFsmStageDn OBJECT-TYPE
    SYNTAX       CfprManagedObjectDn
    MAX-ACCESS   read-only
    STATUS       current
    DESCRIPTION
        "Cisco Firepower sw:EthMonFsmStage:dn managed object property"
    ::= { cfprSwEthMonFsmStageEntry 2 }

cfprSwEthMonFsmStageRn OBJECT-TYPE
    SYNTAX       SnmpAdminString
    MAX-ACCESS   read-only
    STATUS       current
    DESCRIPTION
        "Cisco Firepower sw:EthMonFsmStage:rn managed object property"
    ::= { cfprSwEthMonFsmStageEntry 3 }

cfprSwEthMonFsmStageDescrData OBJECT-TYPE
    SYNTAX       SnmpAdminString
    MAX-ACCESS   read-only
    STATUS       current
    DESCRIPTION
        "Cisco Firepower sw:EthMonFsmStage:descr managed object property"
    ::= { cfprSwEthMonFsmStageEntry 4 }

cfprSwEthMonFsmStageLastUpdateTime OBJECT-TYPE
    SYNTAX       DateAndTime
    MAX-ACCESS   read-only
    STATUS       current
    DESCRIPTION
        "Cisco Firepower sw:EthMonFsmStage:lastUpdateTime
        managed object property"
    ::= { cfprSwEthMonFsmStageEntry 5 }

cfprSwEthMonFsmStageName OBJECT-TYPE
    SYNTAX       CfprSwEthMonFsmStageName
    MAX-ACCESS   read-only
    STATUS       current
    DESCRIPTION
        "Cisco Firepower sw:EthMonFsmStage:name managed object property"
    ::= { cfprSwEthMonFsmStageEntry 6 }

cfprSwEthMonFsmStageOrder OBJECT-TYPE
    SYNTAX       Gauge32
    MAX-ACCESS   read-only
    STATUS       current
    DESCRIPTION
        "Cisco Firepower sw:EthMonFsmStage:order managed object property"
    ::= { cfprSwEthMonFsmStageEntry 7 }

cfprSwEthMonFsmStageRetry OBJECT-TYPE
    SYNTAX       Gauge32
    MAX-ACCESS   read-only
    STATUS       current
    DESCRIPTION
        "Cisco Firepower sw:EthMonFsmStage:retry managed object property"
    ::= { cfprSwEthMonFsmStageEntry 8 }

cfprSwEthMonFsmStageStageStatus OBJECT-TYPE
    SYNTAX       CfprFsmFsmStageStatus
    MAX-ACCESS   read-only
    STATUS       current
    DESCRIPTION
        "Cisco Firepower sw:EthMonFsmStage:stageStatus
        managed object property"
    ::= { cfprSwEthMonFsmStageEntry 9 }

cfprSwEthMonFsmTaskTable OBJECT-TYPE
    SYNTAX           SEQUENCE OF CfprSwEthMonFsmTaskEntry
    MAX-ACCESS       not-accessible
    STATUS           current
    DESCRIPTION
        "Cisco Firepower sw:EthMonFsmTask managed object table"
    ::= { cfprSwObjects 28 }

cfprSwEthMonFsmTaskEntry OBJECT-TYPE
    SYNTAX           CfprSwEthMonFsmTaskEntry
    MAX-ACCESS       not-accessible
    STATUS           current
    DESCRIPTION
        "Entry for the cfprSwEthMonFsmTaskTable table."
    INDEX { cfprSwEthMonFsmTaskInstanceId }
    ::= { cfprSwEthMonFsmTaskTable 1 }

CfprSwEthMonFsmTaskEntry ::= SEQUENCE {
    cfprSwEthMonFsmTaskInstanceId                                    CfprManagedObjectId,
    cfprSwEthMonFsmTaskDn                                            CfprManagedObjectDn,
    cfprSwEthMonFsmTaskRn                                            SnmpAdminString,
    cfprSwEthMonFsmTaskCompletion                                    CfprFsmCompletion,
    cfprSwEthMonFsmTaskFlags                                         CfprFsmFlags,
    cfprSwEthMonFsmTaskItem                                          CfprSwEthMonFsmTaskItem,
    cfprSwEthMonFsmTaskSeqId                                         Gauge32
}

cfprSwEthMonFsmTaskInstanceId OBJECT-TYPE
    SYNTAX       CfprManagedObjectId
    MAX-ACCESS   not-accessible
    STATUS       current
    DESCRIPTION
        "Instance identifier of the managed object."
    ::= { cfprSwEthMonFsmTaskEntry 1 }

cfprSwEthMonFsmTaskDn OBJECT-TYPE
    SYNTAX       CfprManagedObjectDn
    MAX-ACCESS   read-only
    STATUS       current
    DESCRIPTION
        "Cisco Firepower sw:EthMonFsmTask:dn managed object property"
    ::= { cfprSwEthMonFsmTaskEntry 2 }

cfprSwEthMonFsmTaskRn OBJECT-TYPE
    SYNTAX       SnmpAdminString
    MAX-ACCESS   read-only
    STATUS       current
    DESCRIPTION
        "Cisco Firepower sw:EthMonFsmTask:rn managed object property"
    ::= { cfprSwEthMonFsmTaskEntry 3 }

cfprSwEthMonFsmTaskCompletion OBJECT-TYPE
    SYNTAX       CfprFsmCompletion
    MAX-ACCESS   read-only
    STATUS       current
    DESCRIPTION
        "Cisco Firepower sw:EthMonFsmTask:completion managed
        object property"
    ::= { cfprSwEthMonFsmTaskEntry 4 }

cfprSwEthMonFsmTaskFlags OBJECT-TYPE
    SYNTAX       CfprFsmFlags
    MAX-ACCESS   read-only
    STATUS       current
    DESCRIPTION
        "Cisco Firepower sw:EthMonFsmTask:flags managed object property"
    ::= { cfprSwEthMonFsmTaskEntry 5 }

cfprSwEthMonFsmTaskItem OBJECT-TYPE
    SYNTAX       CfprSwEthMonFsmTaskItem
    MAX-ACCESS   read-only
    STATUS       current
    DESCRIPTION
        "Cisco Firepower sw:EthMonFsmTask:item managed object property"
    ::= { cfprSwEthMonFsmTaskEntry 6 }

cfprSwEthMonFsmTaskSeqId OBJECT-TYPE
    SYNTAX       Gauge32
    MAX-ACCESS   read-only
    STATUS       current
    DESCRIPTION
        "Cisco Firepower sw:EthMonFsmTask:seqId managed object property"
    ::= { cfprSwEthMonFsmTaskEntry 7 }

cfprSwEthMonSrcEpTable OBJECT-TYPE
    SYNTAX           SEQUENCE OF CfprSwEthMonSrcEpEntry
    MAX-ACCESS       not-accessible
    STATUS           current
    DESCRIPTION
        "Cisco Firepower sw:EthMonSrcEp managed object table"
    ::= { cfprSwObjects 29 }

cfprSwEthMonSrcEpEntry OBJECT-TYPE
    SYNTAX           CfprSwEthMonSrcEpEntry
    MAX-ACCESS       not-accessible
    STATUS           current
    DESCRIPTION
        "Entry for the cfprSwEthMonSrcEpTable table."
    INDEX { cfprSwEthMonSrcEpInstanceId }
    ::= { cfprSwEthMonSrcEpTable 1 }

CfprSwEthMonSrcEpEntry ::= SEQUENCE {
    cfprSwEthMonSrcEpInstanceId                                      CfprManagedObjectId,
    cfprSwEthMonSrcEpDn                                              CfprManagedObjectDn,
    cfprSwEthMonSrcEpRn                                              SnmpAdminString,
    cfprSwEthMonSrcEpAdminState                                      CfprFabricAdminState,
    cfprSwEthMonSrcEpAggrPortId                                      Gauge32,
    cfprSwEthMonSrcEpChassisId                                       Gauge32,
    cfprSwEthMonSrcEpEpDn                                            SnmpAdminString,
    cfprSwEthMonSrcEpIfRole                                          CfprNetworkPortRole,
    cfprSwEthMonSrcEpIfType                                          CfprSwPIoEpIfType,
    cfprSwEthMonSrcEpLc                                              CfprSwPIoEpLc,
    cfprSwEthMonSrcEpLocale                                          CfprSwMonSrcEpLocale,
    cfprSwEthMonSrcEpMonTrafDir                                      CfprFabricTrafficDirection,
    cfprSwEthMonSrcEpName                                            SnmpAdminString,
    cfprSwEthMonSrcEpPeerAggrPortId                                  Gauge32,
    cfprSwEthMonSrcEpPeerChassisId                                   Gauge32,
    cfprSwEthMonSrcEpPeerDn                                          SnmpAdminString,
    cfprSwEthMonSrcEpPeerPortId                                      Gauge32,
    cfprSwEthMonSrcEpPeerSlotId                                      Gauge32,
    cfprSwEthMonSrcEpPortId                                          Gauge32,
    cfprSwEthMonSrcEpSlotId                                          Gauge32,
    cfprSwEthMonSrcEpSwitchId                                        CfprNetworkSwitchId,
    cfprSwEthMonSrcEpTransport                                       CfprSwEthMonSrcEpTransport,
    cfprSwEthMonSrcEpType                                            CfprNetworkConnectionType
}

cfprSwEthMonSrcEpInstanceId OBJECT-TYPE
    SYNTAX       CfprManagedObjectId
    MAX-ACCESS   not-accessible
    STATUS       current
    DESCRIPTION
        "Instance identifier of the managed object."
    ::= { cfprSwEthMonSrcEpEntry 1 }

cfprSwEthMonSrcEpDn OBJECT-TYPE
    SYNTAX       CfprManagedObjectDn
    MAX-ACCESS   read-only
    STATUS       current
    DESCRIPTION
        "Cisco Firepower sw:EthMonSrcEp:dn managed object property"
    ::= { cfprSwEthMonSrcEpEntry 2 }

cfprSwEthMonSrcEpRn OBJECT-TYPE
    SYNTAX       SnmpAdminString
    MAX-ACCESS   read-only
    STATUS       current
    DESCRIPTION
        "Cisco Firepower sw:EthMonSrcEp:rn managed object property"
    ::= { cfprSwEthMonSrcEpEntry 3 }

cfprSwEthMonSrcEpAdminState OBJECT-TYPE
    SYNTAX       CfprFabricAdminState
    MAX-ACCESS   read-only
    STATUS       current
    DESCRIPTION
        "Cisco Firepower sw:EthMonSrcEp:adminState managed
        object property"
    ::= { cfprSwEthMonSrcEpEntry 4 }

cfprSwEthMonSrcEpAggrPortId OBJECT-TYPE
    SYNTAX       Gauge32
    MAX-ACCESS   read-only
    STATUS       current
    DESCRIPTION
        "Cisco Firepower sw:EthMonSrcEp:aggrPortId managed
        object property"
    ::= { cfprSwEthMonSrcEpEntry 5 }

cfprSwEthMonSrcEpChassisId OBJECT-TYPE
    SYNTAX       Gauge32
    MAX-ACCESS   read-only
    STATUS       current
    DESCRIPTION
        "Cisco Firepower sw:EthMonSrcEp:chassisId managed object property"
    ::= { cfprSwEthMonSrcEpEntry 6 }

cfprSwEthMonSrcEpEpDn OBJECT-TYPE
    SYNTAX       SnmpAdminString
    MAX-ACCESS   read-only
    STATUS       current
    DESCRIPTION
        "Cisco Firepower sw:EthMonSrcEp:epDn managed object property"
    ::= { cfprSwEthMonSrcEpEntry 7 }

cfprSwEthMonSrcEpIfRole OBJECT-TYPE
    SYNTAX       CfprNetworkPortRole
    MAX-ACCESS   read-only
    STATUS       current
    DESCRIPTION
        "Cisco Firepower sw:EthMonSrcEp:ifRole managed object property"
    ::= { cfprSwEthMonSrcEpEntry 8 }

cfprSwEthMonSrcEpIfType OBJECT-TYPE
    SYNTAX       CfprSwPIoEpIfType
    MAX-ACCESS   read-only
    STATUS       current
    DESCRIPTION
        "Cisco Firepower sw:EthMonSrcEp:ifType managed object property"
    ::= { cfprSwEthMonSrcEpEntry 9 }

cfprSwEthMonSrcEpLc OBJECT-TYPE
    SYNTAX       CfprSwPIoEpLc
    MAX-ACCESS   read-only
    STATUS       current
    DESCRIPTION
        "Cisco Firepower sw:EthMonSrcEp:lc managed object property"
    ::= { cfprSwEthMonSrcEpEntry 10 }

cfprSwEthMonSrcEpLocale OBJECT-TYPE
    SYNTAX       CfprSwMonSrcEpLocale
    MAX-ACCESS   read-only
    STATUS       current
    DESCRIPTION
        "Cisco Firepower sw:EthMonSrcEp:locale managed object property"
    ::= { cfprSwEthMonSrcEpEntry 11 }

cfprSwEthMonSrcEpMonTrafDir OBJECT-TYPE
    SYNTAX       CfprFabricTrafficDirection
    MAX-ACCESS   read-only
    STATUS       current
    DESCRIPTION
        "Cisco Firepower sw:EthMonSrcEp:monTrafDir managed
        object property"
    ::= { cfprSwEthMonSrcEpEntry 12 }

cfprSwEthMonSrcEpName OBJECT-TYPE
    SYNTAX       SnmpAdminString
    MAX-ACCESS   read-only
    STATUS       current
    DESCRIPTION
        "Cisco Firepower sw:EthMonSrcEp:name managed object property"
    ::= { cfprSwEthMonSrcEpEntry 13 }

cfprSwEthMonSrcEpPeerAggrPortId OBJECT-TYPE
    SYNTAX       Gauge32
    MAX-ACCESS   read-only
    STATUS       current
    DESCRIPTION
        "Cisco Firepower sw:EthMonSrcEp:peerAggrPortId
        managed object property"
    ::= { cfprSwEthMonSrcEpEntry 14 }

cfprSwEthMonSrcEpPeerChassisId OBJECT-TYPE
    SYNTAX       Gauge32
    MAX-ACCESS   read-only
    STATUS       current
    DESCRIPTION
        "Cisco Firepower sw:EthMonSrcEp:peerChassisId managed
        object property"
    ::= { cfprSwEthMonSrcEpEntry 15 }

cfprSwEthMonSrcEpPeerDn OBJECT-TYPE
    SYNTAX       SnmpAdminString
    MAX-ACCESS   read-only
    STATUS       current
    DESCRIPTION
        "Cisco Firepower sw:EthMonSrcEp:peerDn managed object property"
    ::= { cfprSwEthMonSrcEpEntry 16 }

cfprSwEthMonSrcEpPeerPortId OBJECT-TYPE
    SYNTAX       Gauge32
    MAX-ACCESS   read-only
    STATUS       current
    DESCRIPTION
        "Cisco Firepower sw:EthMonSrcEp:peerPortId managed
        object property"
    ::= { cfprSwEthMonSrcEpEntry 17 }

cfprSwEthMonSrcEpPeerSlotId OBJECT-TYPE
    SYNTAX       Gauge32
    MAX-ACCESS   read-only
    STATUS       current
    DESCRIPTION
        "Cisco Firepower sw:EthMonSrcEp:peerSlotId managed
        object property"
    ::= { cfprSwEthMonSrcEpEntry 18 }

cfprSwEthMonSrcEpPortId OBJECT-TYPE
    SYNTAX       Gauge32
    MAX-ACCESS   read-only
    STATUS       current
    DESCRIPTION
        "Cisco Firepower sw:EthMonSrcEp:portId managed object property"
    ::= { cfprSwEthMonSrcEpEntry 19 }

cfprSwEthMonSrcEpSlotId OBJECT-TYPE
    SYNTAX       Gauge32
    MAX-ACCESS   read-only
    STATUS       current
    DESCRIPTION
        "Cisco Firepower sw:EthMonSrcEp:slotId managed object property"
    ::= { cfprSwEthMonSrcEpEntry 20 }

cfprSwEthMonSrcEpSwitchId OBJECT-TYPE
    SYNTAX       CfprNetworkSwitchId
    MAX-ACCESS   read-only
    STATUS       current
    DESCRIPTION
        "Cisco Firepower sw:EthMonSrcEp:switchId managed object property"
    ::= { cfprSwEthMonSrcEpEntry 21 }

cfprSwEthMonSrcEpTransport OBJECT-TYPE
    SYNTAX       CfprSwEthMonSrcEpTransport
    MAX-ACCESS   read-only
    STATUS       current
    DESCRIPTION
        "Cisco Firepower sw:EthMonSrcEp:transport managed object property"
    ::= { cfprSwEthMonSrcEpEntry 22 }

cfprSwEthMonSrcEpType OBJECT-TYPE
    SYNTAX       CfprNetworkConnectionType
    MAX-ACCESS   read-only
    STATUS       current
    DESCRIPTION
        "Cisco Firepower sw:EthMonSrcEp:type managed object property"
    ::= { cfprSwEthMonSrcEpEntry 23 }

cfprSwEthTargetEpTable OBJECT-TYPE
    SYNTAX           SEQUENCE OF CfprSwEthTargetEpEntry
    MAX-ACCESS       not-accessible
    STATUS           current
    DESCRIPTION
        "Cisco Firepower sw:EthTargetEp managed object table"
    ::= { cfprSwObjects 30 }

cfprSwEthTargetEpEntry OBJECT-TYPE
    SYNTAX           CfprSwEthTargetEpEntry
    MAX-ACCESS       not-accessible
    STATUS           current
    DESCRIPTION
        "Entry for the cfprSwEthTargetEpTable table."
    INDEX { cfprSwEthTargetEpInstanceId }
    ::= { cfprSwEthTargetEpTable 1 }

CfprSwEthTargetEpEntry ::= SEQUENCE {
    cfprSwEthTargetEpInstanceId                                      CfprManagedObjectId,
    cfprSwEthTargetEpDn                                              CfprManagedObjectDn,
    cfprSwEthTargetEpRn                                              SnmpAdminString,
    cfprSwEthTargetEpAdminState                                      CfprSwEthTargetEpAdminState,
    cfprSwEthTargetEpAggrPortId                                      Gauge32,
    cfprSwEthTargetEpChassisId                                       Gauge32,
    cfprSwEthTargetEpEpDn                                            SnmpAdminString,
    cfprSwEthTargetEpFltAggr                                         Unsigned64,
    cfprSwEthTargetEpIfRole                                          CfprNetworkPortRole,
    cfprSwEthTargetEpIfType                                          CfprFabricPIoEpIfType,
    cfprSwEthTargetEpLicGP                                           Unsigned64,
    cfprSwEthTargetEpLicState                                        CfprLicenseState,
    cfprSwEthTargetEpLocale                                          CfprFabricExternalEpLocale,
    cfprSwEthTargetEpMacAddress                                      MacAddress,
    cfprSwEthTargetEpName                                            SnmpAdminString,
    cfprSwEthTargetEpOperState                                       CfprFabricPIoEpOperState,
    cfprSwEthTargetEpOperStateReason                                 SnmpAdminString,
    cfprSwEthTargetEpPeerAggrPortId                                  Gauge32,
    cfprSwEthTargetEpPeerChassisId                                   Gauge32,
    cfprSwEthTargetEpPeerDn                                          SnmpAdminString,
    cfprSwEthTargetEpPeerPortId                                      Gauge32,
    cfprSwEthTargetEpPeerSlotId                                      Gauge32,
    cfprSwEthTargetEpPortId                                          CfprFabricPIoEpPortId,
    cfprSwEthTargetEpSlotId                                          CfprFabricPIoEpSlotId,
    cfprSwEthTargetEpSwitchId                                        CfprNetworkSwitchId,
    cfprSwEthTargetEpTransport                                       CfprSwEthTargetEpTransport,
    cfprSwEthTargetEpType                                            CfprSwTargetEpType,
    cfprSwEthTargetEpWarnings                                        CfprFabricWarnings
}

cfprSwEthTargetEpInstanceId OBJECT-TYPE
    SYNTAX       CfprManagedObjectId
    MAX-ACCESS   not-accessible
    STATUS       current
    DESCRIPTION
        "Instance identifier of the managed object."
    ::= { cfprSwEthTargetEpEntry 1 }

cfprSwEthTargetEpDn OBJECT-TYPE
    SYNTAX       CfprManagedObjectDn
    MAX-ACCESS   read-only
    STATUS       current
    DESCRIPTION
        "Cisco Firepower sw:EthTargetEp:dn managed object property"
    ::= { cfprSwEthTargetEpEntry 2 }

cfprSwEthTargetEpRn OBJECT-TYPE
    SYNTAX       SnmpAdminString
    MAX-ACCESS   read-only
    STATUS       current
    DESCRIPTION
        "Cisco Firepower sw:EthTargetEp:rn managed object property"
    ::= { cfprSwEthTargetEpEntry 3 }

cfprSwEthTargetEpAdminState OBJECT-TYPE
    SYNTAX       CfprSwEthTargetEpAdminState
    MAX-ACCESS   read-only
    STATUS       current
    DESCRIPTION
        "Cisco Firepower sw:EthTargetEp:adminState managed
        object property"
    ::= { cfprSwEthTargetEpEntry 4 }

cfprSwEthTargetEpAggrPortId OBJECT-TYPE
    SYNTAX       Gauge32
    MAX-ACCESS   read-only
    STATUS       current
    DESCRIPTION
        "Cisco Firepower sw:EthTargetEp:aggrPortId managed
        object property"
    ::= { cfprSwEthTargetEpEntry 5 }

cfprSwEthTargetEpChassisId OBJECT-TYPE
    SYNTAX       Gauge32
    MAX-ACCESS   read-only
    STATUS       current
    DESCRIPTION
        "Cisco Firepower sw:EthTargetEp:chassisId managed object property"
    ::= { cfprSwEthTargetEpEntry 6 }

cfprSwEthTargetEpEpDn OBJECT-TYPE
    SYNTAX       SnmpAdminString
    MAX-ACCESS   read-only
    STATUS       current
    DESCRIPTION
        "Cisco Firepower sw:EthTargetEp:epDn managed object property"
    ::= { cfprSwEthTargetEpEntry 7 }

cfprSwEthTargetEpFltAggr OBJECT-TYPE
    SYNTAX       Unsigned64
    MAX-ACCESS   read-only
    STATUS       current
    DESCRIPTION
        "Cisco Firepower sw:EthTargetEp:fltAggr managed object property"
    ::= { cfprSwEthTargetEpEntry 8 }

cfprSwEthTargetEpIfRole OBJECT-TYPE
    SYNTAX       CfprNetworkPortRole
    MAX-ACCESS   read-only
    STATUS       current
    DESCRIPTION
        "Cisco Firepower sw:EthTargetEp:ifRole managed object property"
    ::= { cfprSwEthTargetEpEntry 9 }

cfprSwEthTargetEpIfType OBJECT-TYPE
    SYNTAX       CfprFabricPIoEpIfType
    MAX-ACCESS   read-only
    STATUS       current
    DESCRIPTION
        "Cisco Firepower sw:EthTargetEp:ifType managed object property"
    ::= { cfprSwEthTargetEpEntry 10 }

cfprSwEthTargetEpLicGP OBJECT-TYPE
    SYNTAX       Unsigned64
    MAX-ACCESS   read-only
    STATUS       current
    DESCRIPTION
        "Cisco Firepower sw:EthTargetEp:licGP managed object property"
    ::= { cfprSwEthTargetEpEntry 11 }

cfprSwEthTargetEpLicState OBJECT-TYPE
    SYNTAX       CfprLicenseState
    MAX-ACCESS   read-only
    STATUS       current
    DESCRIPTION
        "Cisco Firepower sw:EthTargetEp:licState managed object property"
    ::= { cfprSwEthTargetEpEntry 12 }

cfprSwEthTargetEpLocale OBJECT-TYPE
    SYNTAX       CfprFabricExternalEpLocale
    MAX-ACCESS   read-only
    STATUS       current
    DESCRIPTION
        "Cisco Firepower sw:EthTargetEp:locale managed object property"
    ::= { cfprSwEthTargetEpEntry 13 }

cfprSwEthTargetEpMacAddress OBJECT-TYPE
    SYNTAX       MacAddress
    MAX-ACCESS   read-only
    STATUS       current
    DESCRIPTION
        "Cisco Firepower sw:EthTargetEp:macAddress managed
        object property"
    ::= { cfprSwEthTargetEpEntry 14 }

cfprSwEthTargetEpName OBJECT-TYPE
    SYNTAX       SnmpAdminString
    MAX-ACCESS   read-only
    STATUS       current
    DESCRIPTION
        "Cisco Firepower sw:EthTargetEp:name managed object property"
    ::= { cfprSwEthTargetEpEntry 15 }

cfprSwEthTargetEpOperState OBJECT-TYPE
    SYNTAX       CfprFabricPIoEpOperState
    MAX-ACCESS   read-only
    STATUS       current
    DESCRIPTION
        "Cisco Firepower sw:EthTargetEp:operState managed object property"
    ::= { cfprSwEthTargetEpEntry 16 }

cfprSwEthTargetEpOperStateReason OBJECT-TYPE
    SYNTAX       SnmpAdminString
    MAX-ACCESS   read-only
    STATUS       current
    DESCRIPTION
        "Cisco Firepower sw:EthTargetEp:operStateReason
        managed object property"
    ::= { cfprSwEthTargetEpEntry 17 }

cfprSwEthTargetEpPeerAggrPortId OBJECT-TYPE
    SYNTAX       Gauge32
    MAX-ACCESS   read-only
    STATUS       current
    DESCRIPTION
        "Cisco Firepower sw:EthTargetEp:peerAggrPortId
        managed object property"
    ::= { cfprSwEthTargetEpEntry 18 }

cfprSwEthTargetEpPeerChassisId OBJECT-TYPE
    SYNTAX       Gauge32
    MAX-ACCESS   read-only
    STATUS       current
    DESCRIPTION
        "Cisco Firepower sw:EthTargetEp:peerChassisId managed
        object property"
    ::= { cfprSwEthTargetEpEntry 19 }

cfprSwEthTargetEpPeerDn OBJECT-TYPE
    SYNTAX       SnmpAdminString
    MAX-ACCESS   read-only
    STATUS       current
    DESCRIPTION
        "Cisco Firepower sw:EthTargetEp:peerDn managed object property"
    ::= { cfprSwEthTargetEpEntry 20 }

cfprSwEthTargetEpPeerPortId OBJECT-TYPE
    SYNTAX       Gauge32
    MAX-ACCESS   read-only
    STATUS       current
    DESCRIPTION
        "Cisco Firepower sw:EthTargetEp:peerPortId managed
        object property"
    ::= { cfprSwEthTargetEpEntry 21 }

cfprSwEthTargetEpPeerSlotId OBJECT-TYPE
    SYNTAX       Gauge32
    MAX-ACCESS   read-only
    STATUS       current
    DESCRIPTION
        "Cisco Firepower sw:EthTargetEp:peerSlotId managed
        object property"
    ::= { cfprSwEthTargetEpEntry 22 }

cfprSwEthTargetEpPortId OBJECT-TYPE
    SYNTAX       CfprFabricPIoEpPortId
    MAX-ACCESS   read-only
    STATUS       current
    DESCRIPTION
        "Cisco Firepower sw:EthTargetEp:portId managed object property"
    ::= { cfprSwEthTargetEpEntry 23 }

cfprSwEthTargetEpSlotId OBJECT-TYPE
    SYNTAX       CfprFabricPIoEpSlotId
    MAX-ACCESS   read-only
    STATUS       current
    DESCRIPTION
        "Cisco Firepower sw:EthTargetEp:slotId managed object property"
    ::= { cfprSwEthTargetEpEntry 24 }

cfprSwEthTargetEpSwitchId OBJECT-TYPE
    SYNTAX       CfprNetworkSwitchId
    MAX-ACCESS   read-only
    STATUS       current
    DESCRIPTION
        "Cisco Firepower sw:EthTargetEp:switchId managed object property"
    ::= { cfprSwEthTargetEpEntry 25 }

cfprSwEthTargetEpTransport OBJECT-TYPE
    SYNTAX       CfprSwEthTargetEpTransport
    MAX-ACCESS   read-only
    STATUS       current
    DESCRIPTION
        "Cisco Firepower sw:EthTargetEp:transport managed object property"
    ::= { cfprSwEthTargetEpEntry 26 }

cfprSwEthTargetEpType OBJECT-TYPE
    SYNTAX       CfprSwTargetEpType
    MAX-ACCESS   read-only
    STATUS       current
    DESCRIPTION
        "Cisco Firepower sw:EthTargetEp:type managed object property"
    ::= { cfprSwEthTargetEpEntry 27 }

cfprSwEthTargetEpWarnings OBJECT-TYPE
    SYNTAX       CfprFabricWarnings
    MAX-ACCESS   read-only
    STATUS       current
    DESCRIPTION
        "Cisco Firepower sw:EthTargetEp:warnings managed object property"
    ::= { cfprSwEthTargetEpEntry 28 }

cfprSwExtUtilityTable OBJECT-TYPE
    SYNTAX           SEQUENCE OF CfprSwExtUtilityEntry
    MAX-ACCESS       not-accessible
    STATUS           current
    DESCRIPTION
        "Cisco Firepower sw:ExtUtility managed object table"
    ::= { cfprSwObjects 31 }

cfprSwExtUtilityEntry OBJECT-TYPE
    SYNTAX           CfprSwExtUtilityEntry
    MAX-ACCESS       not-accessible
    STATUS           current
    DESCRIPTION
        "Entry for the cfprSwExtUtilityTable table."
    INDEX { cfprSwExtUtilityInstanceId }
    ::= { cfprSwExtUtilityTable 1 }

CfprSwExtUtilityEntry ::= SEQUENCE {
    cfprSwExtUtilityInstanceId                                       CfprManagedObjectId,
    cfprSwExtUtilityDn                                               CfprManagedObjectDn,
    cfprSwExtUtilityRn                                               SnmpAdminString,
    cfprSwExtUtilityConfMode                                         CfprSwConfMode,
    cfprSwExtUtilityFsmDescr                                         SnmpAdminString,
    cfprSwExtUtilityFsmPrev                                          SnmpAdminString,
    cfprSwExtUtilityFsmProgr                                         Gauge32,
    cfprSwExtUtilityFsmRmtInvErrCode                                 Gauge32,
    cfprSwExtUtilityFsmRmtInvErrDescr                                SnmpAdminString,
    cfprSwExtUtilityFsmRmtInvRslt                                    CfprConditionRemoteInvRslt,
    cfprSwExtUtilityFsmStageDescr                                    SnmpAdminString,
    cfprSwExtUtilityFsmStamp                                         DateAndTime,
    cfprSwExtUtilityFsmStatus                                        SnmpAdminString,
    cfprSwExtUtilityFsmTry                                           Gauge32,
    cfprSwExtUtilitySwitchId                                         CfprNetworkSwitchId
}

cfprSwExtUtilityInstanceId OBJECT-TYPE
    SYNTAX       CfprManagedObjectId
    MAX-ACCESS   not-accessible
    STATUS       current
    DESCRIPTION
        "Instance identifier of the managed object."
    ::= { cfprSwExtUtilityEntry 1 }

cfprSwExtUtilityDn OBJECT-TYPE
    SYNTAX       CfprManagedObjectDn
    MAX-ACCESS   read-only
    STATUS       current
    DESCRIPTION
        "Cisco Firepower sw:ExtUtility:dn managed object property"
    ::= { cfprSwExtUtilityEntry 2 }

cfprSwExtUtilityRn OBJECT-TYPE
    SYNTAX       SnmpAdminString
    MAX-ACCESS   read-only
    STATUS       current
    DESCRIPTION
        "Cisco Firepower sw:ExtUtility:rn managed object property"
    ::= { cfprSwExtUtilityEntry 3 }

cfprSwExtUtilityConfMode OBJECT-TYPE
    SYNTAX       CfprSwConfMode
    MAX-ACCESS   read-only
    STATUS       current
    DESCRIPTION
        "Cisco Firepower sw:ExtUtility:confMode managed object property"
    ::= { cfprSwExtUtilityEntry 4 }

cfprSwExtUtilityFsmDescr OBJECT-TYPE
    SYNTAX       SnmpAdminString
    MAX-ACCESS   read-only
    STATUS       current
    DESCRIPTION
        "Cisco Firepower sw:ExtUtility:fsmDescr managed object property"
    ::= { cfprSwExtUtilityEntry 5 }

cfprSwExtUtilityFsmPrev OBJECT-TYPE
    SYNTAX       SnmpAdminString
    MAX-ACCESS   read-only
    STATUS       current
    DESCRIPTION
        "Cisco Firepower sw:ExtUtility:fsmPrev managed object property"
    ::= { cfprSwExtUtilityEntry 6 }

cfprSwExtUtilityFsmProgr OBJECT-TYPE
    SYNTAX       Gauge32
    MAX-ACCESS   read-only
    STATUS       current
    DESCRIPTION
        "Cisco Firepower sw:ExtUtility:fsmProgr managed object property"
    ::= { cfprSwExtUtilityEntry 7 }

cfprSwExtUtilityFsmRmtInvErrCode OBJECT-TYPE
    SYNTAX       Gauge32
    MAX-ACCESS   read-only
    STATUS       current
    DESCRIPTION
        "Cisco Firepower sw:ExtUtility:fsmRmtInvErrCode
        managed object property"
    ::= { cfprSwExtUtilityEntry 8 }

cfprSwExtUtilityFsmRmtInvErrDescr OBJECT-TYPE
    SYNTAX       SnmpAdminString
    MAX-ACCESS   read-only
    STATUS       current
    DESCRIPTION
        "Cisco Firepower sw:ExtUtility:fsmRmtInvErrDescr
        managed object property"
    ::= { cfprSwExtUtilityEntry 9 }

cfprSwExtUtilityFsmRmtInvRslt OBJECT-TYPE
    SYNTAX       CfprConditionRemoteInvRslt
    MAX-ACCESS   read-only
    STATUS       current
    DESCRIPTION
        "Cisco Firepower sw:ExtUtility:fsmRmtInvRslt managed
        object property"
    ::= { cfprSwExtUtilityEntry 10 }

cfprSwExtUtilityFsmStageDescr OBJECT-TYPE
    SYNTAX       SnmpAdminString
    MAX-ACCESS   read-only
    STATUS       current
    DESCRIPTION
        "Cisco Firepower sw:ExtUtility:fsmStageDescr managed
        object property"
    ::= { cfprSwExtUtilityEntry 11 }

cfprSwExtUtilityFsmStamp OBJECT-TYPE
    SYNTAX       DateAndTime
    MAX-ACCESS   read-only
    STATUS       current
    DESCRIPTION
        "Cisco Firepower sw:ExtUtility:fsmStamp managed object property"
    ::= { cfprSwExtUtilityEntry 12 }

cfprSwExtUtilityFsmStatus OBJECT-TYPE
    SYNTAX       SnmpAdminString
    MAX-ACCESS   read-only
    STATUS       current
    DESCRIPTION
        "Cisco Firepower sw:ExtUtility:fsmStatus managed object property"
    ::= { cfprSwExtUtilityEntry 13 }

cfprSwExtUtilityFsmTry OBJECT-TYPE
    SYNTAX       Gauge32
    MAX-ACCESS   read-only
    STATUS       current
    DESCRIPTION
        "Cisco Firepower sw:ExtUtility:fsmTry managed object property"
    ::= { cfprSwExtUtilityEntry 14 }

cfprSwExtUtilitySwitchId OBJECT-TYPE
    SYNTAX       CfprNetworkSwitchId
    MAX-ACCESS   read-only
    STATUS       current
    DESCRIPTION
        "Cisco Firepower sw:ExtUtility:switchId managed object property"
    ::= { cfprSwExtUtilityEntry 15 }

cfprSwExtUtilityFsmTable OBJECT-TYPE
    SYNTAX           SEQUENCE OF CfprSwExtUtilityFsmEntry
    MAX-ACCESS       not-accessible
    STATUS           current
    DESCRIPTION
        "Cisco Firepower sw:ExtUtilityFsm managed object table"
    ::= { cfprSwObjects 32 }

cfprSwExtUtilityFsmEntry OBJECT-TYPE
    SYNTAX           CfprSwExtUtilityFsmEntry
    MAX-ACCESS       not-accessible
    STATUS           current
    DESCRIPTION
        "Entry for the cfprSwExtUtilityFsmTable table."
    INDEX { cfprSwExtUtilityFsmInstanceId }
    ::= { cfprSwExtUtilityFsmTable 1 }

CfprSwExtUtilityFsmEntry ::= SEQUENCE {
    cfprSwExtUtilityFsmInstanceId                                    CfprManagedObjectId,
    cfprSwExtUtilityFsmDn                                            CfprManagedObjectDn,
    cfprSwExtUtilityFsmRn                                            SnmpAdminString,
    cfprSwExtUtilityFsmCompletionTime                                DateAndTime,
    cfprSwExtUtilityFsmCurrentFsm                                    CfprSwExtUtilityFsmCurrentFsm,
    cfprSwExtUtilityFsmDescrData                                     SnmpAdminString,
    cfprSwExtUtilityFsmFsmStatus                                     CfprFsmFsmStageStatus,
    cfprSwExtUtilityFsmProgress                                      Gauge32,
    cfprSwExtUtilityFsmRmtErrCode                                    Gauge32,
    cfprSwExtUtilityFsmRmtErrDescr                                   SnmpAdminString,
    cfprSwExtUtilityFsmRmtRslt                                       CfprConditionRemoteInvRslt
}

cfprSwExtUtilityFsmInstanceId OBJECT-TYPE
    SYNTAX       CfprManagedObjectId
    MAX-ACCESS   not-accessible
    STATUS       current
    DESCRIPTION
        "Instance identifier of the managed object."
    ::= { cfprSwExtUtilityFsmEntry 1 }

cfprSwExtUtilityFsmDn OBJECT-TYPE
    SYNTAX       CfprManagedObjectDn
    MAX-ACCESS   read-only
    STATUS       current
    DESCRIPTION
        "Cisco Firepower sw:ExtUtilityFsm:dn managed object property"
    ::= { cfprSwExtUtilityFsmEntry 2 }

cfprSwExtUtilityFsmRn OBJECT-TYPE
    SYNTAX       SnmpAdminString
    MAX-ACCESS   read-only
    STATUS       current
    DESCRIPTION
        "Cisco Firepower sw:ExtUtilityFsm:rn managed object property"
    ::= { cfprSwExtUtilityFsmEntry 3 }

cfprSwExtUtilityFsmCompletionTime OBJECT-TYPE
    SYNTAX       DateAndTime
    MAX-ACCESS   read-only
    STATUS       current
    DESCRIPTION
        "Cisco Firepower sw:ExtUtilityFsm:completionTime
        managed object property"
    ::= { cfprSwExtUtilityFsmEntry 4 }

cfprSwExtUtilityFsmCurrentFsm OBJECT-TYPE
    SYNTAX       CfprSwExtUtilityFsmCurrentFsm
    MAX-ACCESS   read-only
    STATUS       current
    DESCRIPTION
        "Cisco Firepower sw:ExtUtilityFsm:currentFsm managed
        object property"
    ::= { cfprSwExtUtilityFsmEntry 5 }

cfprSwExtUtilityFsmDescrData OBJECT-TYPE
    SYNTAX       SnmpAdminString
    MAX-ACCESS   read-only
    STATUS       current
    DESCRIPTION
        "Cisco Firepower sw:ExtUtilityFsm:descr managed object property"
    ::= { cfprSwExtUtilityFsmEntry 6 }

cfprSwExtUtilityFsmFsmStatus OBJECT-TYPE
    SYNTAX       CfprFsmFsmStageStatus
    MAX-ACCESS   read-only
    STATUS       current
    DESCRIPTION
        "Cisco Firepower sw:ExtUtilityFsm:fsmStatus managed
        object property"
    ::= { cfprSwExtUtilityFsmEntry 7 }

cfprSwExtUtilityFsmProgress OBJECT-TYPE
    SYNTAX       Gauge32
    MAX-ACCESS   read-only
    STATUS       current
    DESCRIPTION
        "Cisco Firepower sw:ExtUtilityFsm:progress managed
        object property"
    ::= { cfprSwExtUtilityFsmEntry 8 }

cfprSwExtUtilityFsmRmtErrCode OBJECT-TYPE
    SYNTAX       Gauge32
    MAX-ACCESS   read-only
    STATUS       current
    DESCRIPTION
        "Cisco Firepower sw:ExtUtilityFsm:rmtErrCode managed
        object property"
    ::= { cfprSwExtUtilityFsmEntry 9 }

cfprSwExtUtilityFsmRmtErrDescr OBJECT-TYPE
    SYNTAX       SnmpAdminString
    MAX-ACCESS   read-only
    STATUS       current
    DESCRIPTION
        "Cisco Firepower sw:ExtUtilityFsm:rmtErrDescr managed
        object property"
    ::= { cfprSwExtUtilityFsmEntry 10 }

cfprSwExtUtilityFsmRmtRslt OBJECT-TYPE
    SYNTAX       CfprConditionRemoteInvRslt
    MAX-ACCESS   read-only
    STATUS       current
    DESCRIPTION
        "Cisco Firepower sw:ExtUtilityFsm:rmtRslt managed object property"
    ::= { cfprSwExtUtilityFsmEntry 11 }

cfprSwExtUtilityFsmStageTable OBJECT-TYPE
    SYNTAX           SEQUENCE OF CfprSwExtUtilityFsmStageEntry
    MAX-ACCESS       not-accessible
    STATUS           current
    DESCRIPTION
        "Cisco Firepower sw:ExtUtilityFsmStage managed object table"
    ::= { cfprSwObjects 33 }

cfprSwExtUtilityFsmStageEntry OBJECT-TYPE
    SYNTAX           CfprSwExtUtilityFsmStageEntry
    MAX-ACCESS       not-accessible
    STATUS           current
    DESCRIPTION
        "Entry for the cfprSwExtUtilityFsmStageTable table."
    INDEX { cfprSwExtUtilityFsmStageInstanceId }
    ::= { cfprSwExtUtilityFsmStageTable 1 }

CfprSwExtUtilityFsmStageEntry ::= SEQUENCE {
    cfprSwExtUtilityFsmStageInstanceId                               CfprManagedObjectId,
    cfprSwExtUtilityFsmStageDn                                       CfprManagedObjectDn,
    cfprSwExtUtilityFsmStageRn                                       SnmpAdminString,
    cfprSwExtUtilityFsmStageDescrData                                SnmpAdminString,
    cfprSwExtUtilityFsmStageLastUpdateTime                           DateAndTime,
    cfprSwExtUtilityFsmStageName                                     CfprSwExtUtilityFsmStageName,
    cfprSwExtUtilityFsmStageOrder                                    Gauge32,
    cfprSwExtUtilityFsmStageRetry                                    Gauge32,
    cfprSwExtUtilityFsmStageStageStatus                              CfprFsmFsmStageStatus
}

cfprSwExtUtilityFsmStageInstanceId OBJECT-TYPE
    SYNTAX       CfprManagedObjectId
    MAX-ACCESS   not-accessible
    STATUS       current
    DESCRIPTION
        "Instance identifier of the managed object."
    ::= { cfprSwExtUtilityFsmStageEntry 1 }

cfprSwExtUtilityFsmStageDn OBJECT-TYPE
    SYNTAX       CfprManagedObjectDn
    MAX-ACCESS   read-only
    STATUS       current
    DESCRIPTION
        "Cisco Firepower sw:ExtUtilityFsmStage:dn managed object property"
    ::= { cfprSwExtUtilityFsmStageEntry 2 }

cfprSwExtUtilityFsmStageRn OBJECT-TYPE
    SYNTAX       SnmpAdminString
    MAX-ACCESS   read-only
    STATUS       current
    DESCRIPTION
        "Cisco Firepower sw:ExtUtilityFsmStage:rn managed object property"
    ::= { cfprSwExtUtilityFsmStageEntry 3 }

cfprSwExtUtilityFsmStageDescrData OBJECT-TYPE
    SYNTAX       SnmpAdminString
    MAX-ACCESS   read-only
    STATUS       current
    DESCRIPTION
        "Cisco Firepower sw:ExtUtilityFsmStage:descr managed
        object property"
    ::= { cfprSwExtUtilityFsmStageEntry 4 }

cfprSwExtUtilityFsmStageLastUpdateTime OBJECT-TYPE
    SYNTAX       DateAndTime
    MAX-ACCESS   read-only
    STATUS       current
    DESCRIPTION
        "Cisco Firepower sw:ExtUtilityFsmStage:lastUpdateTime
        managed object property"
    ::= { cfprSwExtUtilityFsmStageEntry 5 }

cfprSwExtUtilityFsmStageName OBJECT-TYPE
    SYNTAX       CfprSwExtUtilityFsmStageName
    MAX-ACCESS   read-only
    STATUS       current
    DESCRIPTION
        "Cisco Firepower sw:ExtUtilityFsmStage:name managed
        object property"
    ::= { cfprSwExtUtilityFsmStageEntry 6 }

cfprSwExtUtilityFsmStageOrder OBJECT-TYPE
    SYNTAX       Gauge32
    MAX-ACCESS   read-only
    STATUS       current
    DESCRIPTION
        "Cisco Firepower sw:ExtUtilityFsmStage:order managed
        object property"
    ::= { cfprSwExtUtilityFsmStageEntry 7 }

cfprSwExtUtilityFsmStageRetry OBJECT-TYPE
    SYNTAX       Gauge32
    MAX-ACCESS   read-only
    STATUS       current
    DESCRIPTION
        "Cisco Firepower sw:ExtUtilityFsmStage:retry managed
        object property"
    ::= { cfprSwExtUtilityFsmStageEntry 8 }

cfprSwExtUtilityFsmStageStageStatus OBJECT-TYPE
    SYNTAX       CfprFsmFsmStageStatus
    MAX-ACCESS   read-only
    STATUS       current
    DESCRIPTION
        "Cisco Firepower sw:ExtUtilityFsmStage:stageStatus
        managed object property"
    ::= { cfprSwExtUtilityFsmStageEntry 9 }

cfprSwExtUtilityFsmTaskTable OBJECT-TYPE
    SYNTAX           SEQUENCE OF CfprSwExtUtilityFsmTaskEntry
    MAX-ACCESS       not-accessible
    STATUS           current
    DESCRIPTION
        "Cisco Firepower sw:ExtUtilityFsmTask managed object table"
    ::= { cfprSwObjects 34 }

cfprSwExtUtilityFsmTaskEntry OBJECT-TYPE
    SYNTAX           CfprSwExtUtilityFsmTaskEntry
    MAX-ACCESS       not-accessible
    STATUS           current
    DESCRIPTION
        "Entry for the cfprSwExtUtilityFsmTaskTable table."
    INDEX { cfprSwExtUtilityFsmTaskInstanceId }
    ::= { cfprSwExtUtilityFsmTaskTable 1 }

CfprSwExtUtilityFsmTaskEntry ::= SEQUENCE {
    cfprSwExtUtilityFsmTaskInstanceId                                CfprManagedObjectId,
    cfprSwExtUtilityFsmTaskDn                                        CfprManagedObjectDn,
    cfprSwExtUtilityFsmTaskRn                                        SnmpAdminString,
    cfprSwExtUtilityFsmTaskCompletion                                CfprFsmCompletion,
    cfprSwExtUtilityFsmTaskFlags                                     CfprFsmFlags,
    cfprSwExtUtilityFsmTaskItem                                      CfprSwExtUtilityFsmTaskItem,
    cfprSwExtUtilityFsmTaskSeqId                                     Gauge32
}

cfprSwExtUtilityFsmTaskInstanceId OBJECT-TYPE
    SYNTAX       CfprManagedObjectId
    MAX-ACCESS   not-accessible
    STATUS       current
    DESCRIPTION
        "Instance identifier of the managed object."
    ::= { cfprSwExtUtilityFsmTaskEntry 1 }

cfprSwExtUtilityFsmTaskDn OBJECT-TYPE
    SYNTAX       CfprManagedObjectDn
    MAX-ACCESS   read-only
    STATUS       current
    DESCRIPTION
        "Cisco Firepower sw:ExtUtilityFsmTask:dn managed object property"
    ::= { cfprSwExtUtilityFsmTaskEntry 2 }

cfprSwExtUtilityFsmTaskRn OBJECT-TYPE
    SYNTAX       SnmpAdminString
    MAX-ACCESS   read-only
    STATUS       current
    DESCRIPTION
        "Cisco Firepower sw:ExtUtilityFsmTask:rn managed object property"
    ::= { cfprSwExtUtilityFsmTaskEntry 3 }

cfprSwExtUtilityFsmTaskCompletion OBJECT-TYPE
    SYNTAX       CfprFsmCompletion
    MAX-ACCESS   read-only
    STATUS       current
    DESCRIPTION
        "Cisco Firepower sw:ExtUtilityFsmTask:completion
        managed object property"
    ::= { cfprSwExtUtilityFsmTaskEntry 4 }

cfprSwExtUtilityFsmTaskFlags OBJECT-TYPE
    SYNTAX       CfprFsmFlags
    MAX-ACCESS   read-only
    STATUS       current
    DESCRIPTION
        "Cisco Firepower sw:ExtUtilityFsmTask:flags managed
        object property"
    ::= { cfprSwExtUtilityFsmTaskEntry 5 }

cfprSwExtUtilityFsmTaskItem OBJECT-TYPE
    SYNTAX       CfprSwExtUtilityFsmTaskItem
    MAX-ACCESS   read-only
    STATUS       current
    DESCRIPTION
        "Cisco Firepower sw:ExtUtilityFsmTask:item managed
        object property"
    ::= { cfprSwExtUtilityFsmTaskEntry 6 }

cfprSwExtUtilityFsmTaskSeqId OBJECT-TYPE
    SYNTAX       Gauge32
    MAX-ACCESS   read-only
    STATUS       current
    DESCRIPTION
        "Cisco Firepower sw:ExtUtilityFsmTask:seqId managed
        object property"
    ::= { cfprSwExtUtilityFsmTaskEntry 7 }

cfprSwFabricZoneNsTable OBJECT-TYPE
    SYNTAX           SEQUENCE OF CfprSwFabricZoneNsEntry
    MAX-ACCESS       not-accessible
    STATUS           current
    DESCRIPTION
        "Cisco Firepower sw:FabricZoneNs managed object table"
    ::= { cfprSwObjects 35 }

cfprSwFabricZoneNsEntry OBJECT-TYPE
    SYNTAX           CfprSwFabricZoneNsEntry
    MAX-ACCESS       not-accessible
    STATUS           current
    DESCRIPTION
        "Entry for the cfprSwFabricZoneNsTable table."
    INDEX { cfprSwFabricZoneNsInstanceId }
    ::= { cfprSwFabricZoneNsTable 1 }

CfprSwFabricZoneNsEntry ::= SEQUENCE {
    cfprSwFabricZoneNsInstanceId                                     CfprManagedObjectId,
    cfprSwFabricZoneNsDn                                             CfprManagedObjectDn,
    cfprSwFabricZoneNsRn                                             SnmpAdminString,
    cfprSwFabricZoneNsAllocStatus                                    CfprSwFabricZoneNsAllocStatus,
    cfprSwFabricZoneNsLimit                                          Gauge32,
    cfprSwFabricZoneNsSwitchId                                       CfprNetworkSwitchId,
    cfprSwFabricZoneNsZoneCount                                      Gauge32
}

cfprSwFabricZoneNsInstanceId OBJECT-TYPE
    SYNTAX       CfprManagedObjectId
    MAX-ACCESS   not-accessible
    STATUS       current
    DESCRIPTION
        "Instance identifier of the managed object."
    ::= { cfprSwFabricZoneNsEntry 1 }

cfprSwFabricZoneNsDn OBJECT-TYPE
    SYNTAX       CfprManagedObjectDn
    MAX-ACCESS   read-only
    STATUS       current
    DESCRIPTION
        "Cisco Firepower sw:FabricZoneNs:dn managed object property"
    ::= { cfprSwFabricZoneNsEntry 2 }

cfprSwFabricZoneNsRn OBJECT-TYPE
    SYNTAX       SnmpAdminString
    MAX-ACCESS   read-only
    STATUS       current
    DESCRIPTION
        "Cisco Firepower sw:FabricZoneNs:rn managed object property"
    ::= { cfprSwFabricZoneNsEntry 3 }

cfprSwFabricZoneNsAllocStatus OBJECT-TYPE
    SYNTAX       CfprSwFabricZoneNsAllocStatus
    MAX-ACCESS   read-only
    STATUS       current
    DESCRIPTION
        "Cisco Firepower sw:FabricZoneNs:allocStatus managed
        object property"
    ::= { cfprSwFabricZoneNsEntry 4 }

cfprSwFabricZoneNsLimit OBJECT-TYPE
    SYNTAX       Gauge32
    MAX-ACCESS   read-only
    STATUS       current
    DESCRIPTION
        "Cisco Firepower sw:FabricZoneNs:limit managed object property"
    ::= { cfprSwFabricZoneNsEntry 5 }

cfprSwFabricZoneNsSwitchId OBJECT-TYPE
    SYNTAX       CfprNetworkSwitchId
    MAX-ACCESS   read-only
    STATUS       current
    DESCRIPTION
        "Cisco Firepower sw:FabricZoneNs:switchId managed object property"
    ::= { cfprSwFabricZoneNsEntry 6 }

cfprSwFabricZoneNsZoneCount OBJECT-TYPE
    SYNTAX       Gauge32
    MAX-ACCESS   read-only
    STATUS       current
    DESCRIPTION
        "Cisco Firepower sw:FabricZoneNs:zoneCount managed
        object property"
    ::= { cfprSwFabricZoneNsEntry 7 }

cfprSwFabricZoneNsOverrideTable OBJECT-TYPE
    SYNTAX           SEQUENCE OF CfprSwFabricZoneNsOverrideEntry
    MAX-ACCESS       not-accessible
    STATUS           current
    DESCRIPTION
        "Cisco Firepower sw:FabricZoneNsOverride managed object table"
    ::= { cfprSwObjects 36 }

cfprSwFabricZoneNsOverrideEntry OBJECT-TYPE
    SYNTAX           CfprSwFabricZoneNsOverrideEntry
    MAX-ACCESS       not-accessible
    STATUS           current
    DESCRIPTION
        "Entry for the cfprSwFabricZoneNsOverrideTable table."
    INDEX { cfprSwFabricZoneNsOverrideInstanceId }
    ::= { cfprSwFabricZoneNsOverrideTable 1 }

CfprSwFabricZoneNsOverrideEntry ::= SEQUENCE {
    cfprSwFabricZoneNsOverrideInstanceId                             CfprManagedObjectId,
    cfprSwFabricZoneNsOverrideDn                                     CfprManagedObjectDn,
    cfprSwFabricZoneNsOverrideRn                                     SnmpAdminString,
    cfprSwFabricZoneNsOverrideLimit                                  Gauge32
}

cfprSwFabricZoneNsOverrideInstanceId OBJECT-TYPE
    SYNTAX       CfprManagedObjectId
    MAX-ACCESS   not-accessible
    STATUS       current
    DESCRIPTION
        "Instance identifier of the managed object."
    ::= { cfprSwFabricZoneNsOverrideEntry 1 }

cfprSwFabricZoneNsOverrideDn OBJECT-TYPE
    SYNTAX       CfprManagedObjectDn
    MAX-ACCESS   read-only
    STATUS       current
    DESCRIPTION
        "Cisco Firepower sw:FabricZoneNsOverride:dn managed
        object property"
    ::= { cfprSwFabricZoneNsOverrideEntry 2 }

cfprSwFabricZoneNsOverrideRn OBJECT-TYPE
    SYNTAX       SnmpAdminString
    MAX-ACCESS   read-only
    STATUS       current
    DESCRIPTION
        "Cisco Firepower sw:FabricZoneNsOverride:rn managed
        object property"
    ::= { cfprSwFabricZoneNsOverrideEntry 3 }

cfprSwFabricZoneNsOverrideLimit OBJECT-TYPE
    SYNTAX       Gauge32
    MAX-ACCESS   read-only
    STATUS       current
    DESCRIPTION
        "Cisco Firepower sw:FabricZoneNsOverride:limit
        managed object property"
    ::= { cfprSwFabricZoneNsOverrideEntry 4 }

cfprSwFcEstcEpTable OBJECT-TYPE
    SYNTAX           SEQUENCE OF CfprSwFcEstcEpEntry
    MAX-ACCESS       not-accessible
    STATUS           current
    DESCRIPTION
        "Cisco Firepower sw:FcEstcEp managed object table"
    ::= { cfprSwObjects 37 }

cfprSwFcEstcEpEntry OBJECT-TYPE
    SYNTAX           CfprSwFcEstcEpEntry
    MAX-ACCESS       not-accessible
    STATUS           current
    DESCRIPTION
        "Entry for the cfprSwFcEstcEpTable table."
    INDEX { cfprSwFcEstcEpInstanceId }
    ::= { cfprSwFcEstcEpTable 1 }

CfprSwFcEstcEpEntry ::= SEQUENCE {
    cfprSwFcEstcEpInstanceId                                         CfprManagedObjectId,
    cfprSwFcEstcEpDn                                                 CfprManagedObjectDn,
    cfprSwFcEstcEpRn                                                 SnmpAdminString,
    cfprSwFcEstcEpAdminState                                         CfprFabricAdminState,
    cfprSwFcEstcEpAggrPortId                                         Gauge32,
    cfprSwFcEstcEpChassisId                                          Gauge32,
    cfprSwFcEstcEpEpDn                                               SnmpAdminString,
    cfprSwFcEstcEpFillPattern                                        CfprFabricFillPattern,
    cfprSwFcEstcEpIfRole                                             CfprNetworkPortRole,
    cfprSwFcEstcEpIfType                                             CfprSwPIoEpIfType,
    cfprSwFcEstcEpLc                                                 CfprSwPIoEpLc,
    cfprSwFcEstcEpLocale                                             CfprSwEstcEpLocale,
    cfprSwFcEstcEpName                                               SnmpAdminString,
    cfprSwFcEstcEpPeerAggrPortId                                     Gauge32,
    cfprSwFcEstcEpPeerChassisId                                      Gauge32,
    cfprSwFcEstcEpPeerDn                                             SnmpAdminString,
    cfprSwFcEstcEpPeerPortId                                         Gauge32,
    cfprSwFcEstcEpPeerSlotId                                         Gauge32,
    cfprSwFcEstcEpPortId                                             Gauge32,
    cfprSwFcEstcEpPortVsanId                                         Gauge32,
    cfprSwFcEstcEpSlotId                                             Gauge32,
    cfprSwFcEstcEpSwitchId                                           CfprNetworkSwitchId,
    cfprSwFcEstcEpTransport                                          CfprSwFcEstcEpTransport,
    cfprSwFcEstcEpType                                               CfprNetworkConnectionType
}

cfprSwFcEstcEpInstanceId OBJECT-TYPE
    SYNTAX       CfprManagedObjectId
    MAX-ACCESS   not-accessible
    STATUS       current
    DESCRIPTION
        "Instance identifier of the managed object."
    ::= { cfprSwFcEstcEpEntry 1 }

cfprSwFcEstcEpDn OBJECT-TYPE
    SYNTAX       CfprManagedObjectDn
    MAX-ACCESS   read-only
    STATUS       current
    DESCRIPTION
        "Cisco Firepower sw:FcEstcEp:dn managed object property"
    ::= { cfprSwFcEstcEpEntry 2 }

cfprSwFcEstcEpRn OBJECT-TYPE
    SYNTAX       SnmpAdminString
    MAX-ACCESS   read-only
    STATUS       current
    DESCRIPTION
        "Cisco Firepower sw:FcEstcEp:rn managed object property"
    ::= { cfprSwFcEstcEpEntry 3 }

cfprSwFcEstcEpAdminState OBJECT-TYPE
    SYNTAX       CfprFabricAdminState
    MAX-ACCESS   read-only
    STATUS       current
    DESCRIPTION
        "Cisco Firepower sw:FcEstcEp:adminState managed object property"
    ::= { cfprSwFcEstcEpEntry 4 }

cfprSwFcEstcEpAggrPortId OBJECT-TYPE
    SYNTAX       Gauge32
    MAX-ACCESS   read-only
    STATUS       current
    DESCRIPTION
        "Cisco Firepower sw:FcEstcEp:aggrPortId managed object property"
    ::= { cfprSwFcEstcEpEntry 5 }

cfprSwFcEstcEpChassisId OBJECT-TYPE
    SYNTAX       Gauge32
    MAX-ACCESS   read-only
    STATUS       current
    DESCRIPTION
        "Cisco Firepower sw:FcEstcEp:chassisId managed object property"
    ::= { cfprSwFcEstcEpEntry 6 }

cfprSwFcEstcEpEpDn OBJECT-TYPE
    SYNTAX       SnmpAdminString
    MAX-ACCESS   read-only
    STATUS       current
    DESCRIPTION
        "Cisco Firepower sw:FcEstcEp:epDn managed object property"
    ::= { cfprSwFcEstcEpEntry 7 }

cfprSwFcEstcEpFillPattern OBJECT-TYPE
    SYNTAX       CfprFabricFillPattern
    MAX-ACCESS   read-only
    STATUS       current
    DESCRIPTION
        "Cisco Firepower sw:FcEstcEp:fillPattern managed object property"
    ::= { cfprSwFcEstcEpEntry 8 }

cfprSwFcEstcEpIfRole OBJECT-TYPE
    SYNTAX       CfprNetworkPortRole
    MAX-ACCESS   read-only
    STATUS       current
    DESCRIPTION
        "Cisco Firepower sw:FcEstcEp:ifRole managed object property"
    ::= { cfprSwFcEstcEpEntry 9 }

cfprSwFcEstcEpIfType OBJECT-TYPE
    SYNTAX       CfprSwPIoEpIfType
    MAX-ACCESS   read-only
    STATUS       current
    DESCRIPTION
        "Cisco Firepower sw:FcEstcEp:ifType managed object property"
    ::= { cfprSwFcEstcEpEntry 10 }

cfprSwFcEstcEpLc OBJECT-TYPE
    SYNTAX       CfprSwPIoEpLc
    MAX-ACCESS   read-only
    STATUS       current
    DESCRIPTION
        "Cisco Firepower sw:FcEstcEp:lc managed object property"
    ::= { cfprSwFcEstcEpEntry 11 }

cfprSwFcEstcEpLocale OBJECT-TYPE
    SYNTAX       CfprSwEstcEpLocale
    MAX-ACCESS   read-only
    STATUS       current
    DESCRIPTION
        "Cisco Firepower sw:FcEstcEp:locale managed object property"
    ::= { cfprSwFcEstcEpEntry 12 }

cfprSwFcEstcEpName OBJECT-TYPE
    SYNTAX       SnmpAdminString
    MAX-ACCESS   read-only
    STATUS       current
    DESCRIPTION
        "Cisco Firepower sw:FcEstcEp:name managed object property"
    ::= { cfprSwFcEstcEpEntry 13 }

cfprSwFcEstcEpPeerAggrPortId OBJECT-TYPE
    SYNTAX       Gauge32
    MAX-ACCESS   read-only
    STATUS       current
    DESCRIPTION
        "Cisco Firepower sw:FcEstcEp:peerAggrPortId managed
        object property"
    ::= { cfprSwFcEstcEpEntry 14 }

cfprSwFcEstcEpPeerChassisId OBJECT-TYPE
    SYNTAX       Gauge32
    MAX-ACCESS   read-only
    STATUS       current
    DESCRIPTION
        "Cisco Firepower sw:FcEstcEp:peerChassisId managed
        object property"
    ::= { cfprSwFcEstcEpEntry 15 }

cfprSwFcEstcEpPeerDn OBJECT-TYPE
    SYNTAX       SnmpAdminString
    MAX-ACCESS   read-only
    STATUS       current
    DESCRIPTION
        "Cisco Firepower sw:FcEstcEp:peerDn managed object property"
    ::= { cfprSwFcEstcEpEntry 16 }

cfprSwFcEstcEpPeerPortId OBJECT-TYPE
    SYNTAX       Gauge32
    MAX-ACCESS   read-only
    STATUS       current
    DESCRIPTION
        "Cisco Firepower sw:FcEstcEp:peerPortId managed object property"
    ::= { cfprSwFcEstcEpEntry 17 }

cfprSwFcEstcEpPeerSlotId OBJECT-TYPE
    SYNTAX       Gauge32
    MAX-ACCESS   read-only
    STATUS       current
    DESCRIPTION
        "Cisco Firepower sw:FcEstcEp:peerSlotId managed object property"
    ::= { cfprSwFcEstcEpEntry 18 }

cfprSwFcEstcEpPortId OBJECT-TYPE
    SYNTAX       Gauge32
    MAX-ACCESS   read-only
    STATUS       current
    DESCRIPTION
        "Cisco Firepower sw:FcEstcEp:portId managed object property"
    ::= { cfprSwFcEstcEpEntry 19 }

cfprSwFcEstcEpPortVsanId OBJECT-TYPE
    SYNTAX       Gauge32
    MAX-ACCESS   read-only
    STATUS       current
    DESCRIPTION
        "Cisco Firepower sw:FcEstcEp:portVsanId managed object property"
    ::= { cfprSwFcEstcEpEntry 20 }

cfprSwFcEstcEpSlotId OBJECT-TYPE
    SYNTAX       Gauge32
    MAX-ACCESS   read-only
    STATUS       current
    DESCRIPTION
        "Cisco Firepower sw:FcEstcEp:slotId managed object property"
    ::= { cfprSwFcEstcEpEntry 21 }

cfprSwFcEstcEpSwitchId OBJECT-TYPE
    SYNTAX       CfprNetworkSwitchId
    MAX-ACCESS   read-only
    STATUS       current
    DESCRIPTION
        "Cisco Firepower sw:FcEstcEp:switchId managed object property"
    ::= { cfprSwFcEstcEpEntry 22 }

cfprSwFcEstcEpTransport OBJECT-TYPE
    SYNTAX       CfprSwFcEstcEpTransport
    MAX-ACCESS   read-only
    STATUS       current
    DESCRIPTION
        "Cisco Firepower sw:FcEstcEp:transport managed object property"
    ::= { cfprSwFcEstcEpEntry 23 }

cfprSwFcEstcEpType OBJECT-TYPE
    SYNTAX       CfprNetworkConnectionType
    MAX-ACCESS   read-only
    STATUS       current
    DESCRIPTION
        "Cisco Firepower sw:FcEstcEp:type managed object property"
    ::= { cfprSwFcEstcEpEntry 24 }

cfprSwFcMonTable OBJECT-TYPE
    SYNTAX           SEQUENCE OF CfprSwFcMonEntry
    MAX-ACCESS       not-accessible
    STATUS           current
    DESCRIPTION
        "Cisco Firepower sw:FcMon managed object table"
    ::= { cfprSwObjects 38 }

cfprSwFcMonEntry OBJECT-TYPE
    SYNTAX           CfprSwFcMonEntry
    MAX-ACCESS       not-accessible
    STATUS           current
    DESCRIPTION
        "Entry for the cfprSwFcMonTable table."
    INDEX { cfprSwFcMonInstanceId }
    ::= { cfprSwFcMonTable 1 }

CfprSwFcMonEntry ::= SEQUENCE {
    cfprSwFcMonInstanceId                                            CfprManagedObjectId,
    cfprSwFcMonDn                                                    CfprManagedObjectDn,
    cfprSwFcMonRn                                                    SnmpAdminString,
    cfprSwFcMonAdminState                                            CfprSwMonAdminState,
    cfprSwFcMonFsmDescr                                              SnmpAdminString,
    cfprSwFcMonFsmPrev                                               SnmpAdminString,
    cfprSwFcMonFsmProgr                                              Gauge32,
    cfprSwFcMonFsmRmtInvErrCode                                      Gauge32,
    cfprSwFcMonFsmRmtInvErrDescr                                     SnmpAdminString,
    cfprSwFcMonFsmRmtInvRslt                                         CfprConditionRemoteInvRslt,
    cfprSwFcMonFsmStageDescr                                         SnmpAdminString,
    cfprSwFcMonFsmStamp                                              DateAndTime,
    cfprSwFcMonFsmStatus                                             SnmpAdminString,
    cfprSwFcMonFsmTry                                                Gauge32,
    cfprSwFcMonHasLastDest                                           TruthValue,
    cfprSwFcMonLifeCycle                                             CfprSwMonLifeCycle,
    cfprSwFcMonName                                                  SnmpAdminString,
    cfprSwFcMonPeerDn                                                SnmpAdminString,
    cfprSwFcMonSession                                               Gauge32,
    cfprSwFcMonSwitchId                                              CfprNetworkSwitchId,
    cfprSwFcMonTransport                                             CfprSwFcMonTransport,
    cfprSwFcMonType                                                  CfprSwFcMonType
}

cfprSwFcMonInstanceId OBJECT-TYPE
    SYNTAX       CfprManagedObjectId
    MAX-ACCESS   not-accessible
    STATUS       current
    DESCRIPTION
        "Instance identifier of the managed object."
    ::= { cfprSwFcMonEntry 1 }

cfprSwFcMonDn OBJECT-TYPE
    SYNTAX       CfprManagedObjectDn
    MAX-ACCESS   read-only
    STATUS       current
    DESCRIPTION
        "Cisco Firepower sw:FcMon:dn managed object property"
    ::= { cfprSwFcMonEntry 2 }

cfprSwFcMonRn OBJECT-TYPE
    SYNTAX       SnmpAdminString
    MAX-ACCESS   read-only
    STATUS       current
    DESCRIPTION
        "Cisco Firepower sw:FcMon:rn managed object property"
    ::= { cfprSwFcMonEntry 3 }

cfprSwFcMonAdminState OBJECT-TYPE
    SYNTAX       CfprSwMonAdminState
    MAX-ACCESS   read-only
    STATUS       current
    DESCRIPTION
        "Cisco Firepower sw:FcMon:adminState managed object property"
    ::= { cfprSwFcMonEntry 4 }

cfprSwFcMonFsmDescr OBJECT-TYPE
    SYNTAX       SnmpAdminString
    MAX-ACCESS   read-only
    STATUS       current
    DESCRIPTION
        "Cisco Firepower sw:FcMon:fsmDescr managed object property"
    ::= { cfprSwFcMonEntry 5 }

cfprSwFcMonFsmPrev OBJECT-TYPE
    SYNTAX       SnmpAdminString
    MAX-ACCESS   read-only
    STATUS       current
    DESCRIPTION
        "Cisco Firepower sw:FcMon:fsmPrev managed object property"
    ::= { cfprSwFcMonEntry 6 }

cfprSwFcMonFsmProgr OBJECT-TYPE
    SYNTAX       Gauge32
    MAX-ACCESS   read-only
    STATUS       current
    DESCRIPTION
        "Cisco Firepower sw:FcMon:fsmProgr managed object property"
    ::= { cfprSwFcMonEntry 7 }

cfprSwFcMonFsmRmtInvErrCode OBJECT-TYPE
    SYNTAX       Gauge32
    MAX-ACCESS   read-only
    STATUS       current
    DESCRIPTION
        "Cisco Firepower sw:FcMon:fsmRmtInvErrCode managed
        object property"
    ::= { cfprSwFcMonEntry 8 }

cfprSwFcMonFsmRmtInvErrDescr OBJECT-TYPE
    SYNTAX       SnmpAdminString
    MAX-ACCESS   read-only
    STATUS       current
    DESCRIPTION
        "Cisco Firepower sw:FcMon:fsmRmtInvErrDescr managed
        object property"
    ::= { cfprSwFcMonEntry 9 }

cfprSwFcMonFsmRmtInvRslt OBJECT-TYPE
    SYNTAX       CfprConditionRemoteInvRslt
    MAX-ACCESS   read-only
    STATUS       current
    DESCRIPTION
        "Cisco Firepower sw:FcMon:fsmRmtInvRslt managed object property"
    ::= { cfprSwFcMonEntry 10 }

cfprSwFcMonFsmStageDescr OBJECT-TYPE
    SYNTAX       SnmpAdminString
    MAX-ACCESS   read-only
    STATUS       current
    DESCRIPTION
        "Cisco Firepower sw:FcMon:fsmStageDescr managed object property"
    ::= { cfprSwFcMonEntry 11 }

cfprSwFcMonFsmStamp OBJECT-TYPE
    SYNTAX       DateAndTime
    MAX-ACCESS   read-only
    STATUS       current
    DESCRIPTION
        "Cisco Firepower sw:FcMon:fsmStamp managed object property"
    ::= { cfprSwFcMonEntry 12 }

cfprSwFcMonFsmStatus OBJECT-TYPE
    SYNTAX       SnmpAdminString
    MAX-ACCESS   read-only
    STATUS       current
    DESCRIPTION
        "Cisco Firepower sw:FcMon:fsmStatus managed object property"
    ::= { cfprSwFcMonEntry 13 }

cfprSwFcMonFsmTry OBJECT-TYPE
    SYNTAX       Gauge32
    MAX-ACCESS   read-only
    STATUS       current
    DESCRIPTION
        "Cisco Firepower sw:FcMon:fsmTry managed object property"
    ::= { cfprSwFcMonEntry 14 }

cfprSwFcMonHasLastDest OBJECT-TYPE
    SYNTAX       TruthValue
    MAX-ACCESS   read-only
    STATUS       current
    DESCRIPTION
        "Cisco Firepower sw:FcMon:hasLastDest managed object property"
    ::= { cfprSwFcMonEntry 15 }

cfprSwFcMonLifeCycle OBJECT-TYPE
    SYNTAX       CfprSwMonLifeCycle
    MAX-ACCESS   read-only
    STATUS       current
    DESCRIPTION
        "Cisco Firepower sw:FcMon:lifeCycle managed object property"
    ::= { cfprSwFcMonEntry 16 }

cfprSwFcMonName OBJECT-TYPE
    SYNTAX       SnmpAdminString
    MAX-ACCESS   read-only
    STATUS       current
    DESCRIPTION
        "Cisco Firepower sw:FcMon:name managed object property"
    ::= { cfprSwFcMonEntry 17 }

cfprSwFcMonPeerDn OBJECT-TYPE
    SYNTAX       SnmpAdminString
    MAX-ACCESS   read-only
    STATUS       current
    DESCRIPTION
        "Cisco Firepower sw:FcMon:peerDn managed object property"
    ::= { cfprSwFcMonEntry 18 }

cfprSwFcMonSession OBJECT-TYPE
    SYNTAX       Gauge32
    MAX-ACCESS   read-only
    STATUS       current
    DESCRIPTION
        "Cisco Firepower sw:FcMon:session managed object property"
    ::= { cfprSwFcMonEntry 19 }

cfprSwFcMonSwitchId OBJECT-TYPE
    SYNTAX       CfprNetworkSwitchId
    MAX-ACCESS   read-only
    STATUS       current
    DESCRIPTION
        "Cisco Firepower sw:FcMon:switchId managed object property"
    ::= { cfprSwFcMonEntry 20 }

cfprSwFcMonTransport OBJECT-TYPE
    SYNTAX       CfprSwFcMonTransport
    MAX-ACCESS   read-only
    STATUS       current
    DESCRIPTION
        "Cisco Firepower sw:FcMon:transport managed object property"
    ::= { cfprSwFcMonEntry 21 }

cfprSwFcMonType OBJECT-TYPE
    SYNTAX       CfprSwFcMonType
    MAX-ACCESS   read-only
    STATUS       current
    DESCRIPTION
        "Cisco Firepower sw:FcMon:type managed object property"
    ::= { cfprSwFcMonEntry 22 }

cfprSwFcMonDestEpTable OBJECT-TYPE
    SYNTAX           SEQUENCE OF CfprSwFcMonDestEpEntry
    MAX-ACCESS       not-accessible
    STATUS           current
    DESCRIPTION
        "Cisco Firepower sw:FcMonDestEp managed object table"
    ::= { cfprSwObjects 39 }

cfprSwFcMonDestEpEntry OBJECT-TYPE
    SYNTAX           CfprSwFcMonDestEpEntry
    MAX-ACCESS       not-accessible
    STATUS           current
    DESCRIPTION
        "Entry for the cfprSwFcMonDestEpTable table."
    INDEX { cfprSwFcMonDestEpInstanceId }
    ::= { cfprSwFcMonDestEpTable 1 }

CfprSwFcMonDestEpEntry ::= SEQUENCE {
    cfprSwFcMonDestEpInstanceId                                      CfprManagedObjectId,
    cfprSwFcMonDestEpDn                                              CfprManagedObjectDn,
    cfprSwFcMonDestEpRn                                              SnmpAdminString,
    cfprSwFcMonDestEpAdminSpeed                                      CfprPortSpeed,
    cfprSwFcMonDestEpAdminState                                      CfprFabricAdminState,
    cfprSwFcMonDestEpAggrPortId                                      Gauge32,
    cfprSwFcMonDestEpChassisId                                       Gauge32,
    cfprSwFcMonDestEpEpDn                                            SnmpAdminString,
    cfprSwFcMonDestEpIfRole                                          CfprNetworkPortRole,
    cfprSwFcMonDestEpIfType                                          CfprSwPIoEpIfType,
    cfprSwFcMonDestEpLc                                              CfprSwPIoEpLc,
    cfprSwFcMonDestEpLocale                                          CfprNetworkLocale,
    cfprSwFcMonDestEpName                                            SnmpAdminString,
    cfprSwFcMonDestEpPeerAggrPortId                                  Gauge32,
    cfprSwFcMonDestEpPeerChassisId                                   Gauge32,
    cfprSwFcMonDestEpPeerDn                                          SnmpAdminString,
    cfprSwFcMonDestEpPeerPortId                                      Gauge32,
    cfprSwFcMonDestEpPeerSlotId                                      Gauge32,
    cfprSwFcMonDestEpPortId                                          Gauge32,
    cfprSwFcMonDestEpSlotId                                          Gauge32,
    cfprSwFcMonDestEpSwitchId                                        CfprNetworkSwitchId,
    cfprSwFcMonDestEpTransport                                       CfprSwFcMonDestEpTransport,
    cfprSwFcMonDestEpType                                            CfprNetworkConnectionType
}

cfprSwFcMonDestEpInstanceId OBJECT-TYPE
    SYNTAX       CfprManagedObjectId
    MAX-ACCESS   not-accessible
    STATUS       current
    DESCRIPTION
        "Instance identifier of the managed object."
    ::= { cfprSwFcMonDestEpEntry 1 }

cfprSwFcMonDestEpDn OBJECT-TYPE
    SYNTAX       CfprManagedObjectDn
    MAX-ACCESS   read-only
    STATUS       current
    DESCRIPTION
        "Cisco Firepower sw:FcMonDestEp:dn managed object property"
    ::= { cfprSwFcMonDestEpEntry 2 }

cfprSwFcMonDestEpRn OBJECT-TYPE
    SYNTAX       SnmpAdminString
    MAX-ACCESS   read-only
    STATUS       current
    DESCRIPTION
        "Cisco Firepower sw:FcMonDestEp:rn managed object property"
    ::= { cfprSwFcMonDestEpEntry 3 }

cfprSwFcMonDestEpAdminSpeed OBJECT-TYPE
    SYNTAX       CfprPortSpeed
    MAX-ACCESS   read-only
    STATUS       current
    DESCRIPTION
        "Cisco Firepower sw:FcMonDestEp:adminSpeed managed
        object property"
    ::= { cfprSwFcMonDestEpEntry 4 }

cfprSwFcMonDestEpAdminState OBJECT-TYPE
    SYNTAX       CfprFabricAdminState
    MAX-ACCESS   read-only
    STATUS       current
    DESCRIPTION
        "Cisco Firepower sw:FcMonDestEp:adminState managed
        object property"
    ::= { cfprSwFcMonDestEpEntry 5 }

cfprSwFcMonDestEpAggrPortId OBJECT-TYPE
    SYNTAX       Gauge32
    MAX-ACCESS   read-only
    STATUS       current
    DESCRIPTION
        "Cisco Firepower sw:FcMonDestEp:aggrPortId managed
        object property"
    ::= { cfprSwFcMonDestEpEntry 6 }

cfprSwFcMonDestEpChassisId OBJECT-TYPE
    SYNTAX       Gauge32
    MAX-ACCESS   read-only
    STATUS       current
    DESCRIPTION
        "Cisco Firepower sw:FcMonDestEp:chassisId managed object property"
    ::= { cfprSwFcMonDestEpEntry 7 }

cfprSwFcMonDestEpEpDn OBJECT-TYPE
    SYNTAX       SnmpAdminString
    MAX-ACCESS   read-only
    STATUS       current
    DESCRIPTION
        "Cisco Firepower sw:FcMonDestEp:epDn managed object property"
    ::= { cfprSwFcMonDestEpEntry 8 }

cfprSwFcMonDestEpIfRole OBJECT-TYPE
    SYNTAX       CfprNetworkPortRole
    MAX-ACCESS   read-only
    STATUS       current
    DESCRIPTION
        "Cisco Firepower sw:FcMonDestEp:ifRole managed object property"
    ::= { cfprSwFcMonDestEpEntry 9 }

cfprSwFcMonDestEpIfType OBJECT-TYPE
    SYNTAX       CfprSwPIoEpIfType
    MAX-ACCESS   read-only
    STATUS       current
    DESCRIPTION
        "Cisco Firepower sw:FcMonDestEp:ifType managed object property"
    ::= { cfprSwFcMonDestEpEntry 10 }

cfprSwFcMonDestEpLc OBJECT-TYPE
    SYNTAX       CfprSwPIoEpLc
    MAX-ACCESS   read-only
    STATUS       current
    DESCRIPTION
        "Cisco Firepower sw:FcMonDestEp:lc managed object property"
    ::= { cfprSwFcMonDestEpEntry 11 }

cfprSwFcMonDestEpLocale OBJECT-TYPE
    SYNTAX       CfprNetworkLocale
    MAX-ACCESS   read-only
    STATUS       current
    DESCRIPTION
        "Cisco Firepower sw:FcMonDestEp:locale managed object property"
    ::= { cfprSwFcMonDestEpEntry 12 }

cfprSwFcMonDestEpName OBJECT-TYPE
    SYNTAX       SnmpAdminString
    MAX-ACCESS   read-only
    STATUS       current
    DESCRIPTION
        "Cisco Firepower sw:FcMonDestEp:name managed object property"
    ::= { cfprSwFcMonDestEpEntry 13 }

cfprSwFcMonDestEpPeerAggrPortId OBJECT-TYPE
    SYNTAX       Gauge32
    MAX-ACCESS   read-only
    STATUS       current
    DESCRIPTION
        "Cisco Firepower sw:FcMonDestEp:peerAggrPortId
        managed object property"
    ::= { cfprSwFcMonDestEpEntry 14 }

cfprSwFcMonDestEpPeerChassisId OBJECT-TYPE
    SYNTAX       Gauge32
    MAX-ACCESS   read-only
    STATUS       current
    DESCRIPTION
        "Cisco Firepower sw:FcMonDestEp:peerChassisId managed
        object property"
    ::= { cfprSwFcMonDestEpEntry 15 }

cfprSwFcMonDestEpPeerDn OBJECT-TYPE
    SYNTAX       SnmpAdminString
    MAX-ACCESS   read-only
    STATUS       current
    DESCRIPTION
        "Cisco Firepower sw:FcMonDestEp:peerDn managed object property"
    ::= { cfprSwFcMonDestEpEntry 16 }

cfprSwFcMonDestEpPeerPortId OBJECT-TYPE
    SYNTAX       Gauge32
    MAX-ACCESS   read-only
    STATUS       current
    DESCRIPTION
        "Cisco Firepower sw:FcMonDestEp:peerPortId managed
        object property"
    ::= { cfprSwFcMonDestEpEntry 17 }

cfprSwFcMonDestEpPeerSlotId OBJECT-TYPE
    SYNTAX       Gauge32
    MAX-ACCESS   read-only
    STATUS       current
    DESCRIPTION
        "Cisco Firepower sw:FcMonDestEp:peerSlotId managed
        object property"
    ::= { cfprSwFcMonDestEpEntry 18 }

cfprSwFcMonDestEpPortId OBJECT-TYPE
    SYNTAX       Gauge32
    MAX-ACCESS   read-only
    STATUS       current
    DESCRIPTION
        "Cisco Firepower sw:FcMonDestEp:portId managed object property"
    ::= { cfprSwFcMonDestEpEntry 19 }

cfprSwFcMonDestEpSlotId OBJECT-TYPE
    SYNTAX       Gauge32
    MAX-ACCESS   read-only
    STATUS       current
    DESCRIPTION
        "Cisco Firepower sw:FcMonDestEp:slotId managed object property"
    ::= { cfprSwFcMonDestEpEntry 20 }

cfprSwFcMonDestEpSwitchId OBJECT-TYPE
    SYNTAX       CfprNetworkSwitchId
    MAX-ACCESS   read-only
    STATUS       current
    DESCRIPTION
        "Cisco Firepower sw:FcMonDestEp:switchId managed object property"
    ::= { cfprSwFcMonDestEpEntry 21 }

cfprSwFcMonDestEpTransport OBJECT-TYPE
    SYNTAX       CfprSwFcMonDestEpTransport
    MAX-ACCESS   read-only
    STATUS       current
    DESCRIPTION
        "Cisco Firepower sw:FcMonDestEp:transport managed object property"
    ::= { cfprSwFcMonDestEpEntry 22 }

cfprSwFcMonDestEpType OBJECT-TYPE
    SYNTAX       CfprNetworkConnectionType
    MAX-ACCESS   read-only
    STATUS       current
    DESCRIPTION
        "Cisco Firepower sw:FcMonDestEp:type managed object property"
    ::= { cfprSwFcMonDestEpEntry 23 }

cfprSwFcMonFsmTable OBJECT-TYPE
    SYNTAX           SEQUENCE OF CfprSwFcMonFsmEntry
    MAX-ACCESS       not-accessible
    STATUS           current
    DESCRIPTION
        "Cisco Firepower sw:FcMonFsm managed object table"
    ::= { cfprSwObjects 40 }

cfprSwFcMonFsmEntry OBJECT-TYPE
    SYNTAX           CfprSwFcMonFsmEntry
    MAX-ACCESS       not-accessible
    STATUS           current
    DESCRIPTION
        "Entry for the cfprSwFcMonFsmTable table."
    INDEX { cfprSwFcMonFsmInstanceId }
    ::= { cfprSwFcMonFsmTable 1 }

CfprSwFcMonFsmEntry ::= SEQUENCE {
    cfprSwFcMonFsmInstanceId                                         CfprManagedObjectId,
    cfprSwFcMonFsmDn                                                 CfprManagedObjectDn,
    cfprSwFcMonFsmRn                                                 SnmpAdminString,
    cfprSwFcMonFsmCompletionTime                                     DateAndTime,
    cfprSwFcMonFsmCurrentFsm                                         CfprSwFcMonFsmCurrentFsm,
    cfprSwFcMonFsmDescrData                                          SnmpAdminString,
    cfprSwFcMonFsmFsmStatus                                          CfprFsmFsmStageStatus,
    cfprSwFcMonFsmProgress                                           Gauge32,
    cfprSwFcMonFsmRmtErrCode                                         Gauge32,
    cfprSwFcMonFsmRmtErrDescr                                        SnmpAdminString,
    cfprSwFcMonFsmRmtRslt                                            CfprConditionRemoteInvRslt
}

cfprSwFcMonFsmInstanceId OBJECT-TYPE
    SYNTAX       CfprManagedObjectId
    MAX-ACCESS   not-accessible
    STATUS       current
    DESCRIPTION
        "Instance identifier of the managed object."
    ::= { cfprSwFcMonFsmEntry 1 }

cfprSwFcMonFsmDn OBJECT-TYPE
    SYNTAX       CfprManagedObjectDn
    MAX-ACCESS   read-only
    STATUS       current
    DESCRIPTION
        "Cisco Firepower sw:FcMonFsm:dn managed object property"
    ::= { cfprSwFcMonFsmEntry 2 }

cfprSwFcMonFsmRn OBJECT-TYPE
    SYNTAX       SnmpAdminString
    MAX-ACCESS   read-only
    STATUS       current
    DESCRIPTION
        "Cisco Firepower sw:FcMonFsm:rn managed object property"
    ::= { cfprSwFcMonFsmEntry 3 }

cfprSwFcMonFsmCompletionTime OBJECT-TYPE
    SYNTAX       DateAndTime
    MAX-ACCESS   read-only
    STATUS       current
    DESCRIPTION
        "Cisco Firepower sw:FcMonFsm:completionTime managed
        object property"
    ::= { cfprSwFcMonFsmEntry 4 }

cfprSwFcMonFsmCurrentFsm OBJECT-TYPE
    SYNTAX       CfprSwFcMonFsmCurrentFsm
    MAX-ACCESS   read-only
    STATUS       current
    DESCRIPTION
        "Cisco Firepower sw:FcMonFsm:currentFsm managed object property"
    ::= { cfprSwFcMonFsmEntry 5 }

cfprSwFcMonFsmDescrData OBJECT-TYPE
    SYNTAX       SnmpAdminString
    MAX-ACCESS   read-only
    STATUS       current
    DESCRIPTION
        "Cisco Firepower sw:FcMonFsm:descr managed object property"
    ::= { cfprSwFcMonFsmEntry 6 }

cfprSwFcMonFsmFsmStatus OBJECT-TYPE
    SYNTAX       CfprFsmFsmStageStatus
    MAX-ACCESS   read-only
    STATUS       current
    DESCRIPTION
        "Cisco Firepower sw:FcMonFsm:fsmStatus managed object property"
    ::= { cfprSwFcMonFsmEntry 7 }

cfprSwFcMonFsmProgress OBJECT-TYPE
    SYNTAX       Gauge32
    MAX-ACCESS   read-only
    STATUS       current
    DESCRIPTION
        "Cisco Firepower sw:FcMonFsm:progress managed object property"
    ::= { cfprSwFcMonFsmEntry 8 }

cfprSwFcMonFsmRmtErrCode OBJECT-TYPE
    SYNTAX       Gauge32
    MAX-ACCESS   read-only
    STATUS       current
    DESCRIPTION
        "Cisco Firepower sw:FcMonFsm:rmtErrCode managed object property"
    ::= { cfprSwFcMonFsmEntry 9 }

cfprSwFcMonFsmRmtErrDescr OBJECT-TYPE
    SYNTAX       SnmpAdminString
    MAX-ACCESS   read-only
    STATUS       current
    DESCRIPTION
        "Cisco Firepower sw:FcMonFsm:rmtErrDescr managed object property"
    ::= { cfprSwFcMonFsmEntry 10 }

cfprSwFcMonFsmRmtRslt OBJECT-TYPE
    SYNTAX       CfprConditionRemoteInvRslt
    MAX-ACCESS   read-only
    STATUS       current
    DESCRIPTION
        "Cisco Firepower sw:FcMonFsm:rmtRslt managed object property"
    ::= { cfprSwFcMonFsmEntry 11 }

cfprSwFcMonFsmStageTable OBJECT-TYPE
    SYNTAX           SEQUENCE OF CfprSwFcMonFsmStageEntry
    MAX-ACCESS       not-accessible
    STATUS           current
    DESCRIPTION
        "Cisco Firepower sw:FcMonFsmStage managed object table"
    ::= { cfprSwObjects 41 }

cfprSwFcMonFsmStageEntry OBJECT-TYPE
    SYNTAX           CfprSwFcMonFsmStageEntry
    MAX-ACCESS       not-accessible
    STATUS           current
    DESCRIPTION
        "Entry for the cfprSwFcMonFsmStageTable table."
    INDEX { cfprSwFcMonFsmStageInstanceId }
    ::= { cfprSwFcMonFsmStageTable 1 }

CfprSwFcMonFsmStageEntry ::= SEQUENCE {
    cfprSwFcMonFsmStageInstanceId                                    CfprManagedObjectId,
    cfprSwFcMonFsmStageDn                                            CfprManagedObjectDn,
    cfprSwFcMonFsmStageRn                                            SnmpAdminString,
    cfprSwFcMonFsmStageDescrData                                     SnmpAdminString,
    cfprSwFcMonFsmStageLastUpdateTime                                DateAndTime,
    cfprSwFcMonFsmStageName                                          CfprSwFcMonFsmStageName,
    cfprSwFcMonFsmStageOrder                                         Gauge32,
    cfprSwFcMonFsmStageRetry                                         Gauge32,
    cfprSwFcMonFsmStageStageStatus                                   CfprFsmFsmStageStatus
}

cfprSwFcMonFsmStageInstanceId OBJECT-TYPE
    SYNTAX       CfprManagedObjectId
    MAX-ACCESS   not-accessible
    STATUS       current
    DESCRIPTION
        "Instance identifier of the managed object."
    ::= { cfprSwFcMonFsmStageEntry 1 }

cfprSwFcMonFsmStageDn OBJECT-TYPE
    SYNTAX       CfprManagedObjectDn
    MAX-ACCESS   read-only
    STATUS       current
    DESCRIPTION
        "Cisco Firepower sw:FcMonFsmStage:dn managed object property"
    ::= { cfprSwFcMonFsmStageEntry 2 }

cfprSwFcMonFsmStageRn OBJECT-TYPE
    SYNTAX       SnmpAdminString
    MAX-ACCESS   read-only
    STATUS       current
    DESCRIPTION
        "Cisco Firepower sw:FcMonFsmStage:rn managed object property"
    ::= { cfprSwFcMonFsmStageEntry 3 }

cfprSwFcMonFsmStageDescrData OBJECT-TYPE
    SYNTAX       SnmpAdminString
    MAX-ACCESS   read-only
    STATUS       current
    DESCRIPTION
        "Cisco Firepower sw:FcMonFsmStage:descr managed object property"
    ::= { cfprSwFcMonFsmStageEntry 4 }

cfprSwFcMonFsmStageLastUpdateTime OBJECT-TYPE
    SYNTAX       DateAndTime
    MAX-ACCESS   read-only
    STATUS       current
    DESCRIPTION
        "Cisco Firepower sw:FcMonFsmStage:lastUpdateTime
        managed object property"
    ::= { cfprSwFcMonFsmStageEntry 5 }

cfprSwFcMonFsmStageName OBJECT-TYPE
    SYNTAX       CfprSwFcMonFsmStageName
    MAX-ACCESS   read-only
    STATUS       current
    DESCRIPTION
        "Cisco Firepower sw:FcMonFsmStage:name managed object property"
    ::= { cfprSwFcMonFsmStageEntry 6 }

cfprSwFcMonFsmStageOrder OBJECT-TYPE
    SYNTAX       Gauge32
    MAX-ACCESS   read-only
    STATUS       current
    DESCRIPTION
        "Cisco Firepower sw:FcMonFsmStage:order managed object property"
    ::= { cfprSwFcMonFsmStageEntry 7 }

cfprSwFcMonFsmStageRetry OBJECT-TYPE
    SYNTAX       Gauge32
    MAX-ACCESS   read-only
    STATUS       current
    DESCRIPTION
        "Cisco Firepower sw:FcMonFsmStage:retry managed object property"
    ::= { cfprSwFcMonFsmStageEntry 8 }

cfprSwFcMonFsmStageStageStatus OBJECT-TYPE
    SYNTAX       CfprFsmFsmStageStatus
    MAX-ACCESS   read-only
    STATUS       current
    DESCRIPTION
        "Cisco Firepower sw:FcMonFsmStage:stageStatus managed
        object property"
    ::= { cfprSwFcMonFsmStageEntry 9 }

cfprSwFcMonFsmTaskTable OBJECT-TYPE
    SYNTAX           SEQUENCE OF CfprSwFcMonFsmTaskEntry
    MAX-ACCESS       not-accessible
    STATUS           current
    DESCRIPTION
        "Cisco Firepower sw:FcMonFsmTask managed object table"
    ::= { cfprSwObjects 42 }

cfprSwFcMonFsmTaskEntry OBJECT-TYPE
    SYNTAX           CfprSwFcMonFsmTaskEntry
    MAX-ACCESS       not-accessible
    STATUS           current
    DESCRIPTION
        "Entry for the cfprSwFcMonFsmTaskTable table."
    INDEX { cfprSwFcMonFsmTaskInstanceId }
    ::= { cfprSwFcMonFsmTaskTable 1 }

CfprSwFcMonFsmTaskEntry ::= SEQUENCE {
    cfprSwFcMonFsmTaskInstanceId                                     CfprManagedObjectId,
    cfprSwFcMonFsmTaskDn                                             CfprManagedObjectDn,
    cfprSwFcMonFsmTaskRn                                             SnmpAdminString,
    cfprSwFcMonFsmTaskCompletion                                     CfprFsmCompletion,
    cfprSwFcMonFsmTaskFlags                                          CfprFsmFlags,
    cfprSwFcMonFsmTaskItem                                           CfprSwFcMonFsmTaskItem,
    cfprSwFcMonFsmTaskSeqId                                          Gauge32
}

cfprSwFcMonFsmTaskInstanceId OBJECT-TYPE
    SYNTAX       CfprManagedObjectId
    MAX-ACCESS   not-accessible
    STATUS       current
    DESCRIPTION
        "Instance identifier of the managed object."
    ::= { cfprSwFcMonFsmTaskEntry 1 }

cfprSwFcMonFsmTaskDn OBJECT-TYPE
    SYNTAX       CfprManagedObjectDn
    MAX-ACCESS   read-only
    STATUS       current
    DESCRIPTION
        "Cisco Firepower sw:FcMonFsmTask:dn managed object property"
    ::= { cfprSwFcMonFsmTaskEntry 2 }

cfprSwFcMonFsmTaskRn OBJECT-TYPE
    SYNTAX       SnmpAdminString
    MAX-ACCESS   read-only
    STATUS       current
    DESCRIPTION
        "Cisco Firepower sw:FcMonFsmTask:rn managed object property"
    ::= { cfprSwFcMonFsmTaskEntry 3 }

cfprSwFcMonFsmTaskCompletion OBJECT-TYPE
    SYNTAX       CfprFsmCompletion
    MAX-ACCESS   read-only
    STATUS       current
    DESCRIPTION
        "Cisco Firepower sw:FcMonFsmTask:completion managed
        object property"
    ::= { cfprSwFcMonFsmTaskEntry 4 }

cfprSwFcMonFsmTaskFlags OBJECT-TYPE
    SYNTAX       CfprFsmFlags
    MAX-ACCESS   read-only
    STATUS       current
    DESCRIPTION
        "Cisco Firepower sw:FcMonFsmTask:flags managed object property"
    ::= { cfprSwFcMonFsmTaskEntry 5 }

cfprSwFcMonFsmTaskItem OBJECT-TYPE
    SYNTAX       CfprSwFcMonFsmTaskItem
    MAX-ACCESS   read-only
    STATUS       current
    DESCRIPTION
        "Cisco Firepower sw:FcMonFsmTask:item managed object property"
    ::= { cfprSwFcMonFsmTaskEntry 6 }

cfprSwFcMonFsmTaskSeqId OBJECT-TYPE
    SYNTAX       Gauge32
    MAX-ACCESS   read-only
    STATUS       current
    DESCRIPTION
        "Cisco Firepower sw:FcMonFsmTask:seqId managed object property"
    ::= { cfprSwFcMonFsmTaskEntry 7 }

cfprSwFcMonSrcEpTable OBJECT-TYPE
    SYNTAX           SEQUENCE OF CfprSwFcMonSrcEpEntry
    MAX-ACCESS       not-accessible
    STATUS           current
    DESCRIPTION
        "Cisco Firepower sw:FcMonSrcEp managed object table"
    ::= { cfprSwObjects 43 }

cfprSwFcMonSrcEpEntry OBJECT-TYPE
    SYNTAX           CfprSwFcMonSrcEpEntry
    MAX-ACCESS       not-accessible
    STATUS           current
    DESCRIPTION
        "Entry for the cfprSwFcMonSrcEpTable table."
    INDEX { cfprSwFcMonSrcEpInstanceId }
    ::= { cfprSwFcMonSrcEpTable 1 }

CfprSwFcMonSrcEpEntry ::= SEQUENCE {
    cfprSwFcMonSrcEpInstanceId                                       CfprManagedObjectId,
    cfprSwFcMonSrcEpDn                                               CfprManagedObjectDn,
    cfprSwFcMonSrcEpRn                                               SnmpAdminString,
    cfprSwFcMonSrcEpAdminState                                       CfprFabricAdminState,
    cfprSwFcMonSrcEpAggrPortId                                       Gauge32,
    cfprSwFcMonSrcEpChassisId                                        Gauge32,
    cfprSwFcMonSrcEpEpDn                                             SnmpAdminString,
    cfprSwFcMonSrcEpIfRole                                           CfprNetworkPortRole,
    cfprSwFcMonSrcEpIfType                                           CfprSwPIoEpIfType,
    cfprSwFcMonSrcEpLc                                               CfprSwPIoEpLc,
    cfprSwFcMonSrcEpLocale                                           CfprSwMonSrcEpLocale,
    cfprSwFcMonSrcEpMonTrafDir                                       CfprFabricTrafficDirection,
    cfprSwFcMonSrcEpName                                             SnmpAdminString,
    cfprSwFcMonSrcEpPeerAggrPortId                                   Gauge32,
    cfprSwFcMonSrcEpPeerChassisId                                    Gauge32,
    cfprSwFcMonSrcEpPeerDn                                           SnmpAdminString,
    cfprSwFcMonSrcEpPeerPortId                                       Gauge32,
    cfprSwFcMonSrcEpPeerSlotId                                       Gauge32,
    cfprSwFcMonSrcEpPortId                                           Gauge32,
    cfprSwFcMonSrcEpSlotId                                           Gauge32,
    cfprSwFcMonSrcEpSwitchId                                         CfprNetworkSwitchId,
    cfprSwFcMonSrcEpTransport                                        CfprSwFcMonSrcEpTransport,
    cfprSwFcMonSrcEpType                                             CfprNetworkConnectionType
}

cfprSwFcMonSrcEpInstanceId OBJECT-TYPE
    SYNTAX       CfprManagedObjectId
    MAX-ACCESS   not-accessible
    STATUS       current
    DESCRIPTION
        "Instance identifier of the managed object."
    ::= { cfprSwFcMonSrcEpEntry 1 }

cfprSwFcMonSrcEpDn OBJECT-TYPE
    SYNTAX       CfprManagedObjectDn
    MAX-ACCESS   read-only
    STATUS       current
    DESCRIPTION
        "Cisco Firepower sw:FcMonSrcEp:dn managed object property"
    ::= { cfprSwFcMonSrcEpEntry 2 }

cfprSwFcMonSrcEpRn OBJECT-TYPE
    SYNTAX       SnmpAdminString
    MAX-ACCESS   read-only
    STATUS       current
    DESCRIPTION
        "Cisco Firepower sw:FcMonSrcEp:rn managed object property"
    ::= { cfprSwFcMonSrcEpEntry 3 }

cfprSwFcMonSrcEpAdminState OBJECT-TYPE
    SYNTAX       CfprFabricAdminState
    MAX-ACCESS   read-only
    STATUS       current
    DESCRIPTION
        "Cisco Firepower sw:FcMonSrcEp:adminState managed object property"
    ::= { cfprSwFcMonSrcEpEntry 4 }

cfprSwFcMonSrcEpAggrPortId OBJECT-TYPE
    SYNTAX       Gauge32
    MAX-ACCESS   read-only
    STATUS       current
    DESCRIPTION
        "Cisco Firepower sw:FcMonSrcEp:aggrPortId managed object property"
    ::= { cfprSwFcMonSrcEpEntry 5 }

cfprSwFcMonSrcEpChassisId OBJECT-TYPE
    SYNTAX       Gauge32
    MAX-ACCESS   read-only
    STATUS       current
    DESCRIPTION
        "Cisco Firepower sw:FcMonSrcEp:chassisId managed object property"
    ::= { cfprSwFcMonSrcEpEntry 6 }

cfprSwFcMonSrcEpEpDn OBJECT-TYPE
    SYNTAX       SnmpAdminString
    MAX-ACCESS   read-only
    STATUS       current
    DESCRIPTION
        "Cisco Firepower sw:FcMonSrcEp:epDn managed object property"
    ::= { cfprSwFcMonSrcEpEntry 7 }

cfprSwFcMonSrcEpIfRole OBJECT-TYPE
    SYNTAX       CfprNetworkPortRole
    MAX-ACCESS   read-only
    STATUS       current
    DESCRIPTION
        "Cisco Firepower sw:FcMonSrcEp:ifRole managed object property"
    ::= { cfprSwFcMonSrcEpEntry 8 }

cfprSwFcMonSrcEpIfType OBJECT-TYPE
    SYNTAX       CfprSwPIoEpIfType
    MAX-ACCESS   read-only
    STATUS       current
    DESCRIPTION
        "Cisco Firepower sw:FcMonSrcEp:ifType managed object property"
    ::= { cfprSwFcMonSrcEpEntry 9 }

cfprSwFcMonSrcEpLc OBJECT-TYPE
    SYNTAX       CfprSwPIoEpLc
    MAX-ACCESS   read-only
    STATUS       current
    DESCRIPTION
        "Cisco Firepower sw:FcMonSrcEp:lc managed object property"
    ::= { cfprSwFcMonSrcEpEntry 10 }

cfprSwFcMonSrcEpLocale OBJECT-TYPE
    SYNTAX       CfprSwMonSrcEpLocale
    MAX-ACCESS   read-only
    STATUS       current
    DESCRIPTION
        "Cisco Firepower sw:FcMonSrcEp:locale managed object property"
    ::= { cfprSwFcMonSrcEpEntry 11 }

cfprSwFcMonSrcEpMonTrafDir OBJECT-TYPE
    SYNTAX       CfprFabricTrafficDirection
    MAX-ACCESS   read-only
    STATUS       current
    DESCRIPTION
        "Cisco Firepower sw:FcMonSrcEp:monTrafDir managed object property"
    ::= { cfprSwFcMonSrcEpEntry 12 }

cfprSwFcMonSrcEpName OBJECT-TYPE
    SYNTAX       SnmpAdminString
    MAX-ACCESS   read-only
    STATUS       current
    DESCRIPTION
        "Cisco Firepower sw:FcMonSrcEp:name managed object property"
    ::= { cfprSwFcMonSrcEpEntry 13 }

cfprSwFcMonSrcEpPeerAggrPortId OBJECT-TYPE
    SYNTAX       Gauge32
    MAX-ACCESS   read-only
    STATUS       current
    DESCRIPTION
        "Cisco Firepower sw:FcMonSrcEp:peerAggrPortId managed
        object property"
    ::= { cfprSwFcMonSrcEpEntry 14 }

cfprSwFcMonSrcEpPeerChassisId OBJECT-TYPE
    SYNTAX       Gauge32
    MAX-ACCESS   read-only
    STATUS       current
    DESCRIPTION
        "Cisco Firepower sw:FcMonSrcEp:peerChassisId managed
        object property"
    ::= { cfprSwFcMonSrcEpEntry 15 }

cfprSwFcMonSrcEpPeerDn OBJECT-TYPE
    SYNTAX       SnmpAdminString
    MAX-ACCESS   read-only
    STATUS       current
    DESCRIPTION
        "Cisco Firepower sw:FcMonSrcEp:peerDn managed object property"
    ::= { cfprSwFcMonSrcEpEntry 16 }

cfprSwFcMonSrcEpPeerPortId OBJECT-TYPE
    SYNTAX       Gauge32
    MAX-ACCESS   read-only
    STATUS       current
    DESCRIPTION
        "Cisco Firepower sw:FcMonSrcEp:peerPortId managed object property"
    ::= { cfprSwFcMonSrcEpEntry 17 }

cfprSwFcMonSrcEpPeerSlotId OBJECT-TYPE
    SYNTAX       Gauge32
    MAX-ACCESS   read-only
    STATUS       current
    DESCRIPTION
        "Cisco Firepower sw:FcMonSrcEp:peerSlotId managed object property"
    ::= { cfprSwFcMonSrcEpEntry 18 }

cfprSwFcMonSrcEpPortId OBJECT-TYPE
    SYNTAX       Gauge32
    MAX-ACCESS   read-only
    STATUS       current
    DESCRIPTION
        "Cisco Firepower sw:FcMonSrcEp:portId managed object property"
    ::= { cfprSwFcMonSrcEpEntry 19 }

cfprSwFcMonSrcEpSlotId OBJECT-TYPE
    SYNTAX       Gauge32
    MAX-ACCESS   read-only
    STATUS       current
    DESCRIPTION
        "Cisco Firepower sw:FcMonSrcEp:slotId managed object property"
    ::= { cfprSwFcMonSrcEpEntry 20 }

cfprSwFcMonSrcEpSwitchId OBJECT-TYPE
    SYNTAX       CfprNetworkSwitchId
    MAX-ACCESS   read-only
    STATUS       current
    DESCRIPTION
        "Cisco Firepower sw:FcMonSrcEp:switchId managed object property"
    ::= { cfprSwFcMonSrcEpEntry 21 }

cfprSwFcMonSrcEpTransport OBJECT-TYPE
    SYNTAX       CfprSwFcMonSrcEpTransport
    MAX-ACCESS   read-only
    STATUS       current
    DESCRIPTION
        "Cisco Firepower sw:FcMonSrcEp:transport managed object property"
    ::= { cfprSwFcMonSrcEpEntry 22 }

cfprSwFcMonSrcEpType OBJECT-TYPE
    SYNTAX       CfprNetworkConnectionType
    MAX-ACCESS   read-only
    STATUS       current
    DESCRIPTION
        "Cisco Firepower sw:FcMonSrcEp:type managed object property"
    ::= { cfprSwFcMonSrcEpEntry 23 }

cfprSwFcSanBorderTable OBJECT-TYPE
    SYNTAX           SEQUENCE OF CfprSwFcSanBorderEntry
    MAX-ACCESS       not-accessible
    STATUS           current
    DESCRIPTION
        "Cisco Firepower sw:FcSanBorder managed object table"
    ::= { cfprSwObjects 44 }

cfprSwFcSanBorderEntry OBJECT-TYPE
    SYNTAX           CfprSwFcSanBorderEntry
    MAX-ACCESS       not-accessible
    STATUS           current
    DESCRIPTION
        "Entry for the cfprSwFcSanBorderTable table."
    INDEX { cfprSwFcSanBorderInstanceId }
    ::= { cfprSwFcSanBorderTable 1 }

CfprSwFcSanBorderEntry ::= SEQUENCE {
    cfprSwFcSanBorderInstanceId                                      CfprManagedObjectId,
    cfprSwFcSanBorderDn                                              CfprManagedObjectDn,
    cfprSwFcSanBorderRn                                              SnmpAdminString,
    cfprSwFcSanBorderFsmDescr                                        SnmpAdminString,
    cfprSwFcSanBorderFsmPrev                                         SnmpAdminString,
    cfprSwFcSanBorderFsmProgr                                        Gauge32,
    cfprSwFcSanBorderFsmRmtInvErrCode                                Gauge32,
    cfprSwFcSanBorderFsmRmtInvErrDescr                               SnmpAdminString,
    cfprSwFcSanBorderFsmRmtInvRslt                                   CfprConditionRemoteInvRslt,
    cfprSwFcSanBorderFsmStageDescr                                   SnmpAdminString,
    cfprSwFcSanBorderFsmStamp                                        DateAndTime,
    cfprSwFcSanBorderFsmStatus                                       SnmpAdminString,
    cfprSwFcSanBorderFsmTry                                          Gauge32,
    cfprSwFcSanBorderLocale                                          CfprSwBorderDomainLocale,
    cfprSwFcSanBorderName                                            SnmpAdminString,
    cfprSwFcSanBorderSwitchId                                        CfprNetworkSwitchId,
    cfprSwFcSanBorderTransport                                       CfprSwFcSanBorderTransport,
    cfprSwFcSanBorderType                                            CfprSwSanBorderType,
    cfprSwFcSanBorderUplinkTrunking                                  CfprSwFcSanBorderUplinkTrunking
}

cfprSwFcSanBorderInstanceId OBJECT-TYPE
    SYNTAX       CfprManagedObjectId
    MAX-ACCESS   not-accessible
    STATUS       current
    DESCRIPTION
        "Instance identifier of the managed object."
    ::= { cfprSwFcSanBorderEntry 1 }

cfprSwFcSanBorderDn OBJECT-TYPE
    SYNTAX       CfprManagedObjectDn
    MAX-ACCESS   read-only
    STATUS       current
    DESCRIPTION
        "Cisco Firepower sw:FcSanBorder:dn managed object property"
    ::= { cfprSwFcSanBorderEntry 2 }

cfprSwFcSanBorderRn OBJECT-TYPE
    SYNTAX       SnmpAdminString
    MAX-ACCESS   read-only
    STATUS       current
    DESCRIPTION
        "Cisco Firepower sw:FcSanBorder:rn managed object property"
    ::= { cfprSwFcSanBorderEntry 3 }

cfprSwFcSanBorderFsmDescr OBJECT-TYPE
    SYNTAX       SnmpAdminString
    MAX-ACCESS   read-only
    STATUS       current
    DESCRIPTION
        "Cisco Firepower sw:FcSanBorder:fsmDescr managed object property"
    ::= { cfprSwFcSanBorderEntry 4 }

cfprSwFcSanBorderFsmPrev OBJECT-TYPE
    SYNTAX       SnmpAdminString
    MAX-ACCESS   read-only
    STATUS       current
    DESCRIPTION
        "Cisco Firepower sw:FcSanBorder:fsmPrev managed object property"
    ::= { cfprSwFcSanBorderEntry 5 }

cfprSwFcSanBorderFsmProgr OBJECT-TYPE
    SYNTAX       Gauge32
    MAX-ACCESS   read-only
    STATUS       current
    DESCRIPTION
        "Cisco Firepower sw:FcSanBorder:fsmProgr managed object property"
    ::= { cfprSwFcSanBorderEntry 6 }

cfprSwFcSanBorderFsmRmtInvErrCode OBJECT-TYPE
    SYNTAX       Gauge32
    MAX-ACCESS   read-only
    STATUS       current
    DESCRIPTION
        "Cisco Firepower sw:FcSanBorder:fsmRmtInvErrCode
        managed object property"
    ::= { cfprSwFcSanBorderEntry 7 }

cfprSwFcSanBorderFsmRmtInvErrDescr OBJECT-TYPE
    SYNTAX       SnmpAdminString
    MAX-ACCESS   read-only
    STATUS       current
    DESCRIPTION
        "Cisco Firepower sw:FcSanBorder:fsmRmtInvErrDescr
        managed object property"
    ::= { cfprSwFcSanBorderEntry 8 }

cfprSwFcSanBorderFsmRmtInvRslt OBJECT-TYPE
    SYNTAX       CfprConditionRemoteInvRslt
    MAX-ACCESS   read-only
    STATUS       current
    DESCRIPTION
        "Cisco Firepower sw:FcSanBorder:fsmRmtInvRslt managed
        object property"
    ::= { cfprSwFcSanBorderEntry 9 }

cfprSwFcSanBorderFsmStageDescr OBJECT-TYPE
    SYNTAX       SnmpAdminString
    MAX-ACCESS   read-only
    STATUS       current
    DESCRIPTION
        "Cisco Firepower sw:FcSanBorder:fsmStageDescr managed
        object property"
    ::= { cfprSwFcSanBorderEntry 10 }

cfprSwFcSanBorderFsmStamp OBJECT-TYPE
    SYNTAX       DateAndTime
    MAX-ACCESS   read-only
    STATUS       current
    DESCRIPTION
        "Cisco Firepower sw:FcSanBorder:fsmStamp managed object property"
    ::= { cfprSwFcSanBorderEntry 11 }

cfprSwFcSanBorderFsmStatus OBJECT-TYPE
    SYNTAX       SnmpAdminString
    MAX-ACCESS   read-only
    STATUS       current
    DESCRIPTION
        "Cisco Firepower sw:FcSanBorder:fsmStatus managed object property"
    ::= { cfprSwFcSanBorderEntry 12 }

cfprSwFcSanBorderFsmTry OBJECT-TYPE
    SYNTAX       Gauge32
    MAX-ACCESS   read-only
    STATUS       current
    DESCRIPTION
        "Cisco Firepower sw:FcSanBorder:fsmTry managed object property"
    ::= { cfprSwFcSanBorderEntry 13 }

cfprSwFcSanBorderLocale OBJECT-TYPE
    SYNTAX       CfprSwBorderDomainLocale
    MAX-ACCESS   read-only
    STATUS       current
    DESCRIPTION
        "Cisco Firepower sw:FcSanBorder:locale managed object property"
    ::= { cfprSwFcSanBorderEntry 14 }

cfprSwFcSanBorderName OBJECT-TYPE
    SYNTAX       SnmpAdminString
    MAX-ACCESS   read-only
    STATUS       current
    DESCRIPTION
        "Cisco Firepower sw:FcSanBorder:name managed object property"
    ::= { cfprSwFcSanBorderEntry 15 }

cfprSwFcSanBorderSwitchId OBJECT-TYPE
    SYNTAX       CfprNetworkSwitchId
    MAX-ACCESS   read-only
    STATUS       current
    DESCRIPTION
        "Cisco Firepower sw:FcSanBorder:switchId managed object property"
    ::= { cfprSwFcSanBorderEntry 16 }

cfprSwFcSanBorderTransport OBJECT-TYPE
    SYNTAX       CfprSwFcSanBorderTransport
    MAX-ACCESS   read-only
    STATUS       current
    DESCRIPTION
        "Cisco Firepower sw:FcSanBorder:transport managed object property"
    ::= { cfprSwFcSanBorderEntry 17 }

cfprSwFcSanBorderType OBJECT-TYPE
    SYNTAX       CfprSwSanBorderType
    MAX-ACCESS   read-only
    STATUS       current
    DESCRIPTION
        "Cisco Firepower sw:FcSanBorder:type managed object property"
    ::= { cfprSwFcSanBorderEntry 18 }

cfprSwFcSanBorderUplinkTrunking OBJECT-TYPE
    SYNTAX       CfprSwFcSanBorderUplinkTrunking
    MAX-ACCESS   read-only
    STATUS       current
    DESCRIPTION
        "Cisco Firepower sw:FcSanBorder:uplinkTrunking
        managed object property"
    ::= { cfprSwFcSanBorderEntry 19 }

cfprSwFcSanBorderFsmTable OBJECT-TYPE
    SYNTAX           SEQUENCE OF CfprSwFcSanBorderFsmEntry
    MAX-ACCESS       not-accessible
    STATUS           current
    DESCRIPTION
        "Cisco Firepower sw:FcSanBorderFsm managed object table"
    ::= { cfprSwObjects 45 }

cfprSwFcSanBorderFsmEntry OBJECT-TYPE
    SYNTAX           CfprSwFcSanBorderFsmEntry
    MAX-ACCESS       not-accessible
    STATUS           current
    DESCRIPTION
        "Entry for the cfprSwFcSanBorderFsmTable table."
    INDEX { cfprSwFcSanBorderFsmInstanceId }
    ::= { cfprSwFcSanBorderFsmTable 1 }

CfprSwFcSanBorderFsmEntry ::= SEQUENCE {
    cfprSwFcSanBorderFsmInstanceId                                   CfprManagedObjectId,
    cfprSwFcSanBorderFsmDn                                           CfprManagedObjectDn,
    cfprSwFcSanBorderFsmRn                                           SnmpAdminString,
    cfprSwFcSanBorderFsmCompletionTime                               DateAndTime,
    cfprSwFcSanBorderFsmCurrentFsm                                   CfprSwFcSanBorderFsmCurrentFsm,
    cfprSwFcSanBorderFsmDescrData                                    SnmpAdminString,
    cfprSwFcSanBorderFsmFsmStatus                                    CfprFsmFsmStageStatus,
    cfprSwFcSanBorderFsmProgress                                     Gauge32,
    cfprSwFcSanBorderFsmRmtErrCode                                   Gauge32,
    cfprSwFcSanBorderFsmRmtErrDescr                                  SnmpAdminString,
    cfprSwFcSanBorderFsmRmtRslt                                      CfprConditionRemoteInvRslt
}

cfprSwFcSanBorderFsmInstanceId OBJECT-TYPE
    SYNTAX       CfprManagedObjectId
    MAX-ACCESS   not-accessible
    STATUS       current
    DESCRIPTION
        "Instance identifier of the managed object."
    ::= { cfprSwFcSanBorderFsmEntry 1 }

cfprSwFcSanBorderFsmDn OBJECT-TYPE
    SYNTAX       CfprManagedObjectDn
    MAX-ACCESS   read-only
    STATUS       current
    DESCRIPTION
        "Cisco Firepower sw:FcSanBorderFsm:dn managed object property"
    ::= { cfprSwFcSanBorderFsmEntry 2 }

cfprSwFcSanBorderFsmRn OBJECT-TYPE
    SYNTAX       SnmpAdminString
    MAX-ACCESS   read-only
    STATUS       current
    DESCRIPTION
        "Cisco Firepower sw:FcSanBorderFsm:rn managed object property"
    ::= { cfprSwFcSanBorderFsmEntry 3 }

cfprSwFcSanBorderFsmCompletionTime OBJECT-TYPE
    SYNTAX       DateAndTime
    MAX-ACCESS   read-only
    STATUS       current
    DESCRIPTION
        "Cisco Firepower sw:FcSanBorderFsm:completionTime
        managed object property"
    ::= { cfprSwFcSanBorderFsmEntry 4 }

cfprSwFcSanBorderFsmCurrentFsm OBJECT-TYPE
    SYNTAX       CfprSwFcSanBorderFsmCurrentFsm
    MAX-ACCESS   read-only
    STATUS       current
    DESCRIPTION
        "Cisco Firepower sw:FcSanBorderFsm:currentFsm managed
        object property"
    ::= { cfprSwFcSanBorderFsmEntry 5 }

cfprSwFcSanBorderFsmDescrData OBJECT-TYPE
    SYNTAX       SnmpAdminString
    MAX-ACCESS   read-only
    STATUS       current
    DESCRIPTION
        "Cisco Firepower sw:FcSanBorderFsm:descr managed object property"
    ::= { cfprSwFcSanBorderFsmEntry 6 }

cfprSwFcSanBorderFsmFsmStatus OBJECT-TYPE
    SYNTAX       CfprFsmFsmStageStatus
    MAX-ACCESS   read-only
    STATUS       current
    DESCRIPTION
        "Cisco Firepower sw:FcSanBorderFsm:fsmStatus managed
        object property"
    ::= { cfprSwFcSanBorderFsmEntry 7 }

cfprSwFcSanBorderFsmProgress OBJECT-TYPE
    SYNTAX       Gauge32
    MAX-ACCESS   read-only
    STATUS       current
    DESCRIPTION
        "Cisco Firepower sw:FcSanBorderFsm:progress managed
        object property"
    ::= { cfprSwFcSanBorderFsmEntry 8 }

cfprSwFcSanBorderFsmRmtErrCode OBJECT-TYPE
    SYNTAX       Gauge32
    MAX-ACCESS   read-only
    STATUS       current
    DESCRIPTION
        "Cisco Firepower sw:FcSanBorderFsm:rmtErrCode managed
        object property"
    ::= { cfprSwFcSanBorderFsmEntry 9 }

cfprSwFcSanBorderFsmRmtErrDescr OBJECT-TYPE
    SYNTAX       SnmpAdminString
    MAX-ACCESS   read-only
    STATUS       current
    DESCRIPTION
        "Cisco Firepower sw:FcSanBorderFsm:rmtErrDescr
        managed object property"
    ::= { cfprSwFcSanBorderFsmEntry 10 }

cfprSwFcSanBorderFsmRmtRslt OBJECT-TYPE
    SYNTAX       CfprConditionRemoteInvRslt
    MAX-ACCESS   read-only
    STATUS       current
    DESCRIPTION
        "Cisco Firepower sw:FcSanBorderFsm:rmtRslt managed
        object property"
    ::= { cfprSwFcSanBorderFsmEntry 11 }

cfprSwFcSanBorderFsmStageTable OBJECT-TYPE
    SYNTAX           SEQUENCE OF CfprSwFcSanBorderFsmStageEntry
    MAX-ACCESS       not-accessible
    STATUS           current
    DESCRIPTION
        "Cisco Firepower sw:FcSanBorderFsmStage managed object table"
    ::= { cfprSwObjects 46 }

cfprSwFcSanBorderFsmStageEntry OBJECT-TYPE
    SYNTAX           CfprSwFcSanBorderFsmStageEntry
    MAX-ACCESS       not-accessible
    STATUS           current
    DESCRIPTION
        "Entry for the cfprSwFcSanBorderFsmStageTable table."
    INDEX { cfprSwFcSanBorderFsmStageInstanceId }
    ::= { cfprSwFcSanBorderFsmStageTable 1 }

CfprSwFcSanBorderFsmStageEntry ::= SEQUENCE {
    cfprSwFcSanBorderFsmStageInstanceId                              CfprManagedObjectId,
    cfprSwFcSanBorderFsmStageDn                                      CfprManagedObjectDn,
    cfprSwFcSanBorderFsmStageRn                                      SnmpAdminString,
    cfprSwFcSanBorderFsmStageDescrData                               SnmpAdminString,
    cfprSwFcSanBorderFsmStageLastUpdateTime                          DateAndTime,
    cfprSwFcSanBorderFsmStageName                                    CfprSwFcSanBorderFsmStageName,
    cfprSwFcSanBorderFsmStageOrder                                   Gauge32,
    cfprSwFcSanBorderFsmStageRetry                                   Gauge32,
    cfprSwFcSanBorderFsmStageStageStatus                             CfprFsmFsmStageStatus
}

cfprSwFcSanBorderFsmStageInstanceId OBJECT-TYPE
    SYNTAX       CfprManagedObjectId
    MAX-ACCESS   not-accessible
    STATUS       current
    DESCRIPTION
        "Instance identifier of the managed object."
    ::= { cfprSwFcSanBorderFsmStageEntry 1 }

cfprSwFcSanBorderFsmStageDn OBJECT-TYPE
    SYNTAX       CfprManagedObjectDn
    MAX-ACCESS   read-only
    STATUS       current
    DESCRIPTION
        "Cisco Firepower sw:FcSanBorderFsmStage:dn managed
        object property"
    ::= { cfprSwFcSanBorderFsmStageEntry 2 }

cfprSwFcSanBorderFsmStageRn OBJECT-TYPE
    SYNTAX       SnmpAdminString
    MAX-ACCESS   read-only
    STATUS       current
    DESCRIPTION
        "Cisco Firepower sw:FcSanBorderFsmStage:rn managed
        object property"
    ::= { cfprSwFcSanBorderFsmStageEntry 3 }

cfprSwFcSanBorderFsmStageDescrData OBJECT-TYPE
    SYNTAX       SnmpAdminString
    MAX-ACCESS   read-only
    STATUS       current
    DESCRIPTION
        "Cisco Firepower sw:FcSanBorderFsmStage:descr managed
        object property"
    ::= { cfprSwFcSanBorderFsmStageEntry 4 }

cfprSwFcSanBorderFsmStageLastUpdateTime OBJECT-TYPE
    SYNTAX       DateAndTime
    MAX-ACCESS   read-only
    STATUS       current
    DESCRIPTION
        "Cisco Firepower sw:FcSanBorderFsmStage:lastUpdateTime
        managed object property"
    ::= { cfprSwFcSanBorderFsmStageEntry 5 }

cfprSwFcSanBorderFsmStageName OBJECT-TYPE
    SYNTAX       CfprSwFcSanBorderFsmStageName
    MAX-ACCESS   read-only
    STATUS       current
    DESCRIPTION
        "Cisco Firepower sw:FcSanBorderFsmStage:name managed
        object property"
    ::= { cfprSwFcSanBorderFsmStageEntry 6 }

cfprSwFcSanBorderFsmStageOrder OBJECT-TYPE
    SYNTAX       Gauge32
    MAX-ACCESS   read-only
    STATUS       current
    DESCRIPTION
        "Cisco Firepower sw:FcSanBorderFsmStage:order managed
        object property"
    ::= { cfprSwFcSanBorderFsmStageEntry 7 }

cfprSwFcSanBorderFsmStageRetry OBJECT-TYPE
    SYNTAX       Gauge32
    MAX-ACCESS   read-only
    STATUS       current
    DESCRIPTION
        "Cisco Firepower sw:FcSanBorderFsmStage:retry managed
        object property"
    ::= { cfprSwFcSanBorderFsmStageEntry 8 }

cfprSwFcSanBorderFsmStageStageStatus OBJECT-TYPE
    SYNTAX       CfprFsmFsmStageStatus
    MAX-ACCESS   read-only
    STATUS       current
    DESCRIPTION
        "Cisco Firepower sw:FcSanBorderFsmStage:stageStatus
        managed object property"
    ::= { cfprSwFcSanBorderFsmStageEntry 9 }

cfprSwFcSanBorderFsmTaskTable OBJECT-TYPE
    SYNTAX           SEQUENCE OF CfprSwFcSanBorderFsmTaskEntry
    MAX-ACCESS       not-accessible
    STATUS           current
    DESCRIPTION
        "Cisco Firepower sw:FcSanBorderFsmTask managed object table"
    ::= { cfprSwObjects 47 }

cfprSwFcSanBorderFsmTaskEntry OBJECT-TYPE
    SYNTAX           CfprSwFcSanBorderFsmTaskEntry
    MAX-ACCESS       not-accessible
    STATUS           current
    DESCRIPTION
        "Entry for the cfprSwFcSanBorderFsmTaskTable table."
    INDEX { cfprSwFcSanBorderFsmTaskInstanceId }
    ::= { cfprSwFcSanBorderFsmTaskTable 1 }

CfprSwFcSanBorderFsmTaskEntry ::= SEQUENCE {
    cfprSwFcSanBorderFsmTaskInstanceId                               CfprManagedObjectId,
    cfprSwFcSanBorderFsmTaskDn                                       CfprManagedObjectDn,
    cfprSwFcSanBorderFsmTaskRn                                       SnmpAdminString,
    cfprSwFcSanBorderFsmTaskCompletion                               CfprFsmCompletion,
    cfprSwFcSanBorderFsmTaskFlags                                    CfprFsmFlags,
    cfprSwFcSanBorderFsmTaskItem                                     CfprSwFcSanBorderFsmTaskItem,
    cfprSwFcSanBorderFsmTaskSeqId                                    Gauge32
}

cfprSwFcSanBorderFsmTaskInstanceId OBJECT-TYPE
    SYNTAX       CfprManagedObjectId
    MAX-ACCESS   not-accessible
    STATUS       current
    DESCRIPTION
        "Instance identifier of the managed object."
    ::= { cfprSwFcSanBorderFsmTaskEntry 1 }

cfprSwFcSanBorderFsmTaskDn OBJECT-TYPE
    SYNTAX       CfprManagedObjectDn
    MAX-ACCESS   read-only
    STATUS       current
    DESCRIPTION
        "Cisco Firepower sw:FcSanBorderFsmTask:dn managed object property"
    ::= { cfprSwFcSanBorderFsmTaskEntry 2 }

cfprSwFcSanBorderFsmTaskRn OBJECT-TYPE
    SYNTAX       SnmpAdminString
    MAX-ACCESS   read-only
    STATUS       current
    DESCRIPTION
        "Cisco Firepower sw:FcSanBorderFsmTask:rn managed object property"
    ::= { cfprSwFcSanBorderFsmTaskEntry 3 }

cfprSwFcSanBorderFsmTaskCompletion OBJECT-TYPE
    SYNTAX       CfprFsmCompletion
    MAX-ACCESS   read-only
    STATUS       current
    DESCRIPTION
        "Cisco Firepower sw:FcSanBorderFsmTask:completion
        managed object property"
    ::= { cfprSwFcSanBorderFsmTaskEntry 4 }

cfprSwFcSanBorderFsmTaskFlags OBJECT-TYPE
    SYNTAX       CfprFsmFlags
    MAX-ACCESS   read-only
    STATUS       current
    DESCRIPTION
        "Cisco Firepower sw:FcSanBorderFsmTask:flags managed
        object property"
    ::= { cfprSwFcSanBorderFsmTaskEntry 5 }

cfprSwFcSanBorderFsmTaskItem OBJECT-TYPE
    SYNTAX       CfprSwFcSanBorderFsmTaskItem
    MAX-ACCESS   read-only
    STATUS       current
    DESCRIPTION
        "Cisco Firepower sw:FcSanBorderFsmTask:item managed
        object property"
    ::= { cfprSwFcSanBorderFsmTaskEntry 6 }

cfprSwFcSanBorderFsmTaskSeqId OBJECT-TYPE
    SYNTAX       Gauge32
    MAX-ACCESS   read-only
    STATUS       current
    DESCRIPTION
        "Cisco Firepower sw:FcSanBorderFsmTask:seqId managed
        object property"
    ::= { cfprSwFcSanBorderFsmTaskEntry 7 }

cfprSwFcSanEpTable OBJECT-TYPE
    SYNTAX           SEQUENCE OF CfprSwFcSanEpEntry
    MAX-ACCESS       not-accessible
    STATUS           current
    DESCRIPTION
        "Cisco Firepower sw:FcSanEp managed object table"
    ::= { cfprSwObjects 48 }

cfprSwFcSanEpEntry OBJECT-TYPE
    SYNTAX           CfprSwFcSanEpEntry
    MAX-ACCESS       not-accessible
    STATUS           current
    DESCRIPTION
        "Entry for the cfprSwFcSanEpTable table."
    INDEX { cfprSwFcSanEpInstanceId }
    ::= { cfprSwFcSanEpTable 1 }

CfprSwFcSanEpEntry ::= SEQUENCE {
    cfprSwFcSanEpInstanceId                                          CfprManagedObjectId,
    cfprSwFcSanEpDn                                                  CfprManagedObjectDn,
    cfprSwFcSanEpRn                                                  SnmpAdminString,
    cfprSwFcSanEpAdminSpeed                                          CfprPortSpeed,
    cfprSwFcSanEpAdminState                                          CfprFabricAdminState,
    cfprSwFcSanEpAggrPortId                                          Gauge32,
    cfprSwFcSanEpChassisId                                           Gauge32,
    cfprSwFcSanEpEpDn                                                SnmpAdminString,
    cfprSwFcSanEpFillPattern                                         CfprFabricFillPattern,
    cfprSwFcSanEpIfRole                                              CfprSwSanEpIfRole,
    cfprSwFcSanEpIfType                                              CfprSwPIoEpIfType,
    cfprSwFcSanEpLc                                                  CfprSwPIoEpLc,
    cfprSwFcSanEpLocale                                              CfprSwBorderEpLocale,
    cfprSwFcSanEpName                                                SnmpAdminString,
    cfprSwFcSanEpPcId                                                Gauge32,
    cfprSwFcSanEpPeerAggrPortId                                      Gauge32,
    cfprSwFcSanEpPeerChassisId                                       Gauge32,
    cfprSwFcSanEpPeerDn                                              SnmpAdminString,
    cfprSwFcSanEpPeerPortId                                          Gauge32,
    cfprSwFcSanEpPeerSlotId                                          Gauge32,
    cfprSwFcSanEpPortId                                              Gauge32,
    cfprSwFcSanEpPortVsanId                                          Gauge32,
    cfprSwFcSanEpSlotId                                              Gauge32,
    cfprSwFcSanEpSwitchId                                            CfprNetworkSwitchId,
    cfprSwFcSanEpTransport                                           CfprSwFcSanEpTransport,
    cfprSwFcSanEpType                                                CfprSwSanEpType
}

cfprSwFcSanEpInstanceId OBJECT-TYPE
    SYNTAX       CfprManagedObjectId
    MAX-ACCESS   not-accessible
    STATUS       current
    DESCRIPTION
        "Instance identifier of the managed object."
    ::= { cfprSwFcSanEpEntry 1 }

cfprSwFcSanEpDn OBJECT-TYPE
    SYNTAX       CfprManagedObjectDn
    MAX-ACCESS   read-only
    STATUS       current
    DESCRIPTION
        "Cisco Firepower sw:FcSanEp:dn managed object property"
    ::= { cfprSwFcSanEpEntry 2 }

cfprSwFcSanEpRn OBJECT-TYPE
    SYNTAX       SnmpAdminString
    MAX-ACCESS   read-only
    STATUS       current
    DESCRIPTION
        "Cisco Firepower sw:FcSanEp:rn managed object property"
    ::= { cfprSwFcSanEpEntry 3 }

cfprSwFcSanEpAdminSpeed OBJECT-TYPE
    SYNTAX       CfprPortSpeed
    MAX-ACCESS   read-only
    STATUS       current
    DESCRIPTION
        "Cisco Firepower sw:FcSanEp:adminSpeed managed object property"
    ::= { cfprSwFcSanEpEntry 4 }

cfprSwFcSanEpAdminState OBJECT-TYPE
    SYNTAX       CfprFabricAdminState
    MAX-ACCESS   read-only
    STATUS       current
    DESCRIPTION
        "Cisco Firepower sw:FcSanEp:adminState managed object property"
    ::= { cfprSwFcSanEpEntry 5 }

cfprSwFcSanEpAggrPortId OBJECT-TYPE
    SYNTAX       Gauge32
    MAX-ACCESS   read-only
    STATUS       current
    DESCRIPTION
        "Cisco Firepower sw:FcSanEp:aggrPortId managed object property"
    ::= { cfprSwFcSanEpEntry 6 }

cfprSwFcSanEpChassisId OBJECT-TYPE
    SYNTAX       Gauge32
    MAX-ACCESS   read-only
    STATUS       current
    DESCRIPTION
        "Cisco Firepower sw:FcSanEp:chassisId managed object property"
    ::= { cfprSwFcSanEpEntry 7 }

cfprSwFcSanEpEpDn OBJECT-TYPE
    SYNTAX       SnmpAdminString
    MAX-ACCESS   read-only
    STATUS       current
    DESCRIPTION
        "Cisco Firepower sw:FcSanEp:epDn managed object property"
    ::= { cfprSwFcSanEpEntry 8 }

cfprSwFcSanEpFillPattern OBJECT-TYPE
    SYNTAX       CfprFabricFillPattern
    MAX-ACCESS   read-only
    STATUS       current
    DESCRIPTION
        "Cisco Firepower sw:FcSanEp:fillPattern managed object property"
    ::= { cfprSwFcSanEpEntry 9 }

cfprSwFcSanEpIfRole OBJECT-TYPE
    SYNTAX       CfprSwSanEpIfRole
    MAX-ACCESS   read-only
    STATUS       current
    DESCRIPTION
        "Cisco Firepower sw:FcSanEp:ifRole managed object property"
    ::= { cfprSwFcSanEpEntry 10 }

cfprSwFcSanEpIfType OBJECT-TYPE
    SYNTAX       CfprSwPIoEpIfType
    MAX-ACCESS   read-only
    STATUS       current
    DESCRIPTION
        "Cisco Firepower sw:FcSanEp:ifType managed object property"
    ::= { cfprSwFcSanEpEntry 11 }

cfprSwFcSanEpLc OBJECT-TYPE
    SYNTAX       CfprSwPIoEpLc
    MAX-ACCESS   read-only
    STATUS       current
    DESCRIPTION
        "Cisco Firepower sw:FcSanEp:lc managed object property"
    ::= { cfprSwFcSanEpEntry 12 }

cfprSwFcSanEpLocale OBJECT-TYPE
    SYNTAX       CfprSwBorderEpLocale
    MAX-ACCESS   read-only
    STATUS       current
    DESCRIPTION
        "Cisco Firepower sw:FcSanEp:locale managed object property"
    ::= { cfprSwFcSanEpEntry 13 }

cfprSwFcSanEpName OBJECT-TYPE
    SYNTAX       SnmpAdminString
    MAX-ACCESS   read-only
    STATUS       current
    DESCRIPTION
        "Cisco Firepower sw:FcSanEp:name managed object property"
    ::= { cfprSwFcSanEpEntry 14 }

cfprSwFcSanEpPcId OBJECT-TYPE
    SYNTAX       Gauge32
    MAX-ACCESS   read-only
    STATUS       current
    DESCRIPTION
        "Cisco Firepower sw:FcSanEp:pcId managed object property"
    ::= { cfprSwFcSanEpEntry 15 }

cfprSwFcSanEpPeerAggrPortId OBJECT-TYPE
    SYNTAX       Gauge32
    MAX-ACCESS   read-only
    STATUS       current
    DESCRIPTION
        "Cisco Firepower sw:FcSanEp:peerAggrPortId managed
        object property"
    ::= { cfprSwFcSanEpEntry 16 }

cfprSwFcSanEpPeerChassisId OBJECT-TYPE
    SYNTAX       Gauge32
    MAX-ACCESS   read-only
    STATUS       current
    DESCRIPTION
        "Cisco Firepower sw:FcSanEp:peerChassisId managed object property"
    ::= { cfprSwFcSanEpEntry 17 }

cfprSwFcSanEpPeerDn OBJECT-TYPE
    SYNTAX       SnmpAdminString
    MAX-ACCESS   read-only
    STATUS       current
    DESCRIPTION
        "Cisco Firepower sw:FcSanEp:peerDn managed object property"
    ::= { cfprSwFcSanEpEntry 18 }

cfprSwFcSanEpPeerPortId OBJECT-TYPE
    SYNTAX       Gauge32
    MAX-ACCESS   read-only
    STATUS       current
    DESCRIPTION
        "Cisco Firepower sw:FcSanEp:peerPortId managed object property"
    ::= { cfprSwFcSanEpEntry 19 }

cfprSwFcSanEpPeerSlotId OBJECT-TYPE
    SYNTAX       Gauge32
    MAX-ACCESS   read-only
    STATUS       current
    DESCRIPTION
        "Cisco Firepower sw:FcSanEp:peerSlotId managed object property"
    ::= { cfprSwFcSanEpEntry 20 }

cfprSwFcSanEpPortId OBJECT-TYPE
    SYNTAX       Gauge32
    MAX-ACCESS   read-only
    STATUS       current
    DESCRIPTION
        "Cisco Firepower sw:FcSanEp:portId managed object property"
    ::= { cfprSwFcSanEpEntry 21 }

cfprSwFcSanEpPortVsanId OBJECT-TYPE
    SYNTAX       Gauge32
    MAX-ACCESS   read-only
    STATUS       current
    DESCRIPTION
        "Cisco Firepower sw:FcSanEp:portVsanId managed object property"
    ::= { cfprSwFcSanEpEntry 22 }

cfprSwFcSanEpSlotId OBJECT-TYPE
    SYNTAX       Gauge32
    MAX-ACCESS   read-only
    STATUS       current
    DESCRIPTION
        "Cisco Firepower sw:FcSanEp:slotId managed object property"
    ::= { cfprSwFcSanEpEntry 23 }

cfprSwFcSanEpSwitchId OBJECT-TYPE
    SYNTAX       CfprNetworkSwitchId
    MAX-ACCESS   read-only
    STATUS       current
    DESCRIPTION
        "Cisco Firepower sw:FcSanEp:switchId managed object property"
    ::= { cfprSwFcSanEpEntry 24 }

cfprSwFcSanEpTransport OBJECT-TYPE
    SYNTAX       CfprSwFcSanEpTransport
    MAX-ACCESS   read-only
    STATUS       current
    DESCRIPTION
        "Cisco Firepower sw:FcSanEp:transport managed object property"
    ::= { cfprSwFcSanEpEntry 25 }

cfprSwFcSanEpType OBJECT-TYPE
    SYNTAX       CfprSwSanEpType
    MAX-ACCESS   read-only
    STATUS       current
    DESCRIPTION
        "Cisco Firepower sw:FcSanEp:type managed object property"
    ::= { cfprSwFcSanEpEntry 26 }

cfprSwFcSanMonTable OBJECT-TYPE
    SYNTAX           SEQUENCE OF CfprSwFcSanMonEntry
    MAX-ACCESS       not-accessible
    STATUS           current
    DESCRIPTION
        "Cisco Firepower sw:FcSanMon managed object table"
    ::= { cfprSwObjects 49 }

cfprSwFcSanMonEntry OBJECT-TYPE
    SYNTAX           CfprSwFcSanMonEntry
    MAX-ACCESS       not-accessible
    STATUS           current
    DESCRIPTION
        "Entry for the cfprSwFcSanMonTable table."
    INDEX { cfprSwFcSanMonInstanceId }
    ::= { cfprSwFcSanMonTable 1 }

CfprSwFcSanMonEntry ::= SEQUENCE {
    cfprSwFcSanMonInstanceId                                         CfprManagedObjectId,
    cfprSwFcSanMonDn                                                 CfprManagedObjectDn,
    cfprSwFcSanMonRn                                                 SnmpAdminString,
    cfprSwFcSanMonLocale                                             CfprSwMonDomainLocale,
    cfprSwFcSanMonName                                               SnmpAdminString,
    cfprSwFcSanMonSwitchId                                           CfprNetworkSwitchId,
    cfprSwFcSanMonTransport                                          CfprSwFcSanMonTransport,
    cfprSwFcSanMonType                                               CfprSwSanMonType
}

cfprSwFcSanMonInstanceId OBJECT-TYPE
    SYNTAX       CfprManagedObjectId
    MAX-ACCESS   not-accessible
    STATUS       current
    DESCRIPTION
        "Instance identifier of the managed object."
    ::= { cfprSwFcSanMonEntry 1 }

cfprSwFcSanMonDn OBJECT-TYPE
    SYNTAX       CfprManagedObjectDn
    MAX-ACCESS   read-only
    STATUS       current
    DESCRIPTION
        "Cisco Firepower sw:FcSanMon:dn managed object property"
    ::= { cfprSwFcSanMonEntry 2 }

cfprSwFcSanMonRn OBJECT-TYPE
    SYNTAX       SnmpAdminString
    MAX-ACCESS   read-only
    STATUS       current
    DESCRIPTION
        "Cisco Firepower sw:FcSanMon:rn managed object property"
    ::= { cfprSwFcSanMonEntry 3 }

cfprSwFcSanMonLocale OBJECT-TYPE
    SYNTAX       CfprSwMonDomainLocale
    MAX-ACCESS   read-only
    STATUS       current
    DESCRIPTION
        "Cisco Firepower sw:FcSanMon:locale managed object property"
    ::= { cfprSwFcSanMonEntry 4 }

cfprSwFcSanMonName OBJECT-TYPE
    SYNTAX       SnmpAdminString
    MAX-ACCESS   read-only
    STATUS       current
    DESCRIPTION
        "Cisco Firepower sw:FcSanMon:name managed object property"
    ::= { cfprSwFcSanMonEntry 5 }

cfprSwFcSanMonSwitchId OBJECT-TYPE
    SYNTAX       CfprNetworkSwitchId
    MAX-ACCESS   read-only
    STATUS       current
    DESCRIPTION
        "Cisco Firepower sw:FcSanMon:switchId managed object property"
    ::= { cfprSwFcSanMonEntry 6 }

cfprSwFcSanMonTransport OBJECT-TYPE
    SYNTAX       CfprSwFcSanMonTransport
    MAX-ACCESS   read-only
    STATUS       current
    DESCRIPTION
        "Cisco Firepower sw:FcSanMon:transport managed object property"
    ::= { cfprSwFcSanMonEntry 7 }

cfprSwFcSanMonType OBJECT-TYPE
    SYNTAX       CfprSwSanMonType
    MAX-ACCESS   read-only
    STATUS       current
    DESCRIPTION
        "Cisco Firepower sw:FcSanMon:type managed object property"
    ::= { cfprSwFcSanMonEntry 8 }

cfprSwFcSanPcTable OBJECT-TYPE
    SYNTAX           SEQUENCE OF CfprSwFcSanPcEntry
    MAX-ACCESS       not-accessible
    STATUS           current
    DESCRIPTION
        "Cisco Firepower sw:FcSanPc managed object table"
    ::= { cfprSwObjects 50 }

cfprSwFcSanPcEntry OBJECT-TYPE
    SYNTAX           CfprSwFcSanPcEntry
    MAX-ACCESS       not-accessible
    STATUS           current
    DESCRIPTION
        "Entry for the cfprSwFcSanPcTable table."
    INDEX { cfprSwFcSanPcInstanceId }
    ::= { cfprSwFcSanPcTable 1 }

CfprSwFcSanPcEntry ::= SEQUENCE {
    cfprSwFcSanPcInstanceId                                          CfprManagedObjectId,
    cfprSwFcSanPcDn                                                  CfprManagedObjectDn,
    cfprSwFcSanPcRn                                                  SnmpAdminString,
    cfprSwFcSanPcAdminSpeed                                          CfprPortSpeed,
    cfprSwFcSanPcAdminState                                          CfprFabricAdminState,
    cfprSwFcSanPcEpDn                                                SnmpAdminString,
    cfprSwFcSanPcIfRole                                              CfprSwSanPcIfRole,
    cfprSwFcSanPcIfType                                              CfprSwCIoEpIfType,
    cfprSwFcSanPcLocale                                              CfprSwBorderPcLocale,
    cfprSwFcSanPcMonTrafDir                                          CfprFabricTrafficDirection,
    cfprSwFcSanPcName                                                SnmpAdminString,
    cfprSwFcSanPcPcId                                                Gauge32,
    cfprSwFcSanPcPeerDn                                              SnmpAdminString,
    cfprSwFcSanPcPortId                                              Gauge32,
    cfprSwFcSanPcPortVsanId                                          Gauge32,
    cfprSwFcSanPcSwitchId                                            CfprNetworkSwitchId,
    cfprSwFcSanPcTransport                                           CfprSwFcSanPcTransport,
    cfprSwFcSanPcType                                                CfprSwSanPcType
}

cfprSwFcSanPcInstanceId OBJECT-TYPE
    SYNTAX       CfprManagedObjectId
    MAX-ACCESS   not-accessible
    STATUS       current
    DESCRIPTION
        "Instance identifier of the managed object."
    ::= { cfprSwFcSanPcEntry 1 }

cfprSwFcSanPcDn OBJECT-TYPE
    SYNTAX       CfprManagedObjectDn
    MAX-ACCESS   read-only
    STATUS       current
    DESCRIPTION
        "Cisco Firepower sw:FcSanPc:dn managed object property"
    ::= { cfprSwFcSanPcEntry 2 }

cfprSwFcSanPcRn OBJECT-TYPE
    SYNTAX       SnmpAdminString
    MAX-ACCESS   read-only
    STATUS       current
    DESCRIPTION
        "Cisco Firepower sw:FcSanPc:rn managed object property"
    ::= { cfprSwFcSanPcEntry 3 }

cfprSwFcSanPcAdminSpeed OBJECT-TYPE
    SYNTAX       CfprPortSpeed
    MAX-ACCESS   read-only
    STATUS       current
    DESCRIPTION
        "Cisco Firepower sw:FcSanPc:adminSpeed managed object property"
    ::= { cfprSwFcSanPcEntry 4 }

cfprSwFcSanPcAdminState OBJECT-TYPE
    SYNTAX       CfprFabricAdminState
    MAX-ACCESS   read-only
    STATUS       current
    DESCRIPTION
        "Cisco Firepower sw:FcSanPc:adminState managed object property"
    ::= { cfprSwFcSanPcEntry 5 }

cfprSwFcSanPcEpDn OBJECT-TYPE
    SYNTAX       SnmpAdminString
    MAX-ACCESS   read-only
    STATUS       current
    DESCRIPTION
        "Cisco Firepower sw:FcSanPc:epDn managed object property"
    ::= { cfprSwFcSanPcEntry 6 }

cfprSwFcSanPcIfRole OBJECT-TYPE
    SYNTAX       CfprSwSanPcIfRole
    MAX-ACCESS   read-only
    STATUS       current
    DESCRIPTION
        "Cisco Firepower sw:FcSanPc:ifRole managed object property"
    ::= { cfprSwFcSanPcEntry 7 }

cfprSwFcSanPcIfType OBJECT-TYPE
    SYNTAX       CfprSwCIoEpIfType
    MAX-ACCESS   read-only
    STATUS       current
    DESCRIPTION
        "Cisco Firepower sw:FcSanPc:ifType managed object property"
    ::= { cfprSwFcSanPcEntry 8 }

cfprSwFcSanPcLocale OBJECT-TYPE
    SYNTAX       CfprSwBorderPcLocale
    MAX-ACCESS   read-only
    STATUS       current
    DESCRIPTION
        "Cisco Firepower sw:FcSanPc:locale managed object property"
    ::= { cfprSwFcSanPcEntry 9 }

cfprSwFcSanPcMonTrafDir OBJECT-TYPE
    SYNTAX       CfprFabricTrafficDirection
    MAX-ACCESS   read-only
    STATUS       current
    DESCRIPTION
        "Cisco Firepower sw:FcSanPc:monTrafDir managed object property"
    ::= { cfprSwFcSanPcEntry 10 }

cfprSwFcSanPcName OBJECT-TYPE
    SYNTAX       SnmpAdminString
    MAX-ACCESS   read-only
    STATUS       current
    DESCRIPTION
        "Cisco Firepower sw:FcSanPc:name managed object property"
    ::= { cfprSwFcSanPcEntry 11 }

cfprSwFcSanPcPcId OBJECT-TYPE
    SYNTAX       Gauge32
    MAX-ACCESS   read-only
    STATUS       current
    DESCRIPTION
        "Cisco Firepower sw:FcSanPc:pcId managed object property"
    ::= { cfprSwFcSanPcEntry 12 }

cfprSwFcSanPcPeerDn OBJECT-TYPE
    SYNTAX       SnmpAdminString
    MAX-ACCESS   read-only
    STATUS       current
    DESCRIPTION
        "Cisco Firepower sw:FcSanPc:peerDn managed object property"
    ::= { cfprSwFcSanPcEntry 13 }

cfprSwFcSanPcPortId OBJECT-TYPE
    SYNTAX       Gauge32
    MAX-ACCESS   read-only
    STATUS       current
    DESCRIPTION
        "Cisco Firepower sw:FcSanPc:portId managed object property"
    ::= { cfprSwFcSanPcEntry 14 }

cfprSwFcSanPcPortVsanId OBJECT-TYPE
    SYNTAX       Gauge32
    MAX-ACCESS   read-only
    STATUS       current
    DESCRIPTION
        "Cisco Firepower sw:FcSanPc:portVsanId managed object property"
    ::= { cfprSwFcSanPcEntry 15 }

cfprSwFcSanPcSwitchId OBJECT-TYPE
    SYNTAX       CfprNetworkSwitchId
    MAX-ACCESS   read-only
    STATUS       current
    DESCRIPTION
        "Cisco Firepower sw:FcSanPc:switchId managed object property"
    ::= { cfprSwFcSanPcEntry 16 }

cfprSwFcSanPcTransport OBJECT-TYPE
    SYNTAX       CfprSwFcSanPcTransport
    MAX-ACCESS   read-only
    STATUS       current
    DESCRIPTION
        "Cisco Firepower sw:FcSanPc:transport managed object property"
    ::= { cfprSwFcSanPcEntry 17 }

cfprSwFcSanPcType OBJECT-TYPE
    SYNTAX       CfprSwSanPcType
    MAX-ACCESS   read-only
    STATUS       current
    DESCRIPTION
        "Cisco Firepower sw:FcSanPc:type managed object property"
    ::= { cfprSwFcSanPcEntry 18 }

cfprSwFcServerZoneGroupTable OBJECT-TYPE
    SYNTAX           SEQUENCE OF CfprSwFcServerZoneGroupEntry
    MAX-ACCESS       not-accessible
    STATUS           current
    DESCRIPTION
        "Cisco Firepower sw:FcServerZoneGroup managed object table"
    ::= { cfprSwObjects 51 }

cfprSwFcServerZoneGroupEntry OBJECT-TYPE
    SYNTAX           CfprSwFcServerZoneGroupEntry
    MAX-ACCESS       not-accessible
    STATUS           current
    DESCRIPTION
        "Entry for the cfprSwFcServerZoneGroupTable table."
    INDEX { cfprSwFcServerZoneGroupInstanceId }
    ::= { cfprSwFcServerZoneGroupTable 1 }

CfprSwFcServerZoneGroupEntry ::= SEQUENCE {
    cfprSwFcServerZoneGroupInstanceId                                CfprManagedObjectId,
    cfprSwFcServerZoneGroupDn                                        CfprManagedObjectDn,
    cfprSwFcServerZoneGroupRn                                        SnmpAdminString,
    cfprSwFcServerZoneGroupEpDn                                      SnmpAdminString,
    cfprSwFcServerZoneGroupId                                        Gauge32,
    cfprSwFcServerZoneGroupLc                                        CfprSwFcServerZoneGroupLc,
    cfprSwFcServerZoneGroupName                                      SnmpAdminString,
    cfprSwFcServerZoneGroupPeerDn                                    SnmpAdminString,
    cfprSwFcServerZoneGroupServerDn                                  SnmpAdminString
}

cfprSwFcServerZoneGroupInstanceId OBJECT-TYPE
    SYNTAX       CfprManagedObjectId
    MAX-ACCESS   not-accessible
    STATUS       current
    DESCRIPTION
        "Instance identifier of the managed object."
    ::= { cfprSwFcServerZoneGroupEntry 1 }

cfprSwFcServerZoneGroupDn OBJECT-TYPE
    SYNTAX       CfprManagedObjectDn
    MAX-ACCESS   read-only
    STATUS       current
    DESCRIPTION
        "Cisco Firepower sw:FcServerZoneGroup:dn managed object property"
    ::= { cfprSwFcServerZoneGroupEntry 2 }

cfprSwFcServerZoneGroupRn OBJECT-TYPE
    SYNTAX       SnmpAdminString
    MAX-ACCESS   read-only
    STATUS       current
    DESCRIPTION
        "Cisco Firepower sw:FcServerZoneGroup:rn managed object property"
    ::= { cfprSwFcServerZoneGroupEntry 3 }

cfprSwFcServerZoneGroupEpDn OBJECT-TYPE
    SYNTAX       SnmpAdminString
    MAX-ACCESS   read-only
    STATUS       current
    DESCRIPTION
        "Cisco Firepower sw:FcServerZoneGroup:epDn managed
        object property"
    ::= { cfprSwFcServerZoneGroupEntry 4 }

cfprSwFcServerZoneGroupId OBJECT-TYPE
    SYNTAX       Gauge32
    MAX-ACCESS   read-only
    STATUS       current
    DESCRIPTION
        "Cisco Firepower sw:FcServerZoneGroup:id managed object property"
    ::= { cfprSwFcServerZoneGroupEntry 5 }

cfprSwFcServerZoneGroupLc OBJECT-TYPE
    SYNTAX       CfprSwFcServerZoneGroupLc
    MAX-ACCESS   read-only
    STATUS       current
    DESCRIPTION
        "Cisco Firepower sw:FcServerZoneGroup:lc managed object property"
    ::= { cfprSwFcServerZoneGroupEntry 6 }

cfprSwFcServerZoneGroupName OBJECT-TYPE
    SYNTAX       SnmpAdminString
    MAX-ACCESS   read-only
    STATUS       current
    DESCRIPTION
        "Cisco Firepower sw:FcServerZoneGroup:name managed
        object property"
    ::= { cfprSwFcServerZoneGroupEntry 7 }

cfprSwFcServerZoneGroupPeerDn OBJECT-TYPE
    SYNTAX       SnmpAdminString
    MAX-ACCESS   read-only
    STATUS       current
    DESCRIPTION
        "Cisco Firepower sw:FcServerZoneGroup:peerDn managed
        object property"
    ::= { cfprSwFcServerZoneGroupEntry 8 }

cfprSwFcServerZoneGroupServerDn OBJECT-TYPE
    SYNTAX       SnmpAdminString
    MAX-ACCESS   read-only
    STATUS       current
    DESCRIPTION
        "Cisco Firepower sw:FcServerZoneGroup:serverDn
        managed object property"
    ::= { cfprSwFcServerZoneGroupEntry 9 }

cfprSwFcZoneTable OBJECT-TYPE
    SYNTAX           SEQUENCE OF CfprSwFcZoneEntry
    MAX-ACCESS       not-accessible
    STATUS           current
    DESCRIPTION
        "Cisco Firepower sw:FcZone managed object table"
    ::= { cfprSwObjects 52 }

cfprSwFcZoneEntry OBJECT-TYPE
    SYNTAX           CfprSwFcZoneEntry
    MAX-ACCESS       not-accessible
    STATUS           current
    DESCRIPTION
        "Entry for the cfprSwFcZoneTable table."
    INDEX { cfprSwFcZoneInstanceId }
    ::= { cfprSwFcZoneTable 1 }

CfprSwFcZoneEntry ::= SEQUENCE {
    cfprSwFcZoneInstanceId                                           CfprManagedObjectId,
    cfprSwFcZoneDn                                                   CfprManagedObjectDn,
    cfprSwFcZoneRn                                                   SnmpAdminString,
    cfprSwFcZoneId                                                   Gauge32,
    cfprSwFcZoneIdentity                                             SnmpAdminString,
    cfprSwFcZoneLc                                                   CfprSwFcZoneLc,
    cfprSwFcZoneName                                                 SnmpAdminString,
    cfprSwFcZoneOperState                                            CfprLsFcZoneState,
    cfprSwFcZonePeerDn                                               SnmpAdminString
}

cfprSwFcZoneInstanceId OBJECT-TYPE
    SYNTAX       CfprManagedObjectId
    MAX-ACCESS   not-accessible
    STATUS       current
    DESCRIPTION
        "Instance identifier of the managed object."
    ::= { cfprSwFcZoneEntry 1 }

cfprSwFcZoneDn OBJECT-TYPE
    SYNTAX       CfprManagedObjectDn
    MAX-ACCESS   read-only
    STATUS       current
    DESCRIPTION
        "Cisco Firepower sw:FcZone:dn managed object property"
    ::= { cfprSwFcZoneEntry 2 }

cfprSwFcZoneRn OBJECT-TYPE
    SYNTAX       SnmpAdminString
    MAX-ACCESS   read-only
    STATUS       current
    DESCRIPTION
        "Cisco Firepower sw:FcZone:rn managed object property"
    ::= { cfprSwFcZoneEntry 3 }

cfprSwFcZoneId OBJECT-TYPE
    SYNTAX       Gauge32
    MAX-ACCESS   read-only
    STATUS       current
    DESCRIPTION
        "Cisco Firepower sw:FcZone:id managed object property"
    ::= { cfprSwFcZoneEntry 4 }

cfprSwFcZoneIdentity OBJECT-TYPE
    SYNTAX       SnmpAdminString
    MAX-ACCESS   read-only
    STATUS       current
    DESCRIPTION
        "Cisco Firepower sw:FcZone:identity managed object property"
    ::= { cfprSwFcZoneEntry 5 }

cfprSwFcZoneLc OBJECT-TYPE
    SYNTAX       CfprSwFcZoneLc
    MAX-ACCESS   read-only
    STATUS       current
    DESCRIPTION
        "Cisco Firepower sw:FcZone:lc managed object property"
    ::= { cfprSwFcZoneEntry 6 }

cfprSwFcZoneName OBJECT-TYPE
    SYNTAX       SnmpAdminString
    MAX-ACCESS   read-only
    STATUS       current
    DESCRIPTION
        "Cisco Firepower sw:FcZone:name managed object property"
    ::= { cfprSwFcZoneEntry 7 }

cfprSwFcZoneOperState OBJECT-TYPE
    SYNTAX       CfprLsFcZoneState
    MAX-ACCESS   read-only
    STATUS       current
    DESCRIPTION
        "Cisco Firepower sw:FcZone:operState managed object property"
    ::= { cfprSwFcZoneEntry 8 }

cfprSwFcZonePeerDn OBJECT-TYPE
    SYNTAX       SnmpAdminString
    MAX-ACCESS   read-only
    STATUS       current
    DESCRIPTION
        "Cisco Firepower sw:FcZone:peerDn managed object property"
    ::= { cfprSwFcZoneEntry 9 }

cfprSwFcZoneSetTable OBJECT-TYPE
    SYNTAX           SEQUENCE OF CfprSwFcZoneSetEntry
    MAX-ACCESS       not-accessible
    STATUS           current
    DESCRIPTION
        "Cisco Firepower sw:FcZoneSet managed object table"
    ::= { cfprSwObjects 53 }

cfprSwFcZoneSetEntry OBJECT-TYPE
    SYNTAX           CfprSwFcZoneSetEntry
    MAX-ACCESS       not-accessible
    STATUS           current
    DESCRIPTION
        "Entry for the cfprSwFcZoneSetTable table."
    INDEX { cfprSwFcZoneSetInstanceId }
    ::= { cfprSwFcZoneSetTable 1 }

CfprSwFcZoneSetEntry ::= SEQUENCE {
    cfprSwFcZoneSetInstanceId                                        CfprManagedObjectId,
    cfprSwFcZoneSetDn                                                CfprManagedObjectDn,
    cfprSwFcZoneSetRn                                                SnmpAdminString,
    cfprSwFcZoneSetCurrentZonePrefix                                 SnmpAdminString,
    cfprSwFcZoneSetLc                                                CfprSwFcZoneSetLc,
    cfprSwFcZoneSetName                                              SnmpAdminString,
    cfprSwFcZoneSetOldZonePrefix                                     SnmpAdminString
}

cfprSwFcZoneSetInstanceId OBJECT-TYPE
    SYNTAX       CfprManagedObjectId
    MAX-ACCESS   not-accessible
    STATUS       current
    DESCRIPTION
        "Instance identifier of the managed object."
    ::= { cfprSwFcZoneSetEntry 1 }

cfprSwFcZoneSetDn OBJECT-TYPE
    SYNTAX       CfprManagedObjectDn
    MAX-ACCESS   read-only
    STATUS       current
    DESCRIPTION
        "Cisco Firepower sw:FcZoneSet:dn managed object property"
    ::= { cfprSwFcZoneSetEntry 2 }

cfprSwFcZoneSetRn OBJECT-TYPE
    SYNTAX       SnmpAdminString
    MAX-ACCESS   read-only
    STATUS       current
    DESCRIPTION
        "Cisco Firepower sw:FcZoneSet:rn managed object property"
    ::= { cfprSwFcZoneSetEntry 3 }

cfprSwFcZoneSetCurrentZonePrefix OBJECT-TYPE
    SYNTAX       SnmpAdminString
    MAX-ACCESS   read-only
    STATUS       current
    DESCRIPTION
        "Cisco Firepower sw:FcZoneSet:currentZonePrefix
        managed object property"
    ::= { cfprSwFcZoneSetEntry 4 }

cfprSwFcZoneSetLc OBJECT-TYPE
    SYNTAX       CfprSwFcZoneSetLc
    MAX-ACCESS   read-only
    STATUS       current
    DESCRIPTION
        "Cisco Firepower sw:FcZoneSet:lc managed object property"
    ::= { cfprSwFcZoneSetEntry 5 }

cfprSwFcZoneSetName OBJECT-TYPE
    SYNTAX       SnmpAdminString
    MAX-ACCESS   read-only
    STATUS       current
    DESCRIPTION
        "Cisco Firepower sw:FcZoneSet:name managed object property"
    ::= { cfprSwFcZoneSetEntry 6 }

cfprSwFcZoneSetOldZonePrefix OBJECT-TYPE
    SYNTAX       SnmpAdminString
    MAX-ACCESS   read-only
    STATUS       current
    DESCRIPTION
        "Cisco Firepower sw:FcZoneSet:oldZonePrefix managed
        object property"
    ::= { cfprSwFcZoneSetEntry 7 }

cfprSwFcoeEstcEpTable OBJECT-TYPE
    SYNTAX           SEQUENCE OF CfprSwFcoeEstcEpEntry
    MAX-ACCESS       not-accessible
    STATUS           current
    DESCRIPTION
        "Cisco Firepower sw:FcoeEstcEp managed object table"
    ::= { cfprSwObjects 54 }

cfprSwFcoeEstcEpEntry OBJECT-TYPE
    SYNTAX           CfprSwFcoeEstcEpEntry
    MAX-ACCESS       not-accessible
    STATUS           current
    DESCRIPTION
        "Entry for the cfprSwFcoeEstcEpTable table."
    INDEX { cfprSwFcoeEstcEpInstanceId }
    ::= { cfprSwFcoeEstcEpTable 1 }

CfprSwFcoeEstcEpEntry ::= SEQUENCE {
    cfprSwFcoeEstcEpInstanceId                                       CfprManagedObjectId,
    cfprSwFcoeEstcEpDn                                               CfprManagedObjectDn,
    cfprSwFcoeEstcEpRn                                               SnmpAdminString,
    cfprSwFcoeEstcEpAdminState                                       CfprFabricAdminState,
    cfprSwFcoeEstcEpAggrPortId                                       Gauge32,
    cfprSwFcoeEstcEpChassisId                                        Gauge32,
    cfprSwFcoeEstcEpEpDn                                             SnmpAdminString,
    cfprSwFcoeEstcEpIfRole                                           CfprNetworkPortRole,
    cfprSwFcoeEstcEpIfType                                           CfprSwPIoEpIfType,
    cfprSwFcoeEstcEpLc                                               CfprSwPIoEpLc,
    cfprSwFcoeEstcEpLocale                                           CfprSwEstcEpLocale,
    cfprSwFcoeEstcEpName                                             SnmpAdminString,
    cfprSwFcoeEstcEpPeerAggrPortId                                   Gauge32,
    cfprSwFcoeEstcEpPeerChassisId                                    Gauge32,
    cfprSwFcoeEstcEpPeerDn                                           SnmpAdminString,
    cfprSwFcoeEstcEpPeerPortId                                       Gauge32,
    cfprSwFcoeEstcEpPeerSlotId                                       Gauge32,
    cfprSwFcoeEstcEpPeerState                                        CfprSwPeerStatus,
    cfprSwFcoeEstcEpPortId                                           Gauge32,
    cfprSwFcoeEstcEpSlotId                                           Gauge32,
    cfprSwFcoeEstcEpSwitchId                                         CfprNetworkSwitchId,
    cfprSwFcoeEstcEpTransport                                        CfprSwFcoeEstcEpTransport,
    cfprSwFcoeEstcEpType                                             CfprNetworkConnectionType
}

cfprSwFcoeEstcEpInstanceId OBJECT-TYPE
    SYNTAX       CfprManagedObjectId
    MAX-ACCESS   not-accessible
    STATUS       current
    DESCRIPTION
        "Instance identifier of the managed object."
    ::= { cfprSwFcoeEstcEpEntry 1 }

cfprSwFcoeEstcEpDn OBJECT-TYPE
    SYNTAX       CfprManagedObjectDn
    MAX-ACCESS   read-only
    STATUS       current
    DESCRIPTION
        "Cisco Firepower sw:FcoeEstcEp:dn managed object property"
    ::= { cfprSwFcoeEstcEpEntry 2 }

cfprSwFcoeEstcEpRn OBJECT-TYPE
    SYNTAX       SnmpAdminString
    MAX-ACCESS   read-only
    STATUS       current
    DESCRIPTION
        "Cisco Firepower sw:FcoeEstcEp:rn managed object property"
    ::= { cfprSwFcoeEstcEpEntry 3 }

cfprSwFcoeEstcEpAdminState OBJECT-TYPE
    SYNTAX       CfprFabricAdminState
    MAX-ACCESS   read-only
    STATUS       current
    DESCRIPTION
        "Cisco Firepower sw:FcoeEstcEp:adminState managed object property"
    ::= { cfprSwFcoeEstcEpEntry 4 }

cfprSwFcoeEstcEpAggrPortId OBJECT-TYPE
    SYNTAX       Gauge32
    MAX-ACCESS   read-only
    STATUS       current
    DESCRIPTION
        "Cisco Firepower sw:FcoeEstcEp:aggrPortId managed object property"
    ::= { cfprSwFcoeEstcEpEntry 5 }

cfprSwFcoeEstcEpChassisId OBJECT-TYPE
    SYNTAX       Gauge32
    MAX-ACCESS   read-only
    STATUS       current
    DESCRIPTION
        "Cisco Firepower sw:FcoeEstcEp:chassisId managed object property"
    ::= { cfprSwFcoeEstcEpEntry 6 }

cfprSwFcoeEstcEpEpDn OBJECT-TYPE
    SYNTAX       SnmpAdminString
    MAX-ACCESS   read-only
    STATUS       current
    DESCRIPTION
        "Cisco Firepower sw:FcoeEstcEp:epDn managed object property"
    ::= { cfprSwFcoeEstcEpEntry 7 }

cfprSwFcoeEstcEpIfRole OBJECT-TYPE
    SYNTAX       CfprNetworkPortRole
    MAX-ACCESS   read-only
    STATUS       current
    DESCRIPTION
        "Cisco Firepower sw:FcoeEstcEp:ifRole managed object property"
    ::= { cfprSwFcoeEstcEpEntry 8 }

cfprSwFcoeEstcEpIfType OBJECT-TYPE
    SYNTAX       CfprSwPIoEpIfType
    MAX-ACCESS   read-only
    STATUS       current
    DESCRIPTION
        "Cisco Firepower sw:FcoeEstcEp:ifType managed object property"
    ::= { cfprSwFcoeEstcEpEntry 9 }

cfprSwFcoeEstcEpLc OBJECT-TYPE
    SYNTAX       CfprSwPIoEpLc
    MAX-ACCESS   read-only
    STATUS       current
    DESCRIPTION
        "Cisco Firepower sw:FcoeEstcEp:lc managed object property"
    ::= { cfprSwFcoeEstcEpEntry 10 }

cfprSwFcoeEstcEpLocale OBJECT-TYPE
    SYNTAX       CfprSwEstcEpLocale
    MAX-ACCESS   read-only
    STATUS       current
    DESCRIPTION
        "Cisco Firepower sw:FcoeEstcEp:locale managed object property"
    ::= { cfprSwFcoeEstcEpEntry 11 }

cfprSwFcoeEstcEpName OBJECT-TYPE
    SYNTAX       SnmpAdminString
    MAX-ACCESS   read-only
    STATUS       current
    DESCRIPTION
        "Cisco Firepower sw:FcoeEstcEp:name managed object property"
    ::= { cfprSwFcoeEstcEpEntry 12 }

cfprSwFcoeEstcEpPeerAggrPortId OBJECT-TYPE
    SYNTAX       Gauge32
    MAX-ACCESS   read-only
    STATUS       current
    DESCRIPTION
        "Cisco Firepower sw:FcoeEstcEp:peerAggrPortId managed
        object property"
    ::= { cfprSwFcoeEstcEpEntry 13 }

cfprSwFcoeEstcEpPeerChassisId OBJECT-TYPE
    SYNTAX       Gauge32
    MAX-ACCESS   read-only
    STATUS       current
    DESCRIPTION
        "Cisco Firepower sw:FcoeEstcEp:peerChassisId managed
        object property"
    ::= { cfprSwFcoeEstcEpEntry 14 }

cfprSwFcoeEstcEpPeerDn OBJECT-TYPE
    SYNTAX       SnmpAdminString
    MAX-ACCESS   read-only
    STATUS       current
    DESCRIPTION
        "Cisco Firepower sw:FcoeEstcEp:peerDn managed object property"
    ::= { cfprSwFcoeEstcEpEntry 15 }

cfprSwFcoeEstcEpPeerPortId OBJECT-TYPE
    SYNTAX       Gauge32
    MAX-ACCESS   read-only
    STATUS       current
    DESCRIPTION
        "Cisco Firepower sw:FcoeEstcEp:peerPortId managed object property"
    ::= { cfprSwFcoeEstcEpEntry 16 }

cfprSwFcoeEstcEpPeerSlotId OBJECT-TYPE
    SYNTAX       Gauge32
    MAX-ACCESS   read-only
    STATUS       current
    DESCRIPTION
        "Cisco Firepower sw:FcoeEstcEp:peerSlotId managed object property"
    ::= { cfprSwFcoeEstcEpEntry 17 }

cfprSwFcoeEstcEpPeerState OBJECT-TYPE
    SYNTAX       CfprSwPeerStatus
    MAX-ACCESS   read-only
    STATUS       current
    DESCRIPTION
        "Cisco Firepower sw:FcoeEstcEp:peerState managed object property"
    ::= { cfprSwFcoeEstcEpEntry 18 }

cfprSwFcoeEstcEpPortId OBJECT-TYPE
    SYNTAX       Gauge32
    MAX-ACCESS   read-only
    STATUS       current
    DESCRIPTION
        "Cisco Firepower sw:FcoeEstcEp:portId managed object property"
    ::= { cfprSwFcoeEstcEpEntry 19 }

cfprSwFcoeEstcEpSlotId OBJECT-TYPE
    SYNTAX       Gauge32
    MAX-ACCESS   read-only
    STATUS       current
    DESCRIPTION
        "Cisco Firepower sw:FcoeEstcEp:slotId managed object property"
    ::= { cfprSwFcoeEstcEpEntry 20 }

cfprSwFcoeEstcEpSwitchId OBJECT-TYPE
    SYNTAX       CfprNetworkSwitchId
    MAX-ACCESS   read-only
    STATUS       current
    DESCRIPTION
        "Cisco Firepower sw:FcoeEstcEp:switchId managed object property"
    ::= { cfprSwFcoeEstcEpEntry 21 }

cfprSwFcoeEstcEpTransport OBJECT-TYPE
    SYNTAX       CfprSwFcoeEstcEpTransport
    MAX-ACCESS   read-only
    STATUS       current
    DESCRIPTION
        "Cisco Firepower sw:FcoeEstcEp:transport managed object property"
    ::= { cfprSwFcoeEstcEpEntry 22 }

cfprSwFcoeEstcEpType OBJECT-TYPE
    SYNTAX       CfprNetworkConnectionType
    MAX-ACCESS   read-only
    STATUS       current
    DESCRIPTION
        "Cisco Firepower sw:FcoeEstcEp:type managed object property"
    ::= { cfprSwFcoeEstcEpEntry 23 }

cfprSwFcoeSanEpTable OBJECT-TYPE
    SYNTAX           SEQUENCE OF CfprSwFcoeSanEpEntry
    MAX-ACCESS       not-accessible
    STATUS           current
    DESCRIPTION
        "Cisco Firepower sw:FcoeSanEp managed object table"
    ::= { cfprSwObjects 55 }

cfprSwFcoeSanEpEntry OBJECT-TYPE
    SYNTAX           CfprSwFcoeSanEpEntry
    MAX-ACCESS       not-accessible
    STATUS           current
    DESCRIPTION
        "Entry for the cfprSwFcoeSanEpTable table."
    INDEX { cfprSwFcoeSanEpInstanceId }
    ::= { cfprSwFcoeSanEpTable 1 }

CfprSwFcoeSanEpEntry ::= SEQUENCE {
    cfprSwFcoeSanEpInstanceId                                        CfprManagedObjectId,
    cfprSwFcoeSanEpDn                                                CfprManagedObjectDn,
    cfprSwFcoeSanEpRn                                                SnmpAdminString,
    cfprSwFcoeSanEpAdminSpeed                                        CfprPortSpeed,
    cfprSwFcoeSanEpAdminState                                        CfprFabricAdminState,
    cfprSwFcoeSanEpAggrPortId                                        Gauge32,
    cfprSwFcoeSanEpChassisId                                         Gauge32,
    cfprSwFcoeSanEpEpDn                                              SnmpAdminString,
    cfprSwFcoeSanEpIfRole                                            CfprSwSanEpIfRole,
    cfprSwFcoeSanEpIfType                                            CfprSwPIoEpIfType,
    cfprSwFcoeSanEpLc                                                CfprSwPIoEpLc,
    cfprSwFcoeSanEpLocale                                            CfprSwBorderEpLocale,
    cfprSwFcoeSanEpName                                              SnmpAdminString,
    cfprSwFcoeSanEpPcId                                              Gauge32,
    cfprSwFcoeSanEpPeerAggrPortId                                    Gauge32,
    cfprSwFcoeSanEpPeerChassisId                                     Gauge32,
    cfprSwFcoeSanEpPeerDn                                            SnmpAdminString,
    cfprSwFcoeSanEpPeerPortId                                        Gauge32,
    cfprSwFcoeSanEpPeerSlotId                                        Gauge32,
    cfprSwFcoeSanEpPeerState                                         CfprSwPeerStatus,
    cfprSwFcoeSanEpPortId                                            Gauge32,
    cfprSwFcoeSanEpPortVsanId                                        Gauge32,
    cfprSwFcoeSanEpSlotId                                            Gauge32,
    cfprSwFcoeSanEpSwitchId                                          CfprNetworkSwitchId,
    cfprSwFcoeSanEpTransport                                         CfprSwFcoeSanEpTransport,
    cfprSwFcoeSanEpType                                              CfprSwSanEpType,
    cfprSwFcoeSanEpUdldAdminState                                    CfprSwFcoeSanEpUdldAdminState,
    cfprSwFcoeSanEpUdldMode                                          CfprSwFcoeSanEpUdldMode
}

cfprSwFcoeSanEpInstanceId OBJECT-TYPE
    SYNTAX       CfprManagedObjectId
    MAX-ACCESS   not-accessible
    STATUS       current
    DESCRIPTION
        "Instance identifier of the managed object."
    ::= { cfprSwFcoeSanEpEntry 1 }

cfprSwFcoeSanEpDn OBJECT-TYPE
    SYNTAX       CfprManagedObjectDn
    MAX-ACCESS   read-only
    STATUS       current
    DESCRIPTION
        "Cisco Firepower sw:FcoeSanEp:dn managed object property"
    ::= { cfprSwFcoeSanEpEntry 2 }

cfprSwFcoeSanEpRn OBJECT-TYPE
    SYNTAX       SnmpAdminString
    MAX-ACCESS   read-only
    STATUS       current
    DESCRIPTION
        "Cisco Firepower sw:FcoeSanEp:rn managed object property"
    ::= { cfprSwFcoeSanEpEntry 3 }

cfprSwFcoeSanEpAdminSpeed OBJECT-TYPE
    SYNTAX       CfprPortSpeed
    MAX-ACCESS   read-only
    STATUS       current
    DESCRIPTION
        "Cisco Firepower sw:FcoeSanEp:adminSpeed managed object property"
    ::= { cfprSwFcoeSanEpEntry 4 }

cfprSwFcoeSanEpAdminState OBJECT-TYPE
    SYNTAX       CfprFabricAdminState
    MAX-ACCESS   read-only
    STATUS       current
    DESCRIPTION
        "Cisco Firepower sw:FcoeSanEp:adminState managed object property"
    ::= { cfprSwFcoeSanEpEntry 5 }

cfprSwFcoeSanEpAggrPortId OBJECT-TYPE
    SYNTAX       Gauge32
    MAX-ACCESS   read-only
    STATUS       current
    DESCRIPTION
        "Cisco Firepower sw:FcoeSanEp:aggrPortId managed object property"
    ::= { cfprSwFcoeSanEpEntry 6 }

cfprSwFcoeSanEpChassisId OBJECT-TYPE
    SYNTAX       Gauge32
    MAX-ACCESS   read-only
    STATUS       current
    DESCRIPTION
        "Cisco Firepower sw:FcoeSanEp:chassisId managed object property"
    ::= { cfprSwFcoeSanEpEntry 7 }

cfprSwFcoeSanEpEpDn OBJECT-TYPE
    SYNTAX       SnmpAdminString
    MAX-ACCESS   read-only
    STATUS       current
    DESCRIPTION
        "Cisco Firepower sw:FcoeSanEp:epDn managed object property"
    ::= { cfprSwFcoeSanEpEntry 8 }

cfprSwFcoeSanEpIfRole OBJECT-TYPE
    SYNTAX       CfprSwSanEpIfRole
    MAX-ACCESS   read-only
    STATUS       current
    DESCRIPTION
        "Cisco Firepower sw:FcoeSanEp:ifRole managed object property"
    ::= { cfprSwFcoeSanEpEntry 9 }

cfprSwFcoeSanEpIfType OBJECT-TYPE
    SYNTAX       CfprSwPIoEpIfType
    MAX-ACCESS   read-only
    STATUS       current
    DESCRIPTION
        "Cisco Firepower sw:FcoeSanEp:ifType managed object property"
    ::= { cfprSwFcoeSanEpEntry 10 }

cfprSwFcoeSanEpLc OBJECT-TYPE
    SYNTAX       CfprSwPIoEpLc
    MAX-ACCESS   read-only
    STATUS       current
    DESCRIPTION
        "Cisco Firepower sw:FcoeSanEp:lc managed object property"
    ::= { cfprSwFcoeSanEpEntry 11 }

cfprSwFcoeSanEpLocale OBJECT-TYPE
    SYNTAX       CfprSwBorderEpLocale
    MAX-ACCESS   read-only
    STATUS       current
    DESCRIPTION
        "Cisco Firepower sw:FcoeSanEp:locale managed object property"
    ::= { cfprSwFcoeSanEpEntry 12 }

cfprSwFcoeSanEpName OBJECT-TYPE
    SYNTAX       SnmpAdminString
    MAX-ACCESS   read-only
    STATUS       current
    DESCRIPTION
        "Cisco Firepower sw:FcoeSanEp:name managed object property"
    ::= { cfprSwFcoeSanEpEntry 13 }

cfprSwFcoeSanEpPcId OBJECT-TYPE
    SYNTAX       Gauge32
    MAX-ACCESS   read-only
    STATUS       current
    DESCRIPTION
        "Cisco Firepower sw:FcoeSanEp:pcId managed object property"
    ::= { cfprSwFcoeSanEpEntry 14 }

cfprSwFcoeSanEpPeerAggrPortId OBJECT-TYPE
    SYNTAX       Gauge32
    MAX-ACCESS   read-only
    STATUS       current
    DESCRIPTION
        "Cisco Firepower sw:FcoeSanEp:peerAggrPortId managed
        object property"
    ::= { cfprSwFcoeSanEpEntry 15 }

cfprSwFcoeSanEpPeerChassisId OBJECT-TYPE
    SYNTAX       Gauge32
    MAX-ACCESS   read-only
    STATUS       current
    DESCRIPTION
        "Cisco Firepower sw:FcoeSanEp:peerChassisId managed
        object property"
    ::= { cfprSwFcoeSanEpEntry 16 }

cfprSwFcoeSanEpPeerDn OBJECT-TYPE
    SYNTAX       SnmpAdminString
    MAX-ACCESS   read-only
    STATUS       current
    DESCRIPTION
        "Cisco Firepower sw:FcoeSanEp:peerDn managed object property"
    ::= { cfprSwFcoeSanEpEntry 17 }

cfprSwFcoeSanEpPeerPortId OBJECT-TYPE
    SYNTAX       Gauge32
    MAX-ACCESS   read-only
    STATUS       current
    DESCRIPTION
        "Cisco Firepower sw:FcoeSanEp:peerPortId managed object property"
    ::= { cfprSwFcoeSanEpEntry 18 }

cfprSwFcoeSanEpPeerSlotId OBJECT-TYPE
    SYNTAX       Gauge32
    MAX-ACCESS   read-only
    STATUS       current
    DESCRIPTION
        "Cisco Firepower sw:FcoeSanEp:peerSlotId managed object property"
    ::= { cfprSwFcoeSanEpEntry 19 }

cfprSwFcoeSanEpPeerState OBJECT-TYPE
    SYNTAX       CfprSwPeerStatus
    MAX-ACCESS   read-only
    STATUS       current
    DESCRIPTION
        "Cisco Firepower sw:FcoeSanEp:peerState managed object property"
    ::= { cfprSwFcoeSanEpEntry 20 }

cfprSwFcoeSanEpPortId OBJECT-TYPE
    SYNTAX       Gauge32
    MAX-ACCESS   read-only
    STATUS       current
    DESCRIPTION
        "Cisco Firepower sw:FcoeSanEp:portId managed object property"
    ::= { cfprSwFcoeSanEpEntry 21 }

cfprSwFcoeSanEpPortVsanId OBJECT-TYPE
    SYNTAX       Gauge32
    MAX-ACCESS   read-only
    STATUS       current
    DESCRIPTION
        "Cisco Firepower sw:FcoeSanEp:portVsanId managed object property"
    ::= { cfprSwFcoeSanEpEntry 22 }

cfprSwFcoeSanEpSlotId OBJECT-TYPE
    SYNTAX       Gauge32
    MAX-ACCESS   read-only
    STATUS       current
    DESCRIPTION
        "Cisco Firepower sw:FcoeSanEp:slotId managed object property"
    ::= { cfprSwFcoeSanEpEntry 23 }

cfprSwFcoeSanEpSwitchId OBJECT-TYPE
    SYNTAX       CfprNetworkSwitchId
    MAX-ACCESS   read-only
    STATUS       current
    DESCRIPTION
        "Cisco Firepower sw:FcoeSanEp:switchId managed object property"
    ::= { cfprSwFcoeSanEpEntry 24 }

cfprSwFcoeSanEpTransport OBJECT-TYPE
    SYNTAX       CfprSwFcoeSanEpTransport
    MAX-ACCESS   read-only
    STATUS       current
    DESCRIPTION
        "Cisco Firepower sw:FcoeSanEp:transport managed object property"
    ::= { cfprSwFcoeSanEpEntry 25 }

cfprSwFcoeSanEpType OBJECT-TYPE
    SYNTAX       CfprSwSanEpType
    MAX-ACCESS   read-only
    STATUS       current
    DESCRIPTION
        "Cisco Firepower sw:FcoeSanEp:type managed object property"
    ::= { cfprSwFcoeSanEpEntry 26 }

cfprSwFcoeSanEpUdldAdminState OBJECT-TYPE
    SYNTAX       CfprSwFcoeSanEpUdldAdminState
    MAX-ACCESS   read-only
    STATUS       current
    DESCRIPTION
        "Cisco Firepower sw:FcoeSanEp:udldAdminState managed
        object property"
    ::= { cfprSwFcoeSanEpEntry 27 }

cfprSwFcoeSanEpUdldMode OBJECT-TYPE
    SYNTAX       CfprSwFcoeSanEpUdldMode
    MAX-ACCESS   read-only
    STATUS       current
    DESCRIPTION
        "Cisco Firepower sw:FcoeSanEp:udldMode managed object property"
    ::= { cfprSwFcoeSanEpEntry 28 }

cfprSwFcoeSanPcTable OBJECT-TYPE
    SYNTAX           SEQUENCE OF CfprSwFcoeSanPcEntry
    MAX-ACCESS       not-accessible
    STATUS           current
    DESCRIPTION
        "Cisco Firepower sw:FcoeSanPc managed object table"
    ::= { cfprSwObjects 56 }

cfprSwFcoeSanPcEntry OBJECT-TYPE
    SYNTAX           CfprSwFcoeSanPcEntry
    MAX-ACCESS       not-accessible
    STATUS           current
    DESCRIPTION
        "Entry for the cfprSwFcoeSanPcTable table."
    INDEX { cfprSwFcoeSanPcInstanceId }
    ::= { cfprSwFcoeSanPcTable 1 }

CfprSwFcoeSanPcEntry ::= SEQUENCE {
    cfprSwFcoeSanPcInstanceId                                        CfprManagedObjectId,
    cfprSwFcoeSanPcDn                                                CfprManagedObjectDn,
    cfprSwFcoeSanPcRn                                                SnmpAdminString,
    cfprSwFcoeSanPcAdminState                                        CfprFabricAdminState,
    cfprSwFcoeSanPcEpDn                                              SnmpAdminString,
    cfprSwFcoeSanPcIfRole                                            CfprSwSanPcIfRole,
    cfprSwFcoeSanPcIfType                                            CfprSwCIoEpIfType,
    cfprSwFcoeSanPcLacpFastTimer                                     TruthValue,
    cfprSwFcoeSanPcLacpSuspendIndividual                             TruthValue,
    cfprSwFcoeSanPcLocale                                            CfprSwBorderPcLocale,
    cfprSwFcoeSanPcMonTrafDir                                        CfprFabricTrafficDirection,
    cfprSwFcoeSanPcName                                              SnmpAdminString,
    cfprSwFcoeSanPcPcId                                              Gauge32,
    cfprSwFcoeSanPcPeerDn                                            SnmpAdminString,
    cfprSwFcoeSanPcPeerState                                         CfprSwPeerStatus,
    cfprSwFcoeSanPcPortId                                            Gauge32,
    cfprSwFcoeSanPcPortVsanId                                        Gauge32,
    cfprSwFcoeSanPcSwitchId                                          CfprNetworkSwitchId,
    cfprSwFcoeSanPcTransport                                         CfprSwFcoeSanPcTransport,
    cfprSwFcoeSanPcType                                              CfprSwSanPcType
}

cfprSwFcoeSanPcInstanceId OBJECT-TYPE
    SYNTAX       CfprManagedObjectId
    MAX-ACCESS   not-accessible
    STATUS       current
    DESCRIPTION
        "Instance identifier of the managed object."
    ::= { cfprSwFcoeSanPcEntry 1 }

cfprSwFcoeSanPcDn OBJECT-TYPE
    SYNTAX       CfprManagedObjectDn
    MAX-ACCESS   read-only
    STATUS       current
    DESCRIPTION
        "Cisco Firepower sw:FcoeSanPc:dn managed object property"
    ::= { cfprSwFcoeSanPcEntry 2 }

cfprSwFcoeSanPcRn OBJECT-TYPE
    SYNTAX       SnmpAdminString
    MAX-ACCESS   read-only
    STATUS       current
    DESCRIPTION
        "Cisco Firepower sw:FcoeSanPc:rn managed object property"
    ::= { cfprSwFcoeSanPcEntry 3 }

cfprSwFcoeSanPcAdminState OBJECT-TYPE
    SYNTAX       CfprFabricAdminState
    MAX-ACCESS   read-only
    STATUS       current
    DESCRIPTION
        "Cisco Firepower sw:FcoeSanPc:adminState managed object property"
    ::= { cfprSwFcoeSanPcEntry 4 }

cfprSwFcoeSanPcEpDn OBJECT-TYPE
    SYNTAX       SnmpAdminString
    MAX-ACCESS   read-only
    STATUS       current
    DESCRIPTION
        "Cisco Firepower sw:FcoeSanPc:epDn managed object property"
    ::= { cfprSwFcoeSanPcEntry 5 }

cfprSwFcoeSanPcIfRole OBJECT-TYPE
    SYNTAX       CfprSwSanPcIfRole
    MAX-ACCESS   read-only
    STATUS       current
    DESCRIPTION
        "Cisco Firepower sw:FcoeSanPc:ifRole managed object property"
    ::= { cfprSwFcoeSanPcEntry 6 }

cfprSwFcoeSanPcIfType OBJECT-TYPE
    SYNTAX       CfprSwCIoEpIfType
    MAX-ACCESS   read-only
    STATUS       current
    DESCRIPTION
        "Cisco Firepower sw:FcoeSanPc:ifType managed object property"
    ::= { cfprSwFcoeSanPcEntry 7 }

cfprSwFcoeSanPcLacpFastTimer OBJECT-TYPE
    SYNTAX       TruthValue
    MAX-ACCESS   read-only
    STATUS       current
    DESCRIPTION
        "Cisco Firepower sw:FcoeSanPc:lacpFastTimer managed
        object property"
    ::= { cfprSwFcoeSanPcEntry 8 }

cfprSwFcoeSanPcLacpSuspendIndividual OBJECT-TYPE
    SYNTAX       TruthValue
    MAX-ACCESS   read-only
    STATUS       current
    DESCRIPTION
        "Cisco Firepower sw:FcoeSanPc:lacpSuspendIndividual
        managed object property"
    ::= { cfprSwFcoeSanPcEntry 9 }

cfprSwFcoeSanPcLocale OBJECT-TYPE
    SYNTAX       CfprSwBorderPcLocale
    MAX-ACCESS   read-only
    STATUS       current
    DESCRIPTION
        "Cisco Firepower sw:FcoeSanPc:locale managed object property"
    ::= { cfprSwFcoeSanPcEntry 10 }

cfprSwFcoeSanPcMonTrafDir OBJECT-TYPE
    SYNTAX       CfprFabricTrafficDirection
    MAX-ACCESS   read-only
    STATUS       current
    DESCRIPTION
        "Cisco Firepower sw:FcoeSanPc:monTrafDir managed object property"
    ::= { cfprSwFcoeSanPcEntry 11 }

cfprSwFcoeSanPcName OBJECT-TYPE
    SYNTAX       SnmpAdminString
    MAX-ACCESS   read-only
    STATUS       current
    DESCRIPTION
        "Cisco Firepower sw:FcoeSanPc:name managed object property"
    ::= { cfprSwFcoeSanPcEntry 12 }

cfprSwFcoeSanPcPcId OBJECT-TYPE
    SYNTAX       Gauge32
    MAX-ACCESS   read-only
    STATUS       current
    DESCRIPTION
        "Cisco Firepower sw:FcoeSanPc:pcId managed object property"
    ::= { cfprSwFcoeSanPcEntry 13 }

cfprSwFcoeSanPcPeerDn OBJECT-TYPE
    SYNTAX       SnmpAdminString
    MAX-ACCESS   read-only
    STATUS       current
    DESCRIPTION
        "Cisco Firepower sw:FcoeSanPc:peerDn managed object property"
    ::= { cfprSwFcoeSanPcEntry 14 }

cfprSwFcoeSanPcPeerState OBJECT-TYPE
    SYNTAX       CfprSwPeerStatus
    MAX-ACCESS   read-only
    STATUS       current
    DESCRIPTION
        "Cisco Firepower sw:FcoeSanPc:peerState managed object property"
    ::= { cfprSwFcoeSanPcEntry 15 }

cfprSwFcoeSanPcPortId OBJECT-TYPE
    SYNTAX       Gauge32
    MAX-ACCESS   read-only
    STATUS       current
    DESCRIPTION
        "Cisco Firepower sw:FcoeSanPc:portId managed object property"
    ::= { cfprSwFcoeSanPcEntry 16 }

cfprSwFcoeSanPcPortVsanId OBJECT-TYPE
    SYNTAX       Gauge32
    MAX-ACCESS   read-only
    STATUS       current
    DESCRIPTION
        "Cisco Firepower sw:FcoeSanPc:portVsanId managed object property"
    ::= { cfprSwFcoeSanPcEntry 17 }

cfprSwFcoeSanPcSwitchId OBJECT-TYPE
    SYNTAX       CfprNetworkSwitchId
    MAX-ACCESS   read-only
    STATUS       current
    DESCRIPTION
        "Cisco Firepower sw:FcoeSanPc:switchId managed object property"
    ::= { cfprSwFcoeSanPcEntry 18 }

cfprSwFcoeSanPcTransport OBJECT-TYPE
    SYNTAX       CfprSwFcoeSanPcTransport
    MAX-ACCESS   read-only
    STATUS       current
    DESCRIPTION
        "Cisco Firepower sw:FcoeSanPc:transport managed object property"
    ::= { cfprSwFcoeSanPcEntry 19 }

cfprSwFcoeSanPcType OBJECT-TYPE
    SYNTAX       CfprSwSanPcType
    MAX-ACCESS   read-only
    STATUS       current
    DESCRIPTION
        "Cisco Firepower sw:FcoeSanPc:type managed object property"
    ::= { cfprSwFcoeSanPcEntry 20 }

cfprSwIpRouteTable OBJECT-TYPE
    SYNTAX           SEQUENCE OF CfprSwIpRouteEntry
    MAX-ACCESS       not-accessible
    STATUS           current
    DESCRIPTION
        "Cisco Firepower sw:IpRoute managed object table"
    ::= { cfprSwObjects 57 }

cfprSwIpRouteEntry OBJECT-TYPE
    SYNTAX           CfprSwIpRouteEntry
    MAX-ACCESS       not-accessible
    STATUS           current
    DESCRIPTION
        "Entry for the cfprSwIpRouteTable table."
    INDEX { cfprSwIpRouteInstanceId }
    ::= { cfprSwIpRouteTable 1 }

CfprSwIpRouteEntry ::= SEQUENCE {
    cfprSwIpRouteInstanceId                                          CfprManagedObjectId,
    cfprSwIpRouteDn                                                  CfprManagedObjectDn,
    cfprSwIpRouteRn                                                  SnmpAdminString,
    cfprSwIpRouteDestinationIp                                       InetAddressIPv4,
    cfprSwIpRouteDestinationNetmask                                  InetAddressIPv4,
    cfprSwIpRouteName                                                SnmpAdminString,
    cfprSwIpRoutePeerDn                                              SnmpAdminString,
    cfprSwIpRoutePrefix                                              Gauge32,
    cfprSwIpRouteRouteIP                                             InetAddressIPv4,
    cfprSwIpRouteSwitchId                                            CfprNetworkSwitchId
}

cfprSwIpRouteInstanceId OBJECT-TYPE
    SYNTAX       CfprManagedObjectId
    MAX-ACCESS   not-accessible
    STATUS       current
    DESCRIPTION
        "Instance identifier of the managed object."
    ::= { cfprSwIpRouteEntry 1 }

cfprSwIpRouteDn OBJECT-TYPE
    SYNTAX       CfprManagedObjectDn
    MAX-ACCESS   read-only
    STATUS       current
    DESCRIPTION
        "Cisco Firepower sw:IpRoute:dn managed object property"
    ::= { cfprSwIpRouteEntry 2 }

cfprSwIpRouteRn OBJECT-TYPE
    SYNTAX       SnmpAdminString
    MAX-ACCESS   read-only
    STATUS       current
    DESCRIPTION
        "Cisco Firepower sw:IpRoute:rn managed object property"
    ::= { cfprSwIpRouteEntry 3 }

cfprSwIpRouteDestinationIp OBJECT-TYPE
    SYNTAX       InetAddressIPv4
    MAX-ACCESS   read-only
    STATUS       current
    DESCRIPTION
        "Cisco Firepower sw:IpRoute:destinationIp managed object property"
    ::= { cfprSwIpRouteEntry 4 }

cfprSwIpRouteDestinationNetmask OBJECT-TYPE
    SYNTAX       InetAddressIPv4
    MAX-ACCESS   read-only
    STATUS       current
    DESCRIPTION
        "Cisco Firepower sw:IpRoute:destinationNetmask
        managed object property"
    ::= { cfprSwIpRouteEntry 5 }

cfprSwIpRouteName OBJECT-TYPE
    SYNTAX       SnmpAdminString
    MAX-ACCESS   read-only
    STATUS       current
    DESCRIPTION
        "Cisco Firepower sw:IpRoute:name managed object property"
    ::= { cfprSwIpRouteEntry 6 }

cfprSwIpRoutePeerDn OBJECT-TYPE
    SYNTAX       SnmpAdminString
    MAX-ACCESS   read-only
    STATUS       current
    DESCRIPTION
        "Cisco Firepower sw:IpRoute:peerDn managed object property"
    ::= { cfprSwIpRouteEntry 7 }

cfprSwIpRoutePrefix OBJECT-TYPE
    SYNTAX       Gauge32
    MAX-ACCESS   read-only
    STATUS       current
    DESCRIPTION
        "Cisco Firepower sw:IpRoute:prefix managed object property"
    ::= { cfprSwIpRouteEntry 8 }

cfprSwIpRouteRouteIP OBJECT-TYPE
    SYNTAX       InetAddressIPv4
    MAX-ACCESS   read-only
    STATUS       current
    DESCRIPTION
        "Cisco Firepower sw:IpRoute:routeIP managed object property"
    ::= { cfprSwIpRouteEntry 9 }

cfprSwIpRouteSwitchId OBJECT-TYPE
    SYNTAX       CfprNetworkSwitchId
    MAX-ACCESS   read-only
    STATUS       current
    DESCRIPTION
        "Cisco Firepower sw:IpRoute:switchId managed object property"
    ::= { cfprSwIpRouteEntry 10 }

cfprSwNFExporterRefTable OBJECT-TYPE
    SYNTAX           SEQUENCE OF CfprSwNFExporterRefEntry
    MAX-ACCESS       not-accessible
    STATUS           current
    DESCRIPTION
        "Cisco Firepower sw:NFExporterRef managed object table"
    ::= { cfprSwObjects 58 }

cfprSwNFExporterRefEntry OBJECT-TYPE
    SYNTAX           CfprSwNFExporterRefEntry
    MAX-ACCESS       not-accessible
    STATUS           current
    DESCRIPTION
        "Entry for the cfprSwNFExporterRefTable table."
    INDEX { cfprSwNFExporterRefInstanceId }
    ::= { cfprSwNFExporterRefTable 1 }

CfprSwNFExporterRefEntry ::= SEQUENCE {
    cfprSwNFExporterRefInstanceId                                    CfprManagedObjectId,
    cfprSwNFExporterRefDn                                            CfprManagedObjectDn,
    cfprSwNFExporterRefRn                                            SnmpAdminString,
    cfprSwNFExporterRefName                                          SnmpAdminString,
    cfprSwNFExporterRefPeerDn                                        SnmpAdminString
}

cfprSwNFExporterRefInstanceId OBJECT-TYPE
    SYNTAX       CfprManagedObjectId
    MAX-ACCESS   not-accessible
    STATUS       current
    DESCRIPTION
        "Instance identifier of the managed object."
    ::= { cfprSwNFExporterRefEntry 1 }

cfprSwNFExporterRefDn OBJECT-TYPE
    SYNTAX       CfprManagedObjectDn
    MAX-ACCESS   read-only
    STATUS       current
    DESCRIPTION
        "Cisco Firepower sw:NFExporterRef:dn managed object property"
    ::= { cfprSwNFExporterRefEntry 2 }

cfprSwNFExporterRefRn OBJECT-TYPE
    SYNTAX       SnmpAdminString
    MAX-ACCESS   read-only
    STATUS       current
    DESCRIPTION
        "Cisco Firepower sw:NFExporterRef:rn managed object property"
    ::= { cfprSwNFExporterRefEntry 3 }

cfprSwNFExporterRefName OBJECT-TYPE
    SYNTAX       SnmpAdminString
    MAX-ACCESS   read-only
    STATUS       current
    DESCRIPTION
        "Cisco Firepower sw:NFExporterRef:name managed object property"
    ::= { cfprSwNFExporterRefEntry 4 }

cfprSwNFExporterRefPeerDn OBJECT-TYPE
    SYNTAX       SnmpAdminString
    MAX-ACCESS   read-only
    STATUS       current
    DESCRIPTION
        "Cisco Firepower sw:NFExporterRef:peerDn managed object property"
    ::= { cfprSwNFExporterRefEntry 5 }

cfprSwNetflowExporterTable OBJECT-TYPE
    SYNTAX           SEQUENCE OF CfprSwNetflowExporterEntry
    MAX-ACCESS       not-accessible
    STATUS           current
    DESCRIPTION
        "Cisco Firepower sw:NetflowExporter managed object table"
    ::= { cfprSwObjects 59 }

cfprSwNetflowExporterEntry OBJECT-TYPE
    SYNTAX           CfprSwNetflowExporterEntry
    MAX-ACCESS       not-accessible
    STATUS           current
    DESCRIPTION
        "Entry for the cfprSwNetflowExporterTable table."
    INDEX { cfprSwNetflowExporterInstanceId }
    ::= { cfprSwNetflowExporterTable 1 }

CfprSwNetflowExporterEntry ::= SEQUENCE {
    cfprSwNetflowExporterInstanceId                                  CfprManagedObjectId,
    cfprSwNetflowExporterDn                                          CfprManagedObjectDn,
    cfprSwNetflowExporterRn                                          SnmpAdminString,
    cfprSwNetflowExporterDestinationIpAddress                        InetAddressIPv4,
    cfprSwNetflowExporterDestinationPort                             Gauge32,
    cfprSwNetflowExporterDscp                                        Gauge32,
    cfprSwNetflowExporterExportInternal                              Gauge32,
    cfprSwNetflowExporterExporterStatsTimeout                        Gauge32,
    cfprSwNetflowExporterInterfaceTableTimeout                       Gauge32,
    cfprSwNetflowExporterIsValidConfig                               CfprSwNFConfigStatus,
    cfprSwNetflowExporterLifeCycle                                   CfprSwMonLifeCycle,
    cfprSwNetflowExporterName                                        SnmpAdminString,
    cfprSwNetflowExporterPeerDn                                      SnmpAdminString,
    cfprSwNetflowExporterProtocol                                    CfprSwNetflowExporterProtocol,
    cfprSwNetflowExporterSourceVlan                                  Gauge32,
    cfprSwNetflowExporterSwitchId                                    CfprNetworkSwitchId,
    cfprSwNetflowExporterTemplateDataTimeout                         Gauge32,
    cfprSwNetflowExporterTransport                                   CfprSwEthLanFlowMonExporterTransport,
    cfprSwNetflowExporterTransportProtocol                           CfprFabricNFTransport,
    cfprSwNetflowExporterType                                        CfprSwEthLanFlowMonExporterType,
    cfprSwNetflowExporterVersion                                     CfprFabricNFExporterVersion
}

cfprSwNetflowExporterInstanceId OBJECT-TYPE
    SYNTAX       CfprManagedObjectId
    MAX-ACCESS   not-accessible
    STATUS       current
    DESCRIPTION
        "Instance identifier of the managed object."
    ::= { cfprSwNetflowExporterEntry 1 }

cfprSwNetflowExporterDn OBJECT-TYPE
    SYNTAX       CfprManagedObjectDn
    MAX-ACCESS   read-only
    STATUS       current
    DESCRIPTION
        "Cisco Firepower sw:NetflowExporter:dn managed object property"
    ::= { cfprSwNetflowExporterEntry 2 }

cfprSwNetflowExporterRn OBJECT-TYPE
    SYNTAX       SnmpAdminString
    MAX-ACCESS   read-only
    STATUS       current
    DESCRIPTION
        "Cisco Firepower sw:NetflowExporter:rn managed object property"
    ::= { cfprSwNetflowExporterEntry 3 }

cfprSwNetflowExporterDestinationIpAddress OBJECT-TYPE
    SYNTAX       InetAddressIPv4
    MAX-ACCESS   read-only
    STATUS       current
    DESCRIPTION
        "Cisco Firepower sw:NetflowExporter:destinationIpAddress
        managed object property"
    ::= { cfprSwNetflowExporterEntry 4 }

cfprSwNetflowExporterDestinationPort OBJECT-TYPE
    SYNTAX       Gauge32
    MAX-ACCESS   read-only
    STATUS       current
    DESCRIPTION
        "Cisco Firepower sw:NetflowExporter:destinationPort
        managed object property"
    ::= { cfprSwNetflowExporterEntry 5 }

cfprSwNetflowExporterDscp OBJECT-TYPE
    SYNTAX       Gauge32
    MAX-ACCESS   read-only
    STATUS       current
    DESCRIPTION
        "Cisco Firepower sw:NetflowExporter:dscp managed object property"
    ::= { cfprSwNetflowExporterEntry 6 }

cfprSwNetflowExporterExportInternal OBJECT-TYPE
    SYNTAX       Gauge32
    MAX-ACCESS   read-only
    STATUS       current
    DESCRIPTION
        "Cisco Firepower sw:NetflowExporter:exportInternal
        managed object property"
    ::= { cfprSwNetflowExporterEntry 7 }

cfprSwNetflowExporterExporterStatsTimeout OBJECT-TYPE
    SYNTAX       Gauge32
    MAX-ACCESS   read-only
    STATUS       current
    DESCRIPTION
        "Cisco Firepower sw:NetflowExporter:exporterStatsTimeout
        managed object property"
    ::= { cfprSwNetflowExporterEntry 8 }

cfprSwNetflowExporterInterfaceTableTimeout OBJECT-TYPE
    SYNTAX       Gauge32
    MAX-ACCESS   read-only
    STATUS       current
    DESCRIPTION
        "Cisco Firepower sw:NetflowExporter:interfaceTableTimeout
        managed object property"
    ::= { cfprSwNetflowExporterEntry 9 }

cfprSwNetflowExporterIsValidConfig OBJECT-TYPE
    SYNTAX       CfprSwNFConfigStatus
    MAX-ACCESS   read-only
    STATUS       current
    DESCRIPTION
        "Cisco Firepower sw:NetflowExporter:isValidConfig
        managed object property"
    ::= { cfprSwNetflowExporterEntry 10 }

cfprSwNetflowExporterLifeCycle OBJECT-TYPE
    SYNTAX       CfprSwMonLifeCycle
    MAX-ACCESS   read-only
    STATUS       current
    DESCRIPTION
        "Cisco Firepower sw:NetflowExporter:lifeCycle managed
        object property"
    ::= { cfprSwNetflowExporterEntry 11 }

cfprSwNetflowExporterName OBJECT-TYPE
    SYNTAX       SnmpAdminString
    MAX-ACCESS   read-only
    STATUS       current
    DESCRIPTION
        "Cisco Firepower sw:NetflowExporter:name managed object property"
    ::= { cfprSwNetflowExporterEntry 12 }

cfprSwNetflowExporterPeerDn OBJECT-TYPE
    SYNTAX       SnmpAdminString
    MAX-ACCESS   read-only
    STATUS       current
    DESCRIPTION
        "Cisco Firepower sw:NetflowExporter:peerDn managed
        object property"
    ::= { cfprSwNetflowExporterEntry 13 }

cfprSwNetflowExporterProtocol OBJECT-TYPE
    SYNTAX       CfprSwNetflowExporterProtocol
    MAX-ACCESS   read-only
    STATUS       current
    DESCRIPTION
        "Cisco Firepower sw:NetflowExporter:protocol managed
        object property"
    ::= { cfprSwNetflowExporterEntry 14 }

cfprSwNetflowExporterSourceVlan OBJECT-TYPE
    SYNTAX       Gauge32
    MAX-ACCESS   read-only
    STATUS       current
    DESCRIPTION
        "Cisco Firepower sw:NetflowExporter:sourceVlan
        managed object property"
    ::= { cfprSwNetflowExporterEntry 15 }

cfprSwNetflowExporterSwitchId OBJECT-TYPE
    SYNTAX       CfprNetworkSwitchId
    MAX-ACCESS   read-only
    STATUS       current
    DESCRIPTION
        "Cisco Firepower sw:NetflowExporter:switchId managed
        object property"
    ::= { cfprSwNetflowExporterEntry 16 }

cfprSwNetflowExporterTemplateDataTimeout OBJECT-TYPE
    SYNTAX       Gauge32
    MAX-ACCESS   read-only
    STATUS       current
    DESCRIPTION
        "Cisco Firepower sw:NetflowExporter:templateDataTimeout
        managed object property"
    ::= { cfprSwNetflowExporterEntry 17 }

cfprSwNetflowExporterTransport OBJECT-TYPE
    SYNTAX       CfprSwEthLanFlowMonExporterTransport
    MAX-ACCESS   read-only
    STATUS       current
    DESCRIPTION
        "Cisco Firepower sw:NetflowExporter:transport managed
        object property"
    ::= { cfprSwNetflowExporterEntry 18 }

cfprSwNetflowExporterTransportProtocol OBJECT-TYPE
    SYNTAX       CfprFabricNFTransport
    MAX-ACCESS   read-only
    STATUS       current
    DESCRIPTION
        "Cisco Firepower sw:NetflowExporter:transportProtocol
        managed object property"
    ::= { cfprSwNetflowExporterEntry 19 }

cfprSwNetflowExporterType OBJECT-TYPE
    SYNTAX       CfprSwEthLanFlowMonExporterType
    MAX-ACCESS   read-only
    STATUS       current
    DESCRIPTION
        "Cisco Firepower sw:NetflowExporter:type managed object property"
    ::= { cfprSwNetflowExporterEntry 20 }

cfprSwNetflowExporterVersion OBJECT-TYPE
    SYNTAX       CfprFabricNFExporterVersion
    MAX-ACCESS   read-only
    STATUS       current
    DESCRIPTION
        "Cisco Firepower sw:NetflowExporter:version managed
        object property"
    ::= { cfprSwNetflowExporterEntry 21 }

cfprSwNetflowMonSessionTable OBJECT-TYPE
    SYNTAX           SEQUENCE OF CfprSwNetflowMonSessionEntry
    MAX-ACCESS       not-accessible
    STATUS           current
    DESCRIPTION
        "Cisco Firepower sw:NetflowMonSession managed object table"
    ::= { cfprSwObjects 60 }

cfprSwNetflowMonSessionEntry OBJECT-TYPE
    SYNTAX           CfprSwNetflowMonSessionEntry
    MAX-ACCESS       not-accessible
    STATUS           current
    DESCRIPTION
        "Entry for the cfprSwNetflowMonSessionTable table."
    INDEX { cfprSwNetflowMonSessionInstanceId }
    ::= { cfprSwNetflowMonSessionTable 1 }

CfprSwNetflowMonSessionEntry ::= SEQUENCE {
    cfprSwNetflowMonSessionInstanceId                                CfprManagedObjectId,
    cfprSwNetflowMonSessionDn                                        CfprManagedObjectDn,
    cfprSwNetflowMonSessionRn                                        SnmpAdminString,
    cfprSwNetflowMonSessionAdminState                                CfprSwMonAdminState,
    cfprSwNetflowMonSessionHasLastDest                               TruthValue,
    cfprSwNetflowMonSessionLifeCycle                                 CfprSwMonLifeCycle,
    cfprSwNetflowMonSessionName                                      SnmpAdminString,
    cfprSwNetflowMonSessionPeerDn                                    SnmpAdminString,
    cfprSwNetflowMonSessionProtocol                                  CfprSwNetflowMonSessionProtocol,
    cfprSwNetflowMonSessionSession                                   Gauge32,
    cfprSwNetflowMonSessionSwitchId                                  CfprNetworkSwitchId,
    cfprSwNetflowMonSessionTransport                                 CfprSwEthFlowMonSessionTransport,
    cfprSwNetflowMonSessionType                                      CfprSwEthFlowMonSessionType
}

cfprSwNetflowMonSessionInstanceId OBJECT-TYPE
    SYNTAX       CfprManagedObjectId
    MAX-ACCESS   not-accessible
    STATUS       current
    DESCRIPTION
        "Instance identifier of the managed object."
    ::= { cfprSwNetflowMonSessionEntry 1 }

cfprSwNetflowMonSessionDn OBJECT-TYPE
    SYNTAX       CfprManagedObjectDn
    MAX-ACCESS   read-only
    STATUS       current
    DESCRIPTION
        "Cisco Firepower sw:NetflowMonSession:dn managed object property"
    ::= { cfprSwNetflowMonSessionEntry 2 }

cfprSwNetflowMonSessionRn OBJECT-TYPE
    SYNTAX       SnmpAdminString
    MAX-ACCESS   read-only
    STATUS       current
    DESCRIPTION
        "Cisco Firepower sw:NetflowMonSession:rn managed object property"
    ::= { cfprSwNetflowMonSessionEntry 3 }

cfprSwNetflowMonSessionAdminState OBJECT-TYPE
    SYNTAX       CfprSwMonAdminState
    MAX-ACCESS   read-only
    STATUS       current
    DESCRIPTION
        "Cisco Firepower sw:NetflowMonSession:adminState
        managed object property"
    ::= { cfprSwNetflowMonSessionEntry 4 }

cfprSwNetflowMonSessionHasLastDest OBJECT-TYPE
    SYNTAX       TruthValue
    MAX-ACCESS   read-only
    STATUS       current
    DESCRIPTION
        "Cisco Firepower sw:NetflowMonSession:hasLastDest
        managed object property"
    ::= { cfprSwNetflowMonSessionEntry 5 }

cfprSwNetflowMonSessionLifeCycle OBJECT-TYPE
    SYNTAX       CfprSwMonLifeCycle
    MAX-ACCESS   read-only
    STATUS       current
    DESCRIPTION
        "Cisco Firepower sw:NetflowMonSession:lifeCycle
        managed object property"
    ::= { cfprSwNetflowMonSessionEntry 6 }

cfprSwNetflowMonSessionName OBJECT-TYPE
    SYNTAX       SnmpAdminString
    MAX-ACCESS   read-only
    STATUS       current
    DESCRIPTION
        "Cisco Firepower sw:NetflowMonSession:name managed
        object property"
    ::= { cfprSwNetflowMonSessionEntry 7 }

cfprSwNetflowMonSessionPeerDn OBJECT-TYPE
    SYNTAX       SnmpAdminString
    MAX-ACCESS   read-only
    STATUS       current
    DESCRIPTION
        "Cisco Firepower sw:NetflowMonSession:peerDn managed
        object property"
    ::= { cfprSwNetflowMonSessionEntry 8 }

cfprSwNetflowMonSessionProtocol OBJECT-TYPE
    SYNTAX       CfprSwNetflowMonSessionProtocol
    MAX-ACCESS   read-only
    STATUS       current
    DESCRIPTION
        "Cisco Firepower sw:NetflowMonSession:protocol
        managed object property"
    ::= { cfprSwNetflowMonSessionEntry 9 }

cfprSwNetflowMonSessionSession OBJECT-TYPE
    SYNTAX       Gauge32
    MAX-ACCESS   read-only
    STATUS       current
    DESCRIPTION
        "Cisco Firepower sw:NetflowMonSession:session managed
        object property"
    ::= { cfprSwNetflowMonSessionEntry 10 }

cfprSwNetflowMonSessionSwitchId OBJECT-TYPE
    SYNTAX       CfprNetworkSwitchId
    MAX-ACCESS   read-only
    STATUS       current
    DESCRIPTION
        "Cisco Firepower sw:NetflowMonSession:switchId
        managed object property"
    ::= { cfprSwNetflowMonSessionEntry 11 }

cfprSwNetflowMonSessionTransport OBJECT-TYPE
    SYNTAX       CfprSwEthFlowMonSessionTransport
    MAX-ACCESS   read-only
    STATUS       current
    DESCRIPTION
        "Cisco Firepower sw:NetflowMonSession:transport
        managed object property"
    ::= { cfprSwNetflowMonSessionEntry 12 }

cfprSwNetflowMonSessionType OBJECT-TYPE
    SYNTAX       CfprSwEthFlowMonSessionType
    MAX-ACCESS   read-only
    STATUS       current
    DESCRIPTION
        "Cisco Firepower sw:NetflowMonSession:type managed
        object property"
    ::= { cfprSwNetflowMonSessionEntry 13 }

cfprSwNetflowMonitorTable OBJECT-TYPE
    SYNTAX           SEQUENCE OF CfprSwNetflowMonitorEntry
    MAX-ACCESS       not-accessible
    STATUS           current
    DESCRIPTION
        "Cisco Firepower sw:NetflowMonitor managed object table"
    ::= { cfprSwObjects 61 }

cfprSwNetflowMonitorEntry OBJECT-TYPE
    SYNTAX           CfprSwNetflowMonitorEntry
    MAX-ACCESS       not-accessible
    STATUS           current
    DESCRIPTION
        "Entry for the cfprSwNetflowMonitorTable table."
    INDEX { cfprSwNetflowMonitorInstanceId }
    ::= { cfprSwNetflowMonitorTable 1 }

CfprSwNetflowMonitorEntry ::= SEQUENCE {
    cfprSwNetflowMonitorInstanceId                                   CfprManagedObjectId,
    cfprSwNetflowMonitorDn                                           CfprManagedObjectDn,
    cfprSwNetflowMonitorRn                                           SnmpAdminString,
    cfprSwNetflowMonitorActiveTimeout                                Gauge32,
    cfprSwNetflowMonitorAdminState                                   CfprSwFlowMonitorAdminState,
    cfprSwNetflowMonitorFlowRecordDefName                            SnmpAdminString,
    cfprSwNetflowMonitorInactiveTimeout                              Gauge32,
    cfprSwNetflowMonitorIsValidConfig                                CfprSwNFConfigStatus,
    cfprSwNetflowMonitorLifeCycle                                    CfprSwMonLifeCycle,
    cfprSwNetflowMonitorName                                         SnmpAdminString,
    cfprSwNetflowMonitorPeerDn                                       SnmpAdminString,
    cfprSwNetflowMonitorProtocol                                     CfprSwNetflowMonitorProtocol,
    cfprSwNetflowMonitorSwitchId                                     CfprNetworkSwitchId,
    cfprSwNetflowMonitorTransport                                    CfprSwEthLanFlowMonitorTransport,
    cfprSwNetflowMonitorType                                         CfprSwEthLanFlowMonitorType
}

cfprSwNetflowMonitorInstanceId OBJECT-TYPE
    SYNTAX       CfprManagedObjectId
    MAX-ACCESS   not-accessible
    STATUS       current
    DESCRIPTION
        "Instance identifier of the managed object."
    ::= { cfprSwNetflowMonitorEntry 1 }

cfprSwNetflowMonitorDn OBJECT-TYPE
    SYNTAX       CfprManagedObjectDn
    MAX-ACCESS   read-only
    STATUS       current
    DESCRIPTION
        "Cisco Firepower sw:NetflowMonitor:dn managed object property"
    ::= { cfprSwNetflowMonitorEntry 2 }

cfprSwNetflowMonitorRn OBJECT-TYPE
    SYNTAX       SnmpAdminString
    MAX-ACCESS   read-only
    STATUS       current
    DESCRIPTION
        "Cisco Firepower sw:NetflowMonitor:rn managed object property"
    ::= { cfprSwNetflowMonitorEntry 3 }

cfprSwNetflowMonitorActiveTimeout OBJECT-TYPE
    SYNTAX       Gauge32
    MAX-ACCESS   read-only
    STATUS       current
    DESCRIPTION
        "Cisco Firepower sw:NetflowMonitor:activeTimeout
        managed object property"
    ::= { cfprSwNetflowMonitorEntry 4 }

cfprSwNetflowMonitorAdminState OBJECT-TYPE
    SYNTAX       CfprSwFlowMonitorAdminState
    MAX-ACCESS   read-only
    STATUS       current
    DESCRIPTION
        "Cisco Firepower sw:NetflowMonitor:adminState managed
        object property"
    ::= { cfprSwNetflowMonitorEntry 5 }

cfprSwNetflowMonitorFlowRecordDefName OBJECT-TYPE
    SYNTAX       SnmpAdminString
    MAX-ACCESS   read-only
    STATUS       current
    DESCRIPTION
        "Cisco Firepower sw:NetflowMonitor:flowRecordDefName
        managed object property"
    ::= { cfprSwNetflowMonitorEntry 6 }

cfprSwNetflowMonitorInactiveTimeout OBJECT-TYPE
    SYNTAX       Gauge32
    MAX-ACCESS   read-only
    STATUS       current
    DESCRIPTION
        "Cisco Firepower sw:NetflowMonitor:inactiveTimeout
        managed object property"
    ::= { cfprSwNetflowMonitorEntry 7 }

cfprSwNetflowMonitorIsValidConfig OBJECT-TYPE
    SYNTAX       CfprSwNFConfigStatus
    MAX-ACCESS   read-only
    STATUS       current
    DESCRIPTION
        "Cisco Firepower sw:NetflowMonitor:isValidConfig
        managed object property"
    ::= { cfprSwNetflowMonitorEntry 8 }

cfprSwNetflowMonitorLifeCycle OBJECT-TYPE
    SYNTAX       CfprSwMonLifeCycle
    MAX-ACCESS   read-only
    STATUS       current
    DESCRIPTION
        "Cisco Firepower sw:NetflowMonitor:lifeCycle managed
        object property"
    ::= { cfprSwNetflowMonitorEntry 9 }

cfprSwNetflowMonitorName OBJECT-TYPE
    SYNTAX       SnmpAdminString
    MAX-ACCESS   read-only
    STATUS       current
    DESCRIPTION
        "Cisco Firepower sw:NetflowMonitor:name managed object property"
    ::= { cfprSwNetflowMonitorEntry 10 }

cfprSwNetflowMonitorPeerDn OBJECT-TYPE
    SYNTAX       SnmpAdminString
    MAX-ACCESS   read-only
    STATUS       current
    DESCRIPTION
        "Cisco Firepower sw:NetflowMonitor:peerDn managed object property"
    ::= { cfprSwNetflowMonitorEntry 11 }

cfprSwNetflowMonitorProtocol OBJECT-TYPE
    SYNTAX       CfprSwNetflowMonitorProtocol
    MAX-ACCESS   read-only
    STATUS       current
    DESCRIPTION
        "Cisco Firepower sw:NetflowMonitor:protocol managed
        object property"
    ::= { cfprSwNetflowMonitorEntry 12 }

cfprSwNetflowMonitorSwitchId OBJECT-TYPE
    SYNTAX       CfprNetworkSwitchId
    MAX-ACCESS   read-only
    STATUS       current
    DESCRIPTION
        "Cisco Firepower sw:NetflowMonitor:switchId managed
        object property"
    ::= { cfprSwNetflowMonitorEntry 13 }

cfprSwNetflowMonitorTransport OBJECT-TYPE
    SYNTAX       CfprSwEthLanFlowMonitorTransport
    MAX-ACCESS   read-only
    STATUS       current
    DESCRIPTION
        "Cisco Firepower sw:NetflowMonitor:transport managed
        object property"
    ::= { cfprSwNetflowMonitorEntry 14 }

cfprSwNetflowMonitorType OBJECT-TYPE
    SYNTAX       CfprSwEthLanFlowMonitorType
    MAX-ACCESS   read-only
    STATUS       current
    DESCRIPTION
        "Cisco Firepower sw:NetflowMonitor:type managed object property"
    ::= { cfprSwNetflowMonitorEntry 15 }

cfprSwNetflowMonitorRefTable OBJECT-TYPE
    SYNTAX           SEQUENCE OF CfprSwNetflowMonitorRefEntry
    MAX-ACCESS       not-accessible
    STATUS           current
    DESCRIPTION
        "Cisco Firepower sw:NetflowMonitorRef managed object table"
    ::= { cfprSwObjects 62 }

cfprSwNetflowMonitorRefEntry OBJECT-TYPE
    SYNTAX           CfprSwNetflowMonitorRefEntry
    MAX-ACCESS       not-accessible
    STATUS           current
    DESCRIPTION
        "Entry for the cfprSwNetflowMonitorRefTable table."
    INDEX { cfprSwNetflowMonitorRefInstanceId }
    ::= { cfprSwNetflowMonitorRefTable 1 }

CfprSwNetflowMonitorRefEntry ::= SEQUENCE {
    cfprSwNetflowMonitorRefInstanceId                                CfprManagedObjectId,
    cfprSwNetflowMonitorRefDn                                        CfprManagedObjectDn,
    cfprSwNetflowMonitorRefRn                                        SnmpAdminString,
    cfprSwNetflowMonitorRefDirection                                 CfprFabricDirection,
    cfprSwNetflowMonitorRefKeyType                                   CfprFabricFlowMonKeyType,
    cfprSwNetflowMonitorRefName                                      SnmpAdminString,
    cfprSwNetflowMonitorRefSourceDn                                  SnmpAdminString
}

cfprSwNetflowMonitorRefInstanceId OBJECT-TYPE
    SYNTAX       CfprManagedObjectId
    MAX-ACCESS   not-accessible
    STATUS       current
    DESCRIPTION
        "Instance identifier of the managed object."
    ::= { cfprSwNetflowMonitorRefEntry 1 }

cfprSwNetflowMonitorRefDn OBJECT-TYPE
    SYNTAX       CfprManagedObjectDn
    MAX-ACCESS   read-only
    STATUS       current
    DESCRIPTION
        "Cisco Firepower sw:NetflowMonitorRef:dn managed object property"
    ::= { cfprSwNetflowMonitorRefEntry 2 }

cfprSwNetflowMonitorRefRn OBJECT-TYPE
    SYNTAX       SnmpAdminString
    MAX-ACCESS   read-only
    STATUS       current
    DESCRIPTION
        "Cisco Firepower sw:NetflowMonitorRef:rn managed object property"
    ::= { cfprSwNetflowMonitorRefEntry 3 }

cfprSwNetflowMonitorRefDirection OBJECT-TYPE
    SYNTAX       CfprFabricDirection
    MAX-ACCESS   read-only
    STATUS       current
    DESCRIPTION
        "Cisco Firepower sw:NetflowMonitorRef:direction
        managed object property"
    ::= { cfprSwNetflowMonitorRefEntry 4 }

cfprSwNetflowMonitorRefKeyType OBJECT-TYPE
    SYNTAX       CfprFabricFlowMonKeyType
    MAX-ACCESS   read-only
    STATUS       current
    DESCRIPTION
        "Cisco Firepower sw:NetflowMonitorRef:keyType managed
        object property"
    ::= { cfprSwNetflowMonitorRefEntry 5 }

cfprSwNetflowMonitorRefName OBJECT-TYPE
    SYNTAX       SnmpAdminString
    MAX-ACCESS   read-only
    STATUS       current
    DESCRIPTION
        "Cisco Firepower sw:NetflowMonitorRef:name managed
        object property"
    ::= { cfprSwNetflowMonitorRefEntry 6 }

cfprSwNetflowMonitorRefSourceDn OBJECT-TYPE
    SYNTAX       SnmpAdminString
    MAX-ACCESS   read-only
    STATUS       current
    DESCRIPTION
        "Cisco Firepower sw:NetflowMonitorRef:sourceDn
        managed object property"
    ::= { cfprSwNetflowMonitorRefEntry 7 }

cfprSwNetflowRecordDefTable OBJECT-TYPE
    SYNTAX           SEQUENCE OF CfprSwNetflowRecordDefEntry
    MAX-ACCESS       not-accessible
    STATUS           current
    DESCRIPTION
        "Cisco Firepower sw:NetflowRecordDef managed object table"
    ::= { cfprSwObjects 63 }

cfprSwNetflowRecordDefEntry OBJECT-TYPE
    SYNTAX           CfprSwNetflowRecordDefEntry
    MAX-ACCESS       not-accessible
    STATUS           current
    DESCRIPTION
        "Entry for the cfprSwNetflowRecordDefTable table."
    INDEX { cfprSwNetflowRecordDefInstanceId }
    ::= { cfprSwNetflowRecordDefTable 1 }

CfprSwNetflowRecordDefEntry ::= SEQUENCE {
    cfprSwNetflowRecordDefInstanceId                                 CfprManagedObjectId,
    cfprSwNetflowRecordDefDn                                         CfprManagedObjectDn,
    cfprSwNetflowRecordDefRn                                         SnmpAdminString,
    cfprSwNetflowRecordDefIpv4keys                                   CfprFabricFlowMonIpv4Keys,
    cfprSwNetflowRecordDefIpv6keys                                   CfprFabricFlowMonIpv6Keys,
    cfprSwNetflowRecordDefKeyType                                    CfprFabricFlowMonKeyType,
    cfprSwNetflowRecordDefL2keys                                     CfprFabricFlowMonL2Keys,
    cfprSwNetflowRecordDefLifeCycle                                  CfprSwMonLifeCycle,
    cfprSwNetflowRecordDefName                                       SnmpAdminString,
    cfprSwNetflowRecordDefNonkeys                                    CfprFabricFlowMonNonKeys,
    cfprSwNetflowRecordDefPeerDn                                     SnmpAdminString,
    cfprSwNetflowRecordDefProtocol                                   CfprSwNetflowRecordDefProtocol,
    cfprSwNetflowRecordDefSwitchId                                   CfprNetworkSwitchId,
    cfprSwNetflowRecordDefTransport                                  CfprSwEthLanFlowRecordDefTransport,
    cfprSwNetflowRecordDefType                                       CfprSwEthLanFlowRecordDefType
}

cfprSwNetflowRecordDefInstanceId OBJECT-TYPE
    SYNTAX       CfprManagedObjectId
    MAX-ACCESS   not-accessible
    STATUS       current
    DESCRIPTION
        "Instance identifier of the managed object."
    ::= { cfprSwNetflowRecordDefEntry 1 }

cfprSwNetflowRecordDefDn OBJECT-TYPE
    SYNTAX       CfprManagedObjectDn
    MAX-ACCESS   read-only
    STATUS       current
    DESCRIPTION
        "Cisco Firepower sw:NetflowRecordDef:dn managed object property"
    ::= { cfprSwNetflowRecordDefEntry 2 }

cfprSwNetflowRecordDefRn OBJECT-TYPE
    SYNTAX       SnmpAdminString
    MAX-ACCESS   read-only
    STATUS       current
    DESCRIPTION
        "Cisco Firepower sw:NetflowRecordDef:rn managed object property"
    ::= { cfprSwNetflowRecordDefEntry 3 }

cfprSwNetflowRecordDefIpv4keys OBJECT-TYPE
    SYNTAX       CfprFabricFlowMonIpv4Keys
    MAX-ACCESS   read-only
    STATUS       current
    DESCRIPTION
        "Cisco Firepower sw:NetflowRecordDef:ipv4keys managed
        object property"
    ::= { cfprSwNetflowRecordDefEntry 4 }

cfprSwNetflowRecordDefIpv6keys OBJECT-TYPE
    SYNTAX       CfprFabricFlowMonIpv6Keys
    MAX-ACCESS   read-only
    STATUS       current
    DESCRIPTION
        "Cisco Firepower sw:NetflowRecordDef:ipv6keys managed
        object property"
    ::= { cfprSwNetflowRecordDefEntry 5 }

cfprSwNetflowRecordDefKeyType OBJECT-TYPE
    SYNTAX       CfprFabricFlowMonKeyType
    MAX-ACCESS   read-only
    STATUS       current
    DESCRIPTION
        "Cisco Firepower sw:NetflowRecordDef:keyType managed
        object property"
    ::= { cfprSwNetflowRecordDefEntry 6 }

cfprSwNetflowRecordDefL2keys OBJECT-TYPE
    SYNTAX       CfprFabricFlowMonL2Keys
    MAX-ACCESS   read-only
    STATUS       current
    DESCRIPTION
        "Cisco Firepower sw:NetflowRecordDef:l2keys managed
        object property"
    ::= { cfprSwNetflowRecordDefEntry 7 }

cfprSwNetflowRecordDefLifeCycle OBJECT-TYPE
    SYNTAX       CfprSwMonLifeCycle
    MAX-ACCESS   read-only
    STATUS       current
    DESCRIPTION
        "Cisco Firepower sw:NetflowRecordDef:lifeCycle
        managed object property"
    ::= { cfprSwNetflowRecordDefEntry 8 }

cfprSwNetflowRecordDefName OBJECT-TYPE
    SYNTAX       SnmpAdminString
    MAX-ACCESS   read-only
    STATUS       current
    DESCRIPTION
        "Cisco Firepower sw:NetflowRecordDef:name managed object property"
    ::= { cfprSwNetflowRecordDefEntry 9 }

cfprSwNetflowRecordDefNonkeys OBJECT-TYPE
    SYNTAX       CfprFabricFlowMonNonKeys
    MAX-ACCESS   read-only
    STATUS       current
    DESCRIPTION
        "Cisco Firepower sw:NetflowRecordDef:nonkeys managed
        object property"
    ::= { cfprSwNetflowRecordDefEntry 10 }

cfprSwNetflowRecordDefPeerDn OBJECT-TYPE
    SYNTAX       SnmpAdminString
    MAX-ACCESS   read-only
    STATUS       current
    DESCRIPTION
        "Cisco Firepower sw:NetflowRecordDef:peerDn managed
        object property"
    ::= { cfprSwNetflowRecordDefEntry 11 }

cfprSwNetflowRecordDefProtocol OBJECT-TYPE
    SYNTAX       CfprSwNetflowRecordDefProtocol
    MAX-ACCESS   read-only
    STATUS       current
    DESCRIPTION
        "Cisco Firepower sw:NetflowRecordDef:protocol managed
        object property"
    ::= { cfprSwNetflowRecordDefEntry 12 }

cfprSwNetflowRecordDefSwitchId OBJECT-TYPE
    SYNTAX       CfprNetworkSwitchId
    MAX-ACCESS   read-only
    STATUS       current
    DESCRIPTION
        "Cisco Firepower sw:NetflowRecordDef:switchId managed
        object property"
    ::= { cfprSwNetflowRecordDefEntry 13 }

cfprSwNetflowRecordDefTransport OBJECT-TYPE
    SYNTAX       CfprSwEthLanFlowRecordDefTransport
    MAX-ACCESS   read-only
    STATUS       current
    DESCRIPTION
        "Cisco Firepower sw:NetflowRecordDef:transport
        managed object property"
    ::= { cfprSwNetflowRecordDefEntry 14 }

cfprSwNetflowRecordDefType OBJECT-TYPE
    SYNTAX       CfprSwEthLanFlowRecordDefType
    MAX-ACCESS   read-only
    STATUS       current
    DESCRIPTION
        "Cisco Firepower sw:NetflowRecordDef:type managed object property"
    ::= { cfprSwNetflowRecordDefEntry 15 }

cfprSwPhysTable OBJECT-TYPE
    SYNTAX           SEQUENCE OF CfprSwPhysEntry
    MAX-ACCESS       not-accessible
    STATUS           current
    DESCRIPTION
        "Cisco Firepower sw:Phys managed object table"
    ::= { cfprSwObjects 64 }

cfprSwPhysEntry OBJECT-TYPE
    SYNTAX           CfprSwPhysEntry
    MAX-ACCESS       not-accessible
    STATUS           current
    DESCRIPTION
        "Entry for the cfprSwPhysTable table."
    INDEX { cfprSwPhysInstanceId }
    ::= { cfprSwPhysTable 1 }

CfprSwPhysEntry ::= SEQUENCE {
    cfprSwPhysInstanceId                                             CfprManagedObjectId,
    cfprSwPhysDn                                                     CfprManagedObjectDn,
    cfprSwPhysRn                                                     SnmpAdminString,
    cfprSwPhysConfMode                                               CfprSwConfMode,
    cfprSwPhysFsmDescr                                               SnmpAdminString,
    cfprSwPhysFsmPrev                                                SnmpAdminString,
    cfprSwPhysFsmProgr                                               Gauge32,
    cfprSwPhysFsmRmtInvErrCode                                       Gauge32,
    cfprSwPhysFsmRmtInvErrDescr                                      SnmpAdminString,
    cfprSwPhysFsmRmtInvRslt                                          CfprConditionRemoteInvRslt,
    cfprSwPhysFsmStageDescr                                          SnmpAdminString,
    cfprSwPhysFsmStamp                                               DateAndTime,
    cfprSwPhysFsmStatus                                              SnmpAdminString,
    cfprSwPhysFsmTry                                                 Gauge32
}

cfprSwPhysInstanceId OBJECT-TYPE
    SYNTAX       CfprManagedObjectId
    MAX-ACCESS   not-accessible
    STATUS       current
    DESCRIPTION
        "Instance identifier of the managed object."
    ::= { cfprSwPhysEntry 1 }

cfprSwPhysDn OBJECT-TYPE
    SYNTAX       CfprManagedObjectDn
    MAX-ACCESS   read-only
    STATUS       current
    DESCRIPTION
        "Cisco Firepower sw:Phys:dn managed object property"
    ::= { cfprSwPhysEntry 2 }

cfprSwPhysRn OBJECT-TYPE
    SYNTAX       SnmpAdminString
    MAX-ACCESS   read-only
    STATUS       current
    DESCRIPTION
        "Cisco Firepower sw:Phys:rn managed object property"
    ::= { cfprSwPhysEntry 3 }

cfprSwPhysConfMode OBJECT-TYPE
    SYNTAX       CfprSwConfMode
    MAX-ACCESS   read-only
    STATUS       current
    DESCRIPTION
        "Cisco Firepower sw:Phys:confMode managed object property"
    ::= { cfprSwPhysEntry 4 }

cfprSwPhysFsmDescr OBJECT-TYPE
    SYNTAX       SnmpAdminString
    MAX-ACCESS   read-only
    STATUS       current
    DESCRIPTION
        "Cisco Firepower sw:Phys:fsmDescr managed object property"
    ::= { cfprSwPhysEntry 5 }

cfprSwPhysFsmPrev OBJECT-TYPE
    SYNTAX       SnmpAdminString
    MAX-ACCESS   read-only
    STATUS       current
    DESCRIPTION
        "Cisco Firepower sw:Phys:fsmPrev managed object property"
    ::= { cfprSwPhysEntry 6 }

cfprSwPhysFsmProgr OBJECT-TYPE
    SYNTAX       Gauge32
    MAX-ACCESS   read-only
    STATUS       current
    DESCRIPTION
        "Cisco Firepower sw:Phys:fsmProgr managed object property"
    ::= { cfprSwPhysEntry 7 }

cfprSwPhysFsmRmtInvErrCode OBJECT-TYPE
    SYNTAX       Gauge32
    MAX-ACCESS   read-only
    STATUS       current
    DESCRIPTION
        "Cisco Firepower sw:Phys:fsmRmtInvErrCode managed object property"
    ::= { cfprSwPhysEntry 8 }

cfprSwPhysFsmRmtInvErrDescr OBJECT-TYPE
    SYNTAX       SnmpAdminString
    MAX-ACCESS   read-only
    STATUS       current
    DESCRIPTION
        "Cisco Firepower sw:Phys:fsmRmtInvErrDescr managed
        object property"
    ::= { cfprSwPhysEntry 9 }

cfprSwPhysFsmRmtInvRslt OBJECT-TYPE
    SYNTAX       CfprConditionRemoteInvRslt
    MAX-ACCESS   read-only
    STATUS       current
    DESCRIPTION
        "Cisco Firepower sw:Phys:fsmRmtInvRslt managed object property"
    ::= { cfprSwPhysEntry 10 }

cfprSwPhysFsmStageDescr OBJECT-TYPE
    SYNTAX       SnmpAdminString
    MAX-ACCESS   read-only
    STATUS       current
    DESCRIPTION
        "Cisco Firepower sw:Phys:fsmStageDescr managed object property"
    ::= { cfprSwPhysEntry 11 }

cfprSwPhysFsmStamp OBJECT-TYPE
    SYNTAX       DateAndTime
    MAX-ACCESS   read-only
    STATUS       current
    DESCRIPTION
        "Cisco Firepower sw:Phys:fsmStamp managed object property"
    ::= { cfprSwPhysEntry 12 }

cfprSwPhysFsmStatus OBJECT-TYPE
    SYNTAX       SnmpAdminString
    MAX-ACCESS   read-only
    STATUS       current
    DESCRIPTION
        "Cisco Firepower sw:Phys:fsmStatus managed object property"
    ::= { cfprSwPhysEntry 13 }

cfprSwPhysFsmTry OBJECT-TYPE
    SYNTAX       Gauge32
    MAX-ACCESS   read-only
    STATUS       current
    DESCRIPTION
        "Cisco Firepower sw:Phys:fsmTry managed object property"
    ::= { cfprSwPhysEntry 14 }

cfprSwPhysEtherEpTable OBJECT-TYPE
    SYNTAX           SEQUENCE OF CfprSwPhysEtherEpEntry
    MAX-ACCESS       not-accessible
    STATUS           current
    DESCRIPTION
        "Cisco Firepower sw:PhysEtherEp managed object table"
    ::= { cfprSwObjects 65 }

cfprSwPhysEtherEpEntry OBJECT-TYPE
    SYNTAX           CfprSwPhysEtherEpEntry
    MAX-ACCESS       not-accessible
    STATUS           current
    DESCRIPTION
        "Entry for the cfprSwPhysEtherEpTable table."
    INDEX { cfprSwPhysEtherEpInstanceId }
    ::= { cfprSwPhysEtherEpTable 1 }

CfprSwPhysEtherEpEntry ::= SEQUENCE {
    cfprSwPhysEtherEpInstanceId                                      CfprManagedObjectId,
    cfprSwPhysEtherEpDn                                              CfprManagedObjectDn,
    cfprSwPhysEtherEpRn                                              SnmpAdminString,
    cfprSwPhysEtherEpAdminState                                      CfprFabricAdminState,
    cfprSwPhysEtherEpAggrPortId                                      Gauge32,
    cfprSwPhysEtherEpChassisId                                       Gauge32,
    cfprSwPhysEtherEpEpDn                                            SnmpAdminString,
    cfprSwPhysEtherEpIfRole                                          CfprNetworkPortRole,
    cfprSwPhysEtherEpIfType                                          CfprSwPIoEpIfType,
    cfprSwPhysEtherEpLc                                              CfprSwPIoEpLc,
    cfprSwPhysEtherEpLocale                                          CfprNetworkLocale,
    cfprSwPhysEtherEpName                                            SnmpAdminString,
    cfprSwPhysEtherEpPeerAggrPortId                                  Gauge32,
    cfprSwPhysEtherEpPeerChassisId                                   Gauge32,
    cfprSwPhysEtherEpPeerDn                                          SnmpAdminString,
    cfprSwPhysEtherEpPeerPortId                                      Gauge32,
    cfprSwPhysEtherEpPeerSlotId                                      Gauge32,
    cfprSwPhysEtherEpPortId                                          Gauge32,
    cfprSwPhysEtherEpSlotId                                          Gauge32,
    cfprSwPhysEtherEpSwitchId                                        CfprNetworkSwitchId,
    cfprSwPhysEtherEpTransport                                       CfprNetworkTransport,
    cfprSwPhysEtherEpType                                            CfprNetworkConnectionType
}

cfprSwPhysEtherEpInstanceId OBJECT-TYPE
    SYNTAX       CfprManagedObjectId
    MAX-ACCESS   not-accessible
    STATUS       current
    DESCRIPTION
        "Instance identifier of the managed object."
    ::= { cfprSwPhysEtherEpEntry 1 }

cfprSwPhysEtherEpDn OBJECT-TYPE
    SYNTAX       CfprManagedObjectDn
    MAX-ACCESS   read-only
    STATUS       current
    DESCRIPTION
        "Cisco Firepower sw:PhysEtherEp:dn managed object property"
    ::= { cfprSwPhysEtherEpEntry 2 }

cfprSwPhysEtherEpRn OBJECT-TYPE
    SYNTAX       SnmpAdminString
    MAX-ACCESS   read-only
    STATUS       current
    DESCRIPTION
        "Cisco Firepower sw:PhysEtherEp:rn managed object property"
    ::= { cfprSwPhysEtherEpEntry 3 }

cfprSwPhysEtherEpAdminState OBJECT-TYPE
    SYNTAX       CfprFabricAdminState
    MAX-ACCESS   read-only
    STATUS       current
    DESCRIPTION
        "Cisco Firepower sw:PhysEtherEp:adminState managed
        object property"
    ::= { cfprSwPhysEtherEpEntry 4 }

cfprSwPhysEtherEpAggrPortId OBJECT-TYPE
    SYNTAX       Gauge32
    MAX-ACCESS   read-only
    STATUS       current
    DESCRIPTION
        "Cisco Firepower sw:PhysEtherEp:aggrPortId managed
        object property"
    ::= { cfprSwPhysEtherEpEntry 5 }

cfprSwPhysEtherEpChassisId OBJECT-TYPE
    SYNTAX       Gauge32
    MAX-ACCESS   read-only
    STATUS       current
    DESCRIPTION
        "Cisco Firepower sw:PhysEtherEp:chassisId managed object property"
    ::= { cfprSwPhysEtherEpEntry 6 }

cfprSwPhysEtherEpEpDn OBJECT-TYPE
    SYNTAX       SnmpAdminString
    MAX-ACCESS   read-only
    STATUS       current
    DESCRIPTION
        "Cisco Firepower sw:PhysEtherEp:epDn managed object property"
    ::= { cfprSwPhysEtherEpEntry 7 }

cfprSwPhysEtherEpIfRole OBJECT-TYPE
    SYNTAX       CfprNetworkPortRole
    MAX-ACCESS   read-only
    STATUS       current
    DESCRIPTION
        "Cisco Firepower sw:PhysEtherEp:ifRole managed object property"
    ::= { cfprSwPhysEtherEpEntry 8 }

cfprSwPhysEtherEpIfType OBJECT-TYPE
    SYNTAX       CfprSwPIoEpIfType
    MAX-ACCESS   read-only
    STATUS       current
    DESCRIPTION
        "Cisco Firepower sw:PhysEtherEp:ifType managed object property"
    ::= { cfprSwPhysEtherEpEntry 9 }

cfprSwPhysEtherEpLc OBJECT-TYPE
    SYNTAX       CfprSwPIoEpLc
    MAX-ACCESS   read-only
    STATUS       current
    DESCRIPTION
        "Cisco Firepower sw:PhysEtherEp:lc managed object property"
    ::= { cfprSwPhysEtherEpEntry 10 }

cfprSwPhysEtherEpLocale OBJECT-TYPE
    SYNTAX       CfprNetworkLocale
    MAX-ACCESS   read-only
    STATUS       current
    DESCRIPTION
        "Cisco Firepower sw:PhysEtherEp:locale managed object property"
    ::= { cfprSwPhysEtherEpEntry 11 }

cfprSwPhysEtherEpName OBJECT-TYPE
    SYNTAX       SnmpAdminString
    MAX-ACCESS   read-only
    STATUS       current
    DESCRIPTION
        "Cisco Firepower sw:PhysEtherEp:name managed object property"
    ::= { cfprSwPhysEtherEpEntry 12 }

cfprSwPhysEtherEpPeerAggrPortId OBJECT-TYPE
    SYNTAX       Gauge32
    MAX-ACCESS   read-only
    STATUS       current
    DESCRIPTION
        "Cisco Firepower sw:PhysEtherEp:peerAggrPortId
        managed object property"
    ::= { cfprSwPhysEtherEpEntry 13 }

cfprSwPhysEtherEpPeerChassisId OBJECT-TYPE
    SYNTAX       Gauge32
    MAX-ACCESS   read-only
    STATUS       current
    DESCRIPTION
        "Cisco Firepower sw:PhysEtherEp:peerChassisId managed
        object property"
    ::= { cfprSwPhysEtherEpEntry 14 }

cfprSwPhysEtherEpPeerDn OBJECT-TYPE
    SYNTAX       SnmpAdminString
    MAX-ACCESS   read-only
    STATUS       current
    DESCRIPTION
        "Cisco Firepower sw:PhysEtherEp:peerDn managed object property"
    ::= { cfprSwPhysEtherEpEntry 15 }

cfprSwPhysEtherEpPeerPortId OBJECT-TYPE
    SYNTAX       Gauge32
    MAX-ACCESS   read-only
    STATUS       current
    DESCRIPTION
        "Cisco Firepower sw:PhysEtherEp:peerPortId managed
        object property"
    ::= { cfprSwPhysEtherEpEntry 16 }

cfprSwPhysEtherEpPeerSlotId OBJECT-TYPE
    SYNTAX       Gauge32
    MAX-ACCESS   read-only
    STATUS       current
    DESCRIPTION
        "Cisco Firepower sw:PhysEtherEp:peerSlotId managed
        object property"
    ::= { cfprSwPhysEtherEpEntry 17 }

cfprSwPhysEtherEpPortId OBJECT-TYPE
    SYNTAX       Gauge32
    MAX-ACCESS   read-only
    STATUS       current
    DESCRIPTION
        "Cisco Firepower sw:PhysEtherEp:portId managed object property"
    ::= { cfprSwPhysEtherEpEntry 18 }

cfprSwPhysEtherEpSlotId OBJECT-TYPE
    SYNTAX       Gauge32
    MAX-ACCESS   read-only
    STATUS       current
    DESCRIPTION
        "Cisco Firepower sw:PhysEtherEp:slotId managed object property"
    ::= { cfprSwPhysEtherEpEntry 19 }

cfprSwPhysEtherEpSwitchId OBJECT-TYPE
    SYNTAX       CfprNetworkSwitchId
    MAX-ACCESS   read-only
    STATUS       current
    DESCRIPTION
        "Cisco Firepower sw:PhysEtherEp:switchId managed object property"
    ::= { cfprSwPhysEtherEpEntry 20 }

cfprSwPhysEtherEpTransport OBJECT-TYPE
    SYNTAX       CfprNetworkTransport
    MAX-ACCESS   read-only
    STATUS       current
    DESCRIPTION
        "Cisco Firepower sw:PhysEtherEp:transport managed object property"
    ::= { cfprSwPhysEtherEpEntry 21 }

cfprSwPhysEtherEpType OBJECT-TYPE
    SYNTAX       CfprNetworkConnectionType
    MAX-ACCESS   read-only
    STATUS       current
    DESCRIPTION
        "Cisco Firepower sw:PhysEtherEp:type managed object property"
    ::= { cfprSwPhysEtherEpEntry 22 }

cfprSwPhysFcEpTable OBJECT-TYPE
    SYNTAX           SEQUENCE OF CfprSwPhysFcEpEntry
    MAX-ACCESS       not-accessible
    STATUS           current
    DESCRIPTION
        "Cisco Firepower sw:PhysFcEp managed object table"
    ::= { cfprSwObjects 66 }

cfprSwPhysFcEpEntry OBJECT-TYPE
    SYNTAX           CfprSwPhysFcEpEntry
    MAX-ACCESS       not-accessible
    STATUS           current
    DESCRIPTION
        "Entry for the cfprSwPhysFcEpTable table."
    INDEX { cfprSwPhysFcEpInstanceId }
    ::= { cfprSwPhysFcEpTable 1 }

CfprSwPhysFcEpEntry ::= SEQUENCE {
    cfprSwPhysFcEpInstanceId                                         CfprManagedObjectId,
    cfprSwPhysFcEpDn                                                 CfprManagedObjectDn,
    cfprSwPhysFcEpRn                                                 SnmpAdminString,
    cfprSwPhysFcEpAdminState                                         CfprFabricAdminState,
    cfprSwPhysFcEpAggrPortId                                         Gauge32,
    cfprSwPhysFcEpChassisId                                          Gauge32,
    cfprSwPhysFcEpEpDn                                               SnmpAdminString,
    cfprSwPhysFcEpIfRole                                             CfprNetworkPortRole,
    cfprSwPhysFcEpIfType                                             CfprSwPIoEpIfType,
    cfprSwPhysFcEpLc                                                 CfprSwPIoEpLc,
    cfprSwPhysFcEpLocale                                             CfprNetworkLocale,
    cfprSwPhysFcEpName                                               SnmpAdminString,
    cfprSwPhysFcEpPeerAggrPortId                                     Gauge32,
    cfprSwPhysFcEpPeerChassisId                                      Gauge32,
    cfprSwPhysFcEpPeerDn                                             SnmpAdminString,
    cfprSwPhysFcEpPeerPortId                                         Gauge32,
    cfprSwPhysFcEpPeerSlotId                                         Gauge32,
    cfprSwPhysFcEpPortId                                             Gauge32,
    cfprSwPhysFcEpSlotId                                             Gauge32,
    cfprSwPhysFcEpSwitchId                                           CfprNetworkSwitchId,
    cfprSwPhysFcEpTransport                                          CfprNetworkTransport,
    cfprSwPhysFcEpType                                               CfprNetworkConnectionType
}

cfprSwPhysFcEpInstanceId OBJECT-TYPE
    SYNTAX       CfprManagedObjectId
    MAX-ACCESS   not-accessible
    STATUS       current
    DESCRIPTION
        "Instance identifier of the managed object."
    ::= { cfprSwPhysFcEpEntry 1 }

cfprSwPhysFcEpDn OBJECT-TYPE
    SYNTAX       CfprManagedObjectDn
    MAX-ACCESS   read-only
    STATUS       current
    DESCRIPTION
        "Cisco Firepower sw:PhysFcEp:dn managed object property"
    ::= { cfprSwPhysFcEpEntry 2 }

cfprSwPhysFcEpRn OBJECT-TYPE
    SYNTAX       SnmpAdminString
    MAX-ACCESS   read-only
    STATUS       current
    DESCRIPTION
        "Cisco Firepower sw:PhysFcEp:rn managed object property"
    ::= { cfprSwPhysFcEpEntry 3 }

cfprSwPhysFcEpAdminState OBJECT-TYPE
    SYNTAX       CfprFabricAdminState
    MAX-ACCESS   read-only
    STATUS       current
    DESCRIPTION
        "Cisco Firepower sw:PhysFcEp:adminState managed object property"
    ::= { cfprSwPhysFcEpEntry 4 }

cfprSwPhysFcEpAggrPortId OBJECT-TYPE
    SYNTAX       Gauge32
    MAX-ACCESS   read-only
    STATUS       current
    DESCRIPTION
        "Cisco Firepower sw:PhysFcEp:aggrPortId managed object property"
    ::= { cfprSwPhysFcEpEntry 5 }

cfprSwPhysFcEpChassisId OBJECT-TYPE
    SYNTAX       Gauge32
    MAX-ACCESS   read-only
    STATUS       current
    DESCRIPTION
        "Cisco Firepower sw:PhysFcEp:chassisId managed object property"
    ::= { cfprSwPhysFcEpEntry 6 }

cfprSwPhysFcEpEpDn OBJECT-TYPE
    SYNTAX       SnmpAdminString
    MAX-ACCESS   read-only
    STATUS       current
    DESCRIPTION
        "Cisco Firepower sw:PhysFcEp:epDn managed object property"
    ::= { cfprSwPhysFcEpEntry 7 }

cfprSwPhysFcEpIfRole OBJECT-TYPE
    SYNTAX       CfprNetworkPortRole
    MAX-ACCESS   read-only
    STATUS       current
    DESCRIPTION
        "Cisco Firepower sw:PhysFcEp:ifRole managed object property"
    ::= { cfprSwPhysFcEpEntry 8 }

cfprSwPhysFcEpIfType OBJECT-TYPE
    SYNTAX       CfprSwPIoEpIfType
    MAX-ACCESS   read-only
    STATUS       current
    DESCRIPTION
        "Cisco Firepower sw:PhysFcEp:ifType managed object property"
    ::= { cfprSwPhysFcEpEntry 9 }

cfprSwPhysFcEpLc OBJECT-TYPE
    SYNTAX       CfprSwPIoEpLc
    MAX-ACCESS   read-only
    STATUS       current
    DESCRIPTION
        "Cisco Firepower sw:PhysFcEp:lc managed object property"
    ::= { cfprSwPhysFcEpEntry 10 }

cfprSwPhysFcEpLocale OBJECT-TYPE
    SYNTAX       CfprNetworkLocale
    MAX-ACCESS   read-only
    STATUS       current
    DESCRIPTION
        "Cisco Firepower sw:PhysFcEp:locale managed object property"
    ::= { cfprSwPhysFcEpEntry 11 }

cfprSwPhysFcEpName OBJECT-TYPE
    SYNTAX       SnmpAdminString
    MAX-ACCESS   read-only
    STATUS       current
    DESCRIPTION
        "Cisco Firepower sw:PhysFcEp:name managed object property"
    ::= { cfprSwPhysFcEpEntry 12 }

cfprSwPhysFcEpPeerAggrPortId OBJECT-TYPE
    SYNTAX       Gauge32
    MAX-ACCESS   read-only
    STATUS       current
    DESCRIPTION
        "Cisco Firepower sw:PhysFcEp:peerAggrPortId managed
        object property"
    ::= { cfprSwPhysFcEpEntry 13 }

cfprSwPhysFcEpPeerChassisId OBJECT-TYPE
    SYNTAX       Gauge32
    MAX-ACCESS   read-only
    STATUS       current
    DESCRIPTION
        "Cisco Firepower sw:PhysFcEp:peerChassisId managed
        object property"
    ::= { cfprSwPhysFcEpEntry 14 }

cfprSwPhysFcEpPeerDn OBJECT-TYPE
    SYNTAX       SnmpAdminString
    MAX-ACCESS   read-only
    STATUS       current
    DESCRIPTION
        "Cisco Firepower sw:PhysFcEp:peerDn managed object property"
    ::= { cfprSwPhysFcEpEntry 15 }

cfprSwPhysFcEpPeerPortId OBJECT-TYPE
    SYNTAX       Gauge32
    MAX-ACCESS   read-only
    STATUS       current
    DESCRIPTION
        "Cisco Firepower sw:PhysFcEp:peerPortId managed object property"
    ::= { cfprSwPhysFcEpEntry 16 }

cfprSwPhysFcEpPeerSlotId OBJECT-TYPE
    SYNTAX       Gauge32
    MAX-ACCESS   read-only
    STATUS       current
    DESCRIPTION
        "Cisco Firepower sw:PhysFcEp:peerSlotId managed object property"
    ::= { cfprSwPhysFcEpEntry 17 }

cfprSwPhysFcEpPortId OBJECT-TYPE
    SYNTAX       Gauge32
    MAX-ACCESS   read-only
    STATUS       current
    DESCRIPTION
        "Cisco Firepower sw:PhysFcEp:portId managed object property"
    ::= { cfprSwPhysFcEpEntry 18 }

cfprSwPhysFcEpSlotId OBJECT-TYPE
    SYNTAX       Gauge32
    MAX-ACCESS   read-only
    STATUS       current
    DESCRIPTION
        "Cisco Firepower sw:PhysFcEp:slotId managed object property"
    ::= { cfprSwPhysFcEpEntry 19 }

cfprSwPhysFcEpSwitchId OBJECT-TYPE
    SYNTAX       CfprNetworkSwitchId
    MAX-ACCESS   read-only
    STATUS       current
    DESCRIPTION
        "Cisco Firepower sw:PhysFcEp:switchId managed object property"
    ::= { cfprSwPhysFcEpEntry 20 }

cfprSwPhysFcEpTransport OBJECT-TYPE
    SYNTAX       CfprNetworkTransport
    MAX-ACCESS   read-only
    STATUS       current
    DESCRIPTION
        "Cisco Firepower sw:PhysFcEp:transport managed object property"
    ::= { cfprSwPhysFcEpEntry 21 }

cfprSwPhysFcEpType OBJECT-TYPE
    SYNTAX       CfprNetworkConnectionType
    MAX-ACCESS   read-only
    STATUS       current
    DESCRIPTION
        "Cisco Firepower sw:PhysFcEp:type managed object property"
    ::= { cfprSwPhysFcEpEntry 22 }

cfprSwPhysFsmTable OBJECT-TYPE
    SYNTAX           SEQUENCE OF CfprSwPhysFsmEntry
    MAX-ACCESS       not-accessible
    STATUS           current
    DESCRIPTION
        "Cisco Firepower sw:PhysFsm managed object table"
    ::= { cfprSwObjects 67 }

cfprSwPhysFsmEntry OBJECT-TYPE
    SYNTAX           CfprSwPhysFsmEntry
    MAX-ACCESS       not-accessible
    STATUS           current
    DESCRIPTION
        "Entry for the cfprSwPhysFsmTable table."
    INDEX { cfprSwPhysFsmInstanceId }
    ::= { cfprSwPhysFsmTable 1 }

CfprSwPhysFsmEntry ::= SEQUENCE {
    cfprSwPhysFsmInstanceId                                          CfprManagedObjectId,
    cfprSwPhysFsmDn                                                  CfprManagedObjectDn,
    cfprSwPhysFsmRn                                                  SnmpAdminString,
    cfprSwPhysFsmCompletionTime                                      DateAndTime,
    cfprSwPhysFsmCurrentFsm                                          CfprSwPhysFsmCurrentFsm,
    cfprSwPhysFsmDescrData                                           SnmpAdminString,
    cfprSwPhysFsmFsmStatus                                           CfprFsmFsmStageStatus,
    cfprSwPhysFsmProgress                                            Gauge32,
    cfprSwPhysFsmRmtErrCode                                          Gauge32,
    cfprSwPhysFsmRmtErrDescr                                         SnmpAdminString,
    cfprSwPhysFsmRmtRslt                                             CfprConditionRemoteInvRslt
}

cfprSwPhysFsmInstanceId OBJECT-TYPE
    SYNTAX       CfprManagedObjectId
    MAX-ACCESS   not-accessible
    STATUS       current
    DESCRIPTION
        "Instance identifier of the managed object."
    ::= { cfprSwPhysFsmEntry 1 }

cfprSwPhysFsmDn OBJECT-TYPE
    SYNTAX       CfprManagedObjectDn
    MAX-ACCESS   read-only
    STATUS       current
    DESCRIPTION
        "Cisco Firepower sw:PhysFsm:dn managed object property"
    ::= { cfprSwPhysFsmEntry 2 }

cfprSwPhysFsmRn OBJECT-TYPE
    SYNTAX       SnmpAdminString
    MAX-ACCESS   read-only
    STATUS       current
    DESCRIPTION
        "Cisco Firepower sw:PhysFsm:rn managed object property"
    ::= { cfprSwPhysFsmEntry 3 }

cfprSwPhysFsmCompletionTime OBJECT-TYPE
    SYNTAX       DateAndTime
    MAX-ACCESS   read-only
    STATUS       current
    DESCRIPTION
        "Cisco Firepower sw:PhysFsm:completionTime managed
        object property"
    ::= { cfprSwPhysFsmEntry 4 }

cfprSwPhysFsmCurrentFsm OBJECT-TYPE
    SYNTAX       CfprSwPhysFsmCurrentFsm
    MAX-ACCESS   read-only
    STATUS       current
    DESCRIPTION
        "Cisco Firepower sw:PhysFsm:currentFsm managed object property"
    ::= { cfprSwPhysFsmEntry 5 }

cfprSwPhysFsmDescrData OBJECT-TYPE
    SYNTAX       SnmpAdminString
    MAX-ACCESS   read-only
    STATUS       current
    DESCRIPTION
        "Cisco Firepower sw:PhysFsm:descr managed object property"
    ::= { cfprSwPhysFsmEntry 6 }

cfprSwPhysFsmFsmStatus OBJECT-TYPE
    SYNTAX       CfprFsmFsmStageStatus
    MAX-ACCESS   read-only
    STATUS       current
    DESCRIPTION
        "Cisco Firepower sw:PhysFsm:fsmStatus managed object property"
    ::= { cfprSwPhysFsmEntry 7 }

cfprSwPhysFsmProgress OBJECT-TYPE
    SYNTAX       Gauge32
    MAX-ACCESS   read-only
    STATUS       current
    DESCRIPTION
        "Cisco Firepower sw:PhysFsm:progress managed object property"
    ::= { cfprSwPhysFsmEntry 8 }

cfprSwPhysFsmRmtErrCode OBJECT-TYPE
    SYNTAX       Gauge32
    MAX-ACCESS   read-only
    STATUS       current
    DESCRIPTION
        "Cisco Firepower sw:PhysFsm:rmtErrCode managed object property"
    ::= { cfprSwPhysFsmEntry 9 }

cfprSwPhysFsmRmtErrDescr OBJECT-TYPE
    SYNTAX       SnmpAdminString
    MAX-ACCESS   read-only
    STATUS       current
    DESCRIPTION
        "Cisco Firepower sw:PhysFsm:rmtErrDescr managed object property"
    ::= { cfprSwPhysFsmEntry 10 }

cfprSwPhysFsmRmtRslt OBJECT-TYPE
    SYNTAX       CfprConditionRemoteInvRslt
    MAX-ACCESS   read-only
    STATUS       current
    DESCRIPTION
        "Cisco Firepower sw:PhysFsm:rmtRslt managed object property"
    ::= { cfprSwPhysFsmEntry 11 }

cfprSwPhysFsmStageTable OBJECT-TYPE
    SYNTAX           SEQUENCE OF CfprSwPhysFsmStageEntry
    MAX-ACCESS       not-accessible
    STATUS           current
    DESCRIPTION
        "Cisco Firepower sw:PhysFsmStage managed object table"
    ::= { cfprSwObjects 68 }

cfprSwPhysFsmStageEntry OBJECT-TYPE
    SYNTAX           CfprSwPhysFsmStageEntry
    MAX-ACCESS       not-accessible
    STATUS           current
    DESCRIPTION
        "Entry for the cfprSwPhysFsmStageTable table."
    INDEX { cfprSwPhysFsmStageInstanceId }
    ::= { cfprSwPhysFsmStageTable 1 }

CfprSwPhysFsmStageEntry ::= SEQUENCE {
    cfprSwPhysFsmStageInstanceId                                     CfprManagedObjectId,
    cfprSwPhysFsmStageDn                                             CfprManagedObjectDn,
    cfprSwPhysFsmStageRn                                             SnmpAdminString,
    cfprSwPhysFsmStageDescrData                                      SnmpAdminString,
    cfprSwPhysFsmStageLastUpdateTime                                 DateAndTime,
    cfprSwPhysFsmStageName                                           CfprSwPhysFsmStageName,
    cfprSwPhysFsmStageOrder                                          Gauge32,
    cfprSwPhysFsmStageRetry                                          Gauge32,
    cfprSwPhysFsmStageStageStatus                                    CfprFsmFsmStageStatus
}

cfprSwPhysFsmStageInstanceId OBJECT-TYPE
    SYNTAX       CfprManagedObjectId
    MAX-ACCESS   not-accessible
    STATUS       current
    DESCRIPTION
        "Instance identifier of the managed object."
    ::= { cfprSwPhysFsmStageEntry 1 }

cfprSwPhysFsmStageDn OBJECT-TYPE
    SYNTAX       CfprManagedObjectDn
    MAX-ACCESS   read-only
    STATUS       current
    DESCRIPTION
        "Cisco Firepower sw:PhysFsmStage:dn managed object property"
    ::= { cfprSwPhysFsmStageEntry 2 }

cfprSwPhysFsmStageRn OBJECT-TYPE
    SYNTAX       SnmpAdminString
    MAX-ACCESS   read-only
    STATUS       current
    DESCRIPTION
        "Cisco Firepower sw:PhysFsmStage:rn managed object property"
    ::= { cfprSwPhysFsmStageEntry 3 }

cfprSwPhysFsmStageDescrData OBJECT-TYPE
    SYNTAX       SnmpAdminString
    MAX-ACCESS   read-only
    STATUS       current
    DESCRIPTION
        "Cisco Firepower sw:PhysFsmStage:descr managed object property"
    ::= { cfprSwPhysFsmStageEntry 4 }

cfprSwPhysFsmStageLastUpdateTime OBJECT-TYPE
    SYNTAX       DateAndTime
    MAX-ACCESS   read-only
    STATUS       current
    DESCRIPTION
        "Cisco Firepower sw:PhysFsmStage:lastUpdateTime
        managed object property"
    ::= { cfprSwPhysFsmStageEntry 5 }

cfprSwPhysFsmStageName OBJECT-TYPE
    SYNTAX       CfprSwPhysFsmStageName
    MAX-ACCESS   read-only
    STATUS       current
    DESCRIPTION
        "Cisco Firepower sw:PhysFsmStage:name managed object property"
    ::= { cfprSwPhysFsmStageEntry 6 }

cfprSwPhysFsmStageOrder OBJECT-TYPE
    SYNTAX       Gauge32
    MAX-ACCESS   read-only
    STATUS       current
    DESCRIPTION
        "Cisco Firepower sw:PhysFsmStage:order managed object property"
    ::= { cfprSwPhysFsmStageEntry 7 }

cfprSwPhysFsmStageRetry OBJECT-TYPE
    SYNTAX       Gauge32
    MAX-ACCESS   read-only
    STATUS       current
    DESCRIPTION
        "Cisco Firepower sw:PhysFsmStage:retry managed object property"
    ::= { cfprSwPhysFsmStageEntry 8 }

cfprSwPhysFsmStageStageStatus OBJECT-TYPE
    SYNTAX       CfprFsmFsmStageStatus
    MAX-ACCESS   read-only
    STATUS       current
    DESCRIPTION
        "Cisco Firepower sw:PhysFsmStage:stageStatus managed
        object property"
    ::= { cfprSwPhysFsmStageEntry 9 }

cfprSwPhysFsmTaskTable OBJECT-TYPE
    SYNTAX           SEQUENCE OF CfprSwPhysFsmTaskEntry
    MAX-ACCESS       not-accessible
    STATUS           current
    DESCRIPTION
        "Cisco Firepower sw:PhysFsmTask managed object table"
    ::= { cfprSwObjects 69 }

cfprSwPhysFsmTaskEntry OBJECT-TYPE
    SYNTAX           CfprSwPhysFsmTaskEntry
    MAX-ACCESS       not-accessible
    STATUS           current
    DESCRIPTION
        "Entry for the cfprSwPhysFsmTaskTable table."
    INDEX { cfprSwPhysFsmTaskInstanceId }
    ::= { cfprSwPhysFsmTaskTable 1 }

CfprSwPhysFsmTaskEntry ::= SEQUENCE {
    cfprSwPhysFsmTaskInstanceId                                      CfprManagedObjectId,
    cfprSwPhysFsmTaskDn                                              CfprManagedObjectDn,
    cfprSwPhysFsmTaskRn                                              SnmpAdminString,
    cfprSwPhysFsmTaskCompletion                                      CfprFsmCompletion,
    cfprSwPhysFsmTaskFlags                                           CfprFsmFlags,
    cfprSwPhysFsmTaskItem                                            CfprSwPhysFsmTaskItem,
    cfprSwPhysFsmTaskSeqId                                           Gauge32
}

cfprSwPhysFsmTaskInstanceId OBJECT-TYPE
    SYNTAX       CfprManagedObjectId
    MAX-ACCESS   not-accessible
    STATUS       current
    DESCRIPTION
        "Instance identifier of the managed object."
    ::= { cfprSwPhysFsmTaskEntry 1 }

cfprSwPhysFsmTaskDn OBJECT-TYPE
    SYNTAX       CfprManagedObjectDn
    MAX-ACCESS   read-only
    STATUS       current
    DESCRIPTION
        "Cisco Firepower sw:PhysFsmTask:dn managed object property"
    ::= { cfprSwPhysFsmTaskEntry 2 }

cfprSwPhysFsmTaskRn OBJECT-TYPE
    SYNTAX       SnmpAdminString
    MAX-ACCESS   read-only
    STATUS       current
    DESCRIPTION
        "Cisco Firepower sw:PhysFsmTask:rn managed object property"
    ::= { cfprSwPhysFsmTaskEntry 3 }

cfprSwPhysFsmTaskCompletion OBJECT-TYPE
    SYNTAX       CfprFsmCompletion
    MAX-ACCESS   read-only
    STATUS       current
    DESCRIPTION
        "Cisco Firepower sw:PhysFsmTask:completion managed
        object property"
    ::= { cfprSwPhysFsmTaskEntry 4 }

cfprSwPhysFsmTaskFlags OBJECT-TYPE
    SYNTAX       CfprFsmFlags
    MAX-ACCESS   read-only
    STATUS       current
    DESCRIPTION
        "Cisco Firepower sw:PhysFsmTask:flags managed object property"
    ::= { cfprSwPhysFsmTaskEntry 5 }

cfprSwPhysFsmTaskItem OBJECT-TYPE
    SYNTAX       CfprSwPhysFsmTaskItem
    MAX-ACCESS   read-only
    STATUS       current
    DESCRIPTION
        "Cisco Firepower sw:PhysFsmTask:item managed object property"
    ::= { cfprSwPhysFsmTaskEntry 6 }

cfprSwPhysFsmTaskSeqId OBJECT-TYPE
    SYNTAX       Gauge32
    MAX-ACCESS   read-only
    STATUS       current
    DESCRIPTION
        "Cisco Firepower sw:PhysFsmTask:seqId managed object property"
    ::= { cfprSwPhysFsmTaskEntry 7 }

cfprSwPortBreakoutTable OBJECT-TYPE
    SYNTAX           SEQUENCE OF CfprSwPortBreakoutEntry
    MAX-ACCESS       not-accessible
    STATUS           current
    DESCRIPTION
        "Cisco Firepower sw:PortBreakout managed object table"
    ::= { cfprSwObjects 70 }

cfprSwPortBreakoutEntry OBJECT-TYPE
    SYNTAX           CfprSwPortBreakoutEntry
    MAX-ACCESS       not-accessible
    STATUS           current
    DESCRIPTION
        "Entry for the cfprSwPortBreakoutTable table."
    INDEX { cfprSwPortBreakoutInstanceId }
    ::= { cfprSwPortBreakoutTable 1 }

CfprSwPortBreakoutEntry ::= SEQUENCE {
    cfprSwPortBreakoutInstanceId                                     CfprManagedObjectId,
    cfprSwPortBreakoutDn                                             CfprManagedObjectDn,
    cfprSwPortBreakoutRn                                             SnmpAdminString,
    cfprSwPortBreakoutBreakoutType                                   CfprSwBreakoutType,
    cfprSwPortBreakoutPortId                                         CfprSwPortBreakoutPortId,
    cfprSwPortBreakoutSlotId                                         CfprSwPortBreakoutSlotId
}

cfprSwPortBreakoutInstanceId OBJECT-TYPE
    SYNTAX       CfprManagedObjectId
    MAX-ACCESS   not-accessible
    STATUS       current
    DESCRIPTION
        "Instance identifier of the managed object."
    ::= { cfprSwPortBreakoutEntry 1 }

cfprSwPortBreakoutDn OBJECT-TYPE
    SYNTAX       CfprManagedObjectDn
    MAX-ACCESS   read-only
    STATUS       current
    DESCRIPTION
        "Cisco Firepower sw:PortBreakout:dn managed object property"
    ::= { cfprSwPortBreakoutEntry 2 }

cfprSwPortBreakoutRn OBJECT-TYPE
    SYNTAX       SnmpAdminString
    MAX-ACCESS   read-only
    STATUS       current
    DESCRIPTION
        "Cisco Firepower sw:PortBreakout:rn managed object property"
    ::= { cfprSwPortBreakoutEntry 3 }

cfprSwPortBreakoutBreakoutType OBJECT-TYPE
    SYNTAX       CfprSwBreakoutType
    MAX-ACCESS   read-only
    STATUS       current
    DESCRIPTION
        "Cisco Firepower sw:PortBreakout:breakoutType managed
        object property"
    ::= { cfprSwPortBreakoutEntry 4 }

cfprSwPortBreakoutPortId OBJECT-TYPE
    SYNTAX       CfprSwPortBreakoutPortId
    MAX-ACCESS   read-only
    STATUS       current
    DESCRIPTION
        "Cisco Firepower sw:PortBreakout:portId managed object property"
    ::= { cfprSwPortBreakoutEntry 5 }

cfprSwPortBreakoutSlotId OBJECT-TYPE
    SYNTAX       CfprSwPortBreakoutSlotId
    MAX-ACCESS   read-only
    STATUS       current
    DESCRIPTION
        "Cisco Firepower sw:PortBreakout:slotId managed object property"
    ::= { cfprSwPortBreakoutEntry 6 }

cfprSwSspEthLanMonTable OBJECT-TYPE
    SYNTAX           SEQUENCE OF CfprSwSspEthLanMonEntry
    MAX-ACCESS       not-accessible
    STATUS           current
    DESCRIPTION
        "Cisco Firepower sw:SspEthLanMon managed object table"
    ::= { cfprSwObjects 88 }

cfprSwSspEthLanMonEntry OBJECT-TYPE
    SYNTAX           CfprSwSspEthLanMonEntry
    MAX-ACCESS       not-accessible
    STATUS           current
    DESCRIPTION
        "Entry for the cfprSwSspEthLanMonTable table."
    INDEX { cfprSwSspEthLanMonInstanceId }
    ::= { cfprSwSspEthLanMonTable 1 }

CfprSwSspEthLanMonEntry ::= SEQUENCE {
    cfprSwSspEthLanMonInstanceId                                     CfprManagedObjectId,
    cfprSwSspEthLanMonDn                                             CfprManagedObjectDn,
    cfprSwSspEthLanMonRn                                             SnmpAdminString,
    cfprSwSspEthLanMonLocale                                         CfprSwSspMonDomainLocale,
    cfprSwSspEthLanMonName                                           SnmpAdminString,
    cfprSwSspEthLanMonSwitchId                                       CfprNetworkSwitchId,
    cfprSwSspEthLanMonTransport                                      CfprSwSspEthLanMonTransport,
    cfprSwSspEthLanMonType                                           CfprSwSspLanMonType
}

cfprSwSspEthLanMonInstanceId OBJECT-TYPE
    SYNTAX       CfprManagedObjectId
    MAX-ACCESS   not-accessible
    STATUS       current
    DESCRIPTION
        "Instance identifier of the managed object."
    ::= { cfprSwSspEthLanMonEntry 1 }

cfprSwSspEthLanMonDn OBJECT-TYPE
    SYNTAX       CfprManagedObjectDn
    MAX-ACCESS   read-only
    STATUS       current
    DESCRIPTION
        "Cisco Firepower sw:SspEthLanMon:dn managed object property"
    ::= { cfprSwSspEthLanMonEntry 2 }

cfprSwSspEthLanMonRn OBJECT-TYPE
    SYNTAX       SnmpAdminString
    MAX-ACCESS   read-only
    STATUS       current
    DESCRIPTION
        "Cisco Firepower sw:SspEthLanMon:rn managed object property"
    ::= { cfprSwSspEthLanMonEntry 3 }

cfprSwSspEthLanMonLocale OBJECT-TYPE
    SYNTAX       CfprSwSspMonDomainLocale
    MAX-ACCESS   read-only
    STATUS       current
    DESCRIPTION
        "Cisco Firepower sw:SspEthLanMon:locale managed object property"
    ::= { cfprSwSspEthLanMonEntry 4 }

cfprSwSspEthLanMonName OBJECT-TYPE
    SYNTAX       SnmpAdminString
    MAX-ACCESS   read-only
    STATUS       current
    DESCRIPTION
        "Cisco Firepower sw:SspEthLanMon:name managed object property"
    ::= { cfprSwSspEthLanMonEntry 5 }

cfprSwSspEthLanMonSwitchId OBJECT-TYPE
    SYNTAX       CfprNetworkSwitchId
    MAX-ACCESS   read-only
    STATUS       current
    DESCRIPTION
        "Cisco Firepower sw:SspEthLanMon:switchId managed object property"
    ::= { cfprSwSspEthLanMonEntry 6 }

cfprSwSspEthLanMonTransport OBJECT-TYPE
    SYNTAX       CfprSwSspEthLanMonTransport
    MAX-ACCESS   read-only
    STATUS       current
    DESCRIPTION
        "Cisco Firepower sw:SspEthLanMon:transport managed
        object property"
    ::= { cfprSwSspEthLanMonEntry 7 }

cfprSwSspEthLanMonType OBJECT-TYPE
    SYNTAX       CfprSwSspLanMonType
    MAX-ACCESS   read-only
    STATUS       current
    DESCRIPTION
        "Cisco Firepower sw:SspEthLanMon:type managed object property"
    ::= { cfprSwSspEthLanMonEntry 8 }

cfprSwSspEthMonTable OBJECT-TYPE
    SYNTAX           SEQUENCE OF CfprSwSspEthMonEntry
    MAX-ACCESS       not-accessible
    STATUS           current
    DESCRIPTION
        "Cisco Firepower sw:SspEthMon managed object table"
    ::= { cfprSwObjects 89 }

cfprSwSspEthMonEntry OBJECT-TYPE
    SYNTAX           CfprSwSspEthMonEntry
    MAX-ACCESS       not-accessible
    STATUS           current
    DESCRIPTION
        "Entry for the cfprSwSspEthMonTable table."
    INDEX { cfprSwSspEthMonInstanceId }
    ::= { cfprSwSspEthMonTable 1 }

CfprSwSspEthMonEntry ::= SEQUENCE {
    cfprSwSspEthMonInstanceId                                        CfprManagedObjectId,
    cfprSwSspEthMonDn                                                CfprManagedObjectDn,
    cfprSwSspEthMonRn                                                SnmpAdminString,
    cfprSwSspEthMonAdminState                                        CfprSwSspMonAdminState,
    cfprSwSspEthMonAppendFlag                                        CfprFabricPktCaptureAppendFlag,
    cfprSwSspEthMonDelPcap                                           CfprSwSspMonDelPcap,
    cfprSwSspEthMonFsmDescr                                          SnmpAdminString,
    cfprSwSspEthMonFsmPrev                                           SnmpAdminString,
    cfprSwSspEthMonFsmProgr                                          Gauge32,
    cfprSwSspEthMonFsmRmtInvErrCode                                  Gauge32,
    cfprSwSspEthMonFsmRmtInvErrDescr                                 SnmpAdminString,
    cfprSwSspEthMonFsmRmtInvRslt                                     CfprConditionRemoteInvRslt,
    cfprSwSspEthMonFsmStageDescr                                     SnmpAdminString,
    cfprSwSspEthMonFsmStamp                                          DateAndTime,
    cfprSwSspEthMonFsmStatus                                         SnmpAdminString,
    cfprSwSspEthMonFsmTry                                            Gauge32,
    cfprSwSspEthMonLifeCycle                                         CfprSwPktCaptureLifeCycle,
    cfprSwSspEthMonName                                              SnmpAdminString,
    cfprSwSspEthMonPeerDn                                            SnmpAdminString,
    cfprSwSspEthMonSession                                           Gauge32,
    cfprSwSspEthMonSessionMemUsage                                   Unsigned64,
    cfprSwSspEthMonSwitchId                                          CfprNetworkSwitchId,
    cfprSwSspEthMonTransport                                         CfprSwSspEthMonTransport,
    cfprSwSspEthMonType                                              CfprSwSspEthMonType,
    cfprSwSspEthMonSessionPcapSnapLen                                Gauge32,
    cfprSwSspEthMonFsmFlags                                          SnmpAdminString
}

cfprSwSspEthMonInstanceId OBJECT-TYPE
    SYNTAX       CfprManagedObjectId
    MAX-ACCESS   not-accessible
    STATUS       current
    DESCRIPTION
        "Instance identifier of the managed object."
    ::= { cfprSwSspEthMonEntry 1 }

cfprSwSspEthMonDn OBJECT-TYPE
    SYNTAX       CfprManagedObjectDn
    MAX-ACCESS   read-only
    STATUS       current
    DESCRIPTION
        "Cisco Firepower sw:SspEthMon:dn managed object property"
    ::= { cfprSwSspEthMonEntry 2 }

cfprSwSspEthMonRn OBJECT-TYPE
    SYNTAX       SnmpAdminString
    MAX-ACCESS   read-only
    STATUS       current
    DESCRIPTION
        "Cisco Firepower sw:SspEthMon:rn managed object property"
    ::= { cfprSwSspEthMonEntry 3 }

cfprSwSspEthMonAdminState OBJECT-TYPE
    SYNTAX       CfprSwSspMonAdminState
    MAX-ACCESS   read-only
    STATUS       current
    DESCRIPTION
        "Cisco Firepower sw:SspEthMon:adminState managed object property"
    ::= { cfprSwSspEthMonEntry 4 }

cfprSwSspEthMonAppendFlag OBJECT-TYPE
    SYNTAX       CfprFabricPktCaptureAppendFlag
    MAX-ACCESS   read-only
    STATUS       current
    DESCRIPTION
        "Cisco Firepower sw:SspEthMon:appendFlag managed object property"
    ::= { cfprSwSspEthMonEntry 5 }

cfprSwSspEthMonDelPcap OBJECT-TYPE
    SYNTAX       CfprSwSspMonDelPcap
    MAX-ACCESS   read-only
    STATUS       current
    DESCRIPTION
        "Cisco Firepower sw:SspEthMon:delPcap managed object property"
    ::= { cfprSwSspEthMonEntry 6 }

cfprSwSspEthMonFsmDescr OBJECT-TYPE
    SYNTAX       SnmpAdminString
    MAX-ACCESS   read-only
    STATUS       current
    DESCRIPTION
        "Cisco Firepower sw:SspEthMon:fsmDescr managed object property"
    ::= { cfprSwSspEthMonEntry 7 }

cfprSwSspEthMonFsmPrev OBJECT-TYPE
    SYNTAX       SnmpAdminString
    MAX-ACCESS   read-only
    STATUS       current
    DESCRIPTION
        "Cisco Firepower sw:SspEthMon:fsmPrev managed object property"
    ::= { cfprSwSspEthMonEntry 8 }

cfprSwSspEthMonFsmProgr OBJECT-TYPE
    SYNTAX       Gauge32
    MAX-ACCESS   read-only
    STATUS       current
    DESCRIPTION
        "Cisco Firepower sw:SspEthMon:fsmProgr managed object property"
    ::= { cfprSwSspEthMonEntry 9 }

cfprSwSspEthMonFsmRmtInvErrCode OBJECT-TYPE
    SYNTAX       Gauge32
    MAX-ACCESS   read-only
    STATUS       current
    DESCRIPTION
        "Cisco Firepower sw:SspEthMon:fsmRmtInvErrCode
        managed object property"
    ::= { cfprSwSspEthMonEntry 10 }

cfprSwSspEthMonFsmRmtInvErrDescr OBJECT-TYPE
    SYNTAX       SnmpAdminString
    MAX-ACCESS   read-only
    STATUS       current
    DESCRIPTION
        "Cisco Firepower sw:SspEthMon:fsmRmtInvErrDescr
        managed object property"
    ::= { cfprSwSspEthMonEntry 11 }

cfprSwSspEthMonFsmRmtInvRslt OBJECT-TYPE
    SYNTAX       CfprConditionRemoteInvRslt
    MAX-ACCESS   read-only
    STATUS       current
    DESCRIPTION
        "Cisco Firepower sw:SspEthMon:fsmRmtInvRslt managed
        object property"
    ::= { cfprSwSspEthMonEntry 12 }

cfprSwSspEthMonFsmStageDescr OBJECT-TYPE
    SYNTAX       SnmpAdminString
    MAX-ACCESS   read-only
    STATUS       current
    DESCRIPTION
        "Cisco Firepower sw:SspEthMon:fsmStageDescr managed
        object property"
    ::= { cfprSwSspEthMonEntry 13 }

cfprSwSspEthMonFsmStamp OBJECT-TYPE
    SYNTAX       DateAndTime
    MAX-ACCESS   read-only
    STATUS       current
    DESCRIPTION
        "Cisco Firepower sw:SspEthMon:fsmStamp managed object property"
    ::= { cfprSwSspEthMonEntry 14 }

cfprSwSspEthMonFsmStatus OBJECT-TYPE
    SYNTAX       SnmpAdminString
    MAX-ACCESS   read-only
    STATUS       current
    DESCRIPTION
        "Cisco Firepower sw:SspEthMon:fsmStatus managed object property"
    ::= { cfprSwSspEthMonEntry 15 }

cfprSwSspEthMonFsmTry OBJECT-TYPE
    SYNTAX       Gauge32
    MAX-ACCESS   read-only
    STATUS       current
    DESCRIPTION
        "Cisco Firepower sw:SspEthMon:fsmTry managed object property"
    ::= { cfprSwSspEthMonEntry 16 }

cfprSwSspEthMonLifeCycle OBJECT-TYPE
    SYNTAX       CfprSwPktCaptureLifeCycle
    MAX-ACCESS   read-only
    STATUS       current
    DESCRIPTION
        "Cisco Firepower sw:SspEthMon:lifeCycle managed object property"
    ::= { cfprSwSspEthMonEntry 17 }

cfprSwSspEthMonName OBJECT-TYPE
    SYNTAX       SnmpAdminString
    MAX-ACCESS   read-only
    STATUS       current
    DESCRIPTION
        "Cisco Firepower sw:SspEthMon:name managed object property"
    ::= { cfprSwSspEthMonEntry 18 }

cfprSwSspEthMonPeerDn OBJECT-TYPE
    SYNTAX       SnmpAdminString
    MAX-ACCESS   read-only
    STATUS       current
    DESCRIPTION
        "Cisco Firepower sw:SspEthMon:peerDn managed object property"
    ::= { cfprSwSspEthMonEntry 19 }

cfprSwSspEthMonSession OBJECT-TYPE
    SYNTAX       Gauge32
    MAX-ACCESS   read-only
    STATUS       current
    DESCRIPTION
        "Cisco Firepower sw:SspEthMon:session managed object property"
    ::= { cfprSwSspEthMonEntry 20 }

cfprSwSspEthMonSessionMemUsage OBJECT-TYPE
    SYNTAX       Unsigned64
    MAX-ACCESS   read-only
    STATUS       current
    DESCRIPTION
        "Cisco Firepower sw:SspEthMon:sessionMemUsage managed
        object property"
    ::= { cfprSwSspEthMonEntry 21 }

cfprSwSspEthMonSwitchId OBJECT-TYPE
    SYNTAX       CfprNetworkSwitchId
    MAX-ACCESS   read-only
    STATUS       current
    DESCRIPTION
        "Cisco Firepower sw:SspEthMon:switchId managed object property"
    ::= { cfprSwSspEthMonEntry 22 }

cfprSwSspEthMonTransport OBJECT-TYPE
    SYNTAX       CfprSwSspEthMonTransport
    MAX-ACCESS   read-only
    STATUS       current
    DESCRIPTION
        "Cisco Firepower sw:SspEthMon:transport managed object property"
    ::= { cfprSwSspEthMonEntry 23 }

cfprSwSspEthMonType OBJECT-TYPE
    SYNTAX       CfprSwSspEthMonType
    MAX-ACCESS   read-only
    STATUS       current
    DESCRIPTION
        "Cisco Firepower sw:SspEthMon:type managed object property"
    ::= { cfprSwSspEthMonEntry 24 }

cfprSwSspEthMonSessionPcapSnapLen OBJECT-TYPE
    SYNTAX       Gauge32
    MAX-ACCESS   read-only
    STATUS       current
    DESCRIPTION
        "Cisco Firepower sw:SspEthMon:sessionPcapSnapLen
        managed object property"
    ::= { cfprSwSspEthMonEntry 25 }

cfprSwSspEthMonFsmFlags OBJECT-TYPE
    SYNTAX       SnmpAdminString
    MAX-ACCESS   read-only
    STATUS       current
    DESCRIPTION
        "Cisco Firepower sw:SspEthMon:fsmFlags managed object property"
    ::= { cfprSwSspEthMonEntry 26 }

cfprSwSspEthMonFilterEpTable OBJECT-TYPE
    SYNTAX           SEQUENCE OF CfprSwSspEthMonFilterEpEntry
    MAX-ACCESS       not-accessible
    STATUS           current
    DESCRIPTION
        "Cisco Firepower sw:SspEthMonFilterEp managed object table"
    ::= { cfprSwObjects 90 }

cfprSwSspEthMonFilterEpEntry OBJECT-TYPE
    SYNTAX           CfprSwSspEthMonFilterEpEntry
    MAX-ACCESS       not-accessible
    STATUS           current
    DESCRIPTION
        "Entry for the cfprSwSspEthMonFilterEpTable table."
    INDEX { cfprSwSspEthMonFilterEpInstanceId }
    ::= { cfprSwSspEthMonFilterEpTable 1 }

CfprSwSspEthMonFilterEpEntry ::= SEQUENCE {
    cfprSwSspEthMonFilterEpInstanceId                                CfprManagedObjectId,
    cfprSwSspEthMonFilterEpDn                                        CfprManagedObjectDn,
    cfprSwSspEthMonFilterEpRn                                        SnmpAdminString,
    cfprSwSspEthMonFilterEpDestIp                                    InetAddressIPv4,
    cfprSwSspEthMonFilterEpDestMAC                                   MacAddress,
    cfprSwSspEthMonFilterEpDestPort                                  CfprFabricPort,
    cfprSwSspEthMonFilterEpEthertype                                 Gauge32,
    cfprSwSspEthMonFilterEpFilterFlag                                Gauge32,
    cfprSwSspEthMonFilterEpIvlan                                     Gauge32,
    cfprSwSspEthMonFilterEpLifeCycle                                 CfprSwPktCaptureLifeCycle,
    cfprSwSspEthMonFilterEpNameId                                    SnmpAdminString,
    cfprSwSspEthMonFilterEpOvlan                                     Gauge32,
    cfprSwSspEthMonFilterEpPeerDn                                    SnmpAdminString,
    cfprSwSspEthMonFilterEpProtocol                                  Gauge32,
    cfprSwSspEthMonFilterEpRefCount                                  Gauge32,
    cfprSwSspEthMonFilterEpSrcIp                                     InetAddressIPv4,
    cfprSwSspEthMonFilterEpSrcMAC                                    MacAddress,
    cfprSwSspEthMonFilterEpSrcPort                                   CfprFabricPort,
    cfprSwSspEthMonFilterEpDestIpv6                                  InetAddressIPv6,
    cfprSwSspEthMonFilterEpEcmpId                                    Gauge32,
    cfprSwSspEthMonFilterEpSrcIpv6                                   InetAddressIPv6,
    cfprSwSspEthMonFilterEpSubvlan                                   Gauge32,
    cfprSwSspEthMonFilterEpVifId                                     Gauge32
}

cfprSwSspEthMonFilterEpInstanceId OBJECT-TYPE
    SYNTAX       CfprManagedObjectId
    MAX-ACCESS   not-accessible
    STATUS       current
    DESCRIPTION
        "Instance identifier of the managed object."
    ::= { cfprSwSspEthMonFilterEpEntry 1 }

cfprSwSspEthMonFilterEpDn OBJECT-TYPE
    SYNTAX       CfprManagedObjectDn
    MAX-ACCESS   read-only
    STATUS       current
    DESCRIPTION
        "Cisco Firepower sw:SspEthMonFilterEp:dn managed object property"
    ::= { cfprSwSspEthMonFilterEpEntry 2 }

cfprSwSspEthMonFilterEpRn OBJECT-TYPE
    SYNTAX       SnmpAdminString
    MAX-ACCESS   read-only
    STATUS       current
    DESCRIPTION
        "Cisco Firepower sw:SspEthMonFilterEp:rn managed object property"
    ::= { cfprSwSspEthMonFilterEpEntry 3 }

cfprSwSspEthMonFilterEpDestIp OBJECT-TYPE
    SYNTAX       InetAddressIPv4
    MAX-ACCESS   read-only
    STATUS       current
    DESCRIPTION
        "Cisco Firepower sw:SspEthMonFilterEp:destIp managed
        object property"
    ::= { cfprSwSspEthMonFilterEpEntry 4 }

cfprSwSspEthMonFilterEpDestMAC OBJECT-TYPE
    SYNTAX       MacAddress
    MAX-ACCESS   read-only
    STATUS       current
    DESCRIPTION
        "Cisco Firepower sw:SspEthMonFilterEp:destMAC managed
        object property"
    ::= { cfprSwSspEthMonFilterEpEntry 5 }

cfprSwSspEthMonFilterEpDestPort OBJECT-TYPE
    SYNTAX       CfprFabricPort
    MAX-ACCESS   read-only
    STATUS       current
    DESCRIPTION
        "Cisco Firepower sw:SspEthMonFilterEp:destPort
        managed object property"
    ::= { cfprSwSspEthMonFilterEpEntry 6 }

cfprSwSspEthMonFilterEpEthertype OBJECT-TYPE
    SYNTAX       Gauge32
    MAX-ACCESS   read-only
    STATUS       current
    DESCRIPTION
        "Cisco Firepower sw:SspEthMonFilterEp:ethertype
        managed object property"
    ::= { cfprSwSspEthMonFilterEpEntry 7 }

cfprSwSspEthMonFilterEpFilterFlag OBJECT-TYPE
    SYNTAX       Gauge32
    MAX-ACCESS   read-only
    STATUS       current
    DESCRIPTION
        "Cisco Firepower sw:SspEthMonFilterEp:filterFlag
        managed object property"
    ::= { cfprSwSspEthMonFilterEpEntry 8 }

cfprSwSspEthMonFilterEpIvlan OBJECT-TYPE
    SYNTAX       Gauge32
    MAX-ACCESS   read-only
    STATUS       current
    DESCRIPTION
        "Cisco Firepower sw:SspEthMonFilterEp:ivlan managed
        object property"
    ::= { cfprSwSspEthMonFilterEpEntry 9 }

cfprSwSspEthMonFilterEpLifeCycle OBJECT-TYPE
    SYNTAX       CfprSwPktCaptureLifeCycle
    MAX-ACCESS   read-only
    STATUS       current
    DESCRIPTION
        "Cisco Firepower sw:SspEthMonFilterEp:lifeCycle
        managed object property"
    ::= { cfprSwSspEthMonFilterEpEntry 10 }

cfprSwSspEthMonFilterEpNameId OBJECT-TYPE
    SYNTAX       SnmpAdminString
    MAX-ACCESS   read-only
    STATUS       current
    DESCRIPTION
        "Cisco Firepower sw:SspEthMonFilterEp:nameId managed
        object property"
    ::= { cfprSwSspEthMonFilterEpEntry 11 }

cfprSwSspEthMonFilterEpOvlan OBJECT-TYPE
    SYNTAX       Gauge32
    MAX-ACCESS   read-only
    STATUS       current
    DESCRIPTION
        "Cisco Firepower sw:SspEthMonFilterEp:ovlan managed
        object property"
    ::= { cfprSwSspEthMonFilterEpEntry 12 }

cfprSwSspEthMonFilterEpPeerDn OBJECT-TYPE
    SYNTAX       SnmpAdminString
    MAX-ACCESS   read-only
    STATUS       current
    DESCRIPTION
        "Cisco Firepower sw:SspEthMonFilterEp:peerDn managed
        object property"
    ::= { cfprSwSspEthMonFilterEpEntry 13 }

cfprSwSspEthMonFilterEpProtocol OBJECT-TYPE
    SYNTAX       Gauge32
    MAX-ACCESS   read-only
    STATUS       current
    DESCRIPTION
        "Cisco Firepower sw:SspEthMonFilterEp:protocol
        managed object property"
    ::= { cfprSwSspEthMonFilterEpEntry 14 }

cfprSwSspEthMonFilterEpRefCount OBJECT-TYPE
    SYNTAX       Gauge32
    MAX-ACCESS   read-only
    STATUS       current
    DESCRIPTION
        "Cisco Firepower sw:SspEthMonFilterEp:refCount
        managed object property"
    ::= { cfprSwSspEthMonFilterEpEntry 15 }

cfprSwSspEthMonFilterEpSrcIp OBJECT-TYPE
    SYNTAX       InetAddressIPv4
    MAX-ACCESS   read-only
    STATUS       current
    DESCRIPTION
        "Cisco Firepower sw:SspEthMonFilterEp:srcIp managed
        object property"
    ::= { cfprSwSspEthMonFilterEpEntry 16 }

cfprSwSspEthMonFilterEpSrcMAC OBJECT-TYPE
    SYNTAX       MacAddress
    MAX-ACCESS   read-only
    STATUS       current
    DESCRIPTION
        "Cisco Firepower sw:SspEthMonFilterEp:srcMAC managed
        object property"
    ::= { cfprSwSspEthMonFilterEpEntry 17 }

cfprSwSspEthMonFilterEpSrcPort OBJECT-TYPE
    SYNTAX       CfprFabricPort
    MAX-ACCESS   read-only
    STATUS       current
    DESCRIPTION
        "Cisco Firepower sw:SspEthMonFilterEp:srcPort managed
        object property"
    ::= { cfprSwSspEthMonFilterEpEntry 18 }

cfprSwSspEthMonFilterEpDestIpv6 OBJECT-TYPE
    SYNTAX       InetAddressIPv6
    MAX-ACCESS   read-only
    STATUS       current
    DESCRIPTION
        "Cisco Firepower sw:SspEthMonFilterEp:destIpv6
        managed object property"
    ::= { cfprSwSspEthMonFilterEpEntry 19 }

cfprSwSspEthMonFilterEpEcmpId OBJECT-TYPE
    SYNTAX       Gauge32
    MAX-ACCESS   read-only
    STATUS       current
    DESCRIPTION
        "Cisco Firepower sw:SspEthMonFilterEp:ecmpId managed
        object property"
    ::= { cfprSwSspEthMonFilterEpEntry 20 }

cfprSwSspEthMonFilterEpSrcIpv6 OBJECT-TYPE
    SYNTAX       InetAddressIPv6
    MAX-ACCESS   read-only
    STATUS       current
    DESCRIPTION
        "Cisco Firepower sw:SspEthMonFilterEp:srcIpv6 managed
        object property"
    ::= { cfprSwSspEthMonFilterEpEntry 21 }

cfprSwSspEthMonFilterEpSubvlan OBJECT-TYPE
    SYNTAX       Gauge32
    MAX-ACCESS   read-only
    STATUS       current
    DESCRIPTION
        "Cisco Firepower sw:SspEthMonFilterEp:subvlan managed
        object property"
    ::= { cfprSwSspEthMonFilterEpEntry 22 }

cfprSwSspEthMonFilterEpVifId OBJECT-TYPE
    SYNTAX       Gauge32
    MAX-ACCESS   read-only
    STATUS       current
    DESCRIPTION
        "Cisco Firepower sw:SspEthMonFilterEp:vifId managed
        object property"
    ::= { cfprSwSspEthMonFilterEpEntry 23 }

cfprSwSspEthMonFsmTable OBJECT-TYPE
    SYNTAX           SEQUENCE OF CfprSwSspEthMonFsmEntry
    MAX-ACCESS       not-accessible
    STATUS           current
    DESCRIPTION
        "Cisco Firepower sw:SspEthMonFsm managed object table"
    ::= { cfprSwObjects 91 }

cfprSwSspEthMonFsmEntry OBJECT-TYPE
    SYNTAX           CfprSwSspEthMonFsmEntry
    MAX-ACCESS       not-accessible
    STATUS           current
    DESCRIPTION
        "Entry for the cfprSwSspEthMonFsmTable table."
    INDEX { cfprSwSspEthMonFsmInstanceId }
    ::= { cfprSwSspEthMonFsmTable 1 }

CfprSwSspEthMonFsmEntry ::= SEQUENCE {
    cfprSwSspEthMonFsmInstanceId                                     CfprManagedObjectId,
    cfprSwSspEthMonFsmDn                                             CfprManagedObjectDn,
    cfprSwSspEthMonFsmRn                                             SnmpAdminString,
    cfprSwSspEthMonFsmCompletionTime                                 DateAndTime,
    cfprSwSspEthMonFsmCurrentFsm                                     CfprSwSspEthMonFsmCurrentFsm,
    cfprSwSspEthMonFsmDescrData                                      SnmpAdminString,
    cfprSwSspEthMonFsmFsmStatus                                      CfprFsmFsmStageStatus,
    cfprSwSspEthMonFsmProgress                                       Gauge32,
    cfprSwSspEthMonFsmRmtErrCode                                     Gauge32,
    cfprSwSspEthMonFsmRmtErrDescr                                    SnmpAdminString,
    cfprSwSspEthMonFsmRmtRslt                                        CfprConditionRemoteInvRslt
}

cfprSwSspEthMonFsmInstanceId OBJECT-TYPE
    SYNTAX       CfprManagedObjectId
    MAX-ACCESS   not-accessible
    STATUS       current
    DESCRIPTION
        "Instance identifier of the managed object."
    ::= { cfprSwSspEthMonFsmEntry 1 }

cfprSwSspEthMonFsmDn OBJECT-TYPE
    SYNTAX       CfprManagedObjectDn
    MAX-ACCESS   read-only
    STATUS       current
    DESCRIPTION
        "Cisco Firepower sw:SspEthMonFsm:dn managed object property"
    ::= { cfprSwSspEthMonFsmEntry 2 }

cfprSwSspEthMonFsmRn OBJECT-TYPE
    SYNTAX       SnmpAdminString
    MAX-ACCESS   read-only
    STATUS       current
    DESCRIPTION
        "Cisco Firepower sw:SspEthMonFsm:rn managed object property"
    ::= { cfprSwSspEthMonFsmEntry 3 }

cfprSwSspEthMonFsmCompletionTime OBJECT-TYPE
    SYNTAX       DateAndTime
    MAX-ACCESS   read-only
    STATUS       current
    DESCRIPTION
        "Cisco Firepower sw:SspEthMonFsm:completionTime
        managed object property"
    ::= { cfprSwSspEthMonFsmEntry 4 }

cfprSwSspEthMonFsmCurrentFsm OBJECT-TYPE
    SYNTAX       CfprSwSspEthMonFsmCurrentFsm
    MAX-ACCESS   read-only
    STATUS       current
    DESCRIPTION
        "Cisco Firepower sw:SspEthMonFsm:currentFsm managed
        object property"
    ::= { cfprSwSspEthMonFsmEntry 5 }

cfprSwSspEthMonFsmDescrData OBJECT-TYPE
    SYNTAX       SnmpAdminString
    MAX-ACCESS   read-only
    STATUS       current
    DESCRIPTION
        "Cisco Firepower sw:SspEthMonFsm:descr managed object property"
    ::= { cfprSwSspEthMonFsmEntry 6 }

cfprSwSspEthMonFsmFsmStatus OBJECT-TYPE
    SYNTAX       CfprFsmFsmStageStatus
    MAX-ACCESS   read-only
    STATUS       current
    DESCRIPTION
        "Cisco Firepower sw:SspEthMonFsm:fsmStatus managed
        object property"
    ::= { cfprSwSspEthMonFsmEntry 7 }

cfprSwSspEthMonFsmProgress OBJECT-TYPE
    SYNTAX       Gauge32
    MAX-ACCESS   read-only
    STATUS       current
    DESCRIPTION
        "Cisco Firepower sw:SspEthMonFsm:progress managed object property"
    ::= { cfprSwSspEthMonFsmEntry 8 }

cfprSwSspEthMonFsmRmtErrCode OBJECT-TYPE
    SYNTAX       Gauge32
    MAX-ACCESS   read-only
    STATUS       current
    DESCRIPTION
        "Cisco Firepower sw:SspEthMonFsm:rmtErrCode managed
        object property"
    ::= { cfprSwSspEthMonFsmEntry 9 }

cfprSwSspEthMonFsmRmtErrDescr OBJECT-TYPE
    SYNTAX       SnmpAdminString
    MAX-ACCESS   read-only
    STATUS       current
    DESCRIPTION
        "Cisco Firepower sw:SspEthMonFsm:rmtErrDescr managed
        object property"
    ::= { cfprSwSspEthMonFsmEntry 10 }

cfprSwSspEthMonFsmRmtRslt OBJECT-TYPE
    SYNTAX       CfprConditionRemoteInvRslt
    MAX-ACCESS   read-only
    STATUS       current
    DESCRIPTION
        "Cisco Firepower sw:SspEthMonFsm:rmtRslt managed object property"
    ::= { cfprSwSspEthMonFsmEntry 11 }

cfprSwSspEthMonFsmStageTable OBJECT-TYPE
    SYNTAX           SEQUENCE OF CfprSwSspEthMonFsmStageEntry
    MAX-ACCESS       not-accessible
    STATUS           current
    DESCRIPTION
        "Cisco Firepower sw:SspEthMonFsmStage managed object table"
    ::= { cfprSwObjects 92 }

cfprSwSspEthMonFsmStageEntry OBJECT-TYPE
    SYNTAX           CfprSwSspEthMonFsmStageEntry
    MAX-ACCESS       not-accessible
    STATUS           current
    DESCRIPTION
        "Entry for the cfprSwSspEthMonFsmStageTable table."
    INDEX { cfprSwSspEthMonFsmStageInstanceId }
    ::= { cfprSwSspEthMonFsmStageTable 1 }

CfprSwSspEthMonFsmStageEntry ::= SEQUENCE {
    cfprSwSspEthMonFsmStageInstanceId                                CfprManagedObjectId,
    cfprSwSspEthMonFsmStageDn                                        CfprManagedObjectDn,
    cfprSwSspEthMonFsmStageRn                                        SnmpAdminString,
    cfprSwSspEthMonFsmStageDescrData                                 SnmpAdminString,
    cfprSwSspEthMonFsmStageLastUpdateTime                            DateAndTime,
    cfprSwSspEthMonFsmStageName                                      CfprSwSspEthMonFsmStageName,
    cfprSwSspEthMonFsmStageOrder                                     Gauge32,
    cfprSwSspEthMonFsmStageRetry                                     Gauge32,
    cfprSwSspEthMonFsmStageStageStatus                               CfprFsmFsmStageStatus
}

cfprSwSspEthMonFsmStageInstanceId OBJECT-TYPE
    SYNTAX       CfprManagedObjectId
    MAX-ACCESS   not-accessible
    STATUS       current
    DESCRIPTION
        "Instance identifier of the managed object."
    ::= { cfprSwSspEthMonFsmStageEntry 1 }

cfprSwSspEthMonFsmStageDn OBJECT-TYPE
    SYNTAX       CfprManagedObjectDn
    MAX-ACCESS   read-only
    STATUS       current
    DESCRIPTION
        "Cisco Firepower sw:SspEthMonFsmStage:dn managed object property"
    ::= { cfprSwSspEthMonFsmStageEntry 2 }

cfprSwSspEthMonFsmStageRn OBJECT-TYPE
    SYNTAX       SnmpAdminString
    MAX-ACCESS   read-only
    STATUS       current
    DESCRIPTION
        "Cisco Firepower sw:SspEthMonFsmStage:rn managed object property"
    ::= { cfprSwSspEthMonFsmStageEntry 3 }

cfprSwSspEthMonFsmStageDescrData OBJECT-TYPE
    SYNTAX       SnmpAdminString
    MAX-ACCESS   read-only
    STATUS       current
    DESCRIPTION
        "Cisco Firepower sw:SspEthMonFsmStage:descr managed
        object property"
    ::= { cfprSwSspEthMonFsmStageEntry 4 }

cfprSwSspEthMonFsmStageLastUpdateTime OBJECT-TYPE
    SYNTAX       DateAndTime
    MAX-ACCESS   read-only
    STATUS       current
    DESCRIPTION
        "Cisco Firepower sw:SspEthMonFsmStage:lastUpdateTime
        managed object property"
    ::= { cfprSwSspEthMonFsmStageEntry 5 }

cfprSwSspEthMonFsmStageName OBJECT-TYPE
    SYNTAX       CfprSwSspEthMonFsmStageName
    MAX-ACCESS   read-only
    STATUS       current
    DESCRIPTION
        "Cisco Firepower sw:SspEthMonFsmStage:name managed
        object property"
    ::= { cfprSwSspEthMonFsmStageEntry 6 }

cfprSwSspEthMonFsmStageOrder OBJECT-TYPE
    SYNTAX       Gauge32
    MAX-ACCESS   read-only
    STATUS       current
    DESCRIPTION
        "Cisco Firepower sw:SspEthMonFsmStage:order managed
        object property"
    ::= { cfprSwSspEthMonFsmStageEntry 7 }

cfprSwSspEthMonFsmStageRetry OBJECT-TYPE
    SYNTAX       Gauge32
    MAX-ACCESS   read-only
    STATUS       current
    DESCRIPTION
        "Cisco Firepower sw:SspEthMonFsmStage:retry managed
        object property"
    ::= { cfprSwSspEthMonFsmStageEntry 8 }

cfprSwSspEthMonFsmStageStageStatus OBJECT-TYPE
    SYNTAX       CfprFsmFsmStageStatus
    MAX-ACCESS   read-only
    STATUS       current
    DESCRIPTION
        "Cisco Firepower sw:SspEthMonFsmStage:stageStatus
        managed object property"
    ::= { cfprSwSspEthMonFsmStageEntry 9 }

cfprSwSspEthMonFsmTaskTable OBJECT-TYPE
    SYNTAX           SEQUENCE OF CfprSwSspEthMonFsmTaskEntry
    MAX-ACCESS       not-accessible
    STATUS           current
    DESCRIPTION
        "Cisco Firepower sw:SspEthMonFsmTask managed object table"
    ::= { cfprSwObjects 93 }

cfprSwSspEthMonFsmTaskEntry OBJECT-TYPE
    SYNTAX           CfprSwSspEthMonFsmTaskEntry
    MAX-ACCESS       not-accessible
    STATUS           current
    DESCRIPTION
        "Entry for the cfprSwSspEthMonFsmTaskTable table."
    INDEX { cfprSwSspEthMonFsmTaskInstanceId }
    ::= { cfprSwSspEthMonFsmTaskTable 1 }

CfprSwSspEthMonFsmTaskEntry ::= SEQUENCE {
    cfprSwSspEthMonFsmTaskInstanceId                                 CfprManagedObjectId,
    cfprSwSspEthMonFsmTaskDn                                         CfprManagedObjectDn,
    cfprSwSspEthMonFsmTaskRn                                         SnmpAdminString,
    cfprSwSspEthMonFsmTaskCompletion                                 CfprFsmCompletion,
    cfprSwSspEthMonFsmTaskFlags                                      CfprSwSspEthMonFsmTaskFlags,
    cfprSwSspEthMonFsmTaskItem                                       CfprSwSspEthMonFsmTaskItem,
    cfprSwSspEthMonFsmTaskSeqId                                      Gauge32
}

cfprSwSspEthMonFsmTaskInstanceId OBJECT-TYPE
    SYNTAX       CfprManagedObjectId
    MAX-ACCESS   not-accessible
    STATUS       current
    DESCRIPTION
        "Instance identifier of the managed object."
    ::= { cfprSwSspEthMonFsmTaskEntry 1 }

cfprSwSspEthMonFsmTaskDn OBJECT-TYPE
    SYNTAX       CfprManagedObjectDn
    MAX-ACCESS   read-only
    STATUS       current
    DESCRIPTION
        "Cisco Firepower sw:SspEthMonFsmTask:dn managed object property"
    ::= { cfprSwSspEthMonFsmTaskEntry 2 }

cfprSwSspEthMonFsmTaskRn OBJECT-TYPE
    SYNTAX       SnmpAdminString
    MAX-ACCESS   read-only
    STATUS       current
    DESCRIPTION
        "Cisco Firepower sw:SspEthMonFsmTask:rn managed object property"
    ::= { cfprSwSspEthMonFsmTaskEntry 3 }

cfprSwSspEthMonFsmTaskCompletion OBJECT-TYPE
    SYNTAX       CfprFsmCompletion
    MAX-ACCESS   read-only
    STATUS       current
    DESCRIPTION
        "Cisco Firepower sw:SspEthMonFsmTask:completion
        managed object property"
    ::= { cfprSwSspEthMonFsmTaskEntry 4 }

cfprSwSspEthMonFsmTaskFlags OBJECT-TYPE
    SYNTAX       CfprSwSspEthMonFsmTaskFlags
    MAX-ACCESS   read-only
    STATUS       current
    DESCRIPTION
        "Cisco Firepower sw:SspEthMonFsmTask:flags managed
        object property"
    ::= { cfprSwSspEthMonFsmTaskEntry 5 }

cfprSwSspEthMonFsmTaskItem OBJECT-TYPE
    SYNTAX       CfprSwSspEthMonFsmTaskItem
    MAX-ACCESS   read-only
    STATUS       current
    DESCRIPTION
        "Cisco Firepower sw:SspEthMonFsmTask:item managed object property"
    ::= { cfprSwSspEthMonFsmTaskEntry 6 }

cfprSwSspEthMonFsmTaskSeqId OBJECT-TYPE
    SYNTAX       Gauge32
    MAX-ACCESS   read-only
    STATUS       current
    DESCRIPTION
        "Cisco Firepower sw:SspEthMonFsmTask:seqId managed
        object property"
    ::= { cfprSwSspEthMonFsmTaskEntry 7 }

cfprSwSspEthMonSrcAppEpTable OBJECT-TYPE
    SYNTAX           SEQUENCE OF CfprSwSspEthMonSrcAppEpEntry
    MAX-ACCESS       not-accessible
    STATUS           current
    DESCRIPTION
        "Cisco Firepower sw:SspEthMonSrcAppEp managed object table"
    ::= { cfprSwObjects 94 }

cfprSwSspEthMonSrcAppEpEntry OBJECT-TYPE
    SYNTAX           CfprSwSspEthMonSrcAppEpEntry
    MAX-ACCESS       not-accessible
    STATUS           current
    DESCRIPTION
        "Entry for the cfprSwSspEthMonSrcAppEpTable table."
    INDEX { cfprSwSspEthMonSrcAppEpInstanceId }
    ::= { cfprSwSspEthMonSrcAppEpTable 1 }

CfprSwSspEthMonSrcAppEpEntry ::= SEQUENCE {
    cfprSwSspEthMonSrcAppEpInstanceId                                CfprManagedObjectId,
    cfprSwSspEthMonSrcAppEpDn                                        CfprManagedObjectDn,
    cfprSwSspEthMonSrcAppEpRn                                        SnmpAdminString,
    cfprSwSspEthMonSrcAppEpAppName                                   SnmpAdminString,
    cfprSwSspEthMonSrcAppEpExternalPortDn                            SnmpAdminString,
    cfprSwSspEthMonSrcAppEpFilter                                    SnmpAdminString,
    cfprSwSspEthMonSrcAppEpFilterDn                                  SnmpAdminString,
    cfprSwSspEthMonSrcAppEpLifeCycle                                 CfprSwPktCaptureLifeCycle,
    cfprSwSspEthMonSrcAppEpLinkName                                  SnmpAdminString,
    cfprSwSspEthMonSrcAppEpPcapfile                                  SnmpAdminString,
    cfprSwSspEthMonSrcAppEpPcapfilename                              SnmpAdminString,
    cfprSwSspEthMonSrcAppEpPcapsize                                  Gauge32,
    cfprSwSspEthMonSrcAppEpPortChannelDn                             SnmpAdminString,
    cfprSwSspEthMonSrcAppEpPortName                                  SnmpAdminString,
    cfprSwSspEthMonSrcAppEpSlotId                                    Gauge32,
    cfprSwSspEthMonSrcAppEpPeerDn                                    SnmpAdminString
}

cfprSwSspEthMonSrcAppEpInstanceId OBJECT-TYPE
    SYNTAX       CfprManagedObjectId
    MAX-ACCESS   not-accessible
    STATUS       current
    DESCRIPTION
        "Instance identifier of the managed object."
    ::= { cfprSwSspEthMonSrcAppEpEntry 1 }

cfprSwSspEthMonSrcAppEpDn OBJECT-TYPE
    SYNTAX       CfprManagedObjectDn
    MAX-ACCESS   read-only
    STATUS       current
    DESCRIPTION
        "Cisco Firepower sw:SspEthMonSrcAppEp:dn managed object property"
    ::= { cfprSwSspEthMonSrcAppEpEntry 2 }

cfprSwSspEthMonSrcAppEpRn OBJECT-TYPE
    SYNTAX       SnmpAdminString
    MAX-ACCESS   read-only
    STATUS       current
    DESCRIPTION
        "Cisco Firepower sw:SspEthMonSrcAppEp:rn managed object property"
    ::= { cfprSwSspEthMonSrcAppEpEntry 3 }

cfprSwSspEthMonSrcAppEpAppName OBJECT-TYPE
    SYNTAX       SnmpAdminString
    MAX-ACCESS   read-only
    STATUS       current
    DESCRIPTION
        "Cisco Firepower sw:SspEthMonSrcAppEp:appName managed
        object property"
    ::= { cfprSwSspEthMonSrcAppEpEntry 4 }

cfprSwSspEthMonSrcAppEpExternalPortDn OBJECT-TYPE
    SYNTAX       SnmpAdminString
    MAX-ACCESS   read-only
    STATUS       current
    DESCRIPTION
        "Cisco Firepower sw:SspEthMonSrcAppEp:externalPortDn
        managed object property"
    ::= { cfprSwSspEthMonSrcAppEpEntry 5 }

cfprSwSspEthMonSrcAppEpFilter OBJECT-TYPE
    SYNTAX       SnmpAdminString
    MAX-ACCESS   read-only
    STATUS       current
    DESCRIPTION
        "Cisco Firepower sw:SspEthMonSrcAppEp:filter managed
        object property"
    ::= { cfprSwSspEthMonSrcAppEpEntry 6 }

cfprSwSspEthMonSrcAppEpFilterDn OBJECT-TYPE
    SYNTAX       SnmpAdminString
    MAX-ACCESS   read-only
    STATUS       current
    DESCRIPTION
        "Cisco Firepower sw:SspEthMonSrcAppEp:filterDn
        managed object property"
    ::= { cfprSwSspEthMonSrcAppEpEntry 7 }

cfprSwSspEthMonSrcAppEpLifeCycle OBJECT-TYPE
    SYNTAX       CfprSwPktCaptureLifeCycle
    MAX-ACCESS   read-only
    STATUS       current
    DESCRIPTION
        "Cisco Firepower sw:SspEthMonSrcAppEp:lifeCycle
        managed object property"
    ::= { cfprSwSspEthMonSrcAppEpEntry 8 }

cfprSwSspEthMonSrcAppEpLinkName OBJECT-TYPE
    SYNTAX       SnmpAdminString
    MAX-ACCESS   read-only
    STATUS       current
    DESCRIPTION
        "Cisco Firepower sw:SspEthMonSrcAppEp:linkName
        managed object property"
    ::= { cfprSwSspEthMonSrcAppEpEntry 9 }

cfprSwSspEthMonSrcAppEpPcapfile OBJECT-TYPE
    SYNTAX       SnmpAdminString
    MAX-ACCESS   read-only
    STATUS       current
    DESCRIPTION
        "Cisco Firepower sw:SspEthMonSrcAppEp:pcapfile
        managed object property"
    ::= { cfprSwSspEthMonSrcAppEpEntry 10 }

cfprSwSspEthMonSrcAppEpPcapfilename OBJECT-TYPE
    SYNTAX       SnmpAdminString
    MAX-ACCESS   read-only
    STATUS       current
    DESCRIPTION
        "Cisco Firepower sw:SspEthMonSrcAppEp:pcapfilename
        managed object property"
    ::= { cfprSwSspEthMonSrcAppEpEntry 11 }

cfprSwSspEthMonSrcAppEpPcapsize OBJECT-TYPE
    SYNTAX       Gauge32
    MAX-ACCESS   read-only
    STATUS       current
    DESCRIPTION
        "Cisco Firepower sw:SspEthMonSrcAppEp:pcapsize
        managed object property"
    ::= { cfprSwSspEthMonSrcAppEpEntry 12 }

cfprSwSspEthMonSrcAppEpPortChannelDn OBJECT-TYPE
    SYNTAX       SnmpAdminString
    MAX-ACCESS   read-only
    STATUS       current
    DESCRIPTION
        "Cisco Firepower sw:SspEthMonSrcAppEp:portChannelDn
        managed object property"
    ::= { cfprSwSspEthMonSrcAppEpEntry 13 }

cfprSwSspEthMonSrcAppEpPortName OBJECT-TYPE
    SYNTAX       SnmpAdminString
    MAX-ACCESS   read-only
    STATUS       current
    DESCRIPTION
        "Cisco Firepower sw:SspEthMonSrcAppEp:portName
        managed object property"
    ::= { cfprSwSspEthMonSrcAppEpEntry 14 }

cfprSwSspEthMonSrcAppEpSlotId OBJECT-TYPE
    SYNTAX       Gauge32
    MAX-ACCESS   read-only
    STATUS       current
    DESCRIPTION
        "Cisco Firepower sw:SspEthMonSrcAppEp:slotId managed
        object property"
    ::= { cfprSwSspEthMonSrcAppEpEntry 15 }

cfprSwSspEthMonSrcAppEpPeerDn OBJECT-TYPE
    SYNTAX       SnmpAdminString
    MAX-ACCESS   read-only
    STATUS       current
    DESCRIPTION
        "Cisco Firepower sw:SspEthMonSrcAppEp:peerDn managed
        object property"
    ::= { cfprSwSspEthMonSrcAppEpEntry 16 }

cfprSwSspEthMonSrcAppLinksEpTable OBJECT-TYPE
    SYNTAX           SEQUENCE OF CfprSwSspEthMonSrcAppLinksEpEntry
    MAX-ACCESS       not-accessible
    STATUS           current
    DESCRIPTION
        "Cisco Firepower sw:SspEthMonSrcAppLinksEp managed object table"
    ::= { cfprSwObjects 95 }

cfprSwSspEthMonSrcAppLinksEpEntry OBJECT-TYPE
    SYNTAX           CfprSwSspEthMonSrcAppLinksEpEntry
    MAX-ACCESS       not-accessible
    STATUS           current
    DESCRIPTION
        "Entry for the cfprSwSspEthMonSrcAppLinksEpTable table."
    INDEX { cfprSwSspEthMonSrcAppLinksEpInstanceId }
    ::= { cfprSwSspEthMonSrcAppLinksEpTable 1 }

CfprSwSspEthMonSrcAppLinksEpEntry ::= SEQUENCE {
    cfprSwSspEthMonSrcAppLinksEpInstanceId                           CfprManagedObjectId,
    cfprSwSspEthMonSrcAppLinksEpDn                                   CfprManagedObjectDn,
    cfprSwSspEthMonSrcAppLinksEpRn                                   SnmpAdminString,
    cfprSwSspEthMonSrcAppLinksEpChassisId                            Gauge32,
    cfprSwSspEthMonSrcAppLinksEpEqAggrPortId                         Gauge32,
    cfprSwSspEthMonSrcAppLinksEpEqPortId                             Gauge32,
    cfprSwSspEthMonSrcAppLinksEpEqSlotId                             Gauge32,
    cfprSwSspEthMonSrcAppLinksEpFilter                               SnmpAdminString,
    cfprSwSspEthMonSrcAppLinksEpFilterDn                             SnmpAdminString,
    cfprSwSspEthMonSrcAppLinksEpLifeCycle                            CfprSwPktCaptureLifeCycle,
    cfprSwSspEthMonSrcAppLinksEpName                                 SnmpAdminString,
    cfprSwSspEthMonSrcAppLinksEpPcapfile                             SnmpAdminString,
    cfprSwSspEthMonSrcAppLinksEpPcapfilename                         SnmpAdminString,
    cfprSwSspEthMonSrcAppLinksEpPcapsize                             Gauge32,
    cfprSwSspEthMonSrcAppLinksEpSwitchId                             CfprNetworkSwitchId,
    cfprSwSspEthMonSrcAppLinksEpVlan                                 Gauge32,
    cfprSwSspEthMonSrcAppLinksEpVnicName1                            SnmpAdminString,
    cfprSwSspEthMonSrcAppLinksEpVifId                                Gauge32
}

cfprSwSspEthMonSrcAppLinksEpInstanceId OBJECT-TYPE
    SYNTAX       CfprManagedObjectId
    MAX-ACCESS   not-accessible
    STATUS       current
    DESCRIPTION
        "Instance identifier of the managed object."
    ::= { cfprSwSspEthMonSrcAppLinksEpEntry 1 }

cfprSwSspEthMonSrcAppLinksEpDn OBJECT-TYPE
    SYNTAX       CfprManagedObjectDn
    MAX-ACCESS   read-only
    STATUS       current
    DESCRIPTION
        "Cisco Firepower sw:SspEthMonSrcAppLinksEp:dn managed
        object property"
    ::= { cfprSwSspEthMonSrcAppLinksEpEntry 2 }

cfprSwSspEthMonSrcAppLinksEpRn OBJECT-TYPE
    SYNTAX       SnmpAdminString
    MAX-ACCESS   read-only
    STATUS       current
    DESCRIPTION
        "Cisco Firepower sw:SspEthMonSrcAppLinksEp:rn managed
        object property"
    ::= { cfprSwSspEthMonSrcAppLinksEpEntry 3 }

cfprSwSspEthMonSrcAppLinksEpChassisId OBJECT-TYPE
    SYNTAX       Gauge32
    MAX-ACCESS   read-only
    STATUS       current
    DESCRIPTION
        "Cisco Firepower sw:SspEthMonSrcAppLinksEp:chassisId
        managed object property"
    ::= { cfprSwSspEthMonSrcAppLinksEpEntry 4 }

cfprSwSspEthMonSrcAppLinksEpEqAggrPortId OBJECT-TYPE
    SYNTAX       Gauge32
    MAX-ACCESS   read-only
    STATUS       current
    DESCRIPTION
        "Cisco Firepower sw:SspEthMonSrcAppLinksEp:eqAggrPortId
        managed object property"
    ::= { cfprSwSspEthMonSrcAppLinksEpEntry 5 }

cfprSwSspEthMonSrcAppLinksEpEqPortId OBJECT-TYPE
    SYNTAX       Gauge32
    MAX-ACCESS   read-only
    STATUS       current
    DESCRIPTION
        "Cisco Firepower sw:SspEthMonSrcAppLinksEp:eqPortId
        managed object property"
    ::= { cfprSwSspEthMonSrcAppLinksEpEntry 6 }

cfprSwSspEthMonSrcAppLinksEpEqSlotId OBJECT-TYPE
    SYNTAX       Gauge32
    MAX-ACCESS   read-only
    STATUS       current
    DESCRIPTION
        "Cisco Firepower sw:SspEthMonSrcAppLinksEp:eqSlotId
        managed object property"
    ::= { cfprSwSspEthMonSrcAppLinksEpEntry 7 }

cfprSwSspEthMonSrcAppLinksEpFilter OBJECT-TYPE
    SYNTAX       SnmpAdminString
    MAX-ACCESS   read-only
    STATUS       current
    DESCRIPTION
        "Cisco Firepower sw:SspEthMonSrcAppLinksEp:filter
        managed object property"
    ::= { cfprSwSspEthMonSrcAppLinksEpEntry 8 }

cfprSwSspEthMonSrcAppLinksEpFilterDn OBJECT-TYPE
    SYNTAX       SnmpAdminString
    MAX-ACCESS   read-only
    STATUS       current
    DESCRIPTION
        "Cisco Firepower sw:SspEthMonSrcAppLinksEp:filterDn
        managed object property"
    ::= { cfprSwSspEthMonSrcAppLinksEpEntry 9 }

cfprSwSspEthMonSrcAppLinksEpLifeCycle OBJECT-TYPE
    SYNTAX       CfprSwPktCaptureLifeCycle
    MAX-ACCESS   read-only
    STATUS       current
    DESCRIPTION
        "Cisco Firepower sw:SspEthMonSrcAppLinksEp:lifeCycle
        managed object property"
    ::= { cfprSwSspEthMonSrcAppLinksEpEntry 10 }

cfprSwSspEthMonSrcAppLinksEpName OBJECT-TYPE
    SYNTAX       SnmpAdminString
    MAX-ACCESS   read-only
    STATUS       current
    DESCRIPTION
        "Cisco Firepower sw:SspEthMonSrcAppLinksEp:name
        managed object property"
    ::= { cfprSwSspEthMonSrcAppLinksEpEntry 11 }

cfprSwSspEthMonSrcAppLinksEpPcapfile OBJECT-TYPE
    SYNTAX       SnmpAdminString
    MAX-ACCESS   read-only
    STATUS       current
    DESCRIPTION
        "Cisco Firepower sw:SspEthMonSrcAppLinksEp:pcapfile
        managed object property"
    ::= { cfprSwSspEthMonSrcAppLinksEpEntry 12 }

cfprSwSspEthMonSrcAppLinksEpPcapfilename OBJECT-TYPE
    SYNTAX       SnmpAdminString
    MAX-ACCESS   read-only
    STATUS       current
    DESCRIPTION
        "Cisco Firepower sw:SspEthMonSrcAppLinksEp:pcapfilename
        managed object property"
    ::= { cfprSwSspEthMonSrcAppLinksEpEntry 13 }

cfprSwSspEthMonSrcAppLinksEpPcapsize OBJECT-TYPE
    SYNTAX       Gauge32
    MAX-ACCESS   read-only
    STATUS       current
    DESCRIPTION
        "Cisco Firepower sw:SspEthMonSrcAppLinksEp:pcapsize
        managed object property"
    ::= { cfprSwSspEthMonSrcAppLinksEpEntry 14 }

cfprSwSspEthMonSrcAppLinksEpSwitchId OBJECT-TYPE
    SYNTAX       CfprNetworkSwitchId
    MAX-ACCESS   read-only
    STATUS       current
    DESCRIPTION
        "Cisco Firepower sw:SspEthMonSrcAppLinksEp:switchId
        managed object property"
    ::= { cfprSwSspEthMonSrcAppLinksEpEntry 15 }

cfprSwSspEthMonSrcAppLinksEpVlan OBJECT-TYPE
    SYNTAX       Gauge32
    MAX-ACCESS   read-only
    STATUS       current
    DESCRIPTION
        "Cisco Firepower sw:SspEthMonSrcAppLinksEp:vlan
        managed object property"
    ::= { cfprSwSspEthMonSrcAppLinksEpEntry 16 }

cfprSwSspEthMonSrcAppLinksEpVnicName1 OBJECT-TYPE
    SYNTAX       SnmpAdminString
    MAX-ACCESS   read-only
    STATUS       current
    DESCRIPTION
        "Cisco Firepower sw:SspEthMonSrcAppLinksEp:vnicName1
        managed object property"
    ::= { cfprSwSspEthMonSrcAppLinksEpEntry 17 }

cfprSwSspEthMonSrcAppLinksEpVifId OBJECT-TYPE
    SYNTAX       Gauge32
    MAX-ACCESS   read-only
    STATUS       current
    DESCRIPTION
        "Cisco Firepower sw:SspEthMonSrcAppLinksEp:vifId
        managed object property"
    ::= { cfprSwSspEthMonSrcAppLinksEpEntry 18 }

cfprSwSspEthMonSrcPhyEpTable OBJECT-TYPE
    SYNTAX           SEQUENCE OF CfprSwSspEthMonSrcPhyEpEntry
    MAX-ACCESS       not-accessible
    STATUS           current
    DESCRIPTION
        "Cisco Firepower sw:SspEthMonSrcPhyEp managed object table"
    ::= { cfprSwObjects 96 }

cfprSwSspEthMonSrcPhyEpEntry OBJECT-TYPE
    SYNTAX           CfprSwSspEthMonSrcPhyEpEntry
    MAX-ACCESS       not-accessible
    STATUS           current
    DESCRIPTION
        "Entry for the cfprSwSspEthMonSrcPhyEpTable table."
    INDEX { cfprSwSspEthMonSrcPhyEpInstanceId }
    ::= { cfprSwSspEthMonSrcPhyEpTable 1 }

CfprSwSspEthMonSrcPhyEpEntry ::= SEQUENCE {
    cfprSwSspEthMonSrcPhyEpInstanceId                                CfprManagedObjectId,
    cfprSwSspEthMonSrcPhyEpDn                                        CfprManagedObjectDn,
    cfprSwSspEthMonSrcPhyEpRn                                        SnmpAdminString,
    cfprSwSspEthMonSrcPhyEpAggrPortId                                Gauge32,
    cfprSwSspEthMonSrcPhyEpChassisId                                 Gauge32,
    cfprSwSspEthMonSrcPhyEpFilter                                    SnmpAdminString,
    cfprSwSspEthMonSrcPhyEpFilterDn                                  SnmpAdminString,
    cfprSwSspEthMonSrcPhyEpLifeCycle                                 CfprSwPktCaptureLifeCycle,
    cfprSwSspEthMonSrcPhyEpPcapfile                                  SnmpAdminString,
    cfprSwSspEthMonSrcPhyEpPcapfilename                              SnmpAdminString,
    cfprSwSspEthMonSrcPhyEpPcapsize                                  Gauge32,
    cfprSwSspEthMonSrcPhyEpPortId                                    Gauge32,
    cfprSwSspEthMonSrcPhyEpSlotId                                    Gauge32,
    cfprSwSspEthMonSrcPhyEpSwitchId                                  CfprNetworkSwitchId,
    cfprSwSspEthMonSrcPhyEpFsmDescr                                  SnmpAdminString,
    cfprSwSspEthMonSrcPhyEpFsmPrev                                   SnmpAdminString,
    cfprSwSspEthMonSrcPhyEpFsmProgr                                  Gauge32,
    cfprSwSspEthMonSrcPhyEpFsmRmtInvErrCode                          Gauge32,
    cfprSwSspEthMonSrcPhyEpFsmRmtInvErrDescr                         SnmpAdminString,
    cfprSwSspEthMonSrcPhyEpFsmRmtInvRslt                             CfprConditionRemoteInvRslt,
    cfprSwSspEthMonSrcPhyEpFsmStageDescr                             SnmpAdminString,
    cfprSwSspEthMonSrcPhyEpFsmStamp                                  DateAndTime,
    cfprSwSspEthMonSrcPhyEpFsmStatus                                 SnmpAdminString,
    cfprSwSspEthMonSrcPhyEpFsmTry                                    Gauge32,
    cfprSwSspEthMonSrcPhyEpPeerDn                                    SnmpAdminString,
    cfprSwSspEthMonSrcPhyEpEcmpId                                    Gauge32,
    cfprSwSspEthMonSrcPhyEpSubIfVlan                                 Gauge32
}

cfprSwSspEthMonSrcPhyEpInstanceId OBJECT-TYPE
    SYNTAX       CfprManagedObjectId
    MAX-ACCESS   not-accessible
    STATUS       current
    DESCRIPTION
        "Instance identifier of the managed object."
    ::= { cfprSwSspEthMonSrcPhyEpEntry 1 }

cfprSwSspEthMonSrcPhyEpDn OBJECT-TYPE
    SYNTAX       CfprManagedObjectDn
    MAX-ACCESS   read-only
    STATUS       current
    DESCRIPTION
        "Cisco Firepower sw:SspEthMonSrcPhyEp:dn managed object property"
    ::= { cfprSwSspEthMonSrcPhyEpEntry 2 }

cfprSwSspEthMonSrcPhyEpRn OBJECT-TYPE
    SYNTAX       SnmpAdminString
    MAX-ACCESS   read-only
    STATUS       current
    DESCRIPTION
        "Cisco Firepower sw:SspEthMonSrcPhyEp:rn managed object property"
    ::= { cfprSwSspEthMonSrcPhyEpEntry 3 }

cfprSwSspEthMonSrcPhyEpAggrPortId OBJECT-TYPE
    SYNTAX       Gauge32
    MAX-ACCESS   read-only
    STATUS       current
    DESCRIPTION
        "Cisco Firepower sw:SspEthMonSrcPhyEp:aggrPortId
        managed object property"
    ::= { cfprSwSspEthMonSrcPhyEpEntry 4 }

cfprSwSspEthMonSrcPhyEpChassisId OBJECT-TYPE
    SYNTAX       Gauge32
    MAX-ACCESS   read-only
    STATUS       current
    DESCRIPTION
        "Cisco Firepower sw:SspEthMonSrcPhyEp:chassisId
        managed object property"
    ::= { cfprSwSspEthMonSrcPhyEpEntry 5 }

cfprSwSspEthMonSrcPhyEpFilter OBJECT-TYPE
    SYNTAX       SnmpAdminString
    MAX-ACCESS   read-only
    STATUS       current
    DESCRIPTION
        "Cisco Firepower sw:SspEthMonSrcPhyEp:filter managed
        object property"
    ::= { cfprSwSspEthMonSrcPhyEpEntry 6 }

cfprSwSspEthMonSrcPhyEpFilterDn OBJECT-TYPE
    SYNTAX       SnmpAdminString
    MAX-ACCESS   read-only
    STATUS       current
    DESCRIPTION
        "Cisco Firepower sw:SspEthMonSrcPhyEp:filterDn
        managed object property"
    ::= { cfprSwSspEthMonSrcPhyEpEntry 7 }

cfprSwSspEthMonSrcPhyEpLifeCycle OBJECT-TYPE
    SYNTAX       CfprSwPktCaptureLifeCycle
    MAX-ACCESS   read-only
    STATUS       current
    DESCRIPTION
        "Cisco Firepower sw:SspEthMonSrcPhyEp:lifeCycle
        managed object property"
    ::= { cfprSwSspEthMonSrcPhyEpEntry 8 }

cfprSwSspEthMonSrcPhyEpPcapfile OBJECT-TYPE
    SYNTAX       SnmpAdminString
    MAX-ACCESS   read-only
    STATUS       current
    DESCRIPTION
        "Cisco Firepower sw:SspEthMonSrcPhyEp:pcapfile
        managed object property"
    ::= { cfprSwSspEthMonSrcPhyEpEntry 9 }

cfprSwSspEthMonSrcPhyEpPcapfilename OBJECT-TYPE
    SYNTAX       SnmpAdminString
    MAX-ACCESS   read-only
    STATUS       current
    DESCRIPTION
        "Cisco Firepower sw:SspEthMonSrcPhyEp:pcapfilename
        managed object property"
    ::= { cfprSwSspEthMonSrcPhyEpEntry 10 }

cfprSwSspEthMonSrcPhyEpPcapsize OBJECT-TYPE
    SYNTAX       Gauge32
    MAX-ACCESS   read-only
    STATUS       current
    DESCRIPTION
        "Cisco Firepower sw:SspEthMonSrcPhyEp:pcapsize
        managed object property"
    ::= { cfprSwSspEthMonSrcPhyEpEntry 11 }

cfprSwSspEthMonSrcPhyEpPortId OBJECT-TYPE
    SYNTAX       Gauge32
    MAX-ACCESS   read-only
    STATUS       current
    DESCRIPTION
        "Cisco Firepower sw:SspEthMonSrcPhyEp:portId managed
        object property"
    ::= { cfprSwSspEthMonSrcPhyEpEntry 12 }

cfprSwSspEthMonSrcPhyEpSlotId OBJECT-TYPE
    SYNTAX       Gauge32
    MAX-ACCESS   read-only
    STATUS       current
    DESCRIPTION
        "Cisco Firepower sw:SspEthMonSrcPhyEp:slotId managed
        object property"
    ::= { cfprSwSspEthMonSrcPhyEpEntry 13 }

cfprSwSspEthMonSrcPhyEpSwitchId OBJECT-TYPE
    SYNTAX       CfprNetworkSwitchId
    MAX-ACCESS   read-only
    STATUS       current
    DESCRIPTION
        "Cisco Firepower sw:SspEthMonSrcPhyEp:switchId
        managed object property"
    ::= { cfprSwSspEthMonSrcPhyEpEntry 14 }

cfprSwSspEthMonSrcPhyEpFsmDescr OBJECT-TYPE
    SYNTAX       SnmpAdminString
    MAX-ACCESS   read-only
    STATUS       current
    DESCRIPTION
        "Cisco Firepower sw:SspEthMonSrcPhyEp:fsmDescr
        managed object property"
    ::= { cfprSwSspEthMonSrcPhyEpEntry 15 }

cfprSwSspEthMonSrcPhyEpFsmPrev OBJECT-TYPE
    SYNTAX       SnmpAdminString
    MAX-ACCESS   read-only
    STATUS       current
    DESCRIPTION
        "Cisco Firepower sw:SspEthMonSrcPhyEp:fsmPrev managed
        object property"
    ::= { cfprSwSspEthMonSrcPhyEpEntry 16 }

cfprSwSspEthMonSrcPhyEpFsmProgr OBJECT-TYPE
    SYNTAX       Gauge32
    MAX-ACCESS   read-only
    STATUS       current
    DESCRIPTION
        "Cisco Firepower sw:SspEthMonSrcPhyEp:fsmProgr
        managed object property"
    ::= { cfprSwSspEthMonSrcPhyEpEntry 17 }

cfprSwSspEthMonSrcPhyEpFsmRmtInvErrCode OBJECT-TYPE
    SYNTAX       Gauge32
    MAX-ACCESS   read-only
    STATUS       current
    DESCRIPTION
        "Cisco Firepower sw:SspEthMonSrcPhyEp:fsmRmtInvErrCode
        managed object property"
    ::= { cfprSwSspEthMonSrcPhyEpEntry 18 }

cfprSwSspEthMonSrcPhyEpFsmRmtInvErrDescr OBJECT-TYPE
    SYNTAX       SnmpAdminString
    MAX-ACCESS   read-only
    STATUS       current
    DESCRIPTION
        "Cisco Firepower sw:SspEthMonSrcPhyEp:fsmRmtInvErrDescr
        managed object property"
    ::= { cfprSwSspEthMonSrcPhyEpEntry 19 }

cfprSwSspEthMonSrcPhyEpFsmRmtInvRslt OBJECT-TYPE
    SYNTAX       CfprConditionRemoteInvRslt
    MAX-ACCESS   read-only
    STATUS       current
    DESCRIPTION
        "Cisco Firepower sw:SspEthMonSrcPhyEp:fsmRmtInvRslt
        managed object property"
    ::= { cfprSwSspEthMonSrcPhyEpEntry 20 }

cfprSwSspEthMonSrcPhyEpFsmStageDescr OBJECT-TYPE
    SYNTAX       SnmpAdminString
    MAX-ACCESS   read-only
    STATUS       current
    DESCRIPTION
        "Cisco Firepower sw:SspEthMonSrcPhyEp:fsmStageDescr
        managed object property"
    ::= { cfprSwSspEthMonSrcPhyEpEntry 21 }

cfprSwSspEthMonSrcPhyEpFsmStamp OBJECT-TYPE
    SYNTAX       DateAndTime
    MAX-ACCESS   read-only
    STATUS       current
    DESCRIPTION
        "Cisco Firepower sw:SspEthMonSrcPhyEp:fsmStamp
        managed object property"
    ::= { cfprSwSspEthMonSrcPhyEpEntry 22 }

cfprSwSspEthMonSrcPhyEpFsmStatus OBJECT-TYPE
    SYNTAX       SnmpAdminString
    MAX-ACCESS   read-only
    STATUS       current
    DESCRIPTION
        "Cisco Firepower sw:SspEthMonSrcPhyEp:fsmStatus
        managed object property"
    ::= { cfprSwSspEthMonSrcPhyEpEntry 23 }

cfprSwSspEthMonSrcPhyEpFsmTry OBJECT-TYPE
    SYNTAX       Gauge32
    MAX-ACCESS   read-only
    STATUS       current
    DESCRIPTION
        "Cisco Firepower sw:SspEthMonSrcPhyEp:fsmTry managed
        object property"
    ::= { cfprSwSspEthMonSrcPhyEpEntry 24 }

cfprSwSspEthMonSrcPhyEpPeerDn OBJECT-TYPE
    SYNTAX       SnmpAdminString
    MAX-ACCESS   read-only
    STATUS       current
    DESCRIPTION
        "Cisco Firepower sw:SspEthMonSrcPhyEp:peerDn managed
        object property"
    ::= { cfprSwSspEthMonSrcPhyEpEntry 25 }

cfprSwSspEthMonSrcPhyEpEcmpId OBJECT-TYPE
    SYNTAX       Gauge32
    MAX-ACCESS   read-only
    STATUS       current
    DESCRIPTION
        "Cisco Firepower sw:SspEthMonSrcPhyEp:ecmpId managed
        object property"
    ::= { cfprSwSspEthMonSrcPhyEpEntry 26 }

cfprSwSspEthMonSrcPhyEpSubIfVlan OBJECT-TYPE
    SYNTAX       Gauge32
    MAX-ACCESS   read-only
    STATUS       current
    DESCRIPTION
        "Cisco Firepower sw:SspEthMonSrcPhyEp:subIfVlan
        managed object property"
    ::= { cfprSwSspEthMonSrcPhyEpEntry 27 }

cfprSwSspEthMonSrcPhyEpFsmTable OBJECT-TYPE
    SYNTAX           SEQUENCE OF CfprSwSspEthMonSrcPhyEpFsmEntry
    MAX-ACCESS       not-accessible
    STATUS           current
    DESCRIPTION
        "Cisco Firepower sw:SspEthMonSrcPhyEpFsm managed object table"
    ::= { cfprSwObjects 97 }

cfprSwSspEthMonSrcPhyEpFsmEntry OBJECT-TYPE
    SYNTAX           CfprSwSspEthMonSrcPhyEpFsmEntry
    MAX-ACCESS       not-accessible
    STATUS           current
    DESCRIPTION
        "Entry for the cfprSwSspEthMonSrcPhyEpFsmTable table."
    INDEX { cfprSwSspEthMonSrcPhyEpFsmInstanceId }
    ::= { cfprSwSspEthMonSrcPhyEpFsmTable 1 }

CfprSwSspEthMonSrcPhyEpFsmEntry ::= SEQUENCE {
    cfprSwSspEthMonSrcPhyEpFsmInstanceId                             CfprManagedObjectId,
    cfprSwSspEthMonSrcPhyEpFsmDn                                     CfprManagedObjectDn,
    cfprSwSspEthMonSrcPhyEpFsmRn                                     SnmpAdminString,
    cfprSwSspEthMonSrcPhyEpFsmCompletionTime                         DateAndTime,
    cfprSwSspEthMonSrcPhyEpFsmCurrentFsm                             CfprSwSspEthMonSrcPhyEpFsmCurrentFsm,
    cfprSwSspEthMonSrcPhyEpFsmDescrData                              SnmpAdminString,
    cfprSwSspEthMonSrcPhyEpFsmFsmStatus                              CfprFsmFsmStageStatus,
    cfprSwSspEthMonSrcPhyEpFsmProgress                               Gauge32,
    cfprSwSspEthMonSrcPhyEpFsmRmtErrCode                             Gauge32,
    cfprSwSspEthMonSrcPhyEpFsmRmtErrDescr                            SnmpAdminString,
    cfprSwSspEthMonSrcPhyEpFsmRmtRslt                                CfprConditionRemoteInvRslt
}

cfprSwSspEthMonSrcPhyEpFsmInstanceId OBJECT-TYPE
    SYNTAX       CfprManagedObjectId
    MAX-ACCESS   not-accessible
    STATUS       current
    DESCRIPTION
        "Instance identifier of the managed object."
    ::= { cfprSwSspEthMonSrcPhyEpFsmEntry 1 }

cfprSwSspEthMonSrcPhyEpFsmDn OBJECT-TYPE
    SYNTAX       CfprManagedObjectDn
    MAX-ACCESS   read-only
    STATUS       current
    DESCRIPTION
        "Cisco Firepower sw:SspEthMonSrcPhyEpFsm:dn managed
        object property"
    ::= { cfprSwSspEthMonSrcPhyEpFsmEntry 2 }

cfprSwSspEthMonSrcPhyEpFsmRn OBJECT-TYPE
    SYNTAX       SnmpAdminString
    MAX-ACCESS   read-only
    STATUS       current
    DESCRIPTION
        "Cisco Firepower sw:SspEthMonSrcPhyEpFsm:rn managed
        object property"
    ::= { cfprSwSspEthMonSrcPhyEpFsmEntry 3 }

cfprSwSspEthMonSrcPhyEpFsmCompletionTime OBJECT-TYPE
    SYNTAX       DateAndTime
    MAX-ACCESS   read-only
    STATUS       current
    DESCRIPTION
        "Cisco Firepower sw:SspEthMonSrcPhyEpFsm:completionTime
        managed object property"
    ::= { cfprSwSspEthMonSrcPhyEpFsmEntry 4 }

cfprSwSspEthMonSrcPhyEpFsmCurrentFsm OBJECT-TYPE
    SYNTAX       CfprSwSspEthMonSrcPhyEpFsmCurrentFsm
    MAX-ACCESS   read-only
    STATUS       current
    DESCRIPTION
        "Cisco Firepower sw:SspEthMonSrcPhyEpFsm:currentFsm
        managed object property"
    ::= { cfprSwSspEthMonSrcPhyEpFsmEntry 5 }

cfprSwSspEthMonSrcPhyEpFsmDescrData OBJECT-TYPE
    SYNTAX       SnmpAdminString
    MAX-ACCESS   read-only
    STATUS       current
    DESCRIPTION
        "Cisco Firepower sw:SspEthMonSrcPhyEpFsm:descr
        managed object property"
    ::= { cfprSwSspEthMonSrcPhyEpFsmEntry 6 }

cfprSwSspEthMonSrcPhyEpFsmFsmStatus OBJECT-TYPE
    SYNTAX       CfprFsmFsmStageStatus
    MAX-ACCESS   read-only
    STATUS       current
    DESCRIPTION
        "Cisco Firepower sw:SspEthMonSrcPhyEpFsm:fsmStatus
        managed object property"
    ::= { cfprSwSspEthMonSrcPhyEpFsmEntry 7 }

cfprSwSspEthMonSrcPhyEpFsmProgress OBJECT-TYPE
    SYNTAX       Gauge32
    MAX-ACCESS   read-only
    STATUS       current
    DESCRIPTION
        "Cisco Firepower sw:SspEthMonSrcPhyEpFsm:progress
        managed object property"
    ::= { cfprSwSspEthMonSrcPhyEpFsmEntry 8 }

cfprSwSspEthMonSrcPhyEpFsmRmtErrCode OBJECT-TYPE
    SYNTAX       Gauge32
    MAX-ACCESS   read-only
    STATUS       current
    DESCRIPTION
        "Cisco Firepower sw:SspEthMonSrcPhyEpFsm:rmtErrCode
        managed object property"
    ::= { cfprSwSspEthMonSrcPhyEpFsmEntry 9 }

cfprSwSspEthMonSrcPhyEpFsmRmtErrDescr OBJECT-TYPE
    SYNTAX       SnmpAdminString
    MAX-ACCESS   read-only
    STATUS       current
    DESCRIPTION
        "Cisco Firepower sw:SspEthMonSrcPhyEpFsm:rmtErrDescr
        managed object property"
    ::= { cfprSwSspEthMonSrcPhyEpFsmEntry 10 }

cfprSwSspEthMonSrcPhyEpFsmRmtRslt OBJECT-TYPE
    SYNTAX       CfprConditionRemoteInvRslt
    MAX-ACCESS   read-only
    STATUS       current
    DESCRIPTION
        "Cisco Firepower sw:SspEthMonSrcPhyEpFsm:rmtRslt
        managed object property"
    ::= { cfprSwSspEthMonSrcPhyEpFsmEntry 11 }

cfprSwSspEthMonSrcPhyEpFsmStageTable OBJECT-TYPE
    SYNTAX           SEQUENCE OF CfprSwSspEthMonSrcPhyEpFsmStageEntry
    MAX-ACCESS       not-accessible
    STATUS           current
    DESCRIPTION
        "Cisco Firepower sw:SspEthMonSrcPhyEpFsmStage managed
        object table"
    ::= { cfprSwObjects 98 }

cfprSwSspEthMonSrcPhyEpFsmStageEntry OBJECT-TYPE
    SYNTAX           CfprSwSspEthMonSrcPhyEpFsmStageEntry
    MAX-ACCESS       not-accessible
    STATUS           current
    DESCRIPTION
        "Entry for the cfprSwSspEthMonSrcPhyEpFsmStageTable table."
    INDEX { cfprSwSspEthMonSrcPhyEpFsmStageInstanceId }
    ::= { cfprSwSspEthMonSrcPhyEpFsmStageTable 1 }

CfprSwSspEthMonSrcPhyEpFsmStageEntry ::= SEQUENCE {
    cfprSwSspEthMonSrcPhyEpFsmStageInstanceId                        CfprManagedObjectId,
    cfprSwSspEthMonSrcPhyEpFsmStageDn                                CfprManagedObjectDn,
    cfprSwSspEthMonSrcPhyEpFsmStageRn                                SnmpAdminString,
    cfprSwSspEthMonSrcPhyEpFsmStageDescrData                         SnmpAdminString,
    cfprSwSspEthMonSrcPhyEpFsmStageLastUpdateTime                    DateAndTime,
    cfprSwSspEthMonSrcPhyEpFsmStageName                              CfprSwSspEthMonSrcPhyEpFsmStageName,
    cfprSwSspEthMonSrcPhyEpFsmStageOrder                             Gauge32,
    cfprSwSspEthMonSrcPhyEpFsmStageRetry                             Gauge32,
    cfprSwSspEthMonSrcPhyEpFsmStageStageStatus                       CfprFsmFsmStageStatus
}

cfprSwSspEthMonSrcPhyEpFsmStageInstanceId OBJECT-TYPE
    SYNTAX       CfprManagedObjectId
    MAX-ACCESS   not-accessible
    STATUS       current
    DESCRIPTION
        "Instance identifier of the managed object."
    ::= { cfprSwSspEthMonSrcPhyEpFsmStageEntry 1 }

cfprSwSspEthMonSrcPhyEpFsmStageDn OBJECT-TYPE
    SYNTAX       CfprManagedObjectDn
    MAX-ACCESS   read-only
    STATUS       current
    DESCRIPTION
        "Cisco Firepower sw:SspEthMonSrcPhyEpFsmStage:dn
        managed object property"
    ::= { cfprSwSspEthMonSrcPhyEpFsmStageEntry 2 }

cfprSwSspEthMonSrcPhyEpFsmStageRn OBJECT-TYPE
    SYNTAX       SnmpAdminString
    MAX-ACCESS   read-only
    STATUS       current
    DESCRIPTION
        "Cisco Firepower sw:SspEthMonSrcPhyEpFsmStage:rn
        managed object property"
    ::= { cfprSwSspEthMonSrcPhyEpFsmStageEntry 3 }

cfprSwSspEthMonSrcPhyEpFsmStageDescrData OBJECT-TYPE
    SYNTAX       SnmpAdminString
    MAX-ACCESS   read-only
    STATUS       current
    DESCRIPTION
        "Cisco Firepower sw:SspEthMonSrcPhyEpFsmStage:descr
        managed object property"
    ::= { cfprSwSspEthMonSrcPhyEpFsmStageEntry 4 }

cfprSwSspEthMonSrcPhyEpFsmStageLastUpdateTime OBJECT-TYPE
    SYNTAX       DateAndTime
    MAX-ACCESS   read-only
    STATUS       current
    DESCRIPTION
        "Cisco Firepower sw:SspEthMonSrcPhyEpFsmStage:lastUpdateTime
        managed object property"
    ::= { cfprSwSspEthMonSrcPhyEpFsmStageEntry 5 }

cfprSwSspEthMonSrcPhyEpFsmStageName OBJECT-TYPE
    SYNTAX       CfprSwSspEthMonSrcPhyEpFsmStageName
    MAX-ACCESS   read-only
    STATUS       current
    DESCRIPTION
        "Cisco Firepower sw:SspEthMonSrcPhyEpFsmStage:name
        managed object property"
    ::= { cfprSwSspEthMonSrcPhyEpFsmStageEntry 6 }

cfprSwSspEthMonSrcPhyEpFsmStageOrder OBJECT-TYPE
    SYNTAX       Gauge32
    MAX-ACCESS   read-only
    STATUS       current
    DESCRIPTION
        "Cisco Firepower sw:SspEthMonSrcPhyEpFsmStage:order
        managed object property"
    ::= { cfprSwSspEthMonSrcPhyEpFsmStageEntry 7 }

cfprSwSspEthMonSrcPhyEpFsmStageRetry OBJECT-TYPE
    SYNTAX       Gauge32
    MAX-ACCESS   read-only
    STATUS       current
    DESCRIPTION
        "Cisco Firepower sw:SspEthMonSrcPhyEpFsmStage:retry
        managed object property"
    ::= { cfprSwSspEthMonSrcPhyEpFsmStageEntry 8 }

cfprSwSspEthMonSrcPhyEpFsmStageStageStatus OBJECT-TYPE
    SYNTAX       CfprFsmFsmStageStatus
    MAX-ACCESS   read-only
    STATUS       current
    DESCRIPTION
        "Cisco Firepower sw:SspEthMonSrcPhyEpFsmStage:stageStatus
        managed object property"
    ::= { cfprSwSspEthMonSrcPhyEpFsmStageEntry 9 }

cfprSwSspEthMonSrcPhyEpFsmTaskTable OBJECT-TYPE
    SYNTAX           SEQUENCE OF CfprSwSspEthMonSrcPhyEpFsmTaskEntry
    MAX-ACCESS       not-accessible
    STATUS           current
    DESCRIPTION
        "Cisco Firepower sw:SspEthMonSrcPhyEpFsmTask managed object table"
    ::= { cfprSwObjects 99 }

cfprSwSspEthMonSrcPhyEpFsmTaskEntry OBJECT-TYPE
    SYNTAX           CfprSwSspEthMonSrcPhyEpFsmTaskEntry
    MAX-ACCESS       not-accessible
    STATUS           current
    DESCRIPTION
        "Entry for the cfprSwSspEthMonSrcPhyEpFsmTaskTable table."
    INDEX { cfprSwSspEthMonSrcPhyEpFsmTaskInstanceId }
    ::= { cfprSwSspEthMonSrcPhyEpFsmTaskTable 1 }

CfprSwSspEthMonSrcPhyEpFsmTaskEntry ::= SEQUENCE {
    cfprSwSspEthMonSrcPhyEpFsmTaskInstanceId                         CfprManagedObjectId,
    cfprSwSspEthMonSrcPhyEpFsmTaskDn                                 CfprManagedObjectDn,
    cfprSwSspEthMonSrcPhyEpFsmTaskRn                                 SnmpAdminString,
    cfprSwSspEthMonSrcPhyEpFsmTaskCompletion                         CfprFsmCompletion,
    cfprSwSspEthMonSrcPhyEpFsmTaskFlags                              CfprFsmFlags,
    cfprSwSspEthMonSrcPhyEpFsmTaskItem                               CfprSwSspEthMonSrcPhyEpFsmTaskItem,
    cfprSwSspEthMonSrcPhyEpFsmTaskSeqId                              Gauge32
}

cfprSwSspEthMonSrcPhyEpFsmTaskInstanceId OBJECT-TYPE
    SYNTAX       CfprManagedObjectId
    MAX-ACCESS   not-accessible
    STATUS       current
    DESCRIPTION
        "Instance identifier of the managed object."
    ::= { cfprSwSspEthMonSrcPhyEpFsmTaskEntry 1 }

cfprSwSspEthMonSrcPhyEpFsmTaskDn OBJECT-TYPE
    SYNTAX       CfprManagedObjectDn
    MAX-ACCESS   read-only
    STATUS       current
    DESCRIPTION
        "Cisco Firepower sw:SspEthMonSrcPhyEpFsmTask:dn
        managed object property"
    ::= { cfprSwSspEthMonSrcPhyEpFsmTaskEntry 2 }

cfprSwSspEthMonSrcPhyEpFsmTaskRn OBJECT-TYPE
    SYNTAX       SnmpAdminString
    MAX-ACCESS   read-only
    STATUS       current
    DESCRIPTION
        "Cisco Firepower sw:SspEthMonSrcPhyEpFsmTask:rn
        managed object property"
    ::= { cfprSwSspEthMonSrcPhyEpFsmTaskEntry 3 }

cfprSwSspEthMonSrcPhyEpFsmTaskCompletion OBJECT-TYPE
    SYNTAX       CfprFsmCompletion
    MAX-ACCESS   read-only
    STATUS       current
    DESCRIPTION
        "Cisco Firepower sw:SspEthMonSrcPhyEpFsmTask:completion
        managed object property"
    ::= { cfprSwSspEthMonSrcPhyEpFsmTaskEntry 4 }

cfprSwSspEthMonSrcPhyEpFsmTaskFlags OBJECT-TYPE
    SYNTAX       CfprFsmFlags
    MAX-ACCESS   read-only
    STATUS       current
    DESCRIPTION
        "Cisco Firepower sw:SspEthMonSrcPhyEpFsmTask:flags
        managed object property"
    ::= { cfprSwSspEthMonSrcPhyEpFsmTaskEntry 5 }

cfprSwSspEthMonSrcPhyEpFsmTaskItem OBJECT-TYPE
    SYNTAX       CfprSwSspEthMonSrcPhyEpFsmTaskItem
    MAX-ACCESS   read-only
    STATUS       current
    DESCRIPTION
        "Cisco Firepower sw:SspEthMonSrcPhyEpFsmTask:item
        managed object property"
    ::= { cfprSwSspEthMonSrcPhyEpFsmTaskEntry 6 }

cfprSwSspEthMonSrcPhyEpFsmTaskSeqId OBJECT-TYPE
    SYNTAX       Gauge32
    MAX-ACCESS   read-only
    STATUS       current
    DESCRIPTION
        "Cisco Firepower sw:SspEthMonSrcPhyEpFsmTask:seqId
        managed object property"
    ::= { cfprSwSspEthMonSrcPhyEpFsmTaskEntry 7 }

cfprSwSubGroupTable OBJECT-TYPE
    SYNTAX           SEQUENCE OF CfprSwSubGroupEntry
    MAX-ACCESS       not-accessible
    STATUS           current
    DESCRIPTION
        "Cisco Firepower sw:SubGroup managed object table"
    ::= { cfprSwObjects 71 }

cfprSwSubGroupEntry OBJECT-TYPE
    SYNTAX           CfprSwSubGroupEntry
    MAX-ACCESS       not-accessible
    STATUS           current
    DESCRIPTION
        "Entry for the cfprSwSubGroupTable table."
    INDEX { cfprSwSubGroupInstanceId }
    ::= { cfprSwSubGroupTable 1 }

CfprSwSubGroupEntry ::= SEQUENCE {
    cfprSwSubGroupInstanceId                                         CfprManagedObjectId,
    cfprSwSubGroupDn                                                 CfprManagedObjectDn,
    cfprSwSubGroupRn                                                 SnmpAdminString,
    cfprSwSubGroupAggrPortId                                         CfprSwSubGroupAggrPortId,
    cfprSwSubGroupLicGP                                              Unsigned64,
    cfprSwSubGroupLicState                                           CfprLicenseState,
    cfprSwSubGroupLocale                                             CfprNetworkLocale,
    cfprSwSubGroupName                                               SnmpAdminString,
    cfprSwSubGroupSlotId                                             CfprSwSubGroupSlotId,
    cfprSwSubGroupSwitchId                                           CfprNetworkSwitchId,
    cfprSwSubGroupTransport                                          CfprNetworkTransport,
    cfprSwSubGroupType                                               CfprNetworkConnectionType
}

cfprSwSubGroupInstanceId OBJECT-TYPE
    SYNTAX       CfprManagedObjectId
    MAX-ACCESS   not-accessible
    STATUS       current
    DESCRIPTION
        "Instance identifier of the managed object."
    ::= { cfprSwSubGroupEntry 1 }

cfprSwSubGroupDn OBJECT-TYPE
    SYNTAX       CfprManagedObjectDn
    MAX-ACCESS   read-only
    STATUS       current
    DESCRIPTION
        "Cisco Firepower sw:SubGroup:dn managed object property"
    ::= { cfprSwSubGroupEntry 2 }

cfprSwSubGroupRn OBJECT-TYPE
    SYNTAX       SnmpAdminString
    MAX-ACCESS   read-only
    STATUS       current
    DESCRIPTION
        "Cisco Firepower sw:SubGroup:rn managed object property"
    ::= { cfprSwSubGroupEntry 3 }

cfprSwSubGroupAggrPortId OBJECT-TYPE
    SYNTAX       CfprSwSubGroupAggrPortId
    MAX-ACCESS   read-only
    STATUS       current
    DESCRIPTION
        "Cisco Firepower sw:SubGroup:aggrPortId managed object property"
    ::= { cfprSwSubGroupEntry 4 }

cfprSwSubGroupLicGP OBJECT-TYPE
    SYNTAX       Unsigned64
    MAX-ACCESS   read-only
    STATUS       current
    DESCRIPTION
        "Cisco Firepower sw:SubGroup:licGP managed object property"
    ::= { cfprSwSubGroupEntry 5 }

cfprSwSubGroupLicState OBJECT-TYPE
    SYNTAX       CfprLicenseState
    MAX-ACCESS   read-only
    STATUS       current
    DESCRIPTION
        "Cisco Firepower sw:SubGroup:licState managed object property"
    ::= { cfprSwSubGroupEntry 6 }

cfprSwSubGroupLocale OBJECT-TYPE
    SYNTAX       CfprNetworkLocale
    MAX-ACCESS   read-only
    STATUS       current
    DESCRIPTION
        "Cisco Firepower sw:SubGroup:locale managed object property"
    ::= { cfprSwSubGroupEntry 7 }

cfprSwSubGroupName OBJECT-TYPE
    SYNTAX       SnmpAdminString
    MAX-ACCESS   read-only
    STATUS       current
    DESCRIPTION
        "Cisco Firepower sw:SubGroup:name managed object property"
    ::= { cfprSwSubGroupEntry 8 }

cfprSwSubGroupSlotId OBJECT-TYPE
    SYNTAX       CfprSwSubGroupSlotId
    MAX-ACCESS   read-only
    STATUS       current
    DESCRIPTION
        "Cisco Firepower sw:SubGroup:slotId managed object property"
    ::= { cfprSwSubGroupEntry 9 }

cfprSwSubGroupSwitchId OBJECT-TYPE
    SYNTAX       CfprNetworkSwitchId
    MAX-ACCESS   read-only
    STATUS       current
    DESCRIPTION
        "Cisco Firepower sw:SubGroup:switchId managed object property"
    ::= { cfprSwSubGroupEntry 10 }

cfprSwSubGroupTransport OBJECT-TYPE
    SYNTAX       CfprNetworkTransport
    MAX-ACCESS   read-only
    STATUS       current
    DESCRIPTION
        "Cisco Firepower sw:SubGroup:transport managed object property"
    ::= { cfprSwSubGroupEntry 11 }

cfprSwSubGroupType OBJECT-TYPE
    SYNTAX       CfprNetworkConnectionType
    MAX-ACCESS   read-only
    STATUS       current
    DESCRIPTION
        "Cisco Firepower sw:SubGroup:type managed object property"
    ::= { cfprSwSubGroupEntry 12 }

cfprSwSystemStatsTable OBJECT-TYPE
    SYNTAX           SEQUENCE OF CfprSwSystemStatsEntry
    MAX-ACCESS       not-accessible
    STATUS           current
    DESCRIPTION
        "Cisco Firepower sw:SystemStats managed object table"
    ::= { cfprSwObjects 72 }

cfprSwSystemStatsEntry OBJECT-TYPE
    SYNTAX           CfprSwSystemStatsEntry
    MAX-ACCESS       not-accessible
    STATUS           current
    DESCRIPTION
        "Entry for the cfprSwSystemStatsTable table."
    INDEX { cfprSwSystemStatsInstanceId }
    ::= { cfprSwSystemStatsTable 1 }

CfprSwSystemStatsEntry ::= SEQUENCE {
    cfprSwSystemStatsInstanceId                                      CfprManagedObjectId,
    cfprSwSystemStatsDn                                              CfprManagedObjectDn,
    cfprSwSystemStatsRn                                              SnmpAdminString,
    cfprSwSystemStatsIntervals                                       Gauge32,
    cfprSwSystemStatsLoad                                            INTEGER,
    cfprSwSystemStatsLoadAvg                                         INTEGER,
    cfprSwSystemStatsLoadMax                                         INTEGER,
    cfprSwSystemStatsLoadMin                                         INTEGER,
    cfprSwSystemStatsMemAvailable                                    Gauge32,
    cfprSwSystemStatsMemAvailableAvg                                 Gauge32,
    cfprSwSystemStatsMemAvailableMax                                 Gauge32,
    cfprSwSystemStatsMemAvailableMin                                 Gauge32,
    cfprSwSystemStatsMemCached                                       Gauge32,
    cfprSwSystemStatsMemCachedAvg                                    Gauge32,
    cfprSwSystemStatsMemCachedMax                                    Gauge32,
    cfprSwSystemStatsMemCachedMin                                    Gauge32,
    cfprSwSystemStatsSuspect                                         TruthValue,
    cfprSwSystemStatsThresholded                                     CfprSwSystemStatsThresholded,
    cfprSwSystemStatsTimeCollected                                   DateAndTime,
    cfprSwSystemStatsUpdate                                          Gauge32
}

cfprSwSystemStatsInstanceId OBJECT-TYPE
    SYNTAX       CfprManagedObjectId
    MAX-ACCESS   not-accessible
    STATUS       current
    DESCRIPTION
        "Instance identifier of the managed object."
    ::= { cfprSwSystemStatsEntry 1 }

cfprSwSystemStatsDn OBJECT-TYPE
    SYNTAX       CfprManagedObjectDn
    MAX-ACCESS   read-only
    STATUS       current
    DESCRIPTION
        "Cisco Firepower sw:SystemStats:dn managed object property"
    ::= { cfprSwSystemStatsEntry 2 }

cfprSwSystemStatsRn OBJECT-TYPE
    SYNTAX       SnmpAdminString
    MAX-ACCESS   read-only
    STATUS       current
    DESCRIPTION
        "Cisco Firepower sw:SystemStats:rn managed object property"
    ::= { cfprSwSystemStatsEntry 3 }

cfprSwSystemStatsIntervals OBJECT-TYPE
    SYNTAX       Gauge32
    MAX-ACCESS   read-only
    STATUS       current
    DESCRIPTION
        "Cisco Firepower sw:SystemStats:intervals managed object property"
    ::= { cfprSwSystemStatsEntry 4 }

cfprSwSystemStatsLoad OBJECT-TYPE
    SYNTAX       INTEGER
    MAX-ACCESS   read-only
    STATUS       current
    DESCRIPTION
        "Cisco Firepower sw:SystemStats:load managed object property"
    ::= { cfprSwSystemStatsEntry 5 }

cfprSwSystemStatsLoadAvg OBJECT-TYPE
    SYNTAX       INTEGER
    MAX-ACCESS   read-only
    STATUS       current
    DESCRIPTION
        "Cisco Firepower sw:SystemStats:loadAvg managed object property"
    ::= { cfprSwSystemStatsEntry 6 }

cfprSwSystemStatsLoadMax OBJECT-TYPE
    SYNTAX       INTEGER
    MAX-ACCESS   read-only
    STATUS       current
    DESCRIPTION
        "Cisco Firepower sw:SystemStats:loadMax managed object property"
    ::= { cfprSwSystemStatsEntry 7 }

cfprSwSystemStatsLoadMin OBJECT-TYPE
    SYNTAX       INTEGER
    MAX-ACCESS   read-only
    STATUS       current
    DESCRIPTION
        "Cisco Firepower sw:SystemStats:loadMin managed object property"
    ::= { cfprSwSystemStatsEntry 8 }

cfprSwSystemStatsMemAvailable OBJECT-TYPE
    SYNTAX       Gauge32
    MAX-ACCESS   read-only
    STATUS       current
    DESCRIPTION
        "Cisco Firepower sw:SystemStats:memAvailable managed
        object property"
    ::= { cfprSwSystemStatsEntry 9 }

cfprSwSystemStatsMemAvailableAvg OBJECT-TYPE
    SYNTAX       Gauge32
    MAX-ACCESS   read-only
    STATUS       current
    DESCRIPTION
        "Cisco Firepower sw:SystemStats:memAvailableAvg
        managed object property"
    ::= { cfprSwSystemStatsEntry 10 }

cfprSwSystemStatsMemAvailableMax OBJECT-TYPE
    SYNTAX       Gauge32
    MAX-ACCESS   read-only
    STATUS       current
    DESCRIPTION
        "Cisco Firepower sw:SystemStats:memAvailableMax
        managed object property"
    ::= { cfprSwSystemStatsEntry 11 }

cfprSwSystemStatsMemAvailableMin OBJECT-TYPE
    SYNTAX       Gauge32
    MAX-ACCESS   read-only
    STATUS       current
    DESCRIPTION
        "Cisco Firepower sw:SystemStats:memAvailableMin
        managed object property"
    ::= { cfprSwSystemStatsEntry 12 }

cfprSwSystemStatsMemCached OBJECT-TYPE
    SYNTAX       Gauge32
    MAX-ACCESS   read-only
    STATUS       current
    DESCRIPTION
        "Cisco Firepower sw:SystemStats:memCached managed object property"
    ::= { cfprSwSystemStatsEntry 13 }

cfprSwSystemStatsMemCachedAvg OBJECT-TYPE
    SYNTAX       Gauge32
    MAX-ACCESS   read-only
    STATUS       current
    DESCRIPTION
        "Cisco Firepower sw:SystemStats:memCachedAvg managed
        object property"
    ::= { cfprSwSystemStatsEntry 14 }

cfprSwSystemStatsMemCachedMax OBJECT-TYPE
    SYNTAX       Gauge32
    MAX-ACCESS   read-only
    STATUS       current
    DESCRIPTION
        "Cisco Firepower sw:SystemStats:memCachedMax managed
        object property"
    ::= { cfprSwSystemStatsEntry 15 }

cfprSwSystemStatsMemCachedMin OBJECT-TYPE
    SYNTAX       Gauge32
    MAX-ACCESS   read-only
    STATUS       current
    DESCRIPTION
        "Cisco Firepower sw:SystemStats:memCachedMin managed
        object property"
    ::= { cfprSwSystemStatsEntry 16 }

cfprSwSystemStatsSuspect OBJECT-TYPE
    SYNTAX       TruthValue
    MAX-ACCESS   read-only
    STATUS       current
    DESCRIPTION
        "Cisco Firepower sw:SystemStats:suspect managed object property"
    ::= { cfprSwSystemStatsEntry 17 }

cfprSwSystemStatsThresholded OBJECT-TYPE
    SYNTAX       CfprSwSystemStatsThresholded
    MAX-ACCESS   read-only
    STATUS       current
    DESCRIPTION
        "Cisco Firepower sw:SystemStats:thresholded managed
        object property"
    ::= { cfprSwSystemStatsEntry 18 }

cfprSwSystemStatsTimeCollected OBJECT-TYPE
    SYNTAX       DateAndTime
    MAX-ACCESS   read-only
    STATUS       current
    DESCRIPTION
        "Cisco Firepower sw:SystemStats:timeCollected managed
        object property"
    ::= { cfprSwSystemStatsEntry 19 }

cfprSwSystemStatsUpdate OBJECT-TYPE
    SYNTAX       Gauge32
    MAX-ACCESS   read-only
    STATUS       current
    DESCRIPTION
        "Cisco Firepower sw:SystemStats:update managed object property"
    ::= { cfprSwSystemStatsEntry 20 }

cfprSwSystemStatsHistTable OBJECT-TYPE
    SYNTAX           SEQUENCE OF CfprSwSystemStatsHistEntry
    MAX-ACCESS       not-accessible
    STATUS           current
    DESCRIPTION
        "Cisco Firepower sw:SystemStatsHist managed object table"
    ::= { cfprSwObjects 73 }

cfprSwSystemStatsHistEntry OBJECT-TYPE
    SYNTAX           CfprSwSystemStatsHistEntry
    MAX-ACCESS       not-accessible
    STATUS           current
    DESCRIPTION
        "Entry for the cfprSwSystemStatsHistTable table."
    INDEX { cfprSwSystemStatsHistInstanceId }
    ::= { cfprSwSystemStatsHistTable 1 }

CfprSwSystemStatsHistEntry ::= SEQUENCE {
    cfprSwSystemStatsHistInstanceId                                  CfprManagedObjectId,
    cfprSwSystemStatsHistDn                                          CfprManagedObjectDn,
    cfprSwSystemStatsHistRn                                          SnmpAdminString,
    cfprSwSystemStatsHistId                                          Unsigned64,
    cfprSwSystemStatsHistLoad                                        INTEGER,
    cfprSwSystemStatsHistLoadAvg                                     INTEGER,
    cfprSwSystemStatsHistLoadMax                                     INTEGER,
    cfprSwSystemStatsHistLoadMin                                     INTEGER,
    cfprSwSystemStatsHistMemAvailable                                Gauge32,
    cfprSwSystemStatsHistMemAvailableAvg                             Gauge32,
    cfprSwSystemStatsHistMemAvailableMax                             Gauge32,
    cfprSwSystemStatsHistMemAvailableMin                             Gauge32,
    cfprSwSystemStatsHistMemCached                                   Gauge32,
    cfprSwSystemStatsHistMemCachedAvg                                Gauge32,
    cfprSwSystemStatsHistMemCachedMax                                Gauge32,
    cfprSwSystemStatsHistMemCachedMin                                Gauge32,
    cfprSwSystemStatsHistMostRecent                                  TruthValue,
    cfprSwSystemStatsHistSuspect                                     TruthValue,
    cfprSwSystemStatsHistThresholded                                 CfprSwSystemStatsHistThresholded,
    cfprSwSystemStatsHistTimeCollected                               DateAndTime
}

cfprSwSystemStatsHistInstanceId OBJECT-TYPE
    SYNTAX       CfprManagedObjectId
    MAX-ACCESS   not-accessible
    STATUS       current
    DESCRIPTION
        "Instance identifier of the managed object."
    ::= { cfprSwSystemStatsHistEntry 1 }

cfprSwSystemStatsHistDn OBJECT-TYPE
    SYNTAX       CfprManagedObjectDn
    MAX-ACCESS   read-only
    STATUS       current
    DESCRIPTION
        "Cisco Firepower sw:SystemStatsHist:dn managed object property"
    ::= { cfprSwSystemStatsHistEntry 2 }

cfprSwSystemStatsHistRn OBJECT-TYPE
    SYNTAX       SnmpAdminString
    MAX-ACCESS   read-only
    STATUS       current
    DESCRIPTION
        "Cisco Firepower sw:SystemStatsHist:rn managed object property"
    ::= { cfprSwSystemStatsHistEntry 3 }

cfprSwSystemStatsHistId OBJECT-TYPE
    SYNTAX       Unsigned64
    MAX-ACCESS   read-only
    STATUS       current
    DESCRIPTION
        "Cisco Firepower sw:SystemStatsHist:id managed object property"
    ::= { cfprSwSystemStatsHistEntry 4 }

cfprSwSystemStatsHistLoad OBJECT-TYPE
    SYNTAX       INTEGER
    MAX-ACCESS   read-only
    STATUS       current
    DESCRIPTION
        "Cisco Firepower sw:SystemStatsHist:load managed object property"
    ::= { cfprSwSystemStatsHistEntry 5 }

cfprSwSystemStatsHistLoadAvg OBJECT-TYPE
    SYNTAX       INTEGER
    MAX-ACCESS   read-only
    STATUS       current
    DESCRIPTION
        "Cisco Firepower sw:SystemStatsHist:loadAvg managed
        object property"
    ::= { cfprSwSystemStatsHistEntry 6 }

cfprSwSystemStatsHistLoadMax OBJECT-TYPE
    SYNTAX       INTEGER
    MAX-ACCESS   read-only
    STATUS       current
    DESCRIPTION
        "Cisco Firepower sw:SystemStatsHist:loadMax managed
        object property"
    ::= { cfprSwSystemStatsHistEntry 7 }

cfprSwSystemStatsHistLoadMin OBJECT-TYPE
    SYNTAX       INTEGER
    MAX-ACCESS   read-only
    STATUS       current
    DESCRIPTION
        "Cisco Firepower sw:SystemStatsHist:loadMin managed
        object property"
    ::= { cfprSwSystemStatsHistEntry 8 }

cfprSwSystemStatsHistMemAvailable OBJECT-TYPE
    SYNTAX       Gauge32
    MAX-ACCESS   read-only
    STATUS       current
    DESCRIPTION
        "Cisco Firepower sw:SystemStatsHist:memAvailable
        managed object property"
    ::= { cfprSwSystemStatsHistEntry 9 }

cfprSwSystemStatsHistMemAvailableAvg OBJECT-TYPE
    SYNTAX       Gauge32
    MAX-ACCESS   read-only
    STATUS       current
    DESCRIPTION
        "Cisco Firepower sw:SystemStatsHist:memAvailableAvg
        managed object property"
    ::= { cfprSwSystemStatsHistEntry 10 }

cfprSwSystemStatsHistMemAvailableMax OBJECT-TYPE
    SYNTAX       Gauge32
    MAX-ACCESS   read-only
    STATUS       current
    DESCRIPTION
        "Cisco Firepower sw:SystemStatsHist:memAvailableMax
        managed object property"
    ::= { cfprSwSystemStatsHistEntry 11 }

cfprSwSystemStatsHistMemAvailableMin OBJECT-TYPE
    SYNTAX       Gauge32
    MAX-ACCESS   read-only
    STATUS       current
    DESCRIPTION
        "Cisco Firepower sw:SystemStatsHist:memAvailableMin
        managed object property"
    ::= { cfprSwSystemStatsHistEntry 12 }

cfprSwSystemStatsHistMemCached OBJECT-TYPE
    SYNTAX       Gauge32
    MAX-ACCESS   read-only
    STATUS       current
    DESCRIPTION
        "Cisco Firepower sw:SystemStatsHist:memCached managed
        object property"
    ::= { cfprSwSystemStatsHistEntry 13 }

cfprSwSystemStatsHistMemCachedAvg OBJECT-TYPE
    SYNTAX       Gauge32
    MAX-ACCESS   read-only
    STATUS       current
    DESCRIPTION
        "Cisco Firepower sw:SystemStatsHist:memCachedAvg
        managed object property"
    ::= { cfprSwSystemStatsHistEntry 14 }

cfprSwSystemStatsHistMemCachedMax OBJECT-TYPE
    SYNTAX       Gauge32
    MAX-ACCESS   read-only
    STATUS       current
    DESCRIPTION
        "Cisco Firepower sw:SystemStatsHist:memCachedMax
        managed object property"
    ::= { cfprSwSystemStatsHistEntry 15 }

cfprSwSystemStatsHistMemCachedMin OBJECT-TYPE
    SYNTAX       Gauge32
    MAX-ACCESS   read-only
    STATUS       current
    DESCRIPTION
        "Cisco Firepower sw:SystemStatsHist:memCachedMin
        managed object property"
    ::= { cfprSwSystemStatsHistEntry 16 }

cfprSwSystemStatsHistMostRecent OBJECT-TYPE
    SYNTAX       TruthValue
    MAX-ACCESS   read-only
    STATUS       current
    DESCRIPTION
        "Cisco Firepower sw:SystemStatsHist:mostRecent
        managed object property"
    ::= { cfprSwSystemStatsHistEntry 17 }

cfprSwSystemStatsHistSuspect OBJECT-TYPE
    SYNTAX       TruthValue
    MAX-ACCESS   read-only
    STATUS       current
    DESCRIPTION
        "Cisco Firepower sw:SystemStatsHist:suspect managed
        object property"
    ::= { cfprSwSystemStatsHistEntry 18 }

cfprSwSystemStatsHistThresholded OBJECT-TYPE
    SYNTAX       CfprSwSystemStatsHistThresholded
    MAX-ACCESS   read-only
    STATUS       current
    DESCRIPTION
        "Cisco Firepower sw:SystemStatsHist:thresholded
        managed object property"
    ::= { cfprSwSystemStatsHistEntry 19 }

cfprSwSystemStatsHistTimeCollected OBJECT-TYPE
    SYNTAX       DateAndTime
    MAX-ACCESS   read-only
    STATUS       current
    DESCRIPTION
        "Cisco Firepower sw:SystemStatsHist:timeCollected
        managed object property"
    ::= { cfprSwSystemStatsHistEntry 20 }

cfprSwUlanTable OBJECT-TYPE
    SYNTAX           SEQUENCE OF CfprSwUlanEntry
    MAX-ACCESS       not-accessible
    STATUS           current
    DESCRIPTION
        "Cisco Firepower sw:Ulan managed object table"
    ::= { cfprSwObjects 74 }

cfprSwUlanEntry OBJECT-TYPE
    SYNTAX           CfprSwUlanEntry
    MAX-ACCESS       not-accessible
    STATUS           current
    DESCRIPTION
        "Entry for the cfprSwUlanTable table."
    INDEX { cfprSwUlanInstanceId }
    ::= { cfprSwUlanTable 1 }

CfprSwUlanEntry ::= SEQUENCE {
    cfprSwUlanInstanceId                                             CfprManagedObjectId,
    cfprSwUlanDn                                                     CfprManagedObjectDn,
    cfprSwUlanRn                                                     SnmpAdminString,
    cfprSwUlanAssocPrimaryVlanState                                  CfprFabricVlanAssocPrimaryVlanState,
    cfprSwUlanAssocPrimaryVlanSwitchId                               CfprFabricAVlanAssocPrimaryVlanSwitchId,
    cfprSwUlanEpDn                                                   SnmpAdminString,
    cfprSwUlanId                                                     Gauge32,
    cfprSwUlanIfRole                                                 CfprFabricVnetEpIfRole,
    cfprSwUlanIfType                                                 CfprNetworkVnetEpIfType,
    cfprSwUlanLocale                                                 CfprFabricVnetEpLocale,
    cfprSwUlanName                                                   SnmpAdminString,
    cfprSwUlanOperState                                              CfprFabricVlanOperState,
    cfprSwUlanOverlapStateForA                                       CfprFabricVlanOverlapState,
    cfprSwUlanOverlapStateForB                                       CfprFabricVlanOverlapState,
    cfprSwUlanPeerDn                                                 SnmpAdminString,
    cfprSwUlanPolicyOwner                                            CfprFabricVnetEpPolicyOwner,
    cfprSwUlanPubNwDn                                                SnmpAdminString,
    cfprSwUlanPubNwId                                                Gauge32,
    cfprSwUlanPubNwName                                              SnmpAdminString,
    cfprSwUlanPurpose                                                CfprSwUlanPurpose,
    cfprSwUlanSharing                                                CfprFabricAVlanSharing,
    cfprSwUlanSwitchId                                               CfprNetworkSwitchId,
    cfprSwUlanTransport                                              CfprFabricAVlanTransport,
    cfprSwUlanType                                                   CfprFabricAVlanType,
    cfprSwUlanVlanType                                               CfprFabricEpVlanVlanType
}

cfprSwUlanInstanceId OBJECT-TYPE
    SYNTAX       CfprManagedObjectId
    MAX-ACCESS   not-accessible
    STATUS       current
    DESCRIPTION
        "Instance identifier of the managed object."
    ::= { cfprSwUlanEntry 1 }

cfprSwUlanDn OBJECT-TYPE
    SYNTAX       CfprManagedObjectDn
    MAX-ACCESS   read-only
    STATUS       current
    DESCRIPTION
        "Cisco Firepower sw:Ulan:dn managed object property"
    ::= { cfprSwUlanEntry 2 }

cfprSwUlanRn OBJECT-TYPE
    SYNTAX       SnmpAdminString
    MAX-ACCESS   read-only
    STATUS       current
    DESCRIPTION
        "Cisco Firepower sw:Ulan:rn managed object property"
    ::= { cfprSwUlanEntry 3 }

cfprSwUlanAssocPrimaryVlanState OBJECT-TYPE
    SYNTAX       CfprFabricVlanAssocPrimaryVlanState
    MAX-ACCESS   read-only
    STATUS       current
    DESCRIPTION
        "Cisco Firepower sw:Ulan:assocPrimaryVlanState
        managed object property"
    ::= { cfprSwUlanEntry 4 }

cfprSwUlanAssocPrimaryVlanSwitchId OBJECT-TYPE
    SYNTAX       CfprFabricAVlanAssocPrimaryVlanSwitchId
    MAX-ACCESS   read-only
    STATUS       current
    DESCRIPTION
        "Cisco Firepower sw:Ulan:assocPrimaryVlanSwitchId
        managed object property"
    ::= { cfprSwUlanEntry 5 }

cfprSwUlanEpDn OBJECT-TYPE
    SYNTAX       SnmpAdminString
    MAX-ACCESS   read-only
    STATUS       current
    DESCRIPTION
        "Cisco Firepower sw:Ulan:epDn managed object property"
    ::= { cfprSwUlanEntry 6 }

cfprSwUlanId OBJECT-TYPE
    SYNTAX       Gauge32
    MAX-ACCESS   read-only
    STATUS       current
    DESCRIPTION
        "Cisco Firepower sw:Ulan:id managed object property"
    ::= { cfprSwUlanEntry 7 }

cfprSwUlanIfRole OBJECT-TYPE
    SYNTAX       CfprFabricVnetEpIfRole
    MAX-ACCESS   read-only
    STATUS       current
    DESCRIPTION
        "Cisco Firepower sw:Ulan:ifRole managed object property"
    ::= { cfprSwUlanEntry 8 }

cfprSwUlanIfType OBJECT-TYPE
    SYNTAX       CfprNetworkVnetEpIfType
    MAX-ACCESS   read-only
    STATUS       current
    DESCRIPTION
        "Cisco Firepower sw:Ulan:ifType managed object property"
    ::= { cfprSwUlanEntry 9 }

cfprSwUlanLocale OBJECT-TYPE
    SYNTAX       CfprFabricVnetEpLocale
    MAX-ACCESS   read-only
    STATUS       current
    DESCRIPTION
        "Cisco Firepower sw:Ulan:locale managed object property"
    ::= { cfprSwUlanEntry 10 }

cfprSwUlanName OBJECT-TYPE
    SYNTAX       SnmpAdminString
    MAX-ACCESS   read-only
    STATUS       current
    DESCRIPTION
        "Cisco Firepower sw:Ulan:name managed object property"
    ::= { cfprSwUlanEntry 11 }

cfprSwUlanOperState OBJECT-TYPE
    SYNTAX       CfprFabricVlanOperState
    MAX-ACCESS   read-only
    STATUS       current
    DESCRIPTION
        "Cisco Firepower sw:Ulan:operState managed object property"
    ::= { cfprSwUlanEntry 12 }

cfprSwUlanOverlapStateForA OBJECT-TYPE
    SYNTAX       CfprFabricVlanOverlapState
    MAX-ACCESS   read-only
    STATUS       current
    DESCRIPTION
        "Cisco Firepower sw:Ulan:overlapStateForA managed object property"
    ::= { cfprSwUlanEntry 13 }

cfprSwUlanOverlapStateForB OBJECT-TYPE
    SYNTAX       CfprFabricVlanOverlapState
    MAX-ACCESS   read-only
    STATUS       current
    DESCRIPTION
        "Cisco Firepower sw:Ulan:overlapStateForB managed object property"
    ::= { cfprSwUlanEntry 14 }

cfprSwUlanPeerDn OBJECT-TYPE
    SYNTAX       SnmpAdminString
    MAX-ACCESS   read-only
    STATUS       current
    DESCRIPTION
        "Cisco Firepower sw:Ulan:peerDn managed object property"
    ::= { cfprSwUlanEntry 15 }

cfprSwUlanPolicyOwner OBJECT-TYPE
    SYNTAX       CfprFabricVnetEpPolicyOwner
    MAX-ACCESS   read-only
    STATUS       current
    DESCRIPTION
        "Cisco Firepower sw:Ulan:policyOwner managed object property"
    ::= { cfprSwUlanEntry 16 }

cfprSwUlanPubNwDn OBJECT-TYPE
    SYNTAX       SnmpAdminString
    MAX-ACCESS   read-only
    STATUS       current
    DESCRIPTION
        "Cisco Firepower sw:Ulan:pubNwDn managed object property"
    ::= { cfprSwUlanEntry 17 }

cfprSwUlanPubNwId OBJECT-TYPE
    SYNTAX       Gauge32
    MAX-ACCESS   read-only
    STATUS       current
    DESCRIPTION
        "Cisco Firepower sw:Ulan:pubNwId managed object property"
    ::= { cfprSwUlanEntry 18 }

cfprSwUlanPubNwName OBJECT-TYPE
    SYNTAX       SnmpAdminString
    MAX-ACCESS   read-only
    STATUS       current
    DESCRIPTION
        "Cisco Firepower sw:Ulan:pubNwName managed object property"
    ::= { cfprSwUlanEntry 19 }

cfprSwUlanPurpose OBJECT-TYPE
    SYNTAX       CfprSwUlanPurpose
    MAX-ACCESS   read-only
    STATUS       current
    DESCRIPTION
        "Cisco Firepower sw:Ulan:purpose managed object property"
    ::= { cfprSwUlanEntry 20 }

cfprSwUlanSharing OBJECT-TYPE
    SYNTAX       CfprFabricAVlanSharing
    MAX-ACCESS   read-only
    STATUS       current
    DESCRIPTION
        "Cisco Firepower sw:Ulan:sharing managed object property"
    ::= { cfprSwUlanEntry 21 }

cfprSwUlanSwitchId OBJECT-TYPE
    SYNTAX       CfprNetworkSwitchId
    MAX-ACCESS   read-only
    STATUS       current
    DESCRIPTION
        "Cisco Firepower sw:Ulan:switchId managed object property"
    ::= { cfprSwUlanEntry 22 }

cfprSwUlanTransport OBJECT-TYPE
    SYNTAX       CfprFabricAVlanTransport
    MAX-ACCESS   read-only
    STATUS       current
    DESCRIPTION
        "Cisco Firepower sw:Ulan:transport managed object property"
    ::= { cfprSwUlanEntry 23 }

cfprSwUlanType OBJECT-TYPE
    SYNTAX       CfprFabricAVlanType
    MAX-ACCESS   read-only
    STATUS       current
    DESCRIPTION
        "Cisco Firepower sw:Ulan:type managed object property"
    ::= { cfprSwUlanEntry 24 }

cfprSwUlanVlanType OBJECT-TYPE
    SYNTAX       CfprFabricEpVlanVlanType
    MAX-ACCESS   read-only
    STATUS       current
    DESCRIPTION
        "Cisco Firepower sw:Ulan:vlanType managed object property"
    ::= { cfprSwUlanEntry 25 }

cfprSwUtilityDomainTable OBJECT-TYPE
    SYNTAX           SEQUENCE OF CfprSwUtilityDomainEntry
    MAX-ACCESS       not-accessible
    STATUS           current
    DESCRIPTION
        "Cisco Firepower sw:UtilityDomain managed object table"
    ::= { cfprSwObjects 75 }

cfprSwUtilityDomainEntry OBJECT-TYPE
    SYNTAX           CfprSwUtilityDomainEntry
    MAX-ACCESS       not-accessible
    STATUS           current
    DESCRIPTION
        "Entry for the cfprSwUtilityDomainTable table."
    INDEX { cfprSwUtilityDomainInstanceId }
    ::= { cfprSwUtilityDomainTable 1 }

CfprSwUtilityDomainEntry ::= SEQUENCE {
    cfprSwUtilityDomainInstanceId                                    CfprManagedObjectId,
    cfprSwUtilityDomainDn                                            CfprManagedObjectDn,
    cfprSwUtilityDomainRn                                            SnmpAdminString,
    cfprSwUtilityDomainFsmDescr                                      SnmpAdminString,
    cfprSwUtilityDomainFsmPrev                                       SnmpAdminString,
    cfprSwUtilityDomainFsmProgr                                      Gauge32,
    cfprSwUtilityDomainFsmRmtInvErrCode                              Gauge32,
    cfprSwUtilityDomainFsmRmtInvErrDescr                             SnmpAdminString,
    cfprSwUtilityDomainFsmRmtInvRslt                                 CfprConditionRemoteInvRslt,
    cfprSwUtilityDomainFsmStageDescr                                 SnmpAdminString,
    cfprSwUtilityDomainFsmStamp                                      DateAndTime,
    cfprSwUtilityDomainFsmStatus                                     SnmpAdminString,
    cfprSwUtilityDomainFsmTry                                        Gauge32,
    cfprSwUtilityDomainLocale                                        CfprSwUtilityDomainLocale,
    cfprSwUtilityDomainName                                          SnmpAdminString,
    cfprSwUtilityDomainSwitchId                                      CfprNetworkSwitchId,
    cfprSwUtilityDomainTransport                                     CfprNetworkTransport,
    cfprSwUtilityDomainType                                          CfprSwUtilityDomainType
}

cfprSwUtilityDomainInstanceId OBJECT-TYPE
    SYNTAX       CfprManagedObjectId
    MAX-ACCESS   not-accessible
    STATUS       current
    DESCRIPTION
        "Instance identifier of the managed object."
    ::= { cfprSwUtilityDomainEntry 1 }

cfprSwUtilityDomainDn OBJECT-TYPE
    SYNTAX       CfprManagedObjectDn
    MAX-ACCESS   read-only
    STATUS       current
    DESCRIPTION
        "Cisco Firepower sw:UtilityDomain:dn managed object property"
    ::= { cfprSwUtilityDomainEntry 2 }

cfprSwUtilityDomainRn OBJECT-TYPE
    SYNTAX       SnmpAdminString
    MAX-ACCESS   read-only
    STATUS       current
    DESCRIPTION
        "Cisco Firepower sw:UtilityDomain:rn managed object property"
    ::= { cfprSwUtilityDomainEntry 3 }

cfprSwUtilityDomainFsmDescr OBJECT-TYPE
    SYNTAX       SnmpAdminString
    MAX-ACCESS   read-only
    STATUS       current
    DESCRIPTION
        "Cisco Firepower sw:UtilityDomain:fsmDescr managed
        object property"
    ::= { cfprSwUtilityDomainEntry 4 }

cfprSwUtilityDomainFsmPrev OBJECT-TYPE
    SYNTAX       SnmpAdminString
    MAX-ACCESS   read-only
    STATUS       current
    DESCRIPTION
        "Cisco Firepower sw:UtilityDomain:fsmPrev managed object property"
    ::= { cfprSwUtilityDomainEntry 5 }

cfprSwUtilityDomainFsmProgr OBJECT-TYPE
    SYNTAX       Gauge32
    MAX-ACCESS   read-only
    STATUS       current
    DESCRIPTION
        "Cisco Firepower sw:UtilityDomain:fsmProgr managed
        object property"
    ::= { cfprSwUtilityDomainEntry 6 }

cfprSwUtilityDomainFsmRmtInvErrCode OBJECT-TYPE
    SYNTAX       Gauge32
    MAX-ACCESS   read-only
    STATUS       current
    DESCRIPTION
        "Cisco Firepower sw:UtilityDomain:fsmRmtInvErrCode
        managed object property"
    ::= { cfprSwUtilityDomainEntry 7 }

cfprSwUtilityDomainFsmRmtInvErrDescr OBJECT-TYPE
    SYNTAX       SnmpAdminString
    MAX-ACCESS   read-only
    STATUS       current
    DESCRIPTION
        "Cisco Firepower sw:UtilityDomain:fsmRmtInvErrDescr
        managed object property"
    ::= { cfprSwUtilityDomainEntry 8 }

cfprSwUtilityDomainFsmRmtInvRslt OBJECT-TYPE
    SYNTAX       CfprConditionRemoteInvRslt
    MAX-ACCESS   read-only
    STATUS       current
    DESCRIPTION
        "Cisco Firepower sw:UtilityDomain:fsmRmtInvRslt
        managed object property"
    ::= { cfprSwUtilityDomainEntry 9 }

cfprSwUtilityDomainFsmStageDescr OBJECT-TYPE
    SYNTAX       SnmpAdminString
    MAX-ACCESS   read-only
    STATUS       current
    DESCRIPTION
        "Cisco Firepower sw:UtilityDomain:fsmStageDescr
        managed object property"
    ::= { cfprSwUtilityDomainEntry 10 }

cfprSwUtilityDomainFsmStamp OBJECT-TYPE
    SYNTAX       DateAndTime
    MAX-ACCESS   read-only
    STATUS       current
    DESCRIPTION
        "Cisco Firepower sw:UtilityDomain:fsmStamp managed
        object property"
    ::= { cfprSwUtilityDomainEntry 11 }

cfprSwUtilityDomainFsmStatus OBJECT-TYPE
    SYNTAX       SnmpAdminString
    MAX-ACCESS   read-only
    STATUS       current
    DESCRIPTION
        "Cisco Firepower sw:UtilityDomain:fsmStatus managed
        object property"
    ::= { cfprSwUtilityDomainEntry 12 }

cfprSwUtilityDomainFsmTry OBJECT-TYPE
    SYNTAX       Gauge32
    MAX-ACCESS   read-only
    STATUS       current
    DESCRIPTION
        "Cisco Firepower sw:UtilityDomain:fsmTry managed object property"
    ::= { cfprSwUtilityDomainEntry 13 }

cfprSwUtilityDomainLocale OBJECT-TYPE
    SYNTAX       CfprSwUtilityDomainLocale
    MAX-ACCESS   read-only
    STATUS       current
    DESCRIPTION
        "Cisco Firepower sw:UtilityDomain:locale managed object property"
    ::= { cfprSwUtilityDomainEntry 14 }

cfprSwUtilityDomainName OBJECT-TYPE
    SYNTAX       SnmpAdminString
    MAX-ACCESS   read-only
    STATUS       current
    DESCRIPTION
        "Cisco Firepower sw:UtilityDomain:name managed object property"
    ::= { cfprSwUtilityDomainEntry 15 }

cfprSwUtilityDomainSwitchId OBJECT-TYPE
    SYNTAX       CfprNetworkSwitchId
    MAX-ACCESS   read-only
    STATUS       current
    DESCRIPTION
        "Cisco Firepower sw:UtilityDomain:switchId managed
        object property"
    ::= { cfprSwUtilityDomainEntry 16 }

cfprSwUtilityDomainTransport OBJECT-TYPE
    SYNTAX       CfprNetworkTransport
    MAX-ACCESS   read-only
    STATUS       current
    DESCRIPTION
        "Cisco Firepower sw:UtilityDomain:transport managed
        object property"
    ::= { cfprSwUtilityDomainEntry 17 }

cfprSwUtilityDomainType OBJECT-TYPE
    SYNTAX       CfprSwUtilityDomainType
    MAX-ACCESS   read-only
    STATUS       current
    DESCRIPTION
        "Cisco Firepower sw:UtilityDomain:type managed object property"
    ::= { cfprSwUtilityDomainEntry 18 }

cfprSwUtilityDomainFsmTable OBJECT-TYPE
    SYNTAX           SEQUENCE OF CfprSwUtilityDomainFsmEntry
    MAX-ACCESS       not-accessible
    STATUS           current
    DESCRIPTION
        "Cisco Firepower sw:UtilityDomainFsm managed object table"
    ::= { cfprSwObjects 76 }

cfprSwUtilityDomainFsmEntry OBJECT-TYPE
    SYNTAX           CfprSwUtilityDomainFsmEntry
    MAX-ACCESS       not-accessible
    STATUS           current
    DESCRIPTION
        "Entry for the cfprSwUtilityDomainFsmTable table."
    INDEX { cfprSwUtilityDomainFsmInstanceId }
    ::= { cfprSwUtilityDomainFsmTable 1 }

CfprSwUtilityDomainFsmEntry ::= SEQUENCE {
    cfprSwUtilityDomainFsmInstanceId                                 CfprManagedObjectId,
    cfprSwUtilityDomainFsmDn                                         CfprManagedObjectDn,
    cfprSwUtilityDomainFsmRn                                         SnmpAdminString,
    cfprSwUtilityDomainFsmCompletionTime                             DateAndTime,
    cfprSwUtilityDomainFsmCurrentFsm                                 CfprSwUtilityDomainFsmCurrentFsm,
    cfprSwUtilityDomainFsmDescrData                                  SnmpAdminString,
    cfprSwUtilityDomainFsmFsmStatus                                  CfprFsmFsmStageStatus,
    cfprSwUtilityDomainFsmProgress                                   Gauge32,
    cfprSwUtilityDomainFsmRmtErrCode                                 Gauge32,
    cfprSwUtilityDomainFsmRmtErrDescr                                SnmpAdminString,
    cfprSwUtilityDomainFsmRmtRslt                                    CfprConditionRemoteInvRslt
}

cfprSwUtilityDomainFsmInstanceId OBJECT-TYPE
    SYNTAX       CfprManagedObjectId
    MAX-ACCESS   not-accessible
    STATUS       current
    DESCRIPTION
        "Instance identifier of the managed object."
    ::= { cfprSwUtilityDomainFsmEntry 1 }

cfprSwUtilityDomainFsmDn OBJECT-TYPE
    SYNTAX       CfprManagedObjectDn
    MAX-ACCESS   read-only
    STATUS       current
    DESCRIPTION
        "Cisco Firepower sw:UtilityDomainFsm:dn managed object property"
    ::= { cfprSwUtilityDomainFsmEntry 2 }

cfprSwUtilityDomainFsmRn OBJECT-TYPE
    SYNTAX       SnmpAdminString
    MAX-ACCESS   read-only
    STATUS       current
    DESCRIPTION
        "Cisco Firepower sw:UtilityDomainFsm:rn managed object property"
    ::= { cfprSwUtilityDomainFsmEntry 3 }

cfprSwUtilityDomainFsmCompletionTime OBJECT-TYPE
    SYNTAX       DateAndTime
    MAX-ACCESS   read-only
    STATUS       current
    DESCRIPTION
        "Cisco Firepower sw:UtilityDomainFsm:completionTime
        managed object property"
    ::= { cfprSwUtilityDomainFsmEntry 4 }

cfprSwUtilityDomainFsmCurrentFsm OBJECT-TYPE
    SYNTAX       CfprSwUtilityDomainFsmCurrentFsm
    MAX-ACCESS   read-only
    STATUS       current
    DESCRIPTION
        "Cisco Firepower sw:UtilityDomainFsm:currentFsm
        managed object property"
    ::= { cfprSwUtilityDomainFsmEntry 5 }

cfprSwUtilityDomainFsmDescrData OBJECT-TYPE
    SYNTAX       SnmpAdminString
    MAX-ACCESS   read-only
    STATUS       current
    DESCRIPTION
        "Cisco Firepower sw:UtilityDomainFsm:descr managed
        object property"
    ::= { cfprSwUtilityDomainFsmEntry 6 }

cfprSwUtilityDomainFsmFsmStatus OBJECT-TYPE
    SYNTAX       CfprFsmFsmStageStatus
    MAX-ACCESS   read-only
    STATUS       current
    DESCRIPTION
        "Cisco Firepower sw:UtilityDomainFsm:fsmStatus
        managed object property"
    ::= { cfprSwUtilityDomainFsmEntry 7 }

cfprSwUtilityDomainFsmProgress OBJECT-TYPE
    SYNTAX       Gauge32
    MAX-ACCESS   read-only
    STATUS       current
    DESCRIPTION
        "Cisco Firepower sw:UtilityDomainFsm:progress managed
        object property"
    ::= { cfprSwUtilityDomainFsmEntry 8 }

cfprSwUtilityDomainFsmRmtErrCode OBJECT-TYPE
    SYNTAX       Gauge32
    MAX-ACCESS   read-only
    STATUS       current
    DESCRIPTION
        "Cisco Firepower sw:UtilityDomainFsm:rmtErrCode
        managed object property"
    ::= { cfprSwUtilityDomainFsmEntry 9 }

cfprSwUtilityDomainFsmRmtErrDescr OBJECT-TYPE
    SYNTAX       SnmpAdminString
    MAX-ACCESS   read-only
    STATUS       current
    DESCRIPTION
        "Cisco Firepower sw:UtilityDomainFsm:rmtErrDescr
        managed object property"
    ::= { cfprSwUtilityDomainFsmEntry 10 }

cfprSwUtilityDomainFsmRmtRslt OBJECT-TYPE
    SYNTAX       CfprConditionRemoteInvRslt
    MAX-ACCESS   read-only
    STATUS       current
    DESCRIPTION
        "Cisco Firepower sw:UtilityDomainFsm:rmtRslt managed
        object property"
    ::= { cfprSwUtilityDomainFsmEntry 11 }

cfprSwUtilityDomainFsmStageTable OBJECT-TYPE
    SYNTAX           SEQUENCE OF CfprSwUtilityDomainFsmStageEntry
    MAX-ACCESS       not-accessible
    STATUS           current
    DESCRIPTION
        "Cisco Firepower sw:UtilityDomainFsmStage managed object table"
    ::= { cfprSwObjects 77 }

cfprSwUtilityDomainFsmStageEntry OBJECT-TYPE
    SYNTAX           CfprSwUtilityDomainFsmStageEntry
    MAX-ACCESS       not-accessible
    STATUS           current
    DESCRIPTION
        "Entry for the cfprSwUtilityDomainFsmStageTable table."
    INDEX { cfprSwUtilityDomainFsmStageInstanceId }
    ::= { cfprSwUtilityDomainFsmStageTable 1 }

CfprSwUtilityDomainFsmStageEntry ::= SEQUENCE {
    cfprSwUtilityDomainFsmStageInstanceId                            CfprManagedObjectId,
    cfprSwUtilityDomainFsmStageDn                                    CfprManagedObjectDn,
    cfprSwUtilityDomainFsmStageRn                                    SnmpAdminString,
    cfprSwUtilityDomainFsmStageDescrData                             SnmpAdminString,
    cfprSwUtilityDomainFsmStageLastUpdateTime                        DateAndTime,
    cfprSwUtilityDomainFsmStageName                                  CfprSwUtilityDomainFsmStageName,
    cfprSwUtilityDomainFsmStageOrder                                 Gauge32,
    cfprSwUtilityDomainFsmStageRetry                                 Gauge32,
    cfprSwUtilityDomainFsmStageStageStatus                           CfprFsmFsmStageStatus
}

cfprSwUtilityDomainFsmStageInstanceId OBJECT-TYPE
    SYNTAX       CfprManagedObjectId
    MAX-ACCESS   not-accessible
    STATUS       current
    DESCRIPTION
        "Instance identifier of the managed object."
    ::= { cfprSwUtilityDomainFsmStageEntry 1 }

cfprSwUtilityDomainFsmStageDn OBJECT-TYPE
    SYNTAX       CfprManagedObjectDn
    MAX-ACCESS   read-only
    STATUS       current
    DESCRIPTION
        "Cisco Firepower sw:UtilityDomainFsmStage:dn managed
        object property"
    ::= { cfprSwUtilityDomainFsmStageEntry 2 }

cfprSwUtilityDomainFsmStageRn OBJECT-TYPE
    SYNTAX       SnmpAdminString
    MAX-ACCESS   read-only
    STATUS       current
    DESCRIPTION
        "Cisco Firepower sw:UtilityDomainFsmStage:rn managed
        object property"
    ::= { cfprSwUtilityDomainFsmStageEntry 3 }

cfprSwUtilityDomainFsmStageDescrData OBJECT-TYPE
    SYNTAX       SnmpAdminString
    MAX-ACCESS   read-only
    STATUS       current
    DESCRIPTION
        "Cisco Firepower sw:UtilityDomainFsmStage:descr
        managed object property"
    ::= { cfprSwUtilityDomainFsmStageEntry 4 }

cfprSwUtilityDomainFsmStageLastUpdateTime OBJECT-TYPE
    SYNTAX       DateAndTime
    MAX-ACCESS   read-only
    STATUS       current
    DESCRIPTION
        "Cisco Firepower sw:UtilityDomainFsmStage:lastUpdateTime
        managed object property"
    ::= { cfprSwUtilityDomainFsmStageEntry 5 }

cfprSwUtilityDomainFsmStageName OBJECT-TYPE
    SYNTAX       CfprSwUtilityDomainFsmStageName
    MAX-ACCESS   read-only
    STATUS       current
    DESCRIPTION
        "Cisco Firepower sw:UtilityDomainFsmStage:name
        managed object property"
    ::= { cfprSwUtilityDomainFsmStageEntry 6 }

cfprSwUtilityDomainFsmStageOrder OBJECT-TYPE
    SYNTAX       Gauge32
    MAX-ACCESS   read-only
    STATUS       current
    DESCRIPTION
        "Cisco Firepower sw:UtilityDomainFsmStage:order
        managed object property"
    ::= { cfprSwUtilityDomainFsmStageEntry 7 }

cfprSwUtilityDomainFsmStageRetry OBJECT-TYPE
    SYNTAX       Gauge32
    MAX-ACCESS   read-only
    STATUS       current
    DESCRIPTION
        "Cisco Firepower sw:UtilityDomainFsmStage:retry
        managed object property"
    ::= { cfprSwUtilityDomainFsmStageEntry 8 }

cfprSwUtilityDomainFsmStageStageStatus OBJECT-TYPE
    SYNTAX       CfprFsmFsmStageStatus
    MAX-ACCESS   read-only
    STATUS       current
    DESCRIPTION
        "Cisco Firepower sw:UtilityDomainFsmStage:stageStatus
        managed object property"
    ::= { cfprSwUtilityDomainFsmStageEntry 9 }

cfprSwUtilityDomainFsmTaskTable OBJECT-TYPE
    SYNTAX           SEQUENCE OF CfprSwUtilityDomainFsmTaskEntry
    MAX-ACCESS       not-accessible
    STATUS           current
    DESCRIPTION
        "Cisco Firepower sw:UtilityDomainFsmTask managed object table"
    ::= { cfprSwObjects 78 }

cfprSwUtilityDomainFsmTaskEntry OBJECT-TYPE
    SYNTAX           CfprSwUtilityDomainFsmTaskEntry
    MAX-ACCESS       not-accessible
    STATUS           current
    DESCRIPTION
        "Entry for the cfprSwUtilityDomainFsmTaskTable table."
    INDEX { cfprSwUtilityDomainFsmTaskInstanceId }
    ::= { cfprSwUtilityDomainFsmTaskTable 1 }

CfprSwUtilityDomainFsmTaskEntry ::= SEQUENCE {
    cfprSwUtilityDomainFsmTaskInstanceId                             CfprManagedObjectId,
    cfprSwUtilityDomainFsmTaskDn                                     CfprManagedObjectDn,
    cfprSwUtilityDomainFsmTaskRn                                     SnmpAdminString,
    cfprSwUtilityDomainFsmTaskCompletion                             CfprFsmCompletion,
    cfprSwUtilityDomainFsmTaskFlags                                  CfprFsmFlags,
    cfprSwUtilityDomainFsmTaskItem                                   CfprSwUtilityDomainFsmTaskItem,
    cfprSwUtilityDomainFsmTaskSeqId                                  Gauge32
}

cfprSwUtilityDomainFsmTaskInstanceId OBJECT-TYPE
    SYNTAX       CfprManagedObjectId
    MAX-ACCESS   not-accessible
    STATUS       current
    DESCRIPTION
        "Instance identifier of the managed object."
    ::= { cfprSwUtilityDomainFsmTaskEntry 1 }

cfprSwUtilityDomainFsmTaskDn OBJECT-TYPE
    SYNTAX       CfprManagedObjectDn
    MAX-ACCESS   read-only
    STATUS       current
    DESCRIPTION
        "Cisco Firepower sw:UtilityDomainFsmTask:dn managed
        object property"
    ::= { cfprSwUtilityDomainFsmTaskEntry 2 }

cfprSwUtilityDomainFsmTaskRn OBJECT-TYPE
    SYNTAX       SnmpAdminString
    MAX-ACCESS   read-only
    STATUS       current
    DESCRIPTION
        "Cisco Firepower sw:UtilityDomainFsmTask:rn managed
        object property"
    ::= { cfprSwUtilityDomainFsmTaskEntry 3 }

cfprSwUtilityDomainFsmTaskCompletion OBJECT-TYPE
    SYNTAX       CfprFsmCompletion
    MAX-ACCESS   read-only
    STATUS       current
    DESCRIPTION
        "Cisco Firepower sw:UtilityDomainFsmTask:completion
        managed object property"
    ::= { cfprSwUtilityDomainFsmTaskEntry 4 }

cfprSwUtilityDomainFsmTaskFlags OBJECT-TYPE
    SYNTAX       CfprFsmFlags
    MAX-ACCESS   read-only
    STATUS       current
    DESCRIPTION
        "Cisco Firepower sw:UtilityDomainFsmTask:flags
        managed object property"
    ::= { cfprSwUtilityDomainFsmTaskEntry 5 }

cfprSwUtilityDomainFsmTaskItem OBJECT-TYPE
    SYNTAX       CfprSwUtilityDomainFsmTaskItem
    MAX-ACCESS   read-only
    STATUS       current
    DESCRIPTION
        "Cisco Firepower sw:UtilityDomainFsmTask:item managed
        object property"
    ::= { cfprSwUtilityDomainFsmTaskEntry 6 }

cfprSwUtilityDomainFsmTaskSeqId OBJECT-TYPE
    SYNTAX       Gauge32
    MAX-ACCESS   read-only
    STATUS       current
    DESCRIPTION
        "Cisco Firepower sw:UtilityDomainFsmTask:seqId
        managed object property"
    ::= { cfprSwUtilityDomainFsmTaskEntry 7 }

cfprSwVirtL3IntfTable OBJECT-TYPE
    SYNTAX           SEQUENCE OF CfprSwVirtL3IntfEntry
    MAX-ACCESS       not-accessible
    STATUS           current
    DESCRIPTION
        "Cisco Firepower sw:VirtL3Intf managed object table"
    ::= { cfprSwObjects 79 }

cfprSwVirtL3IntfEntry OBJECT-TYPE
    SYNTAX           CfprSwVirtL3IntfEntry
    MAX-ACCESS       not-accessible
    STATUS           current
    DESCRIPTION
        "Entry for the cfprSwVirtL3IntfTable table."
    INDEX { cfprSwVirtL3IntfInstanceId }
    ::= { cfprSwVirtL3IntfTable 1 }

CfprSwVirtL3IntfEntry ::= SEQUENCE {
    cfprSwVirtL3IntfInstanceId                                       CfprManagedObjectId,
    cfprSwVirtL3IntfDn                                               CfprManagedObjectDn,
    cfprSwVirtL3IntfRn                                               SnmpAdminString,
    cfprSwVirtL3IntfIpAddress                                        InetAddressIPv4,
    cfprSwVirtL3IntfName                                             SnmpAdminString,
    cfprSwVirtL3IntfNetmask                                          InetAddressIPv4,
    cfprSwVirtL3IntfVlanId                                           Gauge32
}

cfprSwVirtL3IntfInstanceId OBJECT-TYPE
    SYNTAX       CfprManagedObjectId
    MAX-ACCESS   not-accessible
    STATUS       current
    DESCRIPTION
        "Instance identifier of the managed object."
    ::= { cfprSwVirtL3IntfEntry 1 }

cfprSwVirtL3IntfDn OBJECT-TYPE
    SYNTAX       CfprManagedObjectDn
    MAX-ACCESS   read-only
    STATUS       current
    DESCRIPTION
        "Cisco Firepower sw:VirtL3Intf:dn managed object property"
    ::= { cfprSwVirtL3IntfEntry 2 }

cfprSwVirtL3IntfRn OBJECT-TYPE
    SYNTAX       SnmpAdminString
    MAX-ACCESS   read-only
    STATUS       current
    DESCRIPTION
        "Cisco Firepower sw:VirtL3Intf:rn managed object property"
    ::= { cfprSwVirtL3IntfEntry 3 }

cfprSwVirtL3IntfIpAddress OBJECT-TYPE
    SYNTAX       InetAddressIPv4
    MAX-ACCESS   read-only
    STATUS       current
    DESCRIPTION
        "Cisco Firepower sw:VirtL3Intf:ipAddress managed object property"
    ::= { cfprSwVirtL3IntfEntry 4 }

cfprSwVirtL3IntfName OBJECT-TYPE
    SYNTAX       SnmpAdminString
    MAX-ACCESS   read-only
    STATUS       current
    DESCRIPTION
        "Cisco Firepower sw:VirtL3Intf:name managed object property"
    ::= { cfprSwVirtL3IntfEntry 5 }

cfprSwVirtL3IntfNetmask OBJECT-TYPE
    SYNTAX       InetAddressIPv4
    MAX-ACCESS   read-only
    STATUS       current
    DESCRIPTION
        "Cisco Firepower sw:VirtL3Intf:netmask managed object property"
    ::= { cfprSwVirtL3IntfEntry 6 }

cfprSwVirtL3IntfVlanId OBJECT-TYPE
    SYNTAX       Gauge32
    MAX-ACCESS   read-only
    STATUS       current
    DESCRIPTION
        "Cisco Firepower sw:VirtL3Intf:vlanId managed object property"
    ::= { cfprSwVirtL3IntfEntry 7 }

cfprSwVlanTable OBJECT-TYPE
    SYNTAX           SEQUENCE OF CfprSwVlanEntry
    MAX-ACCESS       not-accessible
    STATUS           current
    DESCRIPTION
        "Cisco Firepower sw:Vlan managed object table"
    ::= { cfprSwObjects 80 }

cfprSwVlanEntry OBJECT-TYPE
    SYNTAX           CfprSwVlanEntry
    MAX-ACCESS       not-accessible
    STATUS           current
    DESCRIPTION
        "Entry for the cfprSwVlanTable table."
    INDEX { cfprSwVlanInstanceId }
    ::= { cfprSwVlanTable 1 }

CfprSwVlanEntry ::= SEQUENCE {
    cfprSwVlanInstanceId                                             CfprManagedObjectId,
    cfprSwVlanDn                                                     CfprManagedObjectDn,
    cfprSwVlanRn                                                     SnmpAdminString,
    cfprSwVlanAssocPrimaryVlanState                                  CfprFabricVlanAssocPrimaryVlanState,
    cfprSwVlanAssocPrimaryVlanSwitchId                               CfprFabricAVlanAssocPrimaryVlanSwitchId,
    cfprSwVlanCompressionType                                        CfprSwVlanCompType,
    cfprSwVlanEpDn                                                   SnmpAdminString,
    cfprSwVlanId                                                     Gauge32,
    cfprSwVlanIfRole                                                 CfprFabricVnetEpIfRole,
    cfprSwVlanIfType                                                 CfprNetworkVnetEpIfType,
    cfprSwVlanLc                                                     CfprSwVlanLc,
    cfprSwVlanLocale                                                 CfprFabricVnetEpLocale,
    cfprSwVlanMonTrafDir                                             CfprFabricTrafficDirection,
    cfprSwVlanName                                                   SnmpAdminString,
    cfprSwVlanOperState                                              CfprFabricVlanOperState,
    cfprSwVlanOverlapStateForA                                       CfprFabricVlanOverlapState,
    cfprSwVlanOverlapStateForB                                       CfprFabricVlanOverlapState,
    cfprSwVlanPeerDn                                                 SnmpAdminString,
    cfprSwVlanPolicyOwner                                            CfprFabricVnetEpPolicyOwner,
    cfprSwVlanPubNwDn                                                SnmpAdminString,
    cfprSwVlanPubNwId                                                Gauge32,
    cfprSwVlanPubNwName                                              SnmpAdminString,
    cfprSwVlanQuerierIpAddrs                                         InetAddressIPv4,
    cfprSwVlanSecVlanPerPrimaryVlanCount                             Gauge32,
    cfprSwVlanSecVlanPerPrimaryVlanCountStatus                       CfprNetworkVlanCountStatus,
    cfprSwVlanSharing                                                CfprFabricAVlanSharing,
    cfprSwVlanSnoopingEnabled                                        TruthValue,
    cfprSwVlanSwitchId                                               CfprNetworkSwitchId,
    cfprSwVlanTransport                                              CfprFabricAVlanTransport,
    cfprSwVlanType                                                   CfprFabricAVlanType,
    cfprSwVlanVlanType                                               CfprFabricEpVlanVlanType
}

cfprSwVlanInstanceId OBJECT-TYPE
    SYNTAX       CfprManagedObjectId
    MAX-ACCESS   not-accessible
    STATUS       current
    DESCRIPTION
        "Instance identifier of the managed object."
    ::= { cfprSwVlanEntry 1 }

cfprSwVlanDn OBJECT-TYPE
    SYNTAX       CfprManagedObjectDn
    MAX-ACCESS   read-only
    STATUS       current
    DESCRIPTION
        "Cisco Firepower sw:Vlan:dn managed object property"
    ::= { cfprSwVlanEntry 2 }

cfprSwVlanRn OBJECT-TYPE
    SYNTAX       SnmpAdminString
    MAX-ACCESS   read-only
    STATUS       current
    DESCRIPTION
        "Cisco Firepower sw:Vlan:rn managed object property"
    ::= { cfprSwVlanEntry 3 }

cfprSwVlanAssocPrimaryVlanState OBJECT-TYPE
    SYNTAX       CfprFabricVlanAssocPrimaryVlanState
    MAX-ACCESS   read-only
    STATUS       current
    DESCRIPTION
        "Cisco Firepower sw:Vlan:assocPrimaryVlanState
        managed object property"
    ::= { cfprSwVlanEntry 4 }

cfprSwVlanAssocPrimaryVlanSwitchId OBJECT-TYPE
    SYNTAX       CfprFabricAVlanAssocPrimaryVlanSwitchId
    MAX-ACCESS   read-only
    STATUS       current
    DESCRIPTION
        "Cisco Firepower sw:Vlan:assocPrimaryVlanSwitchId
        managed object property"
    ::= { cfprSwVlanEntry 5 }

cfprSwVlanCompressionType OBJECT-TYPE
    SYNTAX       CfprSwVlanCompType
    MAX-ACCESS   read-only
    STATUS       current
    DESCRIPTION
        "Cisco Firepower sw:Vlan:compressionType managed object property"
    ::= { cfprSwVlanEntry 6 }

cfprSwVlanEpDn OBJECT-TYPE
    SYNTAX       SnmpAdminString
    MAX-ACCESS   read-only
    STATUS       current
    DESCRIPTION
        "Cisco Firepower sw:Vlan:epDn managed object property"
    ::= { cfprSwVlanEntry 7 }

cfprSwVlanId OBJECT-TYPE
    SYNTAX       Gauge32
    MAX-ACCESS   read-only
    STATUS       current
    DESCRIPTION
        "Cisco Firepower sw:Vlan:id managed object property"
    ::= { cfprSwVlanEntry 8 }

cfprSwVlanIfRole OBJECT-TYPE
    SYNTAX       CfprFabricVnetEpIfRole
    MAX-ACCESS   read-only
    STATUS       current
    DESCRIPTION
        "Cisco Firepower sw:Vlan:ifRole managed object property"
    ::= { cfprSwVlanEntry 9 }

cfprSwVlanIfType OBJECT-TYPE
    SYNTAX       CfprNetworkVnetEpIfType
    MAX-ACCESS   read-only
    STATUS       current
    DESCRIPTION
        "Cisco Firepower sw:Vlan:ifType managed object property"
    ::= { cfprSwVlanEntry 10 }

cfprSwVlanLc OBJECT-TYPE
    SYNTAX       CfprSwVlanLc
    MAX-ACCESS   read-only
    STATUS       current
    DESCRIPTION
        "Cisco Firepower sw:Vlan:lc managed object property"
    ::= { cfprSwVlanEntry 11 }

cfprSwVlanLocale OBJECT-TYPE
    SYNTAX       CfprFabricVnetEpLocale
    MAX-ACCESS   read-only
    STATUS       current
    DESCRIPTION
        "Cisco Firepower sw:Vlan:locale managed object property"
    ::= { cfprSwVlanEntry 12 }

cfprSwVlanMonTrafDir OBJECT-TYPE
    SYNTAX       CfprFabricTrafficDirection
    MAX-ACCESS   read-only
    STATUS       current
    DESCRIPTION
        "Cisco Firepower sw:Vlan:monTrafDir managed object property"
    ::= { cfprSwVlanEntry 13 }

cfprSwVlanName OBJECT-TYPE
    SYNTAX       SnmpAdminString
    MAX-ACCESS   read-only
    STATUS       current
    DESCRIPTION
        "Cisco Firepower sw:Vlan:name managed object property"
    ::= { cfprSwVlanEntry 14 }

cfprSwVlanOperState OBJECT-TYPE
    SYNTAX       CfprFabricVlanOperState
    MAX-ACCESS   read-only
    STATUS       current
    DESCRIPTION
        "Cisco Firepower sw:Vlan:operState managed object property"
    ::= { cfprSwVlanEntry 15 }

cfprSwVlanOverlapStateForA OBJECT-TYPE
    SYNTAX       CfprFabricVlanOverlapState
    MAX-ACCESS   read-only
    STATUS       current
    DESCRIPTION
        "Cisco Firepower sw:Vlan:overlapStateForA managed object property"
    ::= { cfprSwVlanEntry 16 }

cfprSwVlanOverlapStateForB OBJECT-TYPE
    SYNTAX       CfprFabricVlanOverlapState
    MAX-ACCESS   read-only
    STATUS       current
    DESCRIPTION
        "Cisco Firepower sw:Vlan:overlapStateForB managed object property"
    ::= { cfprSwVlanEntry 17 }

cfprSwVlanPeerDn OBJECT-TYPE
    SYNTAX       SnmpAdminString
    MAX-ACCESS   read-only
    STATUS       current
    DESCRIPTION
        "Cisco Firepower sw:Vlan:peerDn managed object property"
    ::= { cfprSwVlanEntry 18 }

cfprSwVlanPolicyOwner OBJECT-TYPE
    SYNTAX       CfprFabricVnetEpPolicyOwner
    MAX-ACCESS   read-only
    STATUS       current
    DESCRIPTION
        "Cisco Firepower sw:Vlan:policyOwner managed object property"
    ::= { cfprSwVlanEntry 19 }

cfprSwVlanPubNwDn OBJECT-TYPE
    SYNTAX       SnmpAdminString
    MAX-ACCESS   read-only
    STATUS       current
    DESCRIPTION
        "Cisco Firepower sw:Vlan:pubNwDn managed object property"
    ::= { cfprSwVlanEntry 20 }

cfprSwVlanPubNwId OBJECT-TYPE
    SYNTAX       Gauge32
    MAX-ACCESS   read-only
    STATUS       current
    DESCRIPTION
        "Cisco Firepower sw:Vlan:pubNwId managed object property"
    ::= { cfprSwVlanEntry 21 }

cfprSwVlanPubNwName OBJECT-TYPE
    SYNTAX       SnmpAdminString
    MAX-ACCESS   read-only
    STATUS       current
    DESCRIPTION
        "Cisco Firepower sw:Vlan:pubNwName managed object property"
    ::= { cfprSwVlanEntry 22 }

cfprSwVlanQuerierIpAddrs OBJECT-TYPE
    SYNTAX       InetAddressIPv4
    MAX-ACCESS   read-only
    STATUS       current
    DESCRIPTION
        "Cisco Firepower sw:Vlan:querierIpAddrs managed object property"
    ::= { cfprSwVlanEntry 23 }

cfprSwVlanSecVlanPerPrimaryVlanCount OBJECT-TYPE
    SYNTAX       Gauge32
    MAX-ACCESS   read-only
    STATUS       current
    DESCRIPTION
        "Cisco Firepower sw:Vlan:secVlanPerPrimaryVlanCount
        managed object property"
    ::= { cfprSwVlanEntry 24 }

cfprSwVlanSecVlanPerPrimaryVlanCountStatus OBJECT-TYPE
    SYNTAX       CfprNetworkVlanCountStatus
    MAX-ACCESS   read-only
    STATUS       current
    DESCRIPTION
        "Cisco Firepower sw:Vlan:secVlanPerPrimaryVlanCountStatus
        managed object property"
    ::= { cfprSwVlanEntry 25 }

cfprSwVlanSharing OBJECT-TYPE
    SYNTAX       CfprFabricAVlanSharing
    MAX-ACCESS   read-only
    STATUS       current
    DESCRIPTION
        "Cisco Firepower sw:Vlan:sharing managed object property"
    ::= { cfprSwVlanEntry 26 }

cfprSwVlanSnoopingEnabled OBJECT-TYPE
    SYNTAX       TruthValue
    MAX-ACCESS   read-only
    STATUS       current
    DESCRIPTION
        "Cisco Firepower sw:Vlan:snoopingEnabled managed object property"
    ::= { cfprSwVlanEntry 27 }

cfprSwVlanSwitchId OBJECT-TYPE
    SYNTAX       CfprNetworkSwitchId
    MAX-ACCESS   read-only
    STATUS       current
    DESCRIPTION
        "Cisco Firepower sw:Vlan:switchId managed object property"
    ::= { cfprSwVlanEntry 28 }

cfprSwVlanTransport OBJECT-TYPE
    SYNTAX       CfprFabricAVlanTransport
    MAX-ACCESS   read-only
    STATUS       current
    DESCRIPTION
        "Cisco Firepower sw:Vlan:transport managed object property"
    ::= { cfprSwVlanEntry 29 }

cfprSwVlanType OBJECT-TYPE
    SYNTAX       CfprFabricAVlanType
    MAX-ACCESS   read-only
    STATUS       current
    DESCRIPTION
        "Cisco Firepower sw:Vlan:type managed object property"
    ::= { cfprSwVlanEntry 30 }

cfprSwVlanVlanType OBJECT-TYPE
    SYNTAX       CfprFabricEpVlanVlanType
    MAX-ACCESS   read-only
    STATUS       current
    DESCRIPTION
        "Cisco Firepower sw:Vlan:vlanType managed object property"
    ::= { cfprSwVlanEntry 31 }

cfprSwVlanGroupTable OBJECT-TYPE
    SYNTAX           SEQUENCE OF CfprSwVlanGroupEntry
    MAX-ACCESS       not-accessible
    STATUS           current
    DESCRIPTION
        "Cisco Firepower sw:VlanGroup managed object table"
    ::= { cfprSwObjects 81 }

cfprSwVlanGroupEntry OBJECT-TYPE
    SYNTAX           CfprSwVlanGroupEntry
    MAX-ACCESS       not-accessible
    STATUS           current
    DESCRIPTION
        "Entry for the cfprSwVlanGroupTable table."
    INDEX { cfprSwVlanGroupInstanceId }
    ::= { cfprSwVlanGroupTable 1 }

CfprSwVlanGroupEntry ::= SEQUENCE {
    cfprSwVlanGroupInstanceId                                        CfprManagedObjectId,
    cfprSwVlanGroupDn                                                CfprManagedObjectDn,
    cfprSwVlanGroupRn                                                SnmpAdminString,
    cfprSwVlanGroupId                                                Gauge32,
    cfprSwVlanGroupPeerDn                                            SnmpAdminString,
    cfprSwVlanGroupSwitchId                                          CfprNetworkSwitchId,
    cfprSwVlanGroupType                                              CfprSwVlanGroupType
}

cfprSwVlanGroupInstanceId OBJECT-TYPE
    SYNTAX       CfprManagedObjectId
    MAX-ACCESS   not-accessible
    STATUS       current
    DESCRIPTION
        "Instance identifier of the managed object."
    ::= { cfprSwVlanGroupEntry 1 }

cfprSwVlanGroupDn OBJECT-TYPE
    SYNTAX       CfprManagedObjectDn
    MAX-ACCESS   read-only
    STATUS       current
    DESCRIPTION
        "Cisco Firepower sw:VlanGroup:dn managed object property"
    ::= { cfprSwVlanGroupEntry 2 }

cfprSwVlanGroupRn OBJECT-TYPE
    SYNTAX       SnmpAdminString
    MAX-ACCESS   read-only
    STATUS       current
    DESCRIPTION
        "Cisco Firepower sw:VlanGroup:rn managed object property"
    ::= { cfprSwVlanGroupEntry 3 }

cfprSwVlanGroupId OBJECT-TYPE
    SYNTAX       Gauge32
    MAX-ACCESS   read-only
    STATUS       current
    DESCRIPTION
        "Cisco Firepower sw:VlanGroup:id managed object property"
    ::= { cfprSwVlanGroupEntry 4 }

cfprSwVlanGroupPeerDn OBJECT-TYPE
    SYNTAX       SnmpAdminString
    MAX-ACCESS   read-only
    STATUS       current
    DESCRIPTION
        "Cisco Firepower sw:VlanGroup:peerDn managed object property"
    ::= { cfprSwVlanGroupEntry 5 }

cfprSwVlanGroupSwitchId OBJECT-TYPE
    SYNTAX       CfprNetworkSwitchId
    MAX-ACCESS   read-only
    STATUS       current
    DESCRIPTION
        "Cisco Firepower sw:VlanGroup:switchId managed object property"
    ::= { cfprSwVlanGroupEntry 6 }

cfprSwVlanGroupType OBJECT-TYPE
    SYNTAX       CfprSwVlanGroupType
    MAX-ACCESS   read-only
    STATUS       current
    DESCRIPTION
        "Cisco Firepower sw:VlanGroup:type managed object property"
    ::= { cfprSwVlanGroupEntry 7 }

cfprSwVlanPortNsTable OBJECT-TYPE
    SYNTAX           SEQUENCE OF CfprSwVlanPortNsEntry
    MAX-ACCESS       not-accessible
    STATUS           current
    DESCRIPTION
        "Cisco Firepower sw:VlanPortNs managed object table"
    ::= { cfprSwObjects 82 }

cfprSwVlanPortNsEntry OBJECT-TYPE
    SYNTAX           CfprSwVlanPortNsEntry
    MAX-ACCESS       not-accessible
    STATUS           current
    DESCRIPTION
        "Entry for the cfprSwVlanPortNsTable table."
    INDEX { cfprSwVlanPortNsInstanceId }
    ::= { cfprSwVlanPortNsTable 1 }

CfprSwVlanPortNsEntry ::= SEQUENCE {
    cfprSwVlanPortNsInstanceId                                       CfprManagedObjectId,
    cfprSwVlanPortNsDn                                               CfprManagedObjectDn,
    cfprSwVlanPortNsRn                                               SnmpAdminString,
    cfprSwVlanPortNsAccessVlanPortCount                              Gauge32,
    cfprSwVlanPortNsAllocStatus                                      CfprSwVlanPortNsAllocStatus,
    cfprSwVlanPortNsBorderVlanPortCount                              Gauge32,
    cfprSwVlanPortNsConfigStatus                                     CfprSwConfigStatus,
    cfprSwVlanPortNsLimit                                            Gauge32,
    cfprSwVlanPortNsSwitchId                                         CfprNetworkSwitchId,
    cfprSwVlanPortNsTotalVlanPortCount                               Gauge32,
    cfprSwVlanPortNsVlanCompOffLimit                                 Gauge32,
    cfprSwVlanPortNsVlanCompOnLimit                                  Gauge32
}

cfprSwVlanPortNsInstanceId OBJECT-TYPE
    SYNTAX       CfprManagedObjectId
    MAX-ACCESS   not-accessible
    STATUS       current
    DESCRIPTION
        "Instance identifier of the managed object."
    ::= { cfprSwVlanPortNsEntry 1 }

cfprSwVlanPortNsDn OBJECT-TYPE
    SYNTAX       CfprManagedObjectDn
    MAX-ACCESS   read-only
    STATUS       current
    DESCRIPTION
        "Cisco Firepower sw:VlanPortNs:dn managed object property"
    ::= { cfprSwVlanPortNsEntry 2 }

cfprSwVlanPortNsRn OBJECT-TYPE
    SYNTAX       SnmpAdminString
    MAX-ACCESS   read-only
    STATUS       current
    DESCRIPTION
        "Cisco Firepower sw:VlanPortNs:rn managed object property"
    ::= { cfprSwVlanPortNsEntry 3 }

cfprSwVlanPortNsAccessVlanPortCount OBJECT-TYPE
    SYNTAX       Gauge32
    MAX-ACCESS   read-only
    STATUS       current
    DESCRIPTION
        "Cisco Firepower sw:VlanPortNs:accessVlanPortCount
        managed object property"
    ::= { cfprSwVlanPortNsEntry 4 }

cfprSwVlanPortNsAllocStatus OBJECT-TYPE
    SYNTAX       CfprSwVlanPortNsAllocStatus
    MAX-ACCESS   read-only
    STATUS       current
    DESCRIPTION
        "Cisco Firepower sw:VlanPortNs:allocStatus managed
        object property"
    ::= { cfprSwVlanPortNsEntry 5 }

cfprSwVlanPortNsBorderVlanPortCount OBJECT-TYPE
    SYNTAX       Gauge32
    MAX-ACCESS   read-only
    STATUS       current
    DESCRIPTION
        "Cisco Firepower sw:VlanPortNs:borderVlanPortCount
        managed object property"
    ::= { cfprSwVlanPortNsEntry 6 }

cfprSwVlanPortNsConfigStatus OBJECT-TYPE
    SYNTAX       CfprSwConfigStatus
    MAX-ACCESS   read-only
    STATUS       current
    DESCRIPTION
        "Cisco Firepower sw:VlanPortNs:configStatus managed
        object property"
    ::= { cfprSwVlanPortNsEntry 7 }

cfprSwVlanPortNsLimit OBJECT-TYPE
    SYNTAX       Gauge32
    MAX-ACCESS   read-only
    STATUS       current
    DESCRIPTION
        "Cisco Firepower sw:VlanPortNs:limit managed object property"
    ::= { cfprSwVlanPortNsEntry 8 }

cfprSwVlanPortNsSwitchId OBJECT-TYPE
    SYNTAX       CfprNetworkSwitchId
    MAX-ACCESS   read-only
    STATUS       current
    DESCRIPTION
        "Cisco Firepower sw:VlanPortNs:switchId managed object property"
    ::= { cfprSwVlanPortNsEntry 9 }

cfprSwVlanPortNsTotalVlanPortCount OBJECT-TYPE
    SYNTAX       Gauge32
    MAX-ACCESS   read-only
    STATUS       current
    DESCRIPTION
        "Cisco Firepower sw:VlanPortNs:totalVlanPortCount
        managed object property"
    ::= { cfprSwVlanPortNsEntry 10 }

cfprSwVlanPortNsVlanCompOffLimit OBJECT-TYPE
    SYNTAX       Gauge32
    MAX-ACCESS   read-only
    STATUS       current
    DESCRIPTION
        "Cisco Firepower sw:VlanPortNs:vlanCompOffLimit
        managed object property"
    ::= { cfprSwVlanPortNsEntry 11 }

cfprSwVlanPortNsVlanCompOnLimit OBJECT-TYPE
    SYNTAX       Gauge32
    MAX-ACCESS   read-only
    STATUS       current
    DESCRIPTION
        "Cisco Firepower sw:VlanPortNs:vlanCompOnLimit
        managed object property"
    ::= { cfprSwVlanPortNsEntry 12 }

cfprSwVlanPortNsOverrideTable OBJECT-TYPE
    SYNTAX           SEQUENCE OF CfprSwVlanPortNsOverrideEntry
    MAX-ACCESS       not-accessible
    STATUS           current
    DESCRIPTION
        "Cisco Firepower sw:VlanPortNsOverride managed object table"
    ::= { cfprSwObjects 83 }

cfprSwVlanPortNsOverrideEntry OBJECT-TYPE
    SYNTAX           CfprSwVlanPortNsOverrideEntry
    MAX-ACCESS       not-accessible
    STATUS           current
    DESCRIPTION
        "Entry for the cfprSwVlanPortNsOverrideTable table."
    INDEX { cfprSwVlanPortNsOverrideInstanceId }
    ::= { cfprSwVlanPortNsOverrideTable 1 }

CfprSwVlanPortNsOverrideEntry ::= SEQUENCE {
    cfprSwVlanPortNsOverrideInstanceId                               CfprManagedObjectId,
    cfprSwVlanPortNsOverrideDn                                       CfprManagedObjectDn,
    cfprSwVlanPortNsOverrideRn                                       SnmpAdminString,
    cfprSwVlanPortNsOverrideLimit                                    Gauge32
}

cfprSwVlanPortNsOverrideInstanceId OBJECT-TYPE
    SYNTAX       CfprManagedObjectId
    MAX-ACCESS   not-accessible
    STATUS       current
    DESCRIPTION
        "Instance identifier of the managed object."
    ::= { cfprSwVlanPortNsOverrideEntry 1 }

cfprSwVlanPortNsOverrideDn OBJECT-TYPE
    SYNTAX       CfprManagedObjectDn
    MAX-ACCESS   read-only
    STATUS       current
    DESCRIPTION
        "Cisco Firepower sw:VlanPortNsOverride:dn managed object property"
    ::= { cfprSwVlanPortNsOverrideEntry 2 }

cfprSwVlanPortNsOverrideRn OBJECT-TYPE
    SYNTAX       SnmpAdminString
    MAX-ACCESS   read-only
    STATUS       current
    DESCRIPTION
        "Cisco Firepower sw:VlanPortNsOverride:rn managed object property"
    ::= { cfprSwVlanPortNsOverrideEntry 3 }

cfprSwVlanPortNsOverrideLimit OBJECT-TYPE
    SYNTAX       Gauge32
    MAX-ACCESS   read-only
    STATUS       current
    DESCRIPTION
        "Cisco Firepower sw:VlanPortNsOverride:limit managed
        object property"
    ::= { cfprSwVlanPortNsOverrideEntry 4 }

cfprSwVlanRefTable OBJECT-TYPE
    SYNTAX           SEQUENCE OF CfprSwVlanRefEntry
    MAX-ACCESS       not-accessible
    STATUS           current
    DESCRIPTION
        "Cisco Firepower sw:VlanRef managed object table"
    ::= { cfprSwObjects 84 }

cfprSwVlanRefEntry OBJECT-TYPE
    SYNTAX           CfprSwVlanRefEntry
    MAX-ACCESS       not-accessible
    STATUS           current
    DESCRIPTION
        "Entry for the cfprSwVlanRefTable table."
    INDEX { cfprSwVlanRefInstanceId }
    ::= { cfprSwVlanRefTable 1 }

CfprSwVlanRefEntry ::= SEQUENCE {
    cfprSwVlanRefInstanceId                                          CfprManagedObjectId,
    cfprSwVlanRefDn                                                  CfprManagedObjectDn,
    cfprSwVlanRefRn                                                  SnmpAdminString,
    cfprSwVlanRefCompressionType                                     CfprSwVlanCompType,
    cfprSwVlanRefConfigStatus                                        CfprSwVlanConfigStatusType,
    cfprSwVlanRefId                                                  Gauge32,
    cfprSwVlanRefPeerDn                                              SnmpAdminString
}

cfprSwVlanRefInstanceId OBJECT-TYPE
    SYNTAX       CfprManagedObjectId
    MAX-ACCESS   not-accessible
    STATUS       current
    DESCRIPTION
        "Instance identifier of the managed object."
    ::= { cfprSwVlanRefEntry 1 }

cfprSwVlanRefDn OBJECT-TYPE
    SYNTAX       CfprManagedObjectDn
    MAX-ACCESS   read-only
    STATUS       current
    DESCRIPTION
        "Cisco Firepower sw:VlanRef:dn managed object property"
    ::= { cfprSwVlanRefEntry 2 }

cfprSwVlanRefRn OBJECT-TYPE
    SYNTAX       SnmpAdminString
    MAX-ACCESS   read-only
    STATUS       current
    DESCRIPTION
        "Cisco Firepower sw:VlanRef:rn managed object property"
    ::= { cfprSwVlanRefEntry 3 }

cfprSwVlanRefCompressionType OBJECT-TYPE
    SYNTAX       CfprSwVlanCompType
    MAX-ACCESS   read-only
    STATUS       current
    DESCRIPTION
        "Cisco Firepower sw:VlanRef:compressionType managed
        object property"
    ::= { cfprSwVlanRefEntry 4 }

cfprSwVlanRefConfigStatus OBJECT-TYPE
    SYNTAX       CfprSwVlanConfigStatusType
    MAX-ACCESS   read-only
    STATUS       current
    DESCRIPTION
        "Cisco Firepower sw:VlanRef:configStatus managed object property"
    ::= { cfprSwVlanRefEntry 5 }

cfprSwVlanRefId OBJECT-TYPE
    SYNTAX       Gauge32
    MAX-ACCESS   read-only
    STATUS       current
    DESCRIPTION
        "Cisco Firepower sw:VlanRef:id managed object property"
    ::= { cfprSwVlanRefEntry 6 }

cfprSwVlanRefPeerDn OBJECT-TYPE
    SYNTAX       SnmpAdminString
    MAX-ACCESS   read-only
    STATUS       current
    DESCRIPTION
        "Cisco Firepower sw:VlanRef:peerDn managed object property"
    ::= { cfprSwVlanRefEntry 7 }

cfprSwVsanTable OBJECT-TYPE
    SYNTAX           SEQUENCE OF CfprSwVsanEntry
    MAX-ACCESS       not-accessible
    STATUS           current
    DESCRIPTION
        "Cisco Firepower sw:Vsan managed object table"
    ::= { cfprSwObjects 85 }

cfprSwVsanEntry OBJECT-TYPE
    SYNTAX           CfprSwVsanEntry
    MAX-ACCESS       not-accessible
    STATUS           current
    DESCRIPTION
        "Entry for the cfprSwVsanTable table."
    INDEX { cfprSwVsanInstanceId }
    ::= { cfprSwVsanTable 1 }

CfprSwVsanEntry ::= SEQUENCE {
    cfprSwVsanInstanceId                                             CfprManagedObjectId,
    cfprSwVsanDn                                                     CfprManagedObjectDn,
    cfprSwVsanRn                                                     SnmpAdminString,
    cfprSwVsanDefaultZoning                                          CfprFabricDefaultZoningState,
    cfprSwVsanEpDn                                                   SnmpAdminString,
    cfprSwVsanFcZoneSharingMode                                      CfprFabricFcZoneSharingMode,
    cfprSwVsanFcoeVlan                                               Gauge32,
    cfprSwVsanFltAggr                                                Unsigned64,
    cfprSwVsanId                                                     Gauge32,
    cfprSwVsanIfRole                                                 CfprFabricVnetEpIfRole,
    cfprSwVsanIfType                                                 CfprNetworkVnetEpIfType,
    cfprSwVsanLc                                                     CfprFsmLifecycle,
    cfprSwVsanLocale                                                 CfprFabricVnetEpLocale,
    cfprSwVsanMonTrafDir                                             CfprFabricTrafficDirection,
    cfprSwVsanName                                                   SnmpAdminString,
    cfprSwVsanOperState                                              CfprFabricVsanOperState,
    cfprSwVsanPeerDn                                                 SnmpAdminString,
    cfprSwVsanPolicyOwner                                            CfprFabricVnetEpPolicyOwner,
    cfprSwVsanSwitchId                                               CfprNetworkSwitchId,
    cfprSwVsanTransport                                              CfprFabricAVsanTransport,
    cfprSwVsanType                                                   CfprFabricAVsanType,
    cfprSwVsanZoningState                                            CfprFabricZoningState
}

cfprSwVsanInstanceId OBJECT-TYPE
    SYNTAX       CfprManagedObjectId
    MAX-ACCESS   not-accessible
    STATUS       current
    DESCRIPTION
        "Instance identifier of the managed object."
    ::= { cfprSwVsanEntry 1 }

cfprSwVsanDn OBJECT-TYPE
    SYNTAX       CfprManagedObjectDn
    MAX-ACCESS   read-only
    STATUS       current
    DESCRIPTION
        "Cisco Firepower sw:Vsan:dn managed object property"
    ::= { cfprSwVsanEntry 2 }

cfprSwVsanRn OBJECT-TYPE
    SYNTAX       SnmpAdminString
    MAX-ACCESS   read-only
    STATUS       current
    DESCRIPTION
        "Cisco Firepower sw:Vsan:rn managed object property"
    ::= { cfprSwVsanEntry 3 }

cfprSwVsanDefaultZoning OBJECT-TYPE
    SYNTAX       CfprFabricDefaultZoningState
    MAX-ACCESS   read-only
    STATUS       current
    DESCRIPTION
        "Cisco Firepower sw:Vsan:defaultZoning managed object property"
    ::= { cfprSwVsanEntry 4 }

cfprSwVsanEpDn OBJECT-TYPE
    SYNTAX       SnmpAdminString
    MAX-ACCESS   read-only
    STATUS       current
    DESCRIPTION
        "Cisco Firepower sw:Vsan:epDn managed object property"
    ::= { cfprSwVsanEntry 5 }

cfprSwVsanFcZoneSharingMode OBJECT-TYPE
    SYNTAX       CfprFabricFcZoneSharingMode
    MAX-ACCESS   read-only
    STATUS       current
    DESCRIPTION
        "Cisco Firepower sw:Vsan:fcZoneSharingMode managed
        object property"
    ::= { cfprSwVsanEntry 6 }

cfprSwVsanFcoeVlan OBJECT-TYPE
    SYNTAX       Gauge32
    MAX-ACCESS   read-only
    STATUS       current
    DESCRIPTION
        "Cisco Firepower sw:Vsan:fcoeVlan managed object property"
    ::= { cfprSwVsanEntry 7 }

cfprSwVsanFltAggr OBJECT-TYPE
    SYNTAX       Unsigned64
    MAX-ACCESS   read-only
    STATUS       current
    DESCRIPTION
        "Cisco Firepower sw:Vsan:fltAggr managed object property"
    ::= { cfprSwVsanEntry 8 }

cfprSwVsanId OBJECT-TYPE
    SYNTAX       Gauge32
    MAX-ACCESS   read-only
    STATUS       current
    DESCRIPTION
        "Cisco Firepower sw:Vsan:id managed object property"
    ::= { cfprSwVsanEntry 9 }

cfprSwVsanIfRole OBJECT-TYPE
    SYNTAX       CfprFabricVnetEpIfRole
    MAX-ACCESS   read-only
    STATUS       current
    DESCRIPTION
        "Cisco Firepower sw:Vsan:ifRole managed object property"
    ::= { cfprSwVsanEntry 10 }

cfprSwVsanIfType OBJECT-TYPE
    SYNTAX       CfprNetworkVnetEpIfType
    MAX-ACCESS   read-only
    STATUS       current
    DESCRIPTION
        "Cisco Firepower sw:Vsan:ifType managed object property"
    ::= { cfprSwVsanEntry 11 }

cfprSwVsanLc OBJECT-TYPE
    SYNTAX       CfprFsmLifecycle
    MAX-ACCESS   read-only
    STATUS       current
    DESCRIPTION
        "Cisco Firepower sw:Vsan:lc managed object property"
    ::= { cfprSwVsanEntry 12 }

cfprSwVsanLocale OBJECT-TYPE
    SYNTAX       CfprFabricVnetEpLocale
    MAX-ACCESS   read-only
    STATUS       current
    DESCRIPTION
        "Cisco Firepower sw:Vsan:locale managed object property"
    ::= { cfprSwVsanEntry 13 }

cfprSwVsanMonTrafDir OBJECT-TYPE
    SYNTAX       CfprFabricTrafficDirection
    MAX-ACCESS   read-only
    STATUS       current
    DESCRIPTION
        "Cisco Firepower sw:Vsan:monTrafDir managed object property"
    ::= { cfprSwVsanEntry 14 }

cfprSwVsanName OBJECT-TYPE
    SYNTAX       SnmpAdminString
    MAX-ACCESS   read-only
    STATUS       current
    DESCRIPTION
        "Cisco Firepower sw:Vsan:name managed object property"
    ::= { cfprSwVsanEntry 15 }

cfprSwVsanOperState OBJECT-TYPE
    SYNTAX       CfprFabricVsanOperState
    MAX-ACCESS   read-only
    STATUS       current
    DESCRIPTION
        "Cisco Firepower sw:Vsan:operState managed object property"
    ::= { cfprSwVsanEntry 16 }

cfprSwVsanPeerDn OBJECT-TYPE
    SYNTAX       SnmpAdminString
    MAX-ACCESS   read-only
    STATUS       current
    DESCRIPTION
        "Cisco Firepower sw:Vsan:peerDn managed object property"
    ::= { cfprSwVsanEntry 17 }

cfprSwVsanPolicyOwner OBJECT-TYPE
    SYNTAX       CfprFabricVnetEpPolicyOwner
    MAX-ACCESS   read-only
    STATUS       current
    DESCRIPTION
        "Cisco Firepower sw:Vsan:policyOwner managed object property"
    ::= { cfprSwVsanEntry 18 }

cfprSwVsanSwitchId OBJECT-TYPE
    SYNTAX       CfprNetworkSwitchId
    MAX-ACCESS   read-only
    STATUS       current
    DESCRIPTION
        "Cisco Firepower sw:Vsan:switchId managed object property"
    ::= { cfprSwVsanEntry 19 }

cfprSwVsanTransport OBJECT-TYPE
    SYNTAX       CfprFabricAVsanTransport
    MAX-ACCESS   read-only
    STATUS       current
    DESCRIPTION
        "Cisco Firepower sw:Vsan:transport managed object property"
    ::= { cfprSwVsanEntry 20 }

cfprSwVsanType OBJECT-TYPE
    SYNTAX       CfprFabricAVsanType
    MAX-ACCESS   read-only
    STATUS       current
    DESCRIPTION
        "Cisco Firepower sw:Vsan:type managed object property"
    ::= { cfprSwVsanEntry 21 }

cfprSwVsanZoningState OBJECT-TYPE
    SYNTAX       CfprFabricZoningState
    MAX-ACCESS   read-only
    STATUS       current
    DESCRIPTION
        "Cisco Firepower sw:Vsan:zoningState managed object property"
    ::= { cfprSwVsanEntry 22 }

cfprSwZoneInitiatorMemberTable OBJECT-TYPE
    SYNTAX           SEQUENCE OF CfprSwZoneInitiatorMemberEntry
    MAX-ACCESS       not-accessible
    STATUS           current
    DESCRIPTION
        "Cisco Firepower sw:ZoneInitiatorMember managed object table"
    ::= { cfprSwObjects 86 }

cfprSwZoneInitiatorMemberEntry OBJECT-TYPE
    SYNTAX           CfprSwZoneInitiatorMemberEntry
    MAX-ACCESS       not-accessible
    STATUS           current
    DESCRIPTION
        "Entry for the cfprSwZoneInitiatorMemberTable table."
    INDEX { cfprSwZoneInitiatorMemberInstanceId }
    ::= { cfprSwZoneInitiatorMemberTable 1 }

CfprSwZoneInitiatorMemberEntry ::= SEQUENCE {
    cfprSwZoneInitiatorMemberInstanceId                              CfprManagedObjectId,
    cfprSwZoneInitiatorMemberDn                                      CfprManagedObjectDn,
    cfprSwZoneInitiatorMemberRn                                      SnmpAdminString,
    cfprSwZoneInitiatorMemberEpDn                                    SnmpAdminString,
    cfprSwZoneInitiatorMemberLc                                      CfprSwFcZoneMemberLc,
    cfprSwZoneInitiatorMemberName                                    SnmpAdminString,
    cfprSwZoneInitiatorMemberPeerDn                                  SnmpAdminString,
    cfprSwZoneInitiatorMemberWwpn                                    Unsigned64
}

cfprSwZoneInitiatorMemberInstanceId OBJECT-TYPE
    SYNTAX       CfprManagedObjectId
    MAX-ACCESS   not-accessible
    STATUS       current
    DESCRIPTION
        "Instance identifier of the managed object."
    ::= { cfprSwZoneInitiatorMemberEntry 1 }

cfprSwZoneInitiatorMemberDn OBJECT-TYPE
    SYNTAX       CfprManagedObjectDn
    MAX-ACCESS   read-only
    STATUS       current
    DESCRIPTION
        "Cisco Firepower sw:ZoneInitiatorMember:dn managed
        object property"
    ::= { cfprSwZoneInitiatorMemberEntry 2 }

cfprSwZoneInitiatorMemberRn OBJECT-TYPE
    SYNTAX       SnmpAdminString
    MAX-ACCESS   read-only
    STATUS       current
    DESCRIPTION
        "Cisco Firepower sw:ZoneInitiatorMember:rn managed
        object property"
    ::= { cfprSwZoneInitiatorMemberEntry 3 }

cfprSwZoneInitiatorMemberEpDn OBJECT-TYPE
    SYNTAX       SnmpAdminString
    MAX-ACCESS   read-only
    STATUS       current
    DESCRIPTION
        "Cisco Firepower sw:ZoneInitiatorMember:epDn managed
        object property"
    ::= { cfprSwZoneInitiatorMemberEntry 4 }

cfprSwZoneInitiatorMemberLc OBJECT-TYPE
    SYNTAX       CfprSwFcZoneMemberLc
    MAX-ACCESS   read-only
    STATUS       current
    DESCRIPTION
        "Cisco Firepower sw:ZoneInitiatorMember:lc managed
        object property"
    ::= { cfprSwZoneInitiatorMemberEntry 5 }

cfprSwZoneInitiatorMemberName OBJECT-TYPE
    SYNTAX       SnmpAdminString
    MAX-ACCESS   read-only
    STATUS       current
    DESCRIPTION
        "Cisco Firepower sw:ZoneInitiatorMember:name managed
        object property"
    ::= { cfprSwZoneInitiatorMemberEntry 6 }

cfprSwZoneInitiatorMemberPeerDn OBJECT-TYPE
    SYNTAX       SnmpAdminString
    MAX-ACCESS   read-only
    STATUS       current
    DESCRIPTION
        "Cisco Firepower sw:ZoneInitiatorMember:peerDn
        managed object property"
    ::= { cfprSwZoneInitiatorMemberEntry 7 }

cfprSwZoneInitiatorMemberWwpn OBJECT-TYPE
    SYNTAX       Unsigned64
    MAX-ACCESS   read-only
    STATUS       current
    DESCRIPTION
        "Cisco Firepower sw:ZoneInitiatorMember:wwpn managed
        object property"
    ::= { cfprSwZoneInitiatorMemberEntry 8 }

cfprSwZoneTargetMemberTable OBJECT-TYPE
    SYNTAX           SEQUENCE OF CfprSwZoneTargetMemberEntry
    MAX-ACCESS       not-accessible
    STATUS           current
    DESCRIPTION
        "Cisco Firepower sw:ZoneTargetMember managed object table"
    ::= { cfprSwObjects 87 }

cfprSwZoneTargetMemberEntry OBJECT-TYPE
    SYNTAX           CfprSwZoneTargetMemberEntry
    MAX-ACCESS       not-accessible
    STATUS           current
    DESCRIPTION
        "Entry for the cfprSwZoneTargetMemberTable table."
    INDEX { cfprSwZoneTargetMemberInstanceId }
    ::= { cfprSwZoneTargetMemberTable 1 }

CfprSwZoneTargetMemberEntry ::= SEQUENCE {
    cfprSwZoneTargetMemberInstanceId                                 CfprManagedObjectId,
    cfprSwZoneTargetMemberDn                                         CfprManagedObjectDn,
    cfprSwZoneTargetMemberRn                                         SnmpAdminString,
    cfprSwZoneTargetMemberEpDn                                       SnmpAdminString,
    cfprSwZoneTargetMemberLc                                         CfprSwFcZoneMemberLc,
    cfprSwZoneTargetMemberName                                       SnmpAdminString,
    cfprSwZoneTargetMemberPeerDn                                     SnmpAdminString,
    cfprSwZoneTargetMemberWwpn                                       Unsigned64
}

cfprSwZoneTargetMemberInstanceId OBJECT-TYPE
    SYNTAX       CfprManagedObjectId
    MAX-ACCESS   not-accessible
    STATUS       current
    DESCRIPTION
        "Instance identifier of the managed object."
    ::= { cfprSwZoneTargetMemberEntry 1 }

cfprSwZoneTargetMemberDn OBJECT-TYPE
    SYNTAX       CfprManagedObjectDn
    MAX-ACCESS   read-only
    STATUS       current
    DESCRIPTION
        "Cisco Firepower sw:ZoneTargetMember:dn managed object property"
    ::= { cfprSwZoneTargetMemberEntry 2 }

cfprSwZoneTargetMemberRn OBJECT-TYPE
    SYNTAX       SnmpAdminString
    MAX-ACCESS   read-only
    STATUS       current
    DESCRIPTION
        "Cisco Firepower sw:ZoneTargetMember:rn managed object property"
    ::= { cfprSwZoneTargetMemberEntry 3 }

cfprSwZoneTargetMemberEpDn OBJECT-TYPE
    SYNTAX       SnmpAdminString
    MAX-ACCESS   read-only
    STATUS       current
    DESCRIPTION
        "Cisco Firepower sw:ZoneTargetMember:epDn managed object property"
    ::= { cfprSwZoneTargetMemberEntry 4 }

cfprSwZoneTargetMemberLc OBJECT-TYPE
    SYNTAX       CfprSwFcZoneMemberLc
    MAX-ACCESS   read-only
    STATUS       current
    DESCRIPTION
        "Cisco Firepower sw:ZoneTargetMember:lc managed object property"
    ::= { cfprSwZoneTargetMemberEntry 5 }

cfprSwZoneTargetMemberName OBJECT-TYPE
    SYNTAX       SnmpAdminString
    MAX-ACCESS   read-only
    STATUS       current
    DESCRIPTION
        "Cisco Firepower sw:ZoneTargetMember:name managed object property"
    ::= { cfprSwZoneTargetMemberEntry 6 }

cfprSwZoneTargetMemberPeerDn OBJECT-TYPE
    SYNTAX       SnmpAdminString
    MAX-ACCESS   read-only
    STATUS       current
    DESCRIPTION
        "Cisco Firepower sw:ZoneTargetMember:peerDn managed
        object property"
    ::= { cfprSwZoneTargetMemberEntry 7 }

cfprSwZoneTargetMemberWwpn OBJECT-TYPE
    SYNTAX       Unsigned64
    MAX-ACCESS   read-only
    STATUS       current
    DESCRIPTION
        "Cisco Firepower sw:ZoneTargetMember:wwpn managed object property"
    ::= { cfprSwZoneTargetMemberEntry 8 }

END
