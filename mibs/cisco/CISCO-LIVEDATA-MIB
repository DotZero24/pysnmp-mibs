-- *****************************************************************
-- CISCO-LIVEDATA-MIB.my
-- Cisco (Unified) LiveData MIB file.
-- Copyright (c) 2005-2006, 2013 by Cisco Systems Inc.
-- All rights reserved.
-- *****************************************************************

CISCO-LIVEDATA-MIB DEFINITIONS ::= BEGIN

IMPORTS
    MODULE-IDENTITY,
    OBJECT-TYPE,
    NOTIFICATION-TYPE,
    Unsigned32,
    Counter32,
    Gauge32,
    Integer32
        FROM SNMPv2-SMI
    MODULE-COMPLIANCE,
    NOTIFICATION-GROUP,
    OBJECT-GROUP
        FROM SNMPv2-CONF
    TEXTUAL-CONVENTION,
    DateAndTime,
    TruthValue
        FROM SNMPv2-TC
    SnmpAdminString
        FROM SNMP-FRAMEWORK-MIB
    ciscoMgmt
        FROM CISCO-SMI;


ciscoLivedataMIB MODULE-IDENTITY
    LAST-UPDATED    "201308290000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "Cisco LiveData is the next generation reporting product for
        Cisco Unified Contact Center Enterprise (CCE).  Cisco
        LiveData provides a horizontally scalable, highly available
        architecture to support systems with large numbers of
        reporting users.  LiveData enables fast refresh rates on
        real-time data (3 seconds or less).  A LiveData node consumes
        real-time data streams from one or more sources, processes
        the data and publishes the resulting data to solution
        consumers.  Consumers may be database management systems,
        applications or reporting engines.

        Cisco LiveData aggregates and publishes real-time data and
        metrics pushed to it (e.g. from the CCE router and/or
        peripheral gateway components) to a message bus; Cisco
        Unified Intelligence Center (CUIC) and the CCE Administrator
        Workstation (AW) subscribe to this message bus to receive
        real-time data updates.  CUIC users then build reports using
        this real-time data; other CCE clients may also query this
        real-time data from the CCE AW database.

        A LiveData cluster consists of one or more nodes; one is
        designated as the master with additional worker nodes as
        needed.  A LiveData cluster may have a remote peer cluster
        that works cooperatively in a fault-tolerant model.  LiveData
        cluster peers communicate with one another to negotiate who
        is the 'active' cluster and who is on 'standby' (only one
        cluster will be active at a time).  If the active cluster
        fails, the standby cluster will transition to active and
        begin consuming the data streams previously consumed by the
        peer cluster.

        In small deployments, a LiveData cluster will be collocated
        with CUIC in the same server virtual machine; in larger
        deployments, a LiveData cluster may include several nodes
        that may or may not be collocated with CUIC.

        A single node in a LiveData cluster will have multiple
        services running in the guest virtual machine that are
        critical to the successful function of that node.  Services
        may be distributed across the nodes of a cluster to balance
        the workload.  Each node will establish and maintain
        connections to data sources in the solution.

        CISCO-LIVEDATA-MIB defines instrumentation unique to the
        LiveData servers (virtual machines). The instrumentation
        includes objects of:
            1) a general nature - attributes of the device and
               application,
            2) cluster status* and identity,
            3) service status and identity and
            4) connection status and attributes (including metrics).
            5) events

        * It is important to note that cluster status is shared
        across all nodes of a cluster; cluster status is not
        device-specific unless there is only one node in the cluster.

        The MIB also defines a single notification type; all nodes in
        all clusters may emit notifications.

        Service and connection instrumentation is exposed as tables.
        The number of entries within each table may change over time,
        adapting to changes within the cluster.

        Glossary:
        ---------
        AW         Administrator Workstation component of a Cisco
                   Unified Contact Center Enterprise deployment.  The
                   AW collects and serves real-time and configuration
                   data to the CCE solution.
        CCE        (Cisco Unified) Contact Center Enterprise; CCE
                   delivers intelligent contact routing, call
                   treatment, network-to-desktop computer telephony
                   integration, and multichannel contact management
                   over an IP infrastructure.
        CUIC       Cisco Unified Intelligence Center; CUIC is a web-
                   based reporting application that provides real-
                   time and historical reporting in an easy-to-use,
                   wizard-based application for Cisco Contact Center
                   products.
        UCCE       Unified Contact Center Enterprise; see 'CCE'."
    REVISION        "201305230000Z"
    DESCRIPTION
        "Initial version of this MIB."
    ::= { ciscoMgmt 814 }



-- ******************************************************************
-- TEXTUAL CONVENTIONS SECTION
-- ******************************************************************

CldIndex ::= TEXTUAL-CONVENTION
    DISPLAY-HINT    "d"
    STATUS          current
    DESCRIPTION
        "This textual convention represents the index value of an
        entry in a table.  In this MIB, table entries are sorted
        within a table in an ascending order based on its index
        value.  Indexes for table entries are assigned by the SNMP
        agent."
    SYNTAX          Unsigned32 (1..4294967295)

CldSeverity ::= TEXTUAL-CONVENTION
    STATUS          current
    DESCRIPTION
        "This textual convention indicates the severity level of a
        notification or a logged event (or trace) message.  The
        severity levels are:

        'emergency':      Events of this severity indicate that a
                          devastating failure has occurred; the
                          system or service is unusable.  Immediate
                          operator intervention is required.

        'alert':          Events of this severity indicate that a
                          devastating failure is imminent that will
                          render the system unusable.  Immediate
                          operator attention is necessary.

        'critical':       Events of this severity indicate that a
                          service-impacting failure is likely to
                          occur soon which is the result of an error
                          that was not appropriately handled by the
                          system. Operator attention is needed as
                          soon as possible.

        'error':          Events of this severity contain important
                          operational state information and may
                          indicate that the system has experienced a
                          temporary impairment or an error that was
                          appropriately handled by the system.  An
                          operator should review the notification
                          soon as possible to determine if additional
                          action is needed.

        'warning':        Events of this severity contain important
                          operational state information that may be a
                          precursor to an error occurrence.  An
                          operator should review the event soon to
                          determine if additional action is needed.

        'notice':         Events of this severity contain health or
                          operational state information that may be
                          pertinent to the health of the system but
                          do not require the immediate attention of
                          the administrator.

        'informational':  Events of this severity contain interesting
                          system-level information that is valuable
                          to an administrator in time, however, the
                          event itself does not indicate a fault or
                          an impairment condition.

        'debug':          Events of this severity provide supplemental
                          information that may be beneficial toward
                          diagnosing or resolving a problem but do not
                          necessarily provide operational health
                          status."
    SYNTAX          INTEGER  {
                        emergency(1),
                        alert(2),
                        critical(3),
                        error(4),
                        warning(5),
                        notice(6),
                        informational(7),
                        debug(8)
                    }
-- ******************************************************************

ciscoLivedataMIBNotifs  OBJECT IDENTIFIER
    ::= { ciscoLivedataMIB 0 }

ciscoLivedataMIBObjects  OBJECT IDENTIFIER
    ::= { ciscoLivedataMIB 1 }

cldGeneral  OBJECT IDENTIFIER
    ::= { ciscoLivedataMIBObjects 1 }

cldCluster  OBJECT IDENTIFIER
    ::= { ciscoLivedataMIBObjects 2 }

cldServices  OBJECT IDENTIFIER
    ::= { ciscoLivedataMIBObjects 3 }

cldReportingConnections  OBJECT IDENTIFIER
    ::= { ciscoLivedataMIBObjects 4 }

cldEvents  OBJECT IDENTIFIER
    ::= { ciscoLivedataMIBObjects 5 }

ciscoLivedataMIBConform  OBJECT IDENTIFIER
    ::= { ciscoLivedataMIB 2 }

ciscoLivedataMIBCompliances  OBJECT IDENTIFIER
    ::= { ciscoLivedataMIBConform 1 }

ciscoLivedataMIBGroups  OBJECT IDENTIFIER
    ::= { ciscoLivedataMIBConform 2 }


-- ******************************************************************
-- GENERAL OBJECTS SECTION
-- ******************************************************************

cldServerName OBJECT-TYPE
    SYNTAX          SnmpAdminString
    MAX-ACCESS      read-only
    STATUS          current
    DESCRIPTION
        "This object indicates the fully-qualified domain name of the
        Cisco LiveData server."
    ::= { cldGeneral 1 }

cldDescription OBJECT-TYPE
    SYNTAX          SnmpAdminString
    MAX-ACCESS      read-only
    STATUS          current
    DESCRIPTION
        "This object indicates a textual description of the Cisco
        LiveData software installed on this server.  This is
        typically the full name of the application."
    ::= { cldGeneral 2 }

cldVersion OBJECT-TYPE
    SYNTAX          SnmpAdminString
    MAX-ACCESS      read-only
    STATUS          current
    DESCRIPTION
        "This object indicates the version number of the Cisco
        LiveData software that is installed on this server."
    ::= { cldGeneral 3 }

cldStartTime OBJECT-TYPE
    SYNTAX          DateAndTime
    MAX-ACCESS      read-only
    STATUS          current
    DESCRIPTION
        "This object indicates the date and time that the Cisco
        LiveData software (the primary application service) was
        started on this server."
    ::= { cldGeneral 4 }

cldTimeZoneName OBJECT-TYPE
    SYNTAX          SnmpAdminString
    MAX-ACCESS      read-only
    STATUS          current
    DESCRIPTION
        "This object indicates the textual name of the time zone
        where the Cisco LiveData server (host) is physically
        located."
    ::= { cldGeneral 5 }

cldTimeZoneOffset OBJECT-TYPE
    SYNTAX          Integer32
    UNITS           "minutes"
    MAX-ACCESS      read-only
    STATUS          current
    DESCRIPTION
        "This object indicates the number of minutes that the local
        time, in the time zone where the Cisco LiveData server (host)
        is physically located, differs from Greenwich Mean Time
        (GMT)."
    ::= { cldGeneral 6 }

cldEventNotifEnable OBJECT-TYPE
    SYNTAX          TruthValue
    MAX-ACCESS      read-write
    STATUS          current
    DESCRIPTION
        "This object specifies whether event generation is enabled in
        the SNMP entity.  This object allows a management station to
        disable, during run time, all outgoing Cisco LiveData
        notifications.  This is typically done during a maintenance
        window when many application components are frequently
        stopped, reconfigured and restarted, which can generate
        periodic floods of notifications that are not desirable
        during a maintenance period.  Please note that this setting
        is persistent even after a restart of the agent; the
        management station must explicitly reset this object value
        back to 'true' to re-enable outgoing application
        notifications from this device.

        When the value of this object is 'true', notifications will
        be sent to configured management stations.  When the value is
        set to 'false' by a management station, notifications will
        not be sent to configured management stations.  The default
        value of this object is 'true'.

        The value of this object does not alter the normal table
        management behavior of the event table, i.e., generated
        events will be stored in the event table regardless of the
        value of this object."
    DEFVAL          { true }
    ::= { cldGeneral 7 }

-- ******************************************************************
-- CLUSTER OBJECTS SECTION
-- ******************************************************************

cldClusterID OBJECT-TYPE
    SYNTAX          SnmpAdminString
    MAX-ACCESS      read-only
    STATUS          current
    DESCRIPTION
        "This object indicates a cluster- unique textual identifier
        for this cluster (e.g. 'sideA')."
    ::= { cldCluster 1 }

cldClusterStatus OBJECT-TYPE
    SYNTAX          INTEGER  {
                        pairedActive(1),
                        pairedStandby(2),
                        isolatedActive(3),
                        isolatedStandby(4),
                        testing(5),
                        outOfService(6)
                    }
    MAX-ACCESS      read-only
    STATUS          current
    DESCRIPTION
        "This object indicates the current status of this cluster of
        Cisco LiveData servers.  A cluster is a group of one or more
        Cisco LiveData servers that work cooperatively to consume and
        process inbound real-time data from one or more data sources.
        Work is distributed between worker nodes within the cluster
        by the master node.  A cluster may have a peer cluster in a
        fault-tolerant deployment model that will assume data
        processing duties in the event where its active peer cluster
        fails.

        'pairedActive':      The cluster is actively processing data
                             and is communicating with its remote
                             peer cluster.

        'pairedStandby':     The cluster is standing by (waiting to
                             process data if necessary) and is
                             communicating with its remote peer
                             cluster.

        'isolatedActive':    The cluster is  is actively processing
                             data but has lost peer-to-peer
                             communication with it's remote peer
                             cluster.

        'isolatedStandby':   The cluster is standing by (waiting to
                             process data if necessary) but has lost
                             peer-to-peer communication with its
                             remote peer cluster.

        'testing':           The cluster is unable to communicate
                             with the remote peer cluster via the
                             peer-to-peer connection and it is
                             invoking the 'test-other-side' procedure
                             to decide whether to become active or to
                             go into a standby state.

        'outOfService':      The cluster is out of service."
    ::= { cldCluster 2 }

cldClusterAddress OBJECT-TYPE
    SYNTAX          SnmpAdminString
    MAX-ACCESS      read-only
    STATUS          current
    DESCRIPTION
        "This object indicates the hostname or the IP address of the
        remote peer cluster for peer-to-peer communication with the
        remote cluster."
    ::= { cldCluster 3 }
-- ******************************************************************
-- SERVICE TABLE SECTION
-- ******************************************************************

cldServiceTable OBJECT-TYPE
    SYNTAX          SEQUENCE OF CldServiceEntry
    MAX-ACCESS      not-accessible
    STATUS          current
    DESCRIPTION
        "The service table is a list of Cisco LiveData services.  A
        service in this context is one or more executable processes
        that have been configured to run on this server.

        Service table objects include both the service name and the
        current run state of that service.  A single LiveData server
        will have multiple running services, each of a different
        type, that encompass the LiveData solution on a particular
        server.  Some of these services work cooperatively with
        similar or dependent services on other server nodes in the
        cluster.

        The SNMP agent constructs the service table at startup; the
        agent refreshes this table periodically during runtime to
        offer a near real-time status of configured services.
        Service table entries cannot be added to or deleted from the
        table by the management station.  All objects in this table
        are read-only."
    ::= { cldServices 1 }

cldServiceEntry OBJECT-TYPE
    SYNTAX          CldServiceEntry
    MAX-ACCESS      not-accessible
    STATUS          current
    DESCRIPTION
        "Each service entry represents a Cisco LiveData service.
        The LiveData application software includes a collection of
        related services, each of which perform a specific,
        necessary function of the application."
    INDEX           { cldServiceIndex }
    ::= { cldServiceTable 1 }

CldServiceEntry ::= SEQUENCE {
        cldServiceIndex     CldIndex,
        cldServiceName      SnmpAdminString,
        cldServiceState     INTEGER,
        cldServiceUpTime    DateAndTime
}

cldServiceIndex OBJECT-TYPE
    SYNTAX          CldIndex
    MAX-ACCESS      not-accessible
    STATUS          current
    DESCRIPTION
        "The service index is a value that uniquely identifies an
        entry in the services table.  This value is arbitrarily
        assigned by the SNMP agent."
    ::= { cldServiceEntry 1 }

cldServiceName OBJECT-TYPE
    SYNTAX          SnmpAdminString
    MAX-ACCESS      read-only
    STATUS          current
    DESCRIPTION
        "This object indicates a user-intuitive textual name for the
        Cisco LiveData service."
    ::= { cldServiceEntry 2 }

cldServiceState OBJECT-TYPE
    SYNTAX          INTEGER  {
                        unknown(1),
                        disabled(2),
                        starting(3),
                        started(4),
                        active(5),
                        stopping(6),
                        stopped(7)
                    }
    MAX-ACCESS      read-only
    STATUS          current
    DESCRIPTION
        "This object indicates the last known state of the Cisco
        LiveData service.  The object value identifies the run
        status of a configured service installed on the Cisco
        LiveData server.  The possible service states are:

        'unknown':       The status of the service cannot be
                         determined.

        'disabled':      The service has been explicitly disabled by
                         an administrator.

        'starting':      The service is currently starting up but has
                         not yet completed its startup procedure.

        'started':       The service has completed its startup
                         procedure and is currently running.

        'active':        The service has been started, is currently
                         running and is actively processing data.

        'stopping':      The service is stopping and is in the midst
                         of its shutdown procedure.

        'stopped':       The service is stopped.  The service may be
                         dysfunctional or impaired, or it has been
                         explicitly stopped by an administrator."
    ::= { cldServiceEntry 3 }

cldServiceUpTime OBJECT-TYPE
    SYNTAX          DateAndTime
    MAX-ACCESS      read-only
    STATUS          current
    DESCRIPTION
        "This object indicates the date and time that this service
        started."
    ::= { cldServiceEntry 4 }


-- ******************************************************************
-- REPORTING CONNECTION TABLE SECTION
-- ******************************************************************

cldReportingConnectionTable OBJECT-TYPE
    SYNTAX          SEQUENCE OF CldReportingConnectionEntry
    MAX-ACCESS      not-accessible
    STATUS          current
    DESCRIPTION
        "The reporting connection table is a list of Cisco LiveData
        server reporting connections. A LiveData server maintains a
        number of active connections to data sources; most often,
        these are contact center solution nodes that generate real-
        time data that is ultimately used for creating reports.

        Reporting connection table objects include objects that
        identify the reporting connection, the current state of that
        connection and a set of metrics and attributes that offer an
        indication of the connection health and performance.  A
        single LiveData server may have multiple reporting
        connections, each to a different peer node and/or to multiple
        data sources from a single node.

        The SNMP agent constructs the reporting connection table at
        startup; the agent refreshes this table periodically during
        runtime when each LiveData service reports connection states.

        Reporting connection table entries cannot be added to or
        deleted from the table by the management station.  All
        objects in this table are read-only."
    ::= { cldReportingConnections 1 }

cldReportingConnectionEntry OBJECT-TYPE
    SYNTAX          CldReportingConnectionEntry
    MAX-ACCESS      not-accessible
    STATUS          current
    DESCRIPTION
        "Each reporting connection entry represents a Cisco LiveData
        reporting connection.  The LiveData application connects to a
        number of data sources, each of which sends real-time data
        as a stream to the LiveData server."
    INDEX           { cldRptConnIndex }
    ::= { cldReportingConnectionTable 1 }

CldReportingConnectionEntry ::= SEQUENCE {
        cldRptConnIndex             CldIndex,
        cldRptConnServerID          SnmpAdminString,
        cldRptConnServerAddress     SnmpAdminString,
        cldRptConnState             INTEGER,
        cldRptConnStateTime         DateAndTime,
        cldRptConnEventRate         Gauge32,
        cldRptConnHeartbeatRTT      Gauge32,
        cldRptConnSocketConnects    Counter32,
        cldRptConnSocketDisconnects Counter32,
        cldRptConnMessagesDiscarded Counter32,
        cldRptConnDSCP              Integer32
}

cldRptConnIndex OBJECT-TYPE
    SYNTAX          CldIndex
    MAX-ACCESS      not-accessible
    STATUS          current
    DESCRIPTION
        "The reporting connection index is a value that uniquely
        identifies an entry in the reporting connection table.
        This value is arbitrarily assigned by the SNMP agent."
    ::= { cldReportingConnectionEntry 1 }

cldRptConnServerID OBJECT-TYPE
    SYNTAX          SnmpAdminString
    MAX-ACCESS      read-only
    STATUS          current
    DESCRIPTION
        "This object indicates a user-intuitive textual
        identification for the Cisco LiveData connection; this is
        indicative of the source of the real-time data streamed via
        this reporting connection."
    ::= { cldReportingConnectionEntry 2 }

cldRptConnServerAddress OBJECT-TYPE
    SYNTAX          SnmpAdminString
    MAX-ACCESS      read-only
    STATUS          current
    DESCRIPTION
        "This object indicates the hostname or IP address of the peer
        node in this reporting connection."
    ::= { cldReportingConnectionEntry 3 }

cldRptConnState OBJECT-TYPE
    SYNTAX          INTEGER  {
                        inactive(1),
                        active(2)
                    }
    MAX-ACCESS      read-only
    STATUS          current
    DESCRIPTION
        "This object indicates the current state of this reporting
        connection; it is either active or inactive."
    ::= { cldReportingConnectionEntry 4 }

cldRptConnStateTime OBJECT-TYPE
    SYNTAX          DateAndTime
    MAX-ACCESS      read-only
    STATUS          current
    DESCRIPTION
        "This object indicates the date and time that this reporting
        connection transitioned into its current state."
    ::= { cldReportingConnectionEntry 5 }

cldRptConnEventRate OBJECT-TYPE
    SYNTAX          Gauge32
    UNITS           "events"
    MAX-ACCESS      read-only
    STATUS          current
    DESCRIPTION
        "This object indicates the number of events that are arriving
        via this connection per second."
    ::= { cldReportingConnectionEntry 6 }

cldRptConnHeartbeatRTT OBJECT-TYPE
    SYNTAX          Gauge32
    UNITS           "milliseconds"
    MAX-ACCESS      read-only
    STATUS          current
    DESCRIPTION
        "This object indicates the time, in milliseconds, for
        heartbeat requests to be returned from the peer node in this
        reporting connection."
    ::= { cldReportingConnectionEntry 7 }

cldRptConnSocketConnects OBJECT-TYPE
    SYNTAX          Counter32
    MAX-ACCESS      read-only
    STATUS          current
    DESCRIPTION
        "This object indicates the number of successful socket
        connections made to the peer node in this reporting
        connection."
    ::= { cldReportingConnectionEntry 8 }

cldRptConnSocketDisconnects OBJECT-TYPE
    SYNTAX          Counter32
    MAX-ACCESS      read-only
    STATUS          current
    DESCRIPTION
        "This object indicates the number of socket disconnects with
        the peer node in this reporting connection.  This is used in
        conjunction with cldConnSocketConnects to identify unstable
        connections to a particular endpoint."
    ::= { cldReportingConnectionEntry 9 }

cldRptConnMessagesDiscarded OBJECT-TYPE
    SYNTAX          Counter32
    UNITS           "messages"
    MAX-ACCESS      read-only
    STATUS          current
    DESCRIPTION
        "This object indicates the number of messages sent by the
        peer node in this reporting connection that have been
        discarded."
    ::= { cldReportingConnectionEntry 10 }

cldRptConnDSCP OBJECT-TYPE
    SYNTAX          Integer32
    MAX-ACCESS      read-only
    STATUS          current
    DESCRIPTION
        "This object indicates the Differentiated Services (DS) value
        currently used by this reporting connection for Quality of
        Service (QoS) marking."
    ::= { cldReportingConnectionEntry 11 }


-- ******************************************************************
-- EVENT TABLE
-- ******************************************************************

cldEventTable OBJECT-TYPE
    SYNTAX          SEQUENCE OF CldEventEntry
    MAX-ACCESS      not-accessible
    STATUS          current
    DESCRIPTION
        "The event table is a list of active Cisco LiveData events.
        The SNMP agent constructs the event table at startup and it
        fills the table as events are generated.

        Events with the same cldEventID value will overwrite existing
        events in the table with the same EventID (i.e. only the most
        recent will persist).

        Event table entries cannot be added to or deleted from the
        table by the management station.  All objects in this table
        are read-only."
    ::= { cldEvents 1 }

cldEventEntry OBJECT-TYPE
    SYNTAX          CldEventEntry
    MAX-ACCESS      not-accessible
    STATUS          current
    DESCRIPTION
        "Each event entry represents a Cisco LiveData event.  The
        LiveData application software generates events when an
        unusual condition has occurred that can potentially affect
        the functioning of the Cisco LiveData server."
    INDEX           { cldEventIndex }
    ::= { cldEventTable 1 }

CldEventEntry ::= SEQUENCE {
        cldEventIndex     CldIndex,
        cldEventID        Unsigned32,
        cldEventAppName   SnmpAdminString,
        cldEventName      SnmpAdminString,
        cldEventState     INTEGER,
        cldEventSeverity  CldSeverity,
        cldEventTimestamp DateAndTime,
        cldEventText      SnmpAdminString
}

cldEventIndex OBJECT-TYPE
    SYNTAX          CldIndex
    MAX-ACCESS      not-accessible
    STATUS          current
    DESCRIPTION
        "The event index is a value that uniquely identifies an entry
        in the event table.  This value is arbitrarily assigned by
        the SNMP agent."
    ::= { cldEventEntry 1 }

cldEventID OBJECT-TYPE
    SYNTAX          Unsigned32
    MAX-ACCESS      read-only
    STATUS          current
    DESCRIPTION
        "This object indicates the unique numeric event message
        identifier that is assigned by the LiveData server to this
        event.  This identifier is unique for each different event.
        The event ID can be used to correlate 'clear' state events
                to 'raise' state events."
    ::= { cldEventEntry 2 }

cldEventAppName OBJECT-TYPE
    SYNTAX          SnmpAdminString
    MAX-ACCESS      read-only
    STATUS          current
    DESCRIPTION
        "This object indicates the service- specific name of the
        Cisco LiveData functional service that generated this event."
    ::= { cldEventEntry 3 }

cldEventName OBJECT-TYPE
    SYNTAX          SnmpAdminString
    MAX-ACCESS      read-only
    STATUS          current
    DESCRIPTION
        "This object indicates the service-specific name of the Cisco
        LiveData event message.  The object value is used to group
        similar events."
    ::= { cldEventEntry 4 }

cldEventState OBJECT-TYPE
    SYNTAX          INTEGER  {
                        raise(1),
                        clear(2)
                    }
    MAX-ACCESS      read-only
    STATUS          current
    DESCRIPTION
        "This object indicates the state (not to be confused with
        severity) of the event and potentially the current status of
        the functional component that generated the event.  The
        possible states are:

        'raise':    A raise state identifies an event received as a
                    result of a health-impacting condition, such as a
                    process failure.  A subsequent clear state event
                    will follow when the error condition is resolved.
                    A node which generates a 'raise' state event may
                    be impaired and likely requires the attention of
                    an administrator.

        'clear':    The clear state indicates that the condition
                    which generated a previous raise notification has
                    been resolved.  This may occur automatically with
                    fault-tolerant deployments or may be the result
                    of administrator intervention."
    ::= { cldEventEntry 5 }

cldEventSeverity OBJECT-TYPE
    SYNTAX          CldSeverity
    MAX-ACCESS      read-only
    STATUS          current
    DESCRIPTION
        "This object indicates the severity level of this event."
    ::= { cldEventEntry 6 }

cldEventTimestamp OBJECT-TYPE
    SYNTAX          DateAndTime
    MAX-ACCESS      read-only
    STATUS          current
    DESCRIPTION
        "This object indicates the date and time that the event was
        generated on the originating device."
    ::= { cldEventEntry 7 }

cldEventText OBJECT-TYPE
    SYNTAX          SnmpAdminString
    MAX-ACCESS      read-only
    STATUS          current
    DESCRIPTION
        "This object indicates the full text of the event which
        includes a description of the event that was generated,
        component state information and potentially a brief
        description of administrative action that may be necessary
        to correct the condition that caused the event to occur."
    ::= { cldEventEntry 8 }



-- ******************************************************************
-- NOTIFICATION OBJECT SECTION
-- ******************************************************************

cldEventNotif NOTIFICATION-TYPE
    OBJECTS         {
                        cldEventID,
                        cldServerName,
                        cldEventAppName,
                        cldEventName,
                        cldEventState,
                        cldEventSeverity,
                        cldEventTimestamp,
                        cldEventText
                    }
    STATUS          current
    DESCRIPTION
        "The SNMP entity generates cldEventNotif when an unusual
        condition has occurred that can potentially affect the
        functioning of the Cisco LiveData server.  This notification
        type describes operational state information of the service
        generating the notification when such service-impacting
        conditions occur.  A notification is sent by a functional
        service of the Cisco LiveData server.
        The notification type includes the following objects:

        'cldEventID':        The unique numeric event message
                             identifier for this event.

        'cldServerName':     The fully-qualified domain name of the
                             Cisco LiveData server that generated the
                             notification.

        'cldEventAppName':   The name of the Cisco LiveData
                             functional service that generated this
                             event.

        'cldEventName':      The service-specific name of the Cisco
                             LiveData event message.

        'cldEventState':     The state of the event, either 'raise'
                             or 'clear'.  A 'raise' state event is
                             generated when an unusual or service-
                             impacting condition occurs while a
                             'clear' state event is generated when
                             a prior condition has been resolved.

        'cldEventSeverity':  The severity level of this event; an
                             integer value from 1 (emergency) to 8
                             (debug).

        'cldEventTimestamp': The date and time that the event was
                             generated.

        'cldEventText':      The full text of the event."
   ::= { ciscoLivedataMIBNotifs 1 }

-- ******************************************************************
-- COMPLIANCE SECTION
-- ******************************************************************

ciscoLivedataMIBCompliance MODULE-COMPLIANCE
    STATUS          current
    DESCRIPTION
        "This object is the compliance statement for entities which
        implement the Cisco LiveData MIB."
    MODULE          CISCO-LIVEDATA-MIB
    MANDATORY-GROUPS {
                        cldGeneralGroup,
                        cldClusterGroup,
                        cldServicesGroup,
                        cldRptConnectionsGroup,
                        cldEventsGroup,
                        cldMIBEventGroup
                    }
    ::= { ciscoLivedataMIBCompliances 1 }

cldGeneralGroup OBJECT-GROUP
    OBJECTS         {
                        cldServerName,
                        cldDescription,
                        cldVersion,
                        cldStartTime,
                        cldTimeZoneName,
                        cldTimeZoneOffset,
                        cldEventNotifEnable
                    }
    STATUS          current
    DESCRIPTION
        "The general group defines the general Cisco LiveData
        objects.  All servers will populate these objects."
    ::= { ciscoLivedataMIBGroups 1 }

cldClusterGroup OBJECT-GROUP
    OBJECTS         {
                        cldClusterID,
                        cldClusterStatus,
                        cldClusterAddress
                    }
    STATUS          current
    DESCRIPTION
        "The cluster group defines the Cisco LiveData objects related
        to the cluster of LiveData servers. All servers will populate
        these objects."
    ::= { ciscoLivedataMIBGroups 2 }

cldServicesGroup OBJECT-GROUP
    OBJECTS         {
                        cldServiceName,
                        cldServiceState,
                        cldServiceUpTime
                    }
    STATUS          current
    DESCRIPTION
        "The services group defines the Cisco LiveData service table
        objects.  All servers will populate these objects, however,
        the number of entries in the table will vary across servers
        and the types of services will vary as well."
    ::= { ciscoLivedataMIBGroups 3 }

cldRptConnectionsGroup OBJECT-GROUP
    OBJECTS         {
                        cldRptConnServerID,
                        cldRptConnServerAddress,
                        cldRptConnState,
                        cldRptConnStateTime,
                        cldRptConnEventRate,
                        cldRptConnHeartbeatRTT,
                        cldRptConnSocketConnects,
                        cldRptConnSocketDisconnects,
                        cldRptConnMessagesDiscarded,
                        cldRptConnDSCP
                    }
    STATUS          current
    DESCRIPTION
        "The reporting connections group defines the Cisco LiveData
        connection table objects.  All servers will populate these
        objects, however, the number of entries in the table will
        vary across servers."
    ::= { ciscoLivedataMIBGroups 4 }

cldEventsGroup OBJECT-GROUP
    OBJECTS         {
                        cldEventID,
                        cldEventAppName,
                        cldEventName,
                        cldEventState,
                        cldEventSeverity,
                        cldEventTimestamp,
                        cldEventText
                    }
    STATUS          current
    DESCRIPTION
        "The events group defines the Cisco LiveData event table
        objects.  All servers will populate these objects, however,
        the number of entries in the table will vary across servers."
    ::= { ciscoLivedataMIBGroups 5 }

cldMIBEventGroup NOTIFICATION-GROUP
   NOTIFICATIONS    { cldEventNotif }
    STATUS          current
    DESCRIPTION
        "This group defines the notification types defined in this
        MIB."
    ::= { ciscoLivedataMIBGroups 6 }

END
