-- *****************************************************************
-- AWCVX-MIB.my: Cisco Aironet Wireless LAN Access Point MIB file
--
-- October 2002, Victor Griswold
--
-- Copyright (c) 2002-2003 by Cisco Systems, Inc.
-- All rights reserved.
-- *****************************************************************
--
-- ********************************************************************
-- * awcVx Management Information Base
-- ********************************************************************

AWCVX-MIB DEFINITIONS ::= BEGIN

IMPORTS
	MODULE-IDENTITY,
	OBJECT-TYPE,
	NOTIFICATION-TYPE,
	enterprises,
	Integer32,
	Counter32,
	IpAddress,
	Unsigned32
		FROM SNMPv2-SMI
	dot1dTpPort
		FROM BRIDGE-MIB
	MODULE-COMPLIANCE,
        NOTIFICATION-GROUP,
	OBJECT-GROUP
		FROM SNMPv2-CONF
	TEXTUAL-CONVENTION,
	DisplayString,
	RowStatus,
	MacAddress,
	TruthValue
		FROM SNMPv2-TC
	ifIndex
		FROM RFC1213-MIB;


-- ********************************************************************
-- *  MODULE IDENTITY
-- ********************************************************************
awcVx MODULE-IDENTITY
	LAST-UPDATED	"200304210000Z"
       	ORGANIZATION	"Cisco Systems, Inc."
	CONTACT-INFO
		"       Cisco Systems
			Customer Service

		Postal: 170 W Tasman Drive
			San Jose, CA  95134
			USA

		   Tel: +1 800 553-NETS

		E-mail: cs-aironet@cisco.com"
	DESCRIPTION
                  "The MIB module for Aironet entities.
                  iso(1).org(3).dod(6).internet(1).private(4).
                  enterprises(1).aironet(522).awcVx(3).

                  This MIB provides network management
                  support for Cisco IEEE 802.11 Wireless LAN
                  type devices such as Access Point and Wireless
                  Access Bridge."

        REVISION        "200304210000Z"
        DESCRIPTION
                "Added awcDot11NonRootMobility to determine if a
                radio should look for a better parent AP in heavy
                traffic and awcFtEnableMcastMapping for multicast
                forwarding configuration."
        REVISION        "200212030000Z"
        DESCRIPTION
                "This revision adds awcDot11QoSTable QoS support,
                awcIfOutDiscardsCoSx statistics to awcIfTable,
                awcPolGrpTable policy group, 802.11A 5GHz radio
                support, and action when Ethernet is lost.  Corrected
                the ranges for awcDot11AuthenticationAlgorithmsIndex
                and awcPolGrpId."
        ::= { enterprises 522 3 }

aironet		OBJECT IDENTIFIER ::= { enterprises 522 }

-- ********************************************************************
-- *  Major sections
-- ********************************************************************
--  Aironet Wireless Communications System (awcSystem) Attributes
--          DEFINED AS "The awcSystem object class provides all
--          standard information to support operation of an Aironet
--          Access Point such as versions, system flags, and what
--          features are enabled.";

        awcSystem OBJECT IDENTIFIER ::=         {awcVx 1}

--  bootconfig VxWorks (bootconfigVx) Attributes
--          DEFINED AS "The bootconfigVx object class provides all
--          standard information to support operation of the boot
--          server.";

        bootconfigVx OBJECT IDENTIFIER ::=        {awcVx 2}

--  Aironet Wireless Communication Serial Device (awcSerialDev)
--          Attributes DEFINED AS "The awcSerialDev object class
--          provides all standard information to support configuration
--          of serial ports.";

        awcSerialDev OBJECT IDENTIFIER ::=        {awcVx 3}

--  Aironet Wireless Communication FTP (awcFtp) Attributes
--          DEFINED AS "The awcFTP object class provides all standard
--          information to support configuration of the FTP protocol.";

        awcFtp OBJECT IDENTIFIER ::=               {awcVx 4}

--  Aironet Wireless Communication 802.11 (awc802dot11) Attributes
--          DEFINED AS "The awc802dot11 object class provides all
--          standard information to support configuration of the 802.11
--          protocol. This class also provides various statistics of
--          802.11 stations.";

        awc802dot11 OBJECT IDENTIFIER ::=       {awcVx 6}

--  Aironet Wireless Communication UserManager (awcUserMgr) Attributes
--          DEFINED AS "The awcUserMgr object class provides all
--          standard information to support configuration of the User
--          Manager.";

        awcUserMgr OBJECT IDENTIFIER ::=           {awcVx 7}

--  Aironet Wireless Communication HTTPd (awcHttpd) Attributes
--          DEFINED AS "The awcHttpd object class provides all standard
--          information to support configuration of the Web Server.";

        awcHttpd OBJECT IDENTIFIER ::=           {awcVx 8}

--  Aironet Wireless Communication DNS Resolver (awcDnsRes) Attributes
--          DEFINED AS "The awcDnsRes object class provides all
--          standard information to support configuration of the DNS
--          Resolver.";

        awcDnsRes OBJECT IDENTIFIER ::=           {awcVx 9}

--  Aironet Wireless Communication SNMP (awcSnmp) Attributes
--          DEFINED AS "The awcSnmp object class provides all standard
--          information to support configuration of the SNMP
--          protocol.";

        awcSnmp OBJECT IDENTIFIER ::=           {awcVx 10}

--  Aironet Wireless Communication SNTP (awcSntp) Attributes
--          DEFINED AS "The awcSntp object class provides all standard
--          information to support configuration of the SNTP
--          protocol.";

        awcSntp OBJECT IDENTIFIER ::=           {awcVx 11}

--  Aironet Wireless Communication Forwarding Table (awcForwardTbl)
--          Attributes
--          DEFINED AS "The awcForwardTbl object class provides all
--          standard information to support configuration of the
--          Forwarding Table.";

        awcForwardTbl OBJECT IDENTIFIER ::=     {awcVx 12}

--  Aironet Wireless Communication RIP (awcRipConfig) Attributes
--          DEFINED AS "The awcRipConfig object class provides all
--          standard information to support configuration of the RIP
--          Protocol.";

        awcRipConfig OBJECT IDENTIFIER ::=      {awcVx 13}

--  Aironet Wireless Communications Event Log (awcEventLog) Attributes
--          DEFINED AS "The awcEventLog object class provides all
--          standard information to support operation of the Event
--          Log.";

        awcEventLog OBJECT IDENTIFIER ::=       {awcVx 14}

--  Aironet Wireless Communications Ethernet Controller (awcEtherMIB)
--          Attributes
--          DEFINED AS "The awcEtherMIB object class provides all
--          standard information to support operation of the Ethernet
--          Controller.";

        awcEtherMIB OBJECT IDENTIFIER ::=       {awcVx 15}

--  Aironet Wireless Communications Policy Groups (awcPolicyGroups)
--          Attributes
--          DEFINED AS "The awcPolicyGroups object class provides all
--          standard information to support specification of named
--          groups of related protocol filters.";

        awcPolicyGroups OBJECT IDENTIFIER ::=       {awcVx 16}

--  Aironet Wireless Communications DDP/IAPP (awcDdpIAPP) Attributes
--          DEFINED AS "The awcDdpIAPP object class provides all
--          standard information to support operation of the DDP and
--          IAPP protocols.";

        awcDdpIAPP OBJECT IDENTIFIER ::=       {awcVx 17}

--  Aironet Wireless Communications Hot Standby (awcHotStandby)
--          Attributes
--          DEFINED AS "The awcHotStandby object class provides all
--          standard information to support operation of an AP in the
--          Hot Standby mode.";

        awcHotStandby OBJECT IDENTIFIER ::=       {awcVx 18}

--  Aironet Wireless Communications Authentication, Authorization, and
--          Accounting (awcAaa) Attributes .
--          DEFINED AS "The awcAaa object class provides all standard
--          information to support configuration of RADIUS and TACACS+
--          client operation.";

        awcAaa OBJECT IDENTIFIER ::=       {awcVx 19}

--  Aironet Wireless Communications Authentication, Authorization, and
--			Accounting (awcAaa)'s accounting configuration
--			DEFINED AS "The awcAcctConfig object provides all the
--			configuration for accounting.";

		awcAcctConfig OBJECT IDENTIFIER ::= { awcAaa 3 }

--  Aironet Wireless Communications Protocol Filters
--          (awcProtocolFilters) Attributes
--          DEFINED AS "The awcProtocolFilters object class provides
--          all standard information to support configuration of static
--          protocol filters on the AP.";

        awcProtocolFilters OBJECT IDENTIFIER ::=       {awcVx 20}

--  Aironet Wireless Communications Mobile IP
--          (awcMobileIP) Attributes
--          DEFINED AS "The awcMobileIP object class provides
--          all standard information to support configuration of proxy
--          mobileIP on the AP.";

        awcMobileIP OBJECT IDENTIFIER ::=       {awcVx 22}

--  Aironet Wireless Communications Experimental (awcExperimental)
--          Attributes
--          DEFINED AS "The awcExperimental object class provides all
--          standard information to support experimental functions.";

--        awcExperimental OBJECT IDENTIFIER ::=   {awcVx 99}

-- ********************************************************************
-- *  MIB attribute OBJECT-TYPE definitions follow
-- ********************************************************************

AwcVlanId ::= TEXTUAL-CONVENTION
	STATUS      current
	DESCRIPTION
		"A 12-bit VLAN ID used in the VLAN Tag header. A value
		of 0 indicates NULL or no VLAN ID."
	SYNTAX      INTEGER (0..4094)

AwcPolId ::= TEXTUAL-CONVENTION
	STATUS      current
	DESCRIPTION
		"A 10-bit Policy Group identifier. A value
		of 0 indicates that no Policy Group is specified."
	SYNTAX      INTEGER (0..1023)

WEPKeytype128 ::= TEXTUAL-CONVENTION
        STATUS       current
        DESCRIPTION
                "Wired Equivalent Privacy (WEP) shared secret
                encryption key, 128-bits."
        SYNTAX       OCTET STRING (SIZE (5..13))

AwcInvokeCommand ::= TEXTUAL-CONVENTION
        STATUS       current
        DESCRIPTION
                "Command directive to control asynchronous operations
                on the host system of the SNMP agent.  Not all
                asynchronous operations support all directives.  For
                example, not all operations support 'restart' or
                'restartNotify' commands.

                    inactive  -  No operation is either started or
                                 in progress.
                    start     -  Start the operation.  Perform the
                                 operation to completion.
                    startNotify  -  Start the operation.  Perform the
                                    operation to completion, then
                                    notify the requesting SNMP Manager
                                    via a Trap.
                    restart   -  If the operation is not already
                                 started, start it.  If it is already
                                 started, re-initialize the operation
                                 in a graceful manner and start it
                                 over again.  Do not alter the Notify
                                 option of the corresponding Start
                                 command.
                    restartNotify - If the operation is not already
                                    started, start it.  If it is
                                    already started, re-initialize the
                                    operation in a graceful manner and
                                    start it over again.  When the
                                    operation is complete, notify the
                                    requesting SNMP Manager via a Trap.
                    cancel    -  If the operation, is not started, do
                                 nothing.  If it is started, stop the
                                 operation gracefully.  Notify the SNMP
                                 Manager via a Trap in accordance with
                                 whether {Re}Start or {Re}StartNotify
                                 was used.

                Multiple use of 'start' before an operation completes
                is ignored.  Multiple use of 'startNotify' before an
                operation completes adds the Notify option of the
                operation."
        SYNTAX       INTEGER { inactive(1),
                               start(2),
                               startNotify(3),
                               restart(4),
                               restartNotify(5),
                               cancel(6) }


AwcDot11MicAlgorithm ::= TEXTUAL-CONVENTION
        STATUS       current
        DESCRIPTION
                "Auxiliary Message Integrity Check (MIC) calculated
                on WEP-encoded packets to validate that they have
                not been modified.  This is in addition to the
                standard 802.11 ICV."
        SYNTAX       INTEGER { micNone(1),
                               micMMH(2) }


AwcDot11WEPKeyPermuteAlgorithm ::= TEXTUAL-CONVENTION
        STATUS       current
        DESCRIPTION
                "Function through which the WEP encryption key is
                permuted between key renewal periods."
        SYNTAX       INTEGER { wepPermuteNone(1),
                               wepPermuteIV(2) }


AwcEventDisposition ::= TEXTUAL-CONVENTION
        STATUS       current
        DESCRIPTION
                "Specifies the manner in which an event should be
                handled by the system.  Events can be counted,
                displayed on the console, recorded in the system's
                event log memory, or an external device can be
                notified of the event.  Each degree of handling
                implies all lower degrees."
        SYNTAX       INTEGER { count(1),
                               displayConsole(2),
                               record(3),
                               notify(4) }


AwcDot11EventDisposition ::= TEXTUAL-CONVENTION
  STATUS       current
  DESCRIPTION
          "Specifies options to handled standard IEEE 802.11 traps
           on this system"
  SYNTAX       INTEGER { noNotification(1),
                         eventLogOnly(2),
                         ieeeTrapOnly(3),
                         eventLogAndIeeeTrap(4) }


AwcHotStandbyStatus ::= TEXTUAL-CONVENTION
        STATUS       current
        DESCRIPTION
                "The status of the hot standby access point:
                    normal(0)          - AP hot standby is running.
                    initializing(1)    - AP hot standby is
                                         being initialized.
                    takeover(2)        - AP takeovers as new
                                         active access point.
                    stopped(3)         - AP hot standby stopped.
                    associating(4)     - Standby AP associates to
                                         active access point.
                    rootMacFailed(5)   - Cannot detect root AP
                                         MAC address.
                    interfaceMerge(6)  - Interface merge.
                    associationFail(7) - Association failed.
                    etherTestFail(8)   - Hot standby test on
                                         Ethernet failed.
                    radioTestFail(9)   - Hot standby test on
                                         radio failed.
                    error(10)          - Hot standby system error."
        SYNTAX       INTEGER { normal(0),
                               initializing(1),
                               takeover(2),
                               stopped(3),
                               associating(4),
                               rootMacFailed(5),
                               interfaceMerge(6),
                               associationFail(7),
                               etherTestFail(8),
                               radioTestFail(9),
                               error(10) }


-- ********************************************************************
-- *  awcSystem parameters
-- ********************************************************************
vxWorksVersion OBJECT-TYPE
                SYNTAX DisplayString (SIZE(0..128))
                MAX-ACCESS read-only
                STATUS current
                DESCRIPTION
                        "The version of the underlying VxWorks
                         operating system."
        ::= {  awcSystem 1 }

creationDate OBJECT-TYPE
                SYNTAX DisplayString (SIZE(0..128))
                MAX-ACCESS read-only
                STATUS current
                DESCRIPTION
                        "The date and time the Access Point system code
                         was initially compiled."
        ::= {  awcSystem 2 }

awcVxVersion OBJECT-TYPE
                SYNTAX DisplayString (SIZE(0..128))
                MAX-ACCESS read-only
                STATUS current
                DESCRIPTION
                        "The version of the Access Point system code."
        ::= {  awcSystem 3 }

sysFlags OBJECT-TYPE
                SYNTAX Unsigned32
                MAX-ACCESS read-write
                STATUS current
                DESCRIPTION
                        "The VxWorks sysFlags system-configuration
                         flags in use by the Access Point system.  Not
                         used by system code with awcVxVersion from
                         10.00 to 11.06."
                DEFVAL { 192 }
        ::= {  awcSystem 4 }

languageCode OBJECT-TYPE
                SYNTAX DisplayString (SIZE(0..128))
                MAX-ACCESS read-write
                STATUS current
                DESCRIPTION
                        "The language currently in use by the system.
                         Max. string length is 128 octets."
                DEFVAL { "en-US" }
        ::= {  awcSystem 5 }

awcDevID OBJECT-TYPE
                SYNTAX Unsigned32
                MAX-ACCESS read-only
                STATUS current
                DESCRIPTION
                        "The Aironet DDP protocol device ID of the
                         system when using the full capabilities
                         with which the system is licensed.  Note
                         that a system may be configured to use
                         fewer capabilities that those for which
                         it is licensed.  For example, a Bridge
                         may be configured for use as an Access Point."
        ::= {  awcSystem 6 }

awcDevIDtxt OBJECT-TYPE
                SYNTAX DisplayString (SIZE(0..128))
                MAX-ACCESS read-only
                STATUS current
                DESCRIPTION
                        "Textual representation of awcDevID.
                         Max. string length is 128 octets."
        ::= {  awcSystem 7 }

enableHTTP OBJECT-TYPE
                SYNTAX TruthValue
                MAX-ACCESS read-write
                STATUS current
                DESCRIPTION
                        "If true, the Access Point's HTTP server
                         can accept connections from other network
                         devices.  If false, the Access Point's HTTP
                         server will only accept connections from the
                         Access Point's console or indirectly over
                         TELNET."
                DEFVAL { true }
        ::= {  awcSystem 8 }

enableTelnet OBJECT-TYPE
                SYNTAX TruthValue
                MAX-ACCESS read-write
                STATUS current
                DESCRIPTION
                        "If true, the Access Point's TELNET server
                         can accept connections from other network
                         devices.  If false, all TELNET connections
                         will be refused."
                DEFVAL { true }
        ::= {  awcSystem 9 }

enableSNMP OBJECT-TYPE
                SYNTAX TruthValue
                MAX-ACCESS read-write
                STATUS current
                DESCRIPTION
                        "If true, the Access Point's SNMP agent can
                         accept connections from other network
                         devices.  If false, all SNMP connections
                         will be refused.  Note that this can only
                         be set to false by an SNMP management
                         station.  If false, it can only be set to true
                         by non-SNMP means."
                DEFVAL { false }
        ::= {  awcSystem 10 }

enableDnsResolver OBJECT-TYPE
                SYNTAX TruthValue
                MAX-ACCESS read-write
                STATUS current
                DESCRIPTION
                        "If true, the Access Point will attempt to
                         resolve IP address references through all
                         configured DNS servers and will attempt to
                         perform reverse-lookup via all configured
                         DNS servers when displaying IP addresses.
                         If false, the Access Point will interpret
                         and display only explicit numeric IP
                         addresses."
                DEFVAL { true }
        ::= {  awcSystem 11 }

enableSNTP OBJECT-TYPE
                SYNTAX TruthValue
                MAX-ACCESS read-write
                STATUS current
                DESCRIPTION
                        "If true, the Access Point will attempt to
                         periodically update its wall-clock time via a
                         configured SNTP server.  If false, the Access
                         Point wall-clock time must be manually
                         adjusted."
                DEFVAL { false }
        ::= {  awcSystem 13 }

enableWDB OBJECT-TYPE
                SYNTAX TruthValue
                MAX-ACCESS read-write
                STATUS current
                DESCRIPTION
                        "If true, the Access Point will enable use of
                         the VxWorks WDB debugger upon its next reboot.
                         If false, no WDB debugging services will be
                         available after the next reboot.  The value
                         of enableWDB is applicable only to special
                         diagnostic versions of the Access Point
                         system code."
                DEFVAL { false }
        ::= {  awcSystem 14 }

pingTxLen OBJECT-TYPE
                SYNTAX Unsigned32 (12..4096)
                MAX-ACCESS read-write
                STATUS current
                DESCRIPTION
                        "The size in octets of ping packets transmitted
                         by the Access Point.  Default 64."
                DEFVAL { 64 }
        ::= {  awcSystem 15 }

awcFirstBoot OBJECT-TYPE
                SYNTAX TruthValue
                MAX-ACCESS read-write
                STATUS current
                DESCRIPTION
                        "If true, no user-specified configuration has
                         been saved by the Access Point since either
                         the system left Cisco manufacturing or since
                         the user performed a Reset All System Factory
                         Defaults operation.  If false, a change in
                         configuration has been saved by the user.
                         Note that configurations specified solely via
                         boot protocols such as DHCP or BOOTP are not
                         considered user-specified for purposes of
                         changing awcFirstBoot."
                DEFVAL { true }
        ::= {  awcSystem 16 }

awcOemOUI OBJECT-TYPE
                SYNTAX MacAddress
                MAX-ACCESS read-only
                STATUS current
                DESCRIPTION
                        "The IEEE Organizationally Unique Identifier of
                         the reseller for which this system is
                         branded."
        ::= {  awcSystem 17 }

awcOemName OBJECT-TYPE
                SYNTAX DisplayString (SIZE(0..128))
                MAX-ACCESS read-only
                STATUS current
                DESCRIPTION
                        "The full name of the reseller for which this
                         system is branded."
        ::= {  awcSystem 18 }

awcOemNameShort OBJECT-TYPE
                SYNTAX DisplayString (SIZE(0..128))
                MAX-ACCESS read-only
                STATUS current
                DESCRIPTION
                        "An abbreviated name of the reseller for which
                         this system is branded."
        ::= {  awcSystem 19 }

awcOemHomeURL OBJECT-TYPE
                SYNTAX DisplayString (SIZE(0..128))
                MAX-ACCESS read-only
                STATUS current
                DESCRIPTION
                        "The URL of the corporate HTML home page of the
                         reseller for which this system is branded."
        ::= {  awcSystem 20 }

enablePSPF OBJECT-TYPE
                SYNTAX TruthValue
                MAX-ACCESS read-write
                STATUS current
                DESCRIPTION
                        "If true, Publicly-Secure Packet Forwarding
                         mode is enabled (i.e. clients can not
                         communicate with each other).  If false,
                         normal packet forwarding is used."
                DEFVAL { false }
        ::= {  awcSystem 21 }

sysExceptionReboot OBJECT-TYPE
                SYNTAX TruthValue
                MAX-ACCESS read-write
                STATUS current
                DESCRIPTION
                        "If true, all access violations or other
                         general faults in any task will result in a
                         reboot of the system.  If false, such errors
                         will not result in a reboot, and thus
                         diagnostics can be performed on the system."
                DEFVAL { true }
        ::= {  awcSystem 24 }

bootblockVersion OBJECT-TYPE
                SYNTAX DisplayString (SIZE(0..128))
                MAX-ACCESS read-only
                STATUS current
                DESCRIPTION
                        "The version of the Access Point boot block
                         (bootstrap loader) code."
        ::= {  awcSystem 25 }

motherboardRevision OBJECT-TYPE
                SYNTAX Unsigned32
                MAX-ACCESS read-only
                STATUS current
                DESCRIPTION
                        "Revision number of the Access Point
                         system motherboard."
        ::= {  awcSystem 26 }

enableSTP OBJECT-TYPE
                SYNTAX TruthValue
                MAX-ACCESS read-write
                STATUS current
                DESCRIPTION
                        "If true and the system is licensed with Bridge
                         capabilities, the IEEE 802.1D Spanning Tree
                         Protocol will be be used to control packet
                         forwarding on all network interfaces.  If
                         false or the system is not licensed with
                         Bridge capabilities, the system will use
                         Access Point heuristics to control packet
                         forwarding on all network interfaces."
        ::= {  awcSystem 27 }

enableRebootKey OBJECT-TYPE
                SYNTAX TruthValue
                MAX-ACCESS read-write
                STATUS current
                DESCRIPTION
                        "If true, the VxWorks Monitor Trap keystroke
                         is enabled from the console and from Telnet.
                         By default, this is <control-X>.  Entering
                         this character initiates a warm-restart of
                         the system.  If false, the VxWorks Monitor
                         Trap keystroke is disabled."
                DEFVAL { false }
        ::= {  awcSystem 28 }

awcLocateUnit OBJECT-TYPE
                SYNTAX TruthValue
                MAX-ACCESS read-write
                STATUS current
                DESCRIPTION
                        "If true, the unit will immediately begin
                         flashing all three of its Status LEDs with
                         an alternating pattern of amber and off.
                         If false, the Status LEDs operate in their
                         normal fashion."
                DEFVAL { false }
        ::= {  awcSystem 29 }


-- ********************************************************************
-- *    End of awcSystem parameters
-- ********************************************************************


-- ********************************************************************
-- *  bootconfigVx parameters
-- ********************************************************************
bootconfigBootProtocol OBJECT-TYPE
                SYNTAX INTEGER {none(1), bootp(2), dhcp(3)}
                MAX-ACCESS read-write
                STATUS current
                DESCRIPTION
                        "The protocol to be used for automatic
                         configuration at the time of system
                         bootstrap/reboot.  Options BOOTP, DHCP,
                         or none."
                DEFVAL { dhcp }
        ::= {  bootconfigVx 1 }

bootconfigReadINI OBJECT-TYPE
                SYNTAX INTEGER {always(1), never(2), ifSpecified(3)}
                MAX-ACCESS read-write
                STATUS current
                DESCRIPTION
                        "If always, the system will attempt to read a
                         .ini-formatted configuration file upon every
                         reboot.  If never, the system will not attempt
                         to read a .ini file upon reboot, even if a
                         boot protocol is in use and the boot server
                         specifies a file to be read.  If ifSpecified,
                         the system will attempt to read a .ini file
                         upon reboot if and only if a boot protocol
                         is in use and the boot server explicitly
                         specifies a file to be read.  The system
                         attempts several filenames in the process of
                         retrieving a .ini file without error.  In
                         order, these filenames are based on the
                         system's BOOTP- or DHCP-assigned client name,
                         then the MIB2 sysName, then the system's IP
                         address, then, as a last resort, the BOOTP- or
                         DHCP-assigned boot file name.  For each
                         filename, the system attempts to read first
                         from the designated defaultFileServer, then,
                         if not successful, from one of either the
                         BOOTP/DHCP server itself or
                         bootconfigFileServerAddr (if specified by the
                         BOOTP/DHCP server)."
                DEFVAL { ifSpecified }
        ::= {  bootconfigVx 2 }

bootconfigServerConfigTimeout OBJECT-TYPE
                SYNTAX Unsigned32
                UNITS "seconds"
                MAX-ACCESS read-write
                STATUS current
                DESCRIPTION
                        "The time in seconds which the system should
                         wait for a configuration response from a
                         BOOTP server before falling back to the
                         stored configuration."
                DEFVAL { 120 }
        ::= {  bootconfigVx 3 }

bootconfigMultOfferTimeout OBJECT-TYPE
                SYNTAX Unsigned32
                UNITS "seconds"
                MAX-ACCESS read-write
                STATUS current
                DESCRIPTION
                        "The time, in seconds, which the system should
                         wait for a better offer configuration response
                         from a DHCP or BOOTP server before choosing
                         the best current offer."
                DEFVAL { 5 }
        ::= {  bootconfigVx 4 }

bootconfigReqLeaseDuration OBJECT-TYPE
                SYNTAX Unsigned32
                UNITS "minutes"
                MAX-ACCESS read-write
                STATUS current
                DESCRIPTION
                        "The requested DHCP lease duration, in
                         minutes."
                DEFVAL { 1440 }
        ::= {  bootconfigVx 5 }

bootconfigMinLeaseDuration OBJECT-TYPE
                SYNTAX Unsigned32
                UNITS "minutes"
                MAX-ACCESS read-write
                STATUS current
                DESCRIPTION
                        "The minimum acceptable DHCP lease duration,
                         in minutes."
                DEFVAL { 0 }
        ::= {  bootconfigVx 6 }

bootconfigDev OBJECT-TYPE
                SYNTAX DisplayString (SIZE(0..128))
                MAX-ACCESS read-write
                STATUS current
                DESCRIPTION
                        "Text string identifying the network device
                         used for bootstrapping the system via BOOTP or
                         DHCP.  This is only applicable in BOOTP mode
                         or when the system is configured as a router,
                         when not all the network interfaces share the
                         same ifPhysAddress."
        ::= {  bootconfigVx 7 }

bootconfigClientAddr OBJECT-TYPE
                SYNTAX IpAddress
                MAX-ACCESS read-only
                STATUS current
                DESCRIPTION
                        "IPv4 network address of this device, as
                         determined by the BOOTP or DHCP protocol."
        ::= {  bootconfigVx 8 }

bootconfigHostAddr OBJECT-TYPE
                SYNTAX IpAddress
                MAX-ACCESS read-only
                STATUS current
                DESCRIPTION
                        "IPv4 network address of the BOOTP or DHCP
                         server from which the configuration
                         of this device was leased."
        ::= {  bootconfigVx 9 }

bootconfigBootFile OBJECT-TYPE
                SYNTAX DisplayString (SIZE(0..128))
                MAX-ACCESS read-only
                STATUS current
                DESCRIPTION
                        "Name of the default boot configuration file,
                         specified by the BOOTP or DHCP server,
                         containing the system configuration to be
                         utilized by this device.  This is considered
                         a default configuration file because many
                         DHCP servers are not capable of distinguishing
                         boot files between different clients."
        ::= {  bootconfigVx 10 }

bootconfigSubnetMask OBJECT-TYPE
                SYNTAX IpAddress
                MAX-ACCESS read-only
                STATUS current
                DESCRIPTION
                        "IPv4 network subnet mask to be used by this
                         device, as determined by the BOOTP or DHCP
                         protocol."
        ::= {  bootconfigVx 11 }

bootconfigGateway OBJECT-TYPE
                SYNTAX IpAddress
                MAX-ACCESS read-only
                STATUS current
                DESCRIPTION
                        "IPv4 network address of the default network
                         gateway to be used by this device, as
                         determined by the BOOTP or DHCP protocol."
        ::= {  bootconfigVx 12 }

bootconfigHostName OBJECT-TYPE
                SYNTAX DisplayString (SIZE(0..128))
                MAX-ACCESS read-only
                STATUS current
                DESCRIPTION
                        "Textual name of the BOOTP or DHCP server from
                         which the configuration of this device was
                         leased.  This should be a DNS-recognizable
                         host name."
        ::= {  bootconfigVx 13 }

bootconfigClientName OBJECT-TYPE
                SYNTAX DisplayString (SIZE(0..128))
                MAX-ACCESS read-only
                STATUS current
                DESCRIPTION
                        "Textual name of this device, as determined by
                         the BOOTP or DHCP protocol.  This should be a
                         DNS-recognizable host name."
        ::= {  bootconfigVx 14 }

bootconfigNameServerTable OBJECT-TYPE
            SYNTAX SEQUENCE OF BootconfigNameServerEntry
            MAX-ACCESS not-accessible
            STATUS current
            DESCRIPTION
                    "Table of DNS Name Servers provided by the
                     bootconfigHostAddr Boot Server."
        ::= { bootconfigVx 15 }

bootconfigNameServerEntry OBJECT-TYPE
            SYNTAX BootconfigNameServerEntry
            MAX-ACCESS not-accessible
            STATUS current
            DESCRIPTION
                    "An entry in bootconfigNameServerTable."
            INDEX {bootconfigNameServerPriority}
        ::= { bootconfigNameServerTable 1 }

BootconfigNameServerEntry ::=
        SEQUENCE {
            bootconfigNameServerPriority                INTEGER,
            bootconfigNameServer                        IpAddress}

bootconfigNameServerPriority OBJECT-TYPE
                SYNTAX INTEGER (1..3)
                MAX-ACCESS read-only
                STATUS current
                DESCRIPTION
                        "The priority order in which a domain name
                         server is queried.  Lower values are queried
                         first."
        ::= {  bootconfigNameServerEntry 1 }

bootconfigNameServer OBJECT-TYPE
                SYNTAX IpAddress
                MAX-ACCESS read-only
                STATUS current
                DESCRIPTION
                        "The IPv4 address of a domain name server."
        ::= {  bootconfigNameServerEntry 2 }

bootconfigDomainName OBJECT-TYPE
                SYNTAX DisplayString (SIZE(0..128))
                MAX-ACCESS read-only
                STATUS current
                DESCRIPTION
                        "Name of the IP domain of which this device
                         is a member, as determined by the BOOTP or
                         DHCP protocol."
        ::= {  bootconfigVx 16 }

bootconfigSntpServer OBJECT-TYPE
                SYNTAX IpAddress
                MAX-ACCESS read-only
                STATUS current
                DESCRIPTION
                        "IPv4 network address of SNTP server for use
                         by this device, as determined by the BOOTP or
                         DHCP protocol."
        ::= {  bootconfigVx 17 }

bootconfigSaveServerResponse OBJECT-TYPE
                SYNTAX TruthValue
                MAX-ACCESS read-write
                STATUS current
                DESCRIPTION
                        "If true, the leased configuration from a boot
                         server is saved as the new system defaults.
                         If false, system defaults remain unchanged
                         when a new configuration is leased."
                DEFVAL { true }
        ::= {  bootconfigVx 18 }

bootconfigCmdInvokeIniLoad OBJECT-TYPE
                SYNTAX AwcInvokeCommand
                MAX-ACCESS read-write
                STATUS current
                DESCRIPTION
                         "Initiate loading of an initialization
                          script '.ini' file from the file server
                          into the system FLASH.

                          Commands recognized:  start."
        ::= {  bootconfigVx 19 }

bootconfigCmdStatusIniLoad OBJECT-TYPE
                SYNTAX Integer32
                MAX-ACCESS read-only
                STATUS current
                DESCRIPTION
                         "Status of the most recent command to load
                          an initialization script '.ini' file.
                          Possible values:
                          0  = Operation completed successfully (or
                               has not taken place).
                          2  = The '.ini' file was not found on the
                               file server.
                          12 = Insufficient memory to load the
                               '.ini' file.
                          22 = Invalid '.ini' file format.
                          35 = File format of the '.ini' file is not
                               supported.
                          68 = Operation is still in progress. Poll
                               again later.
                          72 = Operation was started, but later was
                               canceled."
           ::= {  bootconfigVx 20 }

-- bootconfigCmdInvokeIniSave OBJECT-TYPE
--                 SYNTAX AwcInvokeCommand
--                 MAX-ACCESS read-write
--                 STATUS current
--                 DESCRIPTION
--                          "Initiate saving of an initialization
--                           script '.ini' file to the file server
--                           from the system FLASH."
--         ::= {  bootconfigVx 21 }

-- bootconfigCmdStatusIniSave OBJECT-TYPE
--                 SYNTAX Integer32
--                 MAX-ACCESS read-only
--                 STATUS current
--                 DESCRIPTION
--                          "Status of the most recent command to save
--                           the initialization script '.ini' file.
--                           Possible values:
--                           0  = Operation completed successfully (or
--                                has not taken place).
--                           1  = Insufficient permission to save the
--                                file.
--                           2  = The '.ini' file was not found on the
--                                file server.
--                           22 = Invalid '.ini' file format.
--                           68 = Operation is still in progress. Poll
--                                again later.
--                           72 = Operation was started, but later was
--                                canceled."
--         ::= {  bootconfigVx 22 }

-- bootconfigDetailLevelIniSave OBJECT-TYPE
--                 SYNTAX INTEGER
--                 MAX-ACCESS read-write
--                 STATUS current
--                 DESCRIPTION
--                          "Level of detail and line formatting for
--                           the initialization script '.ini' file to
--                           be saved."
--         ::= {  bootconfigVx 23 }

bootconfigDhcpClassID OBJECT-TYPE
                SYNTAX DisplayString (SIZE(0..128))
                MAX-ACCESS read-write
                STATUS current
                DESCRIPTION
                        "Specification of the DHCP Class Identifier
                         presented by the system when requesting DHCP
                         leases."
                DEFVAL { "AP4800E" }
        ::= {  bootconfigVx 24 }

bootconfigFileServerAddr OBJECT-TYPE
                SYNTAX IpAddress
                MAX-ACCESS read-only
                STATUS current
                DESCRIPTION
                        "IPv4 network address of the file server from
                         which to read configuration files, as
                         determined by the BOOTP or DHCP protocol."
        ::= {  bootconfigVx 25 }

bootconfigLogServerAddr OBJECT-TYPE
                SYNTAX IpAddress
                MAX-ACCESS read-only
                STATUS current
                DESCRIPTION
                        "IPv4 network address of the host to receive
                         SYSLOG messages, as determined by the BOOTP
                         or DHCP protocol."
        ::= {  bootconfigVx 26 }

bootconfigBootCount OBJECT-TYPE
                SYNTAX Unsigned32
                MAX-ACCESS read-only
                STATUS current
                DESCRIPTION
                        "The number of times the system code has been
                         restarted since the system left Cisco
                         manufacturing."
        ::= {  bootconfigVx 27 }

bootconfigDhcpClientIdType OBJECT-TYPE
                SYNTAX INTEGER {
                            ethernet10Mb(1),
                            experimentalEthernet3Mb(2),
                            amateurRadioAxDot25(3),
                            proteonProNetTokenRing(4),
                            chaos(5),
                            ieee802Networks(6),
                            arcnet(7),
                            hyperchannel(8),
                            lanstar(9),
                            autonet(10),
                            localTalk(11),
                            localNet(12),
                            nonHardware(128)
                        }
                MAX-ACCESS read-write
                STATUS current
                DESCRIPTION
                        "The ARP hardware type, per RFC 1700, of
                         bootconfigDhcpClientIdValue.  If it is not
                         a hardware address (e.g. is a fully-qualified
                         domain name), a value of 0 will be used for
                         the DHCP Client Identifier 'htype' field."
        ::= {  bootconfigVx 28 }

bootconfigDhcpClientIdValue OBJECT-TYPE
                SYNTAX DisplayString (SIZE(0..128))
                MAX-ACCESS read-write
                STATUS current
                DESCRIPTION
                        "Specification of the DHCP unique client Identifier
                         presented by the system when requesting DHCP
                         leases."
        ::= {  bootconfigVx 29 }


-- ********************************************************************
-- *    End of bootconfigVx parameters
-- ********************************************************************


-- ********************************************************************
-- *  awcSerialDev parameters
-- ********************************************************************
awcSerialConfigTable OBJECT-TYPE
                SYNTAX SEQUENCE OF AwcSerialConfigEntry
                MAX-ACCESS not-accessible
                STATUS current
                DESCRIPTION
                        "SerialConfigTable attributes.  In tabular form
                         to allow for multiple instances on an agent."
        ::= {  awcSerialDev 1 }

awcSerialConfigEntry OBJECT-TYPE
                SYNTAX AwcSerialConfigEntry
                MAX-ACCESS not-accessible
                STATUS current
                DESCRIPTION
                        "An entry in the awcSerialConfigEntry table."
                INDEX {serialDevIndex}
        ::= {  awcSerialConfigTable 1 }

AwcSerialConfigEntry ::=
                SEQUENCE {
                         serialDevIndex         Integer32,
                         serialAdminStatus      INTEGER,
                         serialOperStatus       INTEGER,
                         serialBaud             Unsigned32,
                         serialParity           INTEGER,
                         serialDataBits         Unsigned32,
                         serialStopBits         Unsigned32,
                         serialFlowControl      INTEGER,
                         serialTerminalType     INTEGER,
                         serialTerminalLines    Unsigned32,
                         serialTerminalColumns  Unsigned32,
                         serialDevFd            Integer32
                         }

serialDevIndex OBJECT-TYPE
                SYNTAX Integer32 (1..2)
                MAX-ACCESS read-only
                STATUS current
                DESCRIPTION
                        "The index used to access rows in the
                         awcSerialConfig table."
        ::= {  awcSerialConfigEntry 1 }

serialAdminStatus OBJECT-TYPE
                SYNTAX INTEGER {up(1), down(2), testing(3), error(4)}
                MAX-ACCESS read-write
                STATUS current
                DESCRIPTION
                        "The requested status of the serial port."
                DEFVAL { up }
        ::= {  awcSerialConfigEntry 2 }

serialOperStatus OBJECT-TYPE
                SYNTAX INTEGER {up(1), down(2), testing(3), error(4)}
                MAX-ACCESS read-only
                STATUS current
                DESCRIPTION
                        "The actual status of the serial port."
        ::= {  awcSerialConfigEntry 3 }

serialBaud OBJECT-TYPE
                SYNTAX Unsigned32
                MAX-ACCESS read-write
                STATUS current
                DESCRIPTION
                        "The baud rate of the serial port."
                DEFVAL { 9600 }
        ::= {  awcSerialConfigEntry 4 }

serialParity OBJECT-TYPE
                SYNTAX INTEGER {none(1), even(2), odd(3), one(4),
                                zero(5)}
                MAX-ACCESS read-write
                STATUS current
                DESCRIPTION
                        "The parity of the serial port."
                DEFVAL { none }
        ::= {  awcSerialConfigEntry 5 }

serialDataBits OBJECT-TYPE
                SYNTAX Unsigned32 (7..8)
                UNITS "bits"
                MAX-ACCESS read-write
                STATUS current
                DESCRIPTION
                        "The number of data bits per character
                         recognized by the serial port."
                DEFVAL { 8 }
        ::= {  awcSerialConfigEntry 6 }

serialStopBits OBJECT-TYPE
                SYNTAX Unsigned32 (1..2)
                UNITS "bits"
                MAX-ACCESS read-write
                STATUS current
                DESCRIPTION
                        "The number of stop bits of the serial port."
                DEFVAL { 1 }
        ::= {  awcSerialConfigEntry 7 }

serialFlowControl OBJECT-TYPE
                SYNTAX INTEGER {none(1), swXonXoff(2), hwRtsCts(3),
                                swHwBoth(4)}
                MAX-ACCESS read-write
                STATUS current
                DESCRIPTION
                        "The flow control method used by the serial
                         port."
                DEFVAL { swXonXoff }
        ::= {  awcSerialConfigEntry 8 }

serialTerminalType OBJECT-TYPE
                SYNTAX INTEGER {teletype(1), ansi(2)}
                MAX-ACCESS read-write
                STATUS current
                DESCRIPTION
                        "The terminal type of the serial port."
                DEFVAL { teletype }
        ::= {  awcSerialConfigEntry 9 }

serialTerminalLines OBJECT-TYPE
                SYNTAX Unsigned32 (16..50)
                MAX-ACCESS read-write
                STATUS current
                DESCRIPTION
                        "The number of horizontal lines available on
                         each terminal page.  Default 24."
                DEFVAL { 24 }
        ::= {  awcSerialConfigEntry 10 }

serialTerminalColumns OBJECT-TYPE
                SYNTAX Unsigned32 (64..132)
                MAX-ACCESS read-write
                STATUS current
                DESCRIPTION
                        "The number of vertical columns available on
                         each terminal page. Default 80."
                DEFVAL { 80 }
        ::= {  awcSerialConfigEntry 11 }

serialDevFd OBJECT-TYPE
                SYNTAX Integer32
                MAX-ACCESS read-only
                STATUS current
                DESCRIPTION
                        "The VxWorks I/O File Descriptor used to access
                         the serial device."
        ::= {  awcSerialConfigEntry 12 }


-- ********************************************************************
-- *    End of awcSerialDev parameters
-- ********************************************************************


-- ********************************************************************
-- *  awcFtp parameters
-- ********************************************************************
defaultFileServer OBJECT-TYPE
                SYNTAX DisplayString (SIZE(0..128))
                MAX-ACCESS read-write
                STATUS current
                DESCRIPTION
                        "The name of the preferred file server to be
                         used for all FTP and TFTP Put and Get
                         operations. Max. name length is 128 octets."
                DEFVAL { "" }
        ::= {  awcFtp 1 }

awcFileXferProtocol OBJECT-TYPE
                SYNTAX INTEGER {tftp(1), ftp(2)}
                MAX-ACCESS read-write
                STATUS current
                DESCRIPTION
                        "The protocol to be used by the system for file
                         transfer (TFTP or FTP)."
                DEFVAL { ftp }
        ::= {  awcFtp 2 }

awcFileXferUser OBJECT-TYPE
                SYNTAX DisplayString (SIZE(0..128))
                MAX-ACCESS read-write
                STATUS current
                DESCRIPTION
                        "The name of the user, as required by all FTP
                         file transfers.  Max. name length is 128
                         octets."
                DEFVAL { "anonymous" }
        ::= {  awcFtp 3 }

awcFileXferPassword OBJECT-TYPE
                SYNTAX DisplayString (SIZE(0..128))
                MAX-ACCESS read-write
                STATUS current
                DESCRIPTION
                        "The password of the user, as required by all
                         FTP file transfers.  Max. password length is
                         128 octets."
                DEFVAL { "" }
        ::= {  awcFtp 4 }

awcFileXferCmdInvokeFileLoad OBJECT-TYPE
                SYNTAX AwcInvokeCommand
                MAX-ACCESS read-write
                STATUS current
                DESCRIPTION
                        "Initiate loading of all specified files
                         from the file server into the system
                         FLASH.

                         Commands recognized:  start."
        ::= {  awcFtp 5 }

awcFileXferCmdStatusFileLoad OBJECT-TYPE
                SYNTAX Integer32
                MAX-ACCESS read-only
                STATUS current
                DESCRIPTION
                         "Status of the most recent command to load
                          the specified fileXferFile* files.
                          Possible values:
                          0  = Operation completed successfully
                               (or has not taken place).
                          2  = At least one file was not found on
                               the file server.
                          12 = Insufficient memory to load all
                               files.
                          22 = No file specified, or invalid file
                               format.
                          35 = File format of at least one of the
                               files is not supported.
                          68 = Operation is still in progress.
                               Poll again later.
                          72 = Operation was started, but later was
                               canceled."
         ::= {  awcFtp 6 }

awcFileXferCmdInvokeFileSave OBJECT-TYPE
                SYNTAX AwcInvokeCommand
                MAX-ACCESS read-write
                STATUS current
                DESCRIPTION
                        "Initiate saving of all specified
                         fileXferFile* files to the file server from
                         the system FLASH.

                         Commands recognized:  start."
        ::= {  awcFtp 7 }

awcFileXferCmdStatusFileSave OBJECT-TYPE
                SYNTAX Integer32
                MAX-ACCESS read-only
                STATUS current
                DESCRIPTION
                         "Status of the most recent command to save
                          the specified fileXferFile* files.
                          Possible values:
                          0  = Operation completed successfully (or
                               has not taken place).
                          1  = Insufficient permission to save the
                               files.
                          2  = A directory specified for saving at
                               least one of the files was not found.
                          22 = No file specified, or invalid file
                               format.
                          68 = Operation is still in progress.
                               Poll again later.
                          72 = Operation was started, but later was
                               canceled."
         ::= {  awcFtp 8 }

awcFileXferFileFirmwareSystem OBJECT-TYPE
                SYNTAX DisplayString (SIZE(0..128))
                MAX-ACCESS read-write
                STATUS current
                DESCRIPTION
                        "The filename of the system firmware image.
                         Max. string length is 128 octets."
                DEFVAL { "" }
        ::= {  awcFtp 9 }

awcFileXferFileFirmwareRadio0 OBJECT-TYPE
                SYNTAX DisplayString (SIZE(0..128))
                MAX-ACCESS read-write
                STATUS current
                DESCRIPTION
                        "The filename of the radio firmware image.
                         Max. string length is 128 octets."
                DEFVAL { "" }
        ::= {  awcFtp 10 }

awcFileXferFileWebUI OBJECT-TYPE
                SYNTAX DisplayString (SIZE(0..128))
                MAX-ACCESS read-write
                STATUS current
                DESCRIPTION
                        "The filename of the system Web pages image.
                         Max. string length is 128 octets."
                DEFVAL { "" }
        ::= {  awcFtp 11 }

awcFileXferFileFpgaPcmcia OBJECT-TYPE
                SYNTAX DisplayString (SIZE(0..128))
                MAX-ACCESS read-write
                STATUS current
                DESCRIPTION
                        "The filename of the FPGA image for the PCMCIA
                         controller.  Max. string length is 128
                         octets."
                DEFVAL { "" }
        ::= {  awcFtp 12 }

awcFileXferTftpPort OBJECT-TYPE
                SYNTAX INTEGER (1..65535)
                MAX-ACCESS read-write
                STATUS current
                DESCRIPTION
                        "IP port number over which to perform TFTP
                         operations.  Default 69."
                DEFVAL { 69 }
        ::= {  awcFtp 13 }

awcFileXferFtpDirectory OBJECT-TYPE
                SYNTAX DisplayString (SIZE(0..128))
                MAX-ACCESS read-write
                STATUS current
                DESCRIPTION
                        "Directory on defaultFileServer in which files
                         are located."
                DEFVAL { "" }
        ::= {  awcFtp 14 }

-- awcFileXferFtpCtrlPort OBJECT-TYPE
--                 SYNTAX INTEGER (1..65535)
--                 MAX-ACCESS read-write
--                 STATUS current
--                 DESCRIPTION
--                         "IP port number over which to perform FTP
--                          Control operations."
--         ::= {  awcFtp 15 }

-- awcFileXferFtpDataPort OBJECT-TYPE
--                 SYNTAX INTEGER (1..65535)
--                 MAX-ACCESS read-write
--                 STATUS current
--                 DESCRIPTION
--                         "IP port number over which to perform FTP
--                          Data operations."
--         ::= {  awcFtp 16 }

awcFileXferFilesFLASH OBJECT-TYPE
                SYNTAX DisplayString (SIZE(0..128))
                MAX-ACCESS read-write
                STATUS current
                DESCRIPTION
                        "The filename of a complete FLASH firmware
                         image for the system, including all
                         non-configuration files within the system
                         FLASH file system. Max. string length is 128
                         octets."
                DEFVAL { "AP340_latest.img" }
        ::= {  awcFtp 17 }

awcFileXferFileFirmwareRadio1 OBJECT-TYPE
                SYNTAX DisplayString (SIZE(0..128))
                MAX-ACCESS read-write
                STATUS current
                DESCRIPTION
                        "The filename of the radio firmware image.
                         Max. string length is 128 octets."
                DEFVAL { "" }
        ::= {  awcFtp 18 }


-- ********************************************************************
-- *    End of awcFtp parameters
-- ********************************************************************


-- ********************************************************************
-- *  awcIfTable parameters
-- ********************************************************************
awcIfTable OBJECT-TYPE
                SYNTAX SEQUENCE OF AwcIfEntry
                MAX-ACCESS not-accessible
                STATUS current
                DESCRIPTION
                        "IfTable attributes.  In tabular form to
                         allow for multiple instances on an agent."
        ::= {  awcVx 5 }

awcIfEntry OBJECT-TYPE
                SYNTAX AwcIfEntry
                MAX-ACCESS not-accessible
                STATUS current
                DESCRIPTION
                        "An entry in the awcIfEntry table."
                INDEX {ifIndex}
        ::= {  awcIfTable 1 }

AwcIfEntry ::=
                SEQUENCE {
                         awcIfDefaultPhysAddress    MacAddress,
                         awcIfPhysAddress           MacAddress,
                         awcIfAdoptPrimaryIdentity  TruthValue,
                         awcIfDefaultIpAddress      IpAddress,
                         awcIfDefaultIpNetMask      IpAddress,
                         awcIfIpAddress             IpAddress,
                         awcIfIpNetMask             IpAddress,
                         awcIfMSDUMaxLength         Unsigned32,
                         awcIfOutDiscardsCoS0       Counter32,
                         awcIfOutDiscardsCoS1       Counter32,
                         awcIfOutDiscardsCoS2       Counter32,
                         awcIfOutDiscardsCoS3       Counter32,
                         awcIfOutDiscardsCoS4       Counter32,
                         awcIfOutDiscardsCoS5       Counter32,
                         awcIfOutDiscardsCoS6       Counter32,
                         awcIfOutDiscardsCoS7       Counter32
                         }

awcIfDefaultPhysAddress OBJECT-TYPE
                SYNTAX MacAddress
                MAX-ACCESS read-only
                STATUS current
                DESCRIPTION
                        "The default, factory-assigned MAC address of
                         the interface.  Guaranteed to be unique across
                         all IEEE 802 devices."
        ::= { awcIfEntry 1 }

awcIfPhysAddress OBJECT-TYPE
                SYNTAX MacAddress
                MAX-ACCESS read-write
                STATUS current
                DESCRIPTION
                        "The MAC address to be used by the interface.
                         If awcIfDefaultPhysAddress is to be used, this
                         is 00:00:00:00:00:00."
                DEFVAL { '000000000000'H }
        ::= { awcIfEntry 2 }

awcIfAdoptPrimaryIdentity OBJECT-TYPE
                SYNTAX TruthValue
                MAX-ACCESS read-write
                STATUS current
                DESCRIPTION
                        "If true, this interface adopts the identity of
                         bootconfigDev, the primary interface.  This
                         includes MAC address, IP address, etc.  This
                         is the conventional mode of operation when
                         operating as a transparent bridge.  If false,
                         this interface always has a unique MAC
                         address."
                DEFVAL { true }
        ::= {  awcIfEntry 3 }

awcIfDefaultIpAddress OBJECT-TYPE
                SYNTAX IpAddress
                MAX-ACCESS read-write
                STATUS current
                DESCRIPTION
                        "The default IPv4 Address of the interface.
                         If BOOTP or DHCP is enabled, this may be
                         overridden by the BOOTP or DHCP server."
                DEFVAL { '0A000001'H }
        ::= {  awcIfEntry 4 }

awcIfDefaultIpNetMask OBJECT-TYPE
                SYNTAX IpAddress
                MAX-ACCESS read-write
                STATUS current
                DESCRIPTION
                        "The default IPv4 netmask of the interface.
                         If BOOTP or DHCP is enabled, this may
                         be overridden by the BOOTP or DHCP server."
                DEFVAL { 'FFFFFF00'H }
        ::= {  awcIfEntry 5 }

awcIfIpAddress OBJECT-TYPE
                SYNTAX IpAddress
                MAX-ACCESS read-only
                STATUS current
                DESCRIPTION
                        "The IPv4 Address currently in use by the
                         interface."
        ::= {  awcIfEntry 6 }

awcIfIpNetMask OBJECT-TYPE
                SYNTAX IpAddress
                MAX-ACCESS read-only
                STATUS current
                DESCRIPTION
                        "The IPv4 netmask currently in use by the
                         interface."
        ::= {  awcIfEntry 7 }

awcIfMSDUMaxLength OBJECT-TYPE
                SYNTAX Unsigned32
                MAX-ACCESS read-only
                STATUS current
                DESCRIPTION
                        "Maximum length of the data portion of a packet
                         for this particular interface.  This is the
                         maximum MAC Service Data Unit length, which is
                         greater than or equal to ifMtu, depending on
                         the configured MAC-level encapsulation."
        ::= {  awcIfEntry 8 }

awcIfOutDiscardsCoS0 OBJECT-TYPE
                SYNTAX Counter32
                MAX-ACCESS read-only
                STATUS current
                DESCRIPTION
                        "The number of outbound packets of CoS 0 which
                         were chosen to be discarded even though no
                         errors had been detected to prevent their
                         being transmitted.  One possible reason for
                         discarding such a packet could be to free up
                         buffer space.  Another reason would be
                         exceeding their maximum time-to-live."
        ::= {  awcIfEntry 9 }

awcIfOutDiscardsCoS1 OBJECT-TYPE
                SYNTAX Counter32
                MAX-ACCESS read-only
                STATUS current
                DESCRIPTION
                        "The number of outbound packets of CoS 1 which
                         were chosen to be discarded even though no
                         errors had been detected to prevent their
                         being transmitted.  One possible reason for
                         discarding such a packet could be to free up
                         buffer space.  Another reason would be
                         exceeding their maximum time-to-live."
        ::= {  awcIfEntry 10 }

awcIfOutDiscardsCoS2 OBJECT-TYPE
                SYNTAX Counter32
                MAX-ACCESS read-only
                STATUS current
                DESCRIPTION
                        "The number of outbound packets of CoS 2 which
                         were chosen to be discarded even though no
                         errors had been detected to prevent their
                         being transmitted.  One possible reason for
                         discarding such a packet could be to free up
                         buffer space.  Another reason would be
                         exceeding their maximum time-to-live."
        ::= {  awcIfEntry 11 }

awcIfOutDiscardsCoS3 OBJECT-TYPE
                SYNTAX Counter32
                MAX-ACCESS read-only
                STATUS current
                DESCRIPTION
                        "The number of outbound packets of CoS 3 which
                         were chosen to be discarded even though no
                         errors had been detected to prevent their
                         being transmitted.  One possible reason for
                         discarding such a packet could be to free up
                         buffer space.  Another reason would be
                         exceeding their maximum time-to-live."
        ::= {  awcIfEntry 12 }

awcIfOutDiscardsCoS4 OBJECT-TYPE
                SYNTAX Counter32
                MAX-ACCESS read-only
                STATUS current
                DESCRIPTION
                        "The number of outbound packets of CoS 4 which
                         were chosen to be discarded even though no
                         errors had been detected to prevent their
                         being transmitted.  One possible reason for
                         discarding such a packet could be to free up
                         buffer space.  Another reason would be
                         exceeding their maximum time-to-live."
        ::= {  awcIfEntry 13 }

awcIfOutDiscardsCoS5 OBJECT-TYPE
                SYNTAX Counter32
                MAX-ACCESS read-only
                STATUS current
                DESCRIPTION
                        "The number of outbound packets of CoS 5 which
                         were chosen to be discarded even though no
                         errors had been detected to prevent their
                         being transmitted.  One possible reason for
                         discarding such a packet could be to free up
                         buffer space.  Another reason would be
                         exceeding their maximum time-to-live."
        ::= {  awcIfEntry 14 }

awcIfOutDiscardsCoS6 OBJECT-TYPE
                SYNTAX Counter32
                MAX-ACCESS read-only
                STATUS current
                DESCRIPTION
                        "The number of outbound packets of CoS 6 which
                         were chosen to be discarded even though no
                         errors had been detected to prevent their
                         being transmitted.  One possible reason for
                         discarding such a packet could be to free up
                         buffer space.  Another reason would be
                         exceeding their maximum time-to-live."
        ::= {  awcIfEntry 15 }

awcIfOutDiscardsCoS7 OBJECT-TYPE
                SYNTAX Counter32
                MAX-ACCESS read-only
                STATUS current
                DESCRIPTION
                        "The number of outbound packets of CoS 7 which
                         were chosen to be discarded even though no
                         errors had been detected to prevent their
                         being transmitted.  One possible reason for
                         discarding such a packet could be to free up
                         buffer space.  Another reason would be
                         exceeding their maximum time-to-live."
        ::= {  awcIfEntry 16 }


-- ********************************************************************
-- *    End of awcIfTable parameters
-- ********************************************************************


-- ********************************************************************
-- *  awc802dot11 parameters
-- ********************************************************************
awcDot11smt OBJECT IDENTIFIER ::=       {awc802dot11 1}


awcDot11StationConfigTable OBJECT-TYPE
                SYNTAX SEQUENCE OF AwcDot11StationConfigEntry
                MAX-ACCESS not-accessible
                STATUS current
                DESCRIPTION
                        "Station Config Table attributes.  In tabular
                         form to allow for multiple instances on an
                         agent."
        ::= {  awcDot11smt 1 }

awcDot11StationConfigEntry OBJECT-TYPE
                SYNTAX AwcDot11StationConfigEntry
                MAX-ACCESS not-accessible
                STATUS current
                DESCRIPTION
                        "An entry in the awcDot11StationConfigTable
                         table."
                INDEX {ifIndex}
        ::= {  awcDot11StationConfigTable 1 }

AwcDot11StationConfigEntry ::=
                SEQUENCE {
                         awcDot11StationRole              INTEGER,
                         awcDot11PowerManagementSubMode   Unsigned32,
                         awcDot11UseAWCExtensions         TruthValue,
                         awcDot11AllowAssocBroadcastSSID  TruthValue,
                         awcDot11PrivacyOptionImplementedMaxRate
                                                          Integer32,
                         awcDot11DesiredBSSLength         INTEGER,
                         awcDot11EnetEncapsulationDefault INTEGER,
                         awcDot11ForceReqFirmwareVersion  TruthValue,
                         awcDot11BridgeSpacing            Unsigned32,
                         awcDot11DesiredSSIDMaxAssociatedSTA INTEGER,
                         awcDot11DesiredSSIDNumAssociatedSTA INTEGER,
                         awcDot11AuxiliarySSIDLength      INTEGER,
                         awcDot11MultipleSSIDPerBSSImplemented
                                                          TruthValue,
                         awcDot11SymbolExtensionsImplemented
                                                          TruthValue,
                         awcDot11SymbolExtensionsEnabled  TruthValue,
                         awcDot11DesiredSSIDMicAlgorithm
                                 AwcDot11MicAlgorithm,
                         awcDot11DesiredSSIDWEPKeyPermuteAlgorithm
                                 AwcDot11WEPKeyPermuteAlgorithm,
                         awcDot11DesiredSSIDInfrastructureWGB
                                                          TruthValue,
                         awcDot11DesiredSSIDDefaultPolId  AwcPolId,
                         awcDot11DesiredSSIDDefaultVlanId AwcVlanId,
                         awcDot11DesiredSSIDEnableProxyMobileIP
                                                          TruthValue,
                         awcDot11InfrastructureSSID       INTEGER,
                         awcDot11QBSSElementImplemented
                                                          TruthValue,
                         awcDot11QBSSElementEnabled       TruthValue,
                         awcDot11InfrastructureSSIDExclusive
                                                          TruthValue,
                         awcDot11SendIGMPGeneralQuery     TruthValue,
                         awcDot11NonRootMobility          INTEGER
                         }

awcDot11StationRole OBJECT-TYPE
                SYNTAX INTEGER {roleClient(1), roleIBSS(2),
                                roleRepeater(3), roleAP(4)}
                MAX-ACCESS read-write
                STATUS current
                DESCRIPTION
                        "The role of this station itself within the
                         802.11 BSS (radio cell) of which it is a
                         member."
                DEFVAL { roleAP }
        ::= {  awcDot11StationConfigEntry 1 }

awcDot11PowerManagementSubMode OBJECT-TYPE
                SYNTAX Unsigned32
                MAX-ACCESS read-write
                STATUS current
                DESCRIPTION
                        "When configured as roleClient, the Power
                         Management Submode of the device."
                DEFVAL { 0 }
        ::= {  awcDot11StationConfigEntry 2 }

awcDot11UseAWCExtensions OBJECT-TYPE
                SYNTAX TruthValue
                MAX-ACCESS read-write
                STATUS current
                DESCRIPTION
                        "If true, Aironet extensions to the basic
                         802.11 protocol are enabled.  This results in
                         better BSS performance and faster roaming.
                         If false, only the basic 802.11 protocols
                         are used.  This ensures maximum compatibility
                         with non-Aironet equipment."
                DEFVAL { true }
        ::= {  awcDot11StationConfigEntry 3 }

awcDot11AllowAssocBroadcastSSID OBJECT-TYPE
                SYNTAX TruthValue
                MAX-ACCESS read-write
                STATUS current
                DESCRIPTION
                        "If true and awcDot11StationRole is either
                         roleAP or roleRepeater, the radio will respond
                         to Broadcast SSID Probe Requests and will
                         broadcast its own SSID within its Beacons.  If
                         false, the radio will not respond to the
                         Broadcast SSID and will not broadcast its SSID
                         within Beacons."
                DEFVAL { true }
        ::= {  awcDot11StationConfigEntry 4 }

awcDot11PrivacyOptionImplementedMaxRate OBJECT-TYPE
                SYNTAX Integer32 (2..127)
                MAX-ACCESS read-only
                STATUS current
                DESCRIPTION
                        "The maximum Transmit bit rate supported by the
                         radio when using WEP encryption.  Expressed in
                         standard 802.11 increments of 500Kb/sec."
        ::= {  awcDot11StationConfigEntry 5 }

awcDot11DesiredBSSLength OBJECT-TYPE
                SYNTAX INTEGER (0..4)
                MAX-ACCESS read-only
                STATUS current
                DESCRIPTION
                        "The number of entries in
                         awcDot11DesiredBSSTable."
        ::= {  awcDot11StationConfigEntry 6 }

awcDot11EnetEncapsulationDefault OBJECT-TYPE
                SYNTAX INTEGER {encap802dot1H(1), encapRfc1042(2)}
                MAX-ACCESS read-write
                STATUS current
                DESCRIPTION
                        "The Ethernet Encapsulation Transform type used
                         within the BSS.  Either IEEE 802.1H or
                         RFC 1042 can be utilized.  IEEE 802.1H
                         provides  exceptions for the Novel
                         IPX and AARP protocols."
                DEFVAL { encapRfc1042 }
        ::= {  awcDot11StationConfigEntry 7 }

awcDot11ForceReqFirmwareVersion OBJECT-TYPE
                SYNTAX TruthValue
                MAX-ACCESS read-write
                STATUS current
                DESCRIPTION
                        "If true, the radio driver will only allow
                         operation with the specific radio firmware
                         revision with which it was originally tested.
                         If false, the radio driver will allow
                         operation with the radio firmware revision
                         with which it was tested, or any later radio
                         firmware revision."
                DEFVAL { true }
        ::= {  awcDot11StationConfigEntry 8 }

awcDot11BridgeSpacing OBJECT-TYPE
                SYNTAX Unsigned32
                MAX-ACCESS read-write
                STATUS current
                DESCRIPTION
          		"If this device is the root side of a Bridge
                         configuration, this value is the distance in
                         kilometers reported between this device and
                         its farthest non-root Bridge."
                DEFVAL { 0 }
        ::= {  awcDot11StationConfigEntry 9 }

awcDot11DesiredSSIDMaxAssociatedSTA OBJECT-TYPE
                SYNTAX INTEGER (0..2007)
                MAX-ACCESS read-write
                STATUS current
                DESCRIPTION
                        "The maximum number of 802.11 Stations which
                         may Associate with this access point through
                         either the Broadcast SSID or through
                         dot11DesiredSSID.  If 0, the maximum number
                         is limited only by the 802.11 standard and
                         by any hardware or radio firmware limitations
                         of the access point."
                DEFVAL { 0 }
        ::= {  awcDot11StationConfigEntry 10 }

awcDot11DesiredSSIDNumAssociatedSTA OBJECT-TYPE
                SYNTAX INTEGER (0..2007)
                MAX-ACCESS read-only
                STATUS current
                DESCRIPTION
                        "The current number of 802.11 Stations which
                         are Associated with this access point through
                         either the Broadcast SSID or through
                         dot11DesiredSSID."
        ::= {  awcDot11StationConfigEntry 11 }

awcDot11AuxiliarySSIDLength OBJECT-TYPE
                SYNTAX INTEGER (0..2007)
                MAX-ACCESS read-only
                STATUS current
                DESCRIPTION
                "The maximum number of entries in
                 awcDot11AuxiliarySSIDTable.  If
                 awcDot11MultipleSSIDPerBSSImplemented is FALSE,
                 awcDot11AuxiliarySSIDLength must be 0."
        ::= {  awcDot11StationConfigEntry 12 }

awcDot11MultipleSSIDPerBSSImplemented OBJECT-TYPE
                SYNTAX TruthValue
                MAX-ACCESS read-only
                STATUS current
                DESCRIPTION
                "This attribute, when TRUE, indicates that the station
                 implementation is capable of responding to 802.11
                 Probe Requests for SSIDs other than dot11DesiredSSID.
                 The default value of this attribute is FALSE."
        ::= {  awcDot11StationConfigEntry 13 }

awcDot11SymbolExtensionsImplemented OBJECT-TYPE
                SYNTAX TruthValue
                MAX-ACCESS read-only
                STATUS current
                DESCRIPTION
                "This attribute, when TRUE, indicates that the station
                 implementation is capable of generating Symbol, Inc.
                 proprietary elements in its Beacons and Probe
                 Responses.  These elements enable support for Symbol
                 Voice-over-IP (VoIP) phones.  The default value of
                 this attribute is FALSE."
        ::= {  awcDot11StationConfigEntry 14 }

awcDot11SymbolExtensionsEnabled OBJECT-TYPE
                SYNTAX TruthValue
                MAX-ACCESS read-write
                STATUS current
                DESCRIPTION
                "Should the Radio generate Symbol, Inc. proprietary
                 elements in its Beacons and Probe Responses in support
                 of Symbol VoIP phones?"
                DEFVAL { false }
        ::= {  awcDot11StationConfigEntry 15 }

awcDot11DesiredSSIDMicAlgorithm OBJECT-TYPE
                SYNTAX AwcDot11MicAlgorithm
                MAX-ACCESS read-write
                STATUS current
                DESCRIPTION
                "Auxiliary Message Integrity Check (MIC) calculated on
                 WEP-encoded packets of stations Associated to this
                 access point through either the Broadcast SSID or
                 dot11DesiredSSID."
                DEFVAL { micNone }
        ::= {  awcDot11StationConfigEntry 16 }

awcDot11DesiredSSIDWEPKeyPermuteAlgorithm OBJECT-TYPE
                SYNTAX AwcDot11WEPKeyPermuteAlgorithm
                MAX-ACCESS read-write
                STATUS current
                DESCRIPTION
                "Function through which the WEP encryption key is
                 permuted between key renewal periods for stations
                 Associated to this access point through either the
                 Broadcast SSID or dot11DesiredSSID."
                DEFVAL { wepPermuteNone }
        ::= {  awcDot11StationConfigEntry 17 }

awcDot11DesiredSSIDInfrastructureWGB OBJECT-TYPE
                SYNTAX TruthValue
                MAX-ACCESS read-write
                STATUS current
                DESCRIPTION
                "When true, Workgroup Bridge-class devices Associated to
                 this access point through either the
                 Broadcast SSID or dot11DesiredSSID are provided
                 the class of service which is provided to network
                 infrastructure stations by their parent access point.
                 This includes use of the 802.11 reliable multicast
                 protocol (4-address packets for multicast).  When false,
                 Workgroup Bridge-class devices are provided the class of
                 service which is provided to ordinary client stations."
                DEFVAL { true }
        ::= {  awcDot11StationConfigEntry 18 }

awcDot11DesiredSSIDDefaultPolId OBJECT-TYPE
                SYNTAX AwcPolId
                MAX-ACCESS read-write
                STATUS current
                DESCRIPTION
                "Default Policy Group Identifier for stations
                 Associated to this access point through either the
                 Broadcast SSID or dot11DesiredSSID.  A value of 0
                 indicates that no special policies are to be applied
                 by default."
	            DEFVAL      { 0 }
        ::= {  awcDot11StationConfigEntry 19 }

awcDot11DesiredSSIDDefaultVlanId OBJECT-TYPE
                SYNTAX AwcVlanId
                MAX-ACCESS read-write
                STATUS current
                DESCRIPTION
                "Default VLAN Identifier for stations
                 Associated to this access point through either the
                 Broadcast SSID or dot11DesiredSSID.  A value of 0
                 indicates that either VLANs are disabled or that
                 the default VLAN is awcNativeVlanId."
	            DEFVAL      { 0 }
        ::= {  awcDot11StationConfigEntry 20 }

awcDot11DesiredSSIDEnableProxyMobileIP OBJECT-TYPE
                SYNTAX TruthValue
                MAX-ACCESS read-write
                STATUS current
                DESCRIPTION
                "If true, Proxy Mobile IP is enabled for use by
                 all stations Associated to this access point
                 through either the Broadcast SSID or
                 dot11DesiredSSID."
                DEFVAL { false }
        ::= {  awcDot11StationConfigEntry 21 }

awcDot11InfrastructureSSID OBJECT-TYPE
                SYNTAX INTEGER (0..2007)
                MAX-ACCESS read-write
                STATUS current
                DESCRIPTION
                    "Index of the SSID which all 802.11 infrastructure
                     stations shall use for Association.  If 0, an
                     access point and its repeaters and other
                     subordinate infrastructure devices will Associate
                     through dot11DesiredSSID.  If non-0, an access
                     point and its subordinate infrastructure devices
                     will Associate through the auxiliary SSID with
                     awcDot11AuxSSIDIndex equal to
                     awcDot11InfrastructureSSID."
                DEFVAL { 0 }
        ::= {  awcDot11StationConfigEntry 22 }

awcDot11QBSSElementImplemented OBJECT-TYPE
                SYNTAX TruthValue
                MAX-ACCESS read-only
                STATUS current
                DESCRIPTION
                "This attribute, when TRUE, indicates that the station
                 implementation is capable of generating 802.11e QBSS
                 elements in its Beacons and Probe
                 Responses.  These elements enable support for basic
                 802.11 Quality of Service.  The default value of
                 this attribute is FALSE."
        ::= {  awcDot11StationConfigEntry 23 }

awcDot11QBSSElementEnabled OBJECT-TYPE
                SYNTAX TruthValue
                MAX-ACCESS read-write
                STATUS current
                DESCRIPTION
                "Should the Radio generate 802.11e QBSS
                 elements in its Beacons and Probe Responses in support
                 of 802.11 Quality of Service?"
                DEFVAL { false }
        ::= {  awcDot11StationConfigEntry 24 }

awcDot11InfrastructureSSIDExclusive OBJECT-TYPE
                SYNTAX TruthValue
                MAX-ACCESS read-write
                STATUS current
                DESCRIPTION
                "Should this access point restrict all infrastructure
                 stations to associate only through the SSID specified
                 by awcDot11InfrastructureSSID?"
                DEFVAL { false }
        ::= {  awcDot11StationConfigEntry 25 }

awcDot11SendIGMPGeneralQuery OBJECT-TYPE
                SYNTAX TruthValue
                MAX-ACCESS read-write
                STATUS current
                DESCRIPTION
                "Should this access point issue an IGMP General Query
                 to all associated stations when they complete all
                 required high-level authentication?  Such an IGMP
                 query can help configure multicast groups efficiently."
                DEFVAL { false }
        ::= {  awcDot11StationConfigEntry 26 }

awcDot11NonRootMobility OBJECT-TYPE
                SYNTAX INTEGER {
                        mobile(1),
                        stationary(2)
                               }
                MAX-ACCESS read-write
                STATUS current
                DESCRIPTION
                        "This object is used to determine if the radio
                         should look for a better parent AP in heavy
                         traffic condition when the awcDot11StationRole
                         is roleClient(1) or roleRepeater(3). It will
                         look for better parent if it is mobile(1)
                         and will not look for better parent if it is
                         stationary(2)."
                DEFVAL { stationary }
        ::= {  awcDot11StationConfigEntry 27 }


awcDot11AuthenticationAlgorithmsTable OBJECT-TYPE
        SYNTAX SEQUENCE OF AwcDot11AuthenticationAlgorithmsEntry
        MAX-ACCESS not-accessible
        STATUS current
        DESCRIPTION
                "This table contains attributes to configure
                authentication algorithm parameters for associations
                through the SSID defined by IEEE802dot11-MIB
                dot11DesiredSSID object.  It defines attributes
                additional to those defined in the IEEE802dot11-MIB
                dot11AuthenticationAlgorithmsTable.  An interface
                may support multiple authentication algorithms.

                This table has an expansion dependent relationship
                on the ifTable.  For each entry in this table,
                there exists at least an entry in the ifTable of
                ifType ieee80211(71).  This table uses the
                dot11AuthenticationAlgorithmsIndex of the
                dot11AuthenticationAlgorithmsTable defined in the
                IEEE802dot11-MIB as the expansion index.

                Entries in this table cannot be created or deleted
                by the network management system.  All entries are
                created or deleted by the agent."
        REFERENCE
                "IEEE Std 802.11-Jan 14 1999, Wireless LAN Medium
                Access Control and Physical Layer Specifications,
                LAN MAN Standards Committee of the IEEE Computer
                Society, section 5.7.6 and IEEE802dot11-MIB."
        ::= {  awcDot11smt 2 }

awcDot11AuthenticationAlgorithmsEntry OBJECT-TYPE
        SYNTAX AwcDot11AuthenticationAlgorithmsEntry
        MAX-ACCESS not-accessible
        STATUS current
        DESCRIPTION
                "Each entry specifies Cisco Aironet product
                specific authentication algorithm
                configuration attributes of the dot11DesiredSSID
                on a radio interface."
        REFERENCE
                "IEEE Std 802.11-Jan 14 1999, Wireless LAN Medium
                Access Control and Physical Layer Specifications,
                LAN MAN Standards Committee of the IEEE Computer
                Society, section 8.2 and IEEE802dot11-MIB."
        INDEX { ifIndex,
                awcDot11AuthenticationAlgorithmsIndex}
        ::= {  awcDot11AuthenticationAlgorithmsTable  1 }

AwcDot11AuthenticationAlgorithmsEntry ::= SEQUENCE {
        awcDot11AuthenticationAlgorithmsIndex      Integer32,
        awcDot11AuthenticationRequireEAP           TruthValue,
        awcDot11AuthenticationDefaultUcastAllowedToGoTo
                OCTET STRING }


awcDot11AuthenticationAlgorithmsIndex OBJECT-TYPE
        SYNTAX Integer32 (1..65536)
        MAX-ACCESS not-accessible
        STATUS current
        DESCRIPTION
                "The auxiliary variable used to identify instances
                of the columnar objects in the Aironet Authentication
                Algorithms Table.  This variable corresponds directly
                to the 802.11 dot11AuthenticationAlgorithmsIndex."
        ::= {  awcDot11AuthenticationAlgorithmsEntry 1 }

awcDot11AuthenticationRequireEAP OBJECT-TYPE
        SYNTAX TruthValue
        MAX-ACCESS read-write
        STATUS current
        DESCRIPTION
                "If true, stations authenticating with the
                 corresponding dot11AuthenticationAlgorithm
                 must complete network-level EAP authentication
                 before they will be unblocked.  If false,
                 stations authenticating with the corresponding
                 dot11AuthenticationAlgorithm will be unblocked
                 as soon as they complete the requirements of
                 802.11 authentication."
        ::= {  awcDot11AuthenticationAlgorithmsEntry 2 }

awcDot11AuthenticationDefaultUcastAllowedToGoTo OBJECT-TYPE
        SYNTAX  OCTET STRING
        MAX-ACCESS  read-write
        STATUS  current
        DESCRIPTION
                "The set of ports to which frames received from
                a specific port and destined for a MAC address
                which is not already listed in dot1dStaticTable
                and authenticates with the corresponding
                dot11AuthenticationAlgorithm, are allowed to be
                forwarded.  Each octet within the value of this
                object specifies a set of eight ports, with the
                first octet specifying ports 1 through 8, the
                second octet specifying ports 9 through 16, etc.
                Within each octet, the most significant bit
                represents the lowest numbered port, and the
                least significant bit represents the highest
                numbered port.  Thus, each port of the bridge is
                represented by a single bit within the value of
                this object.  If that bit has a value of
                '1' then that port is included in the set of
                ports; the port is not included if its bit has a
                value of '0'.  (Note that the setting of the bit
                corresponding to the port from which a frame is
                received is irrelevant.)  The default value of
                this object is a string of ones of appropriate
                length."
        REFERENCE
                "RFC 1493, BRIDGE-MIB, dot1dStaticTable."
        ::= {  awcDot11AuthenticationAlgorithmsEntry 3 }


awcDot11WEPDefaultKeysTable OBJECT-TYPE
                SYNTAX SEQUENCE OF AwcDot11WEPDefaultKeysEntry
                MAX-ACCESS not-accessible
                STATUS current
                DESCRIPTION
                        "Extension of dot11WEPDefaultKeysTable to allow
                         for key lengths other than 40 bits."
        ::= {  awcDot11smt 3 }

awcDot11WEPDefaultKeysEntry OBJECT-TYPE
                SYNTAX AwcDot11WEPDefaultKeysEntry
                MAX-ACCESS not-accessible
                STATUS current
                DESCRIPTION
                        "An entry in the awcDot11WEPDefaultKeysTable
                         table."
                INDEX {ifIndex, awcDot11WEPDefaultKeyIndex}
        ::= {  awcDot11WEPDefaultKeysTable 1 }

AwcDot11WEPDefaultKeysEntry ::=
                SEQUENCE {
                         awcDot11WEPDefaultKeyIndex       INTEGER,
                         awcDot11WEPDefaultKeyLen         INTEGER,
                         awcDot11WEPDefaultKeyValue       WEPKeytype128
                         }

awcDot11WEPDefaultKeyIndex OBJECT-TYPE
                SYNTAX INTEGER (1..4)
                MAX-ACCESS read-only
                STATUS current
                DESCRIPTION
                         "The auxiliary variable used to identify
                          instances of the columnar objects in the WEP
                          Default Keys Table. The value of this
                          variable is equal to the WEPDefaultKeyID + 1"
        ::= {  awcDot11WEPDefaultKeysEntry 1 }

awcDot11WEPDefaultKeyLen OBJECT-TYPE
                SYNTAX INTEGER (0..13)
                MAX-ACCESS read-write
                STATUS current
                DESCRIPTION
                         "Length in octets of
                          awcDot11WEPDefaultKeyValue.  If 0, the
                          corresponding awcDot11WEPDefaultKeyValue is
                          not configured."
        ::= {  awcDot11WEPDefaultKeysEntry 2 }

awcDot11WEPDefaultKeyValue OBJECT-TYPE
                SYNTAX WEPKeytype128
                MAX-ACCESS read-write
                STATUS current
                DESCRIPTION
                         "A WEP default secret key value.  The value is
                          write-only (attempt to read will result in
                          return of a zero-length string)."
        ::= {  awcDot11WEPDefaultKeysEntry 3 }


awcDot11PrivacyTable OBJECT-TYPE
                SYNTAX SEQUENCE OF AwcDot11PrivacyEntry
                MAX-ACCESS not-accessible
                STATUS current
                DESCRIPTION
                        "Additional information about the WEP
                         capabilities of the device.  In tabular form
                         to allow for multiple instances on an agent."
        ::= {  awcDot11smt 5 }

awcDot11PrivacyEntry OBJECT-TYPE
                SYNTAX AwcDot11PrivacyEntry
                MAX-ACCESS not-accessible
                STATUS current
                DESCRIPTION
                        "An entry in the awcDot11PrivacyTable table."
                INDEX {ifIndex}
        ::= {  awcDot11PrivacyTable 1 }

AwcDot11PrivacyEntry ::=
                SEQUENCE {
                         awcDot11WEPDefaultKeyMaxIndex  INTEGER,
                         awcDot11AllowEncrypted         TruthValue,
                         awcDot11WEPKeyMaxLen           INTEGER,
                         awcDot11LEAPUserName           OCTET STRING,
                         awcDot11LEAPPassword           OCTET STRING
                         }

awcDot11WEPDefaultKeyMaxIndex OBJECT-TYPE
                SYNTAX INTEGER (0..4)
                MAX-ACCESS read-only
                STATUS current
                DESCRIPTION
                        "The maximum WEP Default Key index which the
                         radio supports. Range 1..4, or 0 if the radio
                         does not support WEP."
        ::= {  awcDot11PrivacyEntry 1 }

awcDot11AllowEncrypted OBJECT-TYPE
                SYNTAX TruthValue
                MAX-ACCESS read-write
                STATUS current
                DESCRIPTION
                        "When this attribute is true, the STA shall
                         indicate at the MAC service interface received
                         MSDUs regardless of the setting of the WEP
                         subfield of the Frame Control field, so long
                         as the dot11ExcludeUnencrypted attribute is
                         false. The default value of this attribute
                         shall be false."
                DEFVAL { false }
        ::= {  awcDot11PrivacyEntry 2 }

awcDot11WEPKeyMaxLen OBJECT-TYPE
                SYNTAX INTEGER (0..16)
                MAX-ACCESS read-only
                STATUS current
                DESCRIPTION
                        "The maximum WEP Key Length which the radio
                         supports. Range 0..16, or 0 if the radio does
                         not support WEP. Note that, even if the radio
                         supports more than 13 octets of key value, the
                         current 802.11 standard only makes use of
                         the first 13 octets."
        ::= {  awcDot11PrivacyEntry 3 }

awcDot11LEAPUserName OBJECT-TYPE
                SYNTAX OCTET STRING
                MAX-ACCESS read-write
                STATUS current
                DESCRIPTION
                "User Name assigned to the system for use when
                 authenticating with AAA servers."
                DEFVAL { "" }
        ::= {  awcDot11PrivacyEntry 4}

awcDot11LEAPPassword OBJECT-TYPE
                SYNTAX OCTET STRING (SIZE (0..256))
                MAX-ACCESS read-write
                STATUS current
                DESCRIPTION
                "User Password (shared secret) assigned to the system
                 for use when authenticating with AAA servers."
                DEFVAL { "" }
        ::= {  awcDot11PrivacyEntry 5}

awcDot11DesiredBSSTable OBJECT-TYPE
                SYNTAX SEQUENCE OF AwcDot11DesiredBSSEntry
                MAX-ACCESS not-accessible
                STATUS current
                DESCRIPTION
                        "When the radio is not in roleAP, a list of
                         preferred Access Points with which the radio
                         should Associate. In tabular form to allow for
                         multiple instances on an agent."
        ::= {  awcDot11smt 6 }

awcDot11DesiredBSSEntry OBJECT-TYPE
                SYNTAX AwcDot11DesiredBSSEntry
                MAX-ACCESS not-accessible
                STATUS current
                DESCRIPTION
                        "An entry in the awcDot11DesiredBSSTable
                         table."
                INDEX {ifIndex, awcDot11DesiredBSSIndex}
        ::= {  awcDot11DesiredBSSTable 1 }

AwcDot11DesiredBSSEntry ::=
                SEQUENCE {
                         awcDot11DesiredBSSIndex	  INTEGER,
                         awcDot11DesiredBSS           MacAddress
                         }

awcDot11DesiredBSSIndex OBJECT-TYPE
                SYNTAX INTEGER (1..4)
                MAX-ACCESS read-only
                STATUS current
                DESCRIPTION
                        "The priority order in which Preferred Access
                         Points should be probed.  Lower indices are
                         probed first."
        ::= {  awcDot11DesiredBSSEntry 1 }

awcDot11DesiredBSS OBJECT-TYPE
                SYNTAX MacAddress
                MAX-ACCESS read-write
                STATUS current
                DESCRIPTION
                        "The BSS identifier (MAC address) of the Access
                         Point with which the radio should try to
                         Associate, or 00:00:00:00:00:00 if the BSS
                         identifier for this priority is unspecified."
                DEFVAL { '000000000000'H }
        ::= {  awcDot11DesiredBSSEntry 2 }


awcDot11AuxiliarySSIDTable OBJECT-TYPE
                SYNTAX SEQUENCE OF AwcDot11AuxiliarySSIDEntry
                MAX-ACCESS not-accessible
                STATUS current
                DESCRIPTION
                        "When the radio is not in roleClient, a list of
                         Stations which, when Associated to this system,
                         shall always have the same AID."
        ::= {  awcDot11smt 7 }

awcDot11AuxiliarySSIDEntry OBJECT-TYPE
                SYNTAX AwcDot11AuxiliarySSIDEntry
                MAX-ACCESS not-accessible
                STATUS current
                DESCRIPTION
                        "An entry in the awcDot11AuxiliarySSIDTable
                         table."
                INDEX {ifIndex, awcDot11AuxSSIDIndex}
        ::= {  awcDot11AuxiliarySSIDTable 1 }

AwcDot11AuxiliarySSIDEntry ::=
                SEQUENCE {
                         awcDot11AuxSSIDIndex	     	 INTEGER,
                         awcDot11AuxSSID                 OCTET STRING,
                         awcDot11AuxSSIDMaxAssociatedSTA INTEGER,
                         awcDot11AuxSSIDNumAssociatedSTA INTEGER,
                         awcDot11AuxSSIDDefaultPolId	 AwcPolId,
                         awcDot11AuxSSIDDefaultVlanId	 AwcVlanId,
                         awcDot11AuxSSIDEnableProxyMobileIP
                                                         TruthValue
                         }

awcDot11AuxSSIDIndex OBJECT-TYPE
                SYNTAX INTEGER (1..2007)
                MAX-ACCESS read-only
                STATUS current
                DESCRIPTION
                "Identifier of auxiliary SSIDs supported by the access
                 point in addition to dot11DesiredSSID.  Domain from 1
                 to awcDot11AuxiliarySSIDLength."
        ::= {  awcDot11AuxiliarySSIDEntry 1 }

awcDot11AuxSSID OBJECT-TYPE
                SYNTAX OCTET STRING (SIZE(0..32))
                MAX-ACCESS read-write
                STATUS current
                DESCRIPTION
                "This attribute reflects a Service Set ID recognized
                 by the access point.  The access point shall respond
                 to Probe Requests specifying this SSID, but does not
                 advertise this SSID in its Beacons."
                DEFVAL { "" }
        ::= {  awcDot11AuxiliarySSIDEntry 2 }

awcDot11AuxSSIDMaxAssociatedSTA OBJECT-TYPE
                SYNTAX INTEGER (0..2007)
                MAX-ACCESS read-write
                STATUS current
                DESCRIPTION
                        "The maximum number of 802.11 Stations which
                         may Associate with this access point through
                         awcDot11AuxSSID.  If 0, the maximum number
                         is limited only by the 802.11 standard and
                         by any hardware or radio firmware limitations
                         of the access point."
                DEFVAL { 0 }
        ::= {  awcDot11AuxiliarySSIDEntry 3 }

awcDot11AuxSSIDNumAssociatedSTA OBJECT-TYPE
                SYNTAX INTEGER (0..2007)
                MAX-ACCESS read-only
                STATUS current
                DESCRIPTION
                        "The current number of 802.11 Stations which
                         are Associated with this access point through
                         awcDot11AuxSSID."
        ::= {  awcDot11AuxiliarySSIDEntry 4 }

awcDot11AuxSSIDDefaultPolId OBJECT-TYPE
                SYNTAX AwcPolId
                MAX-ACCESS read-write
                STATUS current
                DESCRIPTION
                "Default Policy Group Identifier for stations
                 Associated to this access point over awcDot11AuxSSID.
                 A value of 0 indicates that no special policies are
                 to be applied by default."
	            DEFVAL      { 0 }
        ::= {  awcDot11AuxiliarySSIDEntry 6 }

awcDot11AuxSSIDDefaultVlanId OBJECT-TYPE
                SYNTAX AwcVlanId
                MAX-ACCESS read-write
                STATUS current
                DESCRIPTION
                "Default VLAN Identifier for stations
                 Associated to this access point over awcDot11AuxSSID.
                 A value of 0 indicates that either VLANs are disabled
                 or that the default VLAN is awcNativeVlanId."
	            DEFVAL      { 0 }
        ::= {  awcDot11AuxiliarySSIDEntry 7 }

awcDot11AuxSSIDEnableProxyMobileIP OBJECT-TYPE
                SYNTAX TruthValue
                MAX-ACCESS read-write
                STATUS current
                DESCRIPTION
                "If true, Proxy Mobile IP is enabled for use by
                 all stations Associated to this access point
                 over awcDot11AuxSSID."
                DEFVAL { false }
        ::= {  awcDot11AuxiliarySSIDEntry 8 }

awcDot11AuxSSIDAuthAlgTable OBJECT-TYPE
        SYNTAX SEQUENCE OF AwcDot11AuxSSIDAuthAlgEntry
        MAX-ACCESS not-accessible
        STATUS current
        DESCRIPTION
            "This (conceptual) table of attributes shall be a set of
            all the Aironet-specific parameters for each authentication
            algorithm supported by the station for each auxiliary SSID
            listed in awcDot11AuxiliarySSIDTable."
    ::= {  awcDot11smt 8 }

awcDot11AuxSSIDAuthAlgEntry OBJECT-TYPE
        SYNTAX AwcDot11AuxSSIDAuthAlgEntry
        MAX-ACCESS not-accessible
        STATUS current
        DESCRIPTION
            "An Entry (conceptual row) in the Aironet Auxiliary SSID
             Authentication Algorithms Table.

            ifIndex - Each 802.11 interface is represented by an
            ifEntry.  Interface tables in this MIB module are indexed
            by ifIndex."

        INDEX { ifIndex,
                awcDot11AuxSSIDIndex,
                awcDot11AuxSSIDAuthAlgIndex}
    ::= {  awcDot11AuxSSIDAuthAlgTable  1 }

AwcDot11AuxSSIDAuthAlgEntry ::= SEQUENCE {
            awcDot11AuxSSIDAuthAlgIndex                 Integer32,
			awcDot11AuxSSIDAuthAlgEnable				TruthValue,
            awcDot11AuxSSIDAuthAlgRequireEAP           	TruthValue,
            awcDot11AuxSSIDAuthAlgDefaultUcastAllowedToGoTo
                    OCTET STRING
            }


awcDot11AuxSSIDAuthAlgIndex OBJECT-TYPE
        SYNTAX Integer32 (1..65536)
        MAX-ACCESS not-accessible
        STATUS current
        DESCRIPTION
            "The auxiliary variable used to identify instances
            of the columnar objects in the Aironet Auxiliary SSID
            Authentication Algorithms Table.  This variable
            corresponds directly to the 802.11
            dot11AuthenticationAlgorithmsIndex."
    ::= {  awcDot11AuxSSIDAuthAlgEntry 1 }

awcDot11AuxSSIDAuthAlgEnable OBJECT-TYPE
                SYNTAX TruthValue
                MAX-ACCESS read-write
                STATUS current
                DESCRIPTION
                "If true, stations may authenticate to the SSID
                specified by awcDot11AuxSSIDIndex with the algorithm
                corresponding to dot11AuthenticationAlgorithmsIndex."
    ::= {  awcDot11AuxSSIDAuthAlgEntry 2 }

awcDot11AuxSSIDAuthAlgRequireEAP OBJECT-TYPE
                SYNTAX TruthValue
                MAX-ACCESS read-write
                STATUS current
                DESCRIPTION
                "If true, stations authenticating to the SSID
                 specified by awcDot11AuxSSIDIndex with the
                 corresponding dot11AuthenticationAlgorithm
                 must complete network-level EAP authentication
                 before they will be unblocked.  If false,
                 stations authenticating with the corresponding
                 dot11AuthenticationAlgorithm will be unblocked
                 as soon as they complete the requirements of
                 802.11 authentication."
    ::= {  awcDot11AuxSSIDAuthAlgEntry 3 }

awcDot11AuxSSIDAuthAlgDefaultUcastAllowedToGoTo OBJECT-TYPE
              SYNTAX  OCTET STRING
              MAX-ACCESS  read-write
              STATUS  current
              DESCRIPTION
                  "The set of ports to which frames received from a
                  specific port and destined for a MAC address which
                  is not already listed in dot1dStaticTable and
                  authenticates to the SSID specified by
                  awcDot11AuxSSIDIndex with the corresponding
                  dot11AuthenticationAlgorithm, are
                  allowed to be forwarded.  Each octet
                  within the value of this object specifies a set of
                  eight ports, with the first octet specifying ports
                  1 through 8, the second octet specifying ports 9
                  through 16, etc.  Within each octet, the most
                  significant bit represents the lowest numbered
                  port, and the least significant bit represents the
                  highest numbered port.  Thus, each port of the
                  bridge is represented by a single bit within the
                  value of this object.  If that bit has a value of
                  '1' then that port is included in the set of
                  ports; the port is not included if its bit has a
                  value of '0'.  (Note that the setting of the bit
                  corresponding to the port from which a frame is
                  received is irrelevant.)  The default value of
                  this object is a string of ones of appropriate
                  length."
    ::= {  awcDot11AuxSSIDAuthAlgEntry 4 }


awcDot11AssignedAIDTable OBJECT-TYPE
                SYNTAX SEQUENCE OF AwcDot11AssignedAIDEntry
                MAX-ACCESS not-accessible
                STATUS current
                DESCRIPTION
                        "When the radio is not functioning as a client
                         station (i.e., awcDot11StationRole is not
                         'roleClient'), this is the list of AIDs which
                         this agent will assign to the clients
                         associating with it.  An AID is assigned if
                         the corresponding MAC address matches that of
                         the client.  This table has an expansion
                         dependent relationship on the ifTable.  For
                         each entry in this table, there exists at least
                         an entry in the ifTable of ifType ieee80211(71)."
        ::= {  awcDot11smt 9 }

awcDot11AssignedAIDEntry OBJECT-TYPE
                SYNTAX AwcDot11AssignedAIDEntry
                MAX-ACCESS not-accessible
                STATUS current
                DESCRIPTION
                        "An entry in the awcDot11AssignedAIDTable
                         table."
                INDEX {ifIndex, awcDot11AssignedAID}
        ::= {  awcDot11AssignedAIDTable 1 }

AwcDot11AssignedAIDEntry ::=
                SEQUENCE {
                         awcDot11AssignedAID	  INTEGER,
                         awcDot11AssignedSTA      MacAddress
                         }

awcDot11AssignedAID OBJECT-TYPE
                SYNTAX INTEGER (2..2007)
                MAX-ACCESS read-only
                STATUS current
                DESCRIPTION
                        "An AID which shall be reserved for the
                         exclusive use of a single Station."
        ::= {  awcDot11AssignedAIDEntry 1 }

awcDot11AssignedSTA OBJECT-TYPE
                SYNTAX MacAddress
                MAX-ACCESS read-write
                STATUS current
                DESCRIPTION
                        "The Station (MAC address) which, when
                         Associated to this system, shall always
                         be assigned awcDot11AssignedAID as its
                         802.11 AID."
                REFERENCE
                        "IEEE Std 802.11-Jan 14 1999, Wireless LAN Medium
                        Access Control and Physical Layer Specifications,
                        LAN MAN Standards Committee of the IEEE Computer
                        Society, section 5.7.2."
                DEFVAL { '000000000000'H }
        ::= {  awcDot11AssignedAIDEntry 2 }


awcDot11AccessPointCountersTable OBJECT-TYPE
                SYNTAX SEQUENCE OF AwcDot11AccessPointCountersEntry
                MAX-ACCESS not-accessible
                STATUS current
                DESCRIPTION
                        "This table includes radio statistics collected
                         by the IEEE 802.11 radio interface.  This
                         table has a sparse dependent relationship on
                         the ifTable.  For each entry in this table,
                         there exists an entry in the ifTable of
                         ifType ieee80211(71)."
        ::= {  awcDot11smt 10 }

awcDot11AccessPointCountersEntry OBJECT-TYPE
                SYNTAX AwcDot11AccessPointCountersEntry
                MAX-ACCESS not-accessible
                STATUS current
                DESCRIPTION
                        "Each entry contains counters of frame
                         transmissions and client associations for a
                         radio interface."
                INDEX {ifIndex}
        ::= {  awcDot11AccessPointCountersTable 1 }

AwcDot11AccessPointCountersEntry ::=
                SEQUENCE {
                         awcDot11AssociatedStationCount       Counter32,
                         awcDot11AuthenticatedStationCount    Counter32,
                         awcDot11ReassociatedStationCount     Counter32,
                         awcDot11RoamedStationCount           Counter32,
                         awcDot11DeauthenticateCount          Counter32,
                         awcDot11DisassociateCount            Counter32,
                         awcDot11EncapPktsMMH                 Counter32,
                         awcDot11DecapPktsMMH                 Counter32,
                         awcDot11EncapErrorsMMH               Counter32,
                         awcDot11DecapErrorsMMH               Counter32,
                         awcDot11DecapExistsMMH               Counter32,
                         awcDot11DecapAccessMMH               Counter32
                         }

 awcDot11AssociatedStationCount OBJECT-TYPE
         SYNTAX     Counter32
         MAX-ACCESS read-only
         STATUS     current
         DESCRIPTION
                 "Total number of successful 802.11 Association Request
                  operations to this radio of this access point since system
                  startup."
         REFERENCE
                 "IEEE Std 802.11-Jan 14 1999, Wireless LAN Medium
                  Access Control and Physical Layer Specifications,
                  LAN MAN Standards Committee of the IEEE Computer
                  Society, section 5.7."
         ::= { awcDot11AccessPointCountersEntry 1}

 awcDot11AuthenticatedStationCount OBJECT-TYPE
         SYNTAX     Counter32
         MAX-ACCESS read-only
         STATUS     current
         DESCRIPTION
                 "Total number of successful 802.11 MAC-level
                  Authentication operations to this radio of this access
                  point since system startup. "
         REFERENCE
                 "IEEE Std 802.11-Jan 14 1999, Wireless LAN Medium
                  Access Control and Physical Layer Specifications,
                  LAN MAN Standards Committee of the IEEE Computer
                  Society, section 5.7."
         ::= { awcDot11AccessPointCountersEntry 2 }

 awcDot11ReassociatedStationCount OBJECT-TYPE
         SYNTAX     Counter32
         MAX-ACCESS read-only
         STATUS     current
         DESCRIPTION
                 "Total number of successful 802.11 Reassociation Request
                  operations to this radio of this access point since system
                  startup."
         REFERENCE
                 "IEEE Std 802.11-Jan 14 1999, Wireless LAN Medium
                  Access Control and Physical Layer Specifications,
                  LAN MAN Standards Committee of the IEEE Computer
                  Society, section 5.7."
         ::= { awcDot11AccessPointCountersEntry 3 }

 awcDot11RoamedStationCount OBJECT-TYPE
         SYNTAX     Counter32
         MAX-ACCESS read-only
         STATUS     current
         DESCRIPTION
                 "Total number of times that clients which had
                  successfully (re)associated with this access point
                  successfully reassociated with another access point
                  since system startup."
         ::= { awcDot11AccessPointCountersEntry 4 }

 awcDot11DeauthenticateCount OBJECT-TYPE
         SYNTAX     Counter32
         MAX-ACCESS read-only
         STATUS     current
         DESCRIPTION
                 "Total number of Deauthenticate frames sent over this
                  radio of this access point since system startup."
         REFERENCE
                 "IEEE Std 802.11-Jan 14 1999, Wireless LAN Medium
                  Access Control and Physical Layer Specifications,
                  LAN MAN Standards Committee of the IEEE Computer
                  Society, section 5.7."
         ::= { awcDot11AccessPointCountersEntry 5 }

 awcDot11DisassociateCount OBJECT-TYPE
         SYNTAX     Counter32
         MAX-ACCESS read-only
         STATUS     current
         DESCRIPTION
                 "Total number of Disassociate frames sent over this
                  radio of this access point since system startup."
         REFERENCE
                 "IEEE Std 802.11-Jan 14 1999, Wireless LAN Medium
                  Access Control and Physical Layer Specifications,
                  LAN MAN Standards Committee of the IEEE Computer
                  Society, section 5.7."
         ::= { awcDot11AccessPointCountersEntry 6 }

awcDot11EncapPktsMMH OBJECT-TYPE
         SYNTAX     Counter32
         MAX-ACCESS read-only
         STATUS     current
         DESCRIPTION
                 "Total number of packets for which the a MIC has been
                  requested to be calculated with the MMH algorithm
                  before being submitted for transmission over
                  this radio of this access point since system startup."
         ::= { awcDot11AccessPointCountersEntry 7 }

awcDot11DecapPktsMMH OBJECT-TYPE
         SYNTAX     Counter32
         MAX-ACCESS read-only
         STATUS     current
         DESCRIPTION
                 "Total number of packets received over this radio of
                  this access point since system startup and for which
                  a MIC has been requested to be validated with the
                  MMH algorithm."
         ::= { awcDot11AccessPointCountersEntry 8 }

awcDot11EncapErrorsMMH OBJECT-TYPE
         SYNTAX     Counter32
         MAX-ACCESS read-only
         STATUS     current
         DESCRIPTION
                 "Total number of packets which have failed MIC
                  calculation with the MMH algorithm before being
                  submitted for transmission over this
                  radio of this access point since system startup."
         ::= { awcDot11AccessPointCountersEntry 9 }

awcDot11DecapErrorsMMH OBJECT-TYPE
         SYNTAX     Counter32
         MAX-ACCESS read-only
         STATUS     current
         DESCRIPTION
                 "Total number of packets received over this radio of
                  this access point since system startup which have
                  failed MIC validation with the MMH algorithm."
         ::= { awcDot11AccessPointCountersEntry 10 }

awcDot11DecapExistsMMH OBJECT-TYPE
         SYNTAX     Counter32
         MAX-ACCESS read-only
         STATUS     current
         DESCRIPTION
                 "Total number of packets received over this radio of
                  this access point since system startup which have
                  failed MIC validation with the MMH algorithm
                  specifically due to sequence number and duplicate
                  packet errors."
         ::= { awcDot11AccessPointCountersEntry 11 }

awcDot11DecapAccessMMH OBJECT-TYPE
         SYNTAX     Counter32
         MAX-ACCESS read-only
         STATUS     current
         DESCRIPTION
                 "Total number of packets received over this radio of
                  this access point since system startup which have
                  failed MIC validation with the MMH algorithm
                  specifically due to cryptographic key-mismatch
                  errors."
         ::= { awcDot11AccessPointCountersEntry 12 }


awcDot11mac OBJECT IDENTIFIER ::=       {awc802dot11 2}

awcDot11CountersTable OBJECT-TYPE
        SYNTAX     SEQUENCE OF AwcDot11CountersEntry
        MAX-ACCESS not-accessible
        STATUS     current
        DESCRIPTION
                "This table contains MAC statistics
                 on each of IEEE 802.11 interface.
                 This table has a sparse dependent
                 relationship on the ifTable.  For
                 each entry in this table, there exists
                 an entry in the ifTable of ifType
                 ieee80211(71)."
        ::= { awcDot11mac 2 }

awcDot11CountersEntry OBJECT-TYPE
        SYNTAX     AwcDot11CountersEntry
        MAX-ACCESS not-accessible
        STATUS     current
        DESCRIPTION
                "Each entry contains counters of frame
                 transmissions for a radio interface."
        INDEX { ifIndex }
        ::= { awcDot11CountersTable 1 }

AwcDot11CountersEntry ::=
        SEQUENCE {
                awcDot11TxDeferEnergyCount     Counter32,
                awcDot11RxMacCrcErrorCount     Counter32,
                awcDot11SsidMismatchCount      Counter32}


awcDot11TxDeferEnergyCount OBJECT-TYPE
        SYNTAX     Counter32
        MAX-ACCESS read-only
        STATUS     current
        DESCRIPTION
                "Total number of frames deferred transmission
                 due to energy detect since system startup."
        ::= { awcDot11CountersEntry 1 }

awcDot11RxMacCrcErrorCount OBJECT-TYPE
        SYNTAX     Counter32
        MAX-ACCESS read-only
        STATUS     current
        DESCRIPTION
                "Total number of frames received with
                 MAC CRC errors since system startup."
        ::= { awcDot11CountersEntry 2 }

awcDot11SsidMismatchCount OBJECT-TYPE
        SYNTAX     Counter32
        MAX-ACCESS read-only
        STATUS     current
        DESCRIPTION
                "Total number of Beacon or Probe Response frames received
                 for which the SSID does not match dot11DesiredSSID
                 since system startup."
        REFERENCE
                "IEEE Std 802.11-Jan 14 1999, Wireless LAN Medium
                 Access Control and Physical Layer Specifications,
                 LAN MAN Standards Committee of the IEEE Computer
                 Society, IEEE802dot11-MIB."
        ::= { awcDot11CountersEntry 3 }


awcDot11QoSTable OBJECT-TYPE
        SYNTAX SEQUENCE OF AwcDot11QoSEntry
        MAX-ACCESS not-accessible
        STATUS current
        DESCRIPTION
            "This (conceptual) table of attributes shall be a set of
            parameters for each traffic category (i.e. 802.1D priority)
            of packet passed over the radio."
         ::= { awcDot11mac 4 }

awcDot11QoSEntry OBJECT-TYPE
        SYNTAX AwcDot11QoSEntry
        MAX-ACCESS not-accessible
        STATUS current
        DESCRIPTION
            "An Entry (conceptual row) in the Aironet Quality of
            Service Table.

            ifIndex - Each 802.11 interface is represented by an
            ifEntry.  Interface tables in this MIB module are indexed
            by ifIndex."

        INDEX { ifIndex,
                awcDot11QoSCoS}
    ::= {  awcDot11QoSTable  1 }

AwcDot11QoSEntry ::= SEQUENCE {
            awcDot11QoSCoS      INTEGER,
            awcDot11QoSCWmin    INTEGER,
            awcDot11QoSCWmax    INTEGER
            }


awcDot11QoSCoS OBJECT-TYPE
        SYNTAX INTEGER (1..8)
        MAX-ACCESS not-accessible
        STATUS current
        DESCRIPTION
            "The auxiliary variable used to identify instances
            of the columnar objects in the Aironet Quality of
            Service Table.  This variable corresponds directly to
            the 802.1D traffic category ID, plus 1."
    ::= {  awcDot11QoSEntry 1 }

awcDot11QoSCWmin OBJECT-TYPE
        SYNTAX INTEGER (0..1023)
        MAX-ACCESS read-write
        STATUS current
        DESCRIPTION
            "802.11 CWmin of the traffic category.  The value of this OID
             must be one of the set 0, 1, 3, 7, 15, 31, 63, 127, 255, 511,
             or 1023, and must be less than or equal to awcDot11QoSCWmax."
    ::= {  awcDot11QoSEntry 2 }

awcDot11QoSCWmax OBJECT-TYPE
        SYNTAX INTEGER (1..1023)
        MAX-ACCESS read-write
        STATUS current
        DESCRIPTION
            "802.11 CWmax of the traffic category.  The value of this OID
             must be one of the set 1, 3, 7, 15, 31, 63, 127, 255, 511,
             or 1023, and must be greater than or equal to awcDot11QoSCWmin."
    ::= {  awcDot11QoSEntry 3 }


awcDot11res OBJECT IDENTIFIER ::=       {awc802dot11 3}

awcDot11resAttribute OBJECT IDENTIFIER ::=       {awcDot11res 1}

awcDot11ResourceInfoTable OBJECT-TYPE
                SYNTAX SEQUENCE OF AwcDot11ResourceInfoEntry
                MAX-ACCESS not-accessible
                STATUS current
                DESCRIPTION
                        "Resource Info Table attributes.  In tabular
                         form to allow for multiple instances on an
                         agent."
        ::= {  awcDot11resAttribute 2 }

awcDot11ResourceInfoEntry OBJECT-TYPE
                SYNTAX AwcDot11ResourceInfoEntry
                MAX-ACCESS not-accessible
                STATUS current
                DESCRIPTION
                        "An entry in the awcDot11ResourceInfoTable
                         table."
                INDEX {ifIndex}
        ::= {  awcDot11ResourceInfoTable 1 }

AwcDot11ResourceInfoEntry ::=
                SEQUENCE {
                         awcDot11FirmwareBootstrapVersion DisplayString
                         }

awcDot11FirmwareBootstrapVersion OBJECT-TYPE
                SYNTAX DisplayString (SIZE(0..128))
                MAX-ACCESS read-only
                STATUS current
                DESCRIPTION
                        "The firmware version of the radio boot block.
                         Max. string length is 128 octets."
        ::= {  awcDot11ResourceInfoEntry 1 }

awcDot11phy OBJECT IDENTIFIER ::=       {awc802dot11 4}

awcDot11PhyOperationTable OBJECT-TYPE
                SYNTAX SEQUENCE OF AwcDot11PhyOperationEntry
                MAX-ACCESS not-accessible
                STATUS current
                DESCRIPTION
                        "awcDot11PhyOperationTable attributes.  In
                         tabular form to allow for multiple instances
                         on an agent."
        ::= {  awcDot11phy 1 }

awcDot11PhyOperationEntry OBJECT-TYPE
                SYNTAX AwcDot11PhyOperationEntry
                MAX-ACCESS not-accessible
                STATUS current
                DESCRIPTION
                        "An entry in the awcDot11PhyOperationTable
                         table."
                INDEX {ifIndex}
        ::= {  awcDot11PhyOperationTable 1 }

AwcDot11PhyOperationEntry ::=
                SEQUENCE {
                         awcDot11CurrentCarrierSet     INTEGER,
                         awcDot11ModulationType        INTEGER,
                         awcDot11PreambleType          INTEGER,
                         awcDot11PHYType               INTEGER
                         }

awcDot11CurrentCarrierSet OBJECT-TYPE
                SYNTAX INTEGER {usa(0), europe(1), japan(2), spain(3),
                                france(4), belgium(5), israel(6),
                                canada(7), australia(8), japanWide(9),
                                usa5GHz(11), europe5GHz(12), japan5GHz(13),
                                singapore5GHz(14), taiwan5GHz(15), china(16)}
                MAX-ACCESS read-only
                STATUS current
                DESCRIPTION
                        "The carrier set of the device.  The Carrier
                         Set implies a Regulatory Domain, but
                         geographic-specific restrictions within a
                         Regulatory Domain may necessitate several
                         Carrier Sets within the Regulatory Domain."
        ::= {  awcDot11PhyOperationEntry 1 }

awcDot11ModulationType OBJECT-TYPE
                SYNTAX INTEGER {standard(1), mok(2)}
                MAX-ACCESS read-write
                STATUS current
                DESCRIPTION
                        "The RF modulation of the radio."
                DEFVAL { standard }
        ::= {  awcDot11PhyOperationEntry 2 }

awcDot11PreambleType OBJECT-TYPE
                SYNTAX INTEGER {long(1), short(2)}
                MAX-ACCESS read-write
                STATUS current
                DESCRIPTION
                        "The current radio preamble type in use by the
                         Station.
                         Possible values:
                         1 = Use long preambles whenever possible.
                         2 = Use only short preambles."
        ::= {  awcDot11PhyOperationEntry 3 }

awcDot11PHYType OBJECT-TYPE
        SYNTAX INTEGER {fhss(1), dsss(2), irbaseband(3), dsssDot11A(11)}
        MAX-ACCESS read-only
        STATUS current
        DESCRIPTION

        "This is an 8-bit integer value that identifies the PHY type
        supported by the attached PLCP and PMD. Currently defined
        values and their corresponding PHY types are:

        FHSS 2.4 GHz = 01 , DSSS 2.4 GHz = 02, IR Baseband = 03,
        DSSS 5.0 GHz = 11"

        ::= {  awcDot11PhyOperationEntry 5 }


awcDot11PhyFHSSTable OBJECT-TYPE
                SYNTAX SEQUENCE OF AwcDot11PhyFHSSEntry
                MAX-ACCESS not-accessible
                STATUS current
                DESCRIPTION
                        "awcDot11PhyFHSSTable attributes.  In tabular
                         form to allow for multiple instances on an
                         agent."
        ::= {  awcDot11phy 4 }

awcDot11PhyFHSSEntry OBJECT-TYPE
                SYNTAX AwcDot11PhyFHSSEntry
                MAX-ACCESS not-accessible
                STATUS current
                DESCRIPTION
                        "An entry in the awcDot11PhyFHSSTable table."
                INDEX {ifIndex}
        ::= {  awcDot11PhyFHSSTable 1 }

AwcDot11PhyFHSSEntry ::=
                SEQUENCE {
                         awcDot11Compatible3100     TruthValue
                         }

awcDot11Compatible3100 OBJECT-TYPE
                SYNTAX TruthValue
                MAX-ACCESS read-write
                STATUS current
                DESCRIPTION
                        "Boolean on whether or not the Station should
                         use 1Mb/sec management frames to be compatible
                         with Aironet 3100 series radios."
                DEFVAL { false }
        ::= {  awcDot11PhyFHSSEntry 1 }


awcDot11PhyDSSSTable OBJECT-TYPE
                SYNTAX SEQUENCE OF AwcDot11PhyDSSSEntry
                MAX-ACCESS not-accessible
                STATUS current
                DESCRIPTION
                        "awcDot11PhyDSSSTable attributes.  In tabular
                         form to allow for multiple instances on an
                         agent."
        ::= {  awcDot11phy 5 }

awcDot11PhyDSSSEntry OBJECT-TYPE
                SYNTAX AwcDot11PhyDSSSEntry
                MAX-ACCESS not-accessible
                STATUS current
                DESCRIPTION
                        "An entry in the awcDot11PhyDSSSTable table."
                INDEX {ifIndex}
        ::= {  awcDot11PhyDSSSTable 1 }

AwcDot11PhyDSSSEntry ::=
                SEQUENCE {
                         awcDot11Compatible4500         TruthValue,
                         awcDot11ChannelAutoImplemented TruthValue,
                         awcDot11ChannelAutoEnabled     TruthValue,
                         awcDot11CurrentChannel         INTEGER
                         }

awcDot11Compatible4500 OBJECT-TYPE
                SYNTAX TruthValue
                MAX-ACCESS read-write
                STATUS current
                DESCRIPTION
                        "Boolean on whether or not the Station should
                         use 2Mb/sec management frames to be compatible
                         with Aironet 4500 series radios."
                DEFVAL { false }
        ::= {  awcDot11PhyDSSSEntry 1 }

awcDot11ChannelAutoImplemented OBJECT-TYPE
                SYNTAX TruthValue
                MAX-ACCESS read-only
                STATUS current
                DESCRIPTION
                        "If true, the radio can, when
                         awcDot11StationRole is roleAP, scan for other
                         BSS activity on all channels available in the
                         current awcDot11CurrentCarrierSet before
                         establishing its own BSS.  If false, the radio
                         can only establish its BSS on
                         dot11CurrentChannel."
        ::= {  awcDot11PhyDSSSEntry 2 }

awcDot11ChannelAutoEnabled OBJECT-TYPE
                SYNTAX TruthValue
                MAX-ACCESS read-write
                STATUS current
                DESCRIPTION
                        "If true and awcDot11StationRole is roleAP, the
                         radio will scan for other BSS activity on all
                         channels available in the current
                         awcDot11CurrentCarrierSet before establishing
                         its own BSS.  After the scan, this station
                         will establish its own BSS on the channel it
                         considers to have the least probability of
                         congestion.  If false, this station always
                         establishes its BSS on dot11CurrentChannel."
                DEFVAL { false }
        ::= {  awcDot11PhyDSSSEntry 3 }

awcDot11CurrentChannel OBJECT-TYPE
        SYNTAX INTEGER (1..14)
        MAX-ACCESS read-only
        STATUS current
        DESCRIPTION
            "The current operating frequency channel of the DSSS
             PHY, as selected either by selective scanning or
             via dot11CurrentChannel. Valid channel numbers
             are as defined in 15.4.6.2"
        REFERENCE
            "IEEE Std 802.11-Jan 14 1999, Wireless LAN Medium
             Access Control and Physical Layer Specifications,
             LAN MAN Standards Committee of the IEEE Computer
             Society, IEEE802dot11-MIB."
        ::= {  awcDot11PhyDSSSEntry 4 }

awcDot11SupportedDataRatesPrivacyTable OBJECT-TYPE
        SYNTAX SEQUENCE OF AwcDot11SupportedDataRatesPrivacyEntry
        MAX-ACCESS not-accessible
        STATUS current
        DESCRIPTION
            "For each transmit and receive bit rate, whether or not
             the radio can support WEP encryption at that rate."

    ::= {  awcDot11phy 11 }

awcDot11SupportedDataRatesPrivacyEntry OBJECT-TYPE
        SYNTAX AwcDot11SupportedDataRatesPrivacyEntry
        MAX-ACCESS not-accessible
        STATUS current
        DESCRIPTION
            "An Entry (conceptual row) in the
             awcDot11SupportedDataRatesPrivacy Table.

            ifIndex - Each 802.11 interface is represented by an
            ifEntry.  Interface tables in this MIB module are indexed
            by ifIndex."

        INDEX {ifIndex, awcDot11SupportedDataRatesPrivacyIndex}

    ::= {  awcDot11SupportedDataRatesPrivacyTable  1 }

AwcDot11SupportedDataRatesPrivacyEntry ::= SEQUENCE {
            awcDot11SupportedDataRatesPrivacyIndex  Integer32,
            awcDot11SupportedDataRatesPrivacyValue  Integer32,
            awcDot11SupportedDataRatesPrivacyImplemented
                                                    TruthValue
            }

awcDot11SupportedDataRatesPrivacyIndex OBJECT-TYPE
        SYNTAX Integer32 (1..8)
        MAX-ACCESS read-only
        STATUS current
        DESCRIPTION
            "Index object which identifies which data rate to access.
            Range is 1..8."
    ::= {  awcDot11SupportedDataRatesPrivacyEntry 1 }

awcDot11SupportedDataRatesPrivacyValue OBJECT-TYPE
       SYNTAX Integer32 (2..127)
       MAX-ACCESS read-only
       STATUS current
       DESCRIPTION
           "The receive or transmit bit rates supported by the PLCP
            and PMD, represented by a count from X’02-X’7f,
            corresponding to data rates in increments of 500Kb/s from
            1 Mb/s to 63.5 Mb/s."

   ::= {  awcDot11SupportedDataRatesPrivacyEntry 2 }

awcDot11SupportedDataRatesPrivacyImplemented OBJECT-TYPE
       SYNTAX TruthValue
       MAX-ACCESS read-only
       STATUS current
       DESCRIPTION
           "Whether or not WEP encryption is supported by the radio
            for both Transmit and Receive operations at the
            corresponding bit rate specified by
            awcDot11SupportedDataRatesPrivacyValue."
   ::= {  awcDot11SupportedDataRatesPrivacyEntry 3 }

awcDot11ChanSelectTable OBJECT-TYPE
        SYNTAX SEQUENCE OF AwcDot11ChanSelectEntry
        MAX-ACCESS not-accessible
        STATUS current
        DESCRIPTION
            "This table specifies for each 802.11 channel,
             whether the scanning process controlled by the
             awcDot11ChannelAutoEnabled can select a
             particular channel for use.  This table has an
             expansion dependent relationship on the ifTable.
             For each entry in this table, there exists at least
             an entry in the ifTable of ifType ieee80211(71).
             Entries in this table cannot be created or deleted
             by the network management system.  All entries are
             created or deleted by the agent."
        REFERENCE
            "IEEE Std 802.11-Jan 14 1999, Wireless LAN Medium
             Access Control and Physical Layer Specifications,
             LAN MAN Standards Committee of the IEEE Computer
             Society, section 15.4.6.2."
    ::= {  awcDot11phy 12 }

awcDot11ChanSelectEntry OBJECT-TYPE
        SYNTAX AwcDot11ChanSelectEntry
        MAX-ACCESS not-accessible
        STATUS current
        DESCRIPTION
            "Each entry specifies if a particular radio channel
             is enabled on a radio interface."
        INDEX {ifIndex,
               awcDot11ChanSelectChannel}

    ::= {  awcDot11ChanSelectTable  1 }

AwcDot11ChanSelectEntry ::= SEQUENCE {
            awcDot11ChanSelectChannel  INTEGER,
            awcDot11ChanSelectEnable   TruthValue
            }

awcDot11ChanSelectChannel OBJECT-TYPE
        SYNTAX INTEGER (1..14)
        MAX-ACCESS read-only
        STATUS current
        DESCRIPTION
            "802.11 channel which is a candidate for low-occupancy
             scanning."
        REFERENCE
            "IEEE Std 802.11-Jan 14 1999, Wireless LAN Medium
             Access Control and Physical Layer Specifications,
             LAN MAN Standards Committee of the IEEE Computer
             Society, section 15.4.6.2."
    ::= {  awcDot11ChanSelectEntry 1 }

awcDot11ChanSelectEnable OBJECT-TYPE
       SYNTAX TruthValue
       MAX-ACCESS read-write
       STATUS current
       DESCRIPTION
           "If true, awcDot11ChanSelectChannel is available for the
            system to use as its awcDot11CurrentChannel after scanning
            for channel occupancy.  If false, awcDot11ChanSelectChannel
            is not available."
       REFERENCE
           "IEEE Std 802.11-Jan 14 1999, Wireless LAN Medium
            Access Control and Physical Layer Specifications,
            LAN MAN Standards Committee of the IEEE Computer
            Society, IEEE802dot11-MIB."
       DEFVAL { true }
   ::= {  awcDot11ChanSelectEntry 2 }


-- ********************************************************************
-- *    End of awc802dot11 parameters
-- ********************************************************************

-- ********************************************************************
-- *  awcUserMgr parameters
-- ********************************************************************
userMgrConfigTable OBJECT-TYPE
                SYNTAX SEQUENCE OF UserMgrConfigEntry
                MAX-ACCESS not-accessible
                STATUS current
                DESCRIPTION
                        "System User attributes."
        ::= { awcUserMgr 1 }

userMgrConfigEntry OBJECT-TYPE
                SYNTAX UserMgrConfigEntry
                MAX-ACCESS not-accessible
                STATUS current
                DESCRIPTION
                        "An entry in the user manager table."
                INDEX {userMgrUserIndex}
        ::= { userMgrConfigTable 1 }

UserMgrConfigEntry ::=
                SEQUENCE {
                         userMgrUserIndex         Unsigned32,
                         userMgrUserName          DisplayString,
                         userMgrPassword          OCTET STRING,
                         userMgrCapabilities      Unsigned32,
                         userMgrStatus            RowStatus
                }

userMgrUserIndex OBJECT-TYPE
                SYNTAX Unsigned32
                MAX-ACCESS read-only
                STATUS current
                DESCRIPTION
                        "The index of the user."
        ::= {  userMgrConfigEntry 1 }

userMgrUserName OBJECT-TYPE
                SYNTAX DisplayString (SIZE(0..32))
                MAX-ACCESS read-create
                STATUS current
                DESCRIPTION
                        "The name of the user.  This should be unique
                         across all users.  Max. string length is 32
                         octets."
        ::= {  userMgrConfigEntry 2 }

userMgrPassword OBJECT-TYPE
                SYNTAX OCTET STRING (SIZE(0..24))
                MAX-ACCESS read-create
                STATUS current
                DESCRIPTION
                        "The SHA-1 hashed password of the user in the
                         user manager. When a plaintext password is
                         written, it is automatically replaced by the
                         SHA-1 Secure Hash of that plaintext, prefixed
                         by a 4-octet magic cookie.  Max. string length
                         is 24 octets."
        ::= {  userMgrConfigEntry 3 }

userMgrCapabilities OBJECT-TYPE
                SYNTAX Unsigned32
                MAX-ACCESS read-create
                STATUS current
                DESCRIPTION
                        "Bitmask of the capabilities of the user.
                         The value may be any combination (sum)
                         of the following capability values:
                         0  = none
                         1  = Administrator
                         2  = Write
                         4  = Firmware Update
                         8  = Identity Update
                        16  = SNMP Community"
        ::= {  userMgrConfigEntry 4 }

userMgrStatus OBJECT-TYPE
        SYNTAX   RowStatus
        MAX-ACCESS  read-create
        STATUS  current
        DESCRIPTION
        "Row status of the user.  Allows deletion via SNMP."
        ::= {  userMgrConfigEntry 5 }

enableUserMgr OBJECT-TYPE
                SYNTAX TruthValue
                MAX-ACCESS read-write
                STATUS current
                DESCRIPTION
                        "If true, the User Manager subsystem is active.
                         Web page, console, and SNMP access is
                         restricted in accordance with
                         userMgrCapabilities.  If false, all users have
                         full access to the system. "
                DEFVAL { false }
        ::= {  awcUserMgr 2 }

allowBrowseWithoutLogin OBJECT-TYPE
                SYNTAX TruthValue
                MAX-ACCESS read-write
                STATUS current
                DESCRIPTION
                        "If true, the HTTP user interface to read-only
                         web pages can be accessed without passing
                         HTTP authentication.  If false, any HTTP
                         access requires the user to pass HTTP
                         authentication."
                DEFVAL { true }
        ::= {  awcUserMgr 3 }

protectLegalPage OBJECT-TYPE
                SYNTAX TruthValue
                MAX-ACCESS read-write
                STATUS current
                DESCRIPTION
                        "Should the legal credits page be protected or
                         not."
                DEFVAL { false }
        ::= {  awcUserMgr 4 }

-- ********************************************************************
-- *    End of awcUserMgr parameters
-- ********************************************************************

-- ********************************************************************
-- *  awcHttpd parameters
-- ********************************************************************
defaultWebRoot OBJECT-TYPE
                SYNTAX DisplayString (SIZE(0..128))
                MAX-ACCESS read-write
                STATUS current
                DESCRIPTION
                        "File directory which contains the system's
                         web site root file index.shm.  Max. string
                         length is 128 octets."
                DEFVAL { "mfs0:/StdUI/" }
        ::= {  awcHttpd 1 }

defaultHelpRoot OBJECT-TYPE
                SYNTAX DisplayString (SIZE(0..128))
                MAX-ACCESS read-write
                STATUS current
                DESCRIPTION
                        "URL identifying the directory in which help
                         pages for the system are located.  This URL
                         is prefixed to all help page links.
                         Max. string length is 128 octets."
                DEFVAL { "http://www.cisco.com/warp/public/779/smbiz/prodconfig/help/eag/air/ap3xx" }
        ::= {  awcHttpd 2 }

getWebUI OBJECT-TYPE
                SYNTAX DisplayString (SIZE(0..128))
                MAX-ACCESS read-write
                STATUS current
                DESCRIPTION
                        "The name of an auxilliary set of HTML user
                         interface files to be loaded at system boot
                         time from defaultFileServer.  Archive
                         formats accepted include .tar and .tar.gz.
                         Max. string length is 128 octets."
                DEFVAL { "" }
        ::= {  awcHttpd 3 }

cmdInvokeGetWebUI OBJECT-TYPE
                SYNTAX AwcInvokeCommand
                MAX-ACCESS read-write
                STATUS current
                DESCRIPTION
                        "Initiate loading of the getWebUI file.

                         Commands recognized:  start."

        ::= {  awcHttpd 4 }

cmdStatusGetWebUI OBJECT-TYPE
                SYNTAX Integer32
                MAX-ACCESS read-only
                STATUS current
                DESCRIPTION
                         "Status of the most recent command to load
                          the auxilliary web User Interface pages.
                          Possible values:
                          0  = Operation completed successfully (or
                               has not taken place).
                          2  = File not found on the file server.
                          12 = Insufficient memory to load all
                               files.
                          20 = Identifier encountered while decoding
                               is an ordinary file,
                               not a directory.
                          22 = No file specified, or invalid file
                               format.
                          35 = File format is not supported.
                          68 = Operation is still in progress. Poll
                               again later.
                          72 = Operation was started, but later was
                               canceled."
        ::= {  awcHttpd 5 }

awcHttpdPort OBJECT-TYPE
                SYNTAX INTEGER (1..65535)
                MAX-ACCESS read-write
                STATUS current
                DESCRIPTION
                        "IP port number over which to perform HTTP
                         operations."
                DEFVAL { 80 }
        ::= {  awcHttpd 6 }

awcConsoleAutoApply OBJECT-TYPE
                SYNTAX TruthValue
                MAX-ACCESS read-write
                STATUS current
                DESCRIPTION
                        "The current state of 'auto apply' mode on the
                         console browser."
                DEFVAL { true }
        ::= {  awcHttpd 7 }

-- ********************************************************************
-- *    End of awcHttpd parameters
-- ********************************************************************

-- ********************************************************************
-- *  awcDnsRes parameters
-- ********************************************************************
resolverDomain OBJECT-TYPE
                SYNTAX DisplayString (SIZE(0..128))
                MAX-ACCESS read-only
                STATUS current
                DESCRIPTION
                        "The name of the resolver domain currently in
                         use by the system. Max. string length of 128
                         octets."
                DEFVAL { "" }
        ::= {  awcDnsRes 1 }

resolverDomainSuffix OBJECT-TYPE
                SYNTAX DisplayString (SIZE(0..128))
                MAX-ACCESS read-write
                STATUS current
                DESCRIPTION
                        "The suffix name of the resolver domain.  Used
                         to abbreviate displayed host names.
                         Max. string length is 128 octets."
                DEFVAL { "" }
        ::= {  awcDnsRes 2 }

resolverDomainServerTable OBJECT-TYPE
                SYNTAX SEQUENCE OF ResolverDomainServerEntry
                MAX-ACCESS not-accessible
                STATUS current
                DESCRIPTION
                        "Table of DNS Name Servers currently in use by
                         the system."
        ::= { awcDnsRes 3 }

resolverDomainServerEntry OBJECT-TYPE
                SYNTAX ResolverDomainServerEntry
                MAX-ACCESS not-accessible
                STATUS current
                DESCRIPTION
                        "An entry in resolverDomainServerTable."
                INDEX {resolverDomainServerPriority}
        ::= { resolverDomainServerTable 1 }

ResolverDomainServerEntry ::=
                SEQUENCE {
                        resolverDomainServerPriority    INTEGER,
                        resolverDomainServer            DisplayString}

resolverDomainServerPriority OBJECT-TYPE
                SYNTAX INTEGER (1..3)
                MAX-ACCESS read-only
                STATUS current
                DESCRIPTION
                        "The priority order in which a domain name
                         server is queried."
        ::= {  resolverDomainServerEntry 1 }

resolverDomainServer OBJECT-TYPE
                SYNTAX DisplayString
                MAX-ACCESS read-only
                STATUS current
                DESCRIPTION
                        "The IP Address of a domain name server
                         currently in use by the system."
        ::= {  resolverDomainServerEntry 2 }

defaultResolverDomain OBJECT-TYPE
                SYNTAX DisplayString (SIZE(0..128))
                MAX-ACCESS read-write
                STATUS current
                DESCRIPTION
                        "The name of the resolver domain to be used by
                         the system unless overridden by a BOOTP or
                         DHCP server. Max. string length of 128
                         octets."
                DEFVAL { "" }
        ::= {  awcDnsRes 4 }

defaultResolverDomainServerTable OBJECT-TYPE
                SYNTAX SEQUENCE OF DefaultResolverDomainServerEntry
                MAX-ACCESS not-accessible
                STATUS current
                DESCRIPTION
                        "Table of DNS Name Servers to be used by the
                         system unless overridden by a BOOTP or DHCP
                         server."
        ::= { awcDnsRes 5 }

defaultResolverDomainServerEntry OBJECT-TYPE
                SYNTAX DefaultResolverDomainServerEntry
                MAX-ACCESS not-accessible
                STATUS current
                DESCRIPTION
                        "An entry in defaultResolverDomainServerTable."
                INDEX {defaultResolverDomainServerPriority}
        ::= { defaultResolverDomainServerTable 1 }

DefaultResolverDomainServerEntry ::=
                SEQUENCE {
                        defaultResolverDomainServerPriority
                                                        INTEGER,
                        defaultResolverDomainServer     DisplayString}

defaultResolverDomainServerPriority OBJECT-TYPE
                SYNTAX INTEGER (1..3)
                MAX-ACCESS read-only
                STATUS current
                DESCRIPTION
                        "The priority order in which a domain name
                         server is queried."
        ::= {  defaultResolverDomainServerEntry 1 }

defaultResolverDomainServer OBJECT-TYPE
                SYNTAX DisplayString
                MAX-ACCESS read-write
                STATUS current
                DESCRIPTION
                        "The IP Address of a domain name server to be
                         used by the system unless overridden by a
                         BOOTP or DHCP server."
        ::= {  defaultResolverDomainServerEntry 2 }

-- ********************************************************************
-- *    End of awcDnsRes parameters
-- ********************************************************************

-- ********************************************************************
-- *  awcSnmp parameters
-- ********************************************************************
snmpTrapDest OBJECT-TYPE
                SYNTAX DisplayString (SIZE(0..128))
                MAX-ACCESS read-write
                STATUS current
                DESCRIPTION
                        "The destination of an SNMP trap.  This may be
                         any DNS-recognizable IP address.  Max. string
                         length is 128 octets."
                DEFVAL { "" }
        ::= {  awcSnmp 1 }

snmpTrapCommunity OBJECT-TYPE
                SYNTAX DisplayString (SIZE(0..128))
                MAX-ACCESS read-write
                STATUS current
                DESCRIPTION
                        "The community name of the trap.
                         Max. string length is 128 octets."
                DEFVAL { "" }
        ::= {  awcSnmp 2 }

-- ********************************************************************
-- *    End of awcSnmp parameters
-- ********************************************************************

-- ********************************************************************
-- *  awcSntp parameters
-- ********************************************************************
defaultSntpServer OBJECT-TYPE
                SYNTAX DisplayString (SIZE(0..128))
                MAX-ACCESS read-write
                STATUS current
                DESCRIPTION
                        "The name of the SNTP server to be use by the
                         system, unless overridden by a BOOTP or DHCP
                         server. Max. string length is 128 octets."
                DEFVAL { "" }
        ::= {  awcSntp 1 }

sntpServer OBJECT-TYPE
                SYNTAX DisplayString (SIZE(0..128))
                MAX-ACCESS read-only
                STATUS current
                DESCRIPTION
                        "The name of the SNTP server currently in use
                         by the system.  Max. string length is 128
                         octets."
        ::= {  awcSntp 2 }

-- ********************************************************************
-- *    End of awcSntp parameters
-- ********************************************************************

-- ********************************************************************
-- *  awcForwardTbl parameters
-- ********************************************************************
awcFtStatistics OBJECT IDENTIFIER ::=       {awcForwardTbl 1}

awcFtMcastAddr OBJECT-TYPE
                SYNTAX Integer32
                MAX-ACCESS read-only
                STATUS current
                DESCRIPTION
                        "Count of multicast addresses observed by the
                         system."
        ::= {  awcFtStatistics 1 }

awcFtDsHost OBJECT-TYPE
                SYNTAX Integer32
                MAX-ACCESS read-only
                STATUS current
                DESCRIPTION
                        "Count of DS (infrastructure) host addresses
                         observed by the system over its own DS network
                         interface (Ethernet)."
        ::= {  awcFtStatistics 3 }

awcFtBridgeHost OBJECT-TYPE
                SYNTAX Integer32
                MAX-ACCESS read-only
                STATUS current
                DESCRIPTION
                        "Count of DS (infrastructure) host addresses
                         observed by the system on the remote side of
                         a bridge."
        ::= {  awcFtStatistics 5 }

awcFtClientSTA OBJECT-TYPE
                SYNTAX Integer32
                MAX-ACCESS read-only
                STATUS current
                DESCRIPTION
                        "Count of Client Station addresses observed by
                         the system."
        ::= {  awcFtStatistics 7 }

awcFtClientSTASelf OBJECT-TYPE
                SYNTAX Integer32
                MAX-ACCESS read-only
                STATUS current
                DESCRIPTION
                        "Count of Client Stations which are Associated
                         to the system."
        ::= {  awcFtStatistics 8 }

awcFtBridge OBJECT-TYPE
                SYNTAX Integer32
                MAX-ACCESS read-only
                STATUS current
                DESCRIPTION
                        "Count of non-root Bridge addresses observed by
                         the system."
        ::= {  awcFtStatistics 9 }

awcFtBridgeSelf OBJECT-TYPE
                SYNTAX Integer32
                MAX-ACCESS read-only
                STATUS current
                DESCRIPTION
                        "Count of non-root Bridges which are Associated
                         to the system."
        ::= {  awcFtStatistics 10 }

awcFtRepeater OBJECT-TYPE
                SYNTAX Integer32
                MAX-ACCESS read-only
                STATUS current
                DESCRIPTION
                        "Count of Repeater addresses observed by the
                         system."
        ::= {  awcFtStatistics 11 }

awcFtRepeaterSelf OBJECT-TYPE
                SYNTAX Integer32
                MAX-ACCESS read-only
                STATUS current
                DESCRIPTION
                        "Count of Repeater devices which are Associated
                         to the system."
        ::= {  awcFtStatistics 12 }

awcFtAccessPoint OBJECT-TYPE
                SYNTAX Integer32
                MAX-ACCESS read-only
                STATUS current
                DESCRIPTION
                        "Count of Access Point addresses observed by
                         the system."
        ::= {  awcFtStatistics 13 }

awcFtBridgeRoot OBJECT-TYPE
                SYNTAX Integer32
                MAX-ACCESS read-only
                STATUS current
                DESCRIPTION
                        "Count of Root Bridge addresses observed by
                         the system."
        ::= {  awcFtStatistics 15 }


awcFtConfig OBJECT IDENTIFIER ::=       {awcForwardTbl 2}

awcFtMaxNumEntries OBJECT-TYPE
                SYNTAX Integer32
                MAX-ACCESS read-write
                STATUS current
                DESCRIPTION
                        "The maximum number of entries in the
                         forwarding table.  Must be a power of 2 from
                         1024 to 65536.  The number of entries controls
                         the size of the forwarding table and the hash
                         algorithm used by the forwarding table.
                         Changing the number of entries requires a
                         system reboot."
                DEFVAL { 8192 }
        ::= {  awcFtConfig 1 }

awcFtTimeoutSecUnknown OBJECT-TYPE
				SYNTAX Unsigned32
                UNITS "seconds"
                MAX-ACCESS read-write
                STATUS current
                DESCRIPTION
                        "The default number of seconds an Entry with
                         awcTpFdbClassID=unknown will remain in the
                         Forwarding Table before being staled-out."
                DEFVAL { 300 }
        ::= {  awcFtConfig 2 }

awcFtTimeoutSecMcastAddr OBJECT-TYPE
				SYNTAX Unsigned32
                UNITS "seconds"
                MAX-ACCESS read-write
                STATUS current
                DESCRIPTION
                        "The default number of seconds an Entry with
                         awcTpFdbClassID=multicast will remain in the
                         Forwarding Table before being staled-out."
                DEFVAL { 28800 }
        ::= {  awcFtConfig 3 }

awcFtTimeoutSecDsHost OBJECT-TYPE
				SYNTAX Unsigned32
                UNITS "seconds"
                MAX-ACCESS read-write
                STATUS current
                DESCRIPTION
                        "The default number of seconds an Entry with
                         awcTpFdbClassID=dsHost will remain in the
                         Forwarding Table before being staled-out."
                DEFVAL { 1800 }
        ::= {  awcFtConfig 4 }

awcFtTimeoutSecBridgeHost OBJECT-TYPE
				SYNTAX Unsigned32
                UNITS "seconds"
                MAX-ACCESS read-write
                STATUS current
                DESCRIPTION
                        "The default number of seconds an Entry with
                         awcTpFdbClassID=bridgeHost will remain in the
                         Forwarding Table before being staled-out."
                DEFVAL { 1800 }
        ::= {  awcFtConfig 5 }

awcFtTimeoutSecClientSTA OBJECT-TYPE
				SYNTAX Unsigned32
                UNITS "seconds"
                MAX-ACCESS read-write
                STATUS current
                DESCRIPTION
                        "The default number of seconds an Entry with
                         awcTpFdbClassID=clientStation will remain in
                         the Forwarding Table before being staled-out."
                DEFVAL { 1800 }
        ::= {  awcFtConfig 6 }

awcFtTimeoutSecBridge OBJECT-TYPE
				SYNTAX Unsigned32
                UNITS "seconds"
                MAX-ACCESS read-write
                STATUS current
                DESCRIPTION
                        "The default number of seconds an Entry with
                         awcTpFdbClassID=bridge will remain in the
                         Forwarding Table before being staled-out."
                DEFVAL { 28800 }
        ::= {  awcFtConfig 7 }

awcFtTimeoutSecRepeater OBJECT-TYPE
				SYNTAX Unsigned32
                UNITS "seconds"
                MAX-ACCESS read-write
                STATUS current
                DESCRIPTION
                        "The default number of seconds an Entry with
                         awcTpFdbClassID=repeater will remain in the
                         Forwarding Table before being staled-out."
                DEFVAL { 28800 }
        ::= {  awcFtConfig 8 }

awcFtTimeoutSecAccessPoint OBJECT-TYPE
				SYNTAX Unsigned32
                UNITS "seconds"
                MAX-ACCESS read-write
                STATUS current
                DESCRIPTION
                        "The default number of seconds an Entry with
                         awcTpFdbClassID=accessPoint will remain in the
                         Forwarding Table before being staled-out."
                DEFVAL { 28800 }
        ::= {  awcFtConfig 9 }

awcFtTimeoutSecBridgeRoot OBJECT-TYPE
				SYNTAX Unsigned32
                UNITS "seconds"
                MAX-ACCESS read-write
                STATUS current
                DESCRIPTION
                        "The default number of seconds an Entry with
                         awcTpFdbClassID=bridgeRoot will remain in the
                         Forwarding Table before being staled-out."
                DEFVAL { 28800 }
        ::= {  awcFtConfig 10 }

awcFtEnableAwcTpFdbTable OBJECT-TYPE
                SYNTAX TruthValue
                MAX-ACCESS read-write
                STATUS current
                DESCRIPTION
                        "If true, the system will populate the
                         awcTpFdbEntry MIB for all forwarding table
                         entries.  This improves management statistics.
                         If false, the system will not populate the
                         awcTpFdbEntry MIB for any forwarding table
                         entries.  This improves speed and memory
                         utilization."
                DEFVAL { true }
        ::= {  awcFtConfig 11 }

awcFtEnableMacAuthServer OBJECT-TYPE
                SYNTAX TruthValue
                MAX-ACCESS read-write
                STATUS current
                DESCRIPTION
                        "If true, the system will contact a AAA server
                         for retrieving dot1dStaticTable information
                         for new forwarding table entries if a
                         dot1dStaticTable entry does not already exist
                         for the host address."
                DEFVAL { false }
        ::= {  awcFtConfig 12 }

awcFtRogueApAlertTimeout OBJECT-TYPE
                SYNTAX INTEGER (0..1440)
                MAX-ACCESS read-write
                STATUS current
                DESCRIPTION
                "The minimum number of minutes after a Possible
                 Rogue status is reported about a device before
                 another Possible Rogue status report is
                 issued by this system about the same device."
                DEFVAL { 30 }
        ::= {  awcFtConfig 13 }

awcFtEnableMacOrEapAuth OBJECT-TYPE
                SYNTAX TruthValue
                MAX-ACCESS read-write
                STATUS current
                DESCRIPTION
                        "If true, the system grants full access to those
                         clients which have successfully completed either
                         MAC or EAP authentication."
                DEFVAL { false }
        ::= {  awcFtConfig 14 }

awcFtDot1dTpFdbTableEnable OBJECT-TYPE
                SYNTAX TruthValue
                MAX-ACCESS read-write
                STATUS current
                DESCRIPTION
                        "If true, the system will populate the
                         dot1dTpFdbEntry MIB for all forwarding table
                         entries.  This improves management statistics.
                         If false, the system will not populate the
                         dot1dTpFdbEntry MIB for any forwarding table
                         entries.  This improves speed and memory
                         utilization."
                DEFVAL { true }
        ::= {  awcFtConfig 15 }

awcFtEnableMcastMapping OBJECT-TYPE
                SYNTAX TruthValue
                MAX-ACCESS read-write
                STATUS current
                DESCRIPTION
                        "If true, the system will map multicast forwarding
                         table entries to the broadcast entry.
                         This improves speed and memory utilization.
                         If false, the system will create an entry
                         for each unique multicast address. This improves
                         management statistics and allows filtering of
                         specific multicast addresses."
                DEFVAL { false }
        ::= {  awcFtConfig 16 }


AwcTpFdbClassID ::= TEXTUAL-CONVENTION
  STATUS       current
  DESCRIPTION
          "Description of the general 802.11 classification of a host."
  SYNTAX       INTEGER { unknown(1), multicast(2), dsHost(3),
                         bridgeHost(4), clientStation(5), bridge(6),
                         repeater(7), accessPoint(8), bridgeRoot(9) }

awcTpFdbTable OBJECT-TYPE
                SYNTAX  SEQUENCE OF AwcTpFdbEntry
                MAX-ACCESS not-accessible
                STATUS  current
                DESCRIPTION
                        "A table that contains information about
                        entries for which the bridge has forwarding
                        and/or filtering information.  This information
                        is used by the transparent bridging function
                        for maintaining statistics about each entry."
        ::= { awcForwardTbl 3 }

awcTpFdbEntry OBJECT-TYPE
                SYNTAX  AwcTpFdbEntry
                MAX-ACCESS  not-accessible
                STATUS  current
                DESCRIPTION
                        "Information about a specific MAC address
                        for which the bridge has some forwarding and/or
                        filtering information."
                INDEX   { awcTpFdbAddress }
        ::= { awcTpFdbTable 1 }

AwcTpFdbEntry ::=
                SEQUENCE {
                    awcTpFdbAddress                   MacAddress,
                    awcTpFdbClassID                   AwcTpFdbClassID,
                    awcTpFdbSrcPktsImmed              Counter32,
                    awcTpFdbSrcOctetsImmed            Counter32,
                    awcTpFdbSrcErrorPktsImmed         Counter32,
                    awcTpFdbSrcErrorOctetsImmed       Counter32,
                    awcTpFdbDestPktsImmed             Counter32,
                    awcTpFdbDestOctetsImmed           Counter32,
                    awcTpFdbDestErrorPktsImmed        Counter32,
                    awcTpFdbDestErrorOctetsImmed      Counter32,
                    awcTpFdbDestMaxRetryErrorsImmed   Counter32,
                    awcTpFdbIPv4Addr                  IpAddress
                }

awcTpFdbAddress OBJECT-TYPE
                SYNTAX  MacAddress
                MAX-ACCESS  read-only
                STATUS  current
                DESCRIPTION
                        "A MAC address for which the bridge has
                        forwarding and/or filtering information."
        ::= { awcTpFdbEntry 1 }

awcTpFdbClassID OBJECT-TYPE
                SYNTAX  AwcTpFdbClassID
                MAX-ACCESS  read-only
                STATUS  current
                DESCRIPTION
                        "Observed general 802.11 classification of the
                         entry."
        ::= { awcTpFdbEntry 2 }

awcTpFdbSrcPktsImmed OBJECT-TYPE
        SYNTAX Counter32
        MAX-ACCESS read-only
        STATUS current
        DESCRIPTION
            "Number of observed packets for which this entry was the
             source."
    ::= {  awcTpFdbEntry 3 }

awcTpFdbSrcOctetsImmed OBJECT-TYPE
        SYNTAX Counter32
        MAX-ACCESS read-only
        STATUS current
        DESCRIPTION
            "Number of observed octets for which this entry was the
             source."
    ::= {  awcTpFdbEntry 4 }

awcTpFdbSrcErrorPktsImmed OBJECT-TYPE
        SYNTAX Counter32
        MAX-ACCESS read-only
        STATUS current
        DESCRIPTION
            "Number of observed error packets for which this entry was
             the source."
    ::= {  awcTpFdbEntry 5 }

awcTpFdbSrcErrorOctetsImmed OBJECT-TYPE
        SYNTAX Counter32
        MAX-ACCESS read-only
        STATUS current
        DESCRIPTION
            "Number of observed error octets for which this entry was
             the source."
    ::= {  awcTpFdbEntry 6 }

awcTpFdbDestPktsImmed OBJECT-TYPE
        SYNTAX Counter32
        MAX-ACCESS read-only
        STATUS current
        DESCRIPTION
            "Number of observed packets for which this entry was the
             destination."
    ::= {  awcTpFdbEntry 7 }

awcTpFdbDestOctetsImmed OBJECT-TYPE
        SYNTAX Counter32
        MAX-ACCESS read-only
        STATUS current
        DESCRIPTION
            "Number of observed octets for which this entry was the
             destination."
    ::= {  awcTpFdbEntry 8 }

awcTpFdbDestErrorPktsImmed OBJECT-TYPE
        SYNTAX Counter32
        MAX-ACCESS read-only
        STATUS current
        DESCRIPTION
            "Number of observed error packets for which this entry was
             the destination. This count includes
             awcTpFdbDestMaxRetryErrorsImmed."
    ::= {  awcTpFdbEntry 9 }

awcTpFdbDestErrorOctetsImmed OBJECT-TYPE
        SYNTAX Counter32
        MAX-ACCESS read-only
        STATUS current
        DESCRIPTION
            "Number of observed error octets for which this entry was
             the destination."
    ::= {  awcTpFdbEntry 10 }

awcTpFdbDestMaxRetryErrorsImmed OBJECT-TYPE
        SYNTAX Counter32
        MAX-ACCESS read-only
        STATUS current
        DESCRIPTION
            "Number of observed max-retry error packets for which this
             entry was the destination."
    ::= {  awcTpFdbEntry 11 }

awcTpFdbIPv4Addr OBJECT-TYPE
        SYNTAX IpAddress
        MAX-ACCESS read-only
        STATUS current
        DESCRIPTION
                "Observed IPv4 network address of the entry."
    ::= {  awcTpFdbEntry 16 }


AwcDdpProdDevID ::= TEXTUAL-CONVENTION
  STATUS       current
  DESCRIPTION
          "Aironet DDP Product Device ID of a host."
  SYNTAX       INTEGER {
                   tokenRingAP(74),
                   ethernetAP(76),
                   ethernetBridge(77),
                   tokenRingBridge(78),
                   pc3000Client(84),
                   serialUC(85),
                   ethernetUC(86),
                   pc3500Client(101),
                   pc4500Client(102),
                   generic80211Client(104),
                   pc4800Client(109),
                   pc3100Client(110),
                   mc(111),
                   ethernetClient(112),
                   pc2500Client(113),
                   pc4800bClient(117),
                   euc(120),
                   homeAP(121),
                   eucNoDiversity(122),
                   emcNoDiversity(123),
                   emc(124),
                   series350Client(127),
                   series370Client(128),
                   multicast(240),
                   unknown(241),
                   tokenRingHost(253),
                   ethernetHost(255)
                   }

AwcDdpRadioDevID ::= TEXTUAL-CONVENTION
  STATUS       current
  DESCRIPTION
          "Aironet DDP Radio Device ID of a host."
  SYNTAX       INTEGER {
                   unknown(0),
                   tma900(1),
                   tma2400(2),
                   pc3500(3),
                   pc3000(4),
                   tma2040(5),
                   pc4500(6),
                   pc4800(12),
                   pc3100(13),
                   series350(34),
                   series370(35)
                   }

awcTpFdbDdpTable OBJECT-TYPE
                SYNTAX  SEQUENCE OF AwcTpFdbDdpEntry
                MAX-ACCESS  not-accessible
                STATUS  current
                DESCRIPTION
                        "A table that contains information about
                        entries for which the bridge has forwarding
                        and/or filtering information.  This table
                        maintains only Aironet-specific information
                        about each entry."
        ::= { awcForwardTbl 4 }

awcTpFdbDdpEntry OBJECT-TYPE
                SYNTAX  AwcTpFdbDdpEntry
                MAX-ACCESS  not-accessible
                STATUS  current
                DESCRIPTION
                        "Information about a specific MAC address
                        for which the bridge has some forwarding and/or
                        filtering information."
                INDEX   { awcTpFdbDdpAddress }
        ::= { awcTpFdbDdpTable 1 }

AwcTpFdbDdpEntry ::=
                SEQUENCE {
                    awcTpFdbDdpAddress                MacAddress,
                    awcTpFdbDdpSysName                DisplayString,
                    awcTpFdbDdpProdDevID              AwcDdpProdDevID,
                    awcTpFdbDdpRadioDevID             AwcDdpRadioDevID,
                    awcTpFdbDdpSwVerMajor             INTEGER,
                    awcTpFdbDdpSwVerMinor             INTEGER,
                    awcTpFdbDdpSwVerBeta              INTEGER,
                    awcTpFdbDdpUptime                 Unsigned32,
                    awcTpFdbDdpNumAnnounceSent        Unsigned32,
                    awcTpFdbDdpNumAssociated          INTEGER,
                    awcTpFdbDdpLoad                   INTEGER,
                    awcTpFdbDdpDistFromDS             INTEGER
                }

awcTpFdbDdpAddress OBJECT-TYPE
                SYNTAX  MacAddress
                MAX-ACCESS  read-only
                STATUS  current
                DESCRIPTION
                        "A MAC address for which the bridge has
                        forwarding and/or filtering information."
        ::= { awcTpFdbDdpEntry 1 }

awcTpFdbDdpSysName OBJECT-TYPE
              SYNTAX  DisplayString (SIZE (0..255))
              MAX-ACCESS  read-only
              STATUS  current
              DESCRIPTION
                      "The Aironet DDP System Name of the entry."
        ::= { awcTpFdbDdpEntry 2 }

awcTpFdbDdpProdDevID OBJECT-TYPE
              SYNTAX  AwcDdpProdDevID
              MAX-ACCESS  read-only
              STATUS  current
              DESCRIPTION
                      "The Aironet DDP Product Device ID of the entry."
        ::= { awcTpFdbDdpEntry 3 }

awcTpFdbDdpRadioDevID OBJECT-TYPE
              SYNTAX  AwcDdpRadioDevID
              MAX-ACCESS  read-only
              STATUS  current
              DESCRIPTION
                      "The Aironet DDP Radio Device ID of the entry."
        ::= { awcTpFdbDdpEntry 4 }

awcTpFdbDdpSwVerMajor OBJECT-TYPE
              SYNTAX  INTEGER (0..255)
              MAX-ACCESS  read-only
              STATUS  current
              DESCRIPTION
                      "The Aironet DDP Major Software Version Number of
                       the entry.  If unknown, the value 0 is returned."
        ::= { awcTpFdbDdpEntry 5 }

awcTpFdbDdpSwVerMinor OBJECT-TYPE
              SYNTAX  INTEGER (0..255)
              MAX-ACCESS  read-only
              STATUS  current
              DESCRIPTION
                      "The Aironet DDP Minor Software Version Number of
                       the entry."
        ::= { awcTpFdbDdpEntry 6 }

awcTpFdbDdpSwVerBeta OBJECT-TYPE
              SYNTAX  INTEGER (0..255)
              MAX-ACCESS  read-only
              STATUS  current
              DESCRIPTION
                      "The Aironet DDP Beta Software Version Number of
                       the entry. This number is always 0 for
                       officially-released software."
        ::= { awcTpFdbDdpEntry 7 }

awcTpFdbDdpUptime OBJECT-TYPE
              SYNTAX  Unsigned32
              UNITS "seconds"
              MAX-ACCESS  read-only
              STATUS  current
              DESCRIPTION
                      "The time in seconds that the entry has been
                       operational."
        ::= { awcTpFdbDdpEntry 8 }

awcTpFdbDdpNumAnnounceSent OBJECT-TYPE
              SYNTAX  Unsigned32
              MAX-ACCESS  read-only
              STATUS  current
              DESCRIPTION
                      "The number of times the entry itself believes
                       that it has issued some form of Aironet DDP
                       Presense Announcement. If this field decreases,
                       the entry has probably been reset."
        ::= { awcTpFdbDdpEntry 9 }

awcTpFdbDdpNumAssociated OBJECT-TYPE
              SYNTAX  INTEGER (0..2007)
              MAX-ACCESS  read-only
              STATUS  current
              DESCRIPTION
                      "The number of Stations currently Associated
                       with the entry."
        ::= { awcTpFdbDdpEntry 10 }

awcTpFdbDdpLoad OBJECT-TYPE
              SYNTAX  INTEGER (0..100)
              MAX-ACCESS  read-only
              STATUS  current
              DESCRIPTION
                      "An approximation of the percentage of offered
                       vs. theoretically-available load on the host's
                       radio interface."
        ::= { awcTpFdbDdpEntry 11 }

awcTpFdbDdpDistFromDS OBJECT-TYPE
              SYNTAX  INTEGER (0..255)
              MAX-ACCESS  read-only
              STATUS  current
              DESCRIPTION
                      "The Bridging Distance or Number of Hops between
                       the entry and the backbone Distribution System
                       (DS). If 0, the entry is directly connected to
                       the DS."
        ::= { awcTpFdbDdpEntry 12 }


AwcDot11ClientState ::= TEXTUAL-CONVENTION
  STATUS       current
  DESCRIPTION
          "IEEE 802.11 Station Service State.

          state0 =
                    Station not able to send any frames whatsoever.
                    It is most likely not yet configured.
          state1 =
                    Station can send Class 1 frames.  It is
                    Unauthenticated and Unassociated.
          state2 =
                    Station can send Class 2 frames.  It is
                    Authenticated, but is as yet Unassociated.
          state3 =
                    Station can send Class 3 frames.  It is both
                    Authenticated and Associated."
  SYNTAX       INTEGER {
                   state0(1),
                   state1(2),
                   state2(3),
                   state3(4)
                   }

awcDot11TpFdbTable OBJECT-TYPE
                SYNTAX  SEQUENCE OF AwcDot11TpFdbEntry
                MAX-ACCESS  not-accessible
                STATUS  current
                DESCRIPTION
                        "A table that contains information about
                        entries for which the bridge has forwarding
                        and/or filtering information.  This table
                        maintains only 802.11-specific information
                        about each entry."
        ::= { awcForwardTbl 5 }

awcDot11TpFdbEntry OBJECT-TYPE
                SYNTAX  AwcDot11TpFdbEntry
                MAX-ACCESS  not-accessible
                STATUS  current
                DESCRIPTION
                        "Information about a specific MAC address
                        for which the bridge has some forwarding and/or
                        filtering information."
                INDEX   { awcDot11TpFdbAddress }
        ::= { awcDot11TpFdbTable 1 }

AwcDot11TpFdbEntry ::=
	SEQUENCE {
               awcDot11TpFdbAddress                MacAddress,
               awcDot11TpFdbAID                    Unsigned32,
               awcDot11TpFdbClientState            AwcDot11ClientState,
               awcDot11TpFdbTxShortRetries         Counter32,
               awcDot11TpFdbTxLongRetries          Counter32,
               awcDot11TpFdbLatestTxShortRetries   Counter32,
               awcDot11TpFdbLatestTxLongRetries    Counter32,
               awcDot11TpFdbRxWEPErrors            Counter32,
               awcDot11TpFdbLatestRxSignalStrength Unsigned32,
               awcDot11TpFdbLatestRxSignalQuality  Unsigned32,
               awcDot11TpFdbCapabilities           Unsigned32,
               awcDot11TpFdbListenInterval         Unsigned32,
               awcDot11TpFdbSupportedDataRates     OCTET STRING,
               awcDot11TpFdbPreferredTxRate        Unsigned32,
               awcDot11TpFdbCurrentBSS             MacAddress,
               awcDot11TpFdbSSID                   INTEGER,
               awcDot11TpFdbVlanId                 AwcVlanId
        }

awcDot11TpFdbAddress OBJECT-TYPE
                SYNTAX  MacAddress
                MAX-ACCESS  read-only
                STATUS  current
                DESCRIPTION
                        "A MAC address for which the bridge has
                        forwarding and/or filtering information."
        ::= { awcDot11TpFdbEntry 1 }

awcDot11TpFdbAID OBJECT-TYPE
        SYNTAX Unsigned32
        MAX-ACCESS read-only
        STATUS current
        DESCRIPTION
            "AID with which the Station is associated with this
             system, or 2008 if the
             Station is not currently known to be associated.  If the
             entry is multicast, awcDot11TpFdbAID is 0.  Note that
             the uplink from a Client or Repeater AP to its parent
             is always AID 1."
    ::= {  awcDot11TpFdbEntry 2 }

awcDot11TpFdbClientState OBJECT-TYPE
        SYNTAX AwcDot11ClientState
        MAX-ACCESS read-only
        STATUS current
        DESCRIPTION
            "802.11 Service State of the Station."
    ::= {  awcDot11TpFdbEntry 3 }

awcDot11TpFdbTxShortRetries OBJECT-TYPE
        SYNTAX Counter32
        MAX-ACCESS read-only
        STATUS current
        DESCRIPTION
            "The total number of 802.11 Short Retries incurred across
             all packet Transmission Attempts to this Station."
    ::= {  awcDot11TpFdbEntry 4 }

awcDot11TpFdbTxLongRetries OBJECT-TYPE
        SYNTAX Counter32
        MAX-ACCESS read-only
        STATUS current
        DESCRIPTION
            "The total number of 802.11 Long Retries incurred across
             all packet Transmission Attempts to this Station."
    ::= {  awcDot11TpFdbEntry 5 }

awcDot11TpFdbLatestTxShortRetries OBJECT-TYPE
        SYNTAX Counter32
        MAX-ACCESS read-only
        STATUS current
        DESCRIPTION
            "The number of 802.11 Short Retries incurred during the
             most recent packet Transmission Attempts to this Station."
    ::= {  awcDot11TpFdbEntry 6 }

awcDot11TpFdbLatestTxLongRetries OBJECT-TYPE
        SYNTAX Counter32
        MAX-ACCESS read-only
        STATUS current
        DESCRIPTION
            "The number of 802.11 Long Retries incurred during the
             most recent packet Transmission Attempts to this Station."
    ::= {  awcDot11TpFdbEntry 7 }

awcDot11TpFdbRxWEPErrors OBJECT-TYPE
        SYNTAX Counter32
        MAX-ACCESS read-only
        STATUS current
        DESCRIPTION
            "The total number of packets received from this Station
             which failed to be properly decrypted via the WEP security
             mechanism."
    ::= {  awcDot11TpFdbEntry 8 }

awcDot11TpFdbLatestRxSignalStrength OBJECT-TYPE
        SYNTAX Unsigned32
        MAX-ACCESS read-only
        STATUS current
        DESCRIPTION
            "A device-dependent measure of the signal strength of the
             most recently received packet from this Station.  Might be
             normalized or unnormalized."
    ::= {  awcDot11TpFdbEntry 9 }

awcDot11TpFdbLatestRxSignalQuality OBJECT-TYPE
        SYNTAX Unsigned32
        MAX-ACCESS read-only
        STATUS current
        DESCRIPTION
            "A device-dependent measure of the signal quality of the
             most recently received packet from this Station."
    ::= {  awcDot11TpFdbEntry 10 }

awcDot11TpFdbCapabilities OBJECT-TYPE
        SYNTAX Unsigned32
        MAX-ACCESS read-only
        STATUS current
        DESCRIPTION
            "The possible 802.11 capabilities of the Station's radio."
    ::= {  awcDot11TpFdbEntry 11 }

awcDot11TpFdbListenInterval OBJECT-TYPE
        SYNTAX Unsigned32
        MAX-ACCESS read-only
        STATUS current
        DESCRIPTION
            "The number of beacon intervals across which a the Station
             will sleep in power-save mode, or 1 if the
             Station will never be in power-save mode."
    ::= {  awcDot11TpFdbEntry 12 }

awcDot11TpFdbSupportedDataRates OBJECT-TYPE
        SYNTAX OCTET STRING (SIZE(1..126))
        MAX-ACCESS read-only
        STATUS current
        DESCRIPTION
                "This attribute shall specify the set of data rates
                 at which the station may transmit data.  Each octet
                 contains a value representing a rate.  Each rate
                 shall be within the range from 2 to 255, the lower
                 seven bits 0..6 of which corresponding to data rates
                 in increments of 500 kb/s from 1 Mb/s to 63.5 Mb/s,
                 and shall be supported (as indicated in the supported
                 rates table) for receiving data. This value is
                 reported in transmitted Beacon, Probe Request, Probe
                 Response, Association Request, Association Response,
                 Reassociation Request, and Reassociation Response
                 frames, and is used to determine whether a BSS
                 with which the station desires to synchronize is
                 suitable.  If set, Bit 7 of the rate specification
                 indicates that rate is a member of the Basic Rate Set
                 of the access point."
        ::= { awcDot11TpFdbEntry 13 }

awcDot11TpFdbPreferredTxRate OBJECT-TYPE
        SYNTAX Unsigned32
        MAX-ACCESS read-only
        STATUS current
        DESCRIPTION
                 "The transmission rate at which a packet should
                  currently be transmitted from an AP to this Station.
                  This rate does not carry information about whether or
                  not the rate is in the Basic Rate Set (i.e. bit 0x80
                  is never set)."
    ::= {  awcDot11TpFdbEntry 14 }

awcDot11TpFdbCurrentBSS OBJECT-TYPE
        SYNTAX MacAddress
        MAX-ACCESS read-only
        STATUS current
        DESCRIPTION
                 "BSS to which the station is currently Associated, or
                  00:00:00:00:00:00 if the station's current AP is
                  unknown."
    ::= {  awcDot11TpFdbEntry 15 }

awcDot11TpFdbSSID OBJECT-TYPE
        SYNTAX INTEGER (-1..2007)
        MAX-ACCESS read-only
        STATUS current
        DESCRIPTION
                 "If the Station is Associated to this AP, the SSID via
                  which the Station Associated.  If 0, the Station
                  Associated via dot11DesiredSSID.  If greater than 0,
                  the Station Associated through the auxiliary SSID with
                  awcDot11AuxSSIDIndex equal to awcDot11TpFdbSSID.
                  If -1, the Station is not currently Associated to
                  this AP."
    ::= {  awcDot11TpFdbEntry 16 }

awcDot11TpFdbVlanId OBJECT-TYPE
        SYNTAX AwcVlanId
        MAX-ACCESS read-only
        STATUS current
        DESCRIPTION
                 "Numeric ID of the VLAN over which the Station is
                  communicating.  If 0, the Station is not known to be
                  communicating over any specific VLAN."
    ::= {  awcDot11TpFdbEntry 17 }


awcDot1dTpPortTable OBJECT-TYPE
        SYNTAX  SEQUENCE OF AwcDot1dTpPortEntry
        MAX-ACCESS  not-accessible
        STATUS  current
        DESCRIPTION
              "A table that contains information about every
              port that is associated with this transparent
              bridge.  This table contains information about
              host and protocol filtering for the port.
              Each entry represents a transparent bridge port
              on the device.
              Entries in this table cannot be created or
              deleted by the network management system.
              All entries are created or deleted by the
              agent."
    ::= { awcForwardTbl 6 }

awcDot1dTpPortEntry OBJECT-TYPE
        SYNTAX  AwcDot1dTpPortEntry
        MAX-ACCESS  not-accessible
        STATUS  current
        DESCRIPTION
              "A list of filtering information for each port of a
              transparent bridge.  This information includes
              packet forwarding permission for unicast and
              non-unicast frames and filters ID used for
              the filtering."
        INDEX   { dot1dTpPort }
    ::= { awcDot1dTpPortTable 1 }

AwcDot1dTpPortEntry ::=
      SEQUENCE {
               awcDot1dTpPortDefaultUcastAllowedToGoTo    OCTET STRING,
               awcDot1dTpPortDefaultNUcastAllowedToGoTo   OCTET STRING,
               awcDot1dTpPortMaxNUcastPerSecond           Unsigned32,
               awcDot1dTpPortDefaultInEthertypeFilterId   Unsigned32,
               awcDot1dTpPortDefaultOutEthertypeFilterId  Unsigned32,
               awcDot1dTpPortDefaultInIpProtoFilterId     Unsigned32,
               awcDot1dTpPortDefaultOutIpProtoFilterId    Unsigned32,
               awcDot1dTpPortDefaultInIpPortFilterId      Unsigned32,
               awcDot1dTpPortDefaultOutIpPortFilterId     Unsigned32
               }

awcDot1dTpPortDefaultUcastAllowedToGoTo OBJECT-TYPE
      SYNTAX  OCTET STRING
      MAX-ACCESS  read-write
      STATUS  current
      DESCRIPTION
              "The set of ports to which frames received from a
              specific port and destined for a unicast MAC address
              which is not already listed in dot1dStaticTable are
              allowed to be forwarded.  Each octet
              within the value of this object specifies a set of
              eight ports, with the first octet specifying ports
              1 through 8, the second octet specifying ports 9
              through 16, etc.  Within each octet, the most
              significant bit represents the lowest numbered
              port, and the least significant bit represents the
              highest numbered port.  Thus, each port of the
              bridge is represented by a single bit within the
              value of this object.  If that bit has a value of
              '1' then that port is included in the set of
              ports; the port is not included if its bit has a
              value of '0'.  (Note that the setting of the bit
              corresponding to the port from which a frame is
              received is irrelevant.)  The default value of
              this object is a string of ones of appropriate
              length."
        ::= { awcDot1dTpPortEntry 1 }

awcDot1dTpPortDefaultNUcastAllowedToGoTo OBJECT-TYPE
      SYNTAX  OCTET STRING
      MAX-ACCESS  read-write
      STATUS  current
      DESCRIPTION
              "The set of ports to which frames received from a
              specific port and destined for a multicast MAC address
              which is not already listed in dot1dStaticTable are
              allowed to be forwarded.  Each octet
              within the value of this object specifies a set of
              eight ports, with the first octet specifying ports
              1 through 8, the second octet specifying ports 9
              through 16, etc.  Within each octet, the most
              significant bit represents the lowest numbered
              port, and the least significant bit represents the
              highest numbered port.  Thus, each port of the
              bridge is represented by a single bit within the
              value of this object.  If that bit has a value of
              '1' then that port is included in the set of
              ports; the port is not included if its bit has a
              value of '0'.  (Note that the setting of the bit
              corresponding to the port from which a frame is
              received is irrelevant.)  The default value of
              this object is a string of ones of appropriate
              length."
        ::= { awcDot1dTpPortEntry 2 }

awcDot1dTpPortMaxNUcastPerSecond OBJECT-TYPE
                SYNTAX Unsigned32
                MAX-ACCESS read-write
                STATUS current
                DESCRIPTION
                        "The maximum number of multicast packets
                         allowed to be forwarded over the port each
                         second.  If 0, the number of multicasts
                         is unlimited."
                DEFVAL { 0 }
        ::= { awcDot1dTpPortEntry 3 }

awcDot1dTpPortDefaultInEthertypeFilterId OBJECT-TYPE
                SYNTAX Unsigned32
                MAX-ACCESS read-write
                STATUS current
                DESCRIPTION
                        "awcPfEtSetId of the Ethertype Filter Set to
                         apply to packets received over this port.
                         If 0, no filters are applied."
                DEFVAL { 0 }
        ::= { awcDot1dTpPortEntry 4 }

awcDot1dTpPortDefaultOutEthertypeFilterId OBJECT-TYPE
                SYNTAX Unsigned32
                MAX-ACCESS read-write
                STATUS current
                DESCRIPTION
                        "awcPfEtSetId of the Ethertype Filter Set to
                         apply to packets transmitted over this port.
                         If 0, no filters are applied."
                DEFVAL { 0 }
        ::= { awcDot1dTpPortEntry 5 }

awcDot1dTpPortDefaultInIpProtoFilterId OBJECT-TYPE
                SYNTAX Unsigned32
                MAX-ACCESS read-write
                STATUS current
                DESCRIPTION
                        "awcPfIppSetId of the IP Protocol Filter Set to
                         apply to packets received over this port.
                         If 0, no filters are applied."
                DEFVAL { 0 }
        ::= { awcDot1dTpPortEntry 6 }

awcDot1dTpPortDefaultOutIpProtoFilterId OBJECT-TYPE
                SYNTAX Unsigned32
                MAX-ACCESS read-write
                STATUS current
                DESCRIPTION
                        "awcPfIppSetId of the IP Protocol Filter Set to
                         apply to packets transmitted over this port.
                         If 0, no filters are applied."
                DEFVAL { 0 }
        ::= { awcDot1dTpPortEntry 7 }

awcDot1dTpPortDefaultInIpPortFilterId OBJECT-TYPE
                SYNTAX Unsigned32
                MAX-ACCESS read-write
                STATUS current
                DESCRIPTION
                        "awcPfIptSetId of the IP Port Filter Set to
                         apply to packets received over this port.
                         If 0, no filters are applied."
                DEFVAL { 0 }
        ::= { awcDot1dTpPortEntry 8 }

awcDot1dTpPortDefaultOutIpPortFilterId OBJECT-TYPE
                SYNTAX Unsigned32
                MAX-ACCESS read-write
                STATUS current
                DESCRIPTION
                        "awcPfIptSetId of the IP Port Filter Set to
                         apply to packets transmitted over this port.
                         If 0, no filters are applied."
                DEFVAL { 0 }
        ::= { awcDot1dTpPortEntry 9 }


awcTpFdbAlertTable OBJECT-TYPE
                SYNTAX  SEQUENCE OF AwcTpFdbAlertEntry
                MAX-ACCESS  not-accessible
                STATUS  current
                DESCRIPTION
                        "A table that contains information about
                        entries for which the bridge has forwarding
                        and/or filtering information.  This table
                        maintains only packet-trace alert statistics.
                        Each entry is indexed by a MAC address
                        in the packet forwarding.
                        Entries in this table cannot be created or
                        deleted by the network management system.
                        All entries are created or deleted by the
                        agent."
        ::= { awcForwardTbl 7 }

awcTpFdbAlertEntry OBJECT-TYPE
                SYNTAX  AwcTpFdbAlertEntry
                MAX-ACCESS  not-accessible
                STATUS  current
                DESCRIPTION
                        "Information about a specific MAC address
                        for which the bridge has some forwarding and/or
                        filtering information."
                INDEX   { awcTpFdbAlertAddress }
        ::= { awcTpFdbAlertTable 1 }

AwcTpFdbAlertEntry ::=
	SEQUENCE {
               awcTpFdbAlertAddress                     MacAddress,
               awcTpFdbFromAlertSrcPktsImmed            Counter32,
               awcTpFdbFromAlertSrcOctetsImmed          Counter32,
               awcTpFdbToAlertDestPktsImmed             Counter32,
               awcTpFdbToAlertDestOctetsImmed           Counter32,
               awcTpFdbAlertSentAlertTypePktsImmed      Counter32,
               awcTpFdbAlertSentAlertTypeOctetsImmed    Counter32,
               awcTpFdbAlertRcvdAlertTypePktsImmed      Counter32,
               awcTpFdbAlertRcvdAlertTypeOctetsImmed    Counter32
        }

awcTpFdbAlertAddress OBJECT-TYPE
                SYNTAX  MacAddress
                MAX-ACCESS  read-only
                STATUS  current
                DESCRIPTION
                        "A MAC address for which the bridge has
                        forwarding and/or filtering information."
        ::= { awcTpFdbAlertEntry 1 }

awcTpFdbFromAlertSrcPktsImmed OBJECT-TYPE
        SYNTAX Counter32
        MAX-ACCESS read-only
        STATUS current
        DESCRIPTION
            "The total number of packets directed to this entry,
             over any interface, from a source host
             designated Alert From in the forwarding table."
    ::= {  awcTpFdbAlertEntry 2 }

awcTpFdbFromAlertSrcOctetsImmed OBJECT-TYPE
        SYNTAX Counter32
        MAX-ACCESS read-only
        STATUS current
        DESCRIPTION
            "The total number of octets directed to this entry,
             over any interface, from a source host
             designated Alert From in the forwarding table."
    ::= {  awcTpFdbAlertEntry 3 }

awcTpFdbToAlertDestPktsImmed OBJECT-TYPE
        SYNTAX Counter32
        MAX-ACCESS read-only
        STATUS current
        DESCRIPTION
            "The total number of packets sent by this entry,
             over any interface, to a destination MAC address
             designated Alert To in the forwarding table."
    ::= {  awcTpFdbAlertEntry 4 }

awcTpFdbToAlertDestOctetsImmed OBJECT-TYPE
        SYNTAX Counter32
        MAX-ACCESS read-only
        STATUS current
        DESCRIPTION
            "The total number of packets sent by this entry,
             over any interface, to a destination MAC address
             designated Alert To in the forwarding table."
    ::= {  awcTpFdbAlertEntry 5 }

awcTpFdbAlertSentAlertTypePktsImmed OBJECT-TYPE
        SYNTAX Counter32
        MAX-ACCESS read-only
        STATUS current
        DESCRIPTION
            "The total number of packets sent by this entry,
             over any interface, with a packet type
             designated Alert in an applicable protocol filter."
    ::= {  awcTpFdbAlertEntry 6 }

awcTpFdbAlertSentAlertTypeOctetsImmed OBJECT-TYPE
        SYNTAX Counter32
        MAX-ACCESS read-only
        STATUS current
        DESCRIPTION
            "The total number of octets sent by this entry,
             over any interface, with a packet type
             designated Alert in an applicable protocol filter."
    ::= {  awcTpFdbAlertEntry 7 }

awcTpFdbAlertRcvdAlertTypePktsImmed OBJECT-TYPE
        SYNTAX Counter32
        MAX-ACCESS read-only
        STATUS current
        DESCRIPTION
            "The total number of packets directed to this entry,
             over any interface, with a packet type
             designated Alert in an applicable protocol filter."
    ::= {  awcTpFdbAlertEntry 8 }

awcTpFdbAlertRcvdAlertTypeOctetsImmed OBJECT-TYPE
        SYNTAX Counter32
        MAX-ACCESS read-only
        STATUS current
        DESCRIPTION
            "The total number of octets directed to this entry,
             over any interface, with a packet type
             designated Alert in an applicable protocol filter."
    ::= {  awcTpFdbAlertEntry 9 }


-- ********************************************************************
-- *    End of awcForwardTbl parameters
-- ********************************************************************

-- ********************************************************************
-- *  awcEventLog parameters
-- ********************************************************************

AwcEventSeverity ::= TEXTUAL-CONVENTION
  STATUS       current
  DESCRIPTION
          "Severity of an event handled within the system."
  SYNTAX       INTEGER { systemFatal(2),
                         protocolFatal(3),
                         portFatal(4),
                         systemAlert(5),
                         protocolAlert(6),
                         portAlert(7),
                         externalAlert(8),
                         systemWarning(9),
                         protocolWarning(10),
                         portWarning(11),
                         externalWarning(12),
                         systemInfo(13),
                         protocolInfo(14),
                         portInfo(15),
                         externalInfo(16)
               }



awcEventOffsetGMT OBJECT-TYPE
                SYNTAX Integer32 (-720..720)
                UNITS "minutes"
                MAX-ACCESS read-write
                STATUS current
                DESCRIPTION
                        "The current offset from GMT in minutes."
                DEFVAL { -300 }
        ::= {  awcEventLog 1 }

awcEventUseDaylightSavingsTime OBJECT-TYPE
                SYNTAX TruthValue
                MAX-ACCESS read-write
                STATUS current
                DESCRIPTION
                        "If true, daylight savings time is used."
                DEFVAL { true }
        ::= {  awcEventLog 2 }

awcEventTimestampGMT OBJECT-TYPE
                SYNTAX Integer32
                UNITS "seconds"
                MAX-ACCESS read-write
                STATUS current
                DESCRIPTION
                        "GMT Time, in seconds since January 1, 1970,
                         when the system wall-clock time was last set."
                DEFVAL { 0 }
        ::= {  awcEventLog 3 }

awcEventUptimeModifiedGMT OBJECT-TYPE
                SYNTAX Integer32
                UNITS "seconds"
                MAX-ACCESS read-only
                STATUS current
                DESCRIPTION
                        "System uptime, in seconds, when the system
                         wall-clock time was last set."
        ::= {  awcEventLog 4 }

awcEventDisplayWallClockTime OBJECT-TYPE
                SYNTAX TruthValue
                MAX-ACCESS read-write
                STATUS current
                DESCRIPTION
                        "If true, time display on the system's web
                         pages and console is in wall-clock time.
                         If false, time display is in system uptime."
                DEFVAL { true }
        ::= {  awcEventLog 5 }

awcEventDisplayUptimeAscending OBJECT-TYPE
                SYNTAX TruthValue
                MAX-ACCESS read-write
                STATUS current
                DESCRIPTION
                        "If true, time display in system uptime is
                         measured from the time the system boots,
                         forward.  If false, time display in
                         measured from the current time backwards."
                DEFVAL { true }
        ::= {  awcEventLog 6 }

awcEventDetailDefault OBJECT-TYPE
                SYNTAX Integer32
                MAX-ACCESS read-write
                STATUS current
                DESCRIPTION
                        "Detail level at which, by default, events
                         are displayed.  General detail level
                         classifications are:
                             8 - no display at all
                            16 - sparse detail
                            24 - normal detail
                            32 - verbose detail
                            40 - exhaustive detail
                        "
                DEFVAL { 24 }
        ::= {  awcEventLog 7 }

awcEventSeverityDispConsole OBJECT-TYPE
                SYNTAX AwcEventSeverity
                MAX-ACCESS read-write
                STATUS current
                DESCRIPTION
                        "If an event has a severity level greater than
                         or equal to awcEventSeverityDispConsole, it
                         is displayed on the console shortly after it
                         occurs."
                DEFVAL { externalInfo }
        ::= {  awcEventLog 8 }

awcEventSeverityDispHtmlGUI OBJECT-TYPE
                SYNTAX AwcEventSeverity
                MAX-ACCESS read-write
                STATUS current
                DESCRIPTION
                        "If an event has a severity level greater than
                         or equal to awcEventSeverityDispHtmlGUI, it
                         is displayed on the the Event Log GUI web
                         pages."
                DEFVAL { externalInfo }
        ::= {  awcEventLog 9 }

awcEventSeverityDispHtmlConsole OBJECT-TYPE
                SYNTAX AwcEventSeverity
                MAX-ACCESS read-write
                STATUS current
                DESCRIPTION
                        "If an event has a severity level greater than
                         or equal to awcEventSeverityDispHtmlConsole,
                         it is displayed on the the Event Log console
                         browser pages."
                DEFVAL { externalInfo }
        ::= {  awcEventLog 10 }

awcEventAlertSNMP OBJECT-TYPE
                SYNTAX TruthValue
                MAX-ACCESS read-write
                STATUS current
                DESCRIPTION
                        "If true, events of a severity with Disposition
                         set to notify will generate an SNMP trap."
                DEFVAL { true }
        ::= {  awcEventLog 11 }

awcEventAlertSyslog OBJECT-TYPE
                SYNTAX TruthValue
                MAX-ACCESS read-write
                STATUS current
                DESCRIPTION
                        "If true, events of a severity with Disposition
                         set to notify will generate a sysLog message."
                DEFVAL { true }
        ::= {  awcEventLog 12 }

awcEventStatistics OBJECT IDENTIFIER ::=       {awcEventLog 14}

awcEventCntSeverityNULL OBJECT-TYPE
                SYNTAX Counter32
                MAX-ACCESS read-only
                STATUS current
                DESCRIPTION
                        "NULL message counter."
        ::= {  awcEventStatistics 1 }

awcEventCntSeveritySilent OBJECT-TYPE
                SYNTAX Counter32
                MAX-ACCESS read-only
                STATUS current
                DESCRIPTION
                        "Silent message counter."
        ::= {  awcEventStatistics 2 }

awcEventCntSeveritySystemFatal OBJECT-TYPE
                SYNTAX Counter32
                MAX-ACCESS read-only
                STATUS current
                DESCRIPTION
                        "Fatal system message counter."
        ::= {  awcEventStatistics 3 }

awcEventCntSeverityProtocolFatal OBJECT-TYPE
                SYNTAX Counter32
                MAX-ACCESS read-only
                STATUS current
                DESCRIPTION
                        "Fatal Protocol message counter."
        ::= {  awcEventStatistics 4 }

awcEventCntSeverityPortFatal OBJECT-TYPE
                SYNTAX Counter32
                MAX-ACCESS read-only
                STATUS current
                DESCRIPTION
                        "Fatal Port message counter."
        ::= {  awcEventStatistics 5 }

awcEventCntSeveritySystemAlert OBJECT-TYPE
                SYNTAX Counter32
                MAX-ACCESS read-only
                STATUS current
                DESCRIPTION
                        "System Alert message counter."
        ::= {  awcEventStatistics 6 }

awcEventCntSeverityProtocolAlert OBJECT-TYPE
                SYNTAX Counter32
                MAX-ACCESS read-only
                STATUS current
                DESCRIPTION
                        "Protocol Alert message counter."
        ::= {  awcEventStatistics 7 }

awcEventCntSeverityPortAlert OBJECT-TYPE
                SYNTAX Counter32
                MAX-ACCESS read-only
                STATUS current
                DESCRIPTION
                        "Port Alert message counter."
        ::= {  awcEventStatistics 8 }

awcEventCntSeverityExternalAlert OBJECT-TYPE
                SYNTAX Counter32
                MAX-ACCESS read-only
                STATUS current
                DESCRIPTION
                        "External Alert message counter."
        ::= {  awcEventStatistics 9 }

awcEventCntSeveritySystemWarning OBJECT-TYPE
                SYNTAX Counter32
                MAX-ACCESS read-only
                STATUS current
                DESCRIPTION
                        "System Warning message counter."
        ::= {  awcEventStatistics 10 }

awcEventCntSeverityProtocolWarning OBJECT-TYPE
                SYNTAX Counter32
                MAX-ACCESS read-only
                STATUS current
                DESCRIPTION
                        "Protocol Warning message counter."
        ::= {  awcEventStatistics 11 }

awcEventCntSeverityPortWarning OBJECT-TYPE
                SYNTAX Counter32
                MAX-ACCESS read-only
                STATUS current
                DESCRIPTION
                        "Port Warning message counter."
        ::= {  awcEventStatistics 12 }

awcEventCntSeverityExternalWarning OBJECT-TYPE
                SYNTAX Counter32
                MAX-ACCESS read-only
                STATUS current
                DESCRIPTION
                        "External Warning message counter."
        ::= {  awcEventStatistics 13 }

awcEventCntSeveritySystemInfo OBJECT-TYPE
                SYNTAX Counter32
                MAX-ACCESS read-only
                STATUS current
                DESCRIPTION
                        "System Info message counter."
        ::= {  awcEventStatistics 14 }

awcEventCntSeverityProtocolInfo OBJECT-TYPE
                SYNTAX Counter32
                MAX-ACCESS read-only
                STATUS current
                DESCRIPTION
                        "Protocol Info message counter."
        ::= {  awcEventStatistics 15 }

awcEventCntSeverityPortInfo OBJECT-TYPE
                SYNTAX Counter32
                MAX-ACCESS read-only
                STATUS current
                DESCRIPTION
                        "Port Info message counter."
        ::= {  awcEventStatistics 16 }

awcEventCntSeverityExternalInfo OBJECT-TYPE
                SYNTAX Counter32
                MAX-ACCESS read-only
                STATUS current
                DESCRIPTION
                        "External Info message counter."
        ::= {  awcEventStatistics 17 }


awcEventDisposition OBJECT IDENTIFIER ::=       {awcEventLog 15}

awcEventDispSeverityNULL OBJECT-TYPE
                SYNTAX AwcEventDisposition
                MAX-ACCESS read-write
                STATUS current
                DESCRIPTION
                        "NULL message disposition."
        ::= {  awcEventDisposition 1 }

awcEventDispSeveritySilent OBJECT-TYPE
                SYNTAX AwcEventDisposition
                MAX-ACCESS read-write
                STATUS current
                DESCRIPTION
                        "Silent message disposition."
        ::= {  awcEventDisposition 2 }

awcEventDispSeveritySystemFatal OBJECT-TYPE
                SYNTAX AwcEventDisposition
                MAX-ACCESS read-write
                STATUS current
                DESCRIPTION
                        "Fatal system message disposition."
        ::= {  awcEventDisposition 3 }

awcEventDispSeverityProtocolFatal OBJECT-TYPE
                SYNTAX AwcEventDisposition
                MAX-ACCESS read-write
                STATUS current
                DESCRIPTION
                        "Fatal Protocol message disposition."
        ::= {  awcEventDisposition 4 }

awcEventDispSeverityPortFatal OBJECT-TYPE
                SYNTAX AwcEventDisposition
                MAX-ACCESS read-write
                STATUS current
                DESCRIPTION
                        "Fatal Port message disposition."
        ::= {  awcEventDisposition 5 }

awcEventDispSeveritySystemAlert OBJECT-TYPE
                SYNTAX AwcEventDisposition
                MAX-ACCESS read-write
                STATUS current
                DESCRIPTION
                        "System Alert message disposition."
        ::= {  awcEventDisposition 6 }

awcEventDispSeverityProtocolAlert OBJECT-TYPE
                SYNTAX AwcEventDisposition
                MAX-ACCESS read-write
                STATUS current
                DESCRIPTION
                        "Protocol Alert message disposition."
        ::= {  awcEventDisposition 7 }

awcEventDispSeverityPortAlert OBJECT-TYPE
                SYNTAX AwcEventDisposition
                MAX-ACCESS read-write
                STATUS current
                DESCRIPTION
                        "Port Alert message disposition."
        ::= {  awcEventDisposition 8 }

awcEventDispSeverityExternalAlert OBJECT-TYPE
                SYNTAX AwcEventDisposition
                MAX-ACCESS read-write
                STATUS current
                DESCRIPTION
                        "External Alert message disposition."
        ::= {  awcEventDisposition 9 }

awcEventDispSeveritySystemWarning OBJECT-TYPE
                SYNTAX AwcEventDisposition
                MAX-ACCESS read-write
                STATUS current
                DESCRIPTION
                        "System Warning message disposition."
        ::= {  awcEventDisposition 10 }

awcEventDispSeverityProtocolWarning OBJECT-TYPE
                SYNTAX AwcEventDisposition
                MAX-ACCESS read-write
                STATUS current
                DESCRIPTION
                        "Protocol Warning message disposition."
        ::= {  awcEventDisposition 11 }

awcEventDispSeverityPortWarning OBJECT-TYPE
                SYNTAX AwcEventDisposition
                MAX-ACCESS read-write
                STATUS current
                DESCRIPTION
                        "Port Warning message disposition."
        ::= {  awcEventDisposition 12 }

awcEventDispSeverityExternalWarning OBJECT-TYPE
                SYNTAX AwcEventDisposition
                MAX-ACCESS read-write
                STATUS current
                DESCRIPTION
                        "External Warning message disposition."
        ::= {  awcEventDisposition 13 }

awcEventDispSeveritySystemInfo OBJECT-TYPE
                SYNTAX AwcEventDisposition
                MAX-ACCESS read-write
                STATUS current
                DESCRIPTION
                        "System Info message disposition."
        ::= {  awcEventDisposition 14 }

awcEventDispSeverityProtocolInfo OBJECT-TYPE
                SYNTAX AwcEventDisposition
                MAX-ACCESS read-write
                STATUS current
                DESCRIPTION
                        "Protocol Info message disposition."
        ::= {  awcEventDisposition 15 }

awcEventDispSeverityPortInfo OBJECT-TYPE
                SYNTAX AwcEventDisposition
                MAX-ACCESS read-write
                STATUS current
                DESCRIPTION
                        "Port Info message disposition."
        ::= {  awcEventDisposition 16 }

awcEventDispSeverityExternalInfo OBJECT-TYPE
                SYNTAX AwcEventDisposition
                MAX-ACCESS read-write
                STATUS current
                DESCRIPTION
                        "External Info message disposition."
        ::= {  awcEventDisposition 17 }

awcEventSyslogAddr OBJECT-TYPE
                SYNTAX DisplayString (SIZE(0..128))
                MAX-ACCESS read-write
                STATUS current
                DESCRIPTION
                        "The destination of a sysLog message.
                         This address must be numeric or DNS
                         resolvable.  Max. string length is
                         128 octets."
                DEFVAL { "" }
        ::= {  awcEventLog 16 }

awcEventSyslogFacility OBJECT-TYPE
               	SYNTAX INTEGER (0..8191)
                MAX-ACCESS read-write
                STATUS current
                DESCRIPTION
                        "The facility number encoded within a sysLog
                         message."
                DEFVAL { 16 }
        ::= {  awcEventLog 17 }

awcEventTraceStationSeverity OBJECT-TYPE
        SYNTAX AwcEventSeverity
        MAX-ACCESS read-write
        STATUS current
        DESCRIPTION
                "Severity at which all Detailed Packet Trace events
                 shall be handled."
        DEFVAL { externalInfo }
    ::= { awcEventLog 20 }

awcEventTraceLogSize OBJECT-TYPE
        SYNTAX Unsigned32 (0..8388608)
        MAX-ACCESS read-write
        STATUS current
        DESCRIPTION
                "Size in octets of the system Detailed Event Trace
                 Buffer.  Note that this buffer is statically
                 allocated at system initialization time.  Changing
                 the size of the buffer requires a system reboot."
        DEFVAL { 0 }
    ::= { awcEventLog 21 }

awcEventTracePacketLen OBJECT-TYPE
        SYNTAX Unsigned32 (0..2312)
        MAX-ACCESS read-write
        STATUS current
        DESCRIPTION
                "Maximum size in octets of each Packet Trace Event
                 recorded in the Detailed Event Trace Buffer."
        DEFVAL { 0 }
    ::= { awcEventLog 22 }

awcEventTable OBJECT-TYPE
            SYNTAX SEQUENCE OF AwcEventEntry
            MAX-ACCESS not-accessible
            STATUS current
            DESCRIPTION
                    "SNMP access to Event Log table."
        ::= { awcEventLog 23 }

awcEventEntry OBJECT-TYPE
            SYNTAX AwcEventEntry
            MAX-ACCESS not-accessible
            STATUS current
            DESCRIPTION
                    "An entry in awcEventTable."
            INDEX { awcEventID }
        ::= { awcEventTable 1 }

AwcEventEntry ::=
        SEQUENCE {
            awcEventID                      Unsigned32,
            awcEventTime                    DisplayString,
            awcEventSeverity                AwcEventSeverity,
            awcEventDescription             DisplayString,
            awcEventType                    DisplayString }

awcEventID OBJECT-TYPE
        SYNTAX Unsigned32
        MAX-ACCESS read-only
        STATUS current
        DESCRIPTION
                "System-unique identifier of the event."
    ::= { awcEventEntry 1 }

awcEventTime OBJECT-TYPE
        SYNTAX DisplayString
        MAX-ACCESS read-only
        STATUS current
        DESCRIPTION
                "System time at which the event occurred."
    ::= { awcEventEntry 2 }

awcEventSeverity OBJECT-TYPE
        SYNTAX AwcEventSeverity
        MAX-ACCESS read-only
        STATUS current
        DESCRIPTION
                "Severity of the event."
    ::= { awcEventEntry 3 }

awcEventDescription OBJECT-TYPE
        SYNTAX DisplayString
        MAX-ACCESS read-only
        STATUS current
        DESCRIPTION
                "Detailed description of the event."
    ::= { awcEventEntry 4 }

awcEventType OBJECT-TYPE
        SYNTAX DisplayString
        MAX-ACCESS read-only
        STATUS current
        DESCRIPTION
                "Specific type of the event.  The type is unique for
                 each test condition which can result in event
                 generation."
    ::= { awcEventEntry 5 }


awcEventUseCiscoFormat OBJECT-TYPE
        SYNTAX TruthValue
        MAX-ACCESS read-write
        STATUS current
        DESCRIPTION
                "If true, the system will generate
                syslog messages using Cisco standard EMBLEM-
                compliant format. If false, syslog will use
                legacy Aironet format."
        DEFVAL { false }
	::= {  awcEventLog 25 }


awcDot11AuthenticateFailDisposition  OBJECT-TYPE
        SYNTAX AwcDot11EventDisposition
        MAX-ACCESS read-write
        STATUS current
        DESCRIPTION
                "Specifies how standard IEEE trap dot11AuthenticateFail
                 is handled on the system."
        DEFVAL { eventLogAndIeeeTrap}
    ::= { awcEventLog 26 }


awcDot11DeauthenticateDisposition  OBJECT-TYPE
        SYNTAX AwcDot11EventDisposition
        MAX-ACCESS read-write
        STATUS current
        DESCRIPTION
                "Specifies how standard IEEE 802.11 trap dot11Deauthenticate
                 is handled on the system."
        DEFVAL { eventLogAndIeeeTrap}
    ::= { awcEventLog 27 }


awcDot11DisassociateDisposition  OBJECT-TYPE
        SYNTAX AwcDot11EventDisposition
        MAX-ACCESS read-write
        STATUS current
        DESCRIPTION
                "Specifies how standard IEEE 802.11 trap dot11Disassociate
                 is handled on the system."
        DEFVAL { eventLogAndIeeeTrap}
    ::= { awcEventLog 28 }


-- ********************************************************************
-- *  awcEtherMIB parameters
-- ********************************************************************
awcEtherIfSpeedSelect OBJECT-TYPE
                SYNTAX INTEGER { tenBaseT(3),
                                 oneHundredBaseT(5),
                                 tenBaseTfull(6),
                                 oneHundredBaseTfull(7),
                                 autoDetect(8) }
                MAX-ACCESS read-write
                STATUS current
                DESCRIPTION
                        "Requested Ethernet interface speed and
                         duplex."
                DEFVAL { autoDetect }
        ::= {  awcEtherMIB 1 }

awcEtherDuplex OBJECT-TYPE
                SYNTAX INTEGER { half(1), full(2) }
                MAX-ACCESS read-only
                STATUS current
                DESCRIPTION
                        "Actual Ethernet interface duplex, after any
                         line negotiation has taken place."
        ::= {  awcEtherMIB 5 }

awcEtherCamSize OBJECT-TYPE
        SYNTAX Unsigned32
        MAX-ACCESS read-only
        STATUS current
        DESCRIPTION
                "Number of entries in the hardware Content Addressible
                 Memory MAC address filter available to the Ethernet
                 controller."
        ::= {  awcEtherMIB 7 }

awcEtherEnableSwCam OBJECT-TYPE
        SYNTAX TruthValue
        MAX-ACCESS read-write
        STATUS current
        DESCRIPTION
                "If true, the Ethernet driver makes use of a Software
                 Content Addressible Memory when making packet-forwarding
                 decisions.  When true, forwarding decisions are much
                 faster, but network statistics collection is much
                 coarser.  If false, all packet-forwarding decisions are
                 made by the higher-level packet-bridging logic."
        DEFVAL { false }
        ::= {  awcEtherMIB 8 }

awcEtherForcePortUnblock OBJECT-TYPE
        SYNTAX TruthValue
        MAX-ACCESS read-write
        STATUS current
        DESCRIPTION
                "If true, the Ethernet port has dot1dStpPortState forced
                 to forwarding even when the Spanning Tree Protocol is
                 not enabled.  This provides rapid port re-establishment
                 at the potential cost of not detecting network topology
                 loops involving the Ethernet and other network interfaces
                 such as the radio.  If false, the Ethernet port is blocked
                 whenever there exists the potential for a network topology
                 loop and the Spanning Tree Protocol is not enabled to guard
                 against such loops."
        DEFVAL { false }
        ::= {  awcEtherMIB 9 }

awcEtherLostEthernetSeconds OBJECT-TYPE
        SYNTAX INTEGER (1..10000)
        MAX-ACCESS read-write
        STATUS current
        DESCRIPTION
                "Number of seconds the system must detect loss of backbone
                 connectivity (i.e. loss of Ethernet link and no active
                 trunks available on any of the radios) before taking the
                 action specified by awcEtherLostEthernetAction."
	DEFVAL { 2 }
        ::= {  awcEtherMIB 10 }

awcEtherLostEthernetAction OBJECT-TYPE
        SYNTAX INTEGER { noAction(1), switchRepeater(2), radioOff(3),
                         restrictSSID(4) }
        MAX-ACCESS read-write
        STATUS current
        DESCRIPTION
                "Action taken by the system when a loss of backbone
                 connectivity condition occurs for a period of time
                 longer than awcEtherLostEthernetSeconds."
	DEFVAL { switchRepeater }
        ::= {  awcEtherMIB 11 }

awcEtherLostEthernetSSID OBJECT-TYPE
        SYNTAX Unsigned32
        MAX-ACCESS read-write
        STATUS current
        DESCRIPTION
                "The single SSID index required by the system if
                 awcEtherLostEthernetAction is restrictSSID and backbone
                 connectivity is lost for a period of time longer than
                 awcEtherLostEthernetSeconds.  If 0, only Association to
                 dot11DesiredSSID is allowed.  If non-0, only
                 Association to the auxiliary SSID with the corresponding
                 awcDot11AuxSSIDIndex is allowed."
	DEFVAL { 0 }
        ::= {  awcEtherMIB 12 }


-- ********************************************************************
-- *  awcPolicyGroups parameters
-- ********************************************************************

awcPolGrpTable OBJECT-TYPE
            SYNTAX SEQUENCE OF AwcPolGrpEntry
            MAX-ACCESS not-accessible
            STATUS current
            DESCRIPTION
                    "Table of named groups of related protocol filters"
        ::= { awcPolicyGroups 1 }

awcPolGrpEntry OBJECT-TYPE
            SYNTAX AwcPolGrpEntry
            MAX-ACCESS not-accessible
            STATUS current
            DESCRIPTION
                    "An entry in awcPolGrpTable."
            INDEX {awcPolGrpId}
        ::= { awcPolGrpTable 1 }

AwcPolGrpEntry ::=
        SEQUENCE {
            awcPolGrpId                    Unsigned32,
            awcPolGrpName                  DisplayString,
            awcPolGrpStatus                RowStatus,
            awcPolGrpInEthertypeFilterId   Unsigned32,
            awcPolGrpOutEthertypeFilterId  Unsigned32,
            awcPolGrpInIpProtoFilterId     Unsigned32,
            awcPolGrpOutIpProtoFilterId    Unsigned32,
            awcPolGrpInIpPortFilterId      Unsigned32,
            awcPolGrpOutIpPortFilterId     Unsigned32
         }

awcPolGrpId OBJECT-TYPE
        SYNTAX Unsigned32 (1..1023)
        MAX-ACCESS not-accessible
        STATUS current
        DESCRIPTION
        "Numeric identifier of the Policy Group."
        ::= {  awcPolGrpEntry 1 }

awcPolGrpName OBJECT-TYPE
        SYNTAX DisplayString (SIZE(0..64))
        MAX-ACCESS read-create
        STATUS current
        DESCRIPTION
        "Descriptive name of the Policy Group.
         Max. string length is 64 octets."
        ::= {  awcPolGrpEntry 2 }

awcPolGrpStatus OBJECT-TYPE
        SYNTAX   RowStatus
        MAX-ACCESS  read-create
        STATUS  current
        DESCRIPTION
        "Row status of the entire Policy Group."
        ::= {  awcPolGrpEntry 3 }

awcPolGrpInEthertypeFilterId OBJECT-TYPE
        SYNTAX Unsigned32
        MAX-ACCESS read-create
        STATUS current
        DESCRIPTION
                "awcPfEtSetId of the Ethertype Filter Set to
                 apply to packets received subject to this policy.
                 If 0, no filters are applied."
        DEFVAL { 0 }
        ::= {  awcPolGrpEntry 4 }

awcPolGrpOutEthertypeFilterId OBJECT-TYPE
        SYNTAX Unsigned32
        MAX-ACCESS read-create
        STATUS current
        DESCRIPTION
                "awcPfEtSetId of the Ethertype Filter Set to
                 apply to packets transmitted subject to this policy.
                 If 0, no filters are applied."
        DEFVAL { 0 }
        ::= {  awcPolGrpEntry 5 }

awcPolGrpInIpProtoFilterId OBJECT-TYPE
        SYNTAX Unsigned32
        MAX-ACCESS read-create
        STATUS current
        DESCRIPTION
                "awcPfIppSetId of the IP Protocol Filter Set to
                 apply to packets received subject to this policy.
                 If 0, no filters are applied."
        DEFVAL { 0 }
        ::= {  awcPolGrpEntry 6 }

awcPolGrpOutIpProtoFilterId OBJECT-TYPE
        SYNTAX Unsigned32
        MAX-ACCESS read-create
        STATUS current
        DESCRIPTION
                "awcPfIppSetId of the IP Protocol Filter Set to
                 apply to packets transmitted subject to this policy.
                 If 0, no filters are applied."
        DEFVAL { 0 }
        ::= {  awcPolGrpEntry 7 }

awcPolGrpInIpPortFilterId OBJECT-TYPE
        SYNTAX Unsigned32
        MAX-ACCESS read-create
        STATUS current
        DESCRIPTION
                "awcPfIptSetId of the IP Port Filter Set to
                 apply to packets received subject to this policy.
                 If 0, no filters are applied."
        DEFVAL { 0 }
        ::= {  awcPolGrpEntry 8 }

awcPolGrpOutIpPortFilterId OBJECT-TYPE
        SYNTAX Unsigned32
        MAX-ACCESS read-create
        STATUS current
        DESCRIPTION
                "awcPfIptSetId of the IP Port Filter Set to
                 apply to packets transmitted subject to this policy.
                 If 0, no filters are applied."
        DEFVAL { 0 }
        ::= {  awcPolGrpEntry 9 }


-- ********************************************************************
-- *  awcDscpToCosMap parameters
-- ********************************************************************

awcDscpToCosMapEnable OBJECT-TYPE
		SYNTAX TruthValue
		MAX-ACCESS read-write
		STATUS current
		DESCRIPTION
		        "If true, IP packets which are not already
                 classified with a non-default Class of Service
                 (CoS) can be classified by reference to their
                 Differentiated Services Code-Point (DSCP) value.
                 If false, unclassified IP packets are not subject
                 to DSCP classification."
		DEFVAL { false }
        ::= { awcPolicyGroups 2 }

awcDscpToCosMapTable OBJECT-TYPE
         SYNTAX SEQUENCE OF AwcDscpToCosMapEntry
         MAX-ACCESS not-accessible
         STATUS current
         DESCRIPTION
             "This (conceptual) table to statically map
              Differentiated Services Code-Point (DSCP)
             values to  corresponding Class of Service (CoS)
             values."
          ::= { awcPolicyGroups 3 }

awcDscpToCosMapEntry OBJECT-TYPE
         SYNTAX AwcDscpToCosMapEntry
         MAX-ACCESS not-accessible
         STATUS current
         DESCRIPTION
             "An Entry (conceptual row) in the Aironet DSCP To CoS
             mapping table to statically map a Differentiated
             Services Code-Point (DSCP) value to  corresponding
             Class of Service (CoS) value."

         INDEX { awcDscpToCosMapDscp }

     ::= {  awcDscpToCosMapTable  1 }


AwcDscpToCosMapEntry ::= SEQUENCE {
             awcDscpToCosMapDscp     INTEGER,
             awcDscpToCosMapCos      INTEGER
             }

awcDscpToCosMapDscp OBJECT-TYPE
         SYNTAX INTEGER (1..64)
         MAX-ACCESS not-accessible
         STATUS current
         DESCRIPTION
             "The auxiliary variable used to identify instances
              of the columnar objects in the Aironet Differentiated
              Services Code-Point (DSCP) to  Class of Service (CoS)
              Mapping Table. This variable directly corresponds to
              a Differentiated Services Code-Point, plus 1. The
              value may be used for marking a traffic stream."
     ::= {  awcDscpToCosMapEntry 1 }

awcDscpToCosMapCos OBJECT-TYPE
         SYNTAX INTEGER (0..8)
         MAX-ACCESS read-write
         STATUS current
         DESCRIPTION
             "A  value of Class of Service (CoS) mapped to
             the DSCP value awcDscpToCosMapDscp. This object
             corresponds directly to the 802.1D traffic category
             ID, plus 1. The matching values are therefore in the
             range 1 through 8. The value 0 indicates that no
             matching CoS is configured for the corresponding
             awcDscpToCosMapDscp."
     ::= {  awcDscpToCosMapEntry 2 }


-- ********************************************************************
-- *  awcDdpIAPP parameters
-- ********************************************************************
awcIappMcastIpAddr OBJECT-TYPE
                SYNTAX IpAddress
                MAX-ACCESS read-write
                STATUS current
                DESCRIPTION
                        "Multicast IP network address over which
                         applicable packets of the DDP and IAPP
                         protocols are exchanged between stations.
                         Default 224.0.1.40."
                DEFVAL { 'E0000128'H }
        ::= {  awcDdpIAPP 1 }

awcIappPort OBJECT-TYPE
                SYNTAX INTEGER (1..65535)
                MAX-ACCESS read-write
                STATUS current
                DESCRIPTION
                        "IP port identifier through which applicable
                         packets of the DDP and IAPP protocols are
                         exchanged between stations.
                         Default 2887."
                DEFVAL { 2887 }
        ::= {  awcDdpIAPP 2 }

awcP802dot1XVersion OBJECT-TYPE
        SYNTAX INTEGER { d7(7), d8(8), d10(10) }
            MAX-ACCESS read-write
            STATUS current
            DESCRIPTION
                "Version of the 802.1X Protocol specification which
                 the AP will apply for incoming and outgoing EAPOL
                 traffic. Versions with 'd' designators are draft
                 specifications.  The 802.1x-2001 standard is the
                 same as draft 10."
            DEFVAL { d10 }
        ::= {  awcDdpIAPP 100 }


-- ********************************************************************
-- *  awcHotStandby parameters
-- ********************************************************************

awcHotStandbyMACAddr OBJECT-TYPE
                SYNTAX MacAddress
                MAX-ACCESS read-write
                STATUS current
                DESCRIPTION
                        "The MAC address of the target unit which is
                         being monitored."
                DEFVAL { '000000000000'H }
        ::= {  awcHotStandby 1 }

awcHotStandbyPollingFrequency OBJECT-TYPE
                SYNTAX INTEGER (1..30)
                UNITS "seconds"
                MAX-ACCESS read-write
                STATUS current
                DESCRIPTION
                        "The frequency (in seconds) that the monitored
                         target unit is being polled for testing its
                         health."
                DEFVAL { 1 }
        ::= {  awcHotStandby 2 }

awcHotStandbyPollingTimeOut OBJECT-TYPE
                SYNTAX INTEGER (1..600)
                UNITS "seconds"
                MAX-ACCESS read-write
                STATUS current
                DESCRIPTION
                    "The total time  (in seconds) that the monitoring
                     unit can tolerate the failure at polling the
                     monitored target unit.  After this duration, one
                     more failure of the polling will trigger the
                     standby unit to take the role of monitored unit."
                DEFVAL { 5 }
        ::= {  awcHotStandby 3 }

awcHotStandbyInHotStandby OBJECT-TYPE
                SYNTAX TruthValue
                MAX-ACCESS read-write
                STATUS current
                DESCRIPTION
                    "If true, the current unit is in its monitoring
                     mode, i.e., if the unit is or will be a hot
                     standby device."
                DEFVAL { false }
        ::= {  awcHotStandby 4 }

AwcHotStandbyState ::= TEXTUAL-CONVENTION
  STATUS        current
  DESCRIPTION
        "Hot standby state."
  SYNTAX        INTEGER {
                   running(0),
                   initializing(1),
                   stopped(2),
                   notRunning(3)
                   }

awcHotStandbyState OBJECT-TYPE
        SYNTAX AwcHotStandbyState
        MAX-ACCESS read-only
        STATUS current
        DESCRIPTION
                "The current state, e.g., running, stopped, ... of the hotstandby."
        ::= {  awcHotStandby 5 }

awcHotStandbyStatus OBJECT-TYPE
        SYNTAX AwcHotStandbyStatus
        MAX-ACCESS read-only
        STATUS current
        DESCRIPTION
                "The current stateus, e.g., error, OK, ... of the hotstandby."
        ::= {  awcHotStandby 6 }


-- **********************************************************************
-- *  awcAaa parameters
-- **********************************************************************

awcAaaServerTable OBJECT-TYPE
            SYNTAX SEQUENCE OF AwcAaaServerEntry
            MAX-ACCESS not-accessible
            STATUS current
            DESCRIPTION
                    "This table provides information of AAA servers
                     currently available to this access point and
                     the parameters used to connect to the servers.
                     Each entry corresponds to an AAA server and is
                     indexed by the priority in which the server
                     should be used.   AAA server of lowest priority
                     value should be used first.  Entries in this
                     table cannot be created or deleted by the
                     network management system.  All entries are
                     created or deleted by the agent."
        ::= { awcAaa 1 }

awcAaaServerEntry OBJECT-TYPE
            SYNTAX AwcAaaServerEntry
            MAX-ACCESS not-accessible
            STATUS current
            DESCRIPTION
                    "An entry provide the AAA server usage priority,
                     protocol, name, IP port, request timeout, and
                     authentication mechanisms supported."
            INDEX {awcAaaServerPriority}
        ::= { awcAaaServerTable 1 }

AwcAaaServerEntry ::=
        SEQUENCE {
                awcAaaServerPriority                INTEGER,
                awcAaaServerProtocol                INTEGER,
                awcAaaServerName                    DisplayString,
                awcAaaServerPort                    Unsigned32,
                awcAaaServerTimeout                 Unsigned32,
                awcAaaClientName                    DisplayString,
                awcAaaServerSharedSecret            DisplayString,
                awcAaaServer8021xCapabilityEnabled  TruthValue,
                awcAaaServerMacAddrAuthEnabled      TruthValue,
                awcAaaServerAdminAuthEnabled        TruthValue,
                awcAaaServerMipAuthEnabled          TruthValue,
                awcAaaServerMaxRetransmission       Unsigned32 }

awcAaaServerPriority OBJECT-TYPE
        SYNTAX INTEGER (1..4)
        MAX-ACCESS read-only
        STATUS current
        DESCRIPTION
                "The priority of the server for when multiple servers
                 are configured for the same service. Lower priority
                 servers are used, in sequence, as backups."
        ::= {  awcAaaServerEntry 1 }

awcAaaServerProtocol OBJECT-TYPE
        SYNTAX INTEGER {radius(1), tacacsPlus(2)}
        MAX-ACCESS read-write
        STATUS current
        DESCRIPTION
                "The protocol used to communicate with the AAA server."
        ::= {  awcAaaServerEntry 2 }

awcAaaServerName OBJECT-TYPE
        SYNTAX DisplayString
        MAX-ACCESS read-write
        STATUS current
        DESCRIPTION
                "The DNS-resolvable name or numeric IP address of the
                 AAA server."
        ::= {  awcAaaServerEntry 3 }

awcAaaServerPort OBJECT-TYPE
        SYNTAX Unsigned32
        MAX-ACCESS read-write
        STATUS current
        DESCRIPTION
                "The IP port number of the AAA server."
        ::= {  awcAaaServerEntry 4 }

awcAaaServerTimeout OBJECT-TYPE
        SYNTAX Unsigned32
        MAX-ACCESS read-write
        STATUS current
        DESCRIPTION
                "The amount of time (in seconds) that an Access Point
                 should wait for a response from the AAA server
                 before retransmitting the request. If the Access Point
                 does not receive a response within the timeout
                 period, it retransmits the request. If no response is
                 received for a maximum of awcAaaServerMaxRetransmission
                 retransmissions, the server is considered not reachable
                 and a secondary server (if any) will be chosen.
                 If the AP and the AAA server are connected through a
                 low-speed network and the awcAaaServerTimeout value is set
                 to too low, the network may become congested, as the AP
                 retransmits unacknowledged requests that have not yet
                 reached the server"
        ::= {  awcAaaServerEntry 5 }

awcAaaClientName OBJECT-TYPE
        SYNTAX DisplayString
        MAX-ACCESS read-write
        STATUS current
        DESCRIPTION
                "The name the Access Point uses to identify itself when
                 acting as the supplicant."
        ::= {  awcAaaServerEntry 6 }

awcAaaServerSharedSecret OBJECT-TYPE
        SYNTAX DisplayString
        MAX-ACCESS read-write
        STATUS current
        DESCRIPTION
                "The textual string shared between the AAA server and
                 the access point, used to authenticate the messages
                 delivered between them."
        ::= {  awcAaaServerEntry 7 }

awcAaaServer8021xCapabilityEnabled OBJECT-TYPE
        SYNTAX TruthValue
        MAX-ACCESS read-write
        STATUS current
        DESCRIPTION
                "Is this server to be used for 802.1X authentication?"
        ::= {  awcAaaServerEntry 8 }

awcAaaServerMacAddrAuthEnabled OBJECT-TYPE
        SYNTAX TruthValue
        MAX-ACCESS read-write
        STATUS current
        DESCRIPTION
                "Is this server to be used for MAC-address
                 authentication?"
        ::= {  awcAaaServerEntry 9 }

awcAaaServerAdminAuthEnabled OBJECT-TYPE
        SYNTAX TruthValue
        MAX-ACCESS read-write
        STATUS current
        DESCRIPTION
                "Is this server to be used for AP Admin
                 authentication?"
        ::= {  awcAaaServerEntry 10 }

awcAaaServerMipAuthEnabled OBJECT-TYPE
        SYNTAX TruthValue
        MAX-ACCESS read-write
        STATUS current
        DESCRIPTION
                "Is this server to be used for Proxy Mobile IP
                 authentication?"
        ::= {  awcAaaServerEntry 11 }

awcAaaServerMaxRetransmission OBJECT-TYPE
        SYNTAX Unsigned32
        MAX-ACCESS read-write
        STATUS current
        DESCRIPTION
                "The maximum number of retransmission of a request.
                 If an Access Point does not receive a response within
                 awcAaaServerTimeout, it retransmits the request. If no
                 response is received for a maximum number of
                 retransmissions, the server is considered not reachable
                 and a secondary server (if any) will be chosen
                 temporarily."
        ::= {  awcAaaServerEntry 12 }


awcAcctServerTable OBJECT-TYPE
            SYNTAX SEQUENCE OF AwcAcctServerEntry
            MAX-ACCESS not-accessible
            STATUS current
            DESCRIPTION
                    "This table provides information of AAA
                     accounting servers currently available to
                     this access point and the parameters used to
                     connect to the servers.
                     Each entry corresponds to an AAA server and is
                     indexed by the priority in which the server
                     should be used.   AAA server of lowest priority
                     value should be used first.  Entries in this
                     table cannot be created or deleted by the
                     network management system.  All entries are
                     created or deleted by the agent."
        ::= { awcAaa 2 }

awcAcctServerEntry OBJECT-TYPE
            SYNTAX AwcAcctServerEntry
            MAX-ACCESS not-accessible
            STATUS current
            DESCRIPTION
                    "An entry provide the AAA server usage priority,
                     protocol, name, IP port, request timeout, and
                     security mechanisms supported."
            INDEX {awcAcctServerPriority}
        ::= { awcAcctServerTable 1 }

AwcAcctServerEntry ::=
        SEQUENCE {
                awcAcctServerPriority               INTEGER,
                awcAcctServerProtocol               INTEGER,
                awcAcctServerName                   DisplayString,
                awcAcctServerPort                   Unsigned32,
                awcAcctServerTimeout                Unsigned32,
                awcAcctServerUpdateEnable           TruthValue,
                awcAcctServerUpdateDelay            Unsigned32,
                awcAcctClientName                   DisplayString,
                awcAcctSecureEnabled                TruthValue,
                awcAcctGeneralEnabled               TruthValue,
                awcAcctServerSharedSecret           DisplayString,
                awcAcctServerMaxRetransmission      Unsigned32 }

awcAcctServerPriority OBJECT-TYPE
        SYNTAX INTEGER (1..4)
        MAX-ACCESS read-only
        STATUS current
        DESCRIPTION
                "The priority of the server for when multiple servers
                 are configured for the same service. Lower priority
                 servers are used, in sequence, as backups."
        ::= { awcAcctServerEntry 1 }

awcAcctServerProtocol OBJECT-TYPE
        SYNTAX INTEGER {radius(1), tacacsPlus(2)}
        MAX-ACCESS read-write
        STATUS current
        DESCRIPTION
                "The protocol used to communicate with the AAA server."
        ::= {  awcAcctServerEntry 2 }

awcAcctServerName OBJECT-TYPE
        SYNTAX DisplayString
        MAX-ACCESS read-write
        STATUS current
        DESCRIPTION
                "The DNS-resolvable name or numeric IP address of the
                 AAA server."
        ::= {  awcAcctServerEntry 3 }

awcAcctServerPort OBJECT-TYPE
        SYNTAX Unsigned32
        MAX-ACCESS read-write
        STATUS current
        DESCRIPTION
                "The IP port number of the AAA server."
        ::= {  awcAcctServerEntry 4 }

awcAcctServerTimeout OBJECT-TYPE
        SYNTAX Unsigned32
        MAX-ACCESS read-write
        STATUS current
        DESCRIPTION
                "The amount of time (in seconds) that an Access Point
                 should wait for a response from the Accounting server
                 before retransmitting the request. If the Access Point
                 does not receive a response within the timeout
                 period, it retransmits the request. If no response is
                 received for a maximum of awcAcctServerMaxRetransmission
                 retransmissions, the server is considered not reachable
                 and a secondary server (if any) will be chosen.
                 If the AP and the Accounting server are connected through a
                 low-speed network and the awcAcctServerTimeout value is set
                 to too low, the network may become congested, as the AP
                 retransmits unacknowledged accounting requests that have
                 not yet reached the server"
        ::= {  awcAcctServerEntry 5 }

awcAcctServerUpdateEnable OBJECT-TYPE
        SYNTAX TruthValue
        MAX-ACCESS read-write
        STATUS current
        DESCRIPTION
                "Is the Acct update to this server enabled?."
        ::= {  awcAcctServerEntry 6 }

awcAcctServerUpdateDelay OBJECT-TYPE
        SYNTAX Unsigned32 (60..2592000)
        MAX-ACCESS read-write
        STATUS current
        DESCRIPTION
                "The amount of time (in seconds) that the Access Point
                 should send to the AAA server an update of accounting information."
        ::= {  awcAcctServerEntry 7 }

awcAcctClientName OBJECT-TYPE
        SYNTAX DisplayString
        MAX-ACCESS read-write
        STATUS current
        DESCRIPTION
                "The name the Access Point uses to identify itself when
                 acting as the supplicant."
        ::= {  awcAcctServerEntry 8 }

awcAcctSecureEnabled OBJECT-TYPE
        SYNTAX TruthValue
        MAX-ACCESS read-write
        STATUS current
        DESCRIPTION
                "Is this server to be used for accounting with security AUTH?"
        ::= {  awcAcctServerEntry 9 }

awcAcctGeneralEnabled OBJECT-TYPE
        SYNTAX TruthValue
        MAX-ACCESS read-write
        STATUS current
        DESCRIPTION
                "Is this server to be used for accounting without security AUTH?"
        ::= {  awcAcctServerEntry 10 }

awcAcctServerSharedSecret OBJECT-TYPE
        SYNTAX DisplayString
        MAX-ACCESS read-write
        STATUS current
        DESCRIPTION
                "The textual string shared between the ACCT server and
                 the access point, used to authenticate the messages
                 delivered between them."
        ::= {  awcAcctServerEntry 11 }

awcAcctServerMaxRetransmission OBJECT-TYPE
        SYNTAX Unsigned32
        MAX-ACCESS read-write
        STATUS current
        DESCRIPTION
                "The maximum number of retransmissions of an accounting
                 request. If an Access Point does not receive a response
                 within awcAcctServerTimeout, it retransmits the request.
                 If no response is received for a maximum number of
                 retransmissions, the server is considered not reachable
                 and a secondary server (if any) will be chosen."
        ::= {  awcAcctServerEntry 12 }


awcAcctEnable OBJECT-TYPE
        SYNTAX TruthValue
        MAX-ACCESS read-write
        STATUS current
        DESCRIPTION
                "The boolean indicating if the accounting is enabled."
        DEFVAL { false }
        ::= { awcAcctConfig 1 }

awcAcctStopDelayEnable OBJECT-TYPE
        SYNTAX TruthValue
        MAX-ACCESS read-write
        STATUS current
        DESCRIPTION
                "The boolean indicating if the accounting stop request
				should be delayed before sent."
        DEFVAL { true }
        ::= { awcAcctConfig 2 }

awcAcctStopDelayTime OBJECT-TYPE
        SYNTAX Unsigned32
        MAX-ACCESS read-write
        STATUS current
        DESCRIPTION
                "The duration for the AP to delay sending the STOP message if any."
        DEFVAL { 2 }
        ::= { awcAcctConfig 3 }


-- **********************************************************************
-- *  awcAaaAuthConfig parameters - Common to all Authentication servers
-- **********************************************************************

awcAaaAuthConfig  OBJECT IDENTIFIER ::= { awcAaa 4 }

awcAaaServerPrimaryReattemptPeriod  OBJECT-TYPE
        SYNTAX Unsigned32
        MAX-ACCESS read-write
        STATUS current
        DESCRIPTION
                "While the primary authentication server serving a given
                 authentication function is not reachable, the duration,
                 in minutes, at which the AP should reattempt to return
                 to its primary server serving that authentication function.
                 A value of zero indicates that primary authentication server
                 reattempt is disabled."
        ::= {  awcAaaAuthConfig 1 }

awcAaaServerDot1xAuthCurrent  OBJECT-TYPE
        SYNTAX INTEGER (0..4)
        MAX-ACCESS read-only
        STATUS current
        DESCRIPTION
                "The index of the currently selected AAA server for 802.1X user
                authentication. A value of zero indicates that no authentication
                server is available to service 802.1X authentication function to
                this AP. The value of 1 to 4 indicates the corresponding server
                for 802.1X authentication."
        ::= {  awcAaaAuthConfig 2 }


awcAaaServerMacAddrAuthCurrent  OBJECT-TYPE
        SYNTAX INTEGER (0..4)
        MAX-ACCESS read-only
        STATUS current
        DESCRIPTION
                "The index of the currently selected AAA server for MAC address
                authentication. A value of zero indicates that no authentication
                server is available to service MAC address authentication
                function to this AP. The value of 1 to 4 indicates the
                corresponding server in use for MAC address authentication
                function."
        ::= {  awcAaaAuthConfig 3 }

awcAaaServerAdminAuthCurrent  OBJECT-TYPE
        SYNTAX INTEGER (0..4)
        MAX-ACCESS read-only
        STATUS current
        DESCRIPTION
                "The index of the currently selected AAA server for the Access
                Point administrator authentication function. A value of zero
                indicates that no authentication server is available to service
                admin login authentication function to this AP. The value of 1
                to 4 indicates the corresponding server in use for the AP admin
                authentication function."

        ::= {  awcAaaAuthConfig 4 }

awcAaaServerMipAuthCurrent  OBJECT-TYPE
        SYNTAX INTEGER (0..4)
        MAX-ACCESS read-only
        STATUS current
        DESCRIPTION
                "The index of the currently selected AAA server used to retrieve
                authentication data requied for Proxy Mobile registration and
                authentication function. A value of zero indicates that no
                authentication server is available for this function. The value of 1
                to 4 indicates the corresponding server in use for proxy mobile IP
                related authentication function."

        ::= {  awcAaaAuthConfig 5 }


-- ********************************************************************
-- *  awcProtocolFilters parameters
-- ********************************************************************

AwcPfDisposition ::= TEXTUAL-CONVENTION
  STATUS       current
  DESCRIPTION
          "Designate whether a protocol should be forwarded or blocked,
           or should behave in the default manner of the associated
           network interface."
  SYNTAX       INTEGER { forward(1), block(2), default(3) }

AwcPfPriority ::= TEXTUAL-CONVENTION
  STATUS       current
  DESCRIPTION
          "Designate the 802.1P priority with which a protocol should
           be queued."
  SYNTAX       INTEGER { default(1), background(2), spare(3),
                         excellentEffort(4), controlledLoad(5),
                         interactiveVideo(6), interactiveVoice(7),
                         networkControl(8) }

awcPrFltEthertypeSetTable OBJECT-TYPE
            SYNTAX SEQUENCE OF AwcPrFltEthertypeSetEntry
            MAX-ACCESS not-accessible
            STATUS current
            DESCRIPTION
                    "Table of static Ethertype Filters"
        ::= { awcProtocolFilters 1 }

awcPrFltEthertypeSetEntry OBJECT-TYPE
            SYNTAX AwcPrFltEthertypeSetEntry
            MAX-ACCESS not-accessible
            STATUS current
            DESCRIPTION
                    "An entry in awcPrFltEthertypeTable."
            INDEX {awcPfEtSetId}
        ::= { awcPrFltEthertypeSetTable 1 }

AwcPrFltEthertypeSetEntry ::=
        SEQUENCE {
            awcPfEtSetId                    Unsigned32,
            awcPfEtSetName                  DisplayString,
			awcPfEtDefaultDisposition       AwcPfDisposition,
			awcPfEtDefaultUcastTimeToLive   Unsigned32,
			awcPfEtDefaultNUcastTimeToLive  Unsigned32,
            awcPfEtSetStatus                RowStatus }

awcPfEtSetId OBJECT-TYPE
                SYNTAX Unsigned32
                MAX-ACCESS read-only
                STATUS current
                DESCRIPTION
                        "Numeric identifier of the static Ethertype
                         filters set."
        ::= {  awcPrFltEthertypeSetEntry 1 }

awcPfEtSetName OBJECT-TYPE
                SYNTAX DisplayString (SIZE(0..64))
                MAX-ACCESS read-create
                STATUS current
                DESCRIPTION
                        "Descriptive name of the static Ethertype
                         filters set. Max. string length is 64 octets."
        ::= {  awcPrFltEthertypeSetEntry 2 }

awcPfEtDefaultDisposition OBJECT-TYPE
                SYNTAX   AwcPfDisposition
                MAX-ACCESS  read-create
                STATUS  current
                DESCRIPTION
                "Default packet disposition of the static Ethertype
                 filters set."
                DEFVAL { forward }
        ::= {  awcPrFltEthertypeSetEntry 3 }

awcPfEtDefaultUcastTimeToLive OBJECT-TYPE
                SYNTAX   Unsigned32
                MAX-ACCESS  read-create
                STATUS  current
                DESCRIPTION
                "Default time-to-live for unicast (directed) packets.
                 A value of 0 means to use the system defaults."
                DEFVAL { 0 }
        ::= {  awcPrFltEthertypeSetEntry 4 }

awcPfEtDefaultNUcastTimeToLive OBJECT-TYPE
                SYNTAX   Unsigned32
                MAX-ACCESS  read-create
                STATUS  current
                DESCRIPTION
                "Default time-to-live for non-unicast (multicast)
                 packets. A value of 0 means to use the system
                 defaults."
                DEFVAL { 0 }
        ::= {  awcPrFltEthertypeSetEntry 5 }

awcPfEtSetStatus OBJECT-TYPE
                SYNTAX   RowStatus
                MAX-ACCESS  read-create
                STATUS  current
                DESCRIPTION
                "Row status of the entire static Ethertype filters
                 set."
        ::= {  awcPrFltEthertypeSetEntry 6 }

awcPrFltEthertypeTable OBJECT-TYPE
                SYNTAX SEQUENCE OF AwcPrFltEthertypeEntry
                MAX-ACCESS not-accessible
                STATUS current
                DESCRIPTION
                        "Table of individual static Ethertype filters."
        ::= { awcProtocolFilters 2 }

awcPrFltEthertypeEntry OBJECT-TYPE
                SYNTAX AwcPrFltEthertypeEntry
                MAX-ACCESS not-accessible
                STATUS current
                DESCRIPTION
                        "An entry in the individual static Ethertype
                         filter table."
                INDEX {awcPfEtSetId, awcPfEtEthertype}
        ::= { awcPrFltEthertypeTable 1 }

AwcPrFltEthertypeEntry ::=
                SEQUENCE {
                         awcPfEtEthertype         INTEGER,
                         awcPfEtDisposition       AwcPfDisposition,
                         awcPfEtUserPriority      AwcPfPriority,
                         awcPfEtUcastTimeToLive   Unsigned32,
                         awcPfEtNUcastTimeToLive  Unsigned32,
                         awcPfEtAlert             TruthValue,
                         awcPfEtStatus            RowStatus
                }

awcPfEtEthertype OBJECT-TYPE
                SYNTAX INTEGER (1..255|1501..65535)
                MAX-ACCESS read-only
                STATUS current
                DESCRIPTION
                        "Ethertype (protocol) to which this individual
                         static filter applies"
        ::= {  awcPrFltEthertypeEntry 1 }

awcPfEtDisposition OBJECT-TYPE
                SYNTAX AwcPfDisposition
                MAX-ACCESS read-create
                STATUS current
                DESCRIPTION
                        "Designation of how the protocol should be
                         handled."
                DEFVAL { default }
        ::= {  awcPrFltEthertypeEntry 2 }

awcPfEtUserPriority OBJECT-TYPE
                SYNTAX AwcPfPriority
                MAX-ACCESS read-create
                STATUS current
                DESCRIPTION
                        "Designation of the priority assigned to
                         packets of the Ethertype."
                DEFVAL { default }
        ::= {  awcPrFltEthertypeEntry 3 }

awcPfEtUcastTimeToLive OBJECT-TYPE
                SYNTAX   Unsigned32
                MAX-ACCESS  read-create
                STATUS  current
                DESCRIPTION
                "Time-to-live for unicast (directed) packets.  A
                value of 0 means to use the Filter Set defaults."
                DEFVAL { 0 }
        ::= {  awcPrFltEthertypeEntry 4 }

awcPfEtNUcastTimeToLive OBJECT-TYPE
                SYNTAX   Unsigned32
                MAX-ACCESS  read-create
                STATUS  current
                DESCRIPTION
                "Time-to-live for non-unicast (multicast) packets.  A
                value of 0 means to use the Filter Set defaults."
                DEFVAL { 0 }
        ::= {  awcPrFltEthertypeEntry 5 }

awcPfEtAlert OBJECT-TYPE
                SYNTAX TruthValue
                MAX-ACCESS read-create
                STATUS current
                DESCRIPTION
                        "Should an alert be registered when a packet of
                         this Ethertype is observed?"
                DEFVAL { false }
        ::= {  awcPrFltEthertypeEntry 6 }

awcPfEtStatus OBJECT-TYPE
                SYNTAX   RowStatus
                MAX-ACCESS  read-create
                STATUS  current
                DESCRIPTION
                    "Row status of the individual static Ethertype
                     filters."
        ::= {  awcPrFltEthertypeEntry 7 }



awcPrFltIpProtocolSetTable OBJECT-TYPE
            SYNTAX SEQUENCE OF AwcPrFltIpProtocolSetEntry
            MAX-ACCESS not-accessible
            STATUS current
            DESCRIPTION
                    "Table of static IP Protocol Filters"
        ::= { awcProtocolFilters 3 }

awcPrFltIpProtocolSetEntry OBJECT-TYPE
            SYNTAX AwcPrFltIpProtocolSetEntry
            MAX-ACCESS not-accessible
            STATUS current
            DESCRIPTION
                    "An entry in awcPrFltIpProtocolTable."
            INDEX {awcPfIppSetId}
        ::= { awcPrFltIpProtocolSetTable 1 }

AwcPrFltIpProtocolSetEntry ::=
        SEQUENCE {
            awcPfIppSetId                       Unsigned32,
            awcPfIppSetName                     DisplayString,
            awcPfIppDefaultDisposition          AwcPfDisposition,
            awcPfIppDefaultUcastTimeToLive      Unsigned32,
            awcPfIppDefaultNUcastTimeToLive     Unsigned32,
            awcPfIppSetStatus                   RowStatus }

awcPfIppSetId OBJECT-TYPE
                SYNTAX Unsigned32
                MAX-ACCESS read-only
                STATUS current
                DESCRIPTION
                        "Numeric identifier of the static IP Protocol
                         filters set."
        ::= {  awcPrFltIpProtocolSetEntry 1 }

awcPfIppSetName OBJECT-TYPE
                SYNTAX DisplayString (SIZE(0..64))
                MAX-ACCESS read-create
                STATUS current
                DESCRIPTION
                        "Descriptive name of the static IP Protocol
                         filters set. Max. string length is 64 octets."
        ::= {  awcPrFltIpProtocolSetEntry 2 }

awcPfIppDefaultDisposition OBJECT-TYPE
                SYNTAX   AwcPfDisposition
                MAX-ACCESS  read-create
                STATUS  current
                DESCRIPTION
                "Default packet disposition of the static IP Protocol
                 filters set."
                DEFVAL { forward }
        ::= {  awcPrFltIpProtocolSetEntry 3 }

awcPfIppDefaultUcastTimeToLive OBJECT-TYPE
                SYNTAX   Unsigned32
                MAX-ACCESS  read-create
                STATUS  current
                DESCRIPTION
                "Default time-to-live for unicast (directed) packets.
                 A value of 0 means to use the system defaults."
                DEFVAL { 0 }
        ::= {  awcPrFltIpProtocolSetEntry 4 }

awcPfIppDefaultNUcastTimeToLive OBJECT-TYPE
                SYNTAX   Unsigned32
                MAX-ACCESS  read-create
                STATUS  current
                DESCRIPTION
                "Default time-to-live for non-unicast (multicast)
                 packets.  A value of 0 means to use the system
                 defaults."
                DEFVAL { 0 }
        ::= {  awcPrFltIpProtocolSetEntry 5 }

awcPfIppSetStatus OBJECT-TYPE
                SYNTAX   RowStatus
                MAX-ACCESS  read-create
                STATUS  current
                DESCRIPTION
                "Row status of the entire static IP Protocol filters
                 set."
        ::= {  awcPrFltIpProtocolSetEntry 6 }

awcPrFltIpProtocolTable OBJECT-TYPE
                SYNTAX SEQUENCE OF AwcPrFltIpProtocolEntry
                MAX-ACCESS not-accessible
                STATUS current
                DESCRIPTION
                        "Table of individual static IP Protocol
                         filters."
        ::= { awcProtocolFilters 4 }

awcPrFltIpProtocolEntry OBJECT-TYPE
                SYNTAX AwcPrFltIpProtocolEntry
                MAX-ACCESS not-accessible
                STATUS current
                DESCRIPTION
                        "An entry in the individual static IP Protocol
                         filter table."
                INDEX {awcPfIppSetId, awcPfIppIpProtocol}
        ::= { awcPrFltIpProtocolTable 1 }

AwcPrFltIpProtocolEntry ::=
                SEQUENCE {
                         awcPfIppIpProtocol        INTEGER,
                         awcPfIppDisposition       AwcPfDisposition,
                         awcPfIppUserPriority      AwcPfPriority,
                         awcPfIppUcastTimeToLive   Unsigned32,
                         awcPfIppNUcastTimeToLive  Unsigned32,
                         awcPfIppAlert             TruthValue,
                         awcPfIppStatus            RowStatus
                }

awcPfIppIpProtocol OBJECT-TYPE
                SYNTAX INTEGER (0..255)
                MAX-ACCESS read-only
                STATUS current
                DESCRIPTION
                       "IP Protocol to which this individual static
                        filter applies"
        ::= {  awcPrFltIpProtocolEntry 1 }

awcPfIppDisposition OBJECT-TYPE
                SYNTAX AwcPfDisposition
                MAX-ACCESS read-create
                STATUS current
                DESCRIPTION
                        "Designation of how the protocol should be
                         handled."
                DEFVAL { default }
        ::= {  awcPrFltIpProtocolEntry 2 }

awcPfIppUserPriority OBJECT-TYPE
                SYNTAX AwcPfPriority
                MAX-ACCESS read-create
                STATUS current
                DESCRIPTION
                        "Designation of the priority assigned to
                         packets of the IP Protocol."
                DEFVAL { default }
        ::= {  awcPrFltIpProtocolEntry 3 }

awcPfIppUcastTimeToLive OBJECT-TYPE
                SYNTAX   Unsigned32
                MAX-ACCESS  read-create
                STATUS  current
                DESCRIPTION
                "Time-to-live for unicast (directed) packets.  A
                value of 0 means to use the Filter Set defaults."
                DEFVAL { 0 }
        ::= {  awcPrFltIpProtocolEntry 4 }

awcPfIppNUcastTimeToLive OBJECT-TYPE
                SYNTAX   Unsigned32
                MAX-ACCESS  read-create
                STATUS  current
                DESCRIPTION
                "Time-to-live for non-unicast (multicast) packets.  A
                value of 0 means to use the Filter Set defaults."
                DEFVAL { 0 }
        ::= {  awcPrFltIpProtocolEntry 5 }

awcPfIppAlert OBJECT-TYPE
                SYNTAX TruthValue
                MAX-ACCESS read-create
                STATUS current
                DESCRIPTION
                        "Should an alert be registered when a packet
                         of this IP Protocol is observed?"
                DEFVAL { false }
        ::= {  awcPrFltIpProtocolEntry 6 }

awcPfIppStatus OBJECT-TYPE
                SYNTAX   RowStatus
                MAX-ACCESS  read-create
                STATUS  current
                DESCRIPTION
                "Row status of the individual static IP Protocol
                 filters."
        ::= {  awcPrFltIpProtocolEntry 7 }



awcPrFltIpPortSetTable OBJECT-TYPE
            SYNTAX SEQUENCE OF AwcPrFltIpPortSetEntry
            MAX-ACCESS not-accessible
            STATUS current
            DESCRIPTION
                    "Table of static IP Port Filters"
        ::= { awcProtocolFilters 5 }

awcPrFltIpPortSetEntry OBJECT-TYPE
            SYNTAX AwcPrFltIpPortSetEntry
            MAX-ACCESS not-accessible
            STATUS current
            DESCRIPTION
                    "An entry in awcPrFltIpPortTable."
            INDEX {awcPfIptSetId}
        ::= { awcPrFltIpPortSetTable 1 }

AwcPrFltIpPortSetEntry ::=
        SEQUENCE {
            awcPfIptSetId                       Unsigned32,
            awcPfIptSetName                     DisplayString,
            awcPfIptDefaultDisposition          AwcPfDisposition,
            awcPfIptDefaultUcastTimeToLive      Unsigned32,
            awcPfIptDefaultNUcastTimeToLive     Unsigned32,
            awcPfIptSetStatus                   RowStatus }

awcPfIptSetId OBJECT-TYPE
                SYNTAX Unsigned32
                MAX-ACCESS read-only
                STATUS current
                DESCRIPTION
                        "Numeric identifier of the static IP Port
                         filters set."
        ::= {  awcPrFltIpPortSetEntry 1 }

awcPfIptSetName OBJECT-TYPE
                SYNTAX DisplayString (SIZE(0..64))
                MAX-ACCESS read-create
                STATUS current
                DESCRIPTION
                        "Descriptive name of the static IP Port filters
                         set. Max. string length is 64 octets."
        ::= {  awcPrFltIpPortSetEntry 2 }

awcPfIptDefaultDisposition OBJECT-TYPE
                SYNTAX   AwcPfDisposition
                MAX-ACCESS  read-create
                STATUS  current
                DESCRIPTION
                "Default packet disposition of the static IP Port
                 filters set."
                DEFVAL { forward }
        ::= {  awcPrFltIpPortSetEntry 3 }

awcPfIptDefaultUcastTimeToLive OBJECT-TYPE
                SYNTAX   Unsigned32
                MAX-ACCESS  read-create
                STATUS  current
                DESCRIPTION
                "Default time-to-live for unicast (directed) packets.
                 A value of 0 means to use the system defaults."
                DEFVAL { 0 }
        ::= {  awcPrFltIpPortSetEntry 4 }

awcPfIptDefaultNUcastTimeToLive OBJECT-TYPE
                SYNTAX   Unsigned32
                MAX-ACCESS  read-create
                STATUS  current
                DESCRIPTION
                "Default time-to-live for non-unicast (multicast)
                packets. A value of 0 means to use the system
                defaults."
                DEFVAL { 0 }
        ::= {  awcPrFltIpPortSetEntry 5 }

awcPfIptSetStatus OBJECT-TYPE
                SYNTAX   RowStatus
                MAX-ACCESS  read-create
                STATUS  current
                DESCRIPTION
                "Row status of the entire static IP Port filters set."
        ::= {  awcPrFltIpPortSetEntry 6 }

awcPrFltIpPortTable OBJECT-TYPE
                SYNTAX SEQUENCE OF AwcPrFltIpPortEntry
                MAX-ACCESS not-accessible
                STATUS current
                DESCRIPTION
                        "Table of individual static IP Port filters."
        ::= { awcProtocolFilters 6 }

awcPrFltIpPortEntry OBJECT-TYPE
                SYNTAX AwcPrFltIpPortEntry
                MAX-ACCESS not-accessible
                STATUS current
                DESCRIPTION
                        "An entry in the individual static IP Port
                         filter table."
                INDEX {awcPfIptSetId, awcPfIptIpPort}
        ::= { awcPrFltIpPortTable 1 }

AwcPrFltIpPortEntry ::=
                SEQUENCE {
                         awcPfIptIpPort            INTEGER,
                         awcPfIptDisposition       AwcPfDisposition,
                         awcPfIptUserPriority      AwcPfPriority,
                         awcPfIptUcastTimeToLive   Unsigned32,
                         awcPfIptNUcastTimeToLive  Unsigned32,
                         awcPfIptAlert             TruthValue,
                         awcPfIptStatus            RowStatus
                }

awcPfIptIpPort OBJECT-TYPE
                SYNTAX INTEGER (1..65535)
                MAX-ACCESS read-only
                STATUS current
                DESCRIPTION
                        "IP Port to which this individual static filter
                         applies"
        ::= {  awcPrFltIpPortEntry 1 }

awcPfIptDisposition OBJECT-TYPE
                SYNTAX AwcPfDisposition
                MAX-ACCESS read-create
                STATUS current
                DESCRIPTION
                        "Designation of how the Port should be
                         handled."
                DEFVAL { default }
        ::= {  awcPrFltIpPortEntry 2 }

awcPfIptUserPriority OBJECT-TYPE
                SYNTAX AwcPfPriority
                MAX-ACCESS read-create
                STATUS current
                DESCRIPTION
                        "Designation of the priority assigned to
                         packets of the IP Port."
                DEFVAL { default }
        ::= {  awcPrFltIpPortEntry 3 }

awcPfIptUcastTimeToLive OBJECT-TYPE
                SYNTAX   Unsigned32
                MAX-ACCESS  read-create
                STATUS  current
                DESCRIPTION
                "Time-to-live for unicast (directed) packets.  A
                value of 0 means to use the Filter Set defaults."
                DEFVAL { 0 }
        ::= {  awcPrFltIpPortEntry 4 }

awcPfIptNUcastTimeToLive OBJECT-TYPE
                SYNTAX   Unsigned32
                MAX-ACCESS  read-create
                STATUS  current
                DESCRIPTION
                "Time-to-live for non-unicast (multicast) packets.  A
                value of 0 means to use the Filter Set defaults."
                DEFVAL { 0 }
        ::= {  awcPrFltIpPortEntry 5 }

awcPfIptAlert OBJECT-TYPE
                SYNTAX TruthValue
                MAX-ACCESS read-create
                STATUS current
                DESCRIPTION
                        "Should an alert be registered when a packet of
                         this IP Port is observed?"
                DEFVAL { false }
        ::= {  awcPrFltIpPortEntry 6 }

awcPfIptStatus OBJECT-TYPE
                SYNTAX   RowStatus
                MAX-ACCESS  read-create
                STATUS  current
                DESCRIPTION
                "Row status of the individual static IP Port filters."
        ::= {  awcPrFltIpPortEntry 7 }


-- ********************************************************************
-- *  awcMobileIP parameters
-- ********************************************************************

enableMobileIP OBJECT-TYPE
         SYNTAX TruthValue
         MAX-ACCESS read-write
         STATUS current
         DESCRIPTION
                 "If true, the Access Point's proxy mobile IP
                  service is enabled.  If false, proxy mobile
                  IP service is disabled."
         DEFVAL { true }
         ::= {  awcMobileIP 1 }

awcprimAAP OBJECT-TYPE
        SYNTAX DisplayString (SIZE(0..128))
        MAX-ACCESS read-write
        STATUS current
        DESCRIPTION
                "The first AAP hostname or IP address from a
                 list of 3 AAPs."
        ::= { awcMobileIP 2 }

awcsec1AAP OBJECT-TYPE
        SYNTAX DisplayString (SIZE(0..128))
        MAX-ACCESS read-write
        STATUS current
        DESCRIPTION
                "The second AAP hostname or IP address from a
                 list of 3 AAPs."
        ::= { awcMobileIP 3 }

awcsec2AAP OBJECT-TYPE
        SYNTAX DisplayString (SIZE(0..128))
        MAX-ACCESS read-write
        STATUS current
        DESCRIPTION
                "The third AAP hostname or IP address from a
                 list of 3 AAPs."
        ::= { awcMobileIP 4 }

-- mipSATable

mipSATable OBJECT-TYPE
        SYNTAX  SEQUENCE OF MipSAEntry
        MAX-ACCESS  not-accessible
        STATUS  current
        DESCRIPTION
                "This entity's Mobile IP Local SA Bindings table."
        ::= { awcMobileIP 5}

mipSAEntry OBJECT-TYPE
        SYNTAX  MipSAEntry
        MAX-ACCESS  not-accessible
        STATUS  current
        DESCRIPTION
                "An entry of SA bindings for a range of IP Addresses."
        INDEX   { mipSAIpStart }
        ::= { mipSATable 1 }

MipSAEntry ::= SEQUENCE {
                mipSAIpStart IpAddress,
                mipSAIpEnd IpAddress,
                mipSAGroupSPI DisplayString,
                mipSAGroupKey DisplayString,
                mipSAStatus RowStatus
                        }

mipSAIpStart OBJECT-TYPE
        SYNTAX  IpAddress
        MAX-ACCESS not-accessible
        STATUS  current
        DESCRIPTION
                "Starting IP Address of a range for the SA binding."
        ::= { mipSAEntry 1 }

mipSAIpEnd OBJECT-TYPE
        SYNTAX  IpAddress
        MAX-ACCESS  read-create
        STATUS  current
        DESCRIPTION
                "Ending IP Address of the range for the SA binding."
        ::= { mipSAEntry 2 }

mipSAGroupSPI OBJECT-TYPE
        SYNTAX DisplayString (SIZE(0..128))
        MAX-ACCESS  read-create
        STATUS current
        DESCRIPTION
                "Group SPI for the range of IP Address in the Local
                 SA binding"
        ::= { mipSAEntry 3 }

mipSAGroupKey OBJECT-TYPE
        SYNTAX DisplayString (SIZE(0..128))
        MAX-ACCESS  read-create
        STATUS current
        DESCRIPTION
                "Group Key for the range of IP Address in the Local
                 SA binding"
        ::= { mipSAEntry 4 }

mipSAStatus OBJECT-TYPE
        SYNTAX   RowStatus
        MAX-ACCESS  read-create
        STATUS  current
        DESCRIPTION
                "Row status of the pMIP SA.  Allows deletion via SNMP."
        ::= {  mipSAEntry 5 }

awcmipDebug OBJECT-TYPE
        SYNTAX TruthValue
	MAX-ACCESS  read-write
        STATUS current
        DESCRIPTION
                "If true, the Access Point's proxy mobile IP
                 debug information is printed on the console.
                 If false, debug messages are not printed."
        DEFVAL { true }
        ::= {  awcMobileIP 6 }


-- ********************************************************************
-- *  awcEventLog Traps
-- ********************************************************************

    awcTrapLog NOTIFICATION-TYPE
        OBJECTS { awcEventTime, awcEventSeverity, awcEventDescription,
                  awcEventType }
        STATUS  current
        DESCRIPTION
                "SNMP trap corresponding to an event with a Severity
                 Level requiring Notify Disposition while
                 awcEventAlertSNMP is true."
        ::= { aironet 4 }



-- ********************************************************************
-- *    End of awcEventLog parameters
-- ********************************************************************

-- ********************************************************************
-- *  awcExperimental parameters
-- ********************************************************************

-- ********************************************************************
-- *    End of awcExperimental parameters
-- ********************************************************************

-- ********************************************************************
-- *    Conformance information
-- ********************************************************************

awcVxConformance
              OBJECT IDENTIFIER ::= { awcVx 100 }
awcVxCompliances
              OBJECT IDENTIFIER ::= { awcVxConformance 1 }
awcVxGroups
              OBJECT IDENTIFIER ::= { awcVxConformance 2 }


-- ********************************************************************
-- *    Compliance statements
-- ********************************************************************

awcVxCompliance MODULE-COMPLIANCE
    STATUS  current
    DESCRIPTION
            "The compliance statement for the awcVx group."
    MODULE  -- this module
            MANDATORY-GROUPS {
                    awcSystemGroup,
                    bootconfigVxGroup,
                    awcSerialDevGroup,
                    awcFtpGroup,
                    awcIfTableGroup,
                    awc802dot11Group,
                    awcUserMgrGroup,
                    awcHttpdGroup,
                    awcDnsResGroup,
                    awcSnmpGroup,
                    awcSntpGroup,
                    awcForwardTblGroup,
--                  awcRipConfigGroup,
                    awcEventLogGroup,
                    awcEtherMIBGroup,
                    awcDdpIAPPGroup,
                    awcHotStandbyGroup,
                    awcAaaGroup,
                    awcProtocolFiltersGroup,
                    awcMobileIpGroup
            }

    ::= { awcVxCompliances 1 }

-- ********************************************************************
-- *    Units of conformance
-- ********************************************************************

awcSystemGroup  OBJECT-GROUP
    OBJECTS {
        vxWorksVersion,
        creationDate,
        awcVxVersion,
        sysFlags,
        languageCode,
        awcDevID,
        awcDevIDtxt,
        enableHTTP,
        enableTelnet,
        enableSNMP,
        enableDnsResolver,
        enableSNTP,
        enableWDB,
        pingTxLen,
        awcFirstBoot,
        awcOemOUI,
        awcOemName,
        awcOemNameShort,
        awcOemHomeURL,
        enablePSPF,
        sysExceptionReboot,
        bootblockVersion,
        motherboardRevision,
        enableSTP,
        enableRebootKey,
        awcLocateUnit
    }
    STATUS    current
    DESCRIPTION
      "Standard information to support operation of an Aironet Access
       Point such as versions, system flags, and what features are
       enabled."
    ::= { awcVxGroups 1 }

bootconfigVxGroup  OBJECT-GROUP
    OBJECTS {
        bootconfigBootProtocol,
        bootconfigReadINI,
        bootconfigServerConfigTimeout,
        bootconfigMultOfferTimeout,
        bootconfigReqLeaseDuration,
        bootconfigMinLeaseDuration,
        bootconfigDev,
        bootconfigClientAddr,
        bootconfigHostAddr,
        bootconfigBootFile,
        bootconfigSubnetMask,
        bootconfigGateway,
        bootconfigHostName,
        bootconfigClientName,
        bootconfigNameServerPriority,
        bootconfigNameServer,
        bootconfigDomainName,
        bootconfigSntpServer,
        bootconfigSaveServerResponse,
        bootconfigCmdInvokeIniLoad,
        bootconfigCmdStatusIniLoad,
        bootconfigDhcpClassID,
        bootconfigFileServerAddr,
        bootconfigLogServerAddr,
        bootconfigBootCount,
        bootconfigDhcpClientIdType,
        bootconfigDhcpClientIdValue
    }
    STATUS    current
    DESCRIPTION
      "Standard information to support operation of the boot server."
    ::= { awcVxGroups 2 }

awcSerialDevGroup  OBJECT-GROUP
    OBJECTS {
        serialDevIndex,
        serialAdminStatus,
        serialOperStatus,
        serialBaud,
        serialParity,
        serialDataBits,
        serialStopBits,
        serialFlowControl,
        serialTerminalType,
        serialTerminalLines,
        serialTerminalColumns,
        serialDevFd
    }
    STATUS    current
    DESCRIPTION
      "Standard information to support configuration of serial ports."
    ::= { awcVxGroups 3 }

awcFtpGroup  OBJECT-GROUP
    OBJECTS {
        defaultFileServer,
        awcFileXferProtocol,
        awcFileXferUser,
        awcFileXferPassword,
        awcFileXferCmdInvokeFileLoad,
        awcFileXferCmdStatusFileLoad,
        awcFileXferCmdInvokeFileSave,
        awcFileXferCmdStatusFileSave,
        awcFileXferFileFirmwareSystem,
        awcFileXferFileFirmwareRadio0,
        awcFileXferFileWebUI,
        awcFileXferFileFpgaPcmcia,
        awcFileXferTftpPort,
        awcFileXferFtpDirectory,
        awcFileXferFilesFLASH,
        awcFileXferFileFirmwareRadio1
    }
    STATUS    current
    DESCRIPTION
      "Standard information to support configuration of the FTP
       protocol."
    ::= { awcVxGroups 4 }

awcIfTableGroup  OBJECT-GROUP
    OBJECTS {
        awcIfDefaultPhysAddress,
        awcIfPhysAddress,
        awcIfAdoptPrimaryIdentity,
        awcIfDefaultIpAddress,
        awcIfDefaultIpNetMask,
        awcIfIpAddress,
        awcIfIpNetMask,
        awcIfMSDUMaxLength,
        awcIfOutDiscardsCoS0,
        awcIfOutDiscardsCoS1,
        awcIfOutDiscardsCoS2,
        awcIfOutDiscardsCoS3,
        awcIfOutDiscardsCoS4,
        awcIfOutDiscardsCoS5,
        awcIfOutDiscardsCoS6,
        awcIfOutDiscardsCoS7
    }
    STATUS    current
    DESCRIPTION
      "Standard information to support configuration of network
       interfaces."
    ::= { awcVxGroups 5 }

awc802dot11Group  OBJECT-GROUP
    OBJECTS {
        awcDot11StationRole,
        awcDot11PowerManagementSubMode,
        awcDot11UseAWCExtensions,
        awcDot11AllowAssocBroadcastSSID,
        awcDot11PrivacyOptionImplementedMaxRate,
        awcDot11DesiredBSSLength,
        awcDot11EnetEncapsulationDefault,
        awcDot11ForceReqFirmwareVersion,
        awcDot11BridgeSpacing,
        awcDot11DesiredSSIDMaxAssociatedSTA,
        awcDot11DesiredSSIDNumAssociatedSTA,
        awcDot11AuxiliarySSIDLength,
        awcDot11MultipleSSIDPerBSSImplemented,
        awcDot11SymbolExtensionsImplemented,
        awcDot11SymbolExtensionsEnabled,
        awcDot11DesiredSSIDMicAlgorithm,
        awcDot11DesiredSSIDWEPKeyPermuteAlgorithm,
        awcDot11DesiredSSIDInfrastructureWGB,
        awcDot11DesiredSSIDDefaultPolId,
        awcDot11DesiredSSIDDefaultVlanId,
        awcDot11DesiredSSIDEnableProxyMobileIP,
        awcDot11InfrastructureSSID,
        awcDot11QBSSElementImplemented,
        awcDot11QBSSElementEnabled,
        awcDot11InfrastructureSSIDExclusive,
        awcDot11SendIGMPGeneralQuery,
        awcDot11AuthenticationRequireEAP,
        awcDot11AuthenticationDefaultUcastAllowedToGoTo,
        awcDot11WEPDefaultKeyIndex,
        awcDot11WEPDefaultKeyLen,
        awcDot11WEPDefaultKeyValue,
        awcDot11WEPDefaultKeyMaxIndex,
        awcDot11AllowEncrypted,
        awcDot11WEPKeyMaxLen,
        awcDot11LEAPUserName,
        awcDot11LEAPPassword,
        awcDot11DesiredBSSIndex,
        awcDot11DesiredBSS,
        awcDot11AuxSSIDIndex,
        awcDot11AuxSSID,
        awcDot11AuxSSIDMaxAssociatedSTA,
        awcDot11AuxSSIDNumAssociatedSTA,
        awcDot11AuxSSIDDefaultPolId,
        awcDot11AuxSSIDDefaultVlanId,
        awcDot11AuxSSIDEnableProxyMobileIP,
        awcDot11AuxSSIDAuthAlgEnable,
        awcDot11AuxSSIDAuthAlgRequireEAP,
        awcDot11AuxSSIDAuthAlgDefaultUcastAllowedToGoTo,
        awcDot11AssignedAID,
        awcDot11AssignedSTA,
        awcDot11FirmwareBootstrapVersion,
        awcDot11CurrentCarrierSet,
        awcDot11ModulationType,
        awcDot11PreambleType,
		awcDot11PHYType,
        awcDot11Compatible3100,
        awcDot11Compatible4500,
        awcDot11ChannelAutoImplemented,
        awcDot11ChannelAutoEnabled,
        awcDot11CurrentChannel,
        awcDot11SupportedDataRatesPrivacyIndex,
        awcDot11SupportedDataRatesPrivacyValue,
        awcDot11SupportedDataRatesPrivacyImplemented,
        awcDot11ChanSelectChannel,
        awcDot11ChanSelectEnable,
        awcDot11AssociatedStationCount,
        awcDot11AuthenticatedStationCount,
        awcDot11ReassociatedStationCount,
        awcDot11RoamedStationCount,
        awcDot11DeauthenticateCount,
        awcDot11DisassociateCount,
        awcDot11EncapPktsMMH,
        awcDot11DecapPktsMMH,
        awcDot11EncapErrorsMMH,
        awcDot11DecapErrorsMMH,
        awcDot11DecapExistsMMH,
        awcDot11DecapAccessMMH,
        awcDot11TxDeferEnergyCount,
        awcDot11RxMacCrcErrorCount,
        awcDot11SsidMismatchCount,
        awcDot11QoSCWmin,
        awcDot11QoSCWmax
    }
    STATUS    current
    DESCRIPTION
      "Standard information to support configuration of the 802.11
       protocol."
    ::= { awcVxGroups 6 }

awcUserMgrGroup  OBJECT-GROUP
    OBJECTS {
        userMgrUserIndex,
        userMgrUserName,
        userMgrPassword,
        userMgrCapabilities,
        userMgrStatus,
        enableUserMgr,
        allowBrowseWithoutLogin,
        protectLegalPage
    }
    STATUS    current
    DESCRIPTION
      "Standard information to support configuration of the User
       Manager."
    ::= { awcVxGroups 7 }

awcHttpdGroup  OBJECT-GROUP
    OBJECTS {
        defaultWebRoot,
        defaultHelpRoot,
        getWebUI,
        cmdInvokeGetWebUI,
        cmdStatusGetWebUI,
        awcHttpdPort,
        awcConsoleAutoApply
    }
    STATUS    current
    DESCRIPTION
      "Standard information to support configuration of the Web
       Server."
    ::= { awcVxGroups 8 }

awcDnsResGroup  OBJECT-GROUP
    OBJECTS {
        resolverDomain,
        resolverDomainSuffix,
        resolverDomainServerPriority,
        resolverDomainServer,
        defaultResolverDomain,
        defaultResolverDomainServerPriority,
        defaultResolverDomainServer
    }
    STATUS    current
    DESCRIPTION
      "Standard information to support configuration of the DNS
       Resolver."
    ::= { awcVxGroups 9 }

awcSnmpGroup  OBJECT-GROUP
    OBJECTS {
        snmpTrapDest,
        snmpTrapCommunity
    }
    STATUS    current
    DESCRIPTION
      "Standard information to support configuration of the SNMP
       protocol."
    ::= { awcVxGroups 10 }

awcSntpGroup  OBJECT-GROUP
    OBJECTS {
        defaultSntpServer,
        sntpServer
    }
    STATUS    current
    DESCRIPTION
      "Standard information to support configuration of the SNTP
       protocol."
    ::= { awcVxGroups 11 }

awcForwardTblGroup  OBJECT-GROUP
    OBJECTS {
        awcFtMcastAddr,
        awcFtDsHost,
        awcFtBridgeHost,
        awcFtClientSTA,
        awcFtClientSTASelf,
        awcFtBridge,
        awcFtBridgeSelf,
        awcFtRepeater,
        awcFtRepeaterSelf,
        awcFtAccessPoint,
        awcFtBridgeRoot,
        awcFtMaxNumEntries,
        awcFtTimeoutSecUnknown,
        awcFtTimeoutSecMcastAddr,
        awcFtTimeoutSecDsHost,
        awcFtTimeoutSecBridgeHost,
        awcFtTimeoutSecClientSTA,
        awcFtTimeoutSecBridge,
        awcFtTimeoutSecRepeater,
        awcFtTimeoutSecAccessPoint,
        awcFtTimeoutSecBridgeRoot,
        awcFtEnableAwcTpFdbTable,
        awcFtEnableMacAuthServer,
        awcFtRogueApAlertTimeout,
        awcFtEnableMacOrEapAuth,
        awcFtDot1dTpFdbTableEnable,
        awcTpFdbAddress,
        awcTpFdbClassID,
        awcTpFdbSrcPktsImmed,
        awcTpFdbSrcOctetsImmed,
        awcTpFdbSrcErrorPktsImmed,
        awcTpFdbSrcErrorOctetsImmed,
        awcTpFdbDestPktsImmed,
        awcTpFdbDestOctetsImmed,
        awcTpFdbDestErrorPktsImmed,
        awcTpFdbDestErrorOctetsImmed,
        awcTpFdbDestMaxRetryErrorsImmed,
        awcTpFdbIPv4Addr,
        awcTpFdbDdpAddress,
        awcTpFdbDdpSysName,
        awcTpFdbDdpProdDevID,
        awcTpFdbDdpRadioDevID,
        awcTpFdbDdpSwVerMajor,
        awcTpFdbDdpSwVerMinor,
        awcTpFdbDdpSwVerBeta,
        awcTpFdbDdpUptime,
        awcTpFdbDdpNumAnnounceSent,
        awcTpFdbDdpNumAssociated,
        awcTpFdbDdpLoad,
        awcTpFdbDdpDistFromDS,
        awcDot11TpFdbAddress,
        awcDot11TpFdbAID,
        awcDot11TpFdbClientState,
        awcDot11TpFdbTxShortRetries,
        awcDot11TpFdbTxLongRetries,
        awcDot11TpFdbLatestTxShortRetries,
        awcDot11TpFdbLatestTxLongRetries,
        awcDot11TpFdbRxWEPErrors,
        awcDot11TpFdbLatestRxSignalStrength,
        awcDot11TpFdbLatestRxSignalQuality,
        awcDot11TpFdbCapabilities,
        awcDot11TpFdbListenInterval,
        awcDot11TpFdbSupportedDataRates,
        awcDot11TpFdbPreferredTxRate,
        awcDot11TpFdbCurrentBSS,
        awcDot11TpFdbSSID,
        awcDot11TpFdbVlanId,
        awcDot1dTpPortDefaultUcastAllowedToGoTo,
        awcDot1dTpPortDefaultNUcastAllowedToGoTo,
        awcDot1dTpPortMaxNUcastPerSecond,
        awcDot1dTpPortDefaultInEthertypeFilterId,
        awcDot1dTpPortDefaultOutEthertypeFilterId,
        awcDot1dTpPortDefaultInIpProtoFilterId,
        awcDot1dTpPortDefaultOutIpProtoFilterId,
        awcDot1dTpPortDefaultInIpPortFilterId,
        awcDot1dTpPortDefaultOutIpPortFilterId,
        awcTpFdbAlertAddress,
        awcTpFdbFromAlertSrcPktsImmed,
        awcTpFdbFromAlertSrcOctetsImmed,
        awcTpFdbToAlertDestPktsImmed,
        awcTpFdbToAlertDestOctetsImmed,
        awcTpFdbAlertSentAlertTypePktsImmed,
        awcTpFdbAlertSentAlertTypeOctetsImmed,
        awcTpFdbAlertRcvdAlertTypePktsImmed,
        awcTpFdbAlertRcvdAlertTypeOctetsImmed
    }
    STATUS    current
    DESCRIPTION
      "Standard information to support configuration of the Forwarding
       Table."
    ::= { awcVxGroups 12 }

-- awcRipConfigGroup  OBJECT-GROUP
--     OBJECTS {
--     }
--     STATUS    current
--     DESCRIPTION
--       "Standard information to support configuration of the RIP
--        Protocol."
--     ::= { awcVxGroups 13 }

awcEventLogGroup  OBJECT-GROUP
    OBJECTS {
        awcEventOffsetGMT,
        awcEventUseDaylightSavingsTime,
        awcEventTimestampGMT,
        awcEventUptimeModifiedGMT,
        awcEventDisplayWallClockTime,
        awcEventDisplayUptimeAscending,
        awcEventDetailDefault,
        awcEventSeverityDispConsole,
        awcEventSeverityDispHtmlGUI,
        awcEventSeverityDispHtmlConsole,
        awcEventAlertSNMP,
        awcEventAlertSyslog,
        awcEventCntSeverityNULL,
        awcEventCntSeveritySilent,
        awcEventCntSeveritySystemFatal,
        awcEventCntSeverityProtocolFatal,
        awcEventCntSeverityPortFatal,
        awcEventCntSeveritySystemAlert,
        awcEventCntSeverityProtocolAlert,
        awcEventCntSeverityPortAlert,
        awcEventCntSeverityExternalAlert,
        awcEventCntSeveritySystemWarning,
        awcEventCntSeverityProtocolWarning,
        awcEventCntSeverityPortWarning,
        awcEventCntSeverityExternalWarning,
        awcEventCntSeveritySystemInfo,
        awcEventCntSeverityProtocolInfo,
        awcEventCntSeverityPortInfo,
        awcEventCntSeverityExternalInfo,
        awcEventDispSeverityNULL,
        awcEventDispSeveritySilent,
        awcEventDispSeveritySystemFatal,
        awcEventDispSeverityProtocolFatal,
        awcEventDispSeverityPortFatal,
        awcEventDispSeveritySystemAlert,
        awcEventDispSeverityProtocolAlert,
        awcEventDispSeverityPortAlert,
        awcEventDispSeverityExternalAlert,
        awcEventDispSeveritySystemWarning,
        awcEventDispSeverityProtocolWarning,
        awcEventDispSeverityPortWarning,
        awcEventDispSeverityExternalWarning,
        awcEventDispSeveritySystemInfo,
        awcEventDispSeverityProtocolInfo,
        awcEventDispSeverityPortInfo,
        awcEventDispSeverityExternalInfo,
        awcEventSyslogAddr,
        awcEventSyslogFacility,
        awcEventTraceStationSeverity,
        awcEventTraceLogSize,
        awcEventTracePacketLen,
        awcEventID,
        awcEventTime,
        awcEventSeverity,
        awcEventDescription,
        awcEventType,
        awcEventUseCiscoFormat,
        awcDot11AuthenticateFailDisposition,
        awcDot11DeauthenticateDisposition,
        awcDot11DisassociateDisposition
    }
    STATUS    current
    DESCRIPTION
      "Standard information to support operation of the Event Log."
    ::= { awcVxGroups 14 }

awcEtherMIBGroup  OBJECT-GROUP
    OBJECTS {
        awcEtherIfSpeedSelect,
        awcEtherDuplex,
        awcEtherCamSize,
        awcEtherEnableSwCam,
        awcEtherForcePortUnblock
    }
    STATUS    current
    DESCRIPTION
      "Standard information to support operation of the Ethernet
       Controller."
    ::= { awcVxGroups 15 }

awcPolicyGroupsGroup  OBJECT-GROUP
    OBJECTS {
        awcPolGrpName,
        awcPolGrpStatus,
        awcPolGrpInEthertypeFilterId,
        awcPolGrpOutEthertypeFilterId,
        awcPolGrpInIpProtoFilterId,
        awcPolGrpOutIpProtoFilterId,
        awcPolGrpInIpPortFilterId,
        awcPolGrpOutIpPortFilterId,
        awcDscpToCosMapEnable,
--      awcDscpToCosMapDscp,
        awcDscpToCosMapCos
    }
    STATUS    current
    DESCRIPTION
      "Standard information to support operation of Policy Groups."
    ::= { awcVxGroups 16 }

awcDdpIAPPGroup  OBJECT-GROUP
    OBJECTS {
        awcIappMcastIpAddr,
        awcIappPort,
        awcP802dot1XVersion
    }
    STATUS    current
    DESCRIPTION
      "Standard information to support operation of the DDP and IAPP
       protocols."
    ::= { awcVxGroups 17 }

 awcHotStandbyGroup  OBJECT-GROUP
     OBJECTS {
        awcHotStandbyMACAddr,
        awcHotStandbyPollingFrequency,
        awcHotStandbyPollingTimeOut,
        awcHotStandbyInHotStandby,
        awcHotStandbyState,
        awcHotStandbyStatus
     }
     STATUS    current
     DESCRIPTION
       "Standard information to support operation of an AP in the
        Hot Standby mode."
     ::= { awcVxGroups 18 }

awcAaaGroup  OBJECT-GROUP
    OBJECTS {
		awcAaaServerPriority,
		awcAaaServerProtocol,
		awcAaaServerName,
		awcAaaServerPort,
		awcAaaServerTimeout,
		awcAaaClientName,
		awcAaaServerSharedSecret,
		awcAaaServer8021xCapabilityEnabled,
		awcAaaServerMacAddrAuthEnabled,
        awcAaaServerAdminAuthEnabled,
		awcAaaServerMipAuthEnabled,
        awcAaaServerMaxRetransmission,
		awcAcctServerPriority,
		awcAcctServerProtocol,
		awcAcctServerName,
		awcAcctServerPort,
		awcAcctServerTimeout,
		awcAcctServerUpdateEnable,
		awcAcctServerUpdateDelay,
		awcAcctClientName,
		awcAcctSecureEnabled,
		awcAcctGeneralEnabled,
		awcAcctServerSharedSecret,
        awcAcctServerMaxRetransmission,
        awcAcctEnable,
        awcAcctStopDelayEnable,
        awcAcctStopDelayTime,
        awcAaaServerPrimaryReattemptPeriod,
        awcAaaServerDot1xAuthCurrent,
        awcAaaServerMacAddrAuthCurrent,
        awcAaaServerAdminAuthCurrent,
        awcAaaServerMipAuthCurrent
    }
    STATUS    current
    DESCRIPTION
      "Standard information to support configuration of RADIUS
       and TACACS+ client operation."
    ::= { awcVxGroups 19 }

awcProtocolFiltersGroup  OBJECT-GROUP
    OBJECTS {
        awcPfEtSetId,
        awcPfEtSetName,
        awcPfEtDefaultDisposition,
        awcPfEtDefaultUcastTimeToLive,
        awcPfEtDefaultNUcastTimeToLive,
        awcPfEtSetStatus,
        awcPfEtEthertype,
        awcPfEtDisposition,
        awcPfEtUserPriority,
        awcPfEtUcastTimeToLive,
        awcPfEtNUcastTimeToLive,
        awcPfEtAlert,
        awcPfEtStatus,
        awcPfIppSetId,
        awcPfIppSetName,
        awcPfIppDefaultDisposition,
        awcPfIppDefaultUcastTimeToLive,
        awcPfIppDefaultNUcastTimeToLive,
        awcPfIppSetStatus,
        awcPfIppIpProtocol,
        awcPfIppDisposition,
        awcPfIppUserPriority,
        awcPfIppUcastTimeToLive,
        awcPfIppNUcastTimeToLive,
        awcPfIppAlert,
        awcPfIppStatus,
        awcPfIptSetId,
        awcPfIptSetName,
        awcPfIptDefaultDisposition,
        awcPfIptDefaultUcastTimeToLive,
        awcPfIptDefaultNUcastTimeToLive,
        awcPfIptSetStatus,
        awcPfIptIpPort,
        awcPfIptDisposition,
        awcPfIptUserPriority,
        awcPfIptUcastTimeToLive,
        awcPfIptNUcastTimeToLive,
        awcPfIptAlert,
        awcPfIptStatus
    }
    STATUS    current
    DESCRIPTION
      "Standard information to support configuration of static protocol
       filters on the AP."
    ::= { awcVxGroups 20 }

awcMobileIpGroup OBJECT-GROUP
    OBJECTS {
        enableMobileIP,
        mipSAIpEnd,
        mipSAGroupSPI,
        mipSAGroupKey,
        mipSAStatus,
        awcmipDebug,
        awcprimAAP,
        awcsec1AAP,
        awcsec2AAP
    }
    STATUS    current
    DESCRIPTION
      "Information to support configuration of proxy mobile IP on the AP."
    ::= { awcVxGroups 21 }

awcEthernetLostGroup OBJECT-GROUP
    OBJECTS {
        awcEtherLostEthernetSeconds,
        awcEtherLostEthernetAction,
        awcEtherLostEthernetSSID
    }
    STATUS    current
    DESCRIPTION
      "Information to support AP in case Ethernet connection is lost."
    ::= { awcVxGroups 22 }

awc802dot11GroupExt1  OBJECT-GROUP
    OBJECTS {
        awcDot11NonRootMobility
    }
    STATUS  current
    DESCRIPTION
            "Configuration information for IEEE 802.11 radio driver
             and firmware."
    ::= { awcVxGroups 23 }

awcForwardTblGroupExt1  OBJECT-GROUP
    OBJECTS {
        awcFtEnableMcastMapping
    }
    STATUS    current
    DESCRIPTION
            "Information to support configuration of the Forwarding
             Table."
    ::= { awcVxGroups 24 }

awcTrapLogGroup NOTIFICATION-GROUP
    NOTIFICATIONS { awcTrapLog
    }
    STATUS  current
    DESCRIPTION
            "SNMP trap corresponding to an event with a Severity Level
             requiring Notify Disposition while awcEventAlertSNMP is
             true."
    ::= { awcVxGroups 100 }

-- ********************************************************************
-- *   End of units of conformance
-- ********************************************************************

-- ********************************************************************
-- *   End of awcVx MIB
-- ********************************************************************
END
