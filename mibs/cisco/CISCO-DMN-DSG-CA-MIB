--*****************************************************************
-- CISCO-DMN-DSG-CA.mib : Mib file for Conditional Access.
--
-- August 2010, TEL MIB Team
--
-- Copyright (c) 1999-2010 by Cisco Systems, Inc.
-- All rights reserved.
--*****************************************************************

CISCO-DMN-DSG-CA-MIB

DEFINITIONS ::= BEGIN

IMPORTS
    MODULE-IDENTITY,
    OBJECT-TYPE, Integer32
        FROM SNMPv2-SMI
      DisplayString
        FROM SNMPv2-TC
    OBJECT-GROUP, MODULE-COMPLIANCE
        FROM SNMPv2-CONF
    ciscoDSGUtilities
        FROM CISCO-DMN-DSG-ROOT-MIB;


ciscoDSGCA  MODULE-IDENTITY
    LAST-UPDATED  "201008300500Z" -- August 30 2010 05:00:00 GMT
    ORGANIZATION    "Cisco Systems, Inc."
    CONTACT-INFO
       "Cisco Systems, Inc.
        Customer Service
        Postal: 170 W Tasman Drive
        San Jose, CA 95134
        USA
        Tel: +1 800 553 NETS

        E-mail: cs-ipsla@cisco.com"
    DESCRIPTION    "Cisco Conditional Access MIB."

    REVISION       "201008300500Z"
    DESCRIPTION    "V01.00.04 2010-08-30
                    Updated for adherence to SNMPv2 format."

                    REVISION       "201006170600Z"
    DESCRIPTION    "V01.00.03 2010-06-17
                    The range of caIndex is corrected."

    REVISION       "201003220500Z"
    DESCRIPTION    "V01.00.02 2010-03-22
                    The Syntax of Unsigned32 MIB objects whose range
                    is within the range of Integer32, is updated to
                    Integer32."

    REVISION       "201002121200Z"
    DESCRIPTION    "V01.00.01 2010-02-12
                    The Syntax of read-only objects is updated to
                    DisplayString."

    REVISION       "200912071200Z"
    DESCRIPTION    "V01.00.00 2009-12-07
                    Initial Version."

    ::= { ciscoDSGUtilities 11 }

ca                         OBJECT IDENTIFIER ::= { ciscoDSGCA 1 }

--***********************************
-- CA Branch
--***********************************

caClearADP OBJECT-TYPE
     SYNTAX  INTEGER {
             writeOnly(1),
             yes(2)
             }
     MAX-ACCESS  read-write
     STATUS  current
     DESCRIPTION
        "Set this object to yes( 2 ) to clear Addressed Data
        Packet counters."
     ::= { ca 1 }

caTable                       OBJECT IDENTIFIER ::= { ciscoDSGCA 2 }

-- *************************************
-- CA Table Branch
-- *************************************

caADPTable OBJECT-TYPE
    SYNTAX  SEQUENCE OF CaADPEntry
    MAX-ACCESS  not-accessible
    STATUS  current
    DESCRIPTION
        "Conditional Access table"
    ::= { caTable 1 }

caADPEntry OBJECT-TYPE
    SYNTAX  CaADPEntry
    MAX-ACCESS  not-accessible
    STATUS  current
    DESCRIPTION
        "Conditional Access entry."
    INDEX   { caIndex }
    ::= { caADPTable 1 }

CaADPEntry ::=  SEQUENCE
{
    caIndex           Integer32,
    caUsrAddr         DisplayString,
    caISEVer          DisplayString,
    caADPEncPass      DisplayString,
    caADPEncTotal     DisplayString,
    caADPNonEncPass   DisplayString,
    caADPNonEncTotal  DisplayString
}

caIndex OBJECT-TYPE
    SYNTAX  Integer32(1..32)
    MAX-ACCESS  not-accessible
    STATUS  current
    DESCRIPTION
        "ISE (Internal Secure Element) Number."
    ::= { caADPEntry 1 }

caUsrAddr OBJECT-TYPE
    SYNTAX  DisplayString (SIZE(0..15))
    MAX-ACCESS  read-only
    STATUS  current
    DESCRIPTION
        "ISE ( Internal Secure Element ) User Address."
    ::= { caADPEntry 2 }

caISEVer OBJECT-TYPE
    SYNTAX  DisplayString (SIZE(0..8))
    MAX-ACCESS  read-only
    STATUS  current
    DESCRIPTION
        "ISE (Internal Secure Element) User Version."
    ::= { caADPEntry 3 }

caADPEncPass OBJECT-TYPE
    SYNTAX  DisplayString (SIZE(1..32))
    MAX-ACCESS  read-only
    STATUS  current
    DESCRIPTION
        "Number of Encrypted Addressable Data Packets passed.
        The range is from 0 to 4294967295."
    ::= { caADPEntry 4 }

caADPEncTotal OBJECT-TYPE
    SYNTAX  DisplayString (SIZE(1..32))
    MAX-ACCESS  read-only
    STATUS  current
    DESCRIPTION
        "Number of Encrypted Addressable Data Packets received.
        The range is from 0 to 4294967295."
    ::= { caADPEntry 5 }

caADPNonEncPass OBJECT-TYPE
    SYNTAX  DisplayString (SIZE(1..32))
    MAX-ACCESS  read-only
    STATUS  current
    DESCRIPTION
        "Number of Non-Encrypted Addressable Data Packets passed.
        The range is from 0 to 4294967295."
    ::= { caADPEntry 6 }


caADPNonEncTotal OBJECT-TYPE
     SYNTAX  DisplayString (SIZE(1..32))
     MAX-ACCESS  read-only
     STATUS  current
     DESCRIPTION
        "Number of Non-Encrypted Addressable Data Packets received.
        The range is from 0 to 4294967295."
     ::= { caADPEntry 7}

END
